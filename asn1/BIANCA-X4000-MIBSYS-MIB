-- This file is corresponding to Release 6.1.2.100 from 2001/09/26 00:00:00
-- (C)opyright 1991-1999 BinTec Communications AG, All Rights Reserved
-- $RCSfile: mibsysx4,v $ 
-- $Revision: 1.10 $ 
 
BIANCA-X4000-MIBSYS-MIB DEFINITIONS ::= BEGIN
 
        IMPORTS
		DisplayString FROM SNMPv2-TC
            Counter
                FROM RFC1155-SMI
 
            OBJECT-TYPE
                FROM RFC-1212
				sysDescr, sysName FROM RFC1213-MIB
				TRAP-TYPE FROM RFC-1215;

    org         OBJECT IDENTIFIER ::= { iso 3 }
    dod         OBJECT IDENTIFIER ::= { org 6 }
    internet    OBJECT IDENTIFIER ::= { dod 1 }
    private     OBJECT IDENTIFIER ::= { internet 4 }
    enterprises OBJECT IDENTIFIER ::= { private 1 }
    bintec      OBJECT IDENTIFIER ::= { enterprises 272 }
    bibo        OBJECT IDENTIFIER ::= { bintec 4 }
    sys		OBJECT IDENTIFIER ::= { bibo 17 }
    x4		OBJECT IDENTIFIER ::= {	sys 2 }
    sysX4Config OBJECT IDENTIFIER
        ::= { x4 1 }

    sysX4Traps  OBJECT IDENTIFIER ::= { x4 2 }

-- System Status and Configuration

	sysX4ConfigLcdBrightness OBJECT-TYPE
	    SYNTAX  INTEGER (0..3)
	    ACCESS  read-write
  	    STATUS  mandatory
            DESCRIPTION
		"This variable allows to control the brightness of the LCD 
		display. Lower values mean less, higher values mean
		more brightness. Zero means no brightness."
 	::= { sysX4Config 1 }

	sysX4ConfigLcdContrast OBJECT-TYPE
	    SYNTAX  INTEGER (0..10)
	    ACCESS  read-write
  	    STATUS  mandatory
            DESCRIPTION
		"This variable allows to control the contrast of the LCD 
		display. Lower values mean less, higher values mean
		more contrast. Zero means factory settings."
 	::= { sysX4Config 2 }

	sysX4ConfigLcdConfigure OBJECT-TYPE
	    SYNTAX  INTEGER { off(1), on(2) }
	    ACCESS  read-write
  	    STATUS  mandatory
            DESCRIPTION
	        "This variable determines whether it is possible to configure
		 the brick by using the LCD display and the buttons."
 	::= { sysX4Config 3 }

	sysX4ConfigLcdPin OBJECT-TYPE
	    SYNTAX  DisplayString (SIZE (4..4))
	    ACCESS  read-write
	    STATUS  mandatory
	    DESCRIPTION
		"The PIN is the personal identification number that is needed
		 for authorisation for display configurations.
		 It consists solely of digits and must be 4 
		 characters long.
		 Default Value is '0000'."
 	::= { sysX4Config 4 }

	sysX4ConfigLcdIdleTimer OBJECT-TYPE
	    SYNTAX  INTEGER (0..5)
	    ACCESS  read-write
	    STATUS  mandatory
	    DESCRIPTION
		"After this time the display screen changes to default screen.
		 Default Value is 5. If this value is set to 0, change to
		 defaultscreen is disabled"
 	::= { sysX4Config 5 }

	sysX4ConfigLcdDefaultScreen OBJECT-TYPE
	    SYNTAX  DisplayString (SIZE (0..8))
	    ACCESS  read-write
	    STATUS  mandatory
	    DESCRIPTION
		"This screen will be displayed after the LcdIdleTimer has
		elapsed.
		 Default Value is MainMenu."
 	::= { sysX4Config 6 }

	sysX4ConfigLcdLanguage OBJECT-TYPE
	    SYNTAX  DisplayString (SIZE (0..20))
	    ACCESS  read-write
	    STATUS  mandatory
	    DESCRIPTION
		"Choose your display language."
 	::= { sysX4Config 7 }

	sysX4ConfigTempUnit OBJECT-TYPE
	    SYNTAX  INTEGER { celsius(1), fahrenheit(2) }
	    ACCESS  read-only
  	    STATUS  mandatory
            DESCRIPTION
	        "This variable defines the unit of sysX4Config*Temp, 
	         either Celsius or Fahrenheit."
      	::= { sysX4Config 8 }

	sysX4ConfigMainTemp OBJECT-TYPE
	    SYNTAX  INTEGER (-1000..1000)
	    ACCESS  read-only
  	    STATUS  mandatory
            DESCRIPTION
		"This variable shows the actual main board temperature measured
		 in the units Fahrenheit or Celsius."
 	::= { sysX4Config 9 }

	sysX4ConfigMainTempAlarmThreshold OBJECT-TYPE
	    SYNTAX  INTEGER (-1000..1000)
	    ACCESS  read-write
  	    STATUS  mandatory

            DESCRIPTION
                "system mainboard temperature threshold."
       	::= { sysX4Config 10 }

	sysX4ConfigMainTempAlarmTrap OBJECT-TYPE
	    SYNTAX  INTEGER { normal(1), critical(2) }
	    ACCESS  read-only
  	    STATUS  mandatory

            DESCRIPTION
                "If the system temperature raises above the threshold,
                 a alarm trap is generated every 60 seconds."
       	::= { sysX4Config 11 }

	sysX4ConfigMod1Temp OBJECT-TYPE
	    SYNTAX  INTEGER (-1000..1000)
	    ACCESS  read-only
  	    STATUS  mandatory
            DESCRIPTION
		"This variable shows the actual module sensor1 temperature
		in the units Fahrenheit or Celsius."
 	::= { sysX4Config 12 }

	sysX4ConfigMod1TempAlarmThreshold OBJECT-TYPE
	    SYNTAX  INTEGER (-1000..1000)
	    ACCESS  read-write
  	    STATUS  mandatory

            DESCRIPTION
                "actual module sensor1 temperature threshold."
       	::= { sysX4Config 13 }

	sysX4ConfigMod1TempAlarmTrap OBJECT-TYPE
	    SYNTAX  INTEGER { normal(1), critical(2) }
	    ACCESS  read-only
  	    STATUS  mandatory

            DESCRIPTION
	   "If the actual module sensor1 temperature raises above the threshold,
	    a alarm trap is generated every 60 seconds."
       	::= { sysX4Config 14 }


	sysX4ConfigMod2Temp OBJECT-TYPE
	    SYNTAX  INTEGER (-1000..1000)
	    ACCESS  read-only
  	    STATUS  mandatory
            DESCRIPTION
		"This variable shows the actual module sensor2 temperature
		in the units Fahrenheit or Celsius."
 	::= { sysX4Config 15 }

	sysX4ConfigMod2TempAlarmThreshold OBJECT-TYPE
	    SYNTAX  INTEGER (-1000..1000)
	    ACCESS  read-write
  	    STATUS  mandatory

            DESCRIPTION
                "actual module sensor2 temperature threshold."
       	::= { sysX4Config 16 }

	sysX4ConfigMod2TempAlarmTrap OBJECT-TYPE
	    SYNTAX  INTEGER { normal(1), critical(2) }
	    ACCESS  read-only
  	    STATUS  mandatory

            DESCRIPTION
	   "If the actual module sensor2 temperature raises above the threshold,
	    a alarm trap is generated every 60 seconds."
       	::= { sysX4Config 17 }

---
--- System Status and Configuration Traps
---

	sysX4TrapMainTempCritical TRAP-TYPE
	    ENTERPRISE    sysX4Traps
	    VARIABLES     {
	        sysDescr,
	        sysName,
	        sysX4ConfigTempUnit,
 	        sysX4ConfigMainTemp,
	        sysX4ConfigMainTempAlarmThreshold,
	        sysX4ConfigMod1Temp,
	        sysX4ConfigMod2Temp
	    }
	    DESCRIPTION  "This trap signifies that the system board temperature
	                   raises above the critical alarm-threshold"
	::= 1

	sysX4TrapMainTempOk TRAP-TYPE
	    ENTERPRISE    sysX4Traps
	    VARIABLES     {
	        sysDescr,
                sysName,
	        sysX4ConfigTempUnit,
	        sysX4ConfigMainTemp,
	        sysX4ConfigMainTempAlarmThreshold,
	        sysX4ConfigMod1Temp,
	        sysX4ConfigMod2Temp
	    }
	    DESCRIPTION   "Normal system board temperature has been restored."
	::= 2

	sysX4TrapMod1TempCritical TRAP-TYPE
	    ENTERPRISE    sysX4Traps
	    VARIABLES     {
	        sysDescr,
                sysName,
	        sysX4ConfigTempUnit,
	        sysX4ConfigMainTemp,
	        sysX4ConfigMod1Temp,
	        sysX4ConfigMod1TempAlarmThreshold,
	        sysX4ConfigMod2Temp
	    }
	    DESCRIPTION "This trap signifies that the actual module (sensor 1)
	                 temperature raises above the critical alarm-threshold"
	::= 3

	sysX4TrapMod1Temp1Ok TRAP-TYPE
	    ENTERPRISE    sysX4Traps
	    VARIABLES     {
	        sysDescr,
                sysName,
	        sysX4ConfigTempUnit,
	        sysX4ConfigMainTemp,
	        sysX4ConfigMod1Temp,
	        sysX4ConfigMod1TempAlarmThreshold,
	        sysX4ConfigMod2Temp
	    }
	    DESCRIPTION  "Normal temperature of actual module (sensor 1)
	                  has been restored."
	::= 4

	sysX4TrapMod2TempCritical TRAP-TYPE
	    ENTERPRISE    sysX4Traps
	    VARIABLES     {
	        sysDescr,
                sysName,
	        sysX4ConfigTempUnit,
	        sysX4ConfigMainTemp,
	        sysX4ConfigMod1Temp,
	        sysX4ConfigMod2Temp,
	        sysX4ConfigMod2TempAlarmThreshold
	    }
	    DESCRIPTION "This trap signifies that the actual module (sensor 2)
	                 temperature raises above the critical alarm-threshold"
	::= 5

	sysX4TrapMod2TempOk TRAP-TYPE
	    ENTERPRISE    sysX4Traps
	    VARIABLES     {
	        sysDescr,
                sysName,
	        sysX4ConfigTempUnit,
	        sysX4ConfigMainTemp,
	        sysX4ConfigMod1Temp,
	        sysX4ConfigMod2Temp,
	        sysX4ConfigMod2TempAlarmThreshold
	    }
	    DESCRIPTION  "Normal temperature of actual module (sensor 2)
	                  has been restored."
   ::= 6

END
