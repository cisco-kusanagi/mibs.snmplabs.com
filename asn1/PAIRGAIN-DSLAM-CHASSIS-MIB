------------------------------------------------------------
-- $Workfile:   pgdschas.my  $
--   pg chassis mid
-- $Archive:   S:\dslam\swdev\snmp14.2.1.16\mibs\common\pgdschas.myv  $
-- $Revision:   1.28  $
-- $Date:   Jun 13 2000 16:03:52  $
-- $Author:   singha  $
------------------------------------------------------------

-- Release 1.01
-- Revision 7/29/99
-- HISTORY
-- Author       Date      Description
-- =========  ========    =========================
-- R. Wada	   7-29-99    Added new entry for SDSL Frame Card
-- R. Wada     4-12-2000  Added new entry for SDSL Cell Card
-- Printed
-- Copyright 1998 PairGain Technologies, Inc.  All Rights
-- Reserved.  Reproduction of this document is authorized on
-- condition that the foregoing copyright notice is included.
-- This PairGain SNMP Management Information Base Specification
-- (Specification) embodies PairGain's confidential and
-- proprietary intellectual property.  PairGain retains all
-- title and ownership in the Specification, including any
-- revisions.
--
-- It is PairGain's intent to encourage the widespread use of
-- this Specification in connection with the management of
-- PairGain products. PairGain grants vendors, end-users,
-- and other interested parties a non-exclusive license to
-- use this Specification in connection with the management
-- of PairGain products.
--
-- This Specification is supplied "AS IS," and PairGain makes
-- no warranty, either expressed or implied, as to the use,
-- operation, condition, or performance of the Specification.


PAIRGAIN-DSLAM-CHASSIS-MIB DEFINITIONS ::= BEGIN

-- SECTION 1: Top Level Definitions

IMPORTS
	TEXTUAL-CONVENTION FROM SNMPv2-TC
	Counter, TimeTicks
	    FROM RFC1155-SMI
	OBJECT-TYPE
	    FROM RFC-1212
	pgDSLAMChassis
	    FROM PAIRGAIN-COMMON-HD-MIB;


-- Textual Conventions

    TimeSeconds ::= TEXTUAL-CONVENTION
    STATUS       current
    DESCRIPTION
            "The value of the pgDSLAMCalendarTime object at which a specific
            occurrence happened.  The specific occurrence must be
            defined in the description of any object defined using this
            type."
    SYNTAX       INTEGER(0..4294967295)

    DisplayString ::= OCTET STRING

    PgDSLAMChassisType ::=
	INTEGER {
		unknown(1),        -- unknow type
		dslam-co(2),
                dslam-as5(3),
                dslam-as3(4)
	}

    PgDSLAMUnitType ::=
	INTEGER {
		                unknown(1),

                                -- Management Card
		                management(2),

                                -- Channel Cards
                                -- Values 40 to 49 are reserved for channel cards
                                adsl-cap-frame-8(3), -- 8 port RADSL CAP FRAME
                                adsl-dmt-frame-8(4),  -- 8 port RADSL DMT FRAME
                                adsl-cap-frame-12(5), -- 12 port RADSL CAP FRAME
                                adsl-dmt-frame-12(6), -- 12 port RADSL DMT FRAME
                                hdsl-frame-16(7), -- 16 port HDSL FRAME
                                hdsl-frame-24(8), -- 24 port HDSL FRAME
                                adsl-cap-cell-8(9), -- 8 port RADSL CAP CELL
                                adsl-dmt-cell-8(10),  -- 8 port RADSL DMT CELL
                                adsl-cap-cell-12(11), -- 12 port RADSL CAP CELL
                                adsl-dmt-cell-12(12), -- 12 port RADSL DMT CELL
                                atm-oc3-channel-6(13),  -- 6 port OC-3C ATM
                                t1-circuit-emul-12(14), -- 12 port T1 CIRCUIT EMULATION
                                e1-circuit-emul-12(15), -- 12 port E1 CIRCUIT EMULATION
                                ds3-circuit-emul-6(16), -- 6 port DS3 CIRCUIT EMULATION
                                e3-circuit-emul-6(17), -- 6 port E3 CIRCUIT EMULATION
                                t1-higain-lu-12(18), -- 12 port T1 HIGAIN/CAMPUS LU
                                atm-oc3-channel(40), -- 2 ports OC-3C ATM
                                t1-dsx1-channel(41), -- 8 ports T1 DSX1 IMUX CHANNEL
                                e1-atm-imux-8-channel(42), -- 8 ports E1 ATM IMUX
                                sdsl-frame-16(43), -- 16 port SDSL FRAME
                                sdsl-frame-24(44), -- 24 port SDSL FRAME
                                ds3-atm-channel(45), -- DS-3 ATM
								idsl-frame-24(46), -- 24 port IDSL FRAME
								sdsl-cell-24(47), -- 24 port SDSL CELL
                                -- Line Cards
                                -- Values 50 to 59 are reserved for line cards
                                atm-oc3-line(19), -- OC-3C ATM
                                ds3-atm-line(20), -- DS-3 ATM
                                e3-atm-line(21), -- E3 ATM
                                ds3-fr-line(22), -- DS-3 FR
                                e3-fr-line(23), -- E3 FR
                                ethernet-10-100(24), -- 10/100BASE-T
                                t1-atm-imux-6(25), -- 6 ports T1 ATM IMUX
                                e1-atm-imux-6(26), -- 6 ports E1 ATM IMUX
                                t1-fr-imux-6(27), -- 6 ports T1 FR IMUX
                                e1-fr-imux-6(28), -- 6 ports E1 FR IMUX
                                atm-oc12-line(29), -- OC-12C ATM
                                hissi-line(30), -- HISSI
                                t1-dsx1-line(50), -- 8 ports T1 DS1 IMUX LINE
                                e1-atm-imux-8-line(51), -- 8 ports E1 ATM IMUX
                                t1-dsx1-linemgmt(52), -- 8 port T1 MANAGEMENT
                                pot-splitter(53), -- POT Splitter card

                                -- Test Cards
                                -- Values 60 to 69 are reserved for test cards
                                adsl-cap-frame-test(31), -- RADSL CAP FRAME TEST
                                adsl-dmt-frame-test(32), -- RADSL DMT FRAME TEST
                                sdsl-frame-test(33), -- SDSL FRAME TEST
                                adsl-cap-cell-test(34), -- RADSL CAP CELL TEST
                                adsl-dmt-cell-test(35), -- RADSL DMT CELL TEST
                                sdsl-cell-test(36), -- SDSL CELL TEST
                                circuit-emul-test(37), -- CIRCUIT EMULATION TEST
                                fr-line-test(38), -- TEST FRAME
                                cell-line-test(39) -- TEST CELL
	}

-- SECTION 2: PairGain DSLAM Chassis Group

pgDSLAMChassisType OBJECT-TYPE
	SYNTAX  PgDSLAMChassisType
	ACCESS  read-only
	STATUS  mandatory
	DESCRIPTION
		"The chassis type."
	::= { pgDSLAMChassis 1 }

pgDSLAMChassisPsStatus OBJECT-TYPE
	SYNTAX  INTEGER {
		other(1),               -- unknown power supply status
		oneFail(2),             -- one power supply failed
		bothFail(3),            -- both power supplies failed
		ok(4)                   -- power supplies ok
	}
	ACCESS  read-only
	STATUS  mandatory
	DESCRIPTION
		"The chassis power supply status."
	::= { pgDSLAMChassis 2 }

pgDSLAMChassisFanStatus OBJECT-TYPE
	SYNTAX  INTEGER {
		other(1),       -- unknown fan status or no fans
		fail(2),        -- fans failed
		ok(3),          -- fans are running
		hightemp(4)     -- Chassis's temperature too high
	}
	ACCESS  read-only
	STATUS  mandatory
	DESCRIPTION
		"The status of the chassis cooling fan."
	::= { pgDSLAMChassis 3 }

-- PairGain DSLAM Chassis Slot Configuration Table

pgDSLAMSlotConfigTable OBJECT-TYPE
	SYNTAX  SEQUENCE OF PgDSLAMSlotConfigEntry
	ACCESS  not-accessible
	STATUS  mandatory
	DESCRIPTION
		"The DSLAM chassis slot configuration table."
	::= { pgDSLAMChassis 4 }

pgDSLAMSlotConfigEntry OBJECT-TYPE
	SYNTAX  PgDSLAMSlotConfigEntry
	ACCESS  not-accessible
	STATUS  mandatory
	DESCRIPTION
		"Entry in the DSLAM slot configuration table."
	INDEX   { pgDSLAMSlotNumber }
	::= { pgDSLAMSlotConfigTable 1 }

PgDSLAMSlotConfigEntry ::= SEQUENCE {
	pgDSLAMSlotNumber
		INTEGER,
	pgDSLAMSlotUnitType
		PgDSLAMUnitType,
	pgDSLAMSlotUnitSerialNo
		DisplayString,
	pgDSLAMSlotUnitDescr
		DisplayString,
	pgDSLAMSlotHwVer
		DisplayString(SIZE(10)),
	pgDSLAMSlotFwVer
		DisplayString(SIZE(10)),
	pgDSLAMSlotSwVer
		DisplayString(SIZE(10)),
	pgDSLAMSlotBoardReset
		INTEGER,
	pgDSLAMSlotNmCntlStatus
		INTEGER,
	pgDSLAMSlotIfNumber
                INTEGER,
        pgDSLAMSlotHwID
                DisplayString(SIZE(32))
}

pgDSLAMSlotNumber OBJECT-TYPE
	SYNTAX  INTEGER (1..64)
	ACCESS  read-only
	STATUS  mandatory
	DESCRIPTION
		"The chassis slot number. Valid entries are 1-21.
		The slots are numbered from left to right
		from 1-21.  The DMU is always located in slot 1"
	::= { pgDSLAMSlotConfigEntry 1 }

pgDSLAMSlotUnitType OBJECT-TYPE
	SYNTAX  PgDSLAMUnitType
	ACCESS  read-only
	STATUS  mandatory
	DESCRIPTION
		"The type of Unit this entry represents."
	::= { pgDSLAMSlotConfigEntry 2 }

pgDSLAMSlotUnitSerialNo OBJECT-TYPE
        SYNTAX  DisplayString (SIZE (12))
	ACCESS  read-only
	STATUS  mandatory
	DESCRIPTION
		"Serial number of the Unit."
	::= { pgDSLAMSlotConfigEntry 3 }

pgDSLAMSlotUnitDescr OBJECT-TYPE
	SYNTAX  DisplayString (SIZE(0..128))
	ACCESS  read-write
	STATUS  mandatory
	DESCRIPTION
		"Unit description."
	::= { pgDSLAMSlotConfigEntry 4 }

pgDSLAMSlotHwVer OBJECT-TYPE
	SYNTAX  DisplayString(SIZE(10))
	ACCESS  read-only
	STATUS  mandatory
	DESCRIPTION
		"The hardware revision of the board."
	::= { pgDSLAMSlotConfigEntry 5 }

pgDSLAMSlotFwVer OBJECT-TYPE
	SYNTAX  DisplayString(SIZE(10))
	ACCESS  read-only
	STATUS  mandatory
	DESCRIPTION
		"The firmware revision of the board."
	::= { pgDSLAMSlotConfigEntry 6 }

pgDSLAMSlotSwVer OBJECT-TYPE
	SYNTAX  DisplayString(SIZE(10))
	ACCESS  read-only
	STATUS  mandatory
	DESCRIPTION
		"The software revision of the board."
	::= { pgDSLAMSlotConfigEntry 7 }

pgDSLAMSlotBoardReset OBJECT-TYPE
	SYNTAX  INTEGER {
		noReset(1),    -- not resetting
		reset(2)       -- resetting
		}
	ACCESS  read-write
	STATUS  mandatory
	DESCRIPTION
		"This indicates the reset state of the board.  Writing with
		the value reset (2) will reset the board."
	::= { pgDSLAMSlotConfigEntry 8}

pgDSLAMSlotNmCntlStatus OBJECT-TYPE
	SYNTAX  INTEGER {
		other(1),        -- unknown
		nmControl(2),    -- board under network mgt control
		testControl(3),  -- board under test
		notNmControl(4)  -- board not under network mgt control
		}
	ACCESS  read-only
	STATUS  mandatory
	DESCRIPTION
		"Tells whether the board is under network management control."
	::= { pgDSLAMSlotConfigEntry 9 }

pgDSLAMSlotIfNumber OBJECT-TYPE
	SYNTAX  INTEGER
	ACCESS  read-only
	STATUS  mandatory
	DESCRIPTION
		"The number of MIB-II ifEntry maintained by this board."
	::= { pgDSLAMSlotConfigEntry 10 }

pgDSLAMSlotHwID OBJECT-TYPE
        SYNTAX  DisplayString(SIZE(32))
	ACCESS  read-only
	STATUS  mandatory
	DESCRIPTION
                "The hardware identification number of the board."
        ::= { pgDSLAMSlotConfigEntry 11 }

-- Configuration Change Management

pgDSLAMConfigChangeCnts OBJECT-TYPE
	SYNTAX  Counter
	ACCESS  read-only
	STATUS  mandatory
	DESCRIPTION
		"The number of times a physical configuration change has
		taken place in the chassis such as the insertion/deinsertion
		of a Unit.  Any events causing a change in the pgDSLAMSlotConfigTable
		or the pgDSLAMCommonBoardTable should cause this counter to be
		incremented."
	::= { pgDSLAMChassis 5 }

pgDSLAMConfigLastChange OBJECT-TYPE
	SYNTAX  TimeTicks
	ACCESS  read-only
	STATUS  mandatory
	DESCRIPTION
		"The value of sysUpTime at the time the most recent physical
		configuration change occurred."
	::= { pgDSLAMChassis 6 }

-- Alarm Status Table

pgDSLAMChassisAlarmStatTable  OBJECT-TYPE
	SYNTAX    SEQUENCE OF DSLAMAlarmStatEntry
	ACCESS    not-accessible
	STATUS    mandatory
	DESCRIPTION
	"This table maintains the latest alarm status provided by each channel or line
	card in the chassis.  There is only one alarm status entry per card. That means
	that the subsequent alarm status generated by the same card will overwrite the
	previous status stored in the correspondent entry."
	::= { pgDSLAMChassis 7 }

dslamAlarmStatEntry  OBJECT-TYPE
	SYNTAX    DSLAMAlarmStatEntry
	ACCESS    not-accessible
	STATUS    mandatory
	DESCRIPTION
	"An entry contains the latest alarm status for a channel or line card."
	INDEX { pgDSLAMAlarmCardID }
	::= { pgDSLAMChassisAlarmStatTable 1}

DSLAMAlarmStatEntry ::= SEQUENCE {
	pgDSLAMAlarmCardID       INTEGER,
	pgDSLAMAlarmPortNum      INTEGER,
	pgDSLAMAlarmStatSeverity INTEGER,
	pgDSLAMAlarmTrapOID      OBJECT IDENTIFIER
	}

pgDSLAMAlarmCardID OBJECT-TYPE
	SYNTAX  INTEGER (1..64)
	ACCESS  read-only
	STATUS  mandatory
	DESCRIPTION
	"The slot containing the card which generates this alarm."
	::= { dslamAlarmStatEntry 1 }

pgDSLAMAlarmPortNum OBJECT-TYPE
	SYNTAX  INTEGER (1..32)
	ACCESS  read-only
	STATUS  mandatory
	DESCRIPTION
	"Together with the pgDSLAMAlarmCardID this object uniquely identify a port which
	an alarm condition was detected."
	::= { dslamAlarmStatEntry 2 }

pgDSLAMAlarmStatSeverity OBJECT-TYPE
	SYNTAX  INTEGER {
	none(1),
	minor(2),
	major(3),
	critical(4)
	}
	ACCESS  read-only
	STATUS  mandatory
	DESCRIPTION
	"The severity of the alarm reported by the channel or line card."
	::= { dslamAlarmStatEntry 3 }

pgDSLAMAlarmTrapOID OBJECT-TYPE
	SYNTAX OBJECT IDENTIFIER
	ACCESS  read-only
	STATUS  mandatory
	DESCRIPTION
	"The value of this object uniquely identify the type of alarm generated by the
	channel or line card.  It is the same trap OID used to generate the SNMP trap
	when the alarm threshold value was exceeded."
	::= { dslamAlarmStatEntry 4 }

pgDSLAMChassisLEDStat OBJECT-TYPE
	SYNTAX  OCTET STRING (SIZE (2))
	ACCESS  read-only
	STATUS  mandatory
	DESCRIPTION
		"The octet within the value of this object specifies a set of
             eight LEDs. Within the octet, each bit represents the status
             of a LED on the front panel. Following is the bit-map:
             Lower octet:
             bit 0 : critical alarm LED
             bit 1 : major alarm LED
             bit 2 : minor alarm LED
             bit 3 : power minor alarm LED
             bit 4 : input power 1
             bit 5 : input power 2
             bit 6 : fuse alarm 1
             bit 7 : fuse alarm 2

             Upper octet:
             bit 0 : Alarm Cut Off
             bit 1 : abnormal
             bit 2 : fault
             bit 3 : external alarm
             bit 4 : fan alarm 1
             bit 5 : fan alarm 2
             bit 6 : fan alarm 3
             bit 7 : fan alarm 4

             If a bit has a value of '1' then the correspondant LED is
             on and '0' is off."
	::= { pgDSLAMChassis 8 }

pgDSLAMCalendarTime OBJECT-TYPE
	SYNTAX  Counter
	ACCESS  read-write
	STATUS  mandatory
	DESCRIPTION
            "The current date and time indicated by seconds
             since 1900.1.1 00:00:00
	    "
	::= { pgDSLAMChassis 9 }

-- Slot Status Table

pgDSLAMSlotStatTable  OBJECT-TYPE
	SYNTAX    SEQUENCE OF DSLAMSLOTStatEntry
	ACCESS    not-accessible
	STATUS    mandatory
	DESCRIPTION
	"The state of slots within this chassis."
	::= { pgDSLAMChassis 10 }

pgDSLAMSlotStatEntry  OBJECT-TYPE
	SYNTAX    DSLAMSLOTStatEntry
	ACCESS    not-accessible
	STATUS    mandatory
	DESCRIPTION
	"An entry contains the information of a specified slot."
	INDEX { pgDSLAMSlotID }
	::= { pgDSLAMSlotStatTable 1}

DSLAMSLOTStatEntry ::= SEQUENCE {
	pgDSLAMSlotID       INTEGER,
	pgDSLAMSlotStatus   INTEGER
	}

pgDSLAMSlotID OBJECT-TYPE
	SYNTAX  INTEGER (1..64)
	ACCESS  read-only
	STATUS  mandatory
	DESCRIPTION
	"The slot number."
	::= { pgDSLAMSlotStatEntry 1 }

pgDSLAMSlotStatus OBJECT-TYPE
	SYNTAX  INTEGER {
	unknown(1),
	up(2),
	down(3),
	notPresent(4)
	}
	ACCESS  read-only
	STATUS  mandatory
	DESCRIPTION
	"The status of the specified slot.
       unknown - uncertain state.
       up - the card plugged in this slot is up and running.
       down - the card is not functioning.
       notPresent - there is no card plugged in this slot."
	::= { pgDSLAMSlotStatEntry 2 }

pgDSLAMChassisTemperature OBJECT-TYPE
	SYNTAX  INTEGER
	ACCESS  read-only
	STATUS  mandatory
	DESCRIPTION
		"The current temperature inside the chassis in Centigrade."

	::= { pgDSLAMChassis 11 }

pgDSLAMFileDirectoryTable  OBJECT-TYPE
	SYNTAX    SEQUENCE OF PgDSLAMFileDirectoryEntry
	ACCESS    not-accessible
	STATUS    mandatory
	DESCRIPTION
	"The file directory for each slot."
	::= { pgDSLAMChassis 12 }

pgDSLAMFileDirectoryEntry  OBJECT-TYPE
	SYNTAX    PgDSLAMFileDirectoryEntry
	ACCESS    not-accessible
	STATUS    mandatory
	DESCRIPTION
	"An entry contains the file directory of a specified slot."
        INDEX { pgDSLAMFileDirectorySlotID }
	::= { pgDSLAMFileDirectoryTable 1}

PgDSLAMFileDirectoryEntry ::= SEQUENCE {
	pgDSLAMFileDirectorySlotID   INTEGER,
	pgDSLAMFileDirectory         OCTET STRING (SIZE (0..2047))
	}

pgDSLAMFileDirectorySlotID OBJECT-TYPE
	SYNTAX  INTEGER (1..64)
	ACCESS  read-only
	STATUS  mandatory
	DESCRIPTION
	"The slot number for the file directory."
	::= { pgDSLAMFileDirectoryEntry 1 }

pgDSLAMFileDirectory OBJECT-TYPE
	SYNTAX  OCTET STRING (SIZE (0..2047))
	ACCESS  read-only
	STATUS  mandatory
	DESCRIPTION
	"The file directory."
	::= { pgDSLAMFileDirectoryEntry 2 }

pgDSLAMFsSlotID OBJECT-TYPE
	SYNTAX  INTEGER (1..21)
	ACCESS  read-write
	STATUS  mandatory
	DESCRIPTION
	"The slot number for the file operation."
	::= { pgDSLAMChassis 13 }

pgDSLAMFsFileName OBJECT-TYPE
	SYNTAX  OCTET STRING (SIZE (0..256))
	ACCESS  read-write
	STATUS  mandatory
	DESCRIPTION
	"The file name for the file operation."
	::= { pgDSLAMChassis 14 }

pgDSLAMFsAction OBJECT-TYPE
	SYNTAX  INTEGER {
	unknown(1),
	delete(2)
	}
	ACCESS  read-write
	STATUS  mandatory
	DESCRIPTION
	"The action for the file operation."
	::= { pgDSLAMChassis 15 }

pgDSLAMCalendarTimeOs OBJECT-TYPE
	SYNTAX  OCTET STRING (SIZE (7))
	ACCESS  read-write
	STATUS  mandatory
	DESCRIPTION
            "A date-time format.

            field  octets  contents                  range
            -----  ------  --------                  -----
              1      1-2   year                      0..65536
              2       3    month                     1..12
              3       4    day                       1..31
              4       5    hour                      0..23
              5       6    minutes                   0..59
              6       7    seconds                   0..60

            For example, Tuesday May 26, 1992 at 1:30:15 PM would be
            displayed as: 1992-5-26,13:30:15"

	::= { pgDSLAMChassis 16 }

pgDSLAMAllSlotLED OBJECT-TYPE
	SYNTAX  OCTET STRING (SIZE (0..568))
	ACCESS  read-only
	STATUS  mandatory
	DESCRIPTION
	"This object reflects the current status of all the front panel LED's
	on all the slot of the Avidia Shelf.
	The Semantics of the octet-string is as described below.
	It is set of following structure.
	First  Octet  - SlotID
	Second Octet  - CardType    PgDSLAMUnitType
	Third  Octet  - Number of Bytes Used by the Slot LED Status.
	Fourth Octet  - Status of LED for port1
	Fifth  Octet  - Status of LED for port2
	....
	....
	till depending on the Number of port on the card.
	LED Status in encoded as a bit map described below
	Bits 0-3 represent the State (0000-off,0001-on,0011-Blinking)
	Bits 4-7 represent the Color (0000-clear,0001-green,0011-yellow,0100-red)

	For AMC two octet will be used to represent the LED Status
             Lower octet:
             bit 0 : critical alarm LED
             bit 1 : major alarm LED
             bit 2 : minor alarm LED
             bit 3 : power minor alarm LED
             bit 4 : input power 1
             bit 5 : input power 2
             bit 6 : fuse alarm 1
             bit 7 : fuse alarm 2

             Upper octet:
             bit 0 : Alarm Cut Off
             bit 1 : abnormal
             bit 2 : fault
             bit 3 : external alarm
             bit 4 : fan alarm 1
             bit 5 : fan alarm 2
             bit 6 : fan alarm 3
             bit 7 : fan alarm 4

             If a bit has a value of '1' then the correspondant LED is
             on and '0' is off.
	     For OC-3 each port will have three LED's Tx,Rx,Sync and one APS"

	::= { pgDSLAMChassis 17 }


-- Update History
--
-- Date
END
