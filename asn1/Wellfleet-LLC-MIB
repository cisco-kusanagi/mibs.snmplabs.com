Wellfleet-LLC-MIB DEFINITIONS ::= BEGIN

-- Created by mdl2asn version 3.1
-- Creation date: Wed Aug 30 16:44:48 EDT 1995


    IMPORTS

      Counter
        FROM RFC1155-SMI
      OBJECT-TYPE
        FROM RFC-1212
      DisplayString
        FROM RFC1213-MIB
      wfLlcGroup
        FROM Wellfleet-COMMON-MIB;


    wfLlc		OBJECT IDENTIFIER ::= { wfLlcGroup 1 }

    wfLlcBaseDelete OBJECT-TYPE
        SYNTAX	INTEGER {
    		    created(1),
    		    deleted(2)
    		}
        ACCESS	read-write
        STATUS	mandatory
        DESCRIPTION
                "- Create/Delete parameter. Default is created.
                - Users perform an SNMP SET operation on this
                - object in order to create/delete LLC. "
        DEFVAL	{ created }
        ::= { wfLlc 1 }

    wfLlcBaseDisable OBJECT-TYPE
        SYNTAX	INTEGER {
    		    enabled(1),
    		    disabled(2)
    		}
        ACCESS	read-write
        STATUS	mandatory
        DESCRIPTION
                "- Enable/Disable parameter. Default is disabled.
                - Users perform an SNMP SET operation on this
                - object in order to enable/disable LLC. "
        DEFVAL	{ enabled }
        ::= { wfLlc 2 }

    wfLlcBaseState OBJECT-TYPE
        SYNTAX	INTEGER {
    		    up(1),
    		    down(2),
    		    init(3),
    		    notpresent(4)
    		}
        ACCESS	read-only
        STATUS	mandatory
        DESCRIPTION
                "- The current state of LLC service"
        DEFVAL	{ down }
        ::= { wfLlc 3 }

    wfLlcInterfaceTable OBJECT-TYPE
        SYNTAX	SEQUENCE OF WfLlcInterfaceEntry
        ACCESS	not-accessible
        STATUS	mandatory
        DESCRIPTION
                "A table that contains information about every
                interface that is associated with this
                LLC"
        ::= { wfLlcGroup 2 }

    wfLlcInterfaceEntry OBJECT-TYPE
        SYNTAX	WfLlcInterfaceEntry
        ACCESS	not-accessible
        STATUS	mandatory
        DESCRIPTION
                "An entry in wfLlcInterface."
        INDEX	{ wfLlcInterfaceCircuit }
        ::= { wfLlcInterfaceTable 1 }

    WfLlcInterfaceEntry ::= SEQUENCE {
    	    wfLlcInterfaceDelete
    		INTEGER,
    	    wfLlcInterfaceDisable
    		INTEGER,
    	    wfLlcInterfaceState
    		INTEGER,
    	    wfLlcInterfaceCircuit
    		INTEGER,
    	    wfLlcInterfaceLlc2CctId
    		INTEGER,
    	    wfLlc1InterfaceMaxUinfoSize
    		INTEGER,
    	    wfLlc1InterfaceMaxRetry
    		INTEGER,
    	    wfLlc1InterfaceTAckWait
    		INTEGER,
    	    wfLlc2InterfaceMaxInfoSize
    		INTEGER,
    	    wfLlc2InterfaceK
    		INTEGER,
    	    wfLlc2InterfaceN2
    		INTEGER,
    	    wfLlc2InterfaceN3
    		INTEGER,
    	    wfLlc2InterfaceTAckWait
    		INTEGER,
    	    wfLlc2InterfaceTReject
    		INTEGER,
    	    wfLlc2InterfaceTRemoteBusy
    		INTEGER,
    	    wfLlc2InterfaceTRspAck
    		INTEGER,
    	    wfLlc2InterfaceTIdle
    		INTEGER,
    	    wfLlc2InterfaceTPollCycle
    		INTEGER,
    	    wfLlcInterfaceMaxNumOfSap
    		INTEGER,
    	    wfLlcInterfaceMaxNumOfLink
    		INTEGER,
    	    wfLlcInterfaceDupAddrCheck
    		INTEGER,
    	    wfLlc2InterfaceRW
    		INTEGER,
    	    wfLlc2InterfaceTW
    		INTEGER,
    	    wfLlcInterfaceEncapsType
    		INTEGER,
    	    wfLlcInterfaceSrbRingId
    		INTEGER,
    	    wfLlcInterfaceFrVMask
    		OCTET STRING,
    	    wfLlc2InterfaceDynWin
    		INTEGER,
            wfLlcInterfaceCurrentLinks
                INTEGER,
            wfLlcInterfaceHiWaterLinks
                INTEGER,
            wfLlcInterfaceHiWaterReset
                INTEGER,
	    wfLlcInterfaceFrSapTranslation
                INTEGER
        }

    wfLlcInterfaceDelete OBJECT-TYPE
        SYNTAX	INTEGER {
    		    created(1),
    		    deleted(2)
    		}
        ACCESS	read-write
        STATUS	mandatory
        DESCRIPTION
                "- Create/Delete parameter. Default is created.
                - Users perform an SNMP SET operation on this
                - object in order to create/delete an interface. "
        DEFVAL	{ created }
        ::= { wfLlcInterfaceEntry 1 }

    wfLlcInterfaceDisable OBJECT-TYPE
        SYNTAX	INTEGER {
    		    enabled(1),
    		    disabled(2)
    		}
        ACCESS	read-write
        STATUS	mandatory
        DESCRIPTION
                "-
                - Enable/Disable parameter. Default is enabled.
                - Users perform an SNMP SET operation on this
                - object in order to enable/disable an interface."
        DEFVAL	{ enabled }
        ::= { wfLlcInterfaceEntry 2 }

    wfLlcInterfaceState OBJECT-TYPE
        SYNTAX	INTEGER {
    		    up(1),
    		    down(2),
    		    init(3),
    		    notpresent(4)
    		}
        ACCESS	read-only
        STATUS	mandatory
        DESCRIPTION
                "The current state of the interface."
        DEFVAL	{ down }
        ::= { wfLlcInterfaceEntry 3 }

    wfLlcInterfaceCircuit OBJECT-TYPE
        SYNTAX	INTEGER
        ACCESS	read-only
        STATUS	mandatory
        DESCRIPTION
                "The llc1 circuit of this interface."
        ::= { wfLlcInterfaceEntry 4 }

    wfLlcInterfaceLlc2CctId OBJECT-TYPE
        SYNTAX	INTEGER
        ACCESS	read-write
        STATUS	mandatory
        DESCRIPTION
                "The llc2 circuit number assigned for this slot, line, and llc1 cct."
        ::= { wfLlcInterfaceEntry 5 }

    wfLlc1InterfaceMaxUinfoSize OBJECT-TYPE
        SYNTAX	INTEGER(1..5128)
        ACCESS	read-write
        STATUS	mandatory
        DESCRIPTION
                "- Maximum number of octets in UI PDU. "
        DEFVAL	{ 5128 }
        ::= { wfLlcInterfaceEntry 6 }

    wfLlc1InterfaceMaxRetry OBJECT-TYPE
        SYNTAX	INTEGER(1..2)
        ACCESS	read-write
        STATUS	mandatory
        DESCRIPTION
                "- Maximum retry limit. Specifeis the
                - maximum number of times that an XID
                - or TEST command PDU is sent following
                - the running out of the response timer
                - TResponse"
        DEFVAL	{ 2 }
        ::= { wfLlcInterfaceEntry 7 }

    wfLlc1InterfaceTAckWait OBJECT-TYPE
        SYNTAX	INTEGER(1..30)
        ACCESS	read-write
        STATUS	mandatory
        DESCRIPTION
                "- The amount of time during which the
                - LLC shall expect to receive an
                - an acknowledgment to a sent unnumbered
                - XID or TEST command PDU
                - time in seconds"
        DEFVAL	{ 30 }
        ::= { wfLlcInterfaceEntry 8 }

    wfLlc2InterfaceMaxInfoSize OBJECT-TYPE
        SYNTAX	INTEGER(1..5128)
        ACCESS	read-write
        STATUS	mandatory
        DESCRIPTION
                "- Max number of octets in an I Pdu "
        DEFVAL	{ 5128 }
        ::= { wfLlcInterfaceEntry 9 }

    wfLlc2InterfaceK OBJECT-TYPE
        SYNTAX	INTEGER(1..127)
        ACCESS	read-write
        STATUS	mandatory
        DESCRIPTION
                "- The wfLlc2InterfaceK parameter is no longer used.
                - It is replaced by the send window (wfLlc2InterfaceTW)
                - and the receive window (wfLlc2InterfaceRW) parameters."
        DEFVAL	{ 7 }
        ::= { wfLlcInterfaceEntry 10 }

    wfLlc2InterfaceN2 OBJECT-TYPE
        SYNTAX	INTEGER(1..10)
        ACCESS	read-write
        STATUS	mandatory
        DESCRIPTION
                "- Maximum number of transmissions. This specifies the
                - max number of times that a PDU is sent following the
                - elapse of the ..
                - acknowledgment timer
                - poll timer
                - reject timer"
        DEFVAL	{ 10 }
        ::= { wfLlcInterfaceEntry 11 }

    wfLlc2InterfaceN3 OBJECT-TYPE
        SYNTAX	INTEGER(1..2)
        ACCESS	read-write
        STATUS	mandatory
        DESCRIPTION
                "- Maximum number of received I PDUs before
                - sending a local acknowledgment to the
                - transmitter"
        DEFVAL	{ 1 }
        ::= { wfLlcInterfaceEntry 12 }

    wfLlc2InterfaceTAckWait OBJECT-TYPE
        SYNTAX	INTEGER(1..15)
        ACCESS	read-write
        STATUS	mandatory
        DESCRIPTION
                "- Acknowledment timer for  TX window
                - rotation
                - time in seconds"
        DEFVAL	{ 1 }
        ::= { wfLlcInterfaceEntry 13 }

    wfLlc2InterfaceTReject OBJECT-TYPE
        SYNTAX	INTEGER(1..30)
        ACCESS	read-write
        STATUS	mandatory
        DESCRIPTION
                "- Reject Timer
                - time in seconds"
        DEFVAL	{ 1 }
        ::= { wfLlcInterfaceEntry 14 }

    wfLlc2InterfaceTRemoteBusy OBJECT-TYPE
        SYNTAX	INTEGER(1..60)
        ACCESS	read-write
        STATUS	mandatory
        DESCRIPTION
                "- busy state timer
                - time in seconds"
        DEFVAL	{ 60 }
        ::= { wfLlcInterfaceEntry 15 }

    wfLlc2InterfaceTRspAck OBJECT-TYPE
        SYNTAX	INTEGER(1..10)
        ACCESS	read-write
        STATUS	mandatory
        DESCRIPTION
                "- Local response timer for remote TX
                - window rotation
                - response in seconds"
        DEFVAL	{ 10 }
        ::= { wfLlcInterfaceEntry 16 }

    wfLlc2InterfaceTIdle OBJECT-TYPE
        SYNTAX	INTEGER(1..120)
        ACCESS	read-write
        STATUS	mandatory
        DESCRIPTION
                "- Idle timer
                - in seconds"
        DEFVAL	{ 120 }
        ::= { wfLlcInterfaceEntry 17 }

    wfLlc2InterfaceTPollCycle OBJECT-TYPE
        SYNTAX	INTEGER(1..30)
        ACCESS	read-write
        STATUS	mandatory
        DESCRIPTION
                "- P/F bit cycle timer (link activity)
                - time in secs"
        DEFVAL	{ 30 }
        ::= { wfLlcInterfaceEntry 18 }

    wfLlcInterfaceMaxNumOfSap OBJECT-TYPE
        SYNTAX	INTEGER(4..255)
        ACCESS	read-write
        STATUS	mandatory
        DESCRIPTION
                "- maximum number of saps per LLC service
                - Max = 255 and Min = 4"
        DEFVAL	{ 255 }
        ::= { wfLlcInterfaceEntry 19 }

    wfLlcInterfaceMaxNumOfLink OBJECT-TYPE
        SYNTAX	INTEGER(4..5000)
        ACCESS	read-write
        STATUS	mandatory
        DESCRIPTION
                "- Maximum number of end to end connections
                - per LLC service
                - Max = 5000 and Min = 4 Default:5000"
        DEFVAL	{ 255 }
        ::= { wfLlcInterfaceEntry 20 }

    wfLlcInterfaceDupAddrCheck OBJECT-TYPE
        SYNTAX	INTEGER {
    		    enabled(1),
    		    disabled(2)
    		}
        ACCESS	read-write
        STATUS	mandatory
        DESCRIPTION
                "- Flag to force duplicate address check
                - Default is DISABLED"
        DEFVAL	{ disabled }
        ::= { wfLlcInterfaceEntry 21 }

    wfLlc2InterfaceRW OBJECT-TYPE
        SYNTAX	INTEGER(1..127)
        ACCESS	read-write
        STATUS	mandatory
        DESCRIPTION
                "- Maximum number of outstanding ( = unacknowledged)
                - receive I PDUs. This cannot exceed 127. "
        DEFVAL	{ 7 }
        ::= { wfLlcInterfaceEntry 22 }

    wfLlc2InterfaceTW OBJECT-TYPE
        SYNTAX	INTEGER(1..127)
        ACCESS	read-write
        STATUS	mandatory
        DESCRIPTION
                "- Maximum number of outstanding ( = unacknowledged)
                - transmit I PDUs. This cannot exceed 127.
                - This value acts as a default window size, when no other
                - window size has been agreed upon through
                - an XID3 exchange procedure."
        DEFVAL	{ 7 }
        ::= { wfLlcInterfaceEntry 23 }

    wfLlcInterfaceEncapsType OBJECT-TYPE
        SYNTAX	INTEGER {
    		    default(1),
    		    tring(2),
    		    csmacd(3),
    		    srb(4),
    		    fr(5)
    		}
        ACCESS	read-write
        STATUS	mandatory
        DESCRIPTION
                "This indicates which encapsulation technique
                should be used by LLC. "
        DEFVAL	{ default }
        ::= { wfLlcInterfaceEntry 24 }

    wfLlcInterfaceSrbRingId OBJECT-TYPE
        SYNTAX	INTEGER(1..4095)
        ACCESS	read-write
        STATUS	mandatory
        DESCRIPTION
                "This indicates a ring number to be used by
                LLC if the encapsulation technique is SRB.
                It must be unique in the SRB network."
        ::= { wfLlcInterfaceEntry 25 }

    wfLlcInterfaceFrVMask OBJECT-TYPE
        SYNTAX	OCTET STRING
        ACCESS	read-write
        STATUS	mandatory
        DESCRIPTION
                "- LLC Frame Relay Virtual Mac Address Mask.
                - This Mask specifies the upper 2-4 bytes of the
                - destination mac address.  The lower remaining
                - bytes specifies the DLCI to be used."
        ::= { wfLlcInterfaceEntry 26 }

    wfLlc2InterfaceDynWin OBJECT-TYPE
        SYNTAX	INTEGER {
    		    enabled(1),
    		    disabled(2)
    		}
        ACCESS	read-write
        STATUS	mandatory
        DESCRIPTION
                "- Enable/Disable dynamic window. The default is enabled."
        DEFVAL	{ enabled }
        ::= { wfLlcInterfaceEntry 27 }

   wfLlcInterfaceCurrentLinks OBJECT-TYPE
        SYNTAX  INTEGER
        ACCESS  read-only
        STATUS  mandatory
        DESCRIPTION
                "The number of links on this interface."
        DEFVAL  { 0 }
        ::= { wfLlcInterfaceEntry 28}

    wfLlcInterfaceHiWaterLinks OBJECT-TYPE
        SYNTAX  INTEGER
        ACCESS  read-only
        STATUS  mandatory
        DESCRIPTION
                "The highest number of links present at one time on this interface."
        DEFVAL  { 0 }
        ::= { wfLlcInterfaceEntry 29}

    wfLlcInterfaceHiWaterReset OBJECT-TYPE
        SYNTAX  INTEGER {
                    normal(1),
                    reset(2)
                }
        ACCESS  read-write
        STATUS  mandatory
        DESCRIPTION
                "Setting to 2 (reset) sets HiWaterLinks to CurrentLinks."
        DEFVAL  { normal }
        ::= { wfLlcInterfaceEntry 30}

    wfLlcInterfaceFrSapTranslation OBJECT-TYPE
        SYNTAX  INTEGER {
                    enabled(1),
                    disabled(2)
                }
        ACCESS  read-write
        STATUS  mandatory
        DESCRIPTION
                "Enables SMAC SSAP translation for FR to pass multiple SMACs
		over one VC"
        DEFVAL  { disabled }
        ::= { wfLlcInterfaceEntry 31}

    wfLlcSapTable OBJECT-TYPE
        SYNTAX	SEQUENCE OF WfLlcSapEntry
        ACCESS	not-accessible
        STATUS	mandatory
        DESCRIPTION
                "- llc sap table"
        ::= { wfLlcGroup 3 }

    wfLlcSapEntry OBJECT-TYPE
        SYNTAX	WfLlcSapEntry
        ACCESS	not-accessible
        STATUS	mandatory
        DESCRIPTION
                "An entry in wfLlcSapTable."
        INDEX	{ wfLlcSapCircuit,
    		  wfLlcSapValue }
        ::= { wfLlcSapTable 1 }

    WfLlcSapEntry ::= SEQUENCE {
    	    wfLlcSapCircuit
    		INTEGER,
    	    wfLlcSapValue
    		INTEGER
        }

    wfLlcSapCircuit OBJECT-TYPE
        SYNTAX	INTEGER
        ACCESS	read-only
        STATUS	mandatory
        DESCRIPTION
                "- The llc1  circuit  that this sap is on"
        ::= { wfLlcSapEntry 1 }

    wfLlcSapValue OBJECT-TYPE
        SYNTAX	INTEGER
        ACCESS	read-only
        STATUS	mandatory
        DESCRIPTION
                "- Sap Value"
        ::= { wfLlcSapEntry 2 }

    wfLlcLinkTable OBJECT-TYPE
        SYNTAX	SEQUENCE OF WfLlcLinkEntry
        ACCESS	not-accessible
        STATUS	mandatory
        DESCRIPTION
                "- Link table, indexed by slot, circuit, da, sa, dsap, ssap"
        ::= { wfLlcGroup 4 }

    wfLlcLinkEntry OBJECT-TYPE
        SYNTAX	WfLlcLinkEntry
        ACCESS	not-accessible
        STATUS	mandatory
        DESCRIPTION
                "An entry in wfLlcLinkTable."
        INDEX	{ wfLlcLinkCircuit,
    		  wfLlcLinkDestMadr,
    		  wfLlcLinkSrcMadr,
    		  wfLlcLinkDsap,
    		  wfLlcLinkSsap }
        ::= { wfLlcLinkTable 1 }

    WfLlcLinkEntry ::= SEQUENCE {
    	    wfLlcLinkCircuit
    		INTEGER,
    	    wfLlcLinkDestMadr
    		OCTET STRING,
    	    wfLlcLinkSrcMadr
    		OCTET STRING,
    	    wfLlcLinkDsap
    		INTEGER,
    	    wfLlcLinkSsap
    		INTEGER,
    	    wfLlcInfoRxCnt
    		Counter,
    	    wfLlcInfoTxCnt
    		Counter,
    	    wfLlcInfoReXmitCnt
    		Counter,
    	    wfLlcByteInfoRxCnt
    		Counter,
    	    wfLlcByteInfoTxCnt
    		Counter,
    	    wfLlcRrRxCnt
    		Counter,
    	    wfLlcRrTxCnt
    		Counter,
    	    wfLlcRnrRxCnt
    		Counter,
    	    wfLlcRnrTxCnt
    		Counter,
    	    wfLlcRejRxCnt
    		Counter,
    	    wfLlcRejTxCnt
    		Counter,
    	    wfLlcFrmrRxCnt
    		Counter,
    	    wfLlcFrmrTxCnt
    		Counter,
    	    wfLlcFlowDefersCnt
    		Counter,
    	    wfLlcWaitAckTimeouts
    		Counter,
    	    wfLlcRejectTimeouts
    		Counter,
    	    wfLlcPollCycleTimeouts
    		Counter,
    	    wfLlcStateChangeCnt
    		Counter,
    	    wfLlcLastChangeReason
    		Counter,
    	    wfLlcCurrentState
    		Counter
        }

    wfLlcLinkCircuit OBJECT-TYPE
        SYNTAX	INTEGER
        ACCESS	read-only
        STATUS	mandatory
        DESCRIPTION
                "- The llc1 circuit that this  da/sa/dsap/ssap pair is on."
        ::= { wfLlcLinkEntry 1 }

    wfLlcLinkDestMadr OBJECT-TYPE
        SYNTAX	OCTET STRING (SIZE (6))
        ACCESS	read-only
        STATUS	mandatory
        DESCRIPTION
                "- Destination and source Mac addresses"
        ::= { wfLlcLinkEntry 2 }

    wfLlcLinkSrcMadr OBJECT-TYPE
        SYNTAX	OCTET STRING (SIZE (6))
        ACCESS	read-only
        STATUS	mandatory
        DESCRIPTION
                "- source Mac address"
        ::= { wfLlcLinkEntry 3 }

    wfLlcLinkDsap OBJECT-TYPE
        SYNTAX	INTEGER
        ACCESS	read-only
        STATUS	mandatory
        DESCRIPTION
                "- Destination and source sap's"
        ::= { wfLlcLinkEntry 4 }

    wfLlcLinkSsap OBJECT-TYPE
        SYNTAX	INTEGER
        ACCESS	read-only
        STATUS	mandatory
        DESCRIPTION
                "- Source Sap "
        ::= { wfLlcLinkEntry 5 }

    wfLlcInfoRxCnt OBJECT-TYPE
        SYNTAX	Counter
        ACCESS	read-only
        STATUS	mandatory
        DESCRIPTION
                "- Counter for I Pdus rcvd "
        ::= { wfLlcLinkEntry 6 }

    wfLlcInfoTxCnt OBJECT-TYPE
        SYNTAX	Counter
        ACCESS	read-only
        STATUS	mandatory
        DESCRIPTION
                "- Counter for I Pdus sent "
        ::= { wfLlcLinkEntry 7 }

    wfLlcInfoReXmitCnt OBJECT-TYPE
        SYNTAX	Counter
        ACCESS	read-only
        STATUS	mandatory
        DESCRIPTION
                "- Counter for I Pdus re-xmitted"
        ::= { wfLlcLinkEntry 8 }

    wfLlcByteInfoRxCnt OBJECT-TYPE
        SYNTAX	Counter
        ACCESS	read-only
        STATUS	mandatory
        DESCRIPTION
                "- Counter for unnnumbered information
                - Bytes rcvd"
        ::= { wfLlcLinkEntry 9 }

    wfLlcByteInfoTxCnt OBJECT-TYPE
        SYNTAX	Counter
        ACCESS	read-only
        STATUS	mandatory
        DESCRIPTION
                "- Counter for unnnumbered information
                - Bytes sent"
        ::= { wfLlcLinkEntry 10 }

    wfLlcRrRxCnt OBJECT-TYPE
        SYNTAX	Counter
        ACCESS	read-only
        STATUS	mandatory
        DESCRIPTION
                "- Counter for RR Pdus rcvd "
        ::= { wfLlcLinkEntry 11 }

    wfLlcRrTxCnt OBJECT-TYPE
        SYNTAX	Counter
        ACCESS	read-only
        STATUS	mandatory
        DESCRIPTION
                "- Counter for RR Pdus Xmted"
        ::= { wfLlcLinkEntry 12 }

    wfLlcRnrRxCnt OBJECT-TYPE
        SYNTAX	Counter
        ACCESS	read-only
        STATUS	mandatory
        DESCRIPTION
                "- Counter for RNR Pdus rcvd "
        ::= { wfLlcLinkEntry 13 }

    wfLlcRnrTxCnt OBJECT-TYPE
        SYNTAX	Counter
        ACCESS	read-only
        STATUS	mandatory
        DESCRIPTION
                "- Counter for RNR Pdus sent "
        ::= { wfLlcLinkEntry 14 }

    wfLlcRejRxCnt OBJECT-TYPE
        SYNTAX	Counter
        ACCESS	read-only
        STATUS	mandatory
        DESCRIPTION
                "- Counter for REJ pdus rcvd"
        ::= { wfLlcLinkEntry 15 }

    wfLlcRejTxCnt OBJECT-TYPE
        SYNTAX	Counter
        ACCESS	read-only
        STATUS	mandatory
        DESCRIPTION
                "- Counter for REJ pdus xmted"
        ::= { wfLlcLinkEntry 16 }

    wfLlcFrmrRxCnt OBJECT-TYPE
        SYNTAX	Counter
        ACCESS	read-only
        STATUS	mandatory
        DESCRIPTION
                "- Counter for frame reject rcvd"
        ::= { wfLlcLinkEntry 17 }

    wfLlcFrmrTxCnt OBJECT-TYPE
        SYNTAX	Counter
        ACCESS	read-only
        STATUS	mandatory
        DESCRIPTION
                "- Counter for frame reject sent"
        ::= { wfLlcLinkEntry 18 }

    wfLlcFlowDefersCnt OBJECT-TYPE
        SYNTAX	Counter
        ACCESS	read-only
        STATUS	mandatory
        DESCRIPTION
                "- Counter for the number of times LLC is unable
                - to xmit due to a percieved remote busy condition
                - or to lack of RX window space"
        ::= { wfLlcLinkEntry 19 }

    wfLlcWaitAckTimeouts OBJECT-TYPE
        SYNTAX	Counter
        ACCESS	read-only
        STATUS	mandatory
        DESCRIPTION
                "- Counter for expiration of acknowledgment
                - timers"
        ::= { wfLlcLinkEntry 20 }

    wfLlcRejectTimeouts OBJECT-TYPE
        SYNTAX	Counter
        ACCESS	read-only
        STATUS	mandatory
        DESCRIPTION
                "- Counter for the expiration of reject
                - timeouts"
        ::= { wfLlcLinkEntry 21 }

    wfLlcPollCycleTimeouts OBJECT-TYPE
        SYNTAX	Counter
        ACCESS	read-only
        STATUS	mandatory
        DESCRIPTION
                "- Counter for the expiration of P/F cycle timer"
        ::= { wfLlcLinkEntry 22 }

    wfLlcStateChangeCnt OBJECT-TYPE
        SYNTAX	Counter
        ACCESS	read-only
        STATUS	mandatory
        DESCRIPTION
                "- Counter for number of LLC flow state changes"
        ::= { wfLlcLinkEntry 23 }

    wfLlcLastChangeReason OBJECT-TYPE
        SYNTAX	Counter
        ACCESS	read-only
        STATUS	mandatory
        DESCRIPTION
                "- Counter for the most recent incrementing of the
                - flow state change counter "
        ::= { wfLlcLinkEntry 24 }

    wfLlcCurrentState OBJECT-TYPE
        SYNTAX	Counter
        ACCESS	read-only
        STATUS	mandatory
        DESCRIPTION
                "- Current flow state of the LLC link station"
        ::= { wfLlcLinkEntry 25 }

    wfLlc2TrafficFilterTable OBJECT-TYPE
        SYNTAX	SEQUENCE OF WfLlc2TrafficFilterEntry
        ACCESS	not-accessible
        STATUS	mandatory
        DESCRIPTION
                "LLC2 Traffic Filters"
        ::= { wfLlcGroup 8 }

    wfLlc2TrafficFilterEntry OBJECT-TYPE
        SYNTAX	WfLlc2TrafficFilterEntry
        ACCESS	not-accessible
        STATUS	mandatory
        DESCRIPTION
                "An entry in WfLLC2TrafficFilterTable."
        INDEX	{ wfLlc2TrafficFilterCircuit,
    		  wfLlc2TrafficFilterRuleNumber,
    		  wfLlc2TrafficFilterFragment }
        ::= { wfLlc2TrafficFilterTable 1 }

    WfLlc2TrafficFilterEntry ::= SEQUENCE {
    	    wfLlc2TrafficFilterCreate
    		INTEGER,
    	    wfLlc2TrafficFilterEnable
    		INTEGER,
    	    wfLlc2TrafficFilterStatus
    		INTEGER,
    	    wfLlc2TrafficFilterCounter
    		Counter,
    	    wfLlc2TrafficFilterDefinition
    		OCTET STRING,
    	    wfLlc2TrafficFilterReserved
    		INTEGER,
    	    wfLlc2TrafficFilterCircuit
    		INTEGER,
    	    wfLlc2TrafficFilterRuleNumber
    		INTEGER,
    	    wfLlc2TrafficFilterFragment
    		INTEGER,
    	    wfLlc2TrafficFilterName
    		DisplayString
        }

    wfLlc2TrafficFilterCreate OBJECT-TYPE
        SYNTAX	INTEGER {
    		    created(1),
    		    deleted(2)
    		}
        ACCESS	read-write
        STATUS	mandatory
        DESCRIPTION
                "Defines the existence of the traffic filter rule:
                created - traffic filter exists
                delete - traffic filter does not exist and can be deleted."
        DEFVAL	{ created }
        ::= { wfLlc2TrafficFilterEntry 1 }

    wfLlc2TrafficFilterEnable OBJECT-TYPE
        SYNTAX	INTEGER {
    		    enabled(1),
    		    disabled(2)
    		}
        ACCESS	read-write
        STATUS	mandatory
        DESCRIPTION
                "Defines whether or not the traffic filter rule should be used:
                enabled - activate the rule.
                disabled - inactivate the rule."
        DEFVAL	{ enabled }
        ::= { wfLlc2TrafficFilterEntry 2 }

    wfLlc2TrafficFilterStatus OBJECT-TYPE
        SYNTAX	INTEGER {
    		    active(1),
    		    error(2),
    		    inactive(3)
    		}
        ACCESS	read-only
        STATUS	mandatory
        DESCRIPTION
                "Defines the current status of the traffic filter:
                inactive - the rule is not in use.
                active - the rule is being used.
                error - the application detected an error in the rule."
        DEFVAL	{ inactive }
        ::= { wfLlc2TrafficFilterEntry 3 }

    wfLlc2TrafficFilterCounter OBJECT-TYPE
        SYNTAX	Counter
        ACCESS	read-only
        STATUS	mandatory
        DESCRIPTION
                "The number of received packets that have
                matched this rule."
        ::= { wfLlc2TrafficFilterEntry 4 }

    wfLlc2TrafficFilterDefinition OBJECT-TYPE
        SYNTAX	OCTET STRING
        ACCESS	read-write
        STATUS	mandatory
        DESCRIPTION
                "The filter rule definition."
        ::= { wfLlc2TrafficFilterEntry 5 }

    wfLlc2TrafficFilterReserved OBJECT-TYPE
        SYNTAX	INTEGER
        ACCESS	read-only
        STATUS	mandatory
        DESCRIPTION
                "Reserved field."
        ::= { wfLlc2TrafficFilterEntry 6 }

    wfLlc2TrafficFilterCircuit OBJECT-TYPE
        SYNTAX	INTEGER
        ACCESS	read-only
        STATUS	mandatory
        DESCRIPTION
                "The ID of the Bridge Circuit to which the
                filter is applied."
        ::= { wfLlc2TrafficFilterEntry 7 }

    wfLlc2TrafficFilterRuleNumber OBJECT-TYPE
        SYNTAX	INTEGER
        ACCESS	read-only
        STATUS	mandatory
        DESCRIPTION
                "ID for the rule."
        ::= { wfLlc2TrafficFilterEntry 8 }

    wfLlc2TrafficFilterFragment OBJECT-TYPE
        SYNTAX	INTEGER
        ACCESS	read-only
        STATUS	mandatory
        DESCRIPTION
                "Fragment number - for large rules."
        ::= { wfLlc2TrafficFilterEntry 9 }

    wfLlc2TrafficFilterName OBJECT-TYPE
        SYNTAX	DisplayString
        ACCESS	read-write
        STATUS	mandatory
        DESCRIPTION
                "name of the rule number"
        ::= { wfLlc2TrafficFilterEntry 10 }

    wfLlcDlciTable OBJECT-TYPE
        SYNTAX	SEQUENCE OF WfLlcDlciEntry
        ACCESS	not-accessible
        STATUS	mandatory
        DESCRIPTION
                "ljd: This table defines which DLCI's a LLC interface has access
                to and the appropriate mac address mappings."
        ::= { wfLlcGroup 9 }

    wfLlcDlciEntry OBJECT-TYPE
        SYNTAX	WfLlcDlciEntry
        ACCESS	not-accessible
        STATUS	mandatory
        DESCRIPTION
                "An entry in wfLlcDlciTable."
        INDEX	{ wfLlcDlciCct,
    		  wfLlcDlciNum }
        ::= { wfLlcDlciTable 1 }

    WfLlcDlciEntry ::= SEQUENCE {
    	    wfLlcDlciDelete
    		INTEGER,
    	    wfLlcDlciCct
    		INTEGER,
    	    wfLlcDlciNum
    		INTEGER,
    	    wfLlcDlciLocalMac
    		OCTET STRING,
    	    wfLlcDlciRemoteMac
    		OCTET STRING
        }

    wfLlcDlciDelete OBJECT-TYPE
        SYNTAX	INTEGER {
    		    created(1),
    		    deleted(2)
    		}
        ACCESS	read-write
        STATUS	mandatory
        DESCRIPTION
                "Create/Delete parameter. Default is created. Users perform an SNMP SET
                operation on this object in order to create/delete a DLSw Local Device"
        DEFVAL	{ created }
        ::= { wfLlcDlciEntry 1 }

    wfLlcDlciCct OBJECT-TYPE
        SYNTAX	INTEGER
        ACCESS	read-only
        STATUS	mandatory
        DESCRIPTION
                "The LLC interface circuit on which this mapping is configured."
        ::= { wfLlcDlciEntry 2 }

    wfLlcDlciNum OBJECT-TYPE
        SYNTAX	INTEGER
        ACCESS	read-only
        STATUS	mandatory
        DESCRIPTION
                "The dlci number for this mapping."
        ::= { wfLlcDlciEntry 3 }

    wfLlcDlciLocalMac OBJECT-TYPE
        SYNTAX	OCTET STRING
        ACCESS	read-write
        STATUS	mandatory
        DESCRIPTION
                "The Local MAC address of the end station to be mapped.
                In-coming requests on this DLCI will be mapped to the specified
                Local Mac address. Values are standard MSB Token Ring MAC addresses."
        ::= { wfLlcDlciEntry 4 }

    wfLlcDlciRemoteMac OBJECT-TYPE
        SYNTAX	OCTET STRING
        ACCESS	read-write
        STATUS	mandatory
        DESCRIPTION
                "The Remote MAC address mapping. Out-going requests specifing
                this mac address will be mapped to the DLCI.
                Values are standard MSB Token Ring MAC addresses."
        ::= { wfLlcDlciEntry 5 }

    wfLlcFrSvcTable OBJECT-TYPE
        SYNTAX	SEQUENCE OF WfLlcFrSvcEntry
        ACCESS	not-accessible
        STATUS	mandatory
        DESCRIPTION
                "ljd: This table defines which FrSvc's a LLC interface has access
                to and the appropriate mac address mappings."
        ::= { wfLlcGroup 10 }

    wfLlcFrSvcEntry OBJECT-TYPE
        SYNTAX	WfLlcFrSvcEntry
        ACCESS	not-accessible
        STATUS	mandatory
        DESCRIPTION
                "An entry in wfLlcFrSvcTable."
        INDEX	{ wfLlcFrSvcCct,
    		  wfLlcFrSvcMac }
        ::= { wfLlcFrSvcTable 1 }

    WfLlcFrSvcEntry ::= SEQUENCE {
    	    wfLlcFrSvcDelete
    		INTEGER,
    	    wfLlcFrSvcCct
    		INTEGER,
    	    wfLlcFrSvcMac
    		OCTET STRING,
    	    wfLlcFrSvcMappingType
    		INTEGER,
	    wfLlcFrSvcX121Addr
   		DisplayString,
	    wfLlcFrSvcSubAddr
   		DisplayString,
	    wfLlcFrSvcPlan
   		INTEGER,
	    wfLlcFrSvcTypeOfNumber
   		INTEGER
        }

    wfLlcFrSvcDelete OBJECT-TYPE
        SYNTAX	INTEGER {
    		    created(1),
    		    deleted(2)
    		}
        ACCESS	read-write
        STATUS	mandatory
        DESCRIPTION
                "Create/Delete parameter. Default is created. Users perform 
		an SNMP SET operation on this object in order to create/delete 
		a local or remote DNA to mac mapping"
        DEFVAL	{ created }
        ::= { wfLlcFrSvcEntry 1 }

    wfLlcFrSvcCct OBJECT-TYPE
        SYNTAX	INTEGER
        ACCESS	read-only
        STATUS	mandatory
        DESCRIPTION
                "The LLC interface circuit on which this mapping is configured."
        ::= { wfLlcFrSvcEntry 2 }

    wfLlcFrSvcMac OBJECT-TYPE
        SYNTAX	OCTET STRING (SIZE (6))
        ACCESS	read-only
        STATUS	mandatory
        DESCRIPTION
                "The local or remote MAC address of the end station to be mapped.
                Values are standard MSB Token Ring MAC addresses."
        ::= { wfLlcFrSvcEntry 3 }

    wfLlcFrSvcMappingType OBJECT-TYPE
        SYNTAX	INTEGER{
    		    local(1),
    		    remote(2)
    		}
        ACCESS	read-write
        STATUS	mandatory
        DESCRIPTION
                "Specifies weather this is remote or local mapping."
        DEFVAL	{ local }
        ::= { wfLlcFrSvcEntry 4 }

    wfLlcFrSvcX121Addr OBJECT-TYPE
        SYNTAX	DisplayString
        ACCESS	read-write
        STATUS	mandatory
        DESCRIPTION
                "WAN address (X.121, E.164, etc.) used to register with FR
		to accept an incoming call if the mapping is local, or
		used to establish an SVC (initiate the call) to the configured 
		number if the mapping is remote."
        ::= { wfLlcFrSvcEntry 5 }

    wfLlcFrSvcSubAddr OBJECT-TYPE
        SYNTAX	DisplayString
        ACCESS	read-write
        STATUS	mandatory
        DESCRIPTION
		" Subaddress of type NSAP (Q.931) further qualifies number "
        ::= { wfLlcFrSvcEntry 6 }

    wfLlcFrSvcPlan OBJECT-TYPE
        SYNTAX	INTEGER {
		    e164(1),
		    x121(3)
    		}
        ACCESS	read-write
        STATUS	mandatory
        DESCRIPTION
		" Supported Q.931 4.3.8/4.3.10 numbering plans. Each
		  plan is represented by the 4 least significant bits
		  to align with the values stated in Q.931. "
	DEFVAL	{ x121 }
        ::= { wfLlcFrSvcEntry 7 }

    wfLlcFrSvcTypeOfNumber OBJECT-TYPE
        SYNTAX	INTEGER {
    		    unknown(1),
    		    international(2)
    		}
        ACCESS	read-write
        STATUS	mandatory
	DESCRIPTION
		" Supported Q.931 4.3.8/4.3.10 types of number. Each
		  type is represented by a value one greater than 
		  the values stated in Q.931. "
	DEFVAL	{ international }
        ::= { wfLlcFrSvcEntry 8 }

    END  -- Wellfleet-LLC-MIB
