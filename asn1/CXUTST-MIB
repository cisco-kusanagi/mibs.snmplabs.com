CXUTST-MIB DEFINITIONS ::= BEGIN


IMPORTS
	OBJECT-TYPE     FROM RFC-1212
	cxUTst          FROM CXProduct-SMI;

--  U-Interface Built-In Self Test Configuration Table

--  The table describing:
--      statistics available for monitoring test results of an ISDN U-Interface daughter card

utstTable OBJECT-TYPE
	SYNTAX  SEQUENCE OF UtstEntry
	ACCESS  not-accessible
	STATUS  mandatory
	DESCRIPTION
"A table containing test results of an ISDN U-Interface daughter card."
	::= { cxUTst 10 }


	utstEntry OBJECT-TYPE
		SYNTAX  UtstEntry
		ACCESS  not-accessible
		STATUS  mandatory
		DESCRIPTION
"The parameters for a specific ISDN U-Interface daughter card."
		INDEX { utstSlotNumberIndex }
		::= { utstTable 1 }


	UtstEntry ::=
		SEQUENCE {
-- Parameters
			utstSlotNumberIndex                     INTEGER,
-- Control
-- Status
			utstIoRegTest                           INTEGER,
			utstIoLedsTest                          INTEGER,
			utstImpRegTest                          INTEGER,
			utstImpComTestPollResult                INTEGER,        
			utstUifRegTest                          INTEGER,
			utstUifComTestPollResult                INTEGER
-- Statistics           
			}

	utstSlotNumberIndex OBJECT-TYPE
		SYNTAX  INTEGER (1..6)
		ACCESS  read-only
		STATUS  mandatory
		DESCRIPTION
"Indicates the row containing objects for monitoring an I/O card in the CX 
900.

Range of Values: 1-6

Default Value: none"
		::= { utstEntry 1 }
	

	utstIoRegTest OBJECT-TYPE
		SYNTAX  INTEGER {
					failed                          (1),
					passed                  (2)
				}
		ACCESS  read-only
		STATUS  mandatory
		DESCRIPTION
"Indicates the result of the ISDN U-interface I/O register test.

Options:
failed (1): register test failed

passed (2): register test passed

Default Value: passed (2)"
		::= { utstEntry 20 }


	utstIoLedsTest OBJECT-TYPE
		SYNTAX  INTEGER {
					initializationFailed    (1),
						initializationPassed    (2)
				}
		ACCESS  read-only
		STATUS  mandatory
		DESCRIPTION
"Indicates the result of the ISDN U-interface Integrated Multiprotocol 
Processor (IMP) LEDs test.

Options:
initializationFailed (1): IMP initialization failed

initializationPassed (2): IMP initialization passed

Default Value: initializationPassed"
		::= { utstEntry 21 }


	utstImpRegTest OBJECT-TYPE
		SYNTAX  INTEGER {
					initializationFailed            (1),
					failed                          (2),
					passed                          (3)
				}
		ACCESS  read-only
		STATUS  mandatory
		DESCRIPTION
"Indicates the result of the ISDN U-interface Integrated Multiprotocol 
Processor (IMP) register test.

Options:
initializationFailed (1): IMP initialization failed

failed (2): IMP register test failed

passed (3): IMP register test passed

Default Value: passed (3)"
		::= { utstEntry 22 }


	utstImpComTestPollResult OBJECT-TYPE
		SYNTAX  INTEGER {
					initializationFailed            (1),
					failed                          (2),
					passed                          (3)
				}
		ACCESS  read-only
		STATUS  mandatory
		DESCRIPTION
"Indicates the result of the ISDN U-interface IMP internal communication 
test while in polling mode.

Options:
initializationFailed (1): IMP initialization failed

failed (2): IMP communication test failed in polling mode

passed (3): IMP communication test passed in polling mode

Default Value: passed (3)"
		::= { utstEntry 23 }


	utstUifRegTest OBJECT-TYPE
		SYNTAX  INTEGER {
					initializationFailed            (1),
					failed                          (2),
					passed                          (3)
				}
		ACCESS  read-only
		STATUS  mandatory
		DESCRIPTION
"Indicates the result of the ISDN U-interface transceiver register test.

Options:
initializationFailed (1): IMP initialization test failed

failed (2): transceiver register test failed

passed (3): transceiver register test passed

Default Value: passed (3)"
		::= { utstEntry 24 }


	utstUifComTestPollResult OBJECT-TYPE
		SYNTAX  INTEGER {
					initializationFailed            (1),
					failed                          (2),
					passed                          (3)
				}
		ACCESS  read-only
		STATUS  mandatory
		DESCRIPTION
"Indicates the result of the ISDN U-interface transceiver internal 
communication test while in polling mode.

Options:
initializationFailed (1): IMP initialization failed

failed (2): transceiver communication test failed in polling mode

passed (3): transceiver communication test passed in polling mode

Default Value: passed (3)"
		::= { utstEntry 25 }
END
