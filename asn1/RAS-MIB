RAS-MIB DEFINITIONS ::= BEGIN
         IMPORTS
           Counter32, Integer32, OBJECT-TYPE,
           MODULE-IDENTITY, NOTIFICATION-TYPE
                 FROM SNMPv2-SMI
           TAddress, RowStatus, TruthValue, DateAndTime
                 FROM SNMPv2-TC
           MODULE-COMPLIANCE, OBJECT-GROUP
                 FROM SNMPv2-CONF
           ifIndex
                 FROM IF-MIB
           MmGatekeeperID, MmTAddressTag,MmEndpointID, MmGlobalIdentifier,
           MmAliasTag, MmAliasAddress, mmH323Root, MmH225Crv, MmCallType
                 FROM MULTI-MEDIA-MIB-TC;

      --  this is the MIB module for the RAS objects
         ras  MODULE-IDENTITY
             LAST-UPDATED "9812162253Z"      -- December 16, 1998
             ORGANIZATION "ITU-T"
             CONTACT-INFO
             " ITU-T SG 16 "
             DESCRIPTION
                "RAS MIB"
                      ::= { mmH323Root 2}

         -- groups in RAS

         rasConfiguration    OBJECT IDENTIFIER ::= { ras 1 }
         rasRegistration       OBJECT IDENTIFIER ::= { ras 2 }
         rasAdmission       OBJECT IDENTIFIER ::= { ras 3 }
         rasStats                 OBJECT IDENTIFIER ::= { ras 4 }
         rasEvents              OBJECT IDENTIFIER ::= { ras 5 0 }



         rasConfigurationTable OBJECT-TYPE
             SYNTAX SEQUENCE OF RasConfigurationTableEntry
             MAX-ACCESS not-accessible
             STATUS current
             DESCRIPTION
                "This table contains information about ras configuration parameters.
                 It is a list of ras configuration parameters entries. The number of entries equals to
                 the number of configuration parameters."
             ::= { rasConfiguration 1 }

         rasConfigurationTableEntry OBJECT-TYPE
             SYNTAX RasConfigurationTableEntry
             MAX-ACCESS not-accessible
             STATUS current
             DESCRIPTION
                 "It contains objects that describe the ras configuration parameters."
             INDEX { ifIndex }
                      ::= { rasConfigurationTable 1 }

         RasConfigurationTableEntry ::=
              SEQUENCE {
              rasConfigurationGatekeeperIdentifier
                    MmGatekeeperID,
              rasConfigurationTimer
                    Integer32,
              rasConfigurationMaxNumberOfRetries
                    Integer32,
              rasConfigurationGatekeeperDiscoveryAddressTag
                    MmTAddressTag,
              rasConfigurationGatekeeperDiscoveryAddress
                    TAddress

                    }

         rasConfigurationGatekeeperIdentifier OBJECT-TYPE
             SYNTAX MmGatekeeperID
             MAX-ACCESS read-only
             STATUS current
             DESCRIPTION
                "String that identifies gatekeeper. For a gatekeeper, this string identifies the
                gatekeeper.  In an endpoint, the field is the desired gatekeeper or NULLString
                that identifies gatekeeper."
                ::= { rasConfigurationTableEntry 1 }

         rasConfigurationTimer OBJECT-TYPE
             SYNTAX Integer32
             UNITS "seconds"
             MAX-ACCESS read-write
             STATUS current
             DESCRIPTION
                "The amount of time that the timer is set to in seconds.
                 This is the maximum time that the endpoint will wait for the responce."
             DEFVAL { 3 }
                ::= { rasConfigurationTableEntry 2 }

         rasConfigurationMaxNumberOfRetries OBJECT-TYPE
             SYNTAX Integer32
             MAX-ACCESS read-write
             STATUS current
             DESCRIPTION
                "The maximum number of times the message shall be resent."
          DEFVAL { 3 }
                ::= { rasConfigurationTableEntry 3 }

          rasConfigurationGatekeeperDiscoveryAddressTag OBJECT-TYPE
             SYNTAX MmTAddressTag
             MAX-ACCESS read-only
             STATUS current
             DESCRIPTION
                "The transport address tag of the gatekeeper."
                ::= {rasConfigurationTableEntry 4 }

          rasConfigurationGatekeeperDiscoveryAddress OBJECT-TYPE
             SYNTAX TAddress
             MAX-ACCESS read-only
             STATUS current
             DESCRIPTION
                "The gatekeeper transport address that allow for manual discovery."
                ::= { rasConfigurationTableEntry 5 }

         rasRegistrationTable OBJECT-TYPE
             SYNTAX SEQUENCE OF RasRegistrationTableEntry
             MAX-ACCESS not-accessible
             STATUS current
             DESCRIPTION
                "This table contains information about endpoints that are registered with the
                Gatekeeper. It is a list of registered entities entries. The number of entries equals
                to the number of registered endpoints."
             ::= { rasRegistration 1 }

         rasRegistrationTableEntry OBJECT-TYPE
             SYNTAX RasRegistrationTableEntry
             MAX-ACCESS not-accessible
             STATUS current
             DESCRIPTION
                 "It contains objects that describe the registered endpoint."
             INDEX {  ifIndex,
                      rasRegistrationCallSignallingAddressTag,
                      rasRegistrationCallSignallingAddress,
                      rasRegistrationSrcRasAddressTag,
                      rasRegistrationSrcRasAddress
                   }
                      ::= { rasRegistrationTable 1 }

         RasRegistrationTableEntry ::=
              SEQUENCE {
              rasRegistrationCallSignallingAddressTag
                    MmTAddressTag,
              rasRegistrationCallSignallingAddress
                    TAddress,
              rasRegistrationSrcRasAddressTag
                    MmTAddressTag,
              rasRegistrationSrcRasAddress
                    TAddress,
              rasRegistrationIsGatekeeper
                    TruthValue,
              rasRegistrationGatekeeperId
                    MmGatekeeperID,
              rasRegistrationEndpointId
                    MmEndpointID,
              rasRegistrationEncryption
                    TruthValue,
              rasRegistrationWillSupplyUUIE
                    TruthValue,
              rasRegistrationIntegrityCheckValue
                    TruthValue,
              rasRegistrationTableNumberOfAliases
                    Integer32,
              rasRegistrationTableRowStatus
                    RowStatus,
              rasRegistrationEndpointType
                    Integer32,
              rasRegistrationPregrantedARQ
                    TruthValue,
              rasRegistrationIsregisteredByRRQ
                    TruthValue
       }

        rasRegistrationCallSignallingAddressTag OBJECT-TYPE
             SYNTAX MmTAddressTag
             MAX-ACCESS  not-accessible
             STATUS current
             DESCRIPTION
                "The transport address tag of the endpoint."
                ::= { rasRegistrationTableEntry 1 }

        rasRegistrationCallSignallingAddress OBJECT-TYPE
             SYNTAX TAddress
             MAX-ACCESS  not-accessible
             STATUS current
             DESCRIPTION
                "The endpoint call signalling address."
                ::= { rasRegistrationTableEntry 2 }

        rasRegistrationSrcRasAddressTag OBJECT-TYPE
             SYNTAX MmTAddressTag
             MAX-ACCESS  not-accessible
             STATUS current
             DESCRIPTION
                "The ras address tag of the calling endpoint."
                ::= { rasRegistrationTableEntry 3 }

        rasRegistrationSrcRasAddress OBJECT-TYPE
             SYNTAX TAddress
             MAX-ACCESS  not-accessible
             STATUS current
             DESCRIPTION
                "The ras address of the calling endpoint."
                ::= { rasRegistrationTableEntry 4 }

        rasRegistrationIsGatekeeper OBJECT-TYPE
               SYNTAX TruthValue
               MAX-ACCESS read-only
               STATUS current
               DESCRIPTION
                "This value identifies the endpoint being a gatekeeper."
                ::= { rasRegistrationTableEntry 5 }

        rasRegistrationGatekeeperId OBJECT-TYPE
               SYNTAX MmGatekeeperID
               MAX-ACCESS read-only
               STATUS current
               DESCRIPTION
                "The identifier of the gatekeeper that this endpoint is registered with."
                ::= { rasRegistrationTableEntry 6 }

        rasRegistrationEndpointId OBJECT-TYPE
             SYNTAX MmEndpointID
             MAX-ACCESS read-only
             STATUS current
             DESCRIPTION
                "The endpoint identifier."
                ::= { rasRegistrationTableEntry 7 }

       rasRegistrationEncryption OBJECT-TYPE
             SYNTAX TruthValue
             MAX-ACCESS read-only
             STATUS current
             DESCRIPTION
                "This value indicates that the endpoint is using encryption."
                ::= { rasRegistrationTableEntry 8 }

        rasRegistrationWillSupplyUUIE OBJECT-TYPE
             SYNTAX TruthValue
             MAX-ACCESS read-only
             STATUS current
             DESCRIPTION
                "This value indicates that the endpoint will supply Q.931 message info in IRR
                messages if requested by the gatekeeper."
                ::= { rasRegistrationTableEntry 9 }

        rasRegistrationIntegrityCheckValue OBJECT-TYPE
             SYNTAX TruthValue
             MAX-ACCESS read-only
             STATUS current
             DESCRIPTION
                "The value indicates that the endpoint will supply the integrity check value."
                ::= { rasRegistrationTableEntry 10 }

        rasRegistrationTableNumberOfAliases OBJECT-TYPE
             SYNTAX Integer32
             MAX-ACCESS read-only
             STATUS current
             DESCRIPTION
                "The number of alias addresses for the endpoint."
                ::= { rasRegistrationTableEntry 11 }

        rasRegistrationTableRowStatus OBJECT-TYPE
             SYNTAX     RowStatus
             MAX-ACCESS read-create
             STATUS     current
             DESCRIPTION
                "The row status of the entry. This object is required to create
                 or delete rows remotely by a manager. "
                ::= { rasRegistrationTableEntry 12 }

        rasRegistrationEndpointType OBJECT-TYPE
              SYNTAX Integer32
              MAX-ACCESS read-only
              STATUS current
              DESCRIPTION
                "Terminal type represents the type of H.323 terminal:
                                50  - terminal without MC
                                60  - gateway without MC
                                70  - terminal with MC but without MP
                                80  - gateway  with MC but without MP
                                120 - gatekeeper with MC but without MP
                                160 - MCU with MC but without MP
                                90  - gateway with MC and Data MP
                                130 - gatekeeper with MC and Data MP
                                170 - MCU with MC and Data MP
                                100 - gateway containing MC with Data and audio MP
                                140 - gatekeeper containing MC with Data and audio MP
                                180 - MCU containing MC with Data and audio MP
                                110 - gateway containing MC with Data, Audio and Video MP
                                150 - gatekeeper containing MC with Data, Audio and Video MP
                                190 - MCU containing MC with Data, Audio and Video MP
                                240 - entity with active MC . "
                ::= { rasRegistrationTableEntry 13 }

rasRegistrationPregrantedARQ OBJECT-TYPE
             SYNTAX TruthValue
             MAX-ACCESS read-only
             STATUS current
             DESCRIPTION
                "This value indicates if pregranted ARQ exists."
                ::= { rasRegistrationTableEntry 14 }

rasRegistrationIsregisteredByRRQ OBJECT-TYPE
             SYNTAX TruthValue
             MAX-ACCESS read-only
             STATUS current
             DESCRIPTION
                "This value indicates if this endpoint was registered dynamically - True or statically - False."
                ::= { rasRegistrationTableEntry 15 }


        rasRegistrationAliasTable OBJECT-TYPE
             SYNTAX SEQUENCE OF RasRegistrationAliasTableEntry
             MAX-ACCESS not-accessible
             STATUS current
             DESCRIPTION
                "This table contains information about registered endpoint's aliases.
                 It is a list alias entries. The number of entries equals to the sum of
                 all aliases for all registered endpoints."
             ::= { rasRegistration 2 }

        rasRegistrationAliasTableEntry OBJECT-TYPE
             SYNTAX RasRegistrationAliasTableEntry
             MAX-ACCESS not-accessible
             STATUS current
             DESCRIPTION
                 "It contains an alias that corresponds to a registered endpoint."
             INDEX { ifIndex,
                     rasRegistrationCallSignallingAddressTag,
                     rasRegistrationCallSignallingAddress,
                     rasRegistrationAliasTableIndex}
               ::= { rasRegistrationAliasTable 1 }

        RasRegistrationAliasTableEntry ::=
              SEQUENCE {
            rasRegistrationAliasTableIndex
                    Integer32,
            rasRegistrationAliasTag
                    MmAliasTag,
            rasRegistrationAlias
                    MmAliasAddress

             }

        rasRegistrationAliasTableIndex OBJECT-TYPE
             SYNTAX Integer32
             MAX-ACCESS not-accessible
          STATUS current
             DESCRIPTION
                "An arbitrary index to this table. This index is one for the first alias for every given
                ras address. It is incremented by one for each subsequent alias of the same ras
                address. The last index for a particular ras address is equal to the number of
                aliases for that endpoint."
                ::= { rasRegistrationAliasTableEntry 1 }

       rasRegistrationAliasTag  OBJECT-TYPE
             SYNTAX MmAliasTag
             MAX-ACCESS read-only
             STATUS current
             DESCRIPTION
                "The alias tag of the registred endpoint."
                ::= { rasRegistrationAliasTableEntry 2 }

       rasRegistrationAlias OBJECT-TYPE
             SYNTAX MmAliasAddress
             MAX-ACCESS read-only
             STATUS current
             DESCRIPTION
                "The alias of the registred endpoint."
                ::= { rasRegistrationAliasTableEntry 3 }

      rasRegistrationRasAddressTable OBJECT-TYPE
             SYNTAX SEQUENCE OF RasRegistrationRasAddressTableEntry
             MAX-ACCESS not-accessible
             STATUS current
             DESCRIPTION
                "This table contains information about registered endpoint's
                 additional ras addresses. It is a list ras address entries.
                 The number of entries equals to the sum of all ras addresses
                 for all registered endpoints."
             ::= { rasRegistration 3 }

        rasRegistrationRasAddressTableEntry OBJECT-TYPE
             SYNTAX RasRegistrationRasAddressTableEntry
             MAX-ACCESS not-accessible
             STATUS current
             DESCRIPTION
                 "It contains a ras address that corresponds to the registered
                  endpoint call signaling address."
             INDEX { ifIndex,
                     rasRegistrationCallSignallingAddressTag,
                     rasRegistrationCallSignallingAddress,
                     rasRegistrationRasAddressTableIndex}
               ::= { rasRegistrationRasAddressTable 1 }

        RasRegistrationRasAddressTableEntry ::=
              SEQUENCE {
            rasRegistrationRasAddressTableIndex
                    Integer32,
            rasRegistrationAdditionalSrcRasAddressTag
                    MmTAddressTag,
            rasRegistrationAdditionalSrcRasAddress
                    TAddress
            }

        rasRegistrationRasAddressTableIndex OBJECT-TYPE
             SYNTAX Integer32
             MAX-ACCESS  not-accessible
             STATUS current
             DESCRIPTION
                "An arbitrary index to this table. This index is one for the first alias for every given
                 ras address. It is incremented by one for each subsequent alias of the same ras
                address. The last index for a particular ras address is equal to the number of
                aliases for that endpoint."
                ::= { rasRegistrationRasAddressTableEntry 1 }

        rasRegistrationAdditionalSrcRasAddressTag OBJECT-TYPE
             SYNTAX MmTAddressTag
             MAX-ACCESS read-only
             STATUS current
             DESCRIPTION
                "The transport address tag of the endpoint."
                ::= { rasRegistrationRasAddressTableEntry 2 }

        rasRegistrationAdditionalSrcRasAddress OBJECT-TYPE
             SYNTAX TAddress
             MAX-ACCESS read-only
             STATUS current
             DESCRIPTION
                "The transport address of the endpoint."
                ::= { rasRegistrationRasAddressTableEntry 3 }

       rasRegistrationCallSignalingAddressTable OBJECT-TYPE
             SYNTAX SEQUENCE OF RasRegistrationCallSignalingTableEntry
             MAX-ACCESS not-accessible
             STATUS current
             DESCRIPTION
                "This table contains information about registered endpoint's additional call
                 signaling adresses. It is a list of call signaling address entries.
                 The number of entries equals to the sum of all call signaling addresses for
                 all registered endpoints."
             ::= { rasRegistration 4 }

        rasRegistrationCallSignalingAddressTableEntry OBJECT-TYPE
             SYNTAX RasRegistrationCallSignalingTableEntry
             MAX-ACCESS not-accessible
             STATUS current
             DESCRIPTION
                 "It contains a call signaling address that corresponds to the registered endpoint."
             INDEX { ifIndex,
                     rasRegistrationCallSignallingAddressTag,
                     rasRegistrationCallSignallingAddress,
                     rasRegistrationCallSignalingAddressTableIndex}
               ::= { rasRegistrationCallSignalingAddressTable 1 }

        RasRegistrationCallSignalingTableEntry ::=
              SEQUENCE {
            rasRegistrationCallSignalingAddressTableIndex
                    Integer32,
            rasRegistrationAdditionalCallSignalingAddressTag
                    MmTAddressTag,
            rasRegistrationAdditionalCallSignalingAddress
                    TAddress
             }

        rasRegistrationCallSignalingAddressTableIndex OBJECT-TYPE
             SYNTAX Integer32
             MAX-ACCESS  not-accessible
             STATUS current
             DESCRIPTION
                "An arbitrary index to this table. This index is one for the first alias for every given
                 ras address. It is incremented by one for each subsequent alias of the same ras
                 address. The last index for a particular ras address is equal to the number of
                 aliases for that endpoint."
                ::= { rasRegistrationCallSignalingAddressTableEntry 1 }

       rasRegistrationAdditionalCallSignalingAddressTag OBJECT-TYPE
             SYNTAX MmTAddressTag
             MAX-ACCESS read-only
             STATUS current
             DESCRIPTION
                "The transport address tag of the endpoint."
                ::= { rasRegistrationCallSignalingAddressTableEntry 2 }

       rasRegistrationAdditionalCallSignalingAddress OBJECT-TYPE
             SYNTAX TAddress
             MAX-ACCESS read-only
             STATUS current
             DESCRIPTION
                "The endpoint call signalling address."
                ::= { rasRegistrationCallSignalingAddressTableEntry 3 }

       rasAdmissionTable OBJECT-TYPE
             SYNTAX SEQUENCE OF RasAdmissionTableEntry
             MAX-ACCESS not-accessible
             STATUS current
             DESCRIPTION
                "This table contains information about entities that have been admitted
                 by the gatekeeper. It is a list of admitted endpoints. The number of entries
                 equals to the number of admitted endpoints."
             ::= { rasAdmission 1 }

       rasAdmissionTableEntry OBJECT-TYPE
             SYNTAX RasAdmissionTableEntry
             MAX-ACCESS not-accessible
             STATUS current
             DESCRIPTION
                 "It contains objects that describe endpoints that are
                  admitted by the gatekeeper. "
             INDEX { ifIndex,
                     rasAdmissionSrcCallSignallingAddress,
                     rasAdmissionRasAddress,
                     rasAdmissionCallIdentifier }
                   ::= { rasAdmissionTable 1 }

         RasAdmissionTableEntry ::=
              SEQUENCE {
              rasAdmissionSrcCallSignallingAddressTag
                    MmTAddressTag,
              rasAdmissionSrcCallSignallingAddress
                    TAddress,
              rasAdmissionDestCallSignallingAddressTag
                    MmTAddressTag,
              rasAdmissionDestCallSignallingAddress
                    TAddress,
              rasAdmissionCallIdentifier
                    MmGlobalIdentifier,
              rasAdmissionConferenceId
                    MmGlobalIdentifier,
              rasAdmissionRasAddressTag
                    MmTAddressTag,
              rasAdmissionRasAddress
                    TAddress,
              rasAdmissionCRV
                    MmH225Crv,
              rasAdmissionIsGatekeeper
                     TruthValue,
              rasAdmissionSrcAliasAddressTag
                    MmAliasTag,
              rasAdmissionSrcAliasAddress
                    MmAliasAddress,
              rasAdmissionDestAliasAddressTag
                    MmAliasTag,
              rasAdmissionDestAliasAddress
                    MmAliasAddress,
              rasAdmissionAnswerCallIndicator
                    INTEGER,
              rasAdmissionTime
                    DateAndTime,
              rasAdmissionEndpointId
                    MmEndpointID,
              rasAdmissionBandwidth
                    Integer32,
              rasAdmissionIRRFrequency
                    Integer32,
              rasAdmissionCallType
                     MmCallType,
              rasAdmissionCallModel
                    INTEGER,
              rasAdmissionSrcHandlesBandwidth
                    TruthValue,
              rasAdmissionDestHandlesBandwidth
                    TruthValue,
              rasAdmissionSecurity
                    TruthValue,
              rasAdmissionSrcWillSupplyUUIE
                    TruthValue,
              rasAdmissionDestWillSupplyUUIE
                    TruthValue,
              rasAdmissionTableRowStatus
                    RowStatus
              }

        rasAdmissionSrcCallSignallingAddressTag OBJECT-TYPE
             SYNTAX MmTAddressTag
             MAX-ACCESS  read-only
             STATUS current
             DESCRIPTION
                "The transport address tag of the endpoint."
                ::= { rasAdmissionTableEntry 1 }

       rasAdmissionSrcCallSignallingAddress OBJECT-TYPE
             SYNTAX TAddress
             MAX-ACCESS  not-accessible
             STATUS current
             DESCRIPTION
                "The call signalling address of the caller."
                ::= { rasAdmissionTableEntry 2 }

        rasAdmissionDestCallSignallingAddressTag OBJECT-TYPE
             SYNTAX MmTAddressTag
             MAX-ACCESS read-only
             STATUS current
             DESCRIPTION
                "The transport address tag of the endpoint."
                ::= { rasAdmissionTableEntry 3 }

        rasAdmissionDestCallSignallingAddress OBJECT-TYPE
             SYNTAX TAddress
             MAX-ACCESS read-only
             STATUS current
             DESCRIPTION
                "The call signalling address of the callee."
                ::= { rasAdmissionTableEntry 4 }

        rasAdmissionCallIdentifier OBJECT-TYPE
             SYNTAX MmGlobalIdentifier
             MAX-ACCESS  not-accessible
             STATUS current
             DESCRIPTION
                "Call identifier."
                ::= { rasAdmissionTableEntry 5 }

       rasAdmissionConferenceId OBJECT-TYPE
             SYNTAX MmGlobalIdentifier
             MAX-ACCESS read-only
             STATUS current
             DESCRIPTION
                "Conference identifier."
                ::= { rasAdmissionTableEntry 6 }

       rasAdmissionRasAddressTag OBJECT-TYPE
             SYNTAX MmTAddressTag
             MAX-ACCESS read-only
             STATUS current
             DESCRIPTION
                "The transport address tag of the endpoint."
                ::= { rasAdmissionTableEntry 7 }

        rasAdmissionRasAddress OBJECT-TYPE
             SYNTAX TAddress
             MAX-ACCESS not-accessible
          STATUS current
             DESCRIPTION
                "The call signalling address of the caller."
                ::= { rasAdmissionTableEntry 8 }

        rasAdmissionCRV OBJECT-TYPE
             SYNTAX MmH225Crv
             MAX-ACCESS read-only
             STATUS current
             DESCRIPTION
                "Call reference value of the caller. "
                ::= { rasAdmissionTableEntry 9 }

        rasAdmissionIsGatekeeper OBJECT-TYPE
               SYNTAX TruthValue
               MAX-ACCESS read-only
               STATUS current
               DESCRIPTION
                "This value identifies the endpoint being a gatekeeper."
                ::= { rasAdmissionTableEntry 10 }

        rasAdmissionSrcAliasAddressTag OBJECT-TYPE
             SYNTAX MmAliasTag
             MAX-ACCESS read-only
             STATUS current
             DESCRIPTION
                "The alias address tag of the calling endpoint."
                ::= { rasAdmissionTableEntry 11 }

        rasAdmissionSrcAliasAddress OBJECT-TYPE
             SYNTAX MmAliasAddress
             MAX-ACCESS read-only
             STATUS current
             DESCRIPTION
                "The call alias address of the caller."
                ::= { rasAdmissionTableEntry 12 }

        rasAdmissionDestAliasAddressTag OBJECT-TYPE
             SYNTAX MmAliasTag
             MAX-ACCESS read-only
             STATUS current
             DESCRIPTION
                "The alias address tag of the called endpoint."
                ::= { rasAdmissionTableEntry 13 }

        rasAdmissionDestAliasAddress OBJECT-TYPE
             SYNTAX MmAliasAddress
             MAX-ACCESS read-only
             STATUS current
             DESCRIPTION
                "The alias address of the callee."
                ::= { rasAdmissionTableEntry 14 }

        rasAdmissionAnswerCallIndicator OBJECT-TYPE
             SYNTAX INTEGER { caller (1), callee (2)}
             MAX-ACCESS read-only
             STATUS current
             DESCRIPTION
                "Caller/callee. "
                ::= { rasAdmissionTableEntry 15 }

        rasAdmissionTime OBJECT-TYPE
             SYNTAX DateAndTime
             MAX-ACCESS read-only
             STATUS current
             DESCRIPTION
                "Thetime of the admission."
                ::= { rasAdmissionTableEntry 16 }

        rasAdmissionEndpointId OBJECT-TYPE
             SYNTAX MmEndpointID
             MAX-ACCESS read-only
             STATUS current
             DESCRIPTION
                "Endpoint identifier."
                ::= { rasAdmissionTableEntry 17 }

       rasAdmissionBandwidth  OBJECT-TYPE
             SYNTAX Integer32
             MAX-ACCESS read-only
             STATUS current
             DESCRIPTION
                "The allowed maximum bandwidth for the call; may be less than requested
                 by the endpoint. "
                ::= { rasAdmissionTableEntry 18 }

        rasAdmissionIRRFrequency  OBJECT-TYPE
             SYNTAX Integer32
             MAX-ACCESS read-only
             STATUS current
             DESCRIPTION
                "The time interval in seconds in which the endpoint shall send IRRs to
                 the gatekeeper while on a call. "
                ::= { rasAdmissionTableEntry 19 }

        rasAdmissionCallType OBJECT-TYPE
             SYNTAX MmCallType
             MAX-ACCESS read-only
             STATUS current
             DESCRIPTION
                "Using this value, gatekeeper can attempt to determine real bandwidth usage. "
                ::= { rasAdmissionTableEntry 20 }

        rasAdmissionCallModel OBJECT-TYPE
             SYNTAX INTEGER { direct (1), gatekeeperRouted (2)}
             MAX-ACCESS read-only
             STATUS current
             DESCRIPTION
                "This value of gatekeeper indicates that call signaling is being passed
                via the gatekeeper, while direct indicates that the endpoint-to-endpoint
                call mode is in use. "
                ::= { rasAdmissionTableEntry 21 }

       rasAdmissionSrcHandlesBandwidth OBJECT-TYPE
             SYNTAX TruthValue
             MAX-ACCESS read-only
             STATUS current
             DESCRIPTION
                "This value indicates that the caller reserves its own bandwidth. "
                ::= { rasAdmissionTableEntry 22 }

         rasAdmissionDestHandlesBandwidth OBJECT-TYPE
             SYNTAX TruthValue
             MAX-ACCESS read-only
             STATUS current
             DESCRIPTION
                "This value indicates that the calee reserves its own bandwidth. "
                 ::= { rasAdmissionTableEntry 23 }

         rasAdmissionSecurity OBJECT-TYPE
             SYNTAX TruthValue
             MAX-ACCESS read-only
             STATUS current
             DESCRIPTION
                "This value indicates that the endpoint is using security. "
                ::= { rasAdmissionTableEntry 24 }

         rasAdmissionSrcWillSupplyUUIE OBJECT-TYPE
             SYNTAX TruthValue
             MAX-ACCESS read-only
             STATUS current
             DESCRIPTION
                "This value indicates that the caller will supply Q.931 message info in IRR messages if requested by the gatekeeper "
                ::= { rasAdmissionTableEntry 25 }

         rasAdmissionDestWillSupplyUUIE OBJECT-TYPE
             SYNTAX TruthValue
             MAX-ACCESS read-only
             STATUS current
             DESCRIPTION
                "This value indicates that the callee will supply Q.931 message info in
                IRR messages if requested by the gatekeeper "
                ::= { rasAdmissionTableEntry 26 }

         rasAdmissionTableRowStatus OBJECT-TYPE
             SYNTAX     RowStatus
             MAX-ACCESS read-create
             STATUS     current
             DESCRIPTION
                "The row status of the entry. This object is required to create
                 or delete rows remotely by a manager. "
                ::= { rasAdmissionTableEntry 27 }

         rasStatsTable OBJECT-TYPE
             SYNTAX SEQUENCE OF RasStatsTableEntry
             MAX-ACCESS not-accessible
             STATUS current
             DESCRIPTION
                "This table contains information about ras statistics variables.
                It is a list of ras statistics variables entries. The number of entries
                equals to the number of statistics variables."
             ::= { rasStats 1 }

         rasStatsTableEntry OBJECT-TYPE
             SYNTAX RasStatsTableEntry
             MAX-ACCESS not-accessible
             STATUS current
             DESCRIPTION
                 "It contains objects that describe the ras statistics variables."
             INDEX { ifIndex }
                      ::= { rasStatsTable 1 }

         RasStatsTableEntry ::=
              SEQUENCE {
              rasStatsGatekeeperConfirms
                    Counter32,
              rasStatsGatekeeperRejects
                    Counter32,
              rasStatsRegistrationConfirms
                    Counter32,
              rasStatsRegistrationRejects
                    Counter32,
              rasStatsUnregistrationConfirms
                    Counter32,
              rasStatsUnregistrationRejects
                    Counter32,
              rasStatsAdmissionConfirms
                    Counter32,
              rasStatsAdmissionRejects
                    Counter32,
              rasStatsBandwidthConfirms
                    Counter32,
              rasStatsBandwidthRejects
                    Counter32,
              rasStatsDisengageConfirms
                    Counter32,
              rasStatsDisengageRejects
                    Counter32,
              rasStatsLocationConfirms
                    Counter32,
              rasStatsLocationRejects
                    Counter32,
              rasStatsInfoRequests
                    Counter32,
              rasStatsInfoRequestResponses
                    Counter32,
              rasStatsnonStandardMessages
                    Counter32,
              rasStatsUnknownMessages
                    Counter32,
              rasStatsRequestInProgress
                    Counter32,
              rasStatsResourceAvailabilityIndicator
                    Counter32,
              rasStatsResourceAvailabilityConfirm
                    Counter32,
              rasStatsRegisteredEndpointsNo
                    Counter32,
              rasStatsAdmittedEndpointsNo
                    Counter32,
              rasStatsINAKs
                    Counter32,
              rasStatsIACKs
                    Counter32,
              rasStatsGkRoutedCalls
                    Counter32,
              rasStatsResourceAvailabilityIndications
                    Counter32,
              rasStatsResourceAvailabilityConfirmations
                    Counter32
              }

         rasStatsGatekeeperConfirms OBJECT-TYPE
             SYNTAX  Counter32
             MAX-ACCESS  read-only
             STATUS  current
             DESCRIPTION
                "The number of granting permission to register messages sent by or
                received from a gatekeeper."
                 ::= { rasStatsTableEntry 1 }

         rasStatsGatekeeperRejects OBJECT-TYPE
             SYNTAX  Counter32
             MAX-ACCESS  read-only
             STATUS  current
             DESCRIPTION
                "The number of declining permission to register messages sent by or
                 received from a gatekeeper."
                 ::= { rasStatsTableEntry 2 }

        rasStatsRegistrationConfirms OBJECT-TYPE
             SYNTAX  Counter32
             MAX-ACCESS  read-only
             STATUS  current
             DESCRIPTION
                "The number of registration confirm messages sent by or
                 received from a gatekeeper."
                 ::= { rasStatsTableEntry 3 }

         rasStatsRegistrationRejects OBJECT-TYPE
             SYNTAX  Counter32
             MAX-ACCESS  read-only
             STATUS  current
             DESCRIPTION
                "The number of registration reject messages sent by or
                 received from a gatekeeper."
                 ::= { rasStatsTableEntry 4 }

       rasStatsUnregistrationConfirms OBJECT-TYPE
             SYNTAX  Counter32
             MAX-ACCESS  read-only
             STATUS  current
             DESCRIPTION
                "The number of unregistration confirmation messages received."
                 ::= { rasStatsTableEntry 5 }

        rasStatsUnregistrationRejects OBJECT-TYPE
             SYNTAX  Counter32
             MAX-ACCESS  read-only
             STATUS  current
             DESCRIPTION
                "The number of unregistration reject messages received."
                 ::= { rasStatsTableEntry 6 }

       rasStatsAdmissionConfirms OBJECT-TYPE
             SYNTAX  Counter32
             MAX-ACCESS  read-only
             STATUS  current
             DESCRIPTION
                "The number of admission request messages sent by or
                 received from a gatekeeper."
                 ::= { rasStatsTableEntry 7 }

         rasStatsAdmissionRejects OBJECT-TYPE
             SYNTAX  Counter32
             MAX-ACCESS  read-only
             STATUS  current
             DESCRIPTION
                "The number of admission reject messages sent by or
                 received from a gatekeeper."
                 ::= { rasStatsTableEntry 8 }

        rasStatsBandwidthConfirms OBJECT-TYPE
             SYNTAX  Counter32
             MAX-ACCESS  read-only
             STATUS  current
             DESCRIPTION
                "The number of bandwidth confirm messages
                 received from a gatekeeper."
                 ::= { rasStatsTableEntry 9 }

       rasStatsBandwidthRejects OBJECT-TYPE
             SYNTAX  Counter32
             MAX-ACCESS  read-only
             STATUS  current
             DESCRIPTION
                "The number of bandwidth reject messages sent by or
                 received from a gatekeeper."
                 ::= { rasStatsTableEntry 10 }

       rasStatsDisengageConfirms OBJECT-TYPE
             SYNTAX  Counter32
             MAX-ACCESS  read-only
             STATUS  current
             DESCRIPTION
                "The number of disengage confirm messages
                 received from a gatekeeper."
                 ::= { rasStatsTableEntry 11 }

        rasStatsDisengageRejects OBJECT-TYPE
             SYNTAX  Counter32
             MAX-ACCESS  read-only
             STATUS  current
             DESCRIPTION
                "The number of disengage reject messages sent by
                 a gatekeeper."
                 ::= { rasStatsTableEntry 12 }

       rasStatsLocationConfirms OBJECT-TYPE
             SYNTAX  Counter32
             MAX-ACCESS  read-only
             STATUS  current
             DESCRIPTION
                "The number of location confirm messages sent by or
                 received from a gatekeeper."
                 ::= { rasStatsTableEntry 13 }

       rasStatsLocationRejects OBJECT-TYPE
             SYNTAX  Counter32
             MAX-ACCESS  read-only
             STATUS  current
             DESCRIPTION
                "The number of location reject messages sent by or
                 received from a gatekeeper."
                 ::= { rasStatsTableEntry 14 }

        rasStatsInfoRequests OBJECT-TYPE
             SYNTAX  Counter32
             MAX-ACCESS  read-only
             STATUS  current
             DESCRIPTION
                "The number of info request messages sent
                 by a gatekeeper."
                 ::= { rasStatsTableEntry 15 }

         rasStatsInfoRequestResponses OBJECT-TYPE
             SYNTAX  Counter32
             MAX-ACCESS  read-only
             STATUS  current
             DESCRIPTION
                "The number of info request response messages sent by endpoint or
                 received by a gatekeeper."
                 ::= { rasStatsTableEntry 16 }

         rasStatsnonStandardMessages OBJECT-TYPE
             SYNTAX  Counter32
             MAX-ACCESS  read-only
             STATUS  current
             DESCRIPTION
                "The number of non standard messages received/sent."
                 ::= { rasStatsTableEntry 17 }

      rasStatsUnknownMessages OBJECT-TYPE
             SYNTAX  Counter32
             MAX-ACCESS  read-only
             STATUS  current
             DESCRIPTION
                "The number of unknown messages received."
                 ::= { rasStatsTableEntry 18 }

      rasStatsRequestInProgress OBJECT-TYPE
             SYNTAX  Counter32
             MAX-ACCESS  read-only
             STATUS  current
             DESCRIPTION
                "The number of request in progress messages received."
                 ::= { rasStatsTableEntry 19 }

       rasStatsResourceAvailabilityIndicator OBJECT-TYPE
             SYNTAX  Counter32
             MAX-ACCESS  read-only
             STATUS  current
             DESCRIPTION
                "The number of resource availability indicator messages sent by the endpoint."
                 ::= { rasStatsTableEntry 20 }

         rasStatsResourceAvailabilityConfirm OBJECT-TYPE
             SYNTAX  Counter32
             MAX-ACCESS  read-only
             STATUS  current
             DESCRIPTION
                "The number of availability confirm messages received."
                 ::= { rasStatsTableEntry 21 }

         rasStatsRegisteredEndpointsNo OBJECT-TYPE
              SYNTAX  Counter32
              MAX-ACCESS  read-only
              STATUS  current
              DESCRIPTION
                "The number of registered endpoints."
                 ::= { rasStatsTableEntry 22 }

         rasStatsAdmittedEndpointsNo OBJECT-TYPE
              SYNTAX  Counter32
              MAX-ACCESS  read-only
              STATUS  current
              DESCRIPTION
                "The number of admitted endpoints."
                 ::= { rasStatsTableEntry 23 }

          rasStatsINAKs OBJECT-TYPE
              SYNTAX  Counter32
              MAX-ACCESS  read-only
              STATUS  current
              DESCRIPTION
                "The number of INAK massages received and sent by the endpoint."
                 ::= { rasStatsTableEntry 24 }

           rasStatsIACKs OBJECT-TYPE
              SYNTAX  Counter32
              MAX-ACCESS  read-only
              STATUS  current
              DESCRIPTION
                "The number of IACKs massages received and sent by the endpoint."
                 ::= { rasStatsTableEntry 25 }

       rasStatsGkRoutedCalls OBJECT-TYPE
              SYNTAX Counter32
              MAX-ACCESS  read-only
              STATUS  current
              DESCRIPTION
                "The number of calls that are routed through Gatekeeper."
                 ::= { rasStatsTableEntry 26 }

       rasStatsResourceAvailabilityIndications OBJECT-TYPE
              SYNTAX Counter32
              MAX-ACCESS  read-only
              STATUS  current
              DESCRIPTION
                "The number of RAI massages received and sent by the endpoint."
                 ::= { rasStatsTableEntry 27 }

       rasStatsResourceAvailabilityConfirmations OBJECT-TYPE
              SYNTAX Counter32
              MAX-ACCESS  read-only
              STATUS  current
              DESCRIPTION
                "The number of RAC massages received and sent by the endpoint."
                 ::= { rasStatsTableEntry 28 }

       lastArjReason OBJECT-TYPE
              SYNTAX INTEGER { calledPartyNotRegistered (1), invalidPermission(2),
                               requestDenied(3), undefinedReason (4),
                               callerNotRegistered(5), routeCallToGatekeeper (6),
                               invalidEndpointIdentifier(7), resourceUnavailable(8),
                               securityDenial(9), qosControlNotSupported(10),
                               incompleteAddress (11)}
              MAX-ACCESS read-only
              STATUS current
              DESCRIPTION
                 "This value identifies the reason for the admission reject."
                  ::= { rasEvents 1 }

       lastArjRasAddressTag OBJECT-TYPE
             SYNTAX MmTAddressTag
             MAX-ACCESS read-only
             STATUS current
             DESCRIPTION
                "The transport address tag of the endpoint."
                ::= { rasEvents 2 }

       lastArjRasAddress OBJECT-TYPE
             SYNTAX TAddress
             MAX-ACCESS read-only
             STATUS current
             DESCRIPTION
                "The ras address of the endpoint."
                ::= { rasEvents  3 }

       admissionReject NOTIFICATION-TYPE
            OBJECTS   { ifIndex ,lastArjReason, lastArjRasAddressTag, lastArjRasAddress }
            STATUS current
            DESCRIPTION
                 "This message will be sent on generation and reception of
                  admissionReject for the following reasons:
                  1 - calledPartyNotRegistered
                  2 - invalidPermission
                  3 - requestDenied
                  4 - undefinedReason
                  5 - callerNotRegistered
                  6 - routeCallToGatekeeper
                  7 - invalidEndpointIdentifier
                  8 - resourceUnavailable
                  9 - securityDenial
                  10 - qosControlNotSupported
                  11 - incompleteAddress
                  "
                  ::= {rasEvents 4}

-- conformance; stating the mandatory requirements for the MIB


--
-- CONFORMANCE
--

rasMIBConformance    OBJECT IDENTIFIER ::= { ras 6 }
rasMIBGroups         OBJECT IDENTIFIER ::= { rasMIBConformance 1 }

--
-- Groups for Conformance
--

rasConfigurationGroup OBJECT-GROUP
    OBJECTS {
    rasConfigurationTimer,
    rasConfigurationMaxNumberOfRetries
    }
    STATUS  current
    DESCRIPTION
       "."
    ::= { rasMIBGroups 1 }


rasRegistrationGroup    OBJECT-GROUP
    OBJECTS {

    rasRegistrationIsGatekeeper,
    rasRegistrationGatekeeperId,
    rasRegistrationEndpointId,

    rasRegistrationEncryption,
    rasRegistrationWillSupplyUUIE,
    rasRegistrationIntegrityCheckValue,
    rasRegistrationTableNumberOfAliases,
    rasRegistrationEndpointType,
    rasRegistrationPregrantedARQ,
    rasRegistrationAlias
    }
    STATUS  current
    DESCRIPTION
       "."
    ::= { rasMIBGroups 2 }

rasAdmissionGroup    OBJECT-GROUP
    OBJECTS {
    rasAdmissionConferenceId,
    rasAdmissionRasAddressTag,
    rasAdmissionCRV,
    rasAdmissionIsGatekeeper,
    rasAdmissionSrcCallSignallingAddressTag,
    rasAdmissionDestCallSignallingAddressTag,
    rasAdmissionDestCallSignallingAddress,
    rasAdmissionSrcAliasAddressTag,
    rasAdmissionSrcAliasAddress,
    rasAdmissionDestAliasAddressTag,
    rasAdmissionDestAliasAddress,
    rasAdmissionAnswerCallIndicator,
    rasAdmissionTime,
    rasAdmissionEndpointId,
    rasAdmissionBandwidth,
    rasAdmissionIRRFrequency,
    rasAdmissionCallType,
    rasAdmissionCallModel,
    rasAdmissionSrcHandlesBandwidth,
    rasAdmissionDestHandlesBandwidth,
    rasAdmissionSecurity,
    rasAdmissionSrcWillSupplyUUIE,
    rasAdmissionDestWillSupplyUUIE
    }
    STATUS  current
    DESCRIPTION
       "."
    ::= { rasMIBGroups 3 }

rasStatsGroup    OBJECT-GROUP
    OBJECTS {
         rasStatsGatekeeperConfirms,
         rasStatsGatekeeperRejects,
         rasStatsRegistrationConfirms,
         rasStatsRegistrationRejects,
         rasStatsUnregistrationConfirms,
         rasStatsUnregistrationRejects,
         rasStatsAdmissionConfirms,
         rasStatsAdmissionRejects,
         rasStatsBandwidthConfirms,
         rasStatsBandwidthRejects,
         rasStatsDisengageConfirms,
         rasStatsDisengageRejects,
         rasStatsLocationConfirms,
         rasStatsLocationRejects,
         rasStatsInfoRequests,
         rasStatsInfoRequestResponses,
         rasStatsnonStandardMessages,
         rasStatsUnknownMessages,
         rasStatsRequestInProgress,
         rasStatsResourceAvailabilityIndicator,
         rasStatsResourceAvailabilityConfirm,
         rasStatsRegisteredEndpointsNo,
         rasStatsAdmittedEndpointsNo,
         rasStatsINAKs,
         rasStatsIACKs,
         rasStatsGkRoutedCalls,
         rasStatsResourceAvailabilityIndications,
         rasStatsResourceAvailabilityConfirmations
    }
    STATUS  current
    DESCRIPTION
       "."
    ::= { rasMIBGroups 4 }

rasEventsGroup    OBJECT-GROUP
    OBJECTS {
     lastArjReason,
     lastArjRasAddressTag,
     lastArjRasAddress
    }
    STATUS  current
    DESCRIPTION
       "."
    ::= { rasMIBGroups 5 }


rasMIBCompliance        MODULE-COMPLIANCE
    STATUS      current
    DESCRIPTION
        "The set of objects required for compliance."
    MODULE
        MANDATORY-GROUPS { rasRegistrationGroup, rasAdmissionGroup, rasStatsGroup, rasEventsGroup }
   ::= { rasMIBConformance 2 }

END
