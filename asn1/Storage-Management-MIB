-->#
--># Copyright (C) Siemens AG 1998
-->#               All rights reserved
-->#
-->#protocol specification
-->%PROTOCOL SNMP
-->#
-->#configuration
-->%REMCONFIG NO
-->%REMOPERATION NO
-->#

Storage-Management-MIB DEFINITIONS ::= BEGIN
--  MIB-Version: 4

--
-- Title:   MIB for the BS2000 Storage Management V1.0
-- Date:    Oktober 1995
-- Authors: Birgit Lamers        BS2000 OS45
--          Reinhard Unterstein  BS2000 OS45
--
--
-- Update:  September 1998
--
-- Erweiterungen:   sniStorMgmtGlobalData
--                  sniStorMgmtPubsetInfo
--                  sniStorMgmtDiskInfo
--                  sniStorMgmtTraps
--
-- Author:  Rudolph DC3
--
--
--


IMPORTS
	TRAP-TYPE FROM RFC-1215
	enterprises
	    FROM RFC1155-SMI
	DisplayString
	    FROM RFC1213-MIB
	OBJECT-TYPE
	    FROM RFC-1212;


sni                        OBJECT IDENTIFIER ::= { enterprises 231 }
sniProductMibs             OBJECT IDENTIFIER ::= { sni 2 }
sniStorMgmt                OBJECT IDENTIFIER ::= { sniProductMibs 20 }
sniStorMgmtAvailInfo       OBJECT IDENTIFIER ::= { sniStorMgmt 1 }
sniStorMgmtProductInfo     OBJECT IDENTIFIER ::= { sniStorMgmtAvailInfo 1 }
sniStorMgmtHsmsInfo        OBJECT IDENTIFIER ::= { sniStorMgmtAvailInfo 2 }
sniStorMgmtMarenInfo       OBJECT IDENTIFIER ::= { sniStorMgmtAvailInfo 3 }
sniStorMgmtTlsInfo         OBJECT IDENTIFIER ::= { sniStorMgmtAvailInfo 4 }
sniStorMgmtRobarInfo       OBJECT IDENTIFIER ::= { sniStorMgmtAvailInfo 5 }
sniStorMgmtResourceInfo    OBJECT IDENTIFIER ::= { sniStorMgmt 2 }
sniStorMgmtPubsetInfo      OBJECT IDENTIFIER ::= { sniStorMgmt 3 }
sniStorMgmtDiskInfo        OBJECT IDENTIFIER ::= { sniStorMgmt 4 }
sniStorMgmtGlobalData      OBJECT IDENTIFIER ::= { sniStorMgmt 18 }
sniStorMgmtPubsetTraps     OBJECT IDENTIFIER ::= { sniStorMgmt 20 }
sniStorMgmtDiskTraps       OBJECT IDENTIFIER ::= { sniStorMgmt 21 }


-- Storage Management Availability Infos

-- Storage Management Product Infos

storMgmtProductTabNum             OBJECT-TYPE
	SYNTAX  INTEGER
	ACCESS  read-only
	STATUS  mandatory
	DESCRIPTION "The number of entries in the table storMgmtProductTable"
	::= {sniStorMgmtProductInfo 1}

storMgmtProductTable           OBJECT-TYPE
	SYNTAX  SEQUENCE OF StorMgmtProductEntry
	ACCESS  not-accessible
	STATUS  mandatory
	DESCRIPTION "The Storage management information table"
	::= {sniStorMgmtProductInfo 2}

storMgmtProductEntry        OBJECT-TYPE
	SYNTAX  StorMgmtProductEntry
	ACCESS  not-accessible
	STATUS  mandatory
	DESCRIPTION "An entry in the table"
	INDEX {storMgmtProductIndex}
	::= {storMgmtProductTable 1}


StorMgmtProductEntry ::=
	SEQUENCE 
	{
	    storMgmtProductIndex                INTEGER,
	    storMgmtProductName                 DisplayString,
	    storMgmtProductVersion              DisplayString,
	    storMgmtProductState                INTEGER,
	    storMgmtProductTimestamp            DisplayString
	}

storMgmtProductIndex   OBJECT-TYPE
	SYNTAX  INTEGER
	ACCESS  read-only
	STATUS  mandatory
	DESCRIPTION "A unique value for each entry, its value
	    	     ranges between 1 and the value of storMgmtProductTabNum"
	::= {storMgmtProductEntry 1}

storMgmtProductName       OBJECT-TYPE
	SYNTAX  DisplayString
	ACCESS  read-only
	STATUS  mandatory
	DESCRIPTION "The name of the product itself"
	::= {storMgmtProductEntry 2}

storMgmtProductVersion    OBJECT-TYPE
	SYNTAX  DisplayString
	ACCESS  read-only
	STATUS  mandatory
	DESCRIPTION "The installed version of the specified product"
	::= {storMgmtProductEntry 3}

storMgmtProductState                OBJECT-TYPE
	SYNTAX  INTEGER 
	{
		 created       (1),
		 not-created   (2),
		 in-delete     (3),
		 in-create     (4),
		 in-resume     (5),
		 in-hold       (6),
		 not-resumed   (7),
		 locked        (8),
		 not-installed (255)
	}
	ACCESS  read-only
	STATUS  mandatory
	DESCRIPTION "Current state of the product"
	::= {storMgmtProductEntry 4}

storMgmtProductTimestamp       OBJECT-TYPE
	SYNTAX  DisplayString
	ACCESS  read-only
	STATUS  mandatory
	DESCRIPTION "Status timestamp (only for started and stopped state)"
	::= {storMgmtProductEntry 5}


-- Storage Management HSMS Infos

storMgmtHsmsOpmode              OBJECT-TYPE
	SYNTAX  INTEGER
	{
	   defineshow  (1),
	   simulation  (2),
	   operation   (3)
	}
	ACCESS  read-write
	STATUS  mandatory
	DESCRIPTION "The current operational mode specifies the scope
		     of actions to be performed by HSMS"
	::= {sniStorMgmtHsmsInfo 1}

storMgmtHsmsModeTimestamp          OBJECT-TYPE
	SYNTAX  DisplayString
	ACCESS  read-write
	STATUS  mandatory
	DESCRIPTION "Mode timestamp"
	::= {sniStorMgmtHsmsInfo 2}

storMgmtHsmsServertask          OBJECT-TYPE
	SYNTAX  INTEGER (0..99)
	ACCESS  read-write
	STATUS  mandatory
	DESCRIPTION "Number of current server tasks"
	::= {sniStorMgmtHsmsInfo 3}

storMgmtHsmsWaitJobs         OBJECT-TYPE
	SYNTAX  INTEGER
	ACCESS  read-only
	STATUS  mandatory
	DESCRIPTION "Number of waiting jobs (state is ACCEPTED)"
	::= {sniStorMgmtHsmsInfo 4}

storMgmtHsmsInstances          OBJECT-TYPE
	SYNTAX  INTEGER
	ACCESS  read-only
	STATUS  mandatory
	DESCRIPTION ""
	::= {sniStorMgmtHsmsInfo 5}

storMgmtHsmsAcceptReqs          OBJECT-TYPE
	SYNTAX  INTEGER
	ACCESS  read-only
	STATUS  mandatory
	DESCRIPTION ""
	::= {sniStorMgmtHsmsInfo 6}

storMgmtHsmsCompleteReqs          OBJECT-TYPE
	SYNTAX  INTEGER
	ACCESS  read-only
	STATUS  mandatory
	DESCRIPTION ""
	::= {sniStorMgmtHsmsInfo 7}

storMgmtHsmsInterruptReqs          OBJECT-TYPE
	SYNTAX  INTEGER
	ACCESS  read-only
	STATUS  mandatory
	DESCRIPTION ""
	::= {sniStorMgmtHsmsInfo 8}

storMgmtHsmsWaitReqsRead          OBJECT-TYPE
	SYNTAX  INTEGER
	ACCESS  read-only
	STATUS  mandatory
	DESCRIPTION ""
	::= {sniStorMgmtHsmsInfo 9}

storMgmtHsmsWaitReqsWrite          OBJECT-TYPE
	SYNTAX  INTEGER
	ACCESS  read-only
	STATUS  mandatory
	DESCRIPTION ""
	::= {sniStorMgmtHsmsInfo 10}

storMgmtHsmsWaitReqsExpress          OBJECT-TYPE
	SYNTAX  INTEGER
	ACCESS  read-only
	STATUS  mandatory
	DESCRIPTION ""
	::= {sniStorMgmtHsmsInfo 11}

storMgmtHsmsStimeRead          OBJECT-TYPE
	SYNTAX  INTEGER
	ACCESS  read-only
	STATUS  mandatory
	DESCRIPTION ""
	::= {sniStorMgmtHsmsInfo 12}

storMgmtHsmsStimeWrite          OBJECT-TYPE
	SYNTAX  INTEGER
	ACCESS  read-only
	STATUS  mandatory
	DESCRIPTION ""
	::= {sniStorMgmtHsmsInfo 13}

storMgmtHsmsStimeExpress          OBJECT-TYPE
	SYNTAX  INTEGER
	ACCESS  read-only
	STATUS  mandatory
	DESCRIPTION ""
	::= {sniStorMgmtHsmsInfo 14}

storMgmtHsmsNetload          OBJECT-TYPE
	SYNTAX  INTEGER
	ACCESS  read-only
	STATUS  mandatory
	DESCRIPTION "Netload (in Bytes) while performing a backup"
	::= {sniStorMgmtHsmsInfo 15}

storMgmtHsmsS1Bottleneck     TRAP-TYPE
	      ENTERPRISE sniStorMgmtHsmsInfo
	      DESCRIPTION "Sending a TRAP, if the agent sees the message
			   HSM0468 for S1 bottleneck"
      ::= 1


-- Storage Management MAREN Infos

storMgmtMarenCPTask              OBJECT-TYPE
	SYNTAX  DisplayString (SIZE (0..32))
	ACCESS  read-only
	STATUS  mandatory
	DESCRIPTION "Is MARENCP running?"
	::= {sniStorMgmtMarenInfo 1}

storMgmtMarenUCPTask             OBJECT-TYPE
	SYNTAX  DisplayString (SIZE (0..32))
	ACCESS  read-only
	STATUS  mandatory
	DESCRIPTION "Is MARENUCP running?"
	::= {sniStorMgmtMarenInfo 2}

storMgmtMarenCatConn              OBJECT-TYPE
	SYNTAX  INTEGER 
	{
	   spd       (1),
	   rfalocal  (2),
	   rfaremote (3)
	}
	ACCESS  read-only
	STATUS  mandatory
	DESCRIPTION "Type of connection to the MAREN catalogue;
		     the access to the catalogue is possible via
		     a shared privat disk or via a RFA connection
		     (local or remote)"
	::= {sniStorMgmtMarenInfo 3}

storMgmtMarenConnState              OBJECT-TYPE
	SYNTAX  INTEGER 
	{
	   active    (1),
	   inactive  (2)
	}
	ACCESS  read-only
	STATUS  mandatory
	DESCRIPTION "Is connection to the MAREN catalogue active/inactive?"
	::= {sniStorMgmtMarenInfo 4}

storMgmtMarenLocTabNum             OBJECT-TYPE
	SYNTAX  INTEGER
	ACCESS  read-only
	STATUS  mandatory
	DESCRIPTION "The number of entries in the table storMgmtMarenLocTable"
	::= {sniStorMgmtMarenInfo 5}

storMgmtMarenLocTable           OBJECT-TYPE
	SYNTAX  SEQUENCE OF StorMgmtMarenLocEntry
	ACCESS  not-accessible
	STATUS  mandatory
	DESCRIPTION "List of available MAREN locations"
	::= {sniStorMgmtMarenInfo 6}

storMgmtMarenLocEntry        OBJECT-TYPE
	SYNTAX  StorMgmtMarenLocEntry
	ACCESS  not-accessible
	STATUS  mandatory
	DESCRIPTION "An entry in the table"
	INDEX {storMgmtMarenLocIndex}
	::= {storMgmtMarenLocTable 1}


StorMgmtMarenLocEntry ::=
	SEQUENCE 
	{
	    storMgmtMarenLocIndex                INTEGER,
	    storMgmtMarenLocName                 DisplayString,
	    storMgmtMarenLocOpmode               DisplayString,
	    storMgmtMarenLocFreevol              DisplayString
	}

storMgmtMarenLocIndex   OBJECT-TYPE
	SYNTAX  INTEGER
	ACCESS  read-only
	STATUS  mandatory
	DESCRIPTION "A unique value for each entry, its value
	    	     ranges between 1 and the value of storMgmtMarenLocTabNum"
	::= {storMgmtMarenLocEntry 1}

storMgmtMarenLocName                  OBJECT-TYPE
	SYNTAX  DisplayString (SIZE (1..8))
	ACCESS  read-only
	STATUS  mandatory
	DESCRIPTION "Name of the location, e.g. ROBOTER1 or FIREARCH"
	::= {storMgmtMarenLocEntry 2}

storMgmtMarenLocOpmode                  OBJECT-TYPE
	SYNTAX  DisplayString (SIZE (1..8))
	ACCESS  read-only
	STATUS  mandatory
	DESCRIPTION "Operating mode e.g. TLS-1 or ROBAR-1"
	::= {storMgmtMarenLocEntry 3}

storMgmtMarenLocFreevol               OBJECT-TYPE
	SYNTAX  DisplayString (SIZE (1..64))
	ACCESS  read-only
	STATUS  mandatory
	DESCRIPTION "Number of free volumes in the specified location;
		     varied according to volumetypes TAPE-Cx"
	::= {storMgmtMarenLocEntry 4}

storMgmtMarenNetworkTabNum             OBJECT-TYPE
	SYNTAX  INTEGER
	ACCESS  read-only
	STATUS  mandatory
	DESCRIPTION "The number of entries in the table storMgmtMarenNetworkTable"
	::= {sniStorMgmtMarenInfo 7}

storMgmtMarenNetworkTable           OBJECT-TYPE
	SYNTAX  SEQUENCE OF StorMgmtMarenNetworkEntry
	ACCESS  not-accessible
	STATUS  mandatory
	DESCRIPTION "List of hosts belonging to the same MAREN network
		     as the current host"
	::= {sniStorMgmtMarenInfo 8}

storMgmtMarenNetworkEntry        OBJECT-TYPE
	SYNTAX  StorMgmtMarenNetworkEntry
	ACCESS  not-accessible
	STATUS  mandatory
	DESCRIPTION "An entry in the table"
	INDEX {storMgmtMarenNetworkIndex}
	::= {storMgmtMarenNetworkTable 1}


StorMgmtMarenNetworkEntry ::=
	SEQUENCE 
	{
	    storMgmtMarenNetworkIndex                INTEGER,
	    storMgmtMarenNetworkHost                 DisplayString
	}

storMgmtMarenNetworkIndex   OBJECT-TYPE
	SYNTAX  INTEGER
	ACCESS  read-only
	STATUS  mandatory
	DESCRIPTION "A unique value for each entry, its value
		     ranges between 1 and the value of storMgmtMarenNetworkTabNum"
	::= {storMgmtMarenNetworkEntry 1}

storMgmtMarenNetworkHost                  OBJECT-TYPE
	SYNTAX  DisplayString (SIZE (1..8))
	ACCESS  read-only
	STATUS  mandatory
	DESCRIPTION "Hostnames belonging to the same MAREN network"
	::= {storMgmtMarenNetworkEntry 2}

storMgmtMarenNoVolume     TRAP-TYPE
	      ENTERPRISE sniStorMgmtMarenInfo
	      DESCRIPTION "Sending a TRAP, if the agent sees the message
			   MARUP97 or MARUP98 (no more free volumes available)"
      ::= 1


-- Storage Management TLS Table Infos

storMgmtTlsTabNum             OBJECT-TYPE
	SYNTAX  INTEGER
	ACCESS  read-only
	STATUS  mandatory
	DESCRIPTION "The number of entries in the table storMgmtTlsTable"
	::= {sniStorMgmtTlsInfo 1}

storMgmtTlsTable           OBJECT-TYPE
	SYNTAX  SEQUENCE OF StorMgmtTlsEntry
	ACCESS  not-accessible
	STATUS  mandatory
	DESCRIPTION "The Storage management information table"
	::= {sniStorMgmtTlsInfo 2}

storMgmtTlsEntry        OBJECT-TYPE
	SYNTAX  StorMgmtTlsEntry
	ACCESS  not-accessible
	STATUS  mandatory
	DESCRIPTION "An entry in the table"
	INDEX {storMgmtTlsIndex}
	::= {storMgmtTlsTable 1}


StorMgmtTlsEntry ::=
	SEQUENCE 
	{
	    storMgmtTlsIndex                INTEGER,
	    storMgmtTlsRobState             INTEGER,
	    storMgmtTlsFreeboxno            INTEGER,
	    storMgmtTlsCleanno              INTEGER,
	    storMgmtTlsLocation             DisplayString
	}

storMgmtTlsIndex   OBJECT-TYPE
	SYNTAX  INTEGER
	ACCESS  read-only
	STATUS  mandatory
	DESCRIPTION "A unique value for each entry, its value
	    	     ranges between 1 and the value of storMgmtTlsTabNum"
	::= {storMgmtTlsEntry 1}

storMgmtTlsRobState                 OBJECT-TYPE
	SYNTAX  INTEGER 
	{
	   automatic (1),
	   pause     (2),
	   manual    (3),
	   off       (4)
	}
	ACCESS  read-only
	STATUS  mandatory
	DESCRIPTION "Roboter state can be: automatic mode, pause mode,
		     manual mode or off"
	::= {storMgmtTlsEntry 2}

storMgmtTlsFreeboxno             OBJECT-TYPE
	SYNTAX  INTEGER 
	ACCESS  read-only
	STATUS  mandatory
	DESCRIPTION "Number of free storage boxes in the archive"
	::= {storMgmtTlsEntry 3}

storMgmtTlsCleanno                  OBJECT-TYPE
	SYNTAX  INTEGER 
	ACCESS  read-only
	STATUS  mandatory
	DESCRIPTION "Number of available cleaning cartridges"
	::= {storMgmtTlsEntry 4}


storMgmtTlsLocation              OBJECT-TYPE
	SYNTAX  DisplayString (SIZE (0..63))
	ACCESS  read-only
	STATUS  mandatory
	DESCRIPTION "Location(s) for devices supported by the robot system"
	::= {storMgmtTlsEntry 5}


storMgmtTlsOffline     TRAP-TYPE
	      ENTERPRISE sniStorMgmtTlsInfo
	      DESCRIPTION "Sending a TRAP, if the agent sees the message
			   EXC0858 (no connection to robot)"
      ::= 1


-- Storage Management ROBAR Table Infos

storMgmtRobarTabNum             OBJECT-TYPE
	SYNTAX  INTEGER
	ACCESS  read-only
	STATUS  mandatory
	DESCRIPTION "The number of entries in the table storMgmtRobarTab"
	::= {sniStorMgmtRobarInfo 1}

storMgmtRobarTable           OBJECT-TYPE
	SYNTAX  SEQUENCE OF StorMgmtRobarEntry
	ACCESS  not-accessible
	STATUS  mandatory
	DESCRIPTION "The Storage management information table"
	::= {sniStorMgmtRobarInfo 2}

storMgmtRobarEntry        OBJECT-TYPE
	SYNTAX  StorMgmtRobarEntry
	ACCESS  not-accessible
	STATUS  mandatory
	DESCRIPTION "An entry in the table"
	INDEX {storMgmtRobarIndex}
	::= {storMgmtRobarTable 1}


StorMgmtRobarEntry ::=
	SEQUENCE 
	{
	    storMgmtRobarIndex                INTEGER,
	    storMgmtRobarLocation             DisplayString,
	    storMgmtRobarState                INTEGER,
	    storMgmtRobarVersion              DisplayString,
	    storMgmtRobarConnState            INTEGER,
	    storMgmtRobarRobState             INTEGER,
	    storMgmtRobarRouting              DisplayString
	}

storMgmtRobarIndex   OBJECT-TYPE
	SYNTAX  INTEGER
	ACCESS  read-only
	STATUS  mandatory
	DESCRIPTION "A unique value for each entry, its value
	    	     ranges between 1 and the value of storMgmtRobarTabNum"
	::= {storMgmtRobarEntry 1}

storMgmtRobarLocation              OBJECT-TYPE
	SYNTAX  DisplayString (SIZE (1..8))
	ACCESS  read-only
	STATUS  mandatory
	DESCRIPTION "Current ROBAR location"
	::= {storMgmtRobarEntry 2}

storMgmtRobarState                 OBJECT-TYPE
	SYNTAX  INTEGER 
	{
	    running       (1),
	    terminated    (2),
	    aborted       (3),
	    loaded        (4),
	    in-hold       (5),
	    not-installed (255)
	}
	ACCESS  read-only
	STATUS  mandatory
	DESCRIPTION "Is ROBAR-DCAM running, stopped or even not installed?"
	::= {storMgmtRobarEntry 3}

storMgmtRobarVersion                OBJECT-TYPE
	SYNTAX  DisplayString (SIZE (1..8))
	ACCESS  read-only
	STATUS  mandatory
	DESCRIPTION "Current ROBAR version"
	::= {storMgmtRobarEntry 4}

storMgmtRobarConnState                OBJECT-TYPE
	SYNTAX  INTEGER 
	{
	   active        (1),
	   inactive      (2),
	   not-available (255)
	}
	ACCESS  read-only
	STATUS  mandatory
	DESCRIPTION "Check connection between ROBAR-BS2000 and ROBAR-SINIX"
	::= {storMgmtRobarEntry 5}

storMgmtRobarRobState                 OBJECT-TYPE
	SYNTAX  INTEGER 
	{
	   on  (1),
	   off (2)
	}
	ACCESS  read-only
	STATUS  mandatory
	DESCRIPTION "Roboter state is ON or OFF"
	::= {storMgmtRobarEntry 6}

storMgmtRobarRouting                  OBJECT-TYPE
	SYNTAX  DisplayString (SIZE (0..63))
	ACCESS  read-write
	STATUS  mandatory
	DESCRIPTION "Current routing codes for ROBAR-DCAM"
	::= {storMgmtRobarEntry 7}

storMgmtRobarBs2Messages     TRAP-TYPE
	      ENTERPRISE sniStorMgmtRobarInfo
	      DESCRIPTION "Sending a TRAP, if the agent sees predefined BS2000
			   messages like ROB0042 (ROB ON), ROB0043 (ROB OFF),
			   ROB2000 (Connect ok), ROB2001 (Connect not ok), ..."
      ::= 1


-- Storage Management Resource Infos

storMgmtResourcePubset               OBJECT-TYPE
	SYNTAX  DisplayString (SIZE (1..4))
	ACCESS  read-write
	STATUS  mandatory
	DESCRIPTION "Catalogue ID of the specified pubset"
	::= {sniStorMgmtResourceInfo 1}

storMgmtResourceSaturation           OBJECT-TYPE
	SYNTAX  INTEGER
	{
	   level-0        (1),
	   level-1        (2),
	   level-2        (3),
	   level-3        (4),
	   level-4        (5),
	   level-5        (6),
	   unknown-level  (7)
	}
	ACCESS  read-only
	STATUS  mandatory
	DESCRIPTION "Saturation level for the specified pubset"
	::= {sniStorMgmtResourceInfo 2}

storMgmtResourceCapacity             OBJECT-TYPE
	SYNTAX  INTEGER
	ACCESS  read-only
	STATUS  mandatory
	DESCRIPTION "Capacity of the specified pubset in half pages"
	::= {sniStorMgmtResourceInfo 3}

storMgmtResourceSpaceAllocated       OBJECT-TYPE
	SYNTAX  INTEGER
	ACCESS  read-only
	STATUS  mandatory
	DESCRIPTION "Allocated space of the specified pubset in half pages"
	::= {sniStorMgmtResourceInfo 4}

storMgmtResourceFragment             OBJECT-TYPE
	SYNTAX  DisplayString (SIZE (0..31))
	ACCESS  read-only
	STATUS  mandatory
	DESCRIPTION "Degree of fragmentation"
	::= {sniStorMgmtResourceInfo 5}

storMgmtResourceReusableS1           OBJECT-TYPE
	SYNTAX  DisplayString
	ACCESS  read-only
	STATUS  mandatory
	DESCRIPTION "Information is: number of save files, number of
		     occupied PAM pages according to save files, number
		     of unused PAM pages"
	::= {sniStorMgmtResourceInfo 6}

storMgmtResourceSecureQueue        OBJECT-TYPE
	SYNTAX  INTEGER
	ACCESS  read-only
	STATUS  mandatory
	DESCRIPTION "The number of tasks waiting in the SECURE queue"
	::= {sniStorMgmtResourceInfo 7}


---
---
---      V4 - Erweiterungen
---
---


storMgmtPubsetTabNum        OBJECT-TYPE
	SYNTAX  INTEGER
	ACCESS  read-only
	STATUS  mandatory
	DESCRIPTION "The number of entries in the table storMgmtPubsetTable"
	::= {sniStorMgmtPubsetInfo 1}

storMgmtPubsetTabState            OBJECT-TYPE
	SYNTAX  INTEGER
		{
		 all                        (1),
		 paging                     (2),
		 local                      (3),
		 remote                     (4),
		 accessible                 (5),
		 local-accessible           (6),
		 shared                     (7),
		 exclusive                  (8),
		 remote-accessible          (9),
		 local-accessible-speedcat  (10),
		 xcs-pubset                 (11),
		 hsms-supported             (12),
		 single-feature             (13),
		 system-managed             (14),
		 volume-sets                (15),
		 unused-volsets             (16),
		 master-change-error        (17)
		}
	ACCESS  read-write
	STATUS  mandatory
	DESCRIPTION "State of Pubsets to be shown in the storMgmtPubsetTable "
	::= {sniStorMgmtPubsetInfo 2 }

storMgmtPubsetTable           OBJECT-TYPE
	SYNTAX  SEQUENCE OF StorMgmtPubsetEntry
	ACCESS  not-accessible
	STATUS  mandatory
	DESCRIPTION "The Pubset information table"
	::= {sniStorMgmtPubsetInfo 10}

storMgmtPubsetEntry        OBJECT-TYPE
	SYNTAX  StorMgmtPubsetEntry
	ACCESS  not-accessible
	STATUS  mandatory
	DESCRIPTION "An entry in the table"
	INDEX {storMgmtPubsetIndex}
	::= {storMgmtPubsetTable 1}


StorMgmtPubsetEntry ::=
	SEQUENCE 
	{
	    storMgmtPubsetIndex                DisplayString,
	    storMgmtPubsetTyp                  INTEGER,
	    storMgmtPubsetLocal                INTEGER,
	    storMgmtPubsetHome                 INTEGER,
	    storMgmtPubsetShared               INTEGER,
	    storMgmtPubsetMaster               INTEGER,
	    storMgmtPubsetAccessible           INTEGER,
	    storMgmtPubsetQuiet                INTEGER,
	    storMgmtPubsetPaging               INTEGER,
	    storMgmtPubsetSize                 INTEGER,
	    storMgmtPubsetUsedSize             INTEGER,
	    storMgmtPubsetSaturationLevel      INTEGER
	}

storMgmtPubsetIndex   OBJECT-TYPE
	SYNTAX  DisplayString
	ACCESS  read-only
	STATUS  mandatory
	DESCRIPTION "A unique value for each entry, its value
		     is the CATID of the Pubset storMgmtPubsetIndex "
	::= {storMgmtPubsetEntry 1}


storMgmtPubsetTyp                OBJECT-TYPE
	SYNTAX  INTEGER 
	{
		 single-feature (1),
		 system-managed (2),
		 volumeset (3),
		 unknown      (255)
	}
	ACCESS  read-only
	STATUS  mandatory
	DESCRIPTION "Type of the Pubset"
	::= {storMgmtPubsetEntry 4}

storMgmtPubsetLocal                 OBJECT-TYPE
	SYNTAX  INTEGER 
	{
		 local        (1),
		 remote       (2),
		 unknown      (255)
	}
	ACCESS  read-only
	STATUS  mandatory
	DESCRIPTION "Local / remote Pubset"
	::= {storMgmtPubsetEntry 5}

storMgmtPubsetHome                OBJECT-TYPE
	SYNTAX  INTEGER 
	{
		 home         (1),
		 imported     (2),
		 unknown      (255)
	}
	ACCESS  read-only
	STATUS  mandatory
	DESCRIPTION "Home / imported  Pubset"
	::= {storMgmtPubsetEntry 6}

storMgmtPubsetShared     OBJECT-TYPE
	SYNTAX  INTEGER 
	{
		 shared       (1),
		 exclusive    (2),
		 unknown      (255)
	}
	ACCESS  read-only
	STATUS  mandatory
	DESCRIPTION "shared / exclusive Pubset"
	::= {storMgmtPubsetEntry 7}

storMgmtPubsetMaster    OBJECT-TYPE
	SYNTAX  INTEGER 
	{
		 yes          (1),
		 no           (2),
		 unknown      (255)
	}
	ACCESS  read-only
	STATUS  mandatory
	DESCRIPTION "Master / slave Pubset"
	::= {storMgmtPubsetEntry 8}

storMgmtPubsetAccessible                OBJECT-TYPE
	SYNTAX  INTEGER 
	{
		 accessible   (1),
		 inaccessible (2),
		 unknown      (255)
	}
	ACCESS  read-only
	STATUS  mandatory
	DESCRIPTION "accessible / inaccessible Pubset"
	::= {storMgmtPubsetEntry 9}

storMgmtPubsetQuiet                OBJECT-TYPE
	SYNTAX  INTEGER 
	{
		 yes          (1),
		 no           (2),
		 unknown      (255)
	}
	ACCESS  read-only
	STATUS  mandatory
	DESCRIPTION "quiet Pubset"
	::= {storMgmtPubsetEntry 10}


storMgmtPubsetPaging          OBJECT-TYPE
	SYNTAX  INTEGER 
	{
		 yes          (1),
		 no           (2),
		 unknown      (255)
	}
	ACCESS  read-only
	STATUS  mandatory
	DESCRIPTION "paging Pubset"
	::= {storMgmtPubsetEntry 11}


storMgmtPubsetSize        OBJECT-TYPE
	SYNTAX  INTEGER 
	ACCESS  read-only
	STATUS  mandatory
	DESCRIPTION "Size of Pubset"
	::= {storMgmtPubsetEntry 12}


storMgmtPubsetUsedSize        OBJECT-TYPE
	SYNTAX  INTEGER 
	ACCESS  read-only
	STATUS  mandatory
	DESCRIPTION "used space of Pubset"
	::= {storMgmtPubsetEntry 13}


storMgmtPubsetSaturationLevel         OBJECT-TYPE
	SYNTAX  INTEGER 
	{
	   level-0        (1),
	   level-1        (2),
	   level-2        (3),
	   level-3        (4),
	   level-4        (5),
	   level-5        (6),
	   unknown-level  (7)
	}
	ACCESS  read-only
	STATUS  mandatory
	DESCRIPTION "Saturation level for the specified pubset"
	::= {storMgmtPubsetEntry 14}

--------
--------
--     Disk Table
--------
--------


storMgmtDiskTabNum             OBJECT-TYPE
	SYNTAX  INTEGER
	ACCESS  read-only
	STATUS  mandatory
	DESCRIPTION "The number of entries in the table storMgmtDiskTable"
	::= {sniStorMgmtDiskInfo 1}

storMgmtDiskTabReconfState             OBJECT-TYPE
	SYNTAX  INTEGER
		{
		 all          (1),
		 attached     (2),
		 detached     (3),
		 other        (255)
		}
	ACCESS  read-write
	STATUS  mandatory
	DESCRIPTION "The reconfiguration state of disks to be shown "
	::= {sniStorMgmtDiskInfo 2}

storMgmtDiskTable           OBJECT-TYPE
	SYNTAX  SEQUENCE OF StorMgmtDiskEntry
	ACCESS  not-accessible
	STATUS  mandatory
	DESCRIPTION "The Disk information table"
	::= {sniStorMgmtDiskInfo 10}

storMgmtDiskEntry        OBJECT-TYPE
	SYNTAX  StorMgmtDiskEntry
	ACCESS  not-accessible
	STATUS  mandatory
	DESCRIPTION "An entry in the table"
	INDEX {storMgmtDiskIndex}
	::= {storMgmtDiskTable 1}


StorMgmtDiskEntry ::=
	SEQUENCE 
	{
	    storMgmtDiskIndex                DisplayString,
	    storMgmtDiskVSN                  DisplayString,
	    storMgmtDiskDeviceAllocState     INTEGER,
	    storMgmtDiskSystemUse            INTEGER,
	    storMgmtDiskPoolAttribut         INTEGER,
	    storMgmtDiskReconfState          INTEGER,
	    storMgmtDiskVolAllocState        INTEGER,
	    storMgmtDiskPrivDiskRunState     INTEGER,
	    storMgmtDiskPhaseSet             INTEGER,
	    storMgmtDiskActionState          INTEGER,
	    storMgmtDiskUse                  INTEGER,
	    storMgmtDiskAssignTime           INTEGER,
	    storMgmtDiskUserAllocation       INTEGER,
	    storMgmtDiskOperatorControl      INTEGER,
	    storMgmtDiskSystemAllocation     INTEGER,
	    storMgmtDiskAccess               INTEGER,
	    storMgmtDiskRecordingMode        INTEGER
	}

storMgmtDiskIndex   OBJECT-TYPE
	SYNTAX  DisplayString (SIZE (1..4))
	ACCESS  read-only
	STATUS  mandatory
	DESCRIPTION "A unique value for each entry, its value
		     is the Mnemonic of the Disk "
	::= {storMgmtDiskEntry 1}

storMgmtDiskVSN    OBJECT-TYPE
	SYNTAX  DisplayString (SIZE (1..6))
	ACCESS  read-only
	STATUS  mandatory
	DESCRIPTION "VSN of Disk "
	::= {storMgmtDiskEntry 2}

storMgmtDiskDeviceAllocState   OBJECT-TYPE
	SYNTAX  INTEGER 
	{
		 free                              (1),
		 allocated                         (2),
		 exclusive-allocated               (3),
		 current-public-assigned           (4),
		 dms-used-volume-assigned          (5),
		 drv-assigned                      (6),
		 drv-public-assigned               (7),
		 drv-dms-used-volume-assigned      (8),
		 invalid      (255)
	}
	ACCESS  read-only
	STATUS  mandatory
	DESCRIPTION "Device  Allocation State "
	::= {storMgmtDiskEntry 3}

storMgmtDiskSystemUse   OBJECT-TYPE
	SYNTAX  INTEGER 
	{
		 paging-device  (1),
		 public-device  (2),
		 unknown        (255)
	}
	ACCESS  read-only
	STATUS  mandatory
	DESCRIPTION "Type of the Disk"
	::= {storMgmtDiskEntry 4}

storMgmtDiskPoolAttribut     OBJECT-TYPE
	SYNTAX  INTEGER 
	{
		 shared-privat-disk        (1),
		 device-switchable         (2),
		 unknown      (255)
	}
	ACCESS  read-only
	STATUS  mandatory
	DESCRIPTION "Local / remote Disk"
	::= {storMgmtDiskEntry 5}

storMgmtDiskReconfState     OBJECT-TYPE
	SYNTAX  INTEGER 
	{
		 attached               (1),
		 detach-pending         (2),
		 detached               (3),
		 assignment-in-progress (4),
		 invalid      (255)
	}
	ACCESS  read-only
	STATUS  mandatory
	DESCRIPTION "Reconfiguration State "
	::= {storMgmtDiskEntry 6}

storMgmtDiskVolAllocState   OBJECT-TYPE
	SYNTAX  INTEGER 
	{
		 free               (1),
		 task-exclusive     (2),
		 task-sharable      (3),
		 current-public     (4),
		 current-paging     (5),
		 volume-cancelled    (6),
		 volume-allocated   (7),
		 invalid      (255)
	}
	ACCESS  read-only
	STATUS  mandatory
	DESCRIPTION "Volume Allocation State "
	::= {storMgmtDiskEntry 7}

storMgmtDiskPrivDiskRunState  OBJECT-TYPE
	SYNTAX  INTEGER 
	{
		 offline            (1),
		 active             (2),
		 inactive           (3),
		 end-in-process     (4),
		 unknown            (255)
	}
	ACCESS  read-only
	STATUS  mandatory
	DESCRIPTION "Private Disk Run State "
	::= {storMgmtDiskEntry 8}

storMgmtDiskPhaseSet OBJECT-TYPE
	SYNTAX  INTEGER 
	{
		 online-only        (1),
		 premounting        (2),
		 mounting           (3),
		 in-use             (4),
		 not-specified      (5),
		 unknown            (255)
	}
	ACCESS  read-only
	STATUS  mandatory
	DESCRIPTION "Phase Set"
	::= {storMgmtDiskEntry 9}


storMgmtDiskActionState  OBJECT-TYPE
	SYNTAX  INTEGER 
	{
		 no-action    (1),
		 inoperable   (2),
		 remount      (3),
		 cancelled    (4),
		 no-device-available (5),
		 recover      (6),
		 positioning  (7),
		 writepermission-missing (8),
		 unlock       (9),
		 svl-update   (10),
		 dismount     (11),
		 unknown            (255)
	}
	ACCESS  read-only
	STATUS  mandatory
	DESCRIPTION "Action State"
	::= {storMgmtDiskEntry 10}

storMgmtDiskUse  OBJECT-TYPE
	SYNTAX  INTEGER 
	{
		 dms                (1),
		 special            (2),
		 work               (3),
		 unknown            (255)
	}
	ACCESS  read-only
	STATUS  mandatory
	DESCRIPTION " Disk Use "
	::= {storMgmtDiskEntry 11}

storMgmtDiskAssignTime OBJECT-TYPE
	SYNTAX  INTEGER 
	{
		 standard             (1),
		 user                 (2),
		 user-by-default      (3),
		 operator             (4),
		 operator-by-default  (5),
		 unknown            (255)
	}
	ACCESS  read-only
	STATUS  mandatory
	DESCRIPTION "Assign Time "
	::= {storMgmtDiskEntry 12}

storMgmtDiskUserAllocation OBJECT-TYPE
	SYNTAX  INTEGER 
	{
		 standard             (1),
		 shared               (2),
		 shared-by-default    (3),
		 exclusive            (4),
		 exclusive-by-default (5),
		 no                   (6),
		 no-by-default        (7),
		 all                  (8),
		 all-by-default       (9),
		 unknown            (255)
	}
	ACCESS  read-only
	STATUS  mandatory
	DESCRIPTION "User Allocation "
	::= {storMgmtDiskEntry 13}

storMgmtDiskOperatorControl OBJECT-TYPE
	SYNTAX  INTEGER 
	{
		 standard             (1),
		 shared               (2),
		 shared-by-default    (3),
		 exclusive            (4),
		 exclusive-by-default (5),
		 no                   (6),
		 no-by-default        (7),
		 all                  (8),
		 all-by-default       (9),
		 unknown            (255)
	}
	ACCESS  read-only
	STATUS  mandatory
	DESCRIPTION "Operator Control "
	::= {storMgmtDiskEntry 14}

storMgmtDiskSystemAllocation  OBJECT-TYPE
	SYNTAX  INTEGER 
	{
		 shared             (1),
		 exclusive          (2),
		 all                (3),
		 current-shared     (4),
		 current-exclusive  (5),
		 unknown            (255)
	}
	ACCESS  read-only
	STATUS  mandatory
	DESCRIPTION "Sytem Allocation "
	::= {storMgmtDiskEntry 15}


storMgmtDiskAccess   OBJECT-TYPE
	SYNTAX  INTEGER 
	{
		 write              (1),
		 ppd                (2),
		 from-device        (3),
		 write-from-device  (4),
		 ppd-from-device    (5),
		 unknown            (255)
	}
	ACCESS  read-only
	STATUS  mandatory
	DESCRIPTION "Disk Access "
	::= {storMgmtDiskEntry 16}

storMgmtDiskRecordingMode OBJECT-TYPE
	SYNTAX  INTEGER 
	{
		 single-recording           (1),
		 dual-recording-by-volume   (2),
		 unknown                    (255)
	}
	ACCESS  read-only
	STATUS  mandatory
	DESCRIPTION "Disk Recording Mode"
	::= {storMgmtDiskEntry 17}


storMgmtGlobalDataVersion      OBJECT-TYPE
	SYNTAX  DisplayString (SIZE (1..8))
	ACCESS  read-only
	STATUS  mandatory
	DESCRIPTION "Version of subagent "
	::= {sniStorMgmtGlobalData  1}

storMgmtGlobalDataInputFile OBJECT-TYPE
	SYNTAX  DisplayString
	ACCESS  read-write
	STATUS  mandatory
	DESCRIPTION "Filename of input file "
	::= {sniStorMgmtGlobalData  2 }



storMgmtPubsetSatLevTrap       TRAP-TYPE
	      ENTERPRISE  sniStorMgmtPubsetTraps
	      VARIABLES  { storMgmtPubsetIndex, storMgmtPubsetSaturationLevel }
	      DESCRIPTION "Saturation level x reached"
      ::= 301


storMgmtDiskReconfStateTrap     TRAP-TYPE
	      ENTERPRISE sniStorMgmtDiskTraps
	      VARIABLES  { storMgmtDiskIndex, storMgmtDiskReconfState}
	      DESCRIPTION "DiskReconfstate x reached"
      ::= 301

END
