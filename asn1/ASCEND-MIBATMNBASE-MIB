--			Ascend mibatmnbase MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBATMNBASE-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibatmNbaseProfile  OBJECT IDENTIFIER ::= { configuration 41}

	-- The mibatmNbaseProfile table
	--
	-- This table contains parameters for the mibatmNbaseProfile profile
	--

    mibatmNbaseProfileTable	OBJECT-TYPE
	SYNTAX		SEQUENCE OF MibatmNbaseProfileEntry
	ACCESS		not-accessible
	STATUS		mandatory
	DESCRIPTION	"A list of mibatmNbaseProfile profile entries."
	::= { mibatmNbaseProfile 1 }

    mibatmNbaseProfileEntry	OBJECT-TYPE
	SYNTAX		MibatmNbaseProfileEntry
	ACCESS		not-accessible
	STATUS		mandatory
	DESCRIPTION	"A mibatmNbaseProfile entry containing objects that
			 maps to the parameters of mibatmNbaseProfile profile."
	INDEX		{ atmNbaseProfile-Index-o }
	::= { mibatmNbaseProfileTable 1 }

    MibatmNbaseProfileEntry ::=
	SEQUENCE {
	    atmNbaseProfile-Index-o
		INTEGER,
	    atmNbaseProfile-RandSeed
		INTEGER,
	    atmNbaseProfile-Action-o
		INTEGER
	}

    atmNbaseProfile-Index-o	OBJECT-TYPE
	SYNTAX	INTEGER
	ACCESS	read-only
	STATUS	mandatory
	DESCRIPTION	""
	::= { mibatmNbaseProfileEntry 1 }

    atmNbaseProfile-RandSeed	OBJECT-TYPE
	SYNTAX	INTEGER
	ACCESS	read-write
	STATUS	mandatory
	DESCRIPTION	"Seed for random number generator"
	::= { mibatmNbaseProfileEntry 6 }

    atmNbaseProfile-Action-o	OBJECT-TYPE
	SYNTAX	INTEGER {
		    noAction (1),
		    createProfile (2),
		    deleteProfile (3)
		}
	ACCESS	read-write
	STATUS	mandatory
	DESCRIPTION	""
	::= { mibatmNbaseProfileEntry 16 }

END
