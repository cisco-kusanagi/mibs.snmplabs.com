--
--              Lucent GRF ATMP MIB
--
--              Lucent Technologies, Inc.
--              10250 Valley View Road
--              Minneapolis, MN 55344
--              +1 612 943 8990
--
--              Copyright (c) 1999, Lucent Technologies, Inc.
--              All rights reserved
--
--
--              This defines the Ascend Tunnel Management Protocol (ATMP)
--              as implemented on the GRF network device.  See RFC 2107
--              for protocol details.
--
-- $Id: grf-atmp.smi,v 1.1.2.3 1999/10/18 16:25:57 pkopecky Exp $
--

GRF-ATMP-MIB DEFINITIONS ::= BEGIN

    IMPORTS
      IpAddress, Counter
          FROM RFC1155-SMI
      OBJECT-TYPE
          FROM RFC-1212
			 DisplayString FROM RFC1213-MIB
      grAtmp
          FROM NETSTAR-MIB;

    --
    -- The GRF ATMP MIB contains information pertaining to ATMP tunnels
    -- on the GRF.  The following abbreviations are used: 
    --
    --     FA   : Foreign Agent
    --     DFA  : Default Foreign Agent
    --     HN   : Home Network
    --     HA   : Home Agent
    --     MN   : Mobile Node
    --

    atmpMIBVersion      OBJECT IDENTIFIER ::= { grAtmp 1 }

    atmpGeneralConfig   OBJECT IDENTIFIER ::= { grAtmp 2 }

    atmpDFAConfig       OBJECT IDENTIFIER ::= { grAtmp 3 }

    atmpGeneralStats    OBJECT IDENTIFIER ::= { grAtmp 4 }

    atmpProtocolStats   OBJECT IDENTIFIER ::= { grAtmp 5 }

    atmpTables          OBJECT IDENTIFIER ::= { grAtmp 6 }

    --
    -- ATMP MIB Version Variables
    --
    atmpMIBVersionMajor OBJECT-TYPE
      SYNTAX INTEGER
      ACCESS read-only
      STATUS mandatory
      DESCRIPTION
          "Major version number for the GRF ATMP MIB.  This number is
           incremented when structural changes occur to the GRF ATMP MIB."
      DEFVAL { 1 }
      ::= { atmpMIBVersion 1 }

    atmpMIBVersionMinor OBJECT-TYPE
      SYNTAX INTEGER
      ACCESS read-only
      STATUS mandatory
      DESCRIPTION
          "Minor version number for the GRF ATMP MIB.  This number is
           incremented when non-structural changes occur to the GRF ATMP MIB"
      DEFVAL { 0 }
      ::= { atmpMIBVersion 2 }

    --
    -- ATMP General Configuration
    --
    atmpUDPPort OBJECT-TYPE
      SYNTAX INTEGER
      ACCESS read-only
      STATUS mandatory
      DESCRIPTION
          "UDP port number to be used for ATMP."
      ::= { atmpGeneralConfig 1 }

    atmpEnableAtmpTraps OBJECT-TYPE
      SYNTAX INTEGER {
          enabled( 1 ),         -- turn on atmp traps
          disabled( 2 )         -- turn off atmp traps
      }
      ACCESS read-only
      STATUS mandatory
      DESCRIPTION
          "Enable the atmp traps.  There are no traps in the GRF ATMP
           implementation, so this is always disabled but left as a
           placeholder for future feature enhancement."
      DEFVAL { disabled }
      ::= { atmpGeneralConfig 2 }

    atmpNumberFAs OBJECT-TYPE
      SYNTAX Counter
      ACCESS read-only
      STATUS mandatory
      DESCRIPTION
          "The number of foreign agents in the GRF ATMP configuration."
      ::= { atmpGeneralConfig 3 }

    atmpNumberHNs OBJECT-TYPE
      SYNTAX Counter
      ACCESS read-only
      STATUS mandatory
      DESCRIPTION
          "The number of home networks in the GRF ATMP configuration."
      ::= { atmpGeneralConfig 4 }

    atmpMaxNumberHNs OBJECT-TYPE
      SYNTAX INTEGER
      ACCESS read-only
      STATUS mandatory
      DESCRIPTION
          "The maximum number of home networks allowed in the GRF ATMP
           configuration."
      ::= { atmpGeneralConfig 5 }

    --
    -- ATMP Default Foreign Agent Configuration
    --
    atmpDFAConfigured OBJECT-TYPE
      SYNTAX INTEGER {
          no( 1 ),    -- a default foreign agent is NOT present
          yes( 2 )    -- a default foreign agent is present
      }
      ACCESS read-only
      STATUS mandatory
      DESCRIPTION
          "Specifies whether a default foreign agent is configured in the
           GRF ATMP configuration.  The default foreign agent record
           specifies multiple foreign agents with a single IP wildcard
           address. This is an optional record. A default foreign agent
           type of record can be used in addition to a regular foreign
           agent record to establish tunnels to the same home network."
      ::= { atmpDFAConfig 1 }
      
    atmpDFAWildcardIpAddress OBJECT-TYPE
      SYNTAX DisplayString
      ACCESS read-only
      STATUS mandatory
      DESCRIPTION
          "The default foreign agent requires an IP wildcard address,
           192.15.*.*, for example.  If a wildcard IP address is not
           specified, the default value of *.*.*.* is used.  The address
           need not be wildcarded and can be filled out completely."
      ::= { atmpDFAConfig 2 }

    atmpDFAPassword OBJECT-TYPE
      SYNTAX DisplayString
      ACCESS read-only
      STATUS mandatory
      DESCRIPTION
          "The password that validates the default foreign agent to the
           GRF home agent.  It is also configured in the mobile node's
           RADIUS profile as the Ascend-Home-Agent-Password.  If a
           password is not specified, a tunnel is not negotiated.  Reading
           this object always results in a DisplayString of length zero;
           authentication may not be bypassed by reading the MIB object."
      DEFVAL { ''h }
      ::= { atmpDFAConfig 3 }

    --
    -- ATMP General Statistics
    --
    atmpNumberTunnelsUp OBJECT-TYPE
      SYNTAX INTEGER
      ACCESS read-only
      STATUS mandatory
      DESCRIPTION
          "The number of tunnels currently in the up state."
      ::= { atmpGeneralStats 1 }

    atmpNumberTunnelsRegistering OBJECT-TYPE
      SYNTAX INTEGER
      ACCESS read-only
      STATUS mandatory
      DESCRIPTION
          "The number of tunnels currently in the registering state."
      ::= { atmpGeneralStats 2 }

    atmpNumberFAFailingMatch OBJECT-TYPE
      SYNTAX Counter
      ACCESS read-only
      STATUS mandatory
      DESCRIPTION
          "The number of foreign agents that failed to match any of
           the foreign agent records in the GRF ATMP configuration."
      ::= { atmpGeneralStats 3 }

    atmpNumberFAPasswordRejects OBJECT-TYPE
      SYNTAX Counter
      ACCESS read-only
      STATUS mandatory
      DESCRIPTION
          "The number of foreign agents whose tunnel request failed to
           match the password of the identified foreign agent record in
           the GRF ATMP configuration."
      ::= { atmpGeneralStats 4 }

    atmpNumberDFAMatch OBJECT-TYPE
      SYNTAX Counter
      ACCESS read-only
      STATUS mandatory
      DESCRIPTION
          "The number of foreign agents whose IP address did not match
           that of any specific foreign agent in the GRF ATMP
           configuration, but matched the wildcard address of the default
           foreign agent record."
      ::= { atmpGeneralStats 5 }

    --
    -- ATMP Protocol Statistics
    --
    atmpRxRegistrationRequestPkts OBJECT-TYPE
      SYNTAX Counter
      ACCESS read-only
      STATUS mandatory
      DESCRIPTION
          "The number of ATMP registration request packets received by
           the ATMP daemon process on the GRF."
      ::= { atmpProtocolStats 1 }

    atmpRxChallengeReplyPkts OBJECT-TYPE
      SYNTAX Counter
      ACCESS read-only
      STATUS mandatory
      DESCRIPTION
          "The number of ATMP challenge reply packets received by
           the ATMP daemon process on the GRF."
      ::= { atmpProtocolStats 3 }

    atmpRxDeRegistrationRequestPkts OBJECT-TYPE
      SYNTAX Counter
      ACCESS read-only
      STATUS mandatory
      DESCRIPTION
          "The number of ATMP deregistration request packets received by
           the ATMP daemon process on the GRF."
      ::= { atmpProtocolStats 5 }

    atmpTxChallengeRequestPkts OBJECT-TYPE
      SYNTAX Counter
      ACCESS read-only
      STATUS mandatory
      DESCRIPTION
          "The number of ATMP challenge request packets sent by
           the ATMP daemon process on the GRF."
      ::= { atmpProtocolStats 2 }

    atmpTxRegistrationReplyPkts OBJECT-TYPE
      SYNTAX Counter
      ACCESS read-only
      STATUS mandatory
      DESCRIPTION
          "The number of ATMP registration reply packets sent by
           the ATMP daemon process on the GRF."
      ::= { atmpProtocolStats 4 }

    atmpTxDeRegistrationReplyPkts OBJECT-TYPE
      SYNTAX Counter
      ACCESS read-only
      STATUS mandatory
      DESCRIPTION
          "The number of ATMP deregistration reply packets sent by
           the ATMP daemon process on the GRF."
      ::= { atmpProtocolStats 6 }

    --
    -- ATMP Protocol Error Statistics
    --
    atmpReceiveProtocolErrorStats  OBJECT IDENTIFIER ::= { atmpProtocolStats 7 }

    atmpTransmitProtocolErrorStats OBJECT IDENTIFIER ::= { atmpProtocolStats 8 }

    --
    -- Rx: Receive error statistics
    --
    atmpRxErrorNotificationPkts OBJECT-TYPE
      SYNTAX Counter
      ACCESS read-only
      STATUS mandatory
      DESCRIPTION
          "The number of ATMP error notification packets received by
           the ATMP daemon process on the GRF."
      ::= { atmpReceiveProtocolErrorStats 1 }

    atmpRxNoErrorPkts OBJECT-TYPE
      SYNTAX Counter
      ACCESS read-only
      STATUS mandatory
      DESCRIPTION
          "The number of ATMP error notification packets containing the
           NO_ERROR error code received by the ATMP daemon process on
           the GRF."
      ::= { atmpReceiveProtocolErrorStats 2 }

    atmpRxAuthFailedPkts OBJECT-TYPE
      SYNTAX Counter
      ACCESS read-only
      STATUS mandatory
      DESCRIPTION
          "The number of ATMP error notification packets containing the
           AUTH_FAILED error code received by the ATMP daemon process on
           the GRF."
      ::= { atmpReceiveProtocolErrorStats 3 }

    atmpRxNotEnabledPkts OBJECT-TYPE
      SYNTAX Counter
      ACCESS read-only
      STATUS mandatory
      DESCRIPTION
          "The number of ATMP error notification packets containing the
           NOT_ENABLED error code received by the ATMP daemon process on
           the GRF."
      ::= { atmpReceiveProtocolErrorStats 4 }

    atmpRxTooManyPkts OBJECT-TYPE
      SYNTAX Counter
      ACCESS read-only
      STATUS mandatory
      DESCRIPTION
          "The number of ATMP error notification packets containing the
           TOO_MANY error code received by the ATMP daemon process on
           the GRF."
      ::= { atmpReceiveProtocolErrorStats 5 }

    atmpRxParameterErrorPkts OBJECT-TYPE
      SYNTAX Counter
      ACCESS read-only
      STATUS mandatory
      DESCRIPTION
          "The number of ATMP error notification packets containing the
           PARAMETER_ERROR error code received by the ATMP daemon process on
           the GRF."
      ::= { atmpReceiveProtocolErrorStats 6 }

    atmpRxInvalidTunnelIdPkts OBJECT-TYPE
      SYNTAX Counter
      ACCESS read-only
      STATUS mandatory
      DESCRIPTION
          "The number of ATMP error notification packets containing the
           INVALID_TUNNEL_ID error code received by the ATMP daemon process on
           the GRF."
      ::= { atmpReceiveProtocolErrorStats 7 }

    atmpRxTimeoutPkts OBJECT-TYPE
      SYNTAX Counter
      ACCESS read-only
      STATUS mandatory
      DESCRIPTION
          "The number of ATMP error notification packets containing the
           TIMEOUT error code received by the ATMP daemon process on
           the GRF."
      ::= { atmpReceiveProtocolErrorStats 8 }

    atmpRxNetUnreachablePkts OBJECT-TYPE
      SYNTAX Counter
      ACCESS read-only
      STATUS mandatory
      DESCRIPTION
          "The number of ATMP error notification packets containing the
           NET_UNREACHABLE error code received by the ATMP daemon process on
           the GRF."
      ::= { atmpReceiveProtocolErrorStats 9 }

    atmpRxGeneralErrorPkts OBJECT-TYPE
      SYNTAX Counter
      ACCESS read-only
      STATUS mandatory
      DESCRIPTION
          "The number of ATMP error notification packets containing the
           GENERAL_ERROR error code received by the ATMP daemon process on
           the GRF."
      ::= { atmpReceiveProtocolErrorStats 10 }

    --
    -- The following packet error stats are detected only on the receiving end.
    -- That is, these are errors detected by aitmd, but are not necessarily
    -- known to the sender as an error (e.g. bad ATMP version number)
    --
    atmpRxChallengeRequestPkts OBJECT-TYPE
      SYNTAX Counter
      ACCESS read-only
      STATUS mandatory
      DESCRIPTION
          "The number of ATMP challenge request packets received by
           the ATMP daemon process on the GRF.  These should not be
           received by a home agent, and are dropped."
      ::= { atmpReceiveProtocolErrorStats 11 }

    atmpRxRegistrationReplyPkts OBJECT-TYPE
      SYNTAX Counter
      ACCESS read-only
      STATUS mandatory
      DESCRIPTION
          "The number of ATMP registration reply packets received by
           the ATMP daemon process on the GRF.  These should not be
           received by a home agent, and are dropped."
      ::= { atmpReceiveProtocolErrorStats 12 }

    atmpRxDeRegistrationReplyPkts OBJECT-TYPE
      SYNTAX Counter
      ACCESS read-only
      STATUS mandatory
      DESCRIPTION
          "The number of ATMP deregistration reply packets received by
           the ATMP daemon process on the GRF.  These should not be
           received by a home agent, and are dropped."
      ::= { atmpReceiveProtocolErrorStats 13 }

    atmpRxUndersizeLengthPkts OBJECT-TYPE
      SYNTAX Counter
      ACCESS read-only
      STATUS mandatory
      DESCRIPTION
          "The number of ATMP packets less than the minimum packet length
           received by the ATMP daemon process on the GRF."
      ::= { atmpReceiveProtocolErrorStats 14 }

    atmpRxBadVersionPkts OBJECT-TYPE
      SYNTAX Counter
      ACCESS read-only
      STATUS mandatory
      DESCRIPTION
          "The number of ATMP packets containing a bad ATMP version
           number received by the ATMP daemon process on the GRF."
      ::= { atmpReceiveProtocolErrorStats 15 }

    atmpRxBufferAllocFailPkts OBJECT-TYPE
      SYNTAX Counter
      ACCESS read-only
      STATUS mandatory
      DESCRIPTION
          "The number of received ATMP packets dropped due to buffer
           allocation failure by the ATMP daemon process on the GRF."
      ::= { atmpReceiveProtocolErrorStats 16 }

    atmpRxBadAtmpCodePkts OBJECT-TYPE
      SYNTAX Counter
      ACCESS read-only
      STATUS mandatory
      DESCRIPTION
          "The number of ATMP packets dropped due to receiving an invalid
           type of ATMP packet in the ATMP daemon process on the GRF."
      ::= { atmpReceiveProtocolErrorStats 17 }

    atmpRxNetworkErrors OBJECT-TYPE
      SYNTAX Counter
      ACCESS read-only
      STATUS mandatory
      DESCRIPTION
          "The number of occurrences of a network error while attempting
           to receive ATMP packets by the ATMP daemon process on the GRF."
      ::= { atmpReceiveProtocolErrorStats 18 }

    --
    -- Tx: Transmit error statistics
    --
    atmpTxErrorNotificationPkts OBJECT-TYPE
      SYNTAX Counter
      ACCESS read-only
      STATUS mandatory
      DESCRIPTION
          "The number of ATMP error notification packets sent by
           the ATMP daemon process on the GRF."
      ::= { atmpTransmitProtocolErrorStats 1 }

    atmpTxNoErrorPkts OBJECT-TYPE
      SYNTAX Counter
      ACCESS read-only
      STATUS mandatory
      DESCRIPTION
          "The number of ATMP error notification packets containing the
           NO_ERROR error code sent by the ATMP daemon process on
           the GRF."
      ::= { atmpTransmitProtocolErrorStats 2 }

    atmpTxAuthFailedPkts OBJECT-TYPE
      SYNTAX Counter
      ACCESS read-only
      STATUS mandatory
      DESCRIPTION
          "The number of ATMP error notification packets containing the
           AUTH_FAILED error code sent by the ATMP daemon process on
           the GRF."
      ::= { atmpTransmitProtocolErrorStats 3 }

    atmpTxNotEnabledPkts OBJECT-TYPE
      SYNTAX Counter
      ACCESS read-only
      STATUS mandatory
      DESCRIPTION
          "The number of ATMP error notification packets containing the
           NOT_ENABLED error code sent by the ATMP daemon process on
           the GRF."
      ::= { atmpTransmitProtocolErrorStats 4 }

    atmpTxTooManyPkts OBJECT-TYPE
      SYNTAX Counter
      ACCESS read-only
      STATUS mandatory
      DESCRIPTION
          "The number of ATMP error notification packets containing the
           TOO_MANY error code sent by the ATMP daemon process on
           the GRF."
      ::= { atmpTransmitProtocolErrorStats 5 }

    atmpTxParameterErrorPkts OBJECT-TYPE
      SYNTAX Counter
      ACCESS read-only
      STATUS mandatory
      DESCRIPTION
          "The number of ATMP error notification packets containing the
           PARAMETER_ERROR error code sent by the ATMP daemon process on
           the GRF."
      ::= { atmpTransmitProtocolErrorStats 6 }

    atmpTxInvalidTunnelIdPkts OBJECT-TYPE
      SYNTAX Counter
      ACCESS read-only
      STATUS mandatory
      DESCRIPTION
          "The number of ATMP error notification packets containing the
           INVALID_TUNNEL_ID error code sent by the ATMP daemon process on
           the GRF."
      ::= { atmpTransmitProtocolErrorStats 7 }

    atmpTxTimeoutPkts OBJECT-TYPE
      SYNTAX Counter
      ACCESS read-only
      STATUS mandatory
      DESCRIPTION
          "The number of ATMP error notification packets containing the
           TIMEOUT error code sent by the ATMP daemon process on
           the GRF."
      ::= { atmpTransmitProtocolErrorStats 8 }

    atmpTxNetUnreachablePkts OBJECT-TYPE
      SYNTAX Counter
      ACCESS read-only
      STATUS mandatory
      DESCRIPTION
          "The number of ATMP error notification packets containing the
           NET_UNREACHABLE error code sent by the ATMP daemon process on
           the GRF."
      ::= { atmpTransmitProtocolErrorStats 9 }

    atmpTxGeneralErrorPkts OBJECT-TYPE
      SYNTAX Counter
      ACCESS read-only
      STATUS mandatory
      DESCRIPTION
          "The number of ATMP error notification packets containing the
           GENERAL_ERROR error code sent by the ATMP daemon process on
           the GRF."
      ::= { atmpTransmitProtocolErrorStats 10 }

    atmpTxNetworkErrors OBJECT-TYPE
      SYNTAX Counter
      ACCESS read-only
      STATUS mandatory
      DESCRIPTION
          "The number of occurrences of a network error while attempting
           to send ATMP packets from the ATMP daemon process on the GRF."
      ::= { atmpTransmitProtocolErrorStats 11 }

    --
    -- ATMP Configuration and Runtime Tables
    --
    -- Foreign Agent Table
    --
    atmpFATable OBJECT-TYPE
      SYNTAX SEQUENCE OF AtmpFAEntry
      ACCESS not-accessible
      STATUS mandatory
      DESCRIPTION
          "The Foreign Agent Table.  A list of foreign agent records in
           the GRF ATMP configuration.  This table reflects the foreign
           agent records found in the configuration file of the ATMP
           daemon on the GRF.  The table is indexed by the foreign agent
           IP address (atmpFAIpAddress), and is ordered by the 32-bit
           numerical representation of the foreign agent IP address,
           lowest to highest."
      ::= { atmpTables 1 }

    atmpFAEntry OBJECT-TYPE
      SYNTAX AtmpFAEntry
      ACCESS not-accessible
      STATUS mandatory
      DESCRIPTION
          "An ATMP foreign agent record in the GRF ATMP configuration."
      INDEX { atmpFAIpAddress }
      ::= { atmpFATable 1 }

    AtmpFAEntry ::=
      SEQUENCE {
        atmpFAIpAddress
            IpAddress,
        atmpFAPassword
            DisplayString,
        atmpFANumberTunnels
            INTEGER
      }

    atmpFAIpAddress OBJECT-TYPE
      SYNTAX IpAddress
      ACCESS read-only
      STATUS mandatory
      DESCRIPTION
          "The IP address assigned to the foreign agent.  The home agent uses
           this as the destination address in the GRE header."
      ::= { atmpFAEntry 1 }

    atmpFAPassword OBJECT-TYPE
      SYNTAX DisplayString
      ACCESS read-only
      STATUS mandatory
      DESCRIPTION
          "The password that validates the foreign agent to the GRF home
           agent.  It is also configured in the mobile node's RADIUS profile
           as the Ascend-Home-Agent-Password.  If a password is not specified,
           tunnels cannot be negotiated.  Reading this object always results
           in a DisplayString of length zero; authentication may not be
           bypassed by reading the MIB object."
      DEFVAL { ''h }
      ::= { atmpFAEntry 2 }

    atmpFANumberTunnels OBJECT-TYPE
      SYNTAX INTEGER 
      ACCESS read-only
      STATUS mandatory
      DESCRIPTION
          "The number of tunnels associated with this foreign agent."
      ::= { atmpFAEntry 3 }


    --
    -- Home Network Table
    --
    atmpHNTable OBJECT-TYPE
      SYNTAX SEQUENCE OF AtmpHNEntry
      ACCESS not-accessible
      STATUS mandatory
      DESCRIPTION
          "Home Network Table.  A list of home network records in the GRF
           ATMP configuration.  This table reflects the home network
           records found in the configuration file of the ATMP daemon on
           the GRF.  Some per home network tunnel statistics are kept in
           this table.  The table is indexed by the home agent IP address
           (atmpHAIpAddress), and is ordered by the 32-bit numerical
           representation of the home agent IP address, lowest to highest."
      ::= { atmpTables 2 }

    atmpHNEntry OBJECT-TYPE
      SYNTAX AtmpHNEntry
      ACCESS not-accessible
      STATUS mandatory
      DESCRIPTION
          "An ATMP home network record in the GRF ATMP configuration."
      INDEX { atmpHAIpAddress }
      ::= { atmpHNTable 1 }

    AtmpHNEntry ::=
      SEQUENCE {
        atmpHAIpAddress
            IpAddress,
        atmpHNName
            DisplayString,
        atmpHNMTULimit
            INTEGER,
        atmpHNForceFragmentation
            INTEGER,
        atmpHNBadSourceNotification
            INTEGER,
        atmpHNMaxTunnels
            INTEGER,
        atmpHNInactivityTimeout
            INTEGER,
        atmpHNNumberTunnels
            INTEGER,
        atmpHNInactiveTunnelsRemoved
            Counter,
        atmpHNTunnelsMaxRejected
            Counter,
        atmpHNTunnelHighWater
            INTEGER,
        atmpHNSwitchToStandbyInterface
            Counter,
        atmpHNSwitchToPrimaryInterface
            Counter,
        atmpHNRxErrorCount
            Counter,
        atmpHNTxErrorCount
            Counter,
        atmpHNInterfaceCount
            INTEGER
      }

    atmpHAIpAddress OBJECT-TYPE
      SYNTAX IpAddress
      ACCESS read-only
      STATUS mandatory
      DESCRIPTION
          "The home agent address.  Each home network maps to a different
           local IP address on the GRF.  The foreign agent uses the address
           as the destination address in its IP encapsulation header.
           The GRF home agent uses it as the source address in its IP
           encapsulation header."
      ::= { atmpHNEntry 1 }

    atmpHNName OBJECT-TYPE
      SYNTAX DisplayString
      ACCESS read-only
      STATUS mandatory
      DESCRIPTION
          "The unique name expressed as a text string of up to 31 characters
           that is used by the foreign agent to identify the home network."
      ::= { atmpHNEntry 2 }

    atmpHNMTULimit OBJECT-TYPE
      SYNTAX INTEGER
      ACCESS read-only
      STATUS mandatory
      DESCRIPTION
          "Controls whether and how pre-fragmentation occurs.  If the value
           is 0 (the default), no pre-fragmentation is performed (post-
           fragmentation is performed).  If nonzero, mtu_limit specifies the
           maximum size of the fragments, prior to encapsulation, before 
           pre-fragmentation will occur.  If the value is -1 (auto), the
           mtu_limit is automatically computed for each packet so as to
           avoid post-fragmentation.  If the mtu_limit parameter is not
           present in the home network record, it is set to the default (0)."
      DEFVAL { 0 }
      ::= { atmpHNEntry 3 }

    atmpHNForceFragmentation OBJECT-TYPE
      SYNTAX INTEGER {
          -- The force_fragmentation parameter has the Boolean value yes or
          -- no, and is interpreted only when the mtu_limit is nonzero;
          -- otherwise it has no effect.  The force_fragmentation parameter
          -- controls the behavior of the GRF home agent when it receives a
          -- packet from the home network that requires pre-fragmentation,
          -- but has the IP DF (Don't Fragment) option set. 
          no( 1 ),    -- If force_fragmentation has the value no (the default),
                      -- then the GRF home agent rejects such packets, and
                      -- issues an ICMP HOST UNREACHABLE, MUST FRAGMENT message
                      -- in response.  This is the normal, required behavior
                      -- for a router. 
          yes( 2 )    -- If force_fragmentation has the value yes, then the
                      -- GRF home agent behaves in a non-standard way when it
                      -- receives such a packet: The GRF home agent accepts
                      -- the packet, clears the DF option in the IP header,
                      -- and processes it as if the DF option was not present. 
      }
      ACCESS read-only
      STATUS mandatory
      DESCRIPTION
          "Controls the behavior of the GRF home agent when it receives a
           packet from the home network that requires pre-fragmentation,
           but has the IP DF (Don't Fragment) option set.  It is ignored
           when mtu_limit is zero.  If the force_fragmentation parameter is
           not present in the home network record, it is set to no as the
           default."
      DEFVAL { no }
      ::= { atmpHNEntry 4 }

    atmpHNBadSourceNotification OBJECT-TYPE
      SYNTAX INTEGER {
          no( 1 ),    -- A packet received with non-matching source address
                      -- is dropped, no notification is made.
          yes( 1 )    -- This is the default.  A packet received with
                      -- non-matching source address is dropped and the
                      -- foreign agent is notified; the tunnel is torn down.
      }
      ACCESS read-only
      STATUS mandatory
      DESCRIPTION
          "Controls whether a foreign agent is notified when packets
           from a mobile node have a bad source address.  If the
           bad_source_notification parameter is not present in the
           home network record, the value defaults to yes."
      DEFVAL { no }
      ::= { atmpHNEntry 5 }

    atmpHNMaxTunnels OBJECT-TYPE
      SYNTAX INTEGER
      ACCESS read-only
      STATUS mandatory
      DESCRIPTION
          "The maximum number of tunnels allowed for the home network.
           The maximum tunnel value does not guarantee the number of usable
           tunnels per home network.  It is up to the local administrator to
           determine an appropriate value based on the predicted usage of
           each mobile node and the available bandwidth on the home agent
           to home network link.  The default 0 (zero) is to set no limit.
           If the max_tunnels parameter is not present in the home network
           record, the default value of zero is used."
      DEFVAL { 0 }
      ::= { atmpHNEntry 6 }

    atmpHNInactivityTimeout OBJECT-TYPE
      SYNTAX INTEGER 
      ACCESS read-only
      STATUS mandatory
      DESCRIPTION
          "The number of hours a home network's tunnels can be inactive
           before removal.  The default is 0 (zero) hours if no timer
           parameter is added.  A value of zero disables the inactivity
           timeout feature for the home network.  If the inactivity_timeout
           parameter is not present in the home network record, the default
           value of zero is used."
      DEFVAL { 0 }
      ::= { atmpHNEntry 7 }

    atmpHNNumberTunnels OBJECT-TYPE
      SYNTAX INTEGER 
      ACCESS read-only
      STATUS mandatory
      DESCRIPTION
          "The number of tunnels associated with this home network."
      ::= { atmpHNEntry 8 }

    atmpHNInactiveTunnelsRemoved OBJECT-TYPE
      SYNTAX Counter
      ACCESS read-only
      STATUS mandatory
      DESCRIPTION
          "The number of tunnels associated with this home network that
           were removed because of inactivity."
      ::= { atmpHNEntry 9 }

    atmpHNTunnelsMaxRejected OBJECT-TYPE
      SYNTAX Counter
      ACCESS read-only
      STATUS mandatory
      DESCRIPTION
          "The number of tunnels associated with this home network that
           were rejected because the maximum number of tunnels for the
           home network was exceeded."
      ::= { atmpHNEntry 10 }

    atmpHNTunnelHighWater OBJECT-TYPE
      SYNTAX INTEGER
      ACCESS read-only
      STATUS mandatory
      DESCRIPTION
          "The largest number of concurrently active tunnels associated
           with the home network."
      ::= { atmpHNEntry 11 }

    atmpHNSwitchToStandbyInterface OBJECT-TYPE
      SYNTAX Counter
      ACCESS read-only
      STATUS mandatory
      DESCRIPTION
          "The number of times the Home Agent had to switch to the
           standby interface when the primary interface went down."
      ::= { atmpHNEntry 12 }

    atmpHNSwitchToPrimaryInterface OBJECT-TYPE
      SYNTAX Counter
      ACCESS read-only
      STATUS mandatory
      DESCRIPTION
          "The number of times the Home Agent switched back to the
           primary interface when the primary interface went up again."
      ::= { atmpHNEntry 13 }

    atmpHNRxErrorCount OBJECT-TYPE
      SYNTAX Counter
      ACCESS read-only
      STATUS mandatory
      DESCRIPTION
          "The total number of errors received by this HN.  The last
           10 of these appear in atmpHNRxErrorTable."
      ::= { atmpHNEntry 14 }

    atmpHNTxErrorCount OBJECT-TYPE
      SYNTAX Counter
      ACCESS read-only
      STATUS mandatory
      DESCRIPTION
          "The total number of errors transmitted by this HN.  The last
           10 of these appear in atmpHNTxErrorTable."
      ::= { atmpHNEntry 15 }

    atmpHNInterfaceCount OBJECT-TYPE
      SYNTAX INTEGER
      ACCESS read-only
      STATUS mandatory
      DESCRIPTION
          "The number of interfaces (or circuits) configured for this HN."
      ::= { atmpHNEntry 16 }


    --
    -- The value of the result code from RFC 2107 plus 1.
    --
    AtmpResultCode ::= INTEGER {
        no-error( 1 ),          -- Successful operation.
        auth-failed( 2 ),       -- Authentication of the FA failed.
                                -- Registration denied.
        not-enabled( 3 ),       -- The home agent is not configured to
                                -- run ATMP.
        too-many( 4 ),          -- Too many MN sessions.  The HA is out
                                -- of resources.
        parameter-error( 5 ),   -- An invalid pvalue was detected in an
                                -- ATMP message.
        invalid-tunnel-id( 6 ), -- The tunnel ID contained in a GRE packet
                                -- is invalid or the corresonding mobility
                                -- binding does not exist.  This usually
                                -- occurs when either the MN or HA has reset.
        timeout( 7 ),           -- A response to an ATMP request was not
                                -- received in time.
        net-unreachable( 8 ),   -- The HN for this mobility binding is not
                                -- operational.
        general-error( 9 )      -- General Error indication.
    }


    --
    -- Home Network Transmit Error Table
    --
    atmpHNTxErrorTable OBJECT-TYPE
      SYNTAX SEQUENCE OF AtmpHNTxErrorEntry
      ACCESS not-accessible
      STATUS mandatory
      DESCRIPTION
          "Home Network Transmit Error Table.  A list of the most recent
           errors transmitted from a home network interface.  The error
           code, foreign agent IP address, and the timestamp of
           the transmitted error are tracked in this table.  A
           maximum of 10 errors are stored in this table.  The
           table is indexed by the home agent IP address
           (atmpHAIpAddress) and an error index (atmpHNTxErrorIndex).
           The table is ordered first by the 32-bit numerical
           representation of the home agent IP address, lowest to
           highest, and then by the error index, lowest to highest.
           The error index represents the order of occurrence, where
           the lower the index the more recent the occurrence."
      ::= { atmpTables 3 }

    atmpHNTxErrorEntry OBJECT-TYPE
      SYNTAX AtmpHNTxErrorEntry
      ACCESS not-accessible
      STATUS mandatory
      DESCRIPTION
          "A transmitted error entry of the Home Network Transmit
           Error Table."
      INDEX { atmpHAIpAddress, atmpHNTxErrorIndex }
      ::= { atmpHNTxErrorTable 1 }

    AtmpHNTxErrorEntry ::=
      SEQUENCE {
        atmpHNTxErrorIndex
            INTEGER,
        atmpHNTxErrorCode
            AtmpResultCode,
        atmpHNTxErrorFAIpAddress
            IpAddress,
        atmpHNTxErrorTime
            DisplayString
      }

    atmpHNTxErrorIndex OBJECT-TYPE
      SYNTAX INTEGER 
      ACCESS read-only
      STATUS mandatory
      DESCRIPTION
          "This is the secondary index for the Home Network Transmit
           Error Table.  Indices start at zero and represent the most
           recent to least recent errors that occurred."
      ::= { atmpHNTxErrorEntry 1 }

    atmpHNTxErrorCode OBJECT-TYPE
      SYNTAX AtmpResultCode
      ACCESS read-only
      STATUS mandatory
      DESCRIPTION
          "The error code sent to a foreign agent by the GRF ATMP
           daemon process for a home network.  The error code is
           the value of the result code from RFC 2107 plus 1."
      ::= { atmpHNTxErrorEntry 2 }

    atmpHNTxErrorFAIpAddress OBJECT-TYPE
      SYNTAX IpAddress
      ACCESS read-only
      STATUS mandatory
      DESCRIPTION
          "The IP address of the foreign agent that the GRF ATMP
           daemon process sent atmpHNTxErrorCode to.  If the error
           is associated with an existing tunnel, the foreign agent
           IP address comes from foreign agent record of the
           aitmd.conf configuration file.  Otherwise, the foreign
           agent IP address is the IP address associated with the
           network socket created to send to the foreign agent
           (e.g. failed tunnel negotiation due to unknown foreign
           agent IP address)."
      ::= { atmpHNTxErrorEntry 3 }

    atmpHNTxErrorTime OBJECT-TYPE
      SYNTAX DisplayString
      ACCESS read-only
      STATUS mandatory
      DESCRIPTION
          "The time atmpHNTxErrorCode was sent to the foreign agent."
      ::= { atmpHNTxErrorEntry 4 }


    --
    -- Home Network Receive Error Table
    --
    atmpHNRxErrorTable OBJECT-TYPE
      SYNTAX SEQUENCE OF AtmpHNRxErrorEntry
      ACCESS not-accessible
      STATUS mandatory
      DESCRIPTION
          "Home Network Receive Error Table.  A list of the most recent
           errors received on a home network interface.  The error
           code, foreign agent IP address, and the timestamp of
           the received error are tracked in this table.  A
           maximum of 10 errors are stored in this table.  The
           table is indexed by the home agent IP address
           (atmpHAIpAddress) and an error index (atmpHNRxErrorIndex).
           The table is ordered first by the 32-bit numerical
           representation of the home agent IP address, lowest to
           highest, and then by the error index, lowest to highest.
           The error index represents the order of occurrence, where
           the lower the index the more recent the occurrence."
      ::= { atmpTables 4 }

    atmpHNRxErrorEntry OBJECT-TYPE
      SYNTAX AtmpHNRxErrorEntry
      ACCESS not-accessible
      STATUS mandatory
      DESCRIPTION
          "A received error entry of the Home Network Transmit
           Error Table."
      INDEX { atmpHAIpAddress, atmpHNRxErrorIndex }
      ::= { atmpHNRxErrorTable 1 }

    AtmpHNRxErrorEntry ::=
      SEQUENCE {
        atmpHNRxErrorIndex
            INTEGER,
        atmpHNRxErrorCode
            AtmpResultCode,
        atmpHNRxErrorFAIpAddress
            IpAddress,
        atmpHNRxErrorTime
            DisplayString
      }

    atmpHNRxErrorIndex OBJECT-TYPE
      SYNTAX INTEGER 
      ACCESS read-only
      STATUS mandatory
      DESCRIPTION
          "This is the secondary index for the Home Network Receive
           Error Table.  Indices start at zero and represent the most
           recent to least recent errors that occurred."
      ::= { atmpHNRxErrorEntry 1 }

    atmpHNRxErrorCode OBJECT-TYPE
      SYNTAX AtmpResultCode
      ACCESS read-only
      STATUS mandatory
      DESCRIPTION
          "The error code received from a foreign agent by the GRF ATMP
           daemon process for a home network.  The error code is
           the value of the result code from RFC 2107 plus 1."
      ::= { atmpHNRxErrorEntry 2 }

    atmpHNRxErrorFAIpAddress OBJECT-TYPE
      SYNTAX IpAddress
      ACCESS read-only
      STATUS mandatory
      DESCRIPTION
          "The IP address of the foreign agent that the GRF ATMP
           daemon process received atmpHNRxErrorCode from."
      ::= { atmpHNRxErrorEntry 3 }

    atmpHNRxErrorTime OBJECT-TYPE
      SYNTAX DisplayString
      ACCESS read-only
      STATUS mandatory
      DESCRIPTION
          "The time atmpHNRxErrorCode was received from the foreign agent."
      ::= { atmpHNRxErrorEntry 4 }


    --
    -- Home Network Interface Table
    --
    atmpHNInterfaceTable OBJECT-TYPE
      SYNTAX SEQUENCE OF AtmpHNInterfaceEntry
      ACCESS not-accessible
      STATUS mandatory
      DESCRIPTION
          "Home Network Interface Table.  A list of interface/circuit
           records in a home network record of the GRF ATMP configuration.
           This table defines the interface/circuit records for the home
           network entries found in the Home Network Table.  There must
           be 1 or 2 entries in the configuration.  Each entry has values
           from the configuration file and system runtime parameters of
           the configuration items.  This table is indexed by the Home
           Network Table index (atmpHAIpAddress), and the home network
           interface priority (atmpHNInterfacePriority).  The table is
           ordered first by the 32-bit numerical representation of the
           home agent IP address, lowest to highest, and then by the
           interface priority, lowest to highest."
      ::= { atmpTables 5 }

    atmpHNInterfaceEntry OBJECT-TYPE
      SYNTAX AtmpHNInterfaceEntry
      ACCESS not-accessible
      STATUS mandatory
      DESCRIPTION
          "An ATMP interface record of a home network record in the GRF
           ATMP configuration."
      INDEX { atmpHAIpAddress, atmpHNInterfacePriority }
      ::= { atmpHNInterfaceTable 1 }

    AtmpHNInterfaceEntry ::=
      SEQUENCE {
        atmpHNInterfacePriority
            INTEGER,
        atmpHNInterfaceName
            DisplayString,
        atmpHNInterfaceConfigType
            INTEGER,
        atmpHNInterfaceCard
            INTEGER,
        atmpHNInterfacePort
            INTEGER,
        atmpHNInterfaceDcliOrVpi
            INTEGER,
        atmpHNInterfaceVci
            INTEGER,
        atmpHNInterfaceVpnAddress
            IpAddress,
        atmpHNInterfaceVpnNetmaskSize
            INTEGER,
        atmpHNInterfaceRipv2Enabled
            INTEGER,
        atmpHNInterfaceRipv2Metric
            INTEGER,
        atmpHNInterfaceRipv2Pkts
            Counter,
        atmpHNInterfaceCompleteness
            INTEGER
      }

    atmpHNInterfacePriority OBJECT-TYPE
      SYNTAX INTEGER {
          primary( 1 ),
          secondary( 2 )
      }
      ACCESS read-only
      STATUS mandatory
      DESCRIPTION
          "This is the secondary index for atmpHNInterfaceTable.  
           A combination of the home agent IP address and this 
           index uniquely identify the home network interface 
           entry (atmpHNInterfaceEntry)."
      ::= { atmpHNInterfaceEntry 1 }

    atmpHNInterfaceName OBJECT-TYPE
      SYNTAX DisplayString
      ACCESS read-only
      STATUS mandatory
      DESCRIPTION
          "Interface name in standard GRF gx0yz format that indicates media,
           slot, and logical interface number (interface{name})."
      ::= { atmpHNInterfaceEntry 2 }

    atmpHNInterfaceConfigType OBJECT-TYPE
      SYNTAX INTEGER {
          interface( 1 ),       -- the interface is configured using
                                -- an interace{} record
          circuit( 2 )          -- the interface is configured using
                                -- a circuit{} record
      }
      ACCESS read-only
      STATUS mandatory
      DESCRIPTION
          "The type of configuration record the interface is defined with
           in the GRF ATMP configuration file."
      ::= { atmpHNInterfaceEntry 3 }

    atmpHNInterfaceCard OBJECT-TYPE
      SYNTAX INTEGER
      ACCESS read-only
      STATUS mandatory
      DESCRIPTION
          "The slot number for a HSSI or ATM card.  For interface records,
           this is determined using the interface name (circuit{card})."
      ::= { atmpHNInterfaceEntry 4 }

    atmpHNInterfacePort OBJECT-TYPE
      SYNTAX INTEGER
      ACCESS read-only
      STATUS mandatory
      DESCRIPTION
          "The port number (or link) for the HSSI or ATM circuit.  For
           interface records, this is determined using the interface name
           (circuit{port})."
      ::= { atmpHNInterfaceEntry 5 }

    atmpHNInterfaceDcliOrVpi OBJECT-TYPE
      SYNTAX INTEGER
      ACCESS read-only
      STATUS mandatory
      DESCRIPTION
          "The DLCI for a HSSI link, or the VPI value for an ATMP PVC.
           For interface records, this is determined using the interface
           name (circuit{s0})."
      ::= { atmpHNInterfaceEntry 6 }

    atmpHNInterfaceVci OBJECT-TYPE
      SYNTAX INTEGER
      ACCESS read-only
      STATUS mandatory
      DESCRIPTION
          "The VCI value for an ATM PVC, or 0 (zero) if a HSSI card.  For
           interface records, this is determined using the interface name
           (circuit{s1})."
      ::= { atmpHNInterfaceEntry 7 }

    atmpHNInterfaceVpnAddress OBJECT-TYPE
      SYNTAX IpAddress
      ACCESS read-only
      STATUS mandatory
      DESCRIPTION
          "The customer-assigned virtual private network address for the
           home agent on the home network, must be in the private network
           address space.  If the vpn_addr parameter is not present in the
           interface (or circuit) record, the default value is
           255.255.255.255 (interface{vpn_addr})."
      ::= { atmpHNInterfaceEntry 8 }

    atmpHNInterfaceVpnNetmaskSize OBJECT-TYPE
      SYNTAX INTEGER (1..31)
      ACCESS read-only
      STATUS mandatory
      DESCRIPTION
          "Number of bits in the netmask for the virtual private network
           address.  If the vpn_netmask_size parameter is not present in
           the interface (or circuit) record, the default value is 0 (zero)
           (interface{vpn_netmask_size})."
      ::= { atmpHNInterfaceEntry 9 }

    atmpHNInterfaceRipv2Enabled OBJECT-TYPE
      SYNTAX INTEGER {
          no( 1 ),
          yes( 2 )
      }
      ACCESS read-only
      STATUS mandatory
      DESCRIPTION
          "Sets aitmd to send RIPv2 packets across the circuits to connected
           home networks.  The packets carry the routes of all mobile nodes
           assigned to this home agent.  The routes connect the home agent
           virtual private network address with the mobile node's private
           address.  If the ripv2 record is not present, this defaults to
           not enabled (ripv2{enabled})."
      DEFVAL { no }
      ::= { atmpHNInterfaceEntry 10 }

    atmpHNInterfaceRipv2Metric OBJECT-TYPE
      SYNTAX INTEGER
      ACCESS read-only
      STATUS mandatory
      DESCRIPTION
          "Specifies the metric advertised with each route, where the metric
           is ignored if enabled is specified as no.  If the ripv2 record is
           not present, this defaults to zero (ripv2{metric})."
      ::= { atmpHNInterfaceEntry 11 }

    atmpHNInterfaceRipv2Pkts OBJECT-TYPE
      SYNTAX Counter
      ACCESS read-only
      STATUS mandatory
      DESCRIPTION
          "The number of ripv2 packets sent by the GRF home agent on this
           interface."
      ::= { atmpHNInterfaceEntry 12 }

    atmpHNInterfaceCompleteness OBJECT-TYPE
      SYNTAX INTEGER {
        uninitialized( 1 ),       -- circuit info is not yet initialized
        complete( 2 ),            -- correct and complete
        no-map-to-if( 3 ),        -- have circuit, no ifname
        no-map-to-circuit( 4 ),   -- have ifname, no circuit
        from-circuit-no-if( 5 ),  -- have ifname map, no real interface
        from-if-no-if( 6 )        -- have circuit map, no real interface
      }
      ACCESS read-only
      STATUS mandatory
      DESCRIPTION
          "The completeness status of the interface.  A value other than
           complete (1) is considered an error status."
      ::= { atmpHNInterfaceEntry 13 }



    --
    -- Tunnel Table
    --
    atmpTunnelTable OBJECT-TYPE
      SYNTAX SEQUENCE OF AtmpTunnelEntry
      ACCESS not-accessible
      STATUS mandatory
      DESCRIPTION
          "The Tunnel Table.  A list of ATMP tunnel entries.  This table
           is indexed by the Home Network Table index (atmpHAIpAddress),
           and by the tunnel's mobile node address (atmpTunnelMNIpAddress).
           The table is ordered by the 32-bit numerical representation of
           the home agent IP address, lowest to highest, and then by the
           32-bit numerical representation of the tunnel's mobile node
           IP address, lowest to highest."
      ::= { atmpTables 6 }

    atmpTunnelEntry OBJECT-TYPE
      SYNTAX AtmpTunnelEntry
      ACCESS not-accessible
      STATUS mandatory
      DESCRIPTION
          "An ATMP tunnel entry."
      INDEX { atmpHAIpAddress, atmpTunnelMnIpAddress }
      ::= { atmpTunnelTable 1 }

    AtmpTunnelEntry ::=
      SEQUENCE {
        atmpTunnelId
            INTEGER,
        atmpTunnelState
            INTEGER,
        atmpTunnelProtocol
            INTEGER,
        atmpTunnelFAIpAddress
            IpAddress,
        atmpTunnelMnIpAddress
            IpAddress,
        atmpTunnelMnNetmask
            IpAddress,
        atmpTunnelMnIpxNetAddress
            OCTET STRING,
        atmpTunnelMnIpxNodeAddress
            OCTET STRING,
        atmpTunnelActive
            INTEGER,
        atmpTunnelInPkts
            Counter,
        atmpTunnelInOctets
            Counter,
        atmpTunnelInErrPkts
            Counter,
        atmpTunnelOutPkts
            Counter,
        atmpTunnelOutOctets
            Counter,
        atmpTunnelOutErrPkts
            Counter,
        atmpTunnelInOctetRate
            INTEGER,
        atmpTunnelInOctetSampleRate
            INTEGER,
        atmpTunnelOutOctetRate
            INTEGER,
        atmpTunnelOutOctetSampleRate
            INTEGER,
        atmpTunnelForcedToFragmentPkts
            Counter,
        atmpTunnelFailedToFragmentPkts
            Counter
      }

    atmpTunnelId OBJECT-TYPE
      SYNTAX INTEGER (0..65535)
      ACCESS read-only
      STATUS mandatory
      DESCRIPTION
          "The identification assigned to this tunnel. This number is assigned
           by the HA. NOTE: this number does *not* uniquely identify
           a tunnel by itself.  This is only unique per home network/agent."
      ::= { atmpTunnelEntry 1 }

    atmpTunnelState OBJECT-TYPE
      SYNTAX INTEGER {
          registering( 1 ),     -- registering with the HA
          up( 2 ),              -- tunnel is up
          down( 3 )             -- tunnel is going down
      }
      ACCESS read-only
      STATUS mandatory
      DESCRIPTION
          "The states the tunnel can be in."
      ::= { atmpTunnelEntry 2 }

    atmpTunnelProtocol OBJECT-TYPE
      SYNTAX INTEGER {
          ip( 1 ),              -- supports ip
          ipx( 2 )              -- supports ipx
      }
      ACCESS read-only
      STATUS mandatory
      DESCRIPTION
          "This value indicates the protocol(s) that the tunnel supports.
           The value is a sum. The sum initially takes the value zero.
           Then for each protocol that is supported, the value of the 
           protocol is or'ed to the sum. Example: 3 means ip and ipx."
      ::= { atmpTunnelEntry 3 }

    atmpTunnelFAIpAddress OBJECT-TYPE
      SYNTAX IpAddress
      ACCESS read-only
      STATUS mandatory
      DESCRIPTION
          "The IP address assigned to the foreign agent associated with
           this tunnel.  This can be used as the index into the Foreign
           Agent Table."
      ::= { atmpTunnelEntry 4 }

    atmpTunnelMnIpAddress OBJECT-TYPE
      SYNTAX IpAddress
      ACCESS read-only
      STATUS mandatory
      DESCRIPTION
          "The IP Address of the Mobile Node."
      ::= { atmpTunnelEntry 5 }

    atmpTunnelMnNetmask OBJECT-TYPE
      SYNTAX IpAddress
      ACCESS read-only
      STATUS mandatory
      DESCRIPTION
          "The netmask of the Mobile Node."
      ::= { atmpTunnelEntry 6 }

    atmpTunnelMnIpxNetAddress OBJECT-TYPE
      SYNTAX OCTET STRING (SIZE (4))
      ACCESS read-only
      STATUS mandatory
      DESCRIPTION
          "The IPX network address of the Mobile Node."
      ::= { atmpTunnelEntry 7 }

    atmpTunnelMnIpxNodeAddress OBJECT-TYPE
      SYNTAX OCTET STRING (SIZE (6))
      ACCESS read-only
      STATUS mandatory
      DESCRIPTION
          "The IPX node address of the Mobile Node."
      ::= { atmpTunnelEntry 8 }

    atmpTunnelActive OBJECT-TYPE
      SYNTAX INTEGER {
          inactive( 1 ),        -- tunnel is inactive
          active( 2 )           -- tunnel is active
      }
      ACCESS read-only
      STATUS mandatory
      DESCRIPTION
          "The active/inactive status of the tunnel."
      ::= { atmpTunnelEntry 9 }

    atmpTunnelInPkts OBJECT-TYPE
      SYNTAX Counter
      ACCESS read-only
      STATUS mandatory
      DESCRIPTION
          "The number of packets received on this tunnel from the
           foreign agent.  This is not supported at this time and
           will contain a value of zero."
      ::= { atmpTunnelEntry 10 }

    atmpTunnelInOctets OBJECT-TYPE
      SYNTAX Counter
      ACCESS read-only
      STATUS mandatory
      DESCRIPTION
          "The number of octets received on this tunnel from the
           foreign agent.  This is not supported at this time and
           will contain a value of zero."
      ::= { atmpTunnelEntry 11 }

    atmpTunnelInErrPkts OBJECT-TYPE
      SYNTAX Counter
      ACCESS read-only
      STATUS mandatory
      DESCRIPTION
          "The number of packets received on this tunnel from the
           foreign agent that were dropped.  This is not supported
           at this time and will contain a value of zero."
      ::= { atmpTunnelEntry 12 }

    atmpTunnelOutPkts OBJECT-TYPE
      SYNTAX Counter
      ACCESS read-only
      STATUS mandatory
      DESCRIPTION
          "The number of packets sent on this tunnel to the foreign
           agent.  This is not supported at this time and wile contain
           a value of zero."
      ::= { atmpTunnelEntry 13 }

    atmpTunnelOutOctets OBJECT-TYPE
      SYNTAX Counter
      ACCESS read-only
      STATUS mandatory
      DESCRIPTION
          "The number of octets sent on this tunnel to the foreign
           agent.  This is not supported at this time and will contain
           a value of zero."
      ::= { atmpTunnelEntry 14 }

    atmpTunnelOutErrPkts OBJECT-TYPE
      SYNTAX Counter
      ACCESS read-only
      STATUS mandatory
      DESCRIPTION
          "The number of packets dropped on this tunnel before sending
           to the foreign agent.  This is not supported at this time and
           will contain a value of zero."
      ::= { atmpTunnelEntry 15 }

    atmpTunnelInOctetRate OBJECT-TYPE
      SYNTAX INTEGER
      ACCESS read-only
      STATUS mandatory
      DESCRIPTION
          "The number of octets per second received on this tunnel from
           the peer agent. atmpTunnelInOctets and atmpTunnelInOctetSampleRate
           affect this value.  This is not supported at this time and will
           contain a value of zero."
      ::= { atmpTunnelEntry 16 }

    atmpTunnelInOctetSampleRate OBJECT-TYPE
      SYNTAX INTEGER
      ACCESS read-only
      STATUS mandatory
      DESCRIPTION
          "The number of seconds between samples of atmpTunnelInOctets.
           This is not supported at this time and will contain a value
           of zero."
      ::= { atmpTunnelEntry 17 }

    atmpTunnelOutOctetRate OBJECT-TYPE
      SYNTAX INTEGER
      ACCESS read-only
      STATUS mandatory
      DESCRIPTION
          "The number of octets per second sent on this tunnel to the peer
           agent. atmpTunnelOutOctets and atmpTunnelOutOctetSampleRate
           affect this value.  This is not supported at this time and will
           contain a value of zero."
      ::= { atmpTunnelEntry 18 }

    atmpTunnelOutOctetSampleRate OBJECT-TYPE
      SYNTAX INTEGER
      ACCESS read-only
      STATUS mandatory
      DESCRIPTION
          "The number of seconds between samples of atmpTunnelOutOctets.
           This is not supported at this time and will contain a value
           of zero."
      ::= { atmpTunnelEntry 19 }

    atmpTunnelForcedToFragmentPkts OBJECT-TYPE
      SYNTAX Counter
      ACCESS read-only
      STATUS mandatory
      DESCRIPTION
          "The number of packets forced to pre-fragment despite the DF bit.
           This is not supported at this time and will contain a value of
           zero."
      ::= { atmpTunnelEntry 20 }

    atmpTunnelFailedToFragmentPkts OBJECT-TYPE
      SYNTAX Counter
      ACCESS read-only
      STATUS mandatory
      DESCRIPTION
          "The number of packets required to be fragmented but were
           dropped because force fragmentation was disabled and the
           DF bit in the IP header was set.  This is not supported at
           this time and will contain a value of zero."
      ::= { atmpTunnelEntry 21 }

END
