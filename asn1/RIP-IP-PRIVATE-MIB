RIP-IP-PRIVATE-MIB DEFINITIONS ::= BEGIN

-- Referencing the parent branch.

IMPORTS
            MODULE-IDENTITY, OBJECT-TYPE, IpAddress	FROM SNMPv2-SMI
	    RowStatus					FROM SNMPv2-TC
	    cjnProtocol                             	FROM Cajun-ROOT; 

cjnRip MODULE-IDENTITY
        LAST-UPDATED "9902110000Z" -- Wednesday Mar 3, 1999"
        ORGANIZATION "Lucent's Concord Technology Center (CTC)"
        CONTACT-INFO
	        "Erick Crowell -- ecrowell@lucent.com
		 Raj Duggal (Group Leader) -- rduggal@lucent.com
	         Kalpesh Sheth (sheth@lucent.com)
		 Ira Steckler -- isteckler@lucent.com"
	DESCRIPTION
       		"Cajun Private RIP MIB"
	::= { cjnProtocol 10 }

-- IP RIP (Routing Information Protocol) Global Configuration Group
--
	cjnIpRipGblGroup	OBJECT IDENTIFIER ::= { cjnRip 1 }
	
	cjnIpRipIsEnabled OBJECT-TYPE
              SYNTAX  INTEGER {
        	  false(0),
		   true(1)
		}	
              MAX-ACCESS  read-write
              STATUS  current
              DESCRIPTION
            	   "Enables IP RIP services on this device."
    	  ::= { cjnIpRipGblGroup 1 }

	cjnIpRipUpdateTimer OBJECT-TYPE
	   SYNTAX INTEGER
	   MAX-ACCESS read-write
	   STATUS current
	   DESCRIPTION
	   "RIP route Advertisement Interval (sec) "
	   ::= { cjnIpRipGblGroup 2 }
	
	cjnIpRipPurgeTTL OBJECT-TYPE
	   SYNTAX INTEGER
	   MAX-ACCESS read-write
	   STATUS current
	   DESCRIPTION
	   "TTL for purged RIP routes"
	   ::= { cjnIpRipGblGroup 3 }

	cjnIpRipTriggeredUpdates  OBJECT-TYPE
	    SYNTAX  INTEGER {
	      enable(1),
	      disable(2)
	    }	
	   MAX-ACCESS read-write
	   STATUS current
	   DESCRIPTION
	   "Enable/Disable Triggered RIP updates"
	   ::= { cjnIpRipGblGroup 4 }

	cjnIpRipInterPktDelay OBJECT-TYPE
	   SYNTAX INTEGER
	   MAX-ACCESS read-write
	   STATUS current
	   DESCRIPTION
	   "Delay between two successive RIP route Advertisements (sec)"
	   ::= { cjnIpRipGblGroup 5 }

-- IP RIP (Routing Information Protocol) Global Statistics Group
--
	cjnIpRipStatGroup	OBJECT IDENTIFIER ::= { cjnRip 2 }

-- IP RIP Interface Group
--
	cjnIpRipIfGroup		OBJECT IDENTIFIER ::= { cjnRip 3 }

	cjnIpRipIfTable OBJECT-TYPE
           SYNTAX  SEQUENCE OF CjnIpRipIfEntry
           MAX-ACCESS  not-accessible
           STATUS  current
           DESCRIPTION
           "A list of interface specific RIP Entries"
	   ::= {cjnIpRipIfGroup 1 }

	cjnIpRipIfEntry OBJECT-TYPE
	   SYNTAX  CjnIpRipIfEntry
           MAX-ACCESS  not-accessible
           STATUS  current
           DESCRIPTION
           "An cajun RIP Interface instance"
           INDEX   { cjnIpRipIfIpAddr }
           ::= { cjnIpRipIfTable 1 }

	CjnIpRipIfEntry ::=
	   SEQUENCE {
		cjnIpRipIfIpAddr
			IpAddress,
		cjnIpRipIfRowStatus
			RowStatus,	
		cjnIpRipIfSendRcvMode
			INTEGER,
		cjnIpRipIfSendVersion
			INTEGER,
		cjnIpRipIfRcvVersion
			INTEGER,
		cjnIpRipIfDefaultRouteMode
			INTEGER,
		cjnIpRipIfPoisonMethod
			INTEGER,
		cjnIpRipIfAuthType
			INTEGER,
		cjnIpRipIfAuthKey
			OCTET STRING
		}		
		
	cjnIpRipIfIpAddr OBJECT-TYPE
              SYNTAX  IpAddress
	      MAX-ACCESS  read-only
              STATUS  current
              DESCRIPTION
		"The globally unique IP Address identifier for this interface. This number
               	 MUST exist in the cjnIpIfTable to be valid."
	      ::= { cjnIpRipIfEntry 1 } 

	cjnIpRipIfRowStatus OBJECT-TYPE
              SYNTAX  RowStatus	
              MAX-ACCESS  read-create
              STATUS  current
              DESCRIPTION
                      "The Status of this entry in the table.  Note the
		available states: 
		active(1), -- Obviously Active on this interface.
		notInService(2) -- Configured on Interface but disabled.
		notReady(3), -- Interface entry NOT FULLY configured.
		createAndGo(4), -- NOT SUPPORTED.
		createAndWait(5)  
		or destroy(6) "
	      ::= { cjnIpRipIfEntry 2 }

	cjnIpRipIfSendRcvMode OBJECT-TYPE
        SYNTAX  INTEGER {
		talkOnly(1),
		listenOnly(2),
		talkAndListen(3)
		}	
	      MAX-ACCESS  read-create
        STATUS  current
        DESCRIPTION
              "RIP Send & Receive mode setting."
	      ::= { cjnIpRipIfEntry 3 } 

	cjnIpRipIfSendVersion OBJECT-TYPE
        SYNTAX  INTEGER {
		v1(1),
		v2(2),
		v1v2(3),
		off(4)
		}	
	      MAX-ACCESS  read-create
        STATUS  current
        DESCRIPTION
              "RIP version to adhere to, while sending updates"
	      ::= { cjnIpRipIfEntry 4 } 

	cjnIpRipIfRcvVersion OBJECT-TYPE
        SYNTAX  INTEGER {
		v1(1),
		v2(2),
    		v1v2(3),
		off(4)
		}	
	      MAX-ACCESS  read-create
        STATUS  current
        DESCRIPTION
              "RIP version to adhere to, while receiving updates"
	      ::= { cjnIpRipIfEntry 5 } 

	cjnIpRipIfDefaultRouteMode OBJECT-TYPE
        SYNTAX  INTEGER {
		talkOnly(1),
		listenOnly(2),
    		talkAndListen(3),
    		disable(4)
		}	
	      MAX-ACCESS  read-create
        STATUS  current
        DESCRIPTION
              "RIP default route characteristics. If this MIB Object is set to 
	talkOnly(1) then the known default route is advertised in RIP updates
	but ignored on incoming neighbor updates.  Is this MIB object is set to 
	listenOnly(2) then the known default route is supressed from outgoing
	RIP updates but accepted on incoming neighbor updates."
	      ::= { cjnIpRipIfEntry 6 } 

	cjnIpRipIfPoisonMethod OBJECT-TYPE
        SYNTAX  INTEGER {
		splitHorizon(1),
		splitHorizonWithPoisonReverse(2)
		}	
	      MAX-ACCESS  read-create
        STATUS  current
        DESCRIPTION
              "RIP Poison Reverse Mode."
	      ::= { cjnIpRipIfEntry 7 } 

	cjnIpRipIfAuthType OBJECT-TYPE
        SYNTAX  INTEGER {
		none(1),
		simplePassword(2),
    		mD5(3)
		}	
	      MAX-ACCESS  read-create
        STATUS  current
        DESCRIPTION
              "RIP authentication type"
	      ::= { cjnIpRipIfEntry 8 } 

	cjnIpRipIfAuthKey OBJECT-TYPE
        SYNTAX  OCTET STRING (SIZE(0..16))
	      MAX-ACCESS  read-create
        STATUS  current
        DESCRIPTION
              "RIP authentication key-valid only when cjnIpRipIfAuthType
              is not set to NONE"
	      ::= { cjnIpRipIfEntry 9 } 

-- IP RIP Interface Statistics Group
--

	cjnIpRipIfStatTable OBJECT-TYPE
           SYNTAX  SEQUENCE OF CjnIpRipIfStatEntry
           MAX-ACCESS  not-accessible
           STATUS  current
           DESCRIPTION
           "A list of interface specific RIP Statictics Entries"
	   ::= {cjnIpRipIfGroup 2 }

	cjnIpRipIfStatEntry OBJECT-TYPE
	   SYNTAX  CjnIpRipIfStatEntry
           MAX-ACCESS  not-accessible
           STATUS  current
           DESCRIPTION
           "An cajun RIP Interface Statistics instance"
           INDEX   { cjnIpRipIfStatIpAddr }
           ::= { cjnIpRipIfStatTable 1 }

	CjnIpRipIfStatEntry ::=
	   SEQUENCE {
		cjnIpRipIfStatIpAddr
			IpAddress,
		cjnIpRipIfUpdatesSent
			INTEGER,
		cjnIpRipIfUpdatesRcvd
			INTEGER,
		cjnIpRipIfTrigUpdatesSent
			INTEGER,
		cjnIpRipIfBadPktRcvd
			INTEGER,
		cjnIpRipIfBadRoutesRcvd
			INTEGER
		}
		
	cjnIpRipIfStatIpAddr OBJECT-TYPE
              SYNTAX  IpAddress
	      MAX-ACCESS  read-only
              STATUS  current
              DESCRIPTION
		"The globally unique IP Address identifier for this interface. This number
               	 MUST exist in the cjnIpIfTable to be valid."
	      ::= { cjnIpRipIfStatEntry 1 } 

	cjnIpRipIfUpdatesSent OBJECT-TYPE
        SYNTAX  INTEGER
	MAX-ACCESS  read-write
        STATUS  current
        DESCRIPTION
              "Total# of RIP updates sent on this if"
	      ::= { cjnIpRipIfStatEntry 2 } 

	cjnIpRipIfUpdatesRcvd OBJECT-TYPE
        SYNTAX  INTEGER
	MAX-ACCESS  read-write
        STATUS  current
        DESCRIPTION
              "Total# of RIP updates received on this if"
	      ::= { cjnIpRipIfStatEntry 3 } 

	cjnIpRipIfTrigUpdatesSent OBJECT-TYPE
        SYNTAX  INTEGER
	MAX-ACCESS  read-write
        STATUS  current
        DESCRIPTION
              "Total# of RIP triggered updates sent on this if"
	      ::= { cjnIpRipIfStatEntry 4 } 

	cjnIpRipIfBadPktRcvd OBJECT-TYPE
        SYNTAX  INTEGER
	MAX-ACCESS  read-write
        STATUS  current
        DESCRIPTION
              "Total# of RIP packets received in error on this if"
	      ::= { cjnIpRipIfStatEntry 5 } 

	cjnIpRipIfBadRoutesRcvd OBJECT-TYPE
        SYNTAX  INTEGER
	MAX-ACCESS  read-write
        STATUS  current
        DESCRIPTION
              "Total# of bad RIP network routes received in error on this if"
	      ::= { cjnIpRipIfStatEntry 6 } 


-- IP RIP Neighbor Group
--
	cjnIpRipNeighborGroup		OBJECT IDENTIFIER ::= { cjnRip 4 }

	cjnIpRipNeighborTable OBJECT-TYPE
           SYNTAX  SEQUENCE OF CjnIpRipNeighborEntry
           MAX-ACCESS  not-accessible
           STATUS  current
           DESCRIPTION
           "A list of RIP Trusted Neighbors"
	   ::= {cjnIpRipNeighborGroup 1 }

	cjnIpRipNeighborEntry OBJECT-TYPE
	   SYNTAX  CjnIpRipNeighborEntry
           MAX-ACCESS  not-accessible
           STATUS  current
           DESCRIPTION
           "A RIP Trusted Neighbor Entry"
           INDEX   { cjnIpRipNeighborIpAddr }
           ::= { cjnIpRipNeighborTable 1 }

	CjnIpRipNeighborEntry ::=
	   SEQUENCE {
		cjnIpRipNeighborIpAddr
			IpAddress,
		cjnIpRipNeighborRowStatus
			RowStatus
		}		

	cjnIpRipNeighborIpAddr OBJECT-TYPE
              SYNTAX  IpAddress
	      MAX-ACCESS  read-only
              STATUS  current
              DESCRIPTION
		"The IP Address identifier for this neighbor."
	      ::= { cjnIpRipNeighborEntry 1 }

	cjnIpRipNeighborRowStatus OBJECT-TYPE
              SYNTAX  RowStatus	
              MAX-ACCESS  read-create
              STATUS  current
              DESCRIPTION
                      "The Status of this entry in the table.  Note the
		available states: 
		active(1), -- Obviously Active on this interface.
		notInService(2) -- Configured on Interface but disabled.
		notReady(3), -- Interface entry NOT FULLY configured.
		createAndGo(4), -- NOT SUPPORTED.
		createAndWait(5)  
		or destroy(6) "
	      ::= { cjnIpRipNeighborEntry 2 }  

END
