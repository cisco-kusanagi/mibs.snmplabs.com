NETWORK-ALCHEMY-HARDWARE-MIB DEFINITIONS ::= BEGIN

-- Title:		    Network Alchemy Hardware MIB
-- Date:		    January 31, 2000
-- Author:		    Jonny Larson (jlarson@network-alchemy.com)
-- Location:		    Santa Cruz, CA

IMPORTS  netalModules, hardware FROM NETAL-SMI
         MODULE-IDENTITY, OBJECT-TYPE, Integer32, IpAddress FROM SNMPv2-SMI
         DisplayString          FROM SNMPv2-TC;

networkAlchemyHardwareMIB MODULE-IDENTITY
    LAST-UPDATED "200010250000Z"
    ORGANIZATION "Network Alchemy, Inc."
    CONTACT-INFO 
		 "	Network Alchemy
			Customer Support

		  Postal: 1538 Pacific Av.
			Santa Cruz, CA 95060
			USA
	          E-Mail: snmp-contact@network-alchemy.com"

    DESCRIPTION "Hardware (and version) MIB module."
    REVISION "200010250000Z"
    DESCRIPTION "Four-digit year in dates."
    ::= { netalModules 4 }

hardwarePrimaryCPU OBJECT-TYPE
    SYNTAX      Integer32
    MAX-ACCESS	read-only
    STATUS	current
    DESCRIPTION "Percent idle"
    ::= { hardware 1 }

hardwaresecondarycpu OBJECT-TYPE
    SYNTAX      Integer32
    MAX-ACCESS	read-only
    STATUS	current
    DESCRIPTION "percent"
    ::= { hardware 2 }

hardwarehifnloadave OBJECT-TYPE
    SYNTAX      Integer32
    MAX-ACCESS	read-only
    STATUS	current
    DESCRIPTION "percent"
    ::= { hardware 3 }

hardwarememoryusage OBJECT-TYPE
    SYNTAX      Integer32
    MAX-ACCESS	read-only
    STATUS	current
    DESCRIPTION "Percent of memory currently in use."
    ::= { hardware 4 }

hardwarioload OBJECT-TYPE
    SYNTAX      Integer32
    MAX-ACCESS	read-only
    STATUS	current
    DESCRIPTION "PPS"
    ::= { hardware 5 }

hardwareuptime OBJECT-TYPE
    SYNTAX      Integer32
    MAX-ACCESS	read-only
    STATUS	current
    DESCRIPTION "Uptime in Seconds"
    ::= { hardware 6 }

hardwareosname OBJECT-TYPE
    SYNTAX      DisplayString
    MAX-ACCESS	read-only
    STATUS	current
    DESCRIPTION "Operating system name."
    ::= { hardware 7 }

hardwareosversion OBJECT-TYPE
    SYNTAX      DisplayString
    MAX-ACCESS	read-only
    STATUS	current
    DESCRIPTION "Operating system (kernel) version."
    ::= { hardware 8 }

hardwarecompileuser OBJECT-TYPE
    SYNTAX      DisplayString
    MAX-ACCESS	read-only
    STATUS	current
    DESCRIPTION "What user compiled this kernel."
    ::= { hardware 9 }

hardwarecompiledate OBJECT-TYPE
    SYNTAX      DisplayString
    MAX-ACCESS	read-only
    STATUS	current
    DESCRIPTION "Compile date and time."
    ::= { hardware 10 }

hardwarecompilehost OBJECT-TYPE
    SYNTAX      DisplayString
    MAX-ACCESS	read-only
    STATUS	current
    DESCRIPTION "Computer where this build was made."
    ::= { hardware 11 }

hardwareconfigversion OBJECT-TYPE
    SYNTAX      Integer32
    MAX-ACCESS	read-only
    STATUS	current
    DESCRIPTION "Version of config file (number of config saves)."
    ::= { hardware 12 }

END
