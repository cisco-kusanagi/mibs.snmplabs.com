-- @(#)SynchDataCircuit.mib	9.1 10/16/98
--------------------------------------------------------------------------------
-- file: SynchDataCircuit.mib
--
-- contents:
--	This file contains the Newbridge MIB extensions for a synchronous
--	data circuit, e.g. V.35, RS-232/V.24, X.21, RS-422, etc.
--	The information duplicates some provided by RFC 1317
--	but provides it in a form that is more amenable to use by the 82X1
--	client.
--
-- history:
--	0.1 / 92.08.25 / J. Watt / Creation
--	0.2 / 93.02.08 / J. Watt / Added nncExtSdcLeadsTable
--	0.3 / 93.02.11 / J. Watt / Fix nncExtSdcLeadOperState
--	0.4 / 93.03.05 / J. Watt / remove LeadsAsText objects,
--	0.5 / 93.04.04 / J. Watt / change case of [Oper|Admin]State enums,
--				   made OperState object R/W
--	0.6 / 93.04.26 / G. Celmainis / Added nncExtSdcLeadUIName, reversed state of 
--					LeadOperState
-- M321-C3.01 / 93.06.25 / S. Buchko / Added nncExtSdcActualSpeed
--
-- Copyright 1992 to 1993 Newbridge Networks Corporation.  All Rights Reserved.
--------------------------------------------------------------------------------
NNCGNI00X9-MIB	DEFINITIONS ::= BEGIN


	IMPORTS
		nncExtSyncDataCct
			FROM NNCGNI00X1-SMI

		PositionIndex
			FROM NNCGNI00X4-MIB
			
		PortIndex, CircuitIndex
			FROM  NNCGNI00X7-MIB
			
		DisplayString
			FROM RFC1213-MIB

		OBJECT-TYPE
			FROM RFC-1212;
			

	LeadIndex ::= INTEGER { rdl(1), alb(2), rts(3), dtr(4), ri(5),
				cts(6), dcd(7), dsr(8)}
				
-- for X.21, the C-lead is rts and the I lead is dcd
	
	LeadAdminState ::= INTEGER { forcedOn(1), forcedOff(2), assumedOn(3),
				assumedOff(4), monitor(5) }
				
	LeadOperState  ::= INTEGER { on(1), off(2) }
	

	nncExtSdcTable	OBJECT-TYPE
		SYNTAX	SEQUENCE OF NncExtSdcEntry
		ACCESS	not-accessible
		STATUS	mandatory

		::= { nncExtSyncDataCct 1 }
		
	
	nncExtSdcEntry	OBJECT-TYPE
		SYNTAX	NncExtSdcEntry
		ACCESS	not-accessible
		STATUS	mandatory

		INDEX { nncExtSdcPosnIdx, nncExtSdcPortIdx, nncExtSdcCctIdx }
		::= { nncExtSdcTable 1 }
		
		
	NncExtSdcEntry 
		::= SEQUENCE {
			nncExtSdcPosnIdx
				PositionIndex,
			nncExtSdcPortIdx
				PortIndex,
			nncExtSdcCctIdx
				CircuitIndex,
			nncExtSdcGender
				INTEGER,
			nncExtSdcSpeed
				INTEGER,
			nncExtSdcActualSpeed
				INTEGER
		}
		
	nncExtSdcPosnIdx	OBJECT-TYPE
		SYNTAX	PositionIndex
		ACCESS	read-only
		STATUS	mandatory

		::= { nncExtSdcEntry 1 }


	nncExtSdcPortIdx	OBJECT-TYPE
		SYNTAX	PortIndex
		ACCESS	read-only
		STATUS	mandatory

		::= { nncExtSdcEntry 2 }
		
	
	nncExtSdcCctIdx	OBJECT-TYPE
		SYNTAX	CircuitIndex
		ACCESS	read-only
		STATUS	mandatory

		::= { nncExtSdcEntry 3 }
		
	
	nncExtSdcGender	OBJECT-TYPE
		SYNTAX	INTEGER { dte(1), dce(2) }
		ACCESS	read-write
		STATUS 	mandatory

		::= { nncExtSdcEntry 4 }


	nncExtSdcSpeed	OBJECT-TYPE
		SYNTAX	INTEGER (1..2048000)
		ACCESS	read-write
		STATUS 	mandatory

		::= { nncExtSdcEntry 5 }

	nncExtSdcActualSpeed	OBJECT-TYPE
		SYNTAX	INTEGER (0..2048000)
		ACCESS	read-only
		STATUS	mandatory

			 
		::= { nncExtSdcEntry 6 }


	nncExtSdcLeadsTable	OBJECT-TYPE
		SYNTAX	SEQUENCE OF NncExtSdcLeadsEntry
		ACCESS	not-accessible
		STATUS	mandatory

		::= { nncExtSyncDataCct 2 }
		
	
	nncExtSdcLeadsEntry	OBJECT-TYPE
		SYNTAX	NncExtSdcLeadsEntry
		ACCESS	not-accessible
		STATUS	mandatory

		INDEX { nncExtSdcPosnIdx, nncExtSdcPortIdx, nncExtSdcCctIdx,
			nncExtSdcLeadIdx}
		::= { nncExtSdcLeadsTable 1 }
		
		
	NncExtSdcLeadsEntry 
		::= SEQUENCE {
			nncExtSdcLeadIdx
				LeadIndex,
			nncExtSdcLeadAdminState
				LeadAdminState,
			nncExtSdcLeadOperState
				LeadOperState,
			nncExtSdcLeadUIName
				DisplayString
		}

	nncExtSdcLeadIdx	OBJECT-TYPE
		SYNTAX	INTEGER { rdl(1), alb(2), rts(3), dtr(4), ri(5),
				cts(6), dcd(7), dsr(8)}
		ACCESS	read-only
		STATUS	mandatory

		::= { nncExtSdcLeadsEntry 1 }
		
		
	nncExtSdcLeadAdminState	OBJECT-TYPE
		SYNTAX	INTEGER { forcedOn(1), forcedOff(2), assumedOn(3),
				assumedOff(4), monitor(5) }
		ACCESS	read-write
		STATUS	mandatory

		::= { nncExtSdcLeadsEntry 2 }


	nncExtSdcLeadOperState	OBJECT-TYPE
		SYNTAX	INTEGER { on(1), off(2) }
		ACCESS	read-only
		STATUS	mandatory

		::= { nncExtSdcLeadsEntry 3 }

	nncExtSdcLeadUIName	OBJECT-TYPE
		SYNTAX	DisplayString (SIZE(1..3))
		ACCESS	read-only
		STATUS	mandatory

		::= { nncExtSdcLeadsEntry 4 }
	END
