-- This file is corresponding to Release 6.1.2.100 from 2001/09/26 00:00:00
-- (C)opyright 1991-2000 BinTec Communications AG, All Rights Reserved
-- $RCSfile: mibserial,v $ 
-- $Revision: 1.6 $ 

BIANCA-BRICK-SERIAL-MIB DEFINITIONS ::= BEGIN
 
        IMPORTS
            Counter
                FROM RFC1155-SMI
 
            OBJECT-TYPE
                FROM RFC-1212;

    org		OBJECT IDENTIFIER ::= { iso 3 }
    dod		OBJECT IDENTIFIER ::= { org 6 }
    internet	OBJECT IDENTIFIER ::= { dod 1 }
    private	OBJECT IDENTIFIER ::= { internet 4 }
    enterprises	OBJECT IDENTIFIER ::= { private 1 }
    bintec 	OBJECT IDENTIFIER ::= { enterprises 272 }
    bibo	OBJECT IDENTIFIER ::= { bintec 4 }
    serial	OBJECT IDENTIFIER 
	::= { bibo 25 }


    -- Interfaces Group

    -- Management Information for the Serial Subsystem 

	Date ::= INTEGER
	HexValue ::= INTEGER

        serialIfTable OBJECT-TYPE
            SYNTAX  SEQUENCE OF SerialIfEntry
            ACCESS  not-accessible
            STATUS  mandatory
            DESCRIPTION
		"The serialIfTable contains information relating to the 
                interfaces available on the system. Each entry corresponds to
                an available serial interface. Entries cannot be added or 
		deleted by the user. 

                Creating entries: Entries are created by the system
                automatically when a new serial module is installed.

                Deleting entries: Entries are removed by the system
                after the appropriate serial module is removed."
	::= { serial 1 }

	serialIfEntry OBJECT-TYPE
            SYNTAX  SerialIfEntry
            ACCESS  not-accessible
            STATUS  mandatory
            DESCRIPTION
		""
	    INDEX   { serialIfIndex }
              ::= { serialIfTable 1 }

	SerialIfEntry ::=
            SEQUENCE {
		-- configuration
                serialIfIndex			INTEGER,
		serialIfType			INTEGER,
		serialIfConnector		INTEGER,

		serialIfLeads			INTEGER,
		serialIfClock			INTEGER,
		serialIfSpeed			INTEGER,

		serialIfL2Mode			INTEGER,

		-- status
		serialIfL1State			INTEGER,
		serialIfSpeedReal		Counter,

		-- statistics
		serialIfRxPackets		Counter,
		serialIfRxOctets		Counter,
		serialIfTxPackets		Counter,
		serialIfTxOctets		Counter,
		serialIfRxResets		Counter,
		serialIfRxAborts		Counter,
		serialIfRxOverruns		Counter,
		serialIfRxCRCErrors		Counter,
		serialIfRxGiantFrames		Counter,
		serialIfTxResets		Counter,
		serialIfTxAborts		Counter,
		serialIfTxUnderruns		Counter,
		serialIfTxGiantFrames		Counter
            }

	serialIfIndex OBJECT-TYPE
            SYNTAX  INTEGER
            ACCESS  read-only
            STATUS  mandatory
            DESCRIPTION
                "Unique interface index of the serial interface."
	::= { serialIfEntry 1 }

	-- configuration

	serialIfType OBJECT-TYPE
            SYNTAX  INTEGER { none(1), x21(2), v35(3), v36(4), x21bis(5) }
            ACCESS  read-write
            STATUS  mandatory
            DESCRIPTION
                "The serial physical interface type
 		    none(1)	interface disabled
 		    x21(2)	X.21/V11   (synchronous)
 		    v35(3)	V.35/V11   (synchronous)
 		    v36(4)	V.36/V11   (synchronous)
 		    x21bis(5)	RS232/V.28 (synchronous)"
	::= { serialIfEntry 2 }

	serialIfConnector OBJECT-TYPE
            SYNTAX  INTEGER { dte(1), dce(2) }
            ACCESS  read-write
            STATUS  mandatory
            DESCRIPTION
                "The physical connector type.
	 	 When configured as DCE the pins on the output connector
		 act as a DCE interface. If configured as DTE on the output
		 connector act as a DTE interface.
		    dte(1)	DTE output pins  
		    dce(2) 	DCE output pins "
	::= { serialIfEntry 3 }

	serialIfLeads OBJECT-TYPE
            SYNTAX  INTEGER { enabled(1), disabled(2) }
            ACCESS  read-write
            STATUS  mandatory
            DESCRIPTION
		"The value of IfLeads has influence on the state of the
		 physical layer (L1State). When configured as
		 IfLeads=enabled, the state of the physical layer
		 depends on the signals of the control interface pins
		 Indication/Control on X.21 or RTS/CTS on the other
		 protocols. 
		 When configured as IfLeads=disabled, the state of the 
		 physical layer stays always up.
		    enabled(1)		interface pins accepted.	
		    disabled(2)		ignore interface pins." 
	::= { serialIfEntry 4 }

	serialIfClock OBJECT-TYPE
            SYNTAX  INTEGER { auto(1), extern(2), intern(3) }
            ACCESS  read-write
            STATUS  mandatory
            DESCRIPTION
                "The physical layer (layer 1) clocking mode.
	  	 When configured as AUTO the clock provided depends what is
		 configured on connector. If connector is configured as
		 DTE clock must provided from external, if the connector is
		 configured as DCE clock is generated and is provided at
		 the output pins.
		 It is possible to configure the clock independed from
		 connector type. EXTERNAL clock means the clock must provided
		 by the external device and INTERNAL clock means the clock
		 is generated by the brick and is provided on the output pins.
		 X.21 on clock line is provided.
		 V.35/V.36 two clock lines are provided.
		 auto(1)	connector = DTE = extern,
		 		            DCE = intern
		 extern(2)	clock pins operate as input.
		 intern(3)	clock pins operate as output."
	::= { serialIfEntry 5 }
		
	serialIfSpeed OBJECT-TYPE
	    SYNTAX  INTEGER
	    ACCESS  read-write
	    STATUS  mandatory
	    DESCRIPTION
		"The serial interface speed in bits per second. The range
		 is dependant on the type of the line (balanced/unbalanced)
		 and the quality and length of the cable.
		 Over a short distance (about 5 m) and with a shielded cable 
		 speeds of up to 8 Mbit/sec are possible." 
	::= { serialIfEntry 8 }

	serialIfL2Mode OBJECT-TYPE
            SYNTAX  INTEGER { dte(1), dce(2), auto(3) }
            ACCESS  read-write
            STATUS  mandatory
            DESCRIPTION
                "The layer 2 mode. This value has influence on the
		 HDLC address field (first byte of a HDCL frame). When
		 configured as DTE the address in a command frame is
		 0x01, when configured as DCE it is 0x03. For
		 response frames it is vice versa. When configured as
		 AUTO, layer 2 is set to the same as connector is set.
   		    dte(1)	HDLC address 0x01
		    dce(2)	HDLC address 0x03
		    auto(3)	same as conector = DTE=0x01 DCE=0x03" 
	::= { serialIfEntry 10 }

	-- status information

	serialIfL1State OBJECT-TYPE
            SYNTAX  INTEGER { dn(1), up(2) }
            ACCESS  read-only
            STATUS  mandatory
            DESCRIPTION
                "The serial physical layer state
 		  dn(1)		physical layer is inactive
                  up(2)		physical layer is active"
	::= { serialIfEntry 15 }

	serialIfSpeedReal OBJECT-TYPE
            SYNTAX  INTEGER
            ACCESS  read-only
            STATUS  mandatory
            DESCRIPTION
	    "In DCE/internal clock mode this is the rounded speed in bits per
	     second, because not every baudrate can exactly be generated.
	     In DTE/external clock mode this is the measured speed, where
	     measurement is possible, or the configured speed in serialIfSpeed."
	    ::= { serialIfEntry 16 }

	-- statistic counter

	serialIfRxPackets OBJECT-TYPE
            SYNTAX  Counter
            ACCESS  read-only
            STATUS  mandatory
            DESCRIPTION
                "Count of received valid Frames."
	::= { serialIfEntry 20 }

	serialIfRxOctets OBJECT-TYPE
            SYNTAX  Counter
            ACCESS  read-only
            STATUS  mandatory
            DESCRIPTION
		"Count of received bytes."
	::= { serialIfEntry 21 }

	serialIfTxPackets OBJECT-TYPE
            SYNTAX  Counter
            ACCESS  read-only
            STATUS  mandatory
            DESCRIPTION
                "Count of transmitted valid Frames."
	::= { serialIfEntry 22 }

	serialIfTxOctets OBJECT-TYPE
            SYNTAX  Counter
            ACCESS  read-only
            STATUS  mandatory
            DESCRIPTION
		"Count of transmitted bytes."
	::= { serialIfEntry 23 }

	serialIfRxResets OBJECT-TYPE
            SYNTAX  Counter
            ACCESS  read-only
            STATUS  mandatory
            DESCRIPTION
		"Count of receiver resets. Under rare circumstances it
		might be necessary to reset the receiver to work
		properly." 
	::= { serialIfEntry 24 }

	serialIfRxAborts OBJECT-TYPE
            SYNTAX  Counter
            ACCESS  read-only
            STATUS  mandatory
            DESCRIPTION
		"Count of receiver aborts. The sender of a frame can
		indicate a frame as aborted with a special Abort
		sequence." 
	::= { serialIfEntry 25 }

	serialIfRxOverruns OBJECT-TYPE
            SYNTAX  Counter
            ACCESS  read-only
            STATUS  mandatory
            DESCRIPTION
		"Count of receiver overruns. If the serial port is unable
		to grant sufficiently soon/often the bus, the
		RxFIFO may fill up. This leads to loss of data." 
	::= { serialIfEntry 26 }

	serialIfRxCRCErrors OBJECT-TYPE
            SYNTAX  Counter
            ACCESS  read-only
            STATUS  mandatory
            DESCRIPTION
		"Count of corrupted frames. Errors due to interference
		on the serial cable."
	::= { serialIfEntry 27 }

	serialIfRxGiantFrames OBJECT-TYPE
            SYNTAX  Counter
            ACCESS  read-only
            STATUS  mandatory
            DESCRIPTION
		"Count of received frames with illegal framesize. This
 		 can occur if a frame delimiter is destroyed." 
	::= { serialIfEntry 28 }

	serialIfTxResets OBJECT-TYPE
            SYNTAX  Counter
            ACCESS  read-only
            STATUS  mandatory
            DESCRIPTION
		"Count of transmitter resets. Under rare circumstances
		it might be necessary to reset the transmitter to work
		properly." 
	::= { serialIfEntry 29 }

	serialIfTxAborts OBJECT-TYPE
            SYNTAX  Counter
            ACCESS  read-only
            STATUS  mandatory
            DESCRIPTION
		"Count of transmitter aborts. While sending a frame it
		might be necessary to indicate this frame as aborted. In
		this case the receiver regards this frame as illegal." 
	::= { serialIfEntry 30 }

	serialIfTxUnderruns OBJECT-TYPE
            SYNTAX  Counter
            ACCESS  read-only
            STATUS  mandatory
            DESCRIPTION
		"Count of transmitter underruns. The serial data for the
		serial port is supplied too slowly." 
	::= { serialIfEntry 31 }

	serialIfTxGiantFrames OBJECT-TYPE
            SYNTAX  Counter
            ACCESS  read-only
            STATUS  mandatory
            DESCRIPTION
		"Count of transmitted frames with illegal
		framesize. This can occur if an upper module creates
		packets with more than the maximum allowed packet size."
	::= { serialIfEntry 32 }

END		-- of BIANCA-BRICK definitions
