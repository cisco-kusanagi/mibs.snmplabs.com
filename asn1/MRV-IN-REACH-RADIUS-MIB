-- $Id: ir-radius-mib.mib,v 1.1 2002/06/27 15:39:03 sse Exp $
            MRV-IN-REACH-RADIUS-MIB DEFINITIONS ::= BEGIN

                    IMPORTS
                            Counter
                                    FROM RFC1155-SMI
                            DisplayString
                                    FROM RFC1213-MIB
                            OBJECT-TYPE
                                    FROM RFC-1212
	                    mrvInReachProductDivision
                               FROM MRV-IN-REACH-PRODUCT-DIVISION-MIB;

            xRadius          OBJECT IDENTIFIER ::= { mrvInReachProductDivision 35 }

            -- MRV In-Reach Radius subgroups

            xRadiusPort             OBJECT IDENTIFIER ::= { xRadius 1 }
            xRadiusCircuit          OBJECT IDENTIFIER ::= { xRadius 2 }
            xRadiusConfig           OBJECT IDENTIFIER ::= { xRadius 3 }
            xRadiusServers          OBJECT IDENTIFIER ::= { xRadius 4 }
            xRadiusCounters         OBJECT IDENTIFIER ::= { xRadius 5 }
	        


            -- This is a MIB module for all MRV In-Reach systems that
            -- implement Radius.

            -- Copyright 2002 MRV Communications, Inc. All Rights Reserved.
            -- Reproduction of this document is authorized on
            -- condition that this copyright notice is included.
            -- This MIB document embodies MRV Communications, Inc.'s 
            -- proprietary intellectual property.  MRV Communications, Inc.
            -- retains all title and ownership in this MIB, including any
            -- revisions.
            --
            -- It is MRV Communications, Inc.'s intent to encourage the
            -- widespread use of this MIB in connection with the management of
            -- MRV Communications, Inc. products. MRV Communications,
            -- Inc. grants vendors,end-users, and other interested parties a
            -- non-exclusive license to use this MIB in connection with the
            -- management of MRV Communications, Inc. products.
            --
            -- This MIB document is supplied "AS IS," and MRV 
            -- Communications, Inc. makes no warranty, either express or
            -- implied, as to the use operation, condition, or performance of
            -- the MIB.


        -- the Radius  Port group

            xRadiusPortTable OBJECT-TYPE
                SYNTAX SEQUENCE OF XRadiusPortEntry
                ACCESS not-accessible
                STATUS mandatory
                DESCRIPTION
                    "Table of fields indexed by port."
                ::= { xRadiusPort 1 }

            xRadiusPortEntry OBJECT-TYPE
                SYNTAX XRadiusPortEntry
                ACCESS not-accessible
                STATUS mandatory
                DESCRIPTION
                    "A particular entry."
                INDEX { xRadiusPortIndex }
                ::= { xRadiusPortTable 1 }

            XRadiusPortEntry ::=
                SEQUENCE {
                        xRadiusPortIndex
                            INTEGER,
                        xRadiusPortStatus
                            INTEGER,
                        xRadiusPortSolicitStatus
                            INTEGER,
                        xRadiusAcctPortStatus
                            INTEGER
                         }

            xRadiusPortIndex OBJECT-TYPE
                SYNTAX INTEGER
                ACCESS read-only
                STATUS mandatory
                DESCRIPTION
                    "The index of the port."
                ::= { xRadiusPortEntry 1 }

            xRadiusPortStatus OBJECT-TYPE
                SYNTAX INTEGER { disabled(1), enabled(2) }
                ACCESS read-only
                STATUS mandatory
                DESCRIPTION
                    "Indicates the state of Radius Authentication on 
                     the port."
                DEFVAL { disabled }
                ::= { xRadiusPortEntry 2 }

            xRadiusPortSolicitStatus OBJECT-TYPE
                SYNTAX INTEGER { disabled(1), enabled(2) }
                ACCESS read-write
                STATUS mandatory
                DESCRIPTION
                    "Indicates the state of Radius solicitation mode 
                     on the port."
                DEFVAL { disabled }
                ::= { xRadiusPortEntry 3 }

            xRadiusAcctPortStatus OBJECT-TYPE
                SYNTAX INTEGER { disabled(1), enabled(2), limited(3) }
                ACCESS read-only
                STATUS mandatory
                DESCRIPTION
                    "Indicates the state of Radius Accounting on the port."
                DEFVAL { disabled }
                ::= { xRadiusPortEntry 4 }


        -- the Radius Circuit group

            xRadiusCircuitTable OBJECT-TYPE
                SYNTAX SEQUENCE OF XRadiusCircuitEntry
                ACCESS not-accessible
                STATUS mandatory
                DESCRIPTION
                    "Table of fields indexed by circuit."
                ::= { xRadiusCircuit 1 }

            xRadiusCircuitEntry OBJECT-TYPE
                SYNTAX XRadiusCircuitEntry
                ACCESS not-accessible
                STATUS mandatory
                DESCRIPTION
                    "A particular entry."
                INDEX { xRadiusCircuitIndex }
                ::= { xRadiusCircuitTable 1 }

            XRadiusCircuitEntry ::=
                SEQUENCE {
                        xRadiusCircuitIndex
                            INTEGER,
                        xRadiusCircAcctOnOff
                            INTEGER
                         }

            xRadiusCircuitIndex OBJECT-TYPE
                SYNTAX INTEGER
                ACCESS read-only
                STATUS mandatory
                DESCRIPTION
                    "The index of the circuit."
                ::= { xRadiusCircuitEntry 1 }

            xRadiusCircAcctOnOff OBJECT-TYPE
                SYNTAX INTEGER { disabled(1), enabled(2), limited(3) }
                ACCESS read-only
                STATUS mandatory
                DESCRIPTION
                    "Indicates the state of Radius Accounting on 
                     the circuit."
                DEFVAL { disabled }
                ::= { xRadiusCircuitEntry 2 }


        -- the Radius Configuration group

            xRadiusAuthServerPort OBJECT-TYPE
                SYNTAX INTEGER (0..65535)
                ACCESS read-write
                STATUS mandatory
                DESCRIPTION
                    "The UDP port on which the Radius authentication request
                     will be made."
                DEFVAL { 1645 }
                ::= { xRadiusConfig 1 }

            xRadiusAcctServerPort OBJECT-TYPE
                SYNTAX INTEGER (0..65535)
                ACCESS read-write
                STATUS mandatory
                DESCRIPTION
                    "The UDP port on which the Radius accounting request
                     will be made."
                DEFVAL { 1646 }
                ::= { xRadiusConfig 2 }

            xRadiusTimeout OBJECT-TYPE
                SYNTAX INTEGER (1..255)
                ACCESS read-write
                STATUS mandatory
                DESCRIPTION
                    "The period of time that the Radius client will wait
                     for a reply from the server."
                DEFVAL { 5 }
                ::= { xRadiusConfig 3 }

            xRadiusServerRetries OBJECT-TYPE
                SYNTAX INTEGER (1..10)
                ACCESS read-write
                STATUS mandatory
                DESCRIPTION
                    "The number of times a Radius server will be tried."
                DEFVAL { 3 }
                ::= { xRadiusConfig 4 }

            xRadiusAcctLogAttempts OBJECT-TYPE
                SYNTAX INTEGER (1..50000)
                ACCESS read-write
                STATUS mandatory
                DESCRIPTION
                    "The number of times the client will attempt to log
                     the accounting record to either the primary or 
                     secondary Radius server before giving up and failing."
                DEFVAL { 5 }
                ::= { xRadiusConfig 5 }

            xRadiusChapChallengeSize OBJECT-TYPE
                SYNTAX INTEGER (4..128)
                ACCESS read-write
                STATUS mandatory
                DESCRIPTION
                    "The size of the CHAP challenge that is sent to the 
                     peer and the Radius server."
                DEFVAL { 16 }
                ::= { xRadiusConfig 6 }

            xRadiusLogging OBJECT-TYPE
                SYNTAX INTEGER { disabled(1), enabled(2) }
                ACCESS read-write
                STATUS mandatory
                DESCRIPTION
                    "Indicates the state of Radius logging for packet 
                     tracing and troubleshooting. Messages are logged
                     to the MRV In-Reach event log."
                DEFVAL { disabled }
                ::= { xRadiusConfig 7 }

            xRadiusMessage OBJECT-TYPE
                SYNTAX DisplayString ( SIZE(40) )
                ACCESS read-write
                STATUS mandatory
                DESCRIPTION
                    "The authentication prompting message for Radius
                     logins."
                DEFVAL { "" }
                ::= { xRadiusConfig 8 }


        -- the Radius Server group

            xRadServer1SubGrp       OBJECT IDENTIFIER ::= { xRadiusServers 1 }
            xRadServer2SubGrp       OBJECT IDENTIFIER ::= { xRadiusServers 2 }

            -- the Radius Primary Server entries

            xRadiusServerName1 OBJECT-TYPE
                SYNTAX OCTET STRING ( SIZE(51) )
                ACCESS read-write
                STATUS mandatory
                DESCRIPTION
                    "The primary Radius server queried for authentication."
                DEFVAL { "" }
                ::= { xRadServer1SubGrp 1 }

                        -- Secrets shouldn't be accessed via SNMP
            xRadiusSecret1 OBJECT-TYPE
                SYNTAX OCTET STRING ( SIZE(32) )
                ACCESS read-only
                STATUS obsolete
                DESCRIPTION
                    "The secret value used to communicate with the primary
                     Radius server."
                DEFVAL { "Default_Secret" }
                ::= { xRadServer1SubGrp 2 }

            xRadiusServerAccess1 OBJECT-TYPE
                SYNTAX Counter
                ACCESS read-only
                STATUS mandatory
                DESCRIPTION
                    "The number of successful accesses of primary Radius 
                     server."
                ::= { xRadServer1SubGrp 3 }

            xRadiusServerAccessFailed1 OBJECT-TYPE
                SYNTAX Counter
                ACCESS read-only
                STATUS mandatory
                DESCRIPTION
                    "The number of failed accesses of primary Radius server."
                ::= { xRadServer1SubGrp 4 }

            -- the Radius Secondary Server entries

            xRadiusServerName2 OBJECT-TYPE
                SYNTAX OCTET STRING ( SIZE(51) )
                ACCESS read-write
                STATUS mandatory
                DESCRIPTION
                    "The secondary Radius server queried for authentication, 
                     if the primary one fails."
                DEFVAL { "" }
                ::= { xRadServer2SubGrp 1 }

                        -- Secrets shouldn't be accessed via SNMP
            xRadiusSecret2 OBJECT-TYPE
                SYNTAX OCTET STRING ( SIZE(32) )
                ACCESS read-only
                STATUS obsolete
                DESCRIPTION
                    "The secret value used to communicate with the 
                     secondary Radius server."
                DEFVAL { "Default_Secret" }
                ::= { xRadServer2SubGrp 2 }

            xRadiusServerAccess2 OBJECT-TYPE
                SYNTAX Counter
                ACCESS read-only
                STATUS mandatory
                DESCRIPTION
                    "The number of successful accesses of secondary Radius 
                     server."
                ::= { xRadServer2SubGrp 3}

            xRadiusServerAccessFailed2 OBJECT-TYPE
                SYNTAX Counter
                ACCESS read-only
                STATUS mandatory
                DESCRIPTION
                    "The number of failed accesses of secondary Radius 
                     server."
                ::= { xRadServer2SubGrp 4}


        -- the Radius Counters group

            xRadAuthCtsSubGrp   OBJECT IDENTIFIER ::= { xRadiusCounters 1 }
            xRadAcctCtsSubGrp   OBJECT IDENTIFIER ::= { xRadiusCounters 2 }

            -- the Radius Authentication Counters entries

            xRadiusLogins OBJECT-TYPE
                SYNTAX Counter
                ACCESS read-only
                STATUS mandatory
                DESCRIPTION
                    "The number of successful logins using Radius."
                ::= { xRadAuthCtsSubGrp 1 }

            xRadiusLoginsFailed OBJECT-TYPE
                SYNTAX Counter
                ACCESS read-only
                STATUS mandatory
                DESCRIPTION
                    "The number of failed logins resulting from being 
                     rejected by the Radius server."
                ::= { xRadAuthCtsSubGrp 2 }

            xRadiusConfigFailed OBJECT-TYPE
                SYNTAX Counter
                ACCESS read-only
                STATUS mandatory
                DESCRIPTION
                    "The number of failed logins resulting from unsupported
                     attribute values."
                ::= { xRadAuthCtsSubGrp 3 }

            xRadiusPolicyFailed OBJECT-TYPE
                SYNTAX Counter
                ACCESS read-only
                STATUS mandatory
                DESCRIPTION
                    "The number of failed logins resulting from failing
                     specific Radius policies on the MRV In-Reach unit."
                ::= { xRadAuthCtsSubGrp 4 }

            -- the Radius Accounting Counters entries

            xRadiusAcctSuccess OBJECT-TYPE
                SYNTAX Counter
                ACCESS read-only
                STATUS mandatory
                DESCRIPTION
                    "The number of successfully recorded Radius accounting
                     log records."
                ::= { xRadAcctCtsSubGrp 1}

            xRadiusAcctFailed OBJECT-TYPE
                SYNTAX Counter
                ACCESS read-only
                STATUS mandatory
                DESCRIPTION
                    "The number of failed (not logged) Radius accounting
                     log records."
                ::= { xRadAcctCtsSubGrp 2}

            xRadiusAcctReqWait OBJECT-TYPE
                SYNTAX Counter
                ACCESS read-only
                STATUS mandatory
                DESCRIPTION
                    "The number of log requests waiting for a reply from 
                     the Radius server."
                ::= { xRadAcctCtsSubGrp 3 }

      
END
