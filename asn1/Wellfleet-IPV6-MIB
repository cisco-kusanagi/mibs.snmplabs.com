Wellfleet-IPV6-MIB DEFINITIONS ::= BEGIN

-- Created by mdl2asn version 3.1
-- Creation date: Wed Sep 13 17:08:05 EDT 1995

    IMPORTS
      Counter, Gauge, TimeTicks, IpAddress
        FROM RFC1155-SMI
      OBJECT-TYPE
        FROM RFC-1212
      DisplayString, PhysAddress
        FROM RFC1213-MIB
      wfIpv6Group
        FROM Wellfleet-COMMON-MIB;

          -- textual conventions

    Ipv6Address ::=
              OCTET STRING (SIZE (16))
          -- This data type is used to model IPv6 addresses.
          -- This is a binary string of 16 octets.

    Ipv6AddressPrefix ::=
              OCTET STRING (SIZE (0..16))
          -- This data type is used to model IPv6 address prefixes.
          -- This is a binary string of up to 16 octets.


    wfIpv6RoutingGroup	  OBJECT IDENTIFIER ::= { wfIpv6Group 1 }
    wfIpv6IcmpGroup	  OBJECT IDENTIFIER ::= { wfIpv6Group 2 }
    wfIpv6NDiscGroup	  OBJECT IDENTIFIER ::= { wfIpv6Group 3 }
    wfIpv6UdpGroup	  OBJECT IDENTIFIER ::= { wfIpv6Group 4 }
    wfIpv6LogGroup	  OBJECT IDENTIFIER ::= { wfIpv6Group 5 }
    wfIpv6PolicyGroup     OBJECT IDENTIFIER ::= { wfIpv6Group 6 }


    wfIpv6RoutingGeneralGroup OBJECT IDENTIFIER ::= { wfIpv6RoutingGroup 1 }

-- IPv6 Base attributes

    wfIpv6Base		  OBJECT IDENTIFIER ::= { wfIpv6RoutingGeneralGroup 1 }

    wfIpv6BaseDelete OBJECT-TYPE
        SYNTAX	INTEGER {
    		    created(1),
    		    deleted(2)
    		}
        ACCESS	read-write
        STATUS	mandatory
        DESCRIPTION
                "Create/Delete parameter. Default is created.
                Users perform a set operation on this
                object in order to create/delete IPv6."
        DEFVAL	{ created }
        ::= { wfIpv6Base 1 }

    wfIpv6BaseDisable OBJECT-TYPE
        SYNTAX	INTEGER {
    		    enabled(1),
    		    disabled(2)
    		}
        ACCESS	read-write
        STATUS	mandatory
        DESCRIPTION
                "Enable/Disable parameter. Default is enabled.
                Users perform a set operation on this
                object in order to enable/disable IPv6."
        DEFVAL	{ enabled }
        ::= { wfIpv6Base 2 }

    wfIpv6BaseState OBJECT-TYPE
        SYNTAX	INTEGER {
    		    up(1),
    		    down(2),
    		    init(3),
    		    invalid(4),
    		    notpres(5)
    		}
        ACCESS	read-only
        STATUS	mandatory
        DESCRIPTION
                "The current state of the entire IPv6."
        DEFVAL	{ notpres }
        ::= { wfIpv6Base 3 }

    wfIpv6BaseForwarding OBJECT-TYPE
        SYNTAX	INTEGER {
    		    forwarding(1),
    		    notforwarding(2)
    		}
        ACCESS	read-write
        STATUS	mandatory
        DESCRIPTION
                "The indication of whether this entity is acting
                as an IPv6 router in respect to the forwarding of
                datagrams received by, but not addressed to, this
                entity.  IPv6 routers forward datagrams.  IPv6 hosts
                do not (except those source-routed via the host).

                Note that for some managed nodes, this object may
                take on only a subset of the values possible.
                Accordingly, it is appropriate for an agent to
                return a `badValue' response if a management
                station attempts to change this object to an
                inappropriate value."
        DEFVAL	{ forwarding }
        ::= { wfIpv6Base 4 }

    wfIpv6BaseDefaultHopLimit OBJECT-TYPE
        SYNTAX	INTEGER(0..255)
        ACCESS	read-write
        STATUS	mandatory
        DESCRIPTION
                "The default value inserted into the 'Hop Limit'
                field of the IPv6 header of datagrams originated at
                this entity, whenever a Hop-Limit value is not supplied
                by the transport layer protocol."
        DEFVAL	{ 64 }
        ::= { wfIpv6Base 5 }

    wfIpv6BaseMinLinkMTU OBJECT-TYPE
        SYNTAX	INTEGER(296..65535)
        ACCESS	read-write
        STATUS	mandatory
        DESCRIPTION
                "This parameter indicates the minimum link MTU
                that is assumed for every link in the IPv6 internet.
                IPv6 specification defines this value to be 576 bytes,
                which is the default value of this attribute.
                By changing this parameter to other number it is possible
                to control the maximum size of packets that can be
                generated by this router if the Path MTU discovery
		is disabled."
        DEFVAL	{ 576 }
        ::= { wfIpv6Base 6 }

    wfIpv6BaseMTUDiscovery OBJECT-TYPE
        SYNTAX	INTEGER {
    		    enabled(1),
    		    disabled(2)
    		}
        ACCESS	read-write
        STATUS	mandatory
        DESCRIPTION
                "Whether the Path MTU discovery support for
                self-originated traffic is enabled/disabled"
        DEFVAL	{ enabled }
        ::= { wfIpv6Base 7 }

    wfIpv6BaseMTUTimeout OBJECT-TYPE
        SYNTAX	INTEGER(0..71582788)
        ACCESS	read-write
        STATUS	mandatory
        DESCRIPTION
                "Timeout period for discovered Path MTU value in minutes.
                 0 indicates infinite timeout period, i.e. no timeout."
        DEFVAL	{ 10 }
        ::= { wfIpv6Base 8 }

    wfIpv6BaseIfNumber OBJECT-TYPE
        SYNTAX  INTEGER
        ACCESS  read-only
        STATUS  mandatory
        DESCRIPTION
                "The number of network interfaces (regardless of
                 their current state) present on this system."
        ::= { wfIpv6Base 9 }

    wfIpv6BaseNetworks OBJECT-TYPE
        SYNTAX	INTEGER
        ACCESS	read-only
        STATUS	mandatory
        DESCRIPTION
                "The number of network layer reachability entries
                in the routing table"
        ::= { wfIpv6Base 10 }

    wfIpv6BaseNodes OBJECT-TYPE
        SYNTAX	INTEGER
        ACCESS	read-only
        STATUS	mandatory
        DESCRIPTION
                "This parameter indicates the number of nodes known by IPv6"
        ::= { wfIpv6Base 11 }

    wfIpv6BaseHighestFilterRule OBJECT-TYPE
        SYNTAX	INTEGER(0..255)
        ACCESS	read-write
        STATUS	mandatory
        DESCRIPTION
                "The highest rule number (wfIpv6FilterNumber)
                 that can be used in a traffic filter definition."
        DEFVAL	{ 31 }
        ::= { wfIpv6Base 12 }

-- Network Layer Interface Configuration table

    wfIpv6IfTable OBJECT-TYPE
        SYNTAX	SEQUENCE OF WfIpv6IfEntry
        ACCESS	not-accessible
        STATUS	mandatory
        DESCRIPTION
                "The list of IPv6 interface entries.
		 This is the configuration table of logical
		 IPv6 interfaces at the network layer.

                 An IPv6 interface constitutes a logical network layer
		 attachment to a link ('circuit' in the Bay Networks
		 terminology) at the subnetwork/datalink layer,
		 i.e. the layer immediately below the network layer
		 including internet layer 'tunnels', such as tunnels
		 over IPv4 or IPv6 itself.

		 In Bay Network routers a subnetwork link (a.k.a. circuit)
		 is identified with a circuit id.  One or more circuits can
		 be configured on a physical link. One or more IPv6 logical
		 interfaces can be configured on a given circuit."
        ::= { wfIpv6RoutingGeneralGroup 2 }

    wfIpv6IfEntry OBJECT-TYPE
        SYNTAX	WfIpv6IfEntry
        ACCESS	not-accessible
        STATUS	mandatory
        DESCRIPTION
                "An interface entry containing objects at the
                 a particular IPv6 interface."
        INDEX	{ wfIpv6IfIndex }
        ::= { wfIpv6IfTable 1 }

    WfIpv6IfEntry ::= SEQUENCE {
    	    wfIpv6IfDelete
    		INTEGER,
    	    wfIpv6IfDisable
    		INTEGER,
    	    wfIpv6IfState
    		INTEGER,
    	    wfIpv6IfIndex
    		INTEGER,
    	    wfIpv6IfDescr
    		DisplayString,
    	    wfIpv6IfCircuit
    		INTEGER,
    	    wfIpv6IfCfgToken
    		OCTET STRING,
    	    wfIpv6IfCfgTokenLength
    		INTEGER,
    	    wfIpv6IfToken
    		OCTET STRING,
    	    wfIpv6IfTokenLength
    		INTEGER,
    	    wfIpv6IfCfgPhysicalAddress
    		PhysAddress,
    	    wfIpv6IfPhysicalAddress
    		PhysAddress,
    	    wfIpv6IfCfgLinkMTU
    		INTEGER,
    	    wfIpv6IfFwdCacheSize
    		INTEGER,
    	    wfIpv6IfSlotMask
    		Gauge,
    	    wfIpv6IfLastChange
    		TimeTicks,
    	    wfIpv6IfReasmMaxSize
    		INTEGER,
    	    wfIpv6IfMaxInfo
    		INTEGER,
    	    wfIpv6IfRedirect
    		INTEGER,
            wfIpv6IfIcmpErrorLimit
                INTEGER,
    	    wfIpv6IfTrEndStation
    		INTEGER,
    	    wfIpv6IfSMDSGroupAddress
    		OCTET STRING,
    	    wfIpv6IfFRBcastDlci
    		INTEGER,
    	    wfIpv6IfFRMcast1Dlci
    		INTEGER,
    	    wfIpv6IfFRMcast2Dlci
    		INTEGER,
    	    wfIpv6IfTunnelProtocol
    		INTEGER,
    	    wfIpv6IfIPv4TunnelLocalAddress
    		IpAddress,
    	    wfIpv6IfIPv4TunnelRemoteAddress
    		IpAddress,
    	    wfIpv6IfIpv6TunnelIfIndex
    		INTEGER,
    	    wfIpv6IfIpv6TunnelRemoteAddress
    		Ipv6Address
        }

    wfIpv6IfDelete OBJECT-TYPE
        SYNTAX	INTEGER {
    		    create(1),
    		    delete(2)
    		}
        ACCESS	read-write
        STATUS	mandatory
        DESCRIPTION
                "Create/Delete parameter. Default is created.
                Users perform a set operation on this
                object in order to create/delete an IPv6 interface."
        DEFVAL	{ create }
        ::= { wfIpv6IfEntry 1 }

    wfIpv6IfDisable OBJECT-TYPE
        SYNTAX	INTEGER {
    		    enabled(1),
    		    disabled(2)
    		}
        ACCESS	read-write
        STATUS	mandatory
        DESCRIPTION
                "Enable/Disable parameter. Default is enabled.
                Users perform a set operation on this
                object in order to enable/disable an IPv6 interface."
        DEFVAL	{ enabled }
        ::= { wfIpv6IfEntry 2 }

    wfIpv6IfState OBJECT-TYPE
        SYNTAX	INTEGER {
    		    up(1),        -- ready to pass packets
    		    tokenless(2), -- no address token
    		    down(3),
    		    init(4),
    		    invalid(5),
    		    notpres(6)
    		}
        ACCESS	read-only
        STATUS	mandatory
        DESCRIPTION
                "The current operational state of the interface.

		 Tokenless state indicates the no valid address token
		 is assigned to the interface. This state usually indicates
		 that the link-local interface address failed Duplicate
		 Address Detection.

		 Invalid state indicates an error in processing the cfg record."
        DEFVAL	{ notpres }
        ::= { wfIpv6IfEntry 3 }

    wfIpv6IfIndex OBJECT-TYPE
        SYNTAX	INTEGER
        ACCESS	read-only
        STATUS	mandatory
        DESCRIPTION
                "A unique non-zero value for each interface."
        ::= { wfIpv6IfEntry 4 }

     wfIpv6IfDescr OBJECT-TYPE
        SYNTAX  DisplayString (SIZE (0..255))
        ACCESS  read-write
        STATUS  mandatory
        DESCRIPTION
                "An optional textual string containing description of
                 the interface."
        ::= { wfIpv6IfEntry 5 }

    wfIpv6IfCircuit OBJECT-TYPE
        SYNTAX	INTEGER
        ACCESS	read-write
        STATUS	mandatory
        DESCRIPTION
                "The Circuit Number that this interface runs over.
		 If Circuit Number is between 1 and 1023, it identifies
		 a subnetwork/datalink layer interface, i.e. the layer
		 below the network layer.  A subnetwork layer interface
		 is associated with a physical link or, in some rare
		 cases, with a group of physical links.  Generally, 
		 more than one subnetwork layer interface can be defined
		 on a physical link (e.g. channels on a T1 link).
		
                 If the Circuit Number is higher that 1023, it's
                 a circuitless interface, i.e. a logical IPv6
                 interface that is not associated with any subnetwork
                 layer or physical layer interface.
		 
                 Zero indicates that it's a tunnel endpoint, i.e. IPv6
		 packets are encapsulated and transmitted by another
		 network layer protocol or another instance of the IPv6
		 protocol."
        ::= { wfIpv6IfEntry 6 }

    wfIpv6IfCfgToken OBJECT-TYPE
        SYNTAX	OCTET STRING (SIZE (0..8))
        ACCESS	read-write
        STATUS	mandatory
        DESCRIPTION
                "The desired identifier (interface token) for
		 this interface that is (at least) unique on
		 the link this interface is attached to.  The interface
		 token is combined with an address prefix to form an
		 interface address.  If no token value is configured
		 (the token length is zero),  the interface token is 
		 autoconfigured according to the rules of the link type
		 this interface is attached to."
        ::= { wfIpv6IfEntry 7 }

    wfIpv6IfCfgTokenLength OBJECT-TYPE
        SYNTAX	INTEGER (0..64)
        ACCESS	read-write
        STATUS	mandatory
        DESCRIPTION
                "The length of the configured interface token in bits."
        DEFVAL	{ 0 }
        ::= { wfIpv6IfEntry 8 }

    wfIpv6IfToken OBJECT-TYPE
        SYNTAX	OCTET STRING
        ACCESS	read-only
        STATUS	mandatory
        DESCRIPTION
                "The actual identifier (interface token) for
		 this interface that is (at least) unique on
		 the link this interface is attached to."
        ::= { wfIpv6IfEntry 9 }

    wfIpv6IfTokenLength OBJECT-TYPE
        SYNTAX	INTEGER (0..64)
        ACCESS	read-only
        STATUS	mandatory
        DESCRIPTION
                "The length of the interface token in bits."
        ::= { wfIpv6IfEntry 10 }

    wfIpv6IfCfgPhysicalAddress OBJECT-TYPE
        SYNTAX	PhysAddress
        ACCESS	read-write
        STATUS	mandatory
        DESCRIPTION
                "The desired link layer address set by the user"
        ::= { wfIpv6IfEntry 11 }

    wfIpv6IfPhysicalAddress OBJECT-TYPE
        SYNTAX	PhysAddress
        ACCESS	read-only
        STATUS	mandatory
        DESCRIPTION
                "The Physical Address for this Interface -
		 actual one used"
        ::= { wfIpv6IfEntry 12 }

    wfIpv6IfCfgLinkMTU OBJECT-TYPE
        SYNTAX	INTEGER (0..65535)
        ACCESS	read-write
        STATUS	mandatory
        DESCRIPTION
                "The configured link MTU. It will be only considered if
		 it is less than the default MTU of the underlying media.
		 A value of zero indicates that the default MTU of
		 the underlying media is to be used."
        DEFVAL	{ 0 }
        ::= { wfIpv6IfEntry 13 }

    wfIpv6IfFwdCacheSize OBJECT-TYPE
        SYNTAX	INTEGER(0..20480)
        ACCESS	read-write
        STATUS	mandatory
        DESCRIPTION
                "Maximum number of entries allowed in the Forwarding (Cache)
                 Table at one time.  There is a forwarding table per interface.
                 If this attribute is set to zero, the Forwarding Cache is not
                 used on this interface."
        DEFVAL	{ 128 }
        ::= { wfIpv6IfEntry 14 }

    wfIpv6IfSlotMask OBJECT-TYPE
        SYNTAX	Gauge
        ACCESS	read-write
        STATUS	mandatory
        DESCRIPTION
                "Slot mask for which slots a circuit-less interface is eligible
                to run on.  The most significant bit represents slot 1, the
                next most significant bit represents slot 2, and so on...
                Slots can be 1-14.  This is only valid if wfIpv6IfCircuit
                is greater than 1023."
        DEFVAL	{ 4294705152 }
        ::= { wfIpv6IfEntry 15 }

    wfIpv6IfLastChange OBJECT-TYPE
        SYNTAX  TimeTicks
        ACCESS  read-only
        STATUS  mandatory
        DESCRIPTION
                "The time (in hundredths of a second) since the node
		 was last re-initialized at the time the interface
                 entered its current operational state.  Usually
		 the time since boot."
        ::= { wfIpv6IfEntry 16 }

    wfIpv6IfReasmMaxSize OBJECT-TYPE
        SYNTAX	INTEGER
        ACCESS	read-only
        STATUS	mandatory
        DESCRIPTION
                "The size of the largest IPv6 datagram which this
                 entity can re-assemble from incoming IPv6 fragmented
                 packets received on this interface."
        ::= { wfIpv6IfEntry 17 }

    wfIpv6IfMaxInfo OBJECT-TYPE
        SYNTAX	INTEGER
        ACCESS	read-only
        STATUS	mandatory
        DESCRIPTION
                "The maximum size of the INFO (non-MAC) field that
                 this port will receive or transmit (effective MTU size)."
        ::= { wfIpv6IfEntry 18 }

    wfIpv6IfRedirect OBJECT-TYPE
        SYNTAX	INTEGER {
    		    on(1),
    		    off(2)
    		}
        ACCESS	read-write
        STATUS	mandatory
        DESCRIPTION
                "Indicates whether we're sending out redirects on
		 this Interface or not"
        DEFVAL	{ on }
        ::= { wfIpv6IfEntry 19 }

    wfIpv6IfIcmpErrorLimit OBJECT-TYPE
        SYNTAX	INTEGER
        ACCESS	read-write
        STATUS	mandatory
        DESCRIPTION
                "The maximum number of ICMP Error messages that is allowed
		 to be transmitted within 1 second interval out of
		 this interface."
        DEFVAL	{ 100 }
        ::= { wfIpv6IfEntry 20 }

    wfIpv6IfTrEndStation OBJECT-TYPE
        SYNTAX	INTEGER {
    		    on(1),
    		    off(2)
    		}
        ACCESS	read-write
        STATUS	mandatory
        DESCRIPTION
                "Use Source Routing over token ring selection. Only applies
                if a token ring interface."
        DEFVAL	{ off }
        ::= { wfIpv6IfEntry 21 }

    wfIpv6IfSMDSGroupAddress OBJECT-TYPE
        SYNTAX	OCTET STRING
        ACCESS	read-write
        STATUS	mandatory
        DESCRIPTION
                "The SMDS group address"
        ::= { wfIpv6IfEntry 22 }

    wfIpv6IfFRBcastDlci OBJECT-TYPE
        SYNTAX	INTEGER
        ACCESS	read-write
        STATUS	mandatory
        DESCRIPTION
                "Frame Relay broadcast dlci"
        ::= { wfIpv6IfEntry 23 }

    wfIpv6IfFRMcast1Dlci OBJECT-TYPE
        SYNTAX	INTEGER
        ACCESS	read-write
        STATUS	mandatory
        DESCRIPTION
                "Frame Relay multicast dlci #1"
        ::= { wfIpv6IfEntry 24 }

    wfIpv6IfFRMcast2Dlci OBJECT-TYPE
        SYNTAX	INTEGER
        ACCESS	read-write
        STATUS	mandatory
        DESCRIPTION
                "Frame Relay multicast dlci #2"
        ::= { wfIpv6IfEntry 25 }

    wfIpv6IfTunnelProtocol OBJECT-TYPE
        SYNTAX	INTEGER {
    		    ip4st(1),
    		    ip6st(2),
    		    ip4sa(3),
    		    ip6sa(4),
		    ip4au(5),
	 	    ip6au(6)
    		}
        ACCESS	read-write
        STATUS	mandatory
        DESCRIPTION
                "If wfIpv6IfCircuit is zero, this
                 parameter specifies the tunnel protocol type:
                   ip4st - IPv6-in-IPv4 static tunnel,
                   ip6st - IPv6-in-Ipv6 static tunnel,
                   ip4au - IPv6-in-IPv4 automatic tunnel,
                   ip6au - IPv6-in-Ipv6 automatic tunnel,
                   ip4sa - IPv6-in-Ipv4 semiautomatic tunnel,
                   ip6sa - IPv6-in-Ipv6 semiautomatic tunnel.

		 Static tunnels are tunnels where both local and remote
                 endpoints must be defined.  They are also called
                 configured tunnels.

		 Automatic tunnels are tunnels that don't have predefined
		 remote address,  i.e. the destination address of
		 encapsulating header is derived from the destination
                 address of encapsulated packet.  They also called
		 opened-end tunnels.

		 A semiautomatic tunnel acts as a static tunnel for outgoing
		 traffic and as an automatic (multipoint-to-point) tunnel
		 for incoming traffic. Both local and remote endpoints must
                 be configured."
        DEFVAL	{ ip4st }
        ::= { wfIpv6IfEntry 26 }

    wfIpv6IfIPv4TunnelLocalAddress OBJECT-TYPE
        SYNTAX	IpAddress
        ACCESS	read-write
        STATUS	mandatory
        DESCRIPTION
                "If wfIpv6IfCircuit is zero and the tunnel protocol
		 type is IPv4 or ip4sa, this parameter contains
		 the local IPv4 address of this interface's tunnel."
        ::= { wfIpv6IfEntry 27 }

    wfIpv6IfIPv4TunnelRemoteAddress OBJECT-TYPE
        SYNTAX	IpAddress
        ACCESS	read-write
        STATUS	mandatory
        DESCRIPTION
                "If wfIpv6IfCircuit is zero and the tunnel
		 protocol type is IPv4 or ip4sa, this parameter contains
		 the remote IPv4 address of this interface's tunnel.
		 If this address is 0.0.0.0, this is interface to
		 an automatic tunnel, i.e. the destination address
		 of encapsulating header is derived from the 
                 destination address of encapsulated packet."
        ::= { wfIpv6IfEntry 28 }

    wfIpv6IfIpv6TunnelIfIndex OBJECT-TYPE
        SYNTAX	INTEGER
        ACCESS	read-write
        STATUS	mandatory
        DESCRIPTION
                "If wfIpv6IfCircuit is zero and the tunnel
		 protocol type is IPv6 or ip6sa,  this parameter 
		 contains the IPv6 interface index of the local 
		 end of this interface's tunnel."
        DEFVAL	{ 0 }
        ::= { wfIpv6IfEntry 29 }

    wfIpv6IfIpv6TunnelRemoteAddress OBJECT-TYPE
        SYNTAX	Ipv6Address
        ACCESS	read-write
        STATUS	mandatory
        DESCRIPTION
                "If wfIpv6IfCircuit is zero and the tunnel
		 protocol type is IPv6 or ip6sa,  this parameter 
		 contains the remote IPv6 address
                 of this interface's tunnel. If this address
                 is unspecified (::0), this is interface to
		 an automatic tunnel, i.e. the destination address
		 of encapsulating header is derived from the destination
                 address of encapsulated packet."
        ::= { wfIpv6IfEntry 30 }


-- Address Prefix table

    wfIpv6AddrPrefixTable OBJECT-TYPE
        SYNTAX	SEQUENCE OF WfIpv6AddrPrefixEntry
        ACCESS	not-accessible
        STATUS	mandatory
        DESCRIPTION
                "The list of IPv6 address prefixes of
		 IPv6 interfaces."
        ::= { wfIpv6RoutingGeneralGroup 3 }

    wfIpv6AddrPrefixEntry OBJECT-TYPE
        SYNTAX	WfIpv6AddrPrefixEntry
        ACCESS	not-accessible
        STATUS	mandatory
        DESCRIPTION
                "An interface entry containing objects of
                 a particular IPv6 address prefix."
        INDEX	{ wfIpv6AddrPrefixIfIndex,
                  wfIpv6AddrPrefixIndex }
        ::= { wfIpv6AddrPrefixTable 1 }

    WfIpv6AddrPrefixEntry ::= SEQUENCE {
    	    wfIpv6AddrPrefixDelete
    		INTEGER,
    	    wfIpv6AddrPrefixDisable
    		INTEGER,
    	    wfIpv6AddrPrefixIfIndex
    		INTEGER,
    	    wfIpv6AddrPrefixIndex
    		INTEGER,
    	    wfIpv6AddrPrefix
    		Ipv6AddressPrefix,
    	    wfIpv6AddrPrefixLength
    		INTEGER,
    	    wfIpv6AddrPrefixPreference
    		INTEGER,
            wfIpv6AddrPrefixCost
    		INTEGER,
            wfIpv6AddrPrefixOnLinkFlag
    		INTEGER,
            wfIpv6AddrPrefixAutonomousFlag
    		INTEGER,
            wfIpv6AddrPrefixAdvPreferredLifetime
     		INTEGER,
            wfIpv6AddrPrefixAdvValidLifetime
     		INTEGER,
            wfIpv6AddrPrefixInvalid
                INTEGER,
            wfIpv6AddrPrefixAnycast
                INTEGER
        }

    wfIpv6AddrPrefixDelete OBJECT-TYPE
        SYNTAX	INTEGER {
    		    create(1),
    		    delete(2)
    		}
        ACCESS	read-write
        STATUS	mandatory
        DESCRIPTION
                "Create/Delete parameter. Default is created.
                Users perform a set operation on this object
                in order to create/delete this prefix entry."
        DEFVAL	{ create }
        ::= { wfIpv6AddrPrefixEntry 1 }

    wfIpv6AddrPrefixDisable OBJECT-TYPE
        SYNTAX	INTEGER {
    		    enabled(1),
    		    disabled(2)
    		}
        ACCESS	read-write
        STATUS	mandatory
        DESCRIPTION
                "Enable/Disable parameter. Default is enabled.
                Users perform a set operation on this
                object in order to enable/disable the use of
		a given prefix."
        DEFVAL	{ enabled }
        ::= { wfIpv6AddrPrefixEntry 2 }

    wfIpv6AddrPrefixIfIndex OBJECT-TYPE
        SYNTAX	INTEGER
        ACCESS	read-only
        STATUS	mandatory
        DESCRIPTION
                "The index value which uniquely identifies the IPv6
                 interface to which this entry is applicable.  The
                 interface identified by a particular value of this
                 index is the same interface as identified by the
                 same value of wfIpv6IfIndex."
        ::= { wfIpv6AddrPrefixEntry 3 }

    wfIpv6AddrPrefixIndex OBJECT-TYPE
        SYNTAX	INTEGER
        ACCESS	read-only
        STATUS	mandatory
        DESCRIPTION
                "A index value identifying this prefix on the IPv6
		 interface to which this entry's addressing information
                 pertains."
        ::= { wfIpv6AddrPrefixEntry 4 }

    wfIpv6AddrPrefix OBJECT-TYPE
        SYNTAX	Ipv6AddressPrefix
        ACCESS	read-write
        STATUS	mandatory
        DESCRIPTION
                "The prefix associated with the IPv6 address of
		 this interface."
        ::= { wfIpv6AddrPrefixEntry 5 }

    wfIpv6AddrPrefixLength OBJECT-TYPE
        SYNTAX	INTEGER (3..128)
        ACCESS	read-write
        STATUS	mandatory
        DESCRIPTION
                "The length of the prefix (in bits) associated with
                 the IPv6 address of this entry. A prefix can not be
		 shorter than 3 bits."
        ::= { wfIpv6AddrPrefixEntry 6 }

    wfIpv6AddrPrefixPreference OBJECT-TYPE
        SYNTAX	INTEGER(0..15)
        ACCESS	read-write
        STATUS	mandatory
        DESCRIPTION
                "The Routing Preference in 0 to 15 range.
                 A value of 15 is `most preferred'. Default 15."
        DEFVAL	{ 15 }
        ::= { wfIpv6AddrPrefixEntry 7 }

    wfIpv6AddrPrefixCost OBJECT-TYPE
        SYNTAX	INTEGER(1..15)
        ACCESS	read-write
        STATUS	mandatory
        DESCRIPTION
                "The Cost metric associated with this entry.
                (Used as the RIP metric)"
        DEFVAL	{ 1 }
        ::= { wfIpv6AddrPrefixEntry 8 }

    wfIpv6AddrPrefixOnLinkFlag OBJECT-TYPE
        SYNTAX	INTEGER {
    		    on(1),
    		    off(2)
    		}
        ACCESS	read-write
        STATUS	mandatory
        DESCRIPTION
                "On-link flag. When set (1), indicates that this
		 prefix can be used for on-link determination."
        DEFVAL	{ on }
        ::= { wfIpv6AddrPrefixEntry 9 }

    wfIpv6AddrPrefixAutonomousFlag OBJECT-TYPE
        SYNTAX	INTEGER {
    		    on(1),
    		    off(2)
    		}
        ACCESS	read-write
        STATUS	mandatory
        DESCRIPTION
                "Autonomous address configuration flag. When
		 set (1), indicates that this prefix can be used
		 for autonomous address configuration (i.e. can
		 be used to form a local interface address).
		 If off(2), it is not used to form a local
		 interface address but it is advertised in
		 ND's Router Advertisements."
        DEFVAL	{ on }
        ::= { wfIpv6AddrPrefixEntry 10 }

    wfIpv6AddrPrefixAdvPreferredLifetime OBJECT-TYPE
        SYNTAX	INTEGER
        ACCESS	read-write
        STATUS	mandatory
        DESCRIPTION
                "The value to be placed in the Preferred Lifetime field
		 in the Prefix Information option of Router Advertisements.
		 It is the length of time in seconds (relative to the time
		 the Router Advertisement is sent) that this prefix will
		 remain preferred, i.e. time until deprecation.  A value of
		 0xffffffff represents infinity.

		 The address generated from a deprecated prefix should no
		 longer be used as a source address in new communications,
		 but packets received on such an interface are processed
		 as expected."
        DEFVAL	{ 604800 }
        ::= { wfIpv6AddrPrefixEntry 11 }

    wfIpv6AddrPrefixAdvValidLifetime OBJECT-TYPE
        SYNTAX	INTEGER
        ACCESS	read-write
        STATUS	mandatory
        DESCRIPTION
                 "The value to be placed in the Valid Lifetime field
		 in the Prefix Information option of Router Advertisements.
		 It is the length of time in seconds (relative to the time
		 the Router Advertisement is sent) that this prefix will
		 remain valid, i.e. time until invalidation.  A value of
		 0xffffffff (-1) represents infinity.

                 The address generated from an invalidated prefix should
		 not appear as the destination or source address of a packet."
        DEFVAL	{ -1 }
        ::= { wfIpv6AddrPrefixEntry 12 }

    wfIpv6AddrPrefixInvalid OBJECT-TYPE
        SYNTAX	INTEGER {
    		    valid(1),
    		    invalid(2)
    		}
        ACCESS	read-only
        STATUS	mandatory
        DESCRIPTION
                "Whether this entry is valid or not:
		   valid     - usable prefix,
		   invalid   - misconfigured."
        ::= { wfIpv6AddrPrefixEntry 13 }

    wfIpv6AddrPrefixAnycast OBJECT-TYPE
        SYNTAX	INTEGER {
    		    true(1),
    		    false(2)
    		}
        ACCESS	read-only
        STATUS	mandatory
        DESCRIPTION
                "Whether this prefix is an anycast address prefix:
		   true     - anycast address prefix,
		   false    - unicast address prefix."
        DEFVAL	{ false }
        ::= { wfIpv6AddrPrefixEntry 14 }

-- the IPv6 Address table

    -- The IPv6 address table contains this node's IPv6 addressing
    -- information.

          wfIpv6AddrTable OBJECT-TYPE
              SYNTAX  SEQUENCE OF WfIpv6AddrEntry
              ACCESS  not-accessible
              STATUS  mandatory
              DESCRIPTION
                      "The table of addressing information relevant to
                       this node's interface addresses."
              ::= { wfIpv6RoutingGeneralGroup 4 }

          wfIpv6AddrEntry OBJECT-TYPE
              SYNTAX  WfIpv6AddrEntry
              ACCESS  not-accessible
              STATUS  mandatory
              DESCRIPTION
                      "The addressing information for one of this
                       node's interface addresses."
              INDEX   { wfIpv6AddrIfIndex,
                        wfIpv6AddrAddress }
              ::= { wfIpv6AddrTable 1 }

          WfIpv6AddrEntry ::=
              SEQUENCE {
                  wfIpv6AddrIfIndex
                      INTEGER,
                  wfIpv6AddrAddress
                      Ipv6Address,
                  wfIpv6AddrPfxLength
                      INTEGER,
                  wfIpv6AddrType
                      INTEGER,
                  wfIpv6AddrAnycastFlag
                      INTEGER,
                  wfIpv6AddrStatus
                      INTEGER
              }

          wfIpv6AddrIfIndex OBJECT-TYPE
              SYNTAX  INTEGER
              ACCESS  read-only
              STATUS  mandatory
              DESCRIPTION
                      "The index value which uniquely identifies the IPv6
                       interface to which this entry is applicable.  The
                       interface identified by a particular value of this
                       index is the same interface as identified by the
                       same value of wfIpv6IfIndex."
              ::= { wfIpv6AddrEntry 1 }

          wfIpv6AddrAddress OBJECT-TYPE
              SYNTAX  Ipv6Address
              ACCESS  read-only
              STATUS  mandatory
              DESCRIPTION
                      "The IPv6 address to which this entry's addressing
                       information pertains."
              ::= { wfIpv6AddrEntry 2 }

          wfIpv6AddrPfxLength OBJECT-TYPE
              SYNTAX  INTEGER
              ACCESS  read-only
              STATUS  mandatory
              DESCRIPTION
                      "The length of the prefix (in bits) associated with
                       the IPv6 address of this entry."
              ::= { wfIpv6AddrEntry 3 }

          wfIpv6AddrType OBJECT-TYPE
              SYNTAX	INTEGER {
                                -- address has been formed
                                -- using stateless
                 stateless(1),  -- autoconfiguration

                                -- address has been acquired
                                -- by stateful means
                                -- (e.g. DHCPv6, manual
                 stateful(2),   -- configuration)

                                -- type can not be determined
                 unknown(3)     -- for some reason.

    		}
              ACCESS  read-only
              STATUS  mandatory
              DESCRIPTION
               "The type of address. Note that 'stateless(2)'
               refers to an address that was statelessly
               autoconfigured; 'stateful(3)' refers to a address
               which was acquired by via a stateful protocol
               (e.g. DHCPv6, manual configuration)"
             ::= { wfIpv6AddrEntry 4 }

          wfIpv6AddrAnycastFlag OBJECT-TYPE
              SYNTAX	INTEGER {
    		    true(1),
    		    false(2)
    		}
              ACCESS  read-only
              STATUS  mandatory
              DESCRIPTION
               "This object has the value 'true(1)', if this
               address is an anycast address and the value
               'false(2)' otherwise."
              ::= { wfIpv6AddrEntry 5 }

          wfIpv6AddrStatus OBJECT-TYPE
              SYNTAX      INTEGER {
                  preferred(1),

                  deprecated(2),

                  invalid(3),

                  inaccessible(4),

                                     -- status can not be determined
                  unknown(5)         -- for some reason
               }
              ACCESS  read-only
              STATUS  mandatory
              DESCRIPTION
               "Address status.  The preferred(1) state indicates
               that this is a valid address that can appear as
               the destination or source address of a packet.
               The deprecated(2) this is a valid but deprecated
               address that should no longer be used as a source
               address in new communications, but packets addressed
               to such an address are processed as expected. The
               invalid(3) state indicates that this is not valid 
               address which should not appear as the destination
               or source address of a packet. The inaccessible(4)
               state indicates the address is not accessible because
               the interface to which this address is assigned is
               not operational."
             ::= { wfIpv6AddrEntry 6 }


-- Interface Statistics table

    wfIpv6IfStatsTable OBJECT-TYPE
        SYNTAX	SEQUENCE OF WfIpv6IfStatsEntry
        ACCESS	not-accessible
        STATUS	mandatory
        DESCRIPTION
                "IPv6 interface statistics"
        ::= { wfIpv6RoutingGeneralGroup 5 }

    wfIpv6IfStatsEntry OBJECT-TYPE
        SYNTAX	WfIpv6IfStatsEntry
        ACCESS	not-accessible
        STATUS	mandatory
        DESCRIPTION
            "An interface statistics entry containing objects at
            a particular IPv6 interface."
        INDEX	{ wfIpv6IfStatsIfIndex }
        ::= { wfIpv6IfStatsTable 1 }

    WfIpv6IfStatsEntry ::= SEQUENCE {
    	    wfIpv6IfStatsIfIndex
    		INTEGER,
    	    wfIpv6IfStatsInReceives
    		Counter,
    	    wfIpv6IfStatsInHdrErrors
    		Counter,
    	    wfIpv6IfStatsInTooBigErrors
    		Counter,
    	    wfIpv6IfStatsInNoRoutes
    		Counter,
    	    wfIpv6IfStatsInAddrErrors
    		Counter,
    	    wfIpv6IfStatsInUnknownProtos
    		Counter,
    	    wfIpv6IfStatsInDiscards
    		Counter,
    	    wfIpv6IfStatsInDelivers
    		Counter,
    	    wfIpv6IfStatsForwDatagrams
    		Counter,
    	    wfIpv6IfStatsOutRequests
    		Counter,
    	    wfIpv6IfStatsOutDiscards
    		Counter,
    	    wfIpv6IfStatsFragOKs
    		Counter,
    	    wfIpv6IfStatsFragFails
    		Counter,
    	    wfIpv6IfStatsFragCreates
    		Counter,
    	    wfIpv6IfStatsCacheMisses
    		Counter,
    	    wfIpv6IfStatsCacheNetworks
    		Counter,
    	    wfIpv6IfStatsCacheRemoves
    		Counter,
    	    wfIpv6IfStatsReasmReqds
    		Counter,
    	    wfIpv6IfStatsReasmOKs
    		Counter,
    	    wfIpv6IfStatsReasmFails
    		Counter,
    	    wfIpv6IfStatsMcastInPkts
    		Counter,
    	    wfIpv6IfStatsMcastOutPkts
    		Counter,
    	    wfIpv6IfStatsInTruncatedPkts
    		Counter
        }

     wfIpv6IfStatsIfIndex OBJECT-TYPE
        SYNTAX  INTEGER
        ACCESS  read-only
        STATUS  mandatory
        DESCRIPTION
                "The index value which uniquely identifies the IPv6
                 interface to which this entry is applicable.  The
                 interface identified by a particular value of this
                 index is the same interface as identified by the
                 same value of wfIpv6IfIndex."
        ::= { wfIpv6IfStatsEntry 1 }

    wfIpv6IfStatsInReceives OBJECT-TYPE
        SYNTAX	Counter
        ACCESS	read-only
        STATUS	mandatory
        DESCRIPTION
           "The total number of input datagrams received from
           interfaces, including those received in error."
        ::= { wfIpv6IfStatsEntry 2 }

    wfIpv6IfStatsInHdrErrors OBJECT-TYPE
        SYNTAX	Counter
        ACCESS	read-only
        STATUS	mandatory
        DESCRIPTION
                "The number of input datagrams discarded due to
                errors in their IPv6 headers, including version
                number mismatch, other format errors, hop count
                exceeded, errors discovered in processing their
                IPv6 options, etc."
        ::= { wfIpv6IfStatsEntry 3 }

    wfIpv6IfStatsInTooBigErrors OBJECT-TYPE
        SYNTAX	Counter
        ACCESS	read-only
        STATUS	mandatory
        DESCRIPTION
          "The number of input datagrams that could not be
          forwarded because their size exceeded the link MTU
          of outgoing interface."
        ::= { wfIpv6IfStatsEntry 4 }

    wfIpv6IfStatsInNoRoutes OBJECT-TYPE
        SYNTAX	Counter
        ACCESS	read-only
        STATUS	mandatory
        DESCRIPTION
           "The number of input datagrams discarded because no
            route could be found to transmit them to their
            destination."
        ::= { wfIpv6IfStatsEntry 5 }

    wfIpv6IfStatsInAddrErrors OBJECT-TYPE
        SYNTAX	Counter
        ACCESS	read-only
        STATUS	mandatory
        DESCRIPTION
                "The number of input datagrams discarded because
                the IPv6 address in their IPv6 header's destination
                field was not a valid address to be received at
                this entity.  This count includes invalid
                addresses (e.g., ::0) and unsupported addresses
                (e.g., addresses with unallocated prefixes).  For entities
                which are not IPv6 routers and therefore do not
                forward datagrams, this counter includes datagrams
                discarded because the destination address was not
                a local address."
        ::= { wfIpv6IfStatsEntry 6 }

    wfIpv6IfStatsInUnknownProtos OBJECT-TYPE
        SYNTAX	Counter
        ACCESS	read-only
        STATUS	mandatory
        DESCRIPTION
                "The number of locally-addressed datagrams
                received successfully but discarded because of an
                unknown or unsupported protocol."
        ::= { wfIpv6IfStatsEntry 7 }

    wfIpv6IfStatsInDiscards OBJECT-TYPE
        SYNTAX	Counter
        ACCESS	read-only
        STATUS	mandatory
        DESCRIPTION
                "The number of input IPv6 datagrams for which no
                problems were encountered to prevent their
                continued processing, but which were discarded
                (e.g., for lack of buffer space).  Note that this
                counter does not include any datagrams discarded
                while awaiting re-assembly."
        ::= { wfIpv6IfStatsEntry 8 }

    wfIpv6IfStatsInDelivers OBJECT-TYPE
        SYNTAX	Counter
        ACCESS	read-only
        STATUS	mandatory
        DESCRIPTION
                "The total number of input datagrams successfully
                delivered to IPv6 user-protocols (including ICMP)."
        ::= { wfIpv6IfStatsEntry 9 }

    wfIpv6IfStatsForwDatagrams OBJECT-TYPE
        SYNTAX	Counter
        ACCESS	read-only
        STATUS	mandatory
        DESCRIPTION
           "The number of output datagrams which this
           entity received and forwarded to their final
           destinations.  In entities which do not act
           as IPv6 routers, this counter will include
           only those packets which were Source-Routed
           via this entity, and the Source-Route
           processing was successful.  Note that for
           a successfully forwarded datagram the counter
           of the outgoing interface is incremented."
        ::= { wfIpv6IfStatsEntry 10 }

    wfIpv6IfStatsOutRequests OBJECT-TYPE
        SYNTAX	Counter
        ACCESS	read-only
        STATUS	mandatory
        DESCRIPTION
                "The total number of IPv6 datagrams which local IPv6
                user-protocols (including ICMP) supplied to IPv6 in
                requests for transmission.  Note that this counter
                does not include any datagrams counted in
                wfIpv6IfStatsForwDatagrams."
        ::= { wfIpv6IfStatsEntry 11 }

    wfIpv6IfStatsOutDiscards OBJECT-TYPE
        SYNTAX	Counter
        ACCESS	read-only
        STATUS	mandatory
        DESCRIPTION
                "The number of output IPv6 datagrams for which no
                problem was encountered to prevent their
                transmission to their destination, but which were
                discarded (e.g., for lack of buffer space).  Note
                that this counter would include datagrams counted
                in wfIpv6IfStatsForwDatagrams if any such
                packets met this (discretionary) discard criterion."
        ::= { wfIpv6IfStatsEntry 12 }

    wfIpv6IfStatsFragOKs OBJECT-TYPE
        SYNTAX	Counter
        ACCESS	read-only
        STATUS	mandatory
        DESCRIPTION
           "The number of IPv6 datagrams that have been
            successfully fragmented at this output interface."
        ::= { wfIpv6IfStatsEntry 13 }

    wfIpv6IfStatsFragFails OBJECT-TYPE
        SYNTAX	Counter
        ACCESS	read-only
        STATUS	mandatory
        DESCRIPTION
           "The number of IPv6 datagrams that have been
            discarded because they needed to be fragmented
            at this output interface but could not be."
        ::= { wfIpv6IfStatsEntry 14 }

    wfIpv6IfStatsFragCreates OBJECT-TYPE
        SYNTAX	Counter
        ACCESS	read-only
        STATUS	mandatory
        DESCRIPTION
           "The number of output datagram fragments that have
            been generated as a result of fragmentation at
            this output interface."
        ::= { wfIpv6IfStatsEntry 15 }

    wfIpv6IfStatsCacheMisses OBJECT-TYPE
        SYNTAX	Counter
        ACCESS	read-only
        STATUS	mandatory
        DESCRIPTION
                "The number of FFT cache misses (i.e how many times did the
                cache gate have to do a look up in the RNP because the FFT
                didn't have the destination network"
        ::= { wfIpv6IfStatsEntry 16 }

    wfIpv6IfStatsCacheNetworks OBJECT-TYPE
        SYNTAX	Counter
        ACCESS	read-only
        STATUS	mandatory
        DESCRIPTION
                "The number of network entries in the forwarding cache"
        ::= { wfIpv6IfStatsEntry 17 }

    wfIpv6IfStatsCacheRemoves OBJECT-TYPE
        SYNTAX	Counter
        ACCESS	read-only
        STATUS	mandatory
        DESCRIPTION
                "The number of networks which have been flushed from
                the forwarding cache"
        ::= { wfIpv6IfStatsEntry 18 }

    wfIpv6IfStatsReasmReqds OBJECT-TYPE
        SYNTAX	Counter
        ACCESS	read-only
        STATUS	mandatory
        DESCRIPTION
           "The number of IPv6 fragments received which needed
            to be reassembled at this interface.  Note that this
            counter is incremented at the interface to which
            these fragments were addressed which might not
            be necessarily the input interface for some of
            the fragments."
        ::= { wfIpv6IfStatsEntry 19 }

    wfIpv6IfStatsReasmOKs OBJECT-TYPE
        SYNTAX	Counter
        ACCESS	read-only
        STATUS	mandatory
        DESCRIPTION
                "The number of IPv6 datagrams successfully reassembled."
        ::= { wfIpv6IfStatsEntry 20 }

    wfIpv6IfStatsReasmFails OBJECT-TYPE
        SYNTAX	Counter
        ACCESS	read-only
        STATUS	mandatory
        DESCRIPTION
           "The number of failures detected by the IPv6 re-
           assembly algorithm (for whatever reason: timed
           out, errors, etc).  Note that this is not
           necessarily a count of discarded IPv6 fragments
           since some algorithms (notably the algorithm in
           RFC 815) can lose track of the number of fragments
           by combining them as they are received.
           This counter is incremented at the interface to which
           these fragments were addressed which might not be
           necessarily the input interface for some of the
           fragments."
        ::= { wfIpv6IfStatsEntry 21 }

    wfIpv6IfStatsMcastInPkts OBJECT-TYPE
        SYNTAX	Counter
        ACCESS	read-only
        STATUS	mandatory
        DESCRIPTION
                "The number of multicast packets received
                 by the interface"
        ::= { wfIpv6IfStatsEntry 22 }

    wfIpv6IfStatsMcastOutPkts OBJECT-TYPE
        SYNTAX	Counter
        ACCESS	read-only
        STATUS	mandatory
        DESCRIPTION
                "The number of multicast packets transmitted
                 by the interface"
        ::= { wfIpv6IfStatsEntry 23 }

    wfIpv6IfStatsInTruncatedPkts OBJECT-TYPE
        SYNTAX	Counter
        ACCESS	read-only
        STATUS	mandatory
        DESCRIPTION
                "The number of input datagrams discarded because
                datagram frame didn't carry enough data"
        ::= { wfIpv6IfStatsEntry 24 }


-- Static Route configuration table

    wfIpv6StaticRouteTable OBJECT-TYPE
        SYNTAX	SEQUENCE OF WfIpv6StaticRouteEntry
        ACCESS	not-accessible
        STATUS	mandatory
        DESCRIPTION
                "The list of static routes"
        ::= { wfIpv6RoutingGeneralGroup 6 }

    wfIpv6StaticRouteEntry OBJECT-TYPE
        SYNTAX	WfIpv6StaticRouteEntry
        ACCESS	not-accessible
        STATUS	mandatory
        DESCRIPTION
                "A static route definition"
        INDEX	{ wfIpv6StaticRouteIfIndex, wfIpv6StaticRouteId }
        ::= { wfIpv6StaticRouteTable 1 }

    WfIpv6StaticRouteEntry ::= SEQUENCE {
    	    wfIpv6StaticRouteDelete
    		INTEGER,
    	    wfIpv6StaticRouteDisable
    		INTEGER,
    	    wfIpv6StaticRouteIfIndex
    		INTEGER,
    	    wfIpv6StaticRouteId
    		INTEGER,
    	    wfIpv6StaticRoutePfx
    		Ipv6AddressPrefix,
    	    wfIpv6StaticRoutePfxLength
    		INTEGER,
    	    wfIpv6StaticRouteNextHopAddr
    		Ipv6Address,
    	    wfIpv6StaticRoutePreference
    		INTEGER,
    	    wfIpv6StaticRouteCost
    		INTEGER,
    	    wfIpv6StaticRouteInvalid
    		INTEGER
        }

    wfIpv6StaticRouteDelete OBJECT-TYPE
        SYNTAX	INTEGER {
    		    create(1),
    		    delete(2)
    		}
        ACCESS	read-write
        STATUS	mandatory
        DESCRIPTION
                "Create/Delete parameter. Default is created.
                Users perform a set operation on this
                object in order to create/delete the IPv6
                Static Route."
        DEFVAL	{ create }
        ::= { wfIpv6StaticRouteEntry 1 }

    wfIpv6StaticRouteDisable OBJECT-TYPE
        SYNTAX	INTEGER {
    		    enabled(1),
    		    disabled(2)
    		}
        ACCESS	read-write
        STATUS	mandatory
        DESCRIPTION
                "Enable/Disable parameter. Default is enabled.
                 Users perform a set operation on this object
                 in order to enable/disable this IPv6 Static
	         Route."
        DEFVAL	{ enabled }
        ::= { wfIpv6StaticRouteEntry 2 }

    wfIpv6StaticRouteIfIndex OBJECT-TYPE
        SYNTAX	INTEGER
        ACCESS	read-only
        STATUS	mandatory
        DESCRIPTION
                "The index value which uniquely identifies the local IPv6
		 interface to be used for forwarding to this Next Hop.
                 The interface identified by a particular value of this
                 index is the same interface as identified by the same
	         value of wfIpv6IfIndex.

                 If this parameter is 0, this is a black-hole route, 
                 i.e. packets to destinations matching this route
                 are to be discarded."
        ::= { wfIpv6StaticRouteEntry 3 }

    wfIpv6StaticRouteId OBJECT-TYPE
        SYNTAX	INTEGER
        ACCESS	read-only
        STATUS	mandatory
        DESCRIPTION
                "The Route Identifier: which numbered route this is to be"
        ::= { wfIpv6StaticRouteEntry 4 }

    wfIpv6StaticRoutePfx OBJECT-TYPE
        SYNTAX	Ipv6AddressPrefix
        ACCESS	read-write
        STATUS	mandatory
        DESCRIPTION
                "The destination IPv6 address prefix of this static route"
        ::= { wfIpv6StaticRouteEntry 5 }

    wfIpv6StaticRoutePfxLength OBJECT-TYPE
        SYNTAX	INTEGER(0..128)
        ACCESS	read-write
        STATUS	mandatory
        DESCRIPTION
                "The length (in bits) of the address prefix for this
		 static route"
        ::= { wfIpv6StaticRouteEntry 6 }

    wfIpv6StaticRouteNextHopAddr OBJECT-TYPE
        SYNTAX	Ipv6Address
        ACCESS	read-write
        STATUS	mandatory
        DESCRIPTION
                "The IPv6 Address of the next hop node.

                 This parameter is ignored for black-hole static routes."
        ::= { wfIpv6StaticRouteEntry 7 }

    wfIpv6StaticRoutePreference OBJECT-TYPE
        SYNTAX	INTEGER(0..15)
        ACCESS	read-write
        STATUS	mandatory
        DESCRIPTION
                "The Routing Preference in 0 to 15 range.
                A value of 15 is 'most preferred'. Default 15."
        DEFVAL	{ 15 }
        ::= { wfIpv6StaticRouteEntry 8 }

    wfIpv6StaticRouteCost OBJECT-TYPE
        SYNTAX	INTEGER(1..15)
        ACCESS	read-write
        STATUS	mandatory
        DESCRIPTION
                "The Cost of this Static Route. (Used as the RIP
                metric)"
        DEFVAL	{ 1 }
        ::= { wfIpv6StaticRouteEntry 9 }

    wfIpv6StaticRouteInvalid OBJECT-TYPE
        SYNTAX	INTEGER {
    		    valid(1),
    		    invalid(2)
    		}
        ACCESS	read-only
        STATUS	mandatory
        DESCRIPTION
                "Whether this Static Route is valid or not"
        DEFVAL	{ valid }
        ::= { wfIpv6StaticRouteEntry 10 }

-- Static IPv6->MAC resolutions table
 
   wfIpv6AdjacentNodeTable OBJECT-TYPE
        SYNTAX	SEQUENCE OF WfIpv6AdjacentNodeEntry
        ACCESS	not-accessible
        STATUS	mandatory
        DESCRIPTION
                "The list of Adjacent Static Nodes
		(static IPv6->MAC resolutions)"
        ::= { wfIpv6RoutingGeneralGroup 7 }

    wfIpv6AdjacentNodeEntry OBJECT-TYPE
        SYNTAX	WfIpv6AdjacentNodeEntry
        ACCESS	not-accessible
        STATUS	mandatory
        DESCRIPTION
                "A description of an adjacent node"
        INDEX	{ wfIpv6AdjNodeIfIndex,  wfIpv6AdjNodeAddress }
        ::= { wfIpv6AdjacentNodeTable 1 }

    WfIpv6AdjacentNodeEntry ::= SEQUENCE {
    	    wfIpv6AdjNodeDelete
    		INTEGER,
    	    wfIpv6AdjNodeDisable
    		INTEGER,
    	    wfIpv6AdjNodeIfIndex
    		INTEGER,
    	    wfIpv6AdjNodeAddress
    		Ipv6Address,
    	    wfIpv6AdjNodePhysicalAddr
    		PhysAddress,
    	    wfIpv6AdjNodeEncaps
    		INTEGER,
    	    wfIpv6AdjNodePreference
    		INTEGER,
    	    wfIpv6AdjNodeCost
    		INTEGER,
    	    wfIpv6AdjNodeInvalid
    		INTEGER,
    	    wfIpv6AdjNodeWanAddr
    		DisplayString
        }

    wfIpv6AdjNodeDelete OBJECT-TYPE
        SYNTAX	INTEGER {
    		    create(1),
    		    delete(2)
    		}
        ACCESS	read-write
        STATUS	mandatory
        DESCRIPTION
                "Whether to Delete this Adjacent Node"
        DEFVAL	{ create }
        ::= { wfIpv6AdjacentNodeEntry 1 }

    wfIpv6AdjNodeDisable OBJECT-TYPE
        SYNTAX	INTEGER {
    		    enabled(1),
    		    disabled(2)
    		}
        ACCESS	read-write
        STATUS	mandatory
        DESCRIPTION
                "Whether to Disable this Adjacent Node"
        DEFVAL	{ enabled }
        ::= { wfIpv6AdjacentNodeEntry 2 }

    wfIpv6AdjNodeIfIndex OBJECT-TYPE
        SYNTAX	INTEGER
        ACCESS	read-only
        STATUS	mandatory
        DESCRIPTION
                "The index value which uniquely identifies the local IPv6
		 interface through which this Adjacent Node should be reached.
                 The interface identified by a particular value of this
                 index is the same interface as identified by the same
	         value of wfIpv6IfIndex.

                 If this index is zero, this Adjacent Node is this router 
		 itself, i.e. 'wfIpv6AdjNodeAddress' address is treated as
		 a router's own local address. IPv6 datagrams with such
		 a destination address are considered to be consumed by
		 this router itself.  As an example, such an address can be
		 an IPv6 anycast address assigned to this router."
        ::= { wfIpv6AdjacentNodeEntry 4 }

    wfIpv6AdjNodeAddress OBJECT-TYPE
        SYNTAX	Ipv6Address
        ACCESS	read-only
        STATUS	mandatory
        DESCRIPTION
                "The IPv6 address of this Adjacent Node"
        ::= { wfIpv6AdjacentNodeEntry 3 }

    wfIpv6AdjNodePhysicalAddr OBJECT-TYPE
        SYNTAX	PhysAddress
        ACCESS	read-write
        STATUS	mandatory
        DESCRIPTION
                "The Physical Address for this Adjacent Node.
                 For FR PVC it is a 32 bit DLCI.
                 For ATM PVC it is a 32 bit VCID which has
                 circuit VCI in its most significant 20 bits
                 and VPI in 12 least significant bits."
        ::= { wfIpv6AdjacentNodeEntry 5 }

    wfIpv6AdjNodeEncaps OBJECT-TYPE
        SYNTAX	INTEGER {
    		    other(1),  -- none of the following
    		    snap(2),   -- IEEE 802.2
                    pdn (3),   -- X.25 PDN
                    wan (4)    -- FR SVC, ATM SVC
    		}
        ACCESS	read-write
        STATUS	mandatory
        DESCRIPTION
                "The link layer encapsulation type of this entry.
                 'Snap(2)' is to be specified only if IEEE 802.2
                 encapsulation is to be used over CSMACD or DS1
                 links.
                 For 'pdn(4)', X.121 address is stored in
                 wfIpv6AdjNodeWanAddr.
                 For 'wan(3)', X.121 or E.164 FR address is stored
                 in wfIpv6AdjNodeWanAddr."
        DEFVAL	{ other }
        ::= { wfIpv6AdjacentNodeEntry 6 }

    wfIpv6AdjNodePreference OBJECT-TYPE
        SYNTAX	INTEGER(0..15)
        ACCESS	read-write
        STATUS	mandatory
        DESCRIPTION
                "The Routing Preference in 0 to 15 range.
                 A value of 15 is 'most preferred'. Default 15."
        DEFVAL	{ 15 }
        ::= { wfIpv6AdjacentNodeEntry 7 }

    wfIpv6AdjNodeCost OBJECT-TYPE
        SYNTAX	INTEGER(1..15)
        ACCESS	read-write
        STATUS	mandatory
        DESCRIPTION
                "The Cost of this Adjacent Node. (Used as the RIP metric)"
        DEFVAL	{ 1 }
        ::= { wfIpv6AdjacentNodeEntry 8 }

    wfIpv6AdjNodeInvalid OBJECT-TYPE
        SYNTAX	INTEGER {
    		    valid(1),
    		    invalid(2)
    		}
        ACCESS	read-only
        STATUS	mandatory
        DESCRIPTION
                "Whether the record passed validation or not"
        DEFVAL	{ valid }
        ::= { wfIpv6AdjacentNodeEntry 9 }

    wfIpv6AdjNodeWanAddr OBJECT-TYPE
        SYNTAX	DisplayString
        ACCESS	read-write
        STATUS	mandatory
        DESCRIPTION
                "WAN address (X.121, E.164, etc.) used to establish
                 an SVC to the adjacent host. For X.25 PVC it contains
                 LCN of the PVC encoded as a X.121 address uo to 4 octets
                 in length."
        ::= { wfIpv6AdjacentNodeEntry 10 }


--  IPv6 Routing table 
    -- The IPv6 routing table contains an entry for each IPv6 route
    -- presently known to this entity.


    wfIpv6RouteTable OBJECT-TYPE
        SYNTAX	SEQUENCE OF WfIpv6RouteEntry
        ACCESS	not-accessible
        STATUS	mandatory
        DESCRIPTION
                "IPv6 Routing table"
        ::= { wfIpv6RoutingGeneralGroup 8 }

    wfIpv6RouteEntry OBJECT-TYPE
        SYNTAX	WfIpv6RouteEntry
        ACCESS	not-accessible
        STATUS	mandatory
        DESCRIPTION
                "A routing entry"
        INDEX	{ wfIpv6RouteDest,
    		  wfIpv6RoutePfxLength,
    		  wfIpv6RouteIfIndex,
    		  wfIpv6RouteIndex }
        ::= { wfIpv6RouteTable 1 }

    WfIpv6RouteEntry ::= SEQUENCE {
    	    wfIpv6RouteDest
    		Ipv6Address,
    	    wfIpv6RoutePfxLength
    		INTEGER,
    	    wfIpv6RouteIfIndex
    		INTEGER,
    	    wfIpv6RouteIndex
    		INTEGER,
    	    wfIpv6RouteNextHop
    		Ipv6Address,
    	    wfIpv6RouteType
    		INTEGER,
    	    wfIpv6RouteProtocol
    		INTEGER,
    	    wfIpv6RoutePolicy
    		INTEGER,
    	    wfIpv6RouteAge
    		Gauge,
    	    wfIpv6RouteNextHopRDI
    		OCTET STRING,
    	    wfIpv6RouteMetric
    		Gauge,
    	    wfIpv6RouteWeight
    		Gauge,
    	    wfIpv6RouteInfo
    		OBJECT IDENTIFIER
        }

    wfIpv6RouteDest OBJECT-TYPE
        SYNTAX	Ipv6Address
        ACCESS	read-only
        STATUS	mandatory
        DESCRIPTION
                "The destination IPv6 address of this route.
                 An entry  with  a value of ::0 is considered
		 a default route.

                 This object may not take a Multicast address value."
        ::= { wfIpv6RouteEntry 1 }

    wfIpv6RoutePfxLength OBJECT-TYPE
        SYNTAX	INTEGER
        ACCESS	read-only
        STATUS	mandatory
        DESCRIPTION
                "Indicates the prefix length of the destination
                address."
        ::= { wfIpv6RouteEntry 2 }

    wfIpv6RouteIfIndex OBJECT-TYPE
        SYNTAX	INTEGER
        ACCESS	read-only
        STATUS	mandatory
        DESCRIPTION
                "The index value which uniquely identifies the local
		 interface through which the next hop of this
                 route should be reached.  The interface identified 
		 by a particular value of this index is the same interface
		 as identified by the same value of wfIpv6IfIndex."
        ::= { wfIpv6RouteEntry 3 }

    wfIpv6RouteIndex OBJECT-TYPE
        SYNTAX	INTEGER
        ACCESS	read-only
        STATUS	mandatory
        DESCRIPTION
                "The value which uniquely identifies the route
                among the routes to the same network layer destination"
        ::= { wfIpv6RouteEntry 4 }

    wfIpv6RouteNextHop OBJECT-TYPE
        SYNTAX	Ipv6Address
        ACCESS	read-only
        STATUS	mandatory
        DESCRIPTION
                "On remote routes, the address of the next system
                en route;  Otherwise, ::0"
        ::= { wfIpv6RouteEntry 5 }

    wfIpv6RouteType OBJECT-TYPE
        SYNTAX	INTEGER {
    		    other(1),       -- none of the following

    		    invalid(2),     -- an invalidated route

                                    -- route to directly
                    direct(3),      -- connected (sub-)network

                                    -- route to a non-local
                    indirect(4),    -- destination

                                    -- an route indicating that
                                    -- packets to destinations
                                    -- matching this route are
                    discard(5)      -- to be discarded
    		}
        ACCESS	read-only
        STATUS	mandatory
        DESCRIPTION
           "The type of route. Note that 'direct(3)' refers
           to  a route for which the next hop is the final
           destination; 'indirect(4)' refers to a route for
           which  the  next  hop is not the final
           destination; 'discard(5)' refers to a route
           indicating that packets to destinations matching
           this route are to be discarded (sometimes called
           black-hole route)."
        ::= { wfIpv6RouteEntry 6 }

    wfIpv6RouteProtocol OBJECT-TYPE
        SYNTAX	INTEGER {
    		    other(1),       -- none of the following

                                    -- non-protocol information,
                                    -- e.g., manually configured
                    local(2),       -- entries

                                    -- set via a network
                    netmgmt(3),     -- management protocol

                                    -- obtained via ND,
                    ndisc(4),       -- e.g., Redirect

                                    -- the remaining values are
                                    -- all routing protocols
    		    rip(5),
    		    ospf(6),
    		    idrp(7)
    		}
        ACCESS	read-only
        STATUS	mandatory
        DESCRIPTION
                "The routing mechanism via which this route was
                 learned."
        ::= { wfIpv6RouteEntry 7 }

    wfIpv6RoutePolicy OBJECT-TYPE
        SYNTAX	INTEGER
        ACCESS	read-only
        STATUS	mandatory
        DESCRIPTION
                "The general set of conditions that would cause the
                 selection of one multipath route (set of next hops for
                 a given destination) is referred to as 'policy'.
                 Unless the mechanism indicated by wfIpv6RouteProtocol
                 specified otherwise, the policy specifier is the Priority
		 field of the IPv6 packet header.  The encoding of IPv6
		 Priority is specified by the following convention:

                    0 - uncharacterized traffic
                    1 - 'filler' traffic (e.g., netnews)
                    2 - unattended data transfer (e.g., email)
                    3 - reserved
                    4 - attended bulk transfer (e.g., FTP, NFS)
                    5 - reserved
                    6 - interactive traffic (e.g., telnet, X)
                    7 - internet control traffic (e.g., routing protocols, SNMP)

                 Protocols defining 'policy' otherwise must either
                 define a set of values which are valid for
                 this  object  or  must  implement  an  integer-
                 instanced  policy table for which this object's
                 value acts as an index."
        ::= { wfIpv6RouteEntry 8 }

    wfIpv6RouteAge OBJECT-TYPE
        SYNTAX	Gauge
        ACCESS	read-only
        STATUS	mandatory
        DESCRIPTION
                "The number of seconds since this route was last
                 updated or otherwise determined to be correct.
                 Note that no semantics of `too old' can be implied
                 except through knowledge of the routing protocol
                 by which the route was learned."
        ::= { wfIpv6RouteEntry 9 }

    wfIpv6RouteNextHopRDI OBJECT-TYPE
        SYNTAX	OCTET STRING (SIZE (0 | 16))
        ACCESS	read-only
        STATUS	mandatory
        DESCRIPTION
           "The Routing Domain ID of the Next Hop.
           When  this  is  unknown  or not relevant to the
           protocol indicated by ipv6RouteProtocol, it is
           an octet string of zero size."
        ::= { wfIpv6RouteEntry 10 }

    wfIpv6RouteMetric OBJECT-TYPE
        SYNTAX	Gauge
        ACCESS	read-only
        STATUS	mandatory
        DESCRIPTION
           "The routing metric for this route. The
           semantics of this metric are determined by the
           routing protocol specified in the route's
           ipv6RouteProtocol value.  When this is unknown
           or not relevant to the protocol indicated by
           ipv6RouteProtocol, the object value should be
           set to its maximum value (4,294,967,295)."
        ::= { wfIpv6RouteEntry 11 }

    wfIpv6RouteWeight OBJECT-TYPE
        SYNTAX	Gauge
        ACCESS	read-only
        STATUS	mandatory
        DESCRIPTION
                "The system internal weight value for this route. The
                 semantics of this value are determined by
		 the implementation specific rules. Generally, within
		 routes with the same wfIpv6RoutePolicy value, the lower
		 the weight value the more preferred is the route."
        ::= { wfIpv6RouteEntry 12 }

    wfIpv6RouteInfo OBJECT-TYPE
        SYNTAX	OBJECT IDENTIFIER
        ACCESS	read-only
        STATUS	mandatory
        DESCRIPTION
                "A reference to MIB definitions specific to the
                 particular routing protocol which is responsible
                 for this route, as determined by the  value
                 specified  in the route's wfIpv6RouteProto value.
                 If this information is not present,  its  value
                 should be set to the OBJECT ID { 0 0 },
                 which is a syntactically valid object  identifier,
                 and any implementation conforming to ASN.1
                 and the Basic Encoding Rules must  be  able  to
                 generate and recognize this value."
        ::= { wfIpv6RouteEntry 13 }


-- IPv6 Net-To-Media translation table

    wfIpv6NetToMediaEntryTable OBJECT-TYPE
        SYNTAX	SEQUENCE OF WfIpv6NetToMediaEntry
        ACCESS	not-accessible
        STATUS	mandatory
        DESCRIPTION
                "The IPv6 address translation table contain the IPv6 Address
                 to `physical' address equivalences.  Some interfaces do not
                 use translation tables for determining address
                 equivalences; if all interfaces are of this type, then
                 the Address Translation table is empty, i.e., has zero 
		 entries."
        ::= { wfIpv6RoutingGeneralGroup 9 }

    wfIpv6NetToMediaEntry OBJECT-TYPE
        SYNTAX	WfIpv6NetToMediaEntry
        ACCESS	not-accessible
        STATUS	mandatory
        DESCRIPTION
                "A description of a resolved node"
        INDEX	{ wfIpv6NetToMediaIfIndex,
    		  wfIpv6NetToMediaNetAddress }
        ::= { wfIpv6NetToMediaEntryTable 1 }

    WfIpv6NetToMediaEntry ::= SEQUENCE {
    	    wfIpv6NetToMediaIfIndex
    		INTEGER,
    	    wfIpv6NetToMediaNetAddress
    		Ipv6Address,
    	    wfIpv6NetToMediaPhysAddress
    		PhysAddress,
    	    wfIpv6NetToMediaType
    		INTEGER,
    	    wfIpv6NetToMediaInvalid
    		INTEGER
        }

    wfIpv6NetToMediaIfIndex OBJECT-TYPE
        SYNTAX	INTEGER
        ACCESS	read-only
        STATUS	mandatory
        DESCRIPTION
                "The interface on which this entry's equivalence
                 is effective.  The interface identified by a
                 particular value of this index is the same
                 interface as identified by the same value of
                 wfIpv6IfIndex."
        ::= { wfIpv6NetToMediaEntry 1 }

    wfIpv6NetToMediaNetAddress OBJECT-TYPE
        SYNTAX	Ipv6Address
        ACCESS	read-only
        STATUS	mandatory
        DESCRIPTION
                "The IPv6 Address corresponding to the media-dependent
                `physical' address."
        ::= { wfIpv6NetToMediaEntry 2 }

    wfIpv6NetToMediaPhysAddress OBJECT-TYPE
        SYNTAX	PhysAddress
        ACCESS	read-only
        STATUS	mandatory
        DESCRIPTION
                "The media-dependent `physical' address."
        ::= { wfIpv6NetToMediaEntry 3 }

    wfIpv6NetToMediaType OBJECT-TYPE
        SYNTAX	INTEGER {
                    other(1),        -- none of the following
                    dynamic(2),
                    static(3)
    		}
        ACCESS	read-only
        STATUS	mandatory
        DESCRIPTION
                "The type of mapping."
        ::= { wfIpv6NetToMediaEntry 4 }

    wfIpv6NetToMediaInvalid OBJECT-TYPE
        SYNTAX	INTEGER {
    		    valid(1),
    		    invalid(2)
    		}
        ACCESS	read-write
        STATUS	mandatory
        DESCRIPTION
                "Setting this object to the value invalid(2) has
                 the effect of invalidating the corresponding entry
                 in the wfIpv6NetToMediaTable.  That is, it effectively
                 disassociates the interface identified with said
                 entry from the mapping identified with said entry.
                 It is an implementation-specific matter as to
                 whether the agent removes an invalidated entry
                 from the table.  Accordingly, management stations
                 must be prepared to receive tabular information
                 from agents that corresponds to entries not
                 currently in use.  Proper interpretation of such
                 entries requires examination of the relevant
                 wfIpv6NetToMediaInvalid object."
        DEFVAL	{ valid }
        ::= { wfIpv6NetToMediaEntry 5 }


-- IPv6 Debug Information table

    wfIpv6DbgInfoTable OBJECT-TYPE
        SYNTAX	SEQUENCE OF WfIpv6DbgInfoEntry
        ACCESS	not-accessible
        STATUS	mandatory
        DESCRIPTION
                "The debug info table"
        ::= { wfIpv6RoutingGeneralGroup 10 }

    wfIpv6DbgInfoEntry OBJECT-TYPE
        SYNTAX	WfIpv6DbgInfoEntry
        ACCESS	not-accessible
        STATUS	mandatory
        DESCRIPTION
                "A description of a IPV6_NDISC interface"
        INDEX	{ wfIpv6DbgInfoSlot }
        ::= { wfIpv6DbgInfoTable 1 }

    WfIpv6DbgInfoEntry ::= SEQUENCE {
    	    wfIpv6DbgInfoSlot
    		INTEGER,
    	    wfIpv6DbgInfoState
    		INTEGER,
    	    wfIpv6DbgInfoNetworks
    		INTEGER,
    	    wfIpv6DbgInfoNodes
    		INTEGER,
    	    wfIpv6DbgInfoActiveInterfaces
    		INTEGER,
    	    wfIpv6DbgInfoRtmAddr
    		Gauge
        }

    wfIpv6DbgInfoSlot OBJECT-TYPE
        SYNTAX	INTEGER
        ACCESS	read-only
        STATUS	mandatory
        DESCRIPTION
                "Slot number of this information."
        ::= { wfIpv6DbgInfoEntry 1 }

    wfIpv6DbgInfoState OBJECT-TYPE
        SYNTAX	INTEGER {
    		    up(1),
    		    down(2),
    		    init(3),
    		    invalid(4),
    		    notpres(5)
    		}
        ACCESS	read-only
        STATUS	mandatory
        DESCRIPTION
                "The current state of IPv6 on this slot."
        DEFVAL	{ notpres }
        ::= { wfIpv6DbgInfoEntry 2 }

    wfIpv6DbgInfoNetworks OBJECT-TYPE
        SYNTAX	INTEGER
        ACCESS	read-only
        STATUS	mandatory
        DESCRIPTION
                "The number of network layer reachability entries
                in the routing table on this slot"
        ::= { wfIpv6DbgInfoEntry 3 }

    wfIpv6DbgInfoNodes OBJECT-TYPE
        SYNTAX	INTEGER
        ACCESS	read-only
        STATUS	mandatory
        DESCRIPTION
                "This parameter indicates the number of nodes known
                by IPv6 on this slot."
        ::= { wfIpv6DbgInfoEntry 4 }

    wfIpv6DbgInfoActiveInterfaces OBJECT-TYPE
        SYNTAX	INTEGER
        ACCESS	read-only
        STATUS	mandatory
        DESCRIPTION
                "The number of active IPv6 interface on this slot."
        ::= { wfIpv6DbgInfoEntry 5 }

    wfIpv6DbgInfoRtmAddr OBJECT-TYPE
        SYNTAX	Gauge
        ACCESS	read-only
        STATUS	mandatory
        DESCRIPTION
                "Memory address of IPv6 RTM Environment on this slot."
        ::= { wfIpv6DbgInfoEntry 6 }

-- Traffic filters

    wfIpv6FilterTable OBJECT-TYPE
        SYNTAX	SEQUENCE OF WfIpv6FilterEntry
        ACCESS	not-accessible
        STATUS	mandatory
        DESCRIPTION
                "IPv6 Traffic Filters"
        ::= { wfIpv6RoutingGeneralGroup 11 }

    wfIpv6FilterEntry OBJECT-TYPE
        SYNTAX	WfIpv6FilterEntry
        ACCESS	not-accessible
        STATUS	mandatory
        DESCRIPTION
                "A filtering rule"
        INDEX	{ wfIpv6FilterNumber }
        ::= { wfIpv6FilterTable 1 }

    WfIpv6FilterEntry ::= SEQUENCE {
    	    wfIpv6FilterDelete
    		INTEGER,
    	    wfIpv6FilterDisable
    		INTEGER,
    	    wfIpv6FilterNumber
    		INTEGER,
    	    wfIpv6FilterName
    		DisplayString,
    	    wfIpv6FilterPrecedence
    		Gauge,
    	    wfIpv6FilterPackets
    		Counter,
    	    wfIpv6FilterOctets
    		Counter,
    	    wfIpv6FilterInIfIndex
    		INTEGER,
    	    wfIpv6FilterOutIfIndex
    		INTEGER,
    	    wfIpv6FilterSrcAddresses
    		OCTET STRING,
    	    wfIpv6FilterDstAddresses
    		OCTET STRING,
    	    wfIpv6FilterProtocols
    		OCTET STRING,
    	    wfIpv6FilterAction
    		INTEGER,
    	    wfIpv6FilterLog
    		INTEGER
        }

    wfIpv6FilterDelete OBJECT-TYPE
        SYNTAX	INTEGER {
    		    create(1),
    		    delete(2)
    		}
        ACCESS	read-write
        STATUS	mandatory
        DESCRIPTION
                "Create/Delete parameter. Default is created.
                Users perform a set operation on this object
                in order to create/delete an IPv6 filtering rule."
        DEFVAL	{ create }
        ::= { wfIpv6FilterEntry 1 }

    wfIpv6FilterDisable OBJECT-TYPE
        SYNTAX	INTEGER {
    		    enabled(1),
    		    disabled(2)
    		}
        ACCESS	read-write
        STATUS	mandatory
        DESCRIPTION
                "Enable/Disable parameter. Default is enabled.
                Users perform a set operation on this object
                in order to enable/disable an IPv6 filtering
                rule."
        DEFVAL	{ enabled }
        ::= { wfIpv6FilterEntry 2 }

    wfIpv6FilterNumber OBJECT-TYPE
        SYNTAX	INTEGER
        ACCESS	read-only
        STATUS	mandatory
        DESCRIPTION
                "Filter rule number"
        ::= { wfIpv6FilterEntry 3 }

    wfIpv6FilterName OBJECT-TYPE
        SYNTAX	DisplayString
        ACCESS	read-write
        STATUS	mandatory
        DESCRIPTION
                "Rule name - user specified name for this filter"
        ::= { wfIpv6FilterEntry 4 }

    wfIpv6FilterPrecedence OBJECT-TYPE
        SYNTAX	Gauge
        ACCESS	read-write
        STATUS	mandatory
        DESCRIPTION
                "Precedence. This is a metric to be used to compare
                this policy rule to other rules that a given packet may
                match.  A rule with a higher precedence value will be
                chosen over one with a smaller value.  In the case of
                a tie, the rule index is used (lower wins).

                Note: if there is multiple filters that a given packet
                      may match, it is advisable for a filter with a higher
                      precedence value to be defined with a lower rule
                      index than a filter with a lower precedence value
                      to improve forwarding performance."
        DEFVAL	{ 1 }
        ::= { wfIpv6FilterEntry 5 }

    wfIpv6FilterPackets OBJECT-TYPE
        SYNTAX	Counter
        ACCESS	read-only
        STATUS	mandatory
        DESCRIPTION
                "The number of packets received that have matched this
                 rule."
        ::= { wfIpv6FilterEntry 6 }

    wfIpv6FilterOctets OBJECT-TYPE
        SYNTAX	Counter
        ACCESS	read-only
        STATUS	mandatory
        DESCRIPTION
                "The total number of octets in packets received
                 that have matched this rule."
        ::= { wfIpv6FilterEntry 7 }

    wfIpv6FilterInIfIndex OBJECT-TYPE
        SYNTAX	INTEGER
        ACCESS	read-write
        STATUS	mandatory
        DESCRIPTION
                "Interface index which uniquely identifies the incoming
                 IPv6 interface to which this entry is applicable.
                 An interface identified by a particular value in this
                 object is the same interface as identified by the
                 same value of wfIpv6IfIndex. The index value of 0
		 means 'match any interface'."
        DEFVAL	{ 0 }
        ::= { wfIpv6FilterEntry 8 }

    wfIpv6FilterOutIfIndex OBJECT-TYPE
        SYNTAX	INTEGER
        ACCESS	read-write
        STATUS	mandatory
        DESCRIPTION
                "Interface index which uniquely identifies the outgoing
                 IPv6 interface to which this entry is applicable.

                 An interface identified by a particular value in this
                 object is the same interface as identified by the
                 same value of wfIpv6IfIndex.

                 The index value of 0 means 'match any interface',
                 i.e. all packets that are to be forwarded will
                 match this filter parameter.  Note that packet which
                 are addressed to the router itself will not match
                 a filter that has zero as its wfIpv6FilterOutIfIndex
                 value.

                 The index value of -1 means that only packets which
                 are addressed to the router itself match this filter
                 parameter.

                 The index value of -2 means that all packets, forwarded 
                 or addressed to the router itself, match this filter
                 parameter."
        DEFVAL	{ 0 }
        ::= { wfIpv6FilterEntry 9 }

    wfIpv6FilterSrcAddresses OBJECT-TYPE
        SYNTAX	OCTET STRING
        ACCESS	read-write
        STATUS	mandatory
        DESCRIPTION
                "Source Address identification list. This identifies which
                packet source addresses will match this rule.  If non-null,
                the octet string contains one or more 2-tuples of this form:

                   16 octets: address prefix
                   1 octet: prefix length in bits

                An encoding ::0/0 means 'match any address'.

                A null string also means 'match any address'."
        ::= { wfIpv6FilterEntry 10 }

    wfIpv6FilterDstAddresses OBJECT-TYPE
        SYNTAX	OCTET STRING
        ACCESS	read-write
        STATUS	mandatory
        DESCRIPTION
                "Destination Address identification list. This identifies
                which packet destination addresses will match this rule.  If 
                non-null, the octet string contains one or more 2-tuples of
                this form:

                   16 octets: address prefix
                   1 octet: prefix length

                An encoding ::0/0 means 'match any address'.

                A null string also means 'match any address'."
        ::= { wfIpv6FilterEntry 11 }

    wfIpv6FilterProtocols OBJECT-TYPE
        SYNTAX	OCTET STRING
        ACCESS	read-write
        STATUS	mandatory
        DESCRIPTION
                "List of upper layer protocol types (e.g., UDP is 16,
                 TCP is 6, ICMP is 58) of the packet payload.
                 If non-null, the octet string contains one or more
                 3-tuples of this form:

                    1 octet:  protocol type (zero means 'any protocol')
                    2 octets: value of the first 16 bits of
                              upper-layer payload (zero means 'any value')*
                    2 octets: value of the next 16 bits of
                              upper-layer payload (zero means 'any value')*

                 For UDP and TCP protocol the first 16 bits of payload
                 correspond to the source port number and the next 16
                 bits of payload correspond to the destination port number.

                 *If the protocol type is ICMP(58), the first 2-octets
                  value identifies the ICMP Type and second 2-octets value
                  should be set to 0.

                 A null string also means 'match any protocol'."
       ::= { wfIpv6FilterEntry 12 }

    wfIpv6FilterAction OBJECT-TYPE
        SYNTAX	INTEGER {
    		    forward(1),
    		    discard(2)
    		}
        ACCESS	read-write
        STATUS	mandatory
        DESCRIPTION
                "action. If 'forward(1), packet is to be forwarded;
                 if 'discard(2)', packet is to be discarded"
        DEFVAL	{ discard }
        ::= { wfIpv6FilterEntry 13 }

    wfIpv6FilterLog OBJECT-TYPE
        SYNTAX	INTEGER {
    		    true(1),
    		    false(2)
    		}
        ACCESS	read-write
        STATUS	mandatory
        DESCRIPTION
                "Log Action. If 'true(1), a log event is generated
                 when a packet matches this filter rule; if 'false(2)',
                 no logging is done."
        DEFVAL	{ false }
        ::= { wfIpv6FilterEntry 14 }


-- IPv6 ICMP statistics table

    wfIpv6IcmpTable OBJECT-TYPE
        SYNTAX	SEQUENCE OF WfIpv6IcmpEntry
        ACCESS	not-accessible
        STATUS	mandatory
        DESCRIPTION
                "IPv6 ICMP statistics"
        ::= { wfIpv6IcmpGroup 1 }

    wfIpv6IcmpEntry OBJECT-TYPE
        SYNTAX	WfIpv6IcmpEntry
        ACCESS	not-accessible
        STATUS	mandatory
        DESCRIPTION
            "An ICMPv6 statistics entry containing
            objects at a particular IPv6 interface.

            Note that a receiving interface is
            the interface to which a given ICMPv6 message
            is addressed which may not be necessarily
            the input interface for the message.

            Similarly,  the sending interface is
            the interface that sources a given
            ICMP message which is usually but not
            necessarily the output interface for the message."
        INDEX	{ wfIpv6IcmpIfIndex }
        ::= { wfIpv6IcmpTable 1 }

    WfIpv6IcmpEntry ::= SEQUENCE {
    	    wfIpv6IcmpIfIndex
    		INTEGER,
    	    wfIpv6IcmpInMsgs
    		Counter,
    	    wfIpv6IcmpInErrors
    		Counter,
    	    wfIpv6IcmpInDestUnreachs
    		Counter,
    	    wfIpv6IcmpInAdminProhibs
    		Counter,
    	    wfIpv6IcmpInTimeExcds
    		Counter,
    	    wfIpv6IcmpInParmProbs
    		Counter,
    	    wfIpv6IcmpInPktTooBigs
    		Counter,
    	    wfIpv6IcmpInEchos
    		Counter,
    	    wfIpv6IcmpInEchoReps
    		Counter,
    	    wfIpv6IcmpInRouterSolicits
    		Counter,
    	    wfIpv6IcmpInRouterAdvertisements
    		Counter,
    	    wfIpv6IcmpInNeighborSolicits
    		Counter,
    	    wfIpv6IcmpInNeighborAdvertisements
    		Counter,
    	    wfIpv6IcmpInRedirects
    		Counter,
    	    wfIpv6IcmpInGroupMembQueries
    		Counter,
    	    wfIpv6IcmpInGroupMembResponses
    		Counter,
    	    wfIpv6IcmpInGroupMembReductions
    		Counter,
    	    wfIpv6IcmpOutMsgs
    		Counter,
    	    wfIpv6IcmpOutErrors
    		Counter,
    	    wfIpv6IcmpOutDestUnreachs
    		Counter,
    	    wfIpv6IcmpOutAdminProhibs
    		Counter,
    	    wfIpv6IcmpOutTimeExcds
    		Counter,
    	    wfIpv6IcmpOutParmProbs
    		Counter,
    	    wfIpv6IcmpOutPktTooBigs
    		Counter,
    	    wfIpv6IcmpOutEchos
    		Counter,
    	    wfIpv6IcmpOutEchoReps
    		Counter,
    	    wfIpv6IcmpOutRouterSolicits
    		Counter,
    	    wfIpv6IcmpOutRouterAdvertisements
    		Counter,
    	    wfIpv6IcmpOutNeighborSolicits
    		Counter,
    	    wfIpv6IcmpOutNeighborAdvertisements
    		Counter,
    	    wfIpv6IcmpOutRedirects
    		Counter,
    	    wfIpv6IcmpOutGroupMembQueries
    		Counter,
    	    wfIpv6IcmpOutGroupMembResponses
    		Counter,
    	    wfIpv6IcmpOutGroupMembReductions
    		Counter
        }

    wfIpv6IcmpIfIndex OBJECT-TYPE
        SYNTAX	INTEGER
        ACCESS	read-only
        STATUS	mandatory
        DESCRIPTION
                "The index value which uniquely identifies the local
		 interface to which this entry's information pertains.
		 The interface identified by a particular value of this
		 index is the same interface as identified by the same
		 value of wfIpv6IfIndex."
        ::= { wfIpv6IcmpEntry 1 }

    wfIpv6IcmpInMsgs OBJECT-TYPE
        SYNTAX	Counter
        ACCESS	read-only
        STATUS	mandatory
        DESCRIPTION
                "The total number of ICMP messages which includes
                all those counted by wfIpv6IcmpInErrors."
        ::= { wfIpv6IcmpEntry 2 }

    wfIpv6IcmpInErrors OBJECT-TYPE
        SYNTAX	Counter
        ACCESS	read-only
        STATUS	mandatory
        DESCRIPTION
                "The number of ICMP messages which the entity
                received but determined as having ICMP-specific
                errors (bad ICMP checksums, bad length, etc.)."
        ::= { wfIpv6IcmpEntry 3 }

    wfIpv6IcmpInDestUnreachs OBJECT-TYPE
        SYNTAX	Counter
        ACCESS	read-only
        STATUS	mandatory
        DESCRIPTION
                "The number of ICMP Destination Unreachable messages received."
        ::= { wfIpv6IcmpEntry 4 }

    wfIpv6IcmpInAdminProhibs OBJECT-TYPE
        SYNTAX	Counter
        ACCESS	read-only
        STATUS	mandatory
        DESCRIPTION
                "Number of ICMP dest unreachable/communication
                administratively prohibited messages received.
                Note: may be sent by BFE or another system"
        ::= { wfIpv6IcmpEntry 5 }

    wfIpv6IcmpInTimeExcds OBJECT-TYPE
        SYNTAX	Counter
        ACCESS	read-only
        STATUS	mandatory
        DESCRIPTION
                "The number of ICMP Time Exceeded messages received."
        ::= { wfIpv6IcmpEntry 6 }

    wfIpv6IcmpInParmProbs OBJECT-TYPE
        SYNTAX	Counter
        ACCESS	read-only
        STATUS	mandatory
        DESCRIPTION
                "The number of ICMP Parameter Problem messages received."
        ::= { wfIpv6IcmpEntry 7 }

    wfIpv6IcmpInPktTooBigs OBJECT-TYPE
        SYNTAX	Counter
        ACCESS	read-only
        STATUS	mandatory
        DESCRIPTION
                "The number of ICMP Packet Too Big messages received."
        ::= { wfIpv6IcmpEntry 8 }

    wfIpv6IcmpInEchos OBJECT-TYPE
        SYNTAX	Counter
        ACCESS	read-only
        STATUS	mandatory
        DESCRIPTION
                "The number of ICMP Echo (request) messages received."
        ::= { wfIpv6IcmpEntry 9 }

    wfIpv6IcmpInEchoReps OBJECT-TYPE
        SYNTAX	Counter
        ACCESS	read-only
        STATUS	mandatory
        DESCRIPTION
                "The number of ICMP Echo Reply messages received."
        ::= { wfIpv6IcmpEntry 10 }

    wfIpv6IcmpInRouterSolicits OBJECT-TYPE
        SYNTAX	Counter
        ACCESS	read-only
        STATUS	mandatory
        DESCRIPTION
                "The number of ICMP Router Solicit messages received."
        ::= { wfIpv6IcmpEntry 11 }

    wfIpv6IcmpInRouterAdvertisements OBJECT-TYPE
        SYNTAX	Counter
        ACCESS	read-only
        STATUS	mandatory
        DESCRIPTION
                "The number of ICMP Router Advertisement messages received."
        ::= { wfIpv6IcmpEntry 12 }

    wfIpv6IcmpInNeighborSolicits OBJECT-TYPE
        SYNTAX	Counter
        ACCESS	read-only
        STATUS	mandatory
        DESCRIPTION
                "The number of ICMP Neighbor Solicit messages received."
        ::= { wfIpv6IcmpEntry 13 }

    wfIpv6IcmpInNeighborAdvertisements OBJECT-TYPE
        SYNTAX	Counter
        ACCESS	read-only
        STATUS	mandatory
        DESCRIPTION
                "The number of ICMP Neighbor Advertisement messages received."
        ::= { wfIpv6IcmpEntry 14 }

    wfIpv6IcmpInRedirects OBJECT-TYPE
        SYNTAX	Counter
        ACCESS	read-only
        STATUS	mandatory
        DESCRIPTION
                "The number of Redirect messages received."
        ::= { wfIpv6IcmpEntry 15 }

    wfIpv6IcmpInGroupMembQueries OBJECT-TYPE
        SYNTAX  Counter      
        ACCESS	read-only
        STATUS	mandatory
        DESCRIPTION
         "The number of ICMPv6 Group Membership Query
         messages received by the interface."
        ::= { wfIpv6IcmpEntry 16}

    wfIpv6IcmpInGroupMembResponses OBJECT-TYPE
        SYNTAX Counter
        ACCESS	read-only
        STATUS	mandatory
        DESCRIPTION
         "The number of ICMPv6 Group Membership Response messages
         received by the interface."
        ::= { wfIpv6IcmpEntry 17}

     wfIpv6IcmpInGroupMembReductions OBJECT-TYPE
        SYNTAX	Counter
        ACCESS	read-only
        STATUS	mandatory
        DESCRIPTION
         "The number of ICMPv6 Group Membership Reduction messages
         received by the interface."
        ::= { wfIpv6IcmpEntry 18}

    wfIpv6IcmpOutMsgs OBJECT-TYPE
        SYNTAX	Counter
        ACCESS	read-only
        STATUS	mandatory
        DESCRIPTION
                "The total number of ICMP messages which this
                entity attempted to send.  Note that this counter
                includes all those counted by icmpOutErrors."
        ::= { wfIpv6IcmpEntry 19 }

    wfIpv6IcmpOutErrors OBJECT-TYPE
        SYNTAX	Counter
        ACCESS	read-only
        STATUS	mandatory
        DESCRIPTION
                "The number of ICMP messages which this entity did
                not send due to problems discovered within ICMP
                such as a lack of buffers.  This value should not
                include errors discovered outside the ICMP layer
                such as the inability of IPv6 to route the resultant
                datagram.  In some implementations there may be no
                types of error which contribute to this counter's
                value."
        ::= { wfIpv6IcmpEntry 20 }

    wfIpv6IcmpOutDestUnreachs OBJECT-TYPE
        SYNTAX	Counter
        ACCESS	read-only
        STATUS	mandatory
        DESCRIPTION
                "The number of ICMP Destination Unreachable messages sent."
        ::= { wfIpv6IcmpEntry 21 }

    wfIpv6IcmpOutAdminProhibs OBJECT-TYPE
        SYNTAX	Counter
        ACCESS	read-only
        STATUS	mandatory
        DESCRIPTION
                "Number of ICMP dest unreachable/communication
                administratively prohibited messages sent."
        ::= { wfIpv6IcmpEntry 22 }

    wfIpv6IcmpOutTimeExcds OBJECT-TYPE
        SYNTAX	Counter
        ACCESS	read-only
        STATUS	mandatory
        DESCRIPTION
                "The number of ICMP Time Exceeded messages sent."
        ::= { wfIpv6IcmpEntry 23 }

    wfIpv6IcmpOutParmProbs OBJECT-TYPE
        SYNTAX	Counter
        ACCESS	read-only
        STATUS	mandatory
        DESCRIPTION
                "The number of ICMP Parameter Problem messages sent."
        ::= { wfIpv6IcmpEntry 24 }

    wfIpv6IcmpOutPktTooBigs OBJECT-TYPE
        SYNTAX	Counter
        ACCESS	read-only
        STATUS	mandatory
        DESCRIPTION
                "The number of ICMP Packet Too Big messages sent."
        ::= { wfIpv6IcmpEntry 25 }

    wfIpv6IcmpOutEchos OBJECT-TYPE
        SYNTAX	Counter
        ACCESS	read-only
        STATUS	mandatory
        DESCRIPTION
                "The number of ICMP Echo (request) messages sent."
        ::= { wfIpv6IcmpEntry 26 }

    wfIpv6IcmpOutEchoReps OBJECT-TYPE
        SYNTAX	Counter
        ACCESS	read-only
        STATUS	mandatory
        DESCRIPTION
                "The number of ICMP Echo Reply messages sent."
        ::= { wfIpv6IcmpEntry 27 }

    wfIpv6IcmpOutRouterSolicits OBJECT-TYPE
        SYNTAX	Counter
        ACCESS	read-only
        STATUS	mandatory
        DESCRIPTION
                "The number of ICMP Router Solicitation messages sent."
        ::= { wfIpv6IcmpEntry 28 }

    wfIpv6IcmpOutRouterAdvertisements OBJECT-TYPE
        SYNTAX	Counter
        ACCESS	read-only
        STATUS	mandatory
        DESCRIPTION
                "The number of ICMP Router Advertisement messages received."
        ::= { wfIpv6IcmpEntry 29 }

    wfIpv6IcmpOutNeighborSolicits OBJECT-TYPE
        SYNTAX	Counter
        ACCESS	read-only
        STATUS	mandatory
        DESCRIPTION
                "The number of ICMP Neighbor Solicitation messages sent."
        ::= { wfIpv6IcmpEntry 30 }

    wfIpv6IcmpOutNeighborAdvertisements OBJECT-TYPE
        SYNTAX	Counter
        ACCESS	read-only
        STATUS	mandatory
        DESCRIPTION
                "The number of ICMP Neighbor Advertisement messages received."
        ::= { wfIpv6IcmpEntry 31 }

    wfIpv6IcmpOutRedirects OBJECT-TYPE
        SYNTAX	Counter
        ACCESS	read-only
        STATUS	mandatory
        DESCRIPTION
                "The number of Redirect messages sent. For a host,
                this object will always be zero, since hosts
                do not send redirects."
        ::= { wfIpv6IcmpEntry 32 }

    wfIpv6IcmpOutGroupMembQueries OBJECT-TYPE
        SYNTAX	Counter
        ACCESS	read-only
        STATUS	mandatory
        DESCRIPTION
         "The number of ICMPv6 Group Membership Query
         messages sent"
        ::= { wfIpv6IcmpEntry 33}

    wfIpv6IcmpOutGroupMembResponses OBJECT-TYPE
        SYNTAX	Counter
        ACCESS	read-only
        STATUS	mandatory
        DESCRIPTION
         "The number of ICMPv6 Group Membership Response
         messages sent"
        ::= { wfIpv6IcmpEntry 34}

    wfIpv6IcmpOutGroupMembReductions OBJECT-TYPE
        SYNTAX	Counter
        ACCESS	read-only
        STATUS	mandatory
        DESCRIPTION
         "The number of ICMPv6 Group Membership Reduction
         messages sent"
        ::= { wfIpv6IcmpEntry 35}

-- IPv6 Neighbor Discovery table

    wfIpv6NdiscIfTable OBJECT-TYPE
        SYNTAX	SEQUENCE OF WfIpv6NdiscIfEntry
        ACCESS	not-accessible
        STATUS	mandatory
        DESCRIPTION
                "The list of configured Neighbor Discovery (ND) interfaces"
        ::= { wfIpv6NDiscGroup 1 }

    wfIpv6NdiscIfEntry OBJECT-TYPE
        SYNTAX	WfIpv6NdiscIfEntry
        ACCESS	not-accessible
        STATUS	mandatory
        DESCRIPTION
                "A description of a IPV6_NDISC interface"
        INDEX	{ wfIpv6NdiscIfIndex }
        ::= { wfIpv6NdiscIfTable 1 }

    WfIpv6NdiscIfEntry ::= SEQUENCE {
    	    wfIpv6NdiscIfDelete
    		INTEGER,
    	    wfIpv6NdiscIfDisable
    		INTEGER,
    	    wfIpv6NdiscIfState
    		INTEGER,
    	    wfIpv6NdiscIfIndex
    		INTEGER,
	    wfIpv6NdiscIfSendAdvertisements
    		INTEGER,
	    wfIpv6NdiscIfManagedFlag
    		INTEGER,
	    wfIpv6NdiscIfOtherCfgFlag
    		INTEGER,
	    wfIpv6NdiscIfReachableTime
    		INTEGER,
	    wfIpv6NdiscIfRetransTimer
    		INTEGER,
	    wfIpv6NdiscIfMaxHopLimit
    		INTEGER,
	    wfIpv6NdiscIfMinRtrAdvInterval
    		INTEGER,
	    wfIpv6NdiscIfMaxRtrAdvInterval
    		INTEGER,
	    wfIpv6NdiscIfDefaultLifetime
    		INTEGER,
	    wfIpv6NdiscIfDupAddrDetectTransmits
    		INTEGER
        }

    wfIpv6NdiscIfDelete OBJECT-TYPE
        SYNTAX	INTEGER {
    		    create(1),
    		    delete(2)
    		}
        ACCESS	read-write
        STATUS	mandatory
        DESCRIPTION
                "Create/Delete parameter. Default is created.
                Users perform a set operation on this
                object in order to create/delete an IPV6_NDISC Interface 
		instance."
        DEFVAL	{ create }
        ::= { wfIpv6NdiscIfEntry 1 }

    wfIpv6NdiscIfDisable OBJECT-TYPE
        SYNTAX	INTEGER {
    		    enabled(1),
    		    disabled(2)
    		}
        ACCESS	read-write
        STATUS	mandatory
        DESCRIPTION
                "Enable/Disable parameter. Default is enabled.
                Users perform a set operation on this
                object in order to enable/disable a IPV6_NDISC interface."
        DEFVAL	{ enabled }
        ::= { wfIpv6NdiscIfEntry 2 }

    wfIpv6NdiscIfState OBJECT-TYPE
        SYNTAX	INTEGER {
    		    up(1),
    		    down(2),
    		    init(3),
    		    invalid(4),
    		    notpres(5)
    		}
        ACCESS	read-only
        STATUS	mandatory
        DESCRIPTION
                "The current state of IPV6_NDISC on this interface."
        DEFVAL	{ notpres }
        ::= { wfIpv6NdiscIfEntry 3 }

    wfIpv6NdiscIfIndex OBJECT-TYPE
        SYNTAX	INTEGER
        ACCESS	read-only
        STATUS	mandatory
        DESCRIPTION
                "The index value which uniquely identifies the local
		 interface to which this entry's information pertains.
		 The interface identified by a particular value of this
		 index is the same interface as identified by the same
		 value of wfIpv6IfIndex."
        ::= { wfIpv6NdiscIfEntry 4 }

    wfIpv6NdiscIfSendAdvertisements OBJECT-TYPE
        SYNTAX	INTEGER {
    		    on(1),
    		    off(2)
    		}
        ACCESS	read-write
        STATUS	mandatory
        DESCRIPTION
                "Indicates whether or not periodic Router
		 Advertisements are to be sent."
        DEFVAL	{ off }
        ::= { wfIpv6NdiscIfEntry 5 }

    wfIpv6NdiscIfManagedFlag OBJECT-TYPE
        SYNTAX	INTEGER {
    		    on(1),
    		    off(2)
    		}
        ACCESS	read-write
        STATUS	mandatory
        DESCRIPTION
                "Managed Address Configuration flag.  When set,
		 hosts use the administered (stateful) protocol
		 for address autoconfiguration in addition to any
		 addresses autoconfigured using stateless address
		 autoconfiguration."
        DEFVAL	{ off }
        ::= { wfIpv6NdiscIfEntry 6 }

    wfIpv6NdiscIfOtherCfgFlag OBJECT-TYPE
        SYNTAX	INTEGER {
    		    on(1),
    		    off(2)
    		}
        ACCESS	read-write
        STATUS	mandatory
        DESCRIPTION
                "Other Stateful Configuration flag.  When set,
		 hosts use the administered (stateful) protocol
		 for autoconfiguration of non-address information."
        DEFVAL	{ off }
        ::= { wfIpv6NdiscIfEntry 7 }

    wfIpv6NdiscIfReachableTime OBJECT-TYPE
        SYNTAX	INTEGER
        ACCESS	read-write
        STATUS	mandatory
        DESCRIPTION
                "The time, in milliseconds, that a node assumes 
		 a neighbor is reachable after having received 
		 a reachability confirmation.  A value of zero
		 means unspecified (by this router)."
        DEFVAL	{ 0 }
        ::= { wfIpv6NdiscIfEntry 8 }

    wfIpv6NdiscIfRetransTimer OBJECT-TYPE
        SYNTAX	INTEGER 
        ACCESS	read-write
        STATUS	mandatory
        DESCRIPTION
                "The time, in milliseconds, between retransmitted
		 Neighbor Solicitation messages. A value of zero
		 means unspecified (by this router)."
        DEFVAL	{ 0 }
        ::= { wfIpv6NdiscIfEntry 9 }

    wfIpv6NdiscIfMaxHopLimit OBJECT-TYPE
        SYNTAX	INTEGER (0..255)
        ACCESS	read-write
        STATUS	mandatory
        DESCRIPTION
                "Maximum hop limit (network diameter) to advertise"
        DEFVAL	{ 64 }
        ::= { wfIpv6NdiscIfEntry 10 }

    wfIpv6NdiscIfMinRtrAdvInterval OBJECT-TYPE
        SYNTAX	INTEGER (3..1350)
        ACCESS	read-write
        STATUS	mandatory
        DESCRIPTION
                "The minimum time allowed between sending
		 unsolicited multicast Router Advertisements,
		 in seconds."
        DEFVAL	{ 200 }
        ::= { wfIpv6NdiscIfEntry 11 }

    wfIpv6NdiscIfMaxRtrAdvInterval OBJECT-TYPE
        SYNTAX	INTEGER (4..1800)
        ACCESS	read-write
        STATUS	mandatory
        DESCRIPTION
                "The maximum time allowed between sending
		 unsolicited multicast Router Advertisements,
		 in seconds."
        DEFVAL	{ 600 }
        ::= { wfIpv6NdiscIfEntry 12 }

    wfIpv6NdiscIfDefaultLifetime OBJECT-TYPE
        SYNTAX	INTEGER (0..9000)
        ACCESS	read-write
        STATUS	mandatory
        DESCRIPTION
                "The lifetime associated with the default 
		 router in units of seconds."
        DEFVAL	{ 1800 }
        ::= { wfIpv6NdiscIfEntry 13 }

    wfIpv6NdiscIfDupAddrDetectTransmits OBJECT-TYPE
        SYNTAX	INTEGER (0..10)
        ACCESS	read-write
        STATUS	mandatory
        DESCRIPTION
                "The number of consecutive Neighbor Solicitations
		 messages sent while performing Duplicate Address
		 Detection on a tentative address. A value of zero
		 indicates that no Duplicate Address Detection needs
		 to be performed. A value of one indicates a single
                 transmission with no follow up retransmission."
        DEFVAL	{ 1 }
        ::= { wfIpv6NdiscIfEntry 14 }


-- UDP Statistics

    wfIpv6Udp	OBJECT IDENTIFIER ::= { wfIpv6UdpGroup 1 }

    wfIpv6UdpInDatagrams OBJECT-TYPE
        SYNTAX	Counter
        ACCESS	read-only
        STATUS	mandatory
        DESCRIPTION
                "The total number of UDP datagrams delivered to UDP users."
        ::= { wfIpv6Udp 1 }

    wfIpv6UdpNoPorts OBJECT-TYPE
        SYNTAX	Counter
        ACCESS	read-only
        STATUS	mandatory
        DESCRIPTION
                "The total number of received UDP datagrams for which there
                was no application at the destination port."
        ::= { wfIpv6Udp 2 }

    wfIpv6UdpInErrors OBJECT-TYPE
        SYNTAX	Counter
        ACCESS	read-only
        STATUS	mandatory
        DESCRIPTION
                "The number of received UDP datagrams that could not be
                delivered for reasons other than the lack of an
                application at the destination port."
        ::= { wfIpv6Udp 3 }

    wfIpv6UdpOutDatagrams OBJECT-TYPE
        SYNTAX	Counter
        ACCESS	read-only
        STATUS	mandatory
        DESCRIPTION
                "The total number of UDP datagrams sent from this entity."
        ::= { wfIpv6Udp 4 }

    wfIpv6UdpTable OBJECT-TYPE
        SYNTAX	SEQUENCE OF WfIpv6UdpEntry
        ACCESS	not-accessible
        STATUS	mandatory
        DESCRIPTION
                "The UDP listener table contains information about this
                 entity's UDP end-points on which a local application is
                 currently accepting datagrams."
        ::= { wfIpv6UdpGroup 2 }

    wfIpv6UdpEntry OBJECT-TYPE
        SYNTAX	WfIpv6UdpEntry
        ACCESS	not-accessible
        STATUS	mandatory
        DESCRIPTION
          "Information about a particular current UDP
           listener."
        INDEX	{ wfIpv6UdpLocalIfIndex,
                  wfIpv6UdpLocalAddress,
    		  wfIpv6UdpLocalPort }
        ::= { wfIpv6UdpTable 1 }

    WfIpv6UdpEntry ::= SEQUENCE {
    	    wfIpv6UdpLocalIfIndex
    		INTEGER,
    	    wfIpv6UdpLocalAddress
    		Ipv6Address,
    	    wfIpv6UdpLocalPort
    		INTEGER
        }

    wfIpv6UdpLocalIfIndex OBJECT-TYPE
        SYNTAX	INTEGER
        ACCESS	read-only
        STATUS	mandatory
        DESCRIPTION
                "The index value which uniquely identifies the local
		 interface to which this entry's information pertains.
		 The interface identified by a particular value of this
		 index is the same interface as identified by the same
		 value of wfIpv6IfIndex."
        ::= { wfIpv6UdpEntry 1 }

    wfIpv6UdpLocalAddress OBJECT-TYPE
        SYNTAX	Ipv6Address
        ACCESS	read-only
        STATUS	mandatory
        DESCRIPTION
                "The local IPv6 address for this UDP listener. In the case
                 of a UDP listener which is willing to accept datagrams
                 for any IPv6 address associated with the interface,
                 the value ::0 is used."
        ::= { wfIpv6UdpEntry 2 }

    wfIpv6UdpLocalPort OBJECT-TYPE
        SYNTAX	INTEGER
        ACCESS	read-only
        STATUS	mandatory
        DESCRIPTION
                "The local port value"
        ::= { wfIpv6UdpEntry 3 }


-- IPv6 Log Event Management table

    wfIpv6Log	OBJECT IDENTIFIER ::= { wfIpv6LogGroup 1 }

    wfIpv6LogDelete OBJECT-TYPE
        SYNTAX	INTEGER {
    		    created(1),
    		    deleted(2)
    		}
        ACCESS	read-write
        STATUS	mandatory
        DESCRIPTION
                "Create/Delete parameter. Default is created.
                Users perform a set operation on this
                object in order to create/delete wfIpv6Log mib object."
        DEFVAL	{ created }
        ::= { wfIpv6Log 1 }

    wfIpv6LogDisable OBJECT-TYPE
        SYNTAX	INTEGER {
    		    enabled(1),
    		    disabled(2)
    		}
        ACCESS	read-write
        STATUS	mandatory
        DESCRIPTION
                "Enable/Disable parameter. Default is enabled."
        DEFVAL	{ enabled }
        ::= { wfIpv6Log 2 }

    wfIpv6LogLevel OBJECT-TYPE
        SYNTAX	INTEGER {
    		    debug(1),
    		    trace(2),
    		    info(3),
    		    warning(4),
    		    fault(5)
    		}
        ACCESS	read-write
        STATUS	mandatory
        DESCRIPTION
                "BGP log event level.
		 Setting log to a specific level enables logging IPv6
		 events of this level and higher."
        DEFVAL	{ info }
        ::= { wfIpv6Log 3 }

    wfIpv6LogEvent OBJECT-TYPE
        SYNTAX	INTEGER (0..255)
        ACCESS	read-write
        STATUS	mandatory
        DESCRIPTION
                "Indicates whether a log message which corresponds
                 to the value of this attributes should be
                 sent to the log.

                 It affects wfIpv6LogCodes only. In order to save combined
                 list of messages you have to set wfIpv6LogCfgEvents directly
                 as copy of wfIpv6LogEvents."
        DEFVAL	{ 0 }
        ::= { wfIpv6Log 4 }

    wfIpv6LogEventDisable OBJECT-TYPE
        SYNTAX	INTEGER {
    		    enabled(1),
    		    disabled(2)
    		}
        ACCESS	read-write
        STATUS	mandatory
        DESCRIPTION
                "Indicates whether a log event defined in wfIpv6LogEvent
                 is to be logged."
        DEFVAL	{ enabled }
        ::= { wfIpv6Log 5 }

    wfIpv6LogEvents OBJECT-TYPE
        SYNTAX	OCTET STRING
        ACCESS	read-only
        STATUS	mandatory
        DESCRIPTION
                "Vector of enabled debug messages (to check only).
                 Messages are identified via the string of bits
                 contained within this attribute. The first octet
                 contains bits 0 to 7, the second octet contains
                 bits 8 to 15, and so on, with the most significant
                 bit referring to the lowest bit number in the octet
                 (e.g., the MSB of the first octet refers to bit 0).
                 If a bit, i, is present and set, then the DEBUG log
                 message with the code (i) is enabled."
        ::= { wfIpv6Log 6 }

    wfIpv6LogCfgEvents OBJECT-TYPE
        SYNTAX	OCTET STRING
        ACCESS	read-write
        STATUS	mandatory
        DESCRIPTION
                "User-defined vector of enabled debug messages at boot moment.
                Coded as instance above"
        ::= { wfIpv6Log 7 }

END  -- Wellfleet-IPV6-MIB
