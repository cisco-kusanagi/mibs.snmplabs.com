-- SNMP-Link SL61 MIB

-- v 1.20  01/05/06

-- Copyright (c) 2002-2006 by Omnitronix, Inc.  All rights reserved.


SL61-STD-MIB DEFINITIONS ::= BEGIN

IMPORTS
 ObjectName, enterprises, IpAddress, TimeTicks
    FROM RFC1155-SMI
 OBJECT-TYPE
    FROM RFC-1212
 DisplayString
    FROM SNMPv2-TC
 TRAP-TYPE
    FROM RFC-1215 ;


--***************************************************************************************
--Concise MIB View
--***************************************************************************************

--  status
--    eventSensorStatus
--    dataEventStatus
--  config
--    eventSensorBasics
--    dataEventConfig
--    serialPorts
--    network
--    modem
--    snmp
--    pagers
--    time
--    timeouts
--  productIds
--  techSupport


--***************************************************************************************
--Entire MIB View
--***************************************************************************************

--  status                               .1
--    eventSensorStatus                  .1.1
--      esPointTable                     .1.1.1
--        esPointEntry                   .1.1.1.1
--          esIndexES                    .1.1.1.1.1
--          esIndexPC                    .1.1.1.1.2
--          esIndexPoint                 .1.1.1.1.3
--          esPointName                  .1.1.1.1.4
--          esPointInEventState          .1.1.1.1.5
--          esPointValueInt              .1.1.1.1.6
--          esPointValueStr              .1.1.1.1.7
--          esPointTimeLastChange        .1.1.1.1.8
--          esPointTimetickLastChange    .1.1.1.1.9
--    dataEventStatus                    .1.2
--      deStatusTable                    .1.2.1
--        deStatusEntry                  .1.2.1.1
--          deStatusIndex                .1.2.1.1.1
--          deStatusName                 .1.2.1.1.2
--          deStatusCounter              .1.2.1.1.3
--          deStatusThreshold            .1.2.1.1.4
--          deStatusLastTriggerTime      .1.2.1.1.5
--          deStatusLastTriggerData      .1.2.1.1.6

--  config                               .2
--    eventSensorBasics                  .2.1
--      esNumberEventSensors             .2.1.1
--      esTable                          .2.1.2
--        esEntry                        .2.1.2.1
--          esIndex                      .2.1.2.1.1
--          esName                       .2.1.2.1.2
--          esID                         .2.1.2.1.3
--          esNumberTempSensors          .2.1.2.1.4
--          esTempReportingMode          .2.1.2.1.5
--          esNumberCCs                  .2.1.2.1.6
--          esCCReportingMode            .2.1.2.1.7
--          esNumberHumidSensors         .2.1.2.1.8
--          esHumidReportingMode         .2.1.2.1.9
--          esNumberNoiseSensors         .2.1.2.1.10
--          esNoiseReportingMode         .2.1.2.1.11
--          esNumberAirflowSensors       .2.1.2.1.12
--          esAirflowReportingMode       .2.1.2.1.13
--          esNumberAnalog               .2.1.2.1.14
--          esAnalogReportingMode        .2.1.2.1.15
--          esNumberRelayOutputs         .2.1.2.1.16
--          esRelayReportingMode         .2.1.2.1.17
--    dataEventConfig                    .2.2
--      deFieldTable                     .2.2.1
--        deFieldEntry                   .2.2.1.1
--          deFieldIndex                 .2.2.1.1.1
--          deFieldStart                 .2.2.1.1.2
--          deFieldLength                .2.2.1.1.3
--          deFieldName                  .2.2.1.1.4
--      deConfigTable                    .2.2.2
--        deConfigEntry                  .2.2.2.1
--          deConfigIndex                .2.2.2.1.1
--          deConfigEnabled              .2.2.2.1.2
--          deConfigName                 .2.2.2.1.3
--          deConfigEquation             .2.2.2.1.4
--          deConfigThreshold            .2.2.2.1.5
--          deConfigClearMode            .2.2.2.1.6
--          deConfigClearTime            .2.2.2.1.7
--          deConfigAutoClear            .2.2.2.1.8
--          deConfigActions              .2.2.2.1.9
--          deConfigTrapNumber           .2.2.2.1.10
--          deConfigClass                .2.2.2.1.11
--    serialPorts                        .2.3
--      numberPorts                      .2.3.1
--      portConfigTable                  .2.3.2
--        portConfigEntry                .2.3.2.1
--          portConfigIndex              .2.3.2.1.1
--          portConfigBaud               .2.3.2.1.2
--          portConfigDataFormat         .2.3.2.1.3
--          portConfigStripPtOutputLfs   .2.3.2.1.4
--          portConfigStripPtInputLfs    .2.3.2.1.5
--          portConfigDTRLowIdle         .2.3.2.1.6
--          portConfigMaskEnable         .2.3.2.1.7
--          portConfigDAEnable           .2.3.2.1.8
--    network                            .2.4
--      ipConfigStatic                   .2.4.1
--      ipConfigAddress                  .2.4.2
--      ipConfigSubnetMask               .2.4.3
--      ipConfigDefaultRouter            .2.4.4
--      ipConfigEngage                   .2.4.5
--      telnetDuplex                     .2.4.6
--    modem                              .2.5
--      modemDataFormat                  .2.5.1
--      modemUserSetup                   .2.5.2
--      modemTAPSetup                    .2.5.3
--      modemTimeBetweenOutbound         .2.5.5
--    snmp                               .2.6
--      smTable                          .2.6.1
--        smEntry                        .2.6.1.1
--          smIndex                      .2.6.1.1.1
--          smAddress                    .2.6.1.1.2
--    pagers                             .2.7
--      pagerRetries                     .2.7.1
--      pagerTable                       .2.7.2
--        pagerEntry                     .2.7.2.1
--          pagerIndex                   .2.7.2.1.1
--          pagerType                    .2.7.2.1.2
--          pagerPhoneNumber             .2.7.2.1.3
--          pagerID                      .2.7.2.1.4
--          pagerPostCalloutDelay        .2.7.2.1.5
--          pagerIDDelay                 .2.7.2.1.6
--    time                               .2.8
--      clock                            .2.8.1
--      autoDSTAdjust                    .2.8.2
--    timeouts                           .2.9
--      commandTimeout                   .2.9.1
--      passthroughTimeout               .2.9.2

--  productIds                           .3
--    siteID                             .3.1
--    thisProduct                        .3.2
--    stockTrapString                    .3.3
--    trapEventTypeNumber                .3.4
--    trapEventTypeName                  .3.5
--    trapIncludedValue                  .3.6
--    trapIncludedString                 .3.7
--    trapEventClassNumber               .3.9
--    trapEventClassName                 .3.10

--  techSupport                          .99
--    techSupport objects 1 - 26         .99.1 - .99.26


--***************************************************************************************
--TOP-LEVEL OBJECT IDENTIFIERS
--***************************************************************************************


  omnitronix  OBJECT IDENTIFIER ::= { enterprises 3052 }
  --1.3.6.1.4.1.3052

  sl61  OBJECT IDENTIFIER ::= { omnitronix 4 }
  --1.3.6.1.4.1.3052.4

  status OBJECT IDENTIFIER ::= { sl61 1 }
  --1.3.6.1.4.1.3052.4.1

  config OBJECT IDENTIFIER ::= { sl61 2 }
  --1.3.6.1.4.1.3052.4.2

  productIds OBJECT IDENTIFIER ::= { sl61 3 }
  --1.3.6.1.4.1.3052.4.3

  techSupport OBJECT IDENTIFIER ::= { sl61 99 }
  --1.3.6.1.4.1.3052.4.99


  eventSensorStatus OBJECT IDENTIFIER ::= { status 1 }
  --1.3.6.1.4.1.3052.4.1.1

  dataEventStatus OBJECT IDENTIFIER ::= { status 2 }
  --1.3.6.1.4.1.3052.4.1.2


  eventSensorBasics OBJECT IDENTIFIER ::= { config 1 }
  --1.3.6.1.4.1.3052.4.2.1

  dataEventConfig OBJECT IDENTIFIER ::= { config 2 }
  --1.3.6.1.4.1.3052.4.2.2

  serialPorts OBJECT IDENTIFIER ::= { config 3 }
  --1.3.6.1.4.1.3052.4.2.3

  network OBJECT IDENTIFIER ::= { config 4 }
  --1.3.6.1.4.1.3052.4.2.4

  modem OBJECT IDENTIFIER ::= { config 5 }
  --1.3.6.1.4.1.3052.4.2.5

  snmp OBJECT IDENTIFIER ::= { config 6 }
  --1.3.6.1.4.1.3052.4.2.6

  pagers OBJECT IDENTIFIER ::= { config 7 }
  --1.3.6.1.4.1.3052.4.2.7

  time OBJECT IDENTIFIER ::= { config 8 }
  --1.3.6.1.4.1.3052.4.2.8

  timeouts OBJECT IDENTIFIER ::= { config 9 }
  --1.3.6.1.4.1.3052.4.2.9

--***************************************************************************************
--OBJECT DEFINITIONS
--***************************************************************************************

--***************************************************************************************
--EventSensor Status Section    1.1
--***************************************************************************************

esPointTable OBJECT-TYPE
    SYNTAX SEQUENCE OF ESPoint
    ACCESS not-accessible
    STATUS mandatory
    DESCRIPTION
        "
        This table organizes 4 basic attributes of points.  A point
        is a particular sensor on an EventSensor (e.g., temperature,
        humidity, contact closure 2, relay 5, etc.).  The 4 point
        attributes are its name, whether it's in its event state,
        the point's value as a number and its value as a string.

        Points are referenced by a point index.  The point index
        is a string of 3 numbers separated by periods.
        It contains all the information necessary for getting a piece
        of data off an event sensor; namely, which EventSensor,
        point class, and which-sensor-of-that-class (a.k.a. point).
        "
    ::= { eventSensorStatus 1 }
    --1.3.6.1.4.1.3052.4.1.1.1

esPointEntry OBJECT-TYPE
    SYNTAX ESPoint
    ACCESS not-accessible
    STATUS mandatory
    DESCRIPTION
        "Entry for EventSensor point table"
    INDEX { esIndexES, esIndexPC, esIndexPoint }
    ::= { esPointTable 1 }
    --1.3.6.1.4.1.3052.4.1.1.1.1

esIndexES OBJECT-TYPE
    SYNTAX INTEGER
    ACCESS read-only
    STATUS mandatory
    DESCRIPTION
        "The part of the point index that refers to an
        EventSensor.

        The point index is a string of 3 numbers separated
        by periods.  It contains all the information
        necessary for getting a piece of data off an event
        sensor; namely, which EventSensor, point class,
        and which-sensor-of-that-class (a.k.a. point).

        This object's allowable values are 1 through 16,
        and 200.  200 always refers to the EventSensor
        inside the unit.  1 through 16 refer to additional
        attached EventSensors.

        The number corresponding to an EventSensor is
        determined by the user at the initial configuration
        time.  If there is an internal sensor in the unit,
        it will always be the first item in the Sensor
        Events setup menu.

        For example, if a new EventSensor is configured as
        the 2nd entry AFTER the internal EventSensor (if
        one exists) in the Sensor Events Setup Menu, then
        that EventSensor will be known from then on as
        EventSensor 2.  All point indeces with esIndexES=2
        will now refer to that particular EventSensor.
        "
    ::= { esPointEntry 1 }
    --1.3.6.1.4.1.3052.4.1.1.1.1.1

esIndexPC OBJECT-TYPE
    SYNTAX INTEGER
    ACCESS read-only
    STATUS mandatory
    DESCRIPTION
        "The part of the point index that refers to point class.

        The point index is a string of 3 numbers separated by periods.
        It contains all the information necessary for getting a piece
        of data off an event sensor; namely, which EventSensor,
        point class, and which-sensor-of-that-class (a.k.a. point).

        The values for this object are:
        1=temperature sensor
        2=contact closure
        3=humidity sensor
        4=noise sensor
        5=analog input
        6=relay
        "
    ::= { esPointEntry 2 }
    --1.3.6.1.4.1.3052.4.1.1.1.1.2

esIndexPoint OBJECT-TYPE
    SYNTAX INTEGER
    ACCESS read-only
    STATUS mandatory
    DESCRIPTION
        "The part of the point index that delineates which
        sensor on the EventSensor.

        So this combined with esIndexPC (Point Class or type)
        and esIndexES (which EventSensor) uniquely defines each
        point (sensor or relay) attached to a unit.  For
        example, if esIndexES is 3, esIndexPC is 1 and
        esIndexPoint is 4 then this is the Fourth Temperature
        Sensor on EventSensor number 3."
    ::= { esPointEntry 3 }
    --1.3.6.1.4.1.3052.4.1.1.1.1.3

esPointName OBJECT-TYPE
    SYNTAX DisplayString
    ACCESS read-write
    STATUS mandatory
    DESCRIPTION
        "The name of the point on an EventSensor. For example,
        'AC temp' (in the case of the temperature sensor on an
        EventSensor).

        There can be multiple points of the same point class on an
        EventSensor (e.g., 8 contact closures) and multiple sensor
        classes on an EventSensor (e.g., temperature, contact closure,
        humidity).

        If the point referenced by a given point index is solitary
        (e.g., temperature sensor, because there can be only one on
        an EventSensor), then this object reads as '<EventSensor
        name>'.  Setting this object for solitary point indices sets
        the EventSensor name only.

        On the other hand, if a given point is among other points of
        the same point class on an EventSensor, then this object reads
        as '<Sensor name>'.  Setting this object for these NON-
        solitary point indices sets the sensor name only - not the
        EventSensor name."
    ::= { esPointEntry 4 }
    --1.3.6.1.4.1.3052.4.1.1.1.1.4

esPointInEventState OBJECT-TYPE
    SYNTAX INTEGER
    ACCESS read-write
    STATUS mandatory
    DESCRIPTION
        "A number referring to the event state of a point
        on an EventSensor.  This number can have different
        meanings depending on the point class.

        If the point class is temperature, humidity, or
        analog input, then the values of this object are:
        1=very low
        2=low
        3=normal
        4=high
        5=very high

        For contact closures and relays the values of this
        object are:
        1=point in event state
        2=point in normal state

        For any point class and any point, if the event
        state is undefined, then the value of this object
        is 0.

        For any point class except relay, this object is
        read-only.  For relays, setting this object to 1
        puts the relay into its event (active) state.
        Setting it to 2 puts the relay into its normal
        (inactive) state.  Depending on how the relay's
        active state is configured in the setup menu, the
        relay will then open or close.  This works
        regardless of the control mode of the relay.
        "
    ::= { esPointEntry 5 }
    --1.3.6.1.4.1.3052.4.1.1.1.1.5

esPointValueInt OBJECT-TYPE
    SYNTAX INTEGER (-32768..32767)
    ACCESS read-write
    STATUS mandatory
    DESCRIPTION
        "A number referring to the value of a point on an
        EventSensor.

        If the point class is temperature, then this object
        is the temperature in its configured scale (default
        is Fahrenheit).

        If the point class is contact closure or relay, then
        this object is either 0 (open) or 1 (closed).

        If the point class is humidity, then this object
        is the percent relative humidity.

        If the point class is analog input, then this
        object is the signed input value in tenths of the
        configured units.

        For any point class except relay, this object is
        read-only.  For relays, setting this object to 1
        closes the relay, while setting it to 0 opens it.
        This works regardless of the control mode of the
        relay.
        "
    ::= { esPointEntry 6 }
    --1.3.6.1.4.1.3052.4.1.1.1.1.6

esPointValueStr OBJECT-TYPE
    SYNTAX DisplayString
    ACCESS read-only
    STATUS mandatory
    DESCRIPTION
        "A string referring to the value of a point on an
        EventSensor.

        For contact closures and relays this object is
        either 'Open' or 'Closed'.

        For temperature and humidity point classes, this
        object is the string representation of the
        esPointValueInt object.  For temperature, 'C' or
        'F' is including in the string to indicate scale.

        For analog inputs, this object is the string
        representation of the plus/minus input in volts.
        "
    ::= { esPointEntry 7 }
    --1.3.6.1.4.1.3052.4.1.1.1.1.7

esPointTimeLastChange OBJECT-TYPE
    SYNTAX DisplayString
    ACCESS read-only
    STATUS mandatory
    DESCRIPTION
        "The time of the last time an event was
        triggerred for a point on an EventSensor in
        MM/DD/YY HH:MM:SS format.

        For contact closures, the possible events are
        Active and Inactive.  For temperature, humidity,
        and analog inputs, the possible events are Normal,
        High, Very High, Low, and Very Low.

        For relays, this object is a null string."
    ::= { esPointEntry 8 }
    --1.3.6.1.4.1.3052.4.1.1.1.1.8

esPointTimetickLastChange OBJECT-TYPE
    SYNTAX TimeTicks
    ACCESS read-only
    STATUS mandatory
    DESCRIPTION
        "The time of the last time an event was
        triggerred for a point on an EventSensor in
        100ths of seconds since reset.

        For contact closures, the possible events are
        Active and Inactive.  For temperature, humidity,
        and analog inputs, the possible events are Normal,
        High, Very High, Low, and Very Low.

        For relays, this object is 0."
    ::= { esPointEntry 9 }
    --1.3.6.1.4.1.3052.4.1.1.1.1.9


--***************************************************************************************
--Data Event Status Section 1.2
--***************************************************************************************

deStatusTable OBJECT-TYPE
    SYNTAX SEQUENCE OF DEStatus
    ACCESS not-accessible
    STATUS mandatory
    DESCRIPTION
        "Data Event Status Table"
    ::= { dataEventStatus 1 }
    --1.3.6.1.4.1.3052.4.1.2.1

deStatusEntry OBJECT-TYPE
    SYNTAX DEStatus
    ACCESS not-accessible
    STATUS mandatory
    DESCRIPTION
        "EventSensor status entry"
    INDEX { deStatusIndex }
    ::= { deStatusTable 1 }
    --1.3.6.1.4.1.3052.4.1.2.1.1

deStatusIndex OBJECT-TYPE
    SYNTAX INTEGER
    ACCESS read-only
    STATUS mandatory
    DESCRIPTION
        "Index for Data Events"
    ::= { deStatusEntry 1 }
    --1.3.6.1.4.1.3052.4.1.2.1.1.1

deStatusName OBJECT-TYPE
    SYNTAX DisplayString
    ACCESS read-only
    STATUS mandatory
    DESCRIPTION
        "Data Event name"
    ::= { deStatusEntry 2 }
    --1.3.6.1.4.1.3052.4.1.2.1.1.2

deStatusCounter OBJECT-TYPE
    SYNTAX INTEGER
    ACCESS read-only
    STATUS mandatory
    DESCRIPTION
        "Number of times a data record has matched this
        event's equation.
        Range: 1-999999999"
    ::= { deStatusEntry 3 }
    --1.3.6.1.4.1.3052.4.1.2.1.1.3

deStatusThreshold OBJECT-TYPE
    SYNTAX INTEGER
    ACCESS read-only
    STATUS mandatory
    DESCRIPTION
        "Number of times the equation is matched before
        an event is triggered.
        Range: 1-999999999"
    ::= { deStatusEntry 4 }
    --1.3.6.1.4.1.3052.4.1.2.1.1.4

deStatusLastTriggerTime OBJECT-TYPE
    SYNTAX DisplayString
    ACCESS read-only
    STATUS mandatory
    DESCRIPTION
        "Date/time that this event's counter last reached
        its threshold since the unit was last booted.  If
        this event has not yet been triggered, then this
        value is a null string.
        Format: HH:MM"
    ::= { deStatusEntry 5 }
    --1.3.6.1.4.1.3052.4.1.2.1.1.5

deStatusLastTriggerData OBJECT-TYPE
    SYNTAX DisplayString
    ACCESS read-only
    STATUS mandatory
    DESCRIPTION
        "Data (first 80 chars, or up to CR, whichever
        comes first) that caused this event's counter
        to reach the threshold.  If this event has not
        yet been triggered, then this value is a null
        string."
    ::= { deStatusEntry 6 }
    --1.3.6.1.4.1.3052.4.1.2.1.1.6


--***************************************************************************************
--EventSensor Basics Section    2.1
--***************************************************************************************

esNumberEventSensors OBJECT-TYPE
    SYNTAX INTEGER
    ACCESS read-only
    STATUS mandatory
    DESCRIPTION
        "The number of EventSensors recognized by the SL61,
        including the internal EventSensor.
        Range: 1-17"
    ::= { eventSensorBasics 1 }
    --1.3.6.1.4.1.3052.4.2.1.1

esTable OBJECT-TYPE
    SYNTAX SEQUENCE OF ESExist
    ACCESS not-accessible
    STATUS mandatory
    DESCRIPTION
        "The table of what EventSensors are attached to the unit,
        including the internal EventSensor"
    ::= { eventSensorBasics 2 }
    --1.3.6.1.4.1.3052.4.2.1.2

esEntry OBJECT-TYPE
    SYNTAX ESExist
    ACCESS not-accessible
    STATUS mandatory
    DESCRIPTION
        "Table entry for EventSensor table"
    INDEX { esIndex }
    ::= { esTable 1 }
    --1.3.6.1.4.1.3052.4.2.1.2.1

esIndex OBJECT-TYPE
    SYNTAX INTEGER
    ACCESS read-only
    STATUS mandatory
    DESCRIPTION
        "This number refers to an EventSensor; it has the
        same meaning as the esIndexES object (see above),
        except that this object is used only within the
        esTable branch.

        This object's allowable values are 1 through 16,
        and 200.  200 always refers to the EventSensor
        inside the unit.  1 through 16 refer to additional
        attached EventSensors.

        The number corresponding to an EventSensor is
        determined by the user at the initial configuration
        time.  If there is an internal sensor in the unit,
        it will always be the first item in the Sensor
        Events setup menu.

        For example, if a new EventSensor is configured as
        the 2nd entry AFTER the internal EventSensor (if
        one exists) in the Sensor Events Setup Menu, then
        that EventSensor will be known from then on as
        EventSensor 2.  All point indeces with esIndex=2
        will now refer to that particular EventSensor.
        "
    ::= { esEntry 1 }
    --1.3.6.1.4.1.3052.4.2.1.2.1.1

esName  OBJECT-TYPE
    SYNTAX DisplayString
    ACCESS read-only
    STATUS mandatory
    DESCRIPTION
        "The name of the EventSensor"
    ::= { esEntry 2 }
    --1.3.6.1.4.1.3052.4.2.1.2.1.2

esID    OBJECT-TYPE
    SYNTAX DisplayString
    ACCESS read-only
    STATUS mandatory
    DESCRIPTION
        "The factory-assigned ID of the EventSensor"
    ::= { esEntry 3 }
    --1.3.6.1.4.1.3052.4.2.1.2.1.3


esNumberTempSensors OBJECT-TYPE
    SYNTAX INTEGER
    ACCESS read-only
    STATUS mandatory
    DESCRIPTION
        "The number of temperature sensors on the EventSensor"
    ::= { esEntry 4 }
    --1.3.6.1.4.1.3052.4.2.1.2.1.4

esTempReportingMode OBJECT-TYPE
    SYNTAX DisplayString
    ACCESS read-only
    STATUS mandatory
    DESCRIPTION
        "Description of how temperature values should
        be interpreted."
    ::= { esEntry 5 }
    --1.3.6.1.4.1.3052.4.2.1.2.1.5

esNumberCCs OBJECT-TYPE
    SYNTAX INTEGER
    ACCESS read-only
    STATUS mandatory
    DESCRIPTION
        "The number of contact closures on the EventSensor."
    ::= { esEntry 6 }
    --1.3.6.1.4.1.3052.4.2.1.2.1.6

esCCReportingMode OBJECT-TYPE
    SYNTAX DisplayString
    ACCESS read-only
    STATUS mandatory
    DESCRIPTION
        "Description of how CC values should be interpreted."
    ::= { esEntry 7 }
    --1.3.6.1.4.1.3052.4.2.1.2.1.7

esNumberHumidSensors OBJECT-TYPE
    SYNTAX INTEGER
    ACCESS read-only
    STATUS mandatory
    DESCRIPTION
        "The number of humidity sensors on the EventSensor."
    ::= { esEntry 8 }
    --1.3.6.1.4.1.3052.4.2.1.2.1.8

esHumidReportingMode OBJECT-TYPE
    SYNTAX DisplayString
    ACCESS read-only
    STATUS mandatory
    DESCRIPTION
        "Description of how humidity sensor values should be
        interpreted."
    ::= { esEntry 9 }
    --1.3.6.1.4.1.3052.4.2.1.2.1.9

esNumberNoiseSensors OBJECT-TYPE
    SYNTAX INTEGER
    ACCESS read-only
    STATUS mandatory
    DESCRIPTION
        "The number of noise sensors on the EventSensor."
    ::= { esEntry 10 }
    --1.3.6.1.4.1.3052.4.2.1.2.1.10

esNoiseReportingMode OBJECT-TYPE
    SYNTAX DisplayString
    ACCESS read-only
    STATUS mandatory
    DESCRIPTION
        "Description of how noise sensor values should be
        interpreted."
    ::= { esEntry 11 }
    --1.3.6.1.4.1.3052.4.2.1.2.1.11

esNumberAirflowSensors OBJECT-TYPE
    SYNTAX INTEGER
    ACCESS read-only
    STATUS mandatory
    DESCRIPTION
        "The number of airflow sensors on the EventSensor."
    ::= { esEntry 12 }
    --1.3.6.1.4.1.3052.4.2.1.2.1.12

esAirflowReportingMode OBJECT-TYPE
    SYNTAX DisplayString
    ACCESS read-only
    STATUS mandatory
    DESCRIPTION
        "Description of how airflow sensor values should be
        interpreted."
    ::= { esEntry 13 }
    --1.3.6.1.4.1.3052.4.2.1.2.1.13

esNumberAnalog OBJECT-TYPE
    SYNTAX INTEGER
    ACCESS read-only
    STATUS mandatory
    DESCRIPTION
        "The number of analog inputs on the EventSensor."
    ::= { esEntry 14 }
    --1.3.6.1.4.1.3052.4.2.1.2.1.14

esAnalogReportingMode OBJECT-TYPE
    SYNTAX DisplayString
    ACCESS read-only
    STATUS mandatory
    DESCRIPTION
        "Description of how analog input values should be
        interpreted."
    ::= { esEntry 15 }
    --1.3.6.1.4.1.3052.4.2.1.2.1.15

esNumberRelayOutputs OBJECT-TYPE
    SYNTAX INTEGER
    ACCESS read-only
    STATUS mandatory
    DESCRIPTION
        "The number of relay outputs on the EventSensor"
    ::= { esEntry 16 }
    --1.3.6.1.4.1.3052.4.2.1.2.1.16

esRelayReportingMode OBJECT-TYPE
    SYNTAX DisplayString
    ACCESS read-only
    STATUS mandatory
    DESCRIPTION
        "Description of how relay output values
        should be interpreted."
    ::= { esEntry 17 }
    --1.3.6.1.4.1.3052.4.2.1.2.1.17


--***************************************************************************************
--Data Events Section   2.2
--***************************************************************************************


deFieldTable OBJECT-TYPE
    SYNTAX SEQUENCE OF DEField
    ACCESS not-accessible
    STATUS mandatory
    DESCRIPTION
        "Data event field table"
    ::= { dataEventConfig 1 }
    --1.3.6.1.4.1.3052.4.2.2.1

deFieldEntry OBJECT-TYPE
    SYNTAX DEField
    ACCESS not-accessible
    STATUS mandatory
    DESCRIPTION
        "Data event field entry"
    INDEX { deFieldIndex }
    ::= { deFieldTable 1 }
    --1.3.6.1.4.1.3052.4.2.2.1.1

deFieldIndex OBJECT-TYPE
    SYNTAX INTEGER
    ACCESS read-only
    STATUS mandatory
    DESCRIPTION
        "Index for data alarm"
    ::= { deFieldEntry 1 }
    --1.3.6.1.4.1.3052.4.2.2.1.1.1

deFieldStart OBJECT-TYPE
    SYNTAX INTEGER
    ACCESS read-write
    STATUS mandatory
    DESCRIPTION
        "The start position of the data event field.
        1 is the value of the first position.
        Range: 0-160; 0 disables the field."
    ::= { deFieldEntry 2 }
    --1.3.6.1.4.1.3052.4.2.2.1.1.2

deFieldLength OBJECT-TYPE
    SYNTAX INTEGER
    ACCESS read-write
    STATUS mandatory
    DESCRIPTION
        "The length of the data event field.
        Range: 1-160"
    ::= { deFieldEntry 3 }
    --1.3.6.1.4.1.3052.4.2.2.1.1.3

deFieldName OBJECT-TYPE
    SYNTAX DisplayString
    ACCESS read-write
    STATUS mandatory
    DESCRIPTION
        "The name of the data event field."
    ::= { deFieldEntry 4 }
    --1.3.6.1.4.1.3052.4.2.2.1.1.4


deConfigTable OBJECT-TYPE
    SYNTAX SEQUENCE OF DEConfig
    ACCESS not-accessible
    STATUS mandatory
    DESCRIPTION
        "Table for configuring data events."
    ::= { dataEventConfig 2 }
    --1.3.6.1.4.1.3052.4.2.2.2

deConfigEntry OBJECT-TYPE
    SYNTAX DEConfig
    ACCESS not-accessible
    STATUS mandatory
    DESCRIPTION
        "Entry for Data Event Config table"
    INDEX { deConfigIndex }
    ::= { deConfigTable 1 }
    --1.3.6.1.4.1.3052.4.2.2.2.1

deConfigIndex OBJECT-TYPE
    SYNTAX INTEGER
    ACCESS read-only
    STATUS mandatory
    DESCRIPTION
        "Index for Data Event Config table"
    ::= { deConfigEntry 1 }
    --1.3.6.1.4.1.3052.4.2.2.2.1.1

deConfigEnabled OBJECT-TYPE
    SYNTAX INTEGER
    ACCESS read-write
    STATUS mandatory
    DESCRIPTION
        "0 = not enabled; 1 = enabled"
    ::= { deConfigEntry 2 }
    --1.3.6.1.4.1.3052.4.2.2.2.1.2

deConfigName OBJECT-TYPE
    SYNTAX DisplayString
    ACCESS read-write
    STATUS mandatory
    DESCRIPTION
        "Name of the data event"
    ::= { deConfigEntry 3 }
    --1.3.6.1.4.1.3052.4.2.2.2.1.3

deConfigEquation OBJECT-TYPE
    SYNTAX DisplayString
    ACCESS read-write
    STATUS mandatory
    DESCRIPTION
        "Equation for the data event"
    ::= { deConfigEntry 4 }
    --1.3.6.1.4.1.3052.4.2.2.2.1.4

deConfigThreshold OBJECT-TYPE
    SYNTAX INTEGER
    ACCESS read-write
    STATUS mandatory
    DESCRIPTION
        "Number of times the equation is matched before
        an event is triggered.
        Range: 1-999999999"
    ::= { deConfigEntry 5 }
    --1.3.6.1.4.1.3052.4.2.2.2.1.5

deConfigClearMode OBJECT-TYPE
    SYNTAX INTEGER
    ACCESS read-write
    STATUS mandatory
    DESCRIPTION
        "Value representing at what interval the unit
        clears its data event counters.
        0 = never; 1 = 2 hrs; 2 = 4 hrs; 3 = 6 hrs;
        4 = 8 hrs; 5 = 12 hrs; 6 = daily"
    ::= { deConfigEntry 6 }
    --1.3.6.1.4.1.3052.4.2.2.2.1.6

deConfigClearTime OBJECT-TYPE
    SYNTAX DisplayString
    ACCESS read-write
    STATUS mandatory
    DESCRIPTION
        "HH:MM representing the time of day at which
        this data event is cleared."
    ::= { deConfigEntry 7 }
    --1.3.6.1.4.1.3052.4.2.2.2.1.7

deConfigAutoClear OBJECT-TYPE
    SYNTAX INTEGER
    ACCESS read-write
    STATUS mandatory
    DESCRIPTION
        "1=counter for this event clears when threshold
        is reached. 0=counter doesn't clear."
    ::= { deConfigEntry 8 }
    --1.3.6.1.4.1.3052.4.2.2.2.1.8

deConfigActions OBJECT-TYPE
    SYNTAX DisplayString
    ACCESS read-write
    STATUS mandatory
    DESCRIPTION
        "String that describes what actions are
        associated with this data event.  It is formatted
        'TxxxxxxxxPxxxx', where x is a digit that corresponds
        to which trap manager/pager slot to use.  T means
        Trap and P means Pager.  If there are no slots defined
        for a trap manager/pager, then the T/P is omitted."
    ::= { deConfigEntry 9 }
    --1.3.6.1.4.1.3052.4.2.2.2.1.9

deConfigTrapNumber OBJECT-TYPE
    SYNTAX INTEGER
    ACCESS read-write
    STATUS mandatory
    DESCRIPTION
        "Trap number to use when sending a trap.
        Range: 100 or (1000-1199)"
    ::= { deConfigEntry 10 }
    --1.3.6.1.4.1.3052.4.2.2.2.1.10

deConfigClass OBJECT-TYPE
    SYNTAX INTEGER
    ACCESS read-write
    STATUS mandatory
    DESCRIPTION
        "The class to use for this data event"
    ::= { deConfigEntry 11 }
    --1.3.6.1.4.1.3052.4.2.2.2.1.11


--***************************************************************************************
--Serial Port Section       2.3
--***************************************************************************************

numberPorts OBJECT-TYPE
    SYNTAX INTEGER
    ACCESS read-only
    STATUS mandatory
    DESCRIPTION
        "Number of RS-232 ports found.
        Range: 2 or 4"
    ::= { serialPorts 1 }
    --1.3.6.1.4.1.3052.4.2.3.1

portConfigTable OBJECT-TYPE
    SYNTAX SEQUENCE OF PortConfig
    ACCESS not-accessible
    STATUS mandatory
    DESCRIPTION
        "Port config table"
    ::= { serialPorts 2 }
    --1.3.6.1.4.1.3052.4.2.3.2

portConfigEntry OBJECT-TYPE
    SYNTAX PortConfig
    ACCESS not-accessible
    STATUS mandatory
    DESCRIPTION
        "Port config entry"
    INDEX { portConfigIndex }
    ::= { portConfigTable 1 }
    --1.3.6.1.4.1.3052.4.2.3.2.1

portConfigIndex OBJECT-TYPE
    SYNTAX INTEGER
    ACCESS read-only
    STATUS mandatory
    DESCRIPTION
        "Index for ports"
    ::= { portConfigEntry 1 }
    --1.3.6.1.4.1.3052.4.2.3.2.1.1

portConfigBaud OBJECT-TYPE
    SYNTAX INTEGER
    ACCESS read-write
    STATUS mandatory
    DESCRIPTION
        "Baud rate, 19200, 9600, etc."
    ::= { portConfigEntry 2 }
    --1.3.6.1.4.1.3052.4.2.3.2.1.2

portConfigDataFormat OBJECT-TYPE
    SYNTAX INTEGER
    ACCESS read-write
    STATUS mandatory
    DESCRIPTION
        "Value representing word length, parity, and
        stop bits: 0=8N1, 1=7E1, 2=7O1, 3=7N1"
    ::= { portConfigEntry 3 }
    --1.3.6.1.4.1.3052.4.2.3.2.1.3

portConfigStripPtOutputLfs OBJECT-TYPE
    SYNTAX INTEGER
    ACCESS read-write
    STATUS mandatory
    DESCRIPTION
        "Strip passthrough LFs sent to device on this port:
        1=yes, 0=no."
    ::= { portConfigEntry 4 }
    --1.3.6.1.4.1.3052.4.2.3.2.1.4

portConfigStripPtInputLfs OBJECT-TYPE
    SYNTAX INTEGER
    ACCESS read-write
    STATUS mandatory
    DESCRIPTION
        "Strip passthrough LFs received from device on this
        port: 1=yes, 0=no."
    ::= { portConfigEntry 5 }
    --1.3.6.1.4.1.3052.4.2.3.2.1.5

portConfigDTRLowIdle OBJECT-TYPE
    SYNTAX INTEGER
    ACCESS read-write
    STATUS mandatory
    DESCRIPTION
        "0=DTR always low; 1=DTR low except when pass-
        through is active."
    ::= { portConfigEntry 6 }
    --1.3.6.1.4.1.3052.4.2.3.2.1.6

portConfigMaskEnable OBJECT-TYPE
    SYNTAX INTEGER
    ACCESS read-write
    STATUS mandatory
    DESCRIPTION
        "1=Use the character mask on this port.  0=Do
        not use the mask.  When the mask is enabled,
        the following ASCII characters are ignored
        on the port:
        0, 1, 4-9, 11, 12, 14-31, 128-255.
        When the mask is disabled, all characters are
        accepted on the port."
    ::= { portConfigEntry 7 }
    --1.3.6.1.4.1.3052.4.2.3.2.1.7

portConfigDAEnable OBJECT-TYPE
    SYNTAX INTEGER
    ACCESS read-write
    STATUS mandatory
    DESCRIPTION
        "1=Enable the Data Alarm Evaluator for data
        on this port.  0=Do not evaluate data on this
        port."
    ::= { portConfigEntry 8 }
    --1.3.6.1.4.1.3052.4.2.3.2.1.8


--***************************************************************************************
--Network Section   2.4
--***************************************************************************************

ipConfigStatic OBJECT-TYPE
    SYNTAX INTEGER
    ACCESS read-only
    STATUS mandatory
    DESCRIPTION
         "0= IP address is dynamically obtained.
         1= IP address is statically assigned."
    ::= { network 1 }
    --1.3.6.1.4.1.3052.4.2.4.1

ipConfigAddress OBJECT-TYPE
    SYNTAX IpAddress
    ACCESS read-write
    STATUS mandatory
    DESCRIPTION
        "Current IP address"
    ::= { network 2 }
    --1.3.6.1.4.1.3052.4.2.4.2

ipConfigSubnetMask OBJECT-TYPE
    SYNTAX IpAddress
    ACCESS read-write
    STATUS mandatory
    DESCRIPTION
        "Current subnet mask"
    ::= { network 3 }
    --1.3.6.1.4.1.3052.4.2.4.3

ipConfigDefaultRouter OBJECT-TYPE
    SYNTAX IpAddress
    ACCESS read-write
    STATUS mandatory
    DESCRIPTION
        "Current default router (gateway)"
    ::= { network 4 }
    --1.3.6.1.4.1.3052.4.2.4.4

ipConfigEngage OBJECT-TYPE
    SYNTAX INTEGER
    ACCESS read-write
    STATUS mandatory
    DESCRIPTION
        "Read=0.
        Write requires private community name.
        Any write causes the current object values for
        ipConfigAddress, ipConfigSubnetMask,
        and ipConfigDefaultRouter to be used.
        Causes the unit to reinitialize its network
        stacks with these new values.  Changes to
        ipConfigStatic, ipConfigAddress, ipConfigSubnetMask,
        or ipConfigDefaultRouter do not affect the network
        stack until ipConfigEngage is written with some
        value."
    ::= { network 5 }
    --1.3.6.1.4.1.3052.4.2.4.5

telnetDuplex OBJECT-TYPE
    SYNTAX INTEGER
    ACCESS read-write
    STATUS mandatory
    DESCRIPTION
        "1=Input characters are echoed; 0=no echo."
    ::= { network 6 }
    --1.3.6.1.4.1.3052.4.2.4.6

--***************************************************************************************
--Modem Section     2.5
--***************************************************************************************

modemDataFormat OBJECT-TYPE
    SYNTAX INTEGER
    ACCESS read-write
    STATUS mandatory
    DESCRIPTION
        "Value representing word length, parity, and
        stop bits: 0=8N1, 1=7E1, 2=7O1, 3=7N1"
    ::= { modem 1 }
    --1.3.6.1.4.1.3052.4.2.5.1

modemUserSetup OBJECT-TYPE
    SYNTAX DisplayString
    ACCESS read-write
    STATUS mandatory
    DESCRIPTION
        "Sent to modem on init before the factory setup string"
    ::= { modem 2 }
    --1.3.6.1.4.1.3052.4.2.5.2

modemTAPSetup OBJECT-TYPE
    SYNTAX DisplayString
    ACCESS read-write
    STATUS mandatory
    DESCRIPTION
        "Sent to modem just before doing TAP (alpha pager) protocol"
    ::= { modem 3 }
    --1.3.6.1.4.1.3052.4.2.5.3

modemTimeBetweenOutbound OBJECT-TYPE
    SYNTAX INTEGER
    ACCESS read-write
    STATUS mandatory
    DESCRIPTION
        "# seconds (minimum) between outbound call attempts.
        Range: 60-400"
    ::= { modem 5 }
    --1.3.6.1.4.1.3052.4.2.5.5


--***************************************************************************************
--SNMP Manager Setup Section    2.6
--***************************************************************************************

smTable OBJECT-TYPE
    SYNTAX SEQUENCE OF SMEntry
    ACCESS not-accessible
    STATUS mandatory
    DESCRIPTION
        "SNMP manager table"
    ::= { snmp 1 }
    --1.3.6.1.4.1.3052.4.2.6.1

smEntry OBJECT-TYPE
    SYNTAX SMEntry
    ACCESS not-accessible
    STATUS mandatory
    DESCRIPTION
        "SNMP manager table entry"
    INDEX { smIndex }
    ::= { smTable 1 }
    --1.3.6.1.4.1.3052.4.2.6.1.1

smIndex OBJECT-TYPE
    SYNTAX INTEGER
    ACCESS read-only
    STATUS mandatory
    DESCRIPTION
        "Index for SNMP manager table"
    ::= { smEntry 1 }
    --1.3.6.1.4.1.3052.4.2.6.1.1.1

smAddress OBJECT-TYPE
    SYNTAX IpAddress
    ACCESS read-write
    STATUS mandatory
    DESCRIPTION
        "IP address of SNMP manager"
    ::= { smEntry 2 }
    --1.3.6.1.4.1.3052.4.2.6.1.1.2

--***************************************************************************************
--Pager Setup Section   2.7
--***************************************************************************************

pagerRetries OBJECT-TYPE
    SYNTAX INTEGER
    ACCESS read-write
    STATUS mandatory
    DESCRIPTION
        "Number of times to retry a pager callout.
        Range: 0-255"
    ::= { pagers 1 }
    --1.3.6.1.4.1.3052.4.2.7.1

pagerTable OBJECT-TYPE
    SYNTAX SEQUENCE OF PagerEntry
    ACCESS not-accessible
    STATUS mandatory
    DESCRIPTION
        "Table of pager configurations"
    ::= { pagers 2 }
    --1.3.6.1.4.1.3052.4.2.7.2

pagerEntry OBJECT-TYPE
    SYNTAX PagerEntry
    ACCESS not-accessible
    STATUS mandatory
    DESCRIPTION
        "Pager table entry"
    INDEX { pagerIndex }
    ::= { pagerTable 1 }
    --1.3.6.1.4.1.3052.4.2.7.2.1

pagerIndex OBJECT-TYPE
    SYNTAX INTEGER
    ACCESS read-only
    STATUS mandatory
    DESCRIPTION
        "Index for pager configuration table"
    ::= { pagerEntry 1 }
    --1.3.6.1.4.1.3052.4.2.7.2.1.1

pagerType OBJECT-TYPE
    SYNTAX INTEGER
    ACCESS read-write
    STATUS mandatory
    DESCRIPTION
        "65=alphanumeric; 78=numeric"
    ::= { pagerEntry 2 }
    --1.3.6.1.4.1.3052.4.2.7.2.1.2


pagerPhoneNumber OBJECT-TYPE
    SYNTAX DisplayString
    ACCESS read-write
    STATUS mandatory
    DESCRIPTION
        "Phone number to dial"
    ::= { pagerEntry 3 }
    --1.3.6.1.4.1.3052.4.2.7.2.1.3


pagerID OBJECT-TYPE
    SYNTAX DisplayString
    ACCESS read-write
    STATUS mandatory
    DESCRIPTION
        "For alphanumeric pagers only, the Pager ID
        string provided by your paging company."
    ::= { pagerEntry 4 }
    --1.3.6.1.4.1.3052.4.2.7.2.1.4


pagerPostCalloutDelay OBJECT-TYPE
    SYNTAX INTEGER
    ACCESS read-write
    STATUS mandatory
    DESCRIPTION
        "For numeric pagers, seconds to wait after
        dialing to to send message.
        Range: 0-255"
    ::= { pagerEntry 5 }
    --1.3.6.1.4.1.3052.4.2.7.2.1.5


pagerIDDelay OBJECT-TYPE
    SYNTAX INTEGER
    ACCESS read-write
    STATUS mandatory
    DESCRIPTION
        "For numeric pagers, seconds to wait after
        sending message to hang up.
        Range: 0-255"
    ::= { pagerEntry 6 }
    --1.3.6.1.4.1.3052.4.2.7.2.1.6

--***************************************************************************************
--Time Section  2.8
--***************************************************************************************

clock OBJECT-TYPE
    SYNTAX DisplayString
    ACCESS read-write
    STATUS mandatory
    DESCRIPTION
        "Text string for date and time;
        e.g. 'SUN 01/02/98 12:34:27'.  When setting
        this object, only the date and time are
        required; the unit will ignore a specified
        day of week because it is calculated from
        the date and time.  When this object is included
        in a notification as a varbind, it represents
        the time that the triggering event occurred."
    ::= { time 1 }
    --1.3.6.1.4.1.3052.4.2.8.1

autoDSTAdjust OBJECT-TYPE
    SYNTAX INTEGER
    ACCESS read-write
    STATUS mandatory
    DESCRIPTION
        "0=do not auto adjust; 1=auto adjust for
        daylight savings."
    ::= { time 2 }
    --1.3.6.1.4.1.3052.4.2.8.2


--***************************************************************************************
--Timeouts Section  2.9
--***************************************************************************************

commandTimeout OBJECT-TYPE
    SYNTAX INTEGER
    ACCESS read-write
    STATUS mandatory
    DESCRIPTION
        "Number of minutes of inactivity before a
        command session automatically disconnects.
        0 means it never disconnects."
    ::= { timeouts 1 }
    --1.3.6.1.4.1.3052.4.2.9.1

passthroughTimeout OBJECT-TYPE
    SYNTAX INTEGER
    ACCESS read-write
    STATUS mandatory
    DESCRIPTION
        "Number of minutes of inactivity before a
        passthrough session automatically disconnects.
        0 means it never disconnects."
    ::= { timeouts 2 }
    --1.3.6.1.4.1.3052.4.2.9.2


--***************************************************************************************
--Product IDs Section   3
--***************************************************************************************

siteID OBJECT-TYPE
    SYNTAX DisplayString
    ACCESS read-write
    STATUS mandatory
    DESCRIPTION
        "Site ID string; Max 40 characters."
    ::= { productIds 1 }
    --1.3.6.1.4.1.3052.4.3.1

thisProduct OBJECT-TYPE
    SYNTAX DisplayString
    ACCESS read-only
    STATUS mandatory
    DESCRIPTION
        "This is a factory configured string for the
        product name."
    ::= { productIds 2 }
    --1.3.6.1.4.1.3052.4.3.2

stockTrapString OBJECT-TYPE
    SYNTAX DisplayString
    ACCESS read-only
    STATUS mandatory
    DESCRIPTION
        "This string is included in every stock trap."
    ::= { productIds 3 }
    --1.3.6.1.4.1.3052.4.3.3

trapEventTypeNumber OBJECT-TYPE
    SYNTAX INTEGER
    ACCESS read-only
    STATUS mandatory
    DESCRIPTION
        "The user-defined trap variable for the type of
        event that happened.  Here are the definitions:
           1    Data Alarm
           10   Contact Closure Active
           11   Contact Closure Inactive
           12   Temperature High
           13   Temperature Very High
           14   Temperature Low
           15   Temperature Very Low
           16   Temperature Return to Normal
           17   Humidity High
           18   Humidity Very High
           19   Humidity Low
           20   Humidity Very Low
           21   Humidity Return to Normal
           26   Analog High
           27   Analog Very High
           28   Analog Low
           29   Analog Very Low
           30   Analog Normal
           40   EventSensor Unresponsive
           100  Contact Closure Active Reminder
           101  Temperature High Reminder
           102  Temperature High Very Reminder
           103  Temperature Low Reminder
           104  Temperature Very Low Reminder
           105  Humidity High Reminder
           106  Humidity Very High Reminder
           107  Humidity Low Reminder
           108  Humidity Very Low Reminder
           109  Analog High Reminder
           110  Analog Very High Reminder
           111  Analog Low Reminder
           112  Analog Very Low Reminder"
    ::= { productIds 4 }
    --1.3.6.1.4.1.3052.4.3.4

trapEventTypeName OBJECT-TYPE
    SYNTAX DisplayString
    ACCESS read-only
    STATUS mandatory
    DESCRIPTION
        "The user-defined trap variable for the string
        corresponding to the event type."
    ::= { productIds 5 }
    --1.3.6.1.4.1.3052.4.3.5

trapIncludedValue OBJECT-TYPE
    SYNTAX INTEGER (-32768..32767)
    ACCESS read-only
    STATUS mandatory
    DESCRIPTION
        "The user-defined trap variable for the generic
        included value."
    ::= { productIds 6 }
    --1.3.6.1.4.1.3052.4.3.6

trapIncludedString OBJECT-TYPE
    SYNTAX DisplayString
    ACCESS read-only
    STATUS mandatory
    DESCRIPTION
        "The user-defined trap variable for the generic
        included string."
    ::= { productIds 7 }
    --1.3.6.1.4.1.3052.4.3.7

trapEventClassNumber OBJECT-TYPE
    SYNTAX INTEGER
    ACCESS not-accessible
    STATUS mandatory
    DESCRIPTION
        "The user-defined trap variable for the configurable
        class number associated with the triggering event."
    ::= { productIds 9 }
    --1.3.6.1.4.1.3052.4.3.9

trapEventClassName OBJECT-TYPE
    SYNTAX INTEGER
    ACCESS not-accessible
    STATUS mandatory
    DESCRIPTION
        "The user-defined trap variable for the configurable
         class name associated with the class number."
    ::= { productIds 10 }
    --1.3.6.1.4.1.3052.4.3.10

--***************************************************************************************
--Tech Support Section      99
--***************************************************************************************

techSupport1 OBJECT-TYPE
    SYNTAX INTEGER
    ACCESS read-write
    STATUS mandatory
    DESCRIPTION ""
    ::= { techSupport 1 }

techSupport2 OBJECT IDENTIFIER ::= { techSupport 2 }

techSupport2n1 OBJECT-TYPE
    SYNTAX INTEGER
    ACCESS read-write
    STATUS mandatory
    DESCRIPTION ""
    ::= { techSupport2 1 }

techSupport2n2 OBJECT-TYPE
    SYNTAX INTEGER
    ACCESS read-write
    STATUS mandatory
    DESCRIPTION ""
    ::= { techSupport2 2 }

techSupport3 OBJECT IDENTIFIER ::= { techSupport 3 }

techSupport3n1 OBJECT-TYPE
    SYNTAX INTEGER
    ACCESS read-write
    STATUS mandatory
    DESCRIPTION ""
    ::= { techSupport3 1 }

techSupport3n2 OBJECT-TYPE
    SYNTAX INTEGER
    ACCESS read-write
    STATUS mandatory
    DESCRIPTION ""
    ::= { techSupport3 2 }

techSupport3n3 OBJECT-TYPE
    SYNTAX INTEGER
    ACCESS read-write
    STATUS mandatory
    DESCRIPTION ""
    ::= { techSupport3 3 }

techSupport3n4 OBJECT-TYPE
    SYNTAX INTEGER
    ACCESS read-write
    STATUS mandatory
    DESCRIPTION ""
    ::= { techSupport3 4 }

techSupport3n5 OBJECT-TYPE
    SYNTAX INTEGER
    ACCESS read-write
    STATUS mandatory
    DESCRIPTION ""
    ::= { techSupport3 5 }

techSupport4 OBJECT-TYPE
    SYNTAX INTEGER
    ACCESS read-write
    STATUS mandatory
    DESCRIPTION ""
    ::= { techSupport 4 }

techSupport7 OBJECT-TYPE
    SYNTAX INTEGER
    ACCESS read-write
    STATUS mandatory
    DESCRIPTION ""
    ::= { techSupport 7 }

techSupport9 OBJECT-TYPE
    SYNTAX INTEGER
    ACCESS read-write
    STATUS mandatory
    DESCRIPTION ""
    ::= { techSupport 9 }

techSupport10 OBJECT-TYPE
    SYNTAX DisplayString
    ACCESS read-write
    STATUS mandatory
    DESCRIPTION ""
    ::= { techSupport 10 }

techSupport11 OBJECT-TYPE
    SYNTAX INTEGER
    ACCESS read-write
    STATUS mandatory
    DESCRIPTION ""
    ::= { techSupport 11 }

techSupport16 OBJECT-TYPE
    SYNTAX INTEGER
    ACCESS read-write
    STATUS mandatory
    DESCRIPTION ""
    ::= { techSupport 16 }

techSupport17 OBJECT-TYPE
    SYNTAX INTEGER
    ACCESS read-write
    STATUS mandatory
    DESCRIPTION ""
    ::= { techSupport 17 }

techSupport18 OBJECT-TYPE
    SYNTAX INTEGER
    ACCESS read-write
    STATUS mandatory
    DESCRIPTION ""
    ::= { techSupport 18 }

techSupport19 OBJECT-TYPE
    SYNTAX DisplayString
    ACCESS read-write
    STATUS mandatory
    DESCRIPTION ""
    ::= { techSupport 19 }

techSupport20Table OBJECT-TYPE
    SYNTAX SEQUENCE OF TechSupport20Entry
    ACCESS not-accessible
    STATUS mandatory
    DESCRIPTION ""
    ::= { techSupport 20 }

techSupport20Entry OBJECT-TYPE
    SYNTAX TechSupport20Entry
    ACCESS not-accessible
    STATUS mandatory
    DESCRIPTION ""
    INDEX { techSupport20Index }
    ::= { techSupport20Table 1 }

techSupport20Index OBJECT-TYPE
    SYNTAX INTEGER
    ACCESS read-only
    STATUS mandatory
    DESCRIPTION ""
    ::= { techSupport20Entry 1 }

techSupport20 OBJECT-TYPE
    SYNTAX DisplayString
    ACCESS read-write
    STATUS mandatory
    DESCRIPTION ""
    ::= { techSupport20Entry 2 }

techSupport21Table OBJECT-TYPE
    SYNTAX SEQUENCE OF TechSupport21Entry
    ACCESS not-accessible
    STATUS mandatory
    DESCRIPTION ""
    ::= { techSupport 21 }

techSupport21Entry OBJECT-TYPE
    SYNTAX TechSupport21Entry
    ACCESS not-accessible
    STATUS mandatory
    DESCRIPTION ""
    INDEX { techSupport21Index }
    ::= { techSupport21Table 1 }

techSupport21Index OBJECT-TYPE
    SYNTAX INTEGER
    ACCESS read-only
    STATUS mandatory
    DESCRIPTION ""
    ::= { techSupport21Entry 1 }

techSupport21 OBJECT-TYPE
    SYNTAX INTEGER
    ACCESS read-only
    STATUS mandatory
    DESCRIPTION ""
    ::= { techSupport21Entry 2 }

techSupport22 OBJECT-TYPE
    SYNTAX INTEGER
    ACCESS read-write
    STATUS mandatory
    DESCRIPTION ""
    ::= { techSupport 22 }

techSupport24 OBJECT-TYPE
    SYNTAX DisplayString
    ACCESS read-write
    STATUS mandatory
    DESCRIPTION ""
    ::= { techSupport 24 }

techSupport25 OBJECT-TYPE
    SYNTAX DisplayString
    ACCESS read-write
    STATUS mandatory
    DESCRIPTION ""
    ::= { techSupport 25 }

techSupport26 OBJECT-TYPE
    SYNTAX DisplayString
    ACCESS read-write
    STATUS mandatory
    DESCRIPTION ""
    ::= { techSupport 26 }


--***************************************************************************************
--TABLE DEFINITIONS
--***************************************************************************************


PortConfig ::=
    SEQUENCE {
        portConfigIndex
            INTEGER,
        portConfigBaud
            INTEGER,
        portConfigDataFormat
            INTEGER,
        portConfigStripPtOutputLfs
            INTEGER,
        portConfigStripPtInputLfs
            INTEGER,
        portConfigDTRLowIdle
            INTEGER,
        portConfigMaskEnable
            INTEGER,
        portConfigDAEnable
            INTEGER
}

DEField ::=
    SEQUENCE {
        deFieldIndex
            INTEGER,
        deFieldStart
            INTEGER,
        deFieldLength
            INTEGER,
        deFieldName
            DisplayString
}

DEConfig ::=
    SEQUENCE {
        deConfigIndex
            INTEGER,
        deConfigEnabled
            INTEGER,
        deConfigName
            DisplayString,
        deConfigEquation
            DisplayString,
        deConfigThreshold
            INTEGER,
        deConfigClearMode
            INTEGER,
        deConfigClearTime
            DisplayString,
        deConfigAutoClear
            INTEGER,
        deConfigActions
            DisplayString,
        deConfigTrapNumber
            INTEGER,
        deConfigClass
            INTEGER
}

DEStatus ::=
    SEQUENCE {
        deStatusIndex
            INTEGER,
        deStatusName
            DisplayString,
        deStatusCounter
            INTEGER,
        deStatusThreshold
            INTEGER,
        deStatusLastTriggerTime
            DisplayString,
        deStatusLastTriggerData
            DisplayString
}


ESExist ::=
    SEQUENCE {
        esIndex
            INTEGER,
        esName
            DisplayString,
        esID
            DisplayString,
        esNumberTempSensors
            INTEGER,
        esTempReportingMode
            DisplayString,
        esNumberCCs
            INTEGER,
        esCCReportingMode
            DisplayString,
        esNumberHumidSensors
            INTEGER,
        esHumidReportingMode
            DisplayString,
        esNumberNoiseSensors
            INTEGER,
        esNoiseReportingMode
            DisplayString,
        esNumberAirflowSensors
            INTEGER,
        esAirflowReportingMode
            DisplayString,
        esNumberAnalog
            INTEGER,
        esAnalogReportingMode
            DisplayString,
        esNumberRelayOutputs
            INTEGER,
        esRelayReportingMode
            DisplayString
}

ESPoint ::=
    SEQUENCE {
        esIndexES
            INTEGER,
        esIndexPC
            INTEGER,
        esIndexPoint
            INTEGER,
        esPointName
            DisplayString,
        esPointInEventState
            INTEGER,
        esPointValueInt
            INTEGER,
        esPointValueStr
            DisplayString,
        esPointTimeLastChange
            DisplayString,
        esPointTimetickLastChange
            TimeTicks
}

SMEntry ::=
    SEQUENCE {
        smIndex
            INTEGER,
        smAddress
            IpAddress
}


PagerEntry ::=
    SEQUENCE {
        pagerIndex
            INTEGER,
        pagerType
            INTEGER,
        pagerPhoneNumber
            DisplayString,
        pagerID
            DisplayString,
        pagerPostCalloutDelay
            INTEGER,
        pagerIDDelay
            INTEGER
}

TechSupport20Entry ::=
    SEQUENCE {
        techSupport20Index
            INTEGER,
        techSupport20
            DisplayString
}

TechSupport21Entry ::=
    SEQUENCE {
        techSupport21Index
            INTEGER,
        techSupport21
            INTEGER
}


--***************************************************************************************
--TRAP DEFINITIONS
--***************************************************************************************

sl61TestTrap TRAP-TYPE
    ENTERPRISE sl61
    VARIABLES { siteID, stockTrapString }
    DESCRIPTION
        "An test trap is issued by the user."
    ::= 1

sl61StockESDisconnectTrap TRAP-TYPE
    ENTERPRISE sl61
    VARIABLES { siteID, stockTrapString }
    DESCRIPTION
        "A stock EventSensor disconnect trap is issued when an
        EventSensor has been unreponsive for the configured timeout."
    ::= 50

sl61StockDataEventTrap  TRAP-TYPE
    ENTERPRISE sl61
    VARIABLES { siteID, stockTrapString }
    DESCRIPTION
        "A stock data event trap is issued when a data event happens."
    ::= 100

sl61StockContactClosureTrap TRAP-TYPE
    ENTERPRISE sl61
    VARIABLES { siteID, stockTrapString }
    DESCRIPTION
        "A stock contact closure trap is issued when a contact closure
        event happens."
    ::= 110

sl61StockTempTrap   TRAP-TYPE
    ENTERPRISE sl61
    VARIABLES { siteID, stockTrapString }
    DESCRIPTION
        "A stock temperature trap is issued when a temperature event
        happens."
    ::= 120

sl61StockHumidityTrap   TRAP-TYPE
    ENTERPRISE sl61
    VARIABLES { siteID, stockTrapString }
    DESCRIPTION
        "A stock humidity trap is issued when a humidity event
        happens."
    ::= 130

sl61StockAnalogTrap TRAP-TYPE
    ENTERPRISE sl61
    VARIABLES { siteID, stockTrapString }
    DESCRIPTION
        "A stock analog trap is issued when an analog sensor event
        happens."
    ::= 140

sl61UserTrap1000 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1000."
    ::= 1000

sl61UserTrap1001 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1001."
    ::= 1001

sl61UserTrap1002 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1002."
    ::= 1002

sl61UserTrap1003 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1003."
    ::= 1003

sl61UserTrap1004 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1004."
    ::= 1004

sl61UserTrap1005 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1005."
    ::= 1005

sl61UserTrap1006 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1006."
    ::= 1006

sl61UserTrap1007 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1007."
    ::= 1007

sl61UserTrap1008 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1008."
    ::= 1008

sl61UserTrap1009 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1009."
    ::= 1009

sl61UserTrap1010 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1010."
    ::= 1010

sl61UserTrap1011 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1011."
    ::= 1011

sl61UserTrap1012 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1012."
    ::= 1012

sl61UserTrap1013 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1013."
    ::= 1013

sl61UserTrap1014 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1014."
    ::= 1014

sl61UserTrap1015 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1015."
    ::= 1015

sl61UserTrap1016 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1016."
    ::= 1016

sl61UserTrap1017 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1017."
    ::= 1017

sl61UserTrap1018 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1018."
    ::= 1018

sl61UserTrap1019 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1019."
    ::= 1019

sl61UserTrap1020 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1020."
    ::= 1020

sl61UserTrap1021 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1021."
    ::= 1021

sl61UserTrap1022 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1022."
    ::= 1022

sl61UserTrap1023 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1023."
    ::= 1023

sl61UserTrap1024 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1024."
    ::= 1024

sl61UserTrap1025 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1025."
    ::= 1025

sl61UserTrap1026 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1026."
    ::= 1026

sl61UserTrap1027 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1027."
    ::= 1027

sl61UserTrap1028 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1028."
    ::= 1028

sl61UserTrap1029 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1029."
    ::= 1029

sl61UserTrap1030 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1030."
    ::= 1030

sl61UserTrap1031 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1031."
    ::= 1031

sl61UserTrap1032 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1032."
    ::= 1032

sl61UserTrap1033 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1033."
    ::= 1033

sl61UserTrap1034 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1034."
    ::= 1034

sl61UserTrap1035 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1035."
    ::= 1035

sl61UserTrap1036 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1036."
    ::= 1036

sl61UserTrap1037 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1037."
    ::= 1037

sl61UserTrap1038 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1038."
    ::= 1038

sl61UserTrap1039 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1039."
    ::= 1039

sl61UserTrap1040 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1040."
    ::= 1040

sl61UserTrap1041 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1041."
    ::= 1041

sl61UserTrap1042 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1042."
    ::= 1042

sl61UserTrap1043 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1043."
    ::= 1043

sl61UserTrap1044 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1044."
    ::= 1044

sl61UserTrap1045 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1045."
    ::= 1045

sl61UserTrap1046 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1046."
    ::= 1046

sl61UserTrap1047 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1047."
    ::= 1047

sl61UserTrap1048 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1048."
    ::= 1048

sl61UserTrap1049 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1049."
    ::= 1049

sl61UserTrap1050 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1050."
    ::= 1050

sl61UserTrap1051 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1051."
    ::= 1051

sl61UserTrap1052 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1052."
    ::= 1052

sl61UserTrap1053 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1053."
    ::= 1053

sl61UserTrap1054 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1054."
    ::= 1054

sl61UserTrap1055 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1055."
    ::= 1055

sl61UserTrap1056 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1056."
    ::= 1056

sl61UserTrap1057 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1057."
    ::= 1057

sl61UserTrap1058 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1058."
    ::= 1058

sl61UserTrap1059 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1059."
    ::= 1059

sl61UserTrap1060 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1060."
    ::= 1060

sl61UserTrap1061 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1061."
    ::= 1061

sl61UserTrap1062 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1062."
    ::= 1062

sl61UserTrap1063 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1063."
    ::= 1063

sl61UserTrap1064 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1064."
    ::= 1064

sl61UserTrap1065 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1065."
    ::= 1065

sl61UserTrap1066 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1066."
    ::= 1066

sl61UserTrap1067 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1067."
    ::= 1067

sl61UserTrap1068 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1068."
    ::= 1068

sl61UserTrap1069 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1069."
    ::= 1069

sl61UserTrap1070 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1070."
    ::= 1070

sl61UserTrap1071 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1071."
    ::= 1071

sl61UserTrap1072 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1072."
    ::= 1072

sl61UserTrap1073 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1073."
    ::= 1073

sl61UserTrap1074 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1074."
    ::= 1074

sl61UserTrap1075 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1075."
    ::= 1075

sl61UserTrap1076 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1076."
    ::= 1076

sl61UserTrap1077 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1077."
    ::= 1077

sl61UserTrap1078 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1078."
    ::= 1078

sl61UserTrap1079 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1079."
    ::= 1079

sl61UserTrap1080 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1080."
    ::= 1080

sl61UserTrap1081 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1081."
    ::= 1081

sl61UserTrap1082 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1082."
    ::= 1082

sl61UserTrap1083 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1083."
    ::= 1083

sl61UserTrap1084 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1084."
    ::= 1084

sl61UserTrap1085 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1085."
    ::= 1085

sl61UserTrap1086 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1086."
    ::= 1086

sl61UserTrap1087 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1087."
    ::= 1087

sl61UserTrap1088 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1088."
    ::= 1088

sl61UserTrap1089 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1089."
    ::= 1089

sl61UserTrap1090 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1090."
    ::= 1090

sl61UserTrap1091 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1091."
    ::= 1091

sl61UserTrap1092 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1092."
    ::= 1092

sl61UserTrap1093 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1093."
    ::= 1093

sl61UserTrap1094 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1094."
    ::= 1094

sl61UserTrap1095 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1095."
    ::= 1095

sl61UserTrap1096 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1096."
    ::= 1096

sl61UserTrap1097 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1097."
    ::= 1097

sl61UserTrap1098 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1098."
    ::= 1098

sl61UserTrap1099 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1099."
    ::= 1099

sl61UserTrap1100 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1100."
    ::= 1100

sl61UserTrap1101 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1101."
    ::= 1101

sl61UserTrap1102 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1102."
    ::= 1102

sl61UserTrap1103 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1103."
    ::= 1103

sl61UserTrap1104 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1104."
    ::= 1104

sl61UserTrap1105 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1105."
    ::= 1105

sl61UserTrap1106 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1106."
    ::= 1106

sl61UserTrap1107 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1107."
    ::= 1107

sl61UserTrap1108 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1108."
    ::= 1108

sl61UserTrap1109 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1109."
    ::= 1109

sl61UserTrap1110 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1110."
    ::= 1110

sl61UserTrap1111 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1111."
    ::= 1111

sl61UserTrap1112 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1112."
    ::= 1112

sl61UserTrap1113 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1113."
    ::= 1113

sl61UserTrap1114 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1114."
    ::= 1114

sl61UserTrap1115 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1115."
    ::= 1115

sl61UserTrap1116 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1116."
    ::= 1116

sl61UserTrap1117 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1117."
    ::= 1117

sl61UserTrap1118 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1118."
    ::= 1118

sl61UserTrap1119 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1119."
    ::= 1119

sl61UserTrap1120 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1120."
    ::= 1120

sl61UserTrap1121 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1121."
    ::= 1121

sl61UserTrap1122 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1122."
    ::= 1122

sl61UserTrap1123 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1123."
    ::= 1123

sl61UserTrap1124 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1124."
    ::= 1124

sl61UserTrap1125 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1125."
    ::= 1125

sl61UserTrap1126 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1126."
    ::= 1126

sl61UserTrap1127 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1127."
    ::= 1127

sl61UserTrap1128 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1128."
    ::= 1128

sl61UserTrap1129 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1129."
    ::= 1129

sl61UserTrap1130 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1130."
    ::= 1130

sl61UserTrap1131 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1131."
    ::= 1131

sl61UserTrap1132 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1132."
    ::= 1132

sl61UserTrap1133 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1133."
    ::= 1133

sl61UserTrap1134 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1134."
    ::= 1134

sl61UserTrap1135 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1135."
    ::= 1135

sl61UserTrap1136 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1136."
    ::= 1136

sl61UserTrap1137 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1137."
    ::= 1137

sl61UserTrap1138 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1138."
    ::= 1138

sl61UserTrap1139 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1139."
    ::= 1139

sl61UserTrap1140 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1140."
    ::= 1140

sl61UserTrap1141 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1141."
    ::= 1141

sl61UserTrap1142 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1142."
    ::= 1142

sl61UserTrap1143 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1143."
    ::= 1143

sl61UserTrap1144 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1144."
    ::= 1144

sl61UserTrap1145 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1145."
    ::= 1145

sl61UserTrap1146 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1146."
    ::= 1146

sl61UserTrap1147 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1147."
    ::= 1147

sl61UserTrap1148 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1148."
    ::= 1148

sl61UserTrap1149 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1149."
    ::= 1149

sl61UserTrap1150 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1150."
    ::= 1150

sl61UserTrap1151 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1151."
    ::= 1151

sl61UserTrap1152 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1152."
    ::= 1152

sl61UserTrap1153 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1153."
    ::= 1153

sl61UserTrap1154 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1154."
    ::= 1154

sl61UserTrap1155 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1155."
    ::= 1155

sl61UserTrap1156 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1156."
    ::= 1156

sl61UserTrap1157 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1157."
    ::= 1157

sl61UserTrap1158 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1158."
    ::= 1158

sl61UserTrap1159 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1159."
    ::= 1159

sl61UserTrap1160 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1160."
    ::= 1160

sl61UserTrap1161 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1161."
    ::= 1161

sl61UserTrap1162 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1162."
    ::= 1162

sl61UserTrap1163 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1163."
    ::= 1163

sl61UserTrap1164 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1164."
    ::= 1164

sl61UserTrap1165 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1165."
    ::= 1165

sl61UserTrap1166 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1166."
    ::= 1166

sl61UserTrap1167 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1167."
    ::= 1167

sl61UserTrap1168 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1168."
    ::= 1168

sl61UserTrap1169 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1169."
    ::= 1169

sl61UserTrap1170 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1170."
    ::= 1170

sl61UserTrap1171 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1171."
    ::= 1171

sl61UserTrap1172 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1172."
    ::= 1172

sl61UserTrap1173 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1173."
    ::= 1173

sl61UserTrap1174 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1174."
    ::= 1174

sl61UserTrap1175 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1175."
    ::= 1175

sl61UserTrap1176 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1176."
    ::= 1176

sl61UserTrap1177 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1177."
    ::= 1177

sl61UserTrap1178 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1178."
    ::= 1178

sl61UserTrap1179 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1179."
    ::= 1179

sl61UserTrap1180 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1180."
    ::= 1180

sl61UserTrap1181 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1181."
    ::= 1181

sl61UserTrap1182 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1182."
    ::= 1182

sl61UserTrap1183 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1183."
    ::= 1183

sl61UserTrap1184 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1184."
    ::= 1184

sl61UserTrap1185 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1185."
    ::= 1185

sl61UserTrap1186 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1186."
    ::= 1186

sl61UserTrap1187 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1187."
    ::= 1187

sl61UserTrap1188 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1188."
    ::= 1188

sl61UserTrap1189 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1189."
    ::= 1189

sl61UserTrap1190 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1190."
    ::= 1190

sl61UserTrap1191 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1191."
    ::= 1191

sl61UserTrap1192 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1192."
    ::= 1192

sl61UserTrap1193 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1193."
    ::= 1193

sl61UserTrap1194 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1194."
    ::= 1194

sl61UserTrap1195 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1195."
    ::= 1195

sl61UserTrap1196 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1196."
    ::= 1196

sl61UserTrap1197 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1197."
    ::= 1197

sl61UserTrap1198 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1198."
    ::= 1198

sl61UserTrap1199 TRAP-TYPE
    ENTERPRISE sl61
    VARIABLES { siteID, esIndex, esName, trapEventTypeNumber,
        trapEventTypeName, esIndexPoint, esPointName, esID,
        clock, trapIncludedValue, trapIncludedString,
        trapEventClassNumber, trapEventClassName }
    DESCRIPTION
        "This user-defined trap is issued when an event happens that causes a
        trap with specific trap type 1199."
    ::= 1199


END
