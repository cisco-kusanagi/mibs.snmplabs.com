--
-- This SMIv2 module has been generated by smidump 0.2-cvs. Do not edit.
--

SONUS-PERFORMANCE-STATISTICS-MIB DEFINITIONS ::= BEGIN

IMPORTS
    PerfCurrentCount, PerfIntervalCount
        FROM PerfHist-TC-MIB
    Integer32, MODULE-IDENTITY, OBJECT-TYPE, TimeTicks
        FROM SNMPv2-SMI
    TruthValue
        FROM SNMPv2-TC
    sonusResourcesMIBs
        FROM SONUS-SMI;

sonusPerformanceStatisticsMIB MODULE-IDENTITY
    LAST-UPDATED    "200008280000Z"
    ORGANIZATION    
            "Sonus Networks, Inc."
    CONTACT-INFO    
            "   Customer Support    
             Sonus Networks, Inc,
             5 carlisle Road
             Westford, MA 01886
             USA
             
             Tel: 978-692-8999
             Fax: 978-392-9118
             E-mail: cs.snmp@sonusnet.com"
    DESCRIPTION     
            "The MIB module to describe
             Sonus Performance Statistics objects."
    ::= { sonusResourcesMIBs 6 }


sonusPerformanceStatisticsObjects OBJECT IDENTIFIER
    ::= { sonusPerformanceStatisticsMIB 1 }

sonusTrunkGroup OBJECT IDENTIFIER
    ::= { sonusPerformanceStatisticsObjects 1 }

sonusTrunkGroupIntervalSize OBJECT-TYPE
    SYNTAX          Integer32 (5..1440)
    MAX-ACCESS      read-only
    STATUS          current
    DESCRIPTION     
            "The size of the intervals in minutes for the Sonus
             Trunk Group interval table."
    DEFVAL          { 15 }
    ::= { sonusTrunkGroup 1 }

sonusTrunkGroupNumberOfIntervals OBJECT-TYPE
    SYNTAX          Integer32 (1..288)
    MAX-ACCESS      read-only
    STATUS          current
    DESCRIPTION     
            "The number of intervals for the Sonus Trunk Group 
             interval table. The sonusTrunkGroupIntervalSize times
             the sonusTrunkGroupNumberOfIntervals must be <= 1440."
    DEFVAL          { 4 }
    ::= { sonusTrunkGroup 2 }

sonusTrunkGroupCurrentTable OBJECT-TYPE
    SYNTAX          SEQUENCE OF SonusTrunkGroupCurrentEntry
    MAX-ACCESS      not-accessible
    STATUS          current
    DESCRIPTION     
            "The Sonus Trunk Group Current table."
    ::= { sonusTrunkGroup 3 }

sonusTrunkGroupCurrentEntry OBJECT-TYPE
    SYNTAX          SonusTrunkGroupCurrentEntry
    MAX-ACCESS      not-accessible
    STATUS          current
    DESCRIPTION     
            "An entry in the Sonus Trunk Group Current table."
    INDEX           { sonusTrunkGroupCurrentIndex }
    ::= { sonusTrunkGroupCurrentTable 1 }

SonusTrunkGroupCurrentEntry ::=
    SEQUENCE {
        sonusTrunkGroupCurrentIndex     Integer32,
        sonusTrunkGroupCurrentInUsage   PerfCurrentCount,
        sonusTrunkGroupCurrentOutUsage  PerfCurrentCount,
        sonusTrunkGroupCurrentInCalls   PerfCurrentCount,
        sonusTrunkGroupCurrentOutCalls  PerfCurrentCount,
        sonusTrunkGroupCurrentInCallAttempts    PerfCurrentCount,
        sonusTrunkGroupCurrentOutCallAttempts     PerfCurrentCount,
        sonusTrunkGroupCurrentMaxCompletedCalls       PerfCurrentCount,
        sonusTrunkGroupCurrentCallSetupTime   PerfCurrentCount,
        sonusTrunkGroupCurrentCallSetups PerfCurrentCount,
        sonusTrunkGroupCurrentInCallFailNoRoutes        PerfCurrentCount,
        sonusTrunkGroupCurrentInCallFailNoResources           PerfCurrentCount,
        sonusTrunkGroupCurrentInCallFailNoService         PerfCurrentCount,
        sonusTrunkGroupCurrentInCallFailInvalidCall           PerfCurrentCount,
        sonusTrunkGroupCurrentInCallFailNetworkFailure              PerfCurrentCount,
        sonusTrunkGroupCurrentInCallFailProtocolError             PerfCurrentCount,
        sonusTrunkGroupCurrentInCallFailUnspecified           PerfCurrentCount,
        sonusTrunkGroupCurrentOutCallFailNoRoutes         PerfCurrentCount,
        sonusTrunkGroupCurrentOutCallFailNoResources            PerfCurrentCount,
        sonusTrunkGroupCurrentOutCallFailNoService          PerfCurrentCount,
        sonusTrunkGroupCurrentOutCallFailInvalidCall            PerfCurrentCount,
        sonusTrunkGroupCurrentOutCallFailNetworkFailure               PerfCurrentCount,
        sonusTrunkGroupCurrentOutCallFailProtocolError              PerfCurrentCount,
        sonusTrunkGroupCurrentOutCallFailUnspecified            PerfCurrentCount
    }

sonusTrunkGroupCurrentIndex OBJECT-TYPE
    SYNTAX          Integer32
    MAX-ACCESS      not-accessible
    STATUS          current
    DESCRIPTION     
            "The index into the sonusTgTable."
    ::= { sonusTrunkGroupCurrentEntry 1 }

sonusTrunkGroupCurrentInUsage OBJECT-TYPE
    SYNTAX          PerfCurrentCount
    MAX-ACCESS      read-only
    STATUS          current
    DESCRIPTION     
            "The current usage in the inbound direction for this trunk group. 
             Usage is defined as the time a trunk is seized to the time it 
             is released."
    ::= { sonusTrunkGroupCurrentEntry 2 }

sonusTrunkGroupCurrentOutUsage OBJECT-TYPE
    SYNTAX          PerfCurrentCount
    MAX-ACCESS      read-only
    STATUS          current
    DESCRIPTION     
            "The current usage in the outbound direction for this trunk group. 
             Usage is defined as the time a trunk is seized to the time it 
             is released."
    ::= { sonusTrunkGroupCurrentEntry 3 }

sonusTrunkGroupCurrentInCalls OBJECT-TYPE
    SYNTAX          PerfCurrentCount
    MAX-ACCESS      read-only
    STATUS          current
    DESCRIPTION     
            "The current number of completed inbound calls on this trunk
             group."
    ::= { sonusTrunkGroupCurrentEntry 4 }

sonusTrunkGroupCurrentOutCalls OBJECT-TYPE
    SYNTAX          PerfCurrentCount
    MAX-ACCESS      read-only
    STATUS          current
    DESCRIPTION     
            "The current number of completed outbound calls on this trunk
             group."
    ::= { sonusTrunkGroupCurrentEntry 5 }

sonusTrunkGroupCurrentInCallAttempts OBJECT-TYPE
    SYNTAX          PerfCurrentCount
    MAX-ACCESS      read-only
    STATUS          current
    DESCRIPTION     
            "The current number of inbound call attempts on this trunk
             group."
    ::= { sonusTrunkGroupCurrentEntry 6 }

sonusTrunkGroupCurrentOutCallAttempts OBJECT-TYPE
    SYNTAX          PerfCurrentCount
    MAX-ACCESS      read-only
    STATUS          current
    DESCRIPTION     
            "The current number of outbound call attempts on this trunk
             group."
    ::= { sonusTrunkGroupCurrentEntry 7 }

sonusTrunkGroupCurrentMaxCompletedCalls OBJECT-TYPE
    SYNTAX          PerfCurrentCount
    MAX-ACCESS      read-only
    STATUS          current
    DESCRIPTION     
            "The current maximum number of completed calls
             in the inbound and outbound direction for this trunk group."
    ::= { sonusTrunkGroupCurrentEntry 8 }

sonusTrunkGroupCurrentCallSetupTime OBJECT-TYPE
    SYNTAX          PerfCurrentCount
    MAX-ACCESS      read-only
    STATUS          current
    DESCRIPTION     
            "The current total call setup time for all completed calls
             in the inbound and outbound directions for this trunk group
             measured in hundredths of a second.  This object can be used 
             as the numerator for calculating average call setup time."
    ::= { sonusTrunkGroupCurrentEntry 9 }

sonusTrunkGroupCurrentCallSetups OBJECT-TYPE
    SYNTAX          PerfCurrentCount
    MAX-ACCESS      read-only
    STATUS          current
    DESCRIPTION     
            "The current total number of calls setup but not necessarily
             completed in the inbound and outbound directions for 
             this trunk group.  This object can be used as the denominator
             for calculating average call setup time."
    ::= { sonusTrunkGroupCurrentEntry 10 }

sonusTrunkGroupCurrentInCallFailNoRoutes OBJECT-TYPE
    SYNTAX          PerfCurrentCount
    MAX-ACCESS      read-only
    STATUS          current
    DESCRIPTION     
            "The current number of inbound failed calls because there was no
             route available for this trunk group."
    ::= { sonusTrunkGroupCurrentEntry 11 }

sonusTrunkGroupCurrentInCallFailNoResources OBJECT-TYPE
    SYNTAX          PerfCurrentCount
    MAX-ACCESS      read-only
    STATUS          current
    DESCRIPTION     
            "The current number of inbound failed calls because there was an
             unavailable resource for this trunk group."
    ::= { sonusTrunkGroupCurrentEntry 12 }

sonusTrunkGroupCurrentInCallFailNoService OBJECT-TYPE
    SYNTAX          PerfCurrentCount
    MAX-ACCESS      read-only
    STATUS          current
    DESCRIPTION     
            "The current number of inbound failed calls because there was an
             unavailable service for this trunk group."
    ::= { sonusTrunkGroupCurrentEntry 13 }

sonusTrunkGroupCurrentInCallFailInvalidCall OBJECT-TYPE
    SYNTAX          PerfCurrentCount
    MAX-ACCESS      read-only
    STATUS          current
    DESCRIPTION     
            "The current number of inbound failed calls because there was an
             invalid call attempt for this trunk group."
    ::= { sonusTrunkGroupCurrentEntry 14 }

sonusTrunkGroupCurrentInCallFailNetworkFailure OBJECT-TYPE
    SYNTAX          PerfCurrentCount
    MAX-ACCESS      read-only
    STATUS          current
    DESCRIPTION     
            "The current number of inbound failed calls because there was a
             network failure for this trunk group."
    ::= { sonusTrunkGroupCurrentEntry 15 }

sonusTrunkGroupCurrentInCallFailProtocolError OBJECT-TYPE
    SYNTAX          PerfCurrentCount
    MAX-ACCESS      read-only
    STATUS          current
    DESCRIPTION     
            "The current number of inbound failed calls because there was a
             protocol error for this trunk group."
    ::= { sonusTrunkGroupCurrentEntry 16 }

sonusTrunkGroupCurrentInCallFailUnspecified OBJECT-TYPE
    SYNTAX          PerfCurrentCount
    MAX-ACCESS      read-only
    STATUS          current
    DESCRIPTION     
            "The current number of inbound failed calls for an unspecified
             reason for this trunk group."
    ::= { sonusTrunkGroupCurrentEntry 17 }

sonusTrunkGroupCurrentOutCallFailNoRoutes OBJECT-TYPE
    SYNTAX          PerfCurrentCount
    MAX-ACCESS      read-only
    STATUS          current
    DESCRIPTION     
            "The current number of outbound failed calls because there was no
             route available for this trunk group."
    ::= { sonusTrunkGroupCurrentEntry 18 }

sonusTrunkGroupCurrentOutCallFailNoResources OBJECT-TYPE
    SYNTAX          PerfCurrentCount
    MAX-ACCESS      read-only
    STATUS          current
    DESCRIPTION     
            "The current number of outbound failed calls because there was an
             unavailable resource for this trunk group."
    ::= { sonusTrunkGroupCurrentEntry 19 }

sonusTrunkGroupCurrentOutCallFailNoService OBJECT-TYPE
    SYNTAX          PerfCurrentCount
    MAX-ACCESS      read-only
    STATUS          current
    DESCRIPTION     
            "The current number of outbound failed calls because there was an
             unavailable service for this trunk group."
    ::= { sonusTrunkGroupCurrentEntry 20 }

sonusTrunkGroupCurrentOutCallFailInvalidCall OBJECT-TYPE
    SYNTAX          PerfCurrentCount
    MAX-ACCESS      read-only
    STATUS          current
    DESCRIPTION     
            "The current number of outbound failed calls because there was an
             invalid call attempt for this trunk group."
    ::= { sonusTrunkGroupCurrentEntry 21 }

sonusTrunkGroupCurrentOutCallFailNetworkFailure OBJECT-TYPE
    SYNTAX          PerfCurrentCount
    MAX-ACCESS      read-only
    STATUS          current
    DESCRIPTION     
            "The current number of outbound failed calls because there was a
             network failure for this trunk group."
    ::= { sonusTrunkGroupCurrentEntry 22 }

sonusTrunkGroupCurrentOutCallFailProtocolError OBJECT-TYPE
    SYNTAX          PerfCurrentCount
    MAX-ACCESS      read-only
    STATUS          current
    DESCRIPTION     
            "The current number of outbound failed calls because there was a
             protocol error for this trunk group."
    ::= { sonusTrunkGroupCurrentEntry 23 }

sonusTrunkGroupCurrentOutCallFailUnspecified OBJECT-TYPE
    SYNTAX          PerfCurrentCount
    MAX-ACCESS      read-only
    STATUS          current
    DESCRIPTION     
            "The current number of outbound failed calls for an unspecified
             reason for this trunk group."
    ::= { sonusTrunkGroupCurrentEntry 24 }

sonusTrunkGroupIntervalTable OBJECT-TYPE
    SYNTAX          SEQUENCE OF SonusTrunkGroupIntervalEntry
    MAX-ACCESS      not-accessible
    STATUS          current
    DESCRIPTION     
            "The Sonus Trunk Group Interval table."
    ::= { sonusTrunkGroup 4 }

sonusTrunkGroupIntervalEntry OBJECT-TYPE
    SYNTAX          SonusTrunkGroupIntervalEntry
    MAX-ACCESS      not-accessible
    STATUS          current
    DESCRIPTION     
            "An entry in the Sonus Trunk Group Interval table."
    INDEX           { sonusTrunkGroupIntervalIndex, 
                      sonusTrunkGroupIntervalNumber }
    ::= { sonusTrunkGroupIntervalTable 1 }

SonusTrunkGroupIntervalEntry ::=
    SEQUENCE {
        sonusTrunkGroupIntervalIndex    Integer32,
        sonusTrunkGroupIntervalNumber   Integer32,
        sonusTrunkGroupIntervalInUsage  PerfIntervalCount,
        sonusTrunkGroupIntervalOutUsage PerfIntervalCount,
        sonusTrunkGroupIntervalInCalls  PerfIntervalCount,
        sonusTrunkGroupIntervalOutCalls PerfIntervalCount,
        sonusTrunkGroupIntervalInCallAttempts     PerfIntervalCount,
        sonusTrunkGroupIntervalOutCallAttempts      PerfIntervalCount,
        sonusTrunkGroupIntervalMaxCompletedCalls        PerfIntervalCount,
        sonusTrunkGroupIntervalCallSetupTime    PerfIntervalCount,
        sonusTrunkGroupIntervalCallSetups PerfIntervalCount,
        sonusTrunkGroupIntervalInCallFailNoRoutes         PerfIntervalCount,
        sonusTrunkGroupIntervalInCallFailNoResources            PerfIntervalCount,
        sonusTrunkGroupIntervalInCallFailNoService          PerfIntervalCount,
        sonusTrunkGroupIntervalInCallFailInvalidCall            PerfIntervalCount,
        sonusTrunkGroupIntervalInCallFailNetworkFailure               PerfIntervalCount,
        sonusTrunkGroupIntervalInCallFailProtocolError              PerfIntervalCount,
        sonusTrunkGroupIntervalInCallFailUnspecified            PerfIntervalCount,
        sonusTrunkGroupIntervalOutCallFailNoRoutes          PerfIntervalCount,
        sonusTrunkGroupIntervalOutCallFailNoResources             PerfIntervalCount,
        sonusTrunkGroupIntervalOutCallFailNoService           PerfIntervalCount,
        sonusTrunkGroupIntervalOutCallFailInvalidCall             PerfIntervalCount,
        sonusTrunkGroupIntervalOutCallFailNetworkFailure                PerfIntervalCount,
        sonusTrunkGroupIntervalOutCallFailProtocolError               PerfIntervalCount,
        sonusTrunkGroupIntervalOutCallFailUnspecified             PerfIntervalCount,
        sonusTrunkGroupIntervalTime     TimeTicks,
        sonusTrunkGroupIntervalValidData TruthValue
    }

sonusTrunkGroupIntervalIndex OBJECT-TYPE
    SYNTAX          Integer32
    MAX-ACCESS      not-accessible
    STATUS          current
    DESCRIPTION     
            "The index into the sonusTgTable."
    ::= { sonusTrunkGroupIntervalEntry 1 }

sonusTrunkGroupIntervalNumber OBJECT-TYPE
    SYNTAX          Integer32 (1..288)
    MAX-ACCESS      not-accessible
    STATUS          current
    DESCRIPTION     
            "A number between 1 and 288, which identifies the
             interval for which the set of statistics is available.
             The interval identified by 1 is the most recently
             completed interval,
             and the interval identified
             by N is the interval immediately preceding the
             one identified
             by N-1."
    ::= { sonusTrunkGroupIntervalEntry 2 }

sonusTrunkGroupIntervalInUsage OBJECT-TYPE
    SYNTAX          PerfIntervalCount
    MAX-ACCESS      read-only
    STATUS          current
    DESCRIPTION     
            "The usage in the inbound direction for this trunk group for
             the specified interval.
             Usage is defined as the time a trunk is seized to the time it 
             is released."
    ::= { sonusTrunkGroupIntervalEntry 3 }

sonusTrunkGroupIntervalOutUsage OBJECT-TYPE
    SYNTAX          PerfIntervalCount
    MAX-ACCESS      read-only
    STATUS          current
    DESCRIPTION     
            "The usage in the outbound direction for this trunk group for
             the specified interval. 
             Usage is defined as the time a trunk is seized to the time it 
             is released."
    ::= { sonusTrunkGroupIntervalEntry 4 }

sonusTrunkGroupIntervalInCalls OBJECT-TYPE
    SYNTAX          PerfIntervalCount
    MAX-ACCESS      read-only
    STATUS          current
    DESCRIPTION     
            "The number of completed inbound calls on this trunk
             group for the specified interval."
    ::= { sonusTrunkGroupIntervalEntry 5 }

sonusTrunkGroupIntervalOutCalls OBJECT-TYPE
    SYNTAX          PerfIntervalCount
    MAX-ACCESS      read-only
    STATUS          current
    DESCRIPTION     
            "The number of completed outbound calls on this trunk
             group for the specified interval."
    ::= { sonusTrunkGroupIntervalEntry 6 }

sonusTrunkGroupIntervalInCallAttempts OBJECT-TYPE
    SYNTAX          PerfIntervalCount
    MAX-ACCESS      read-only
    STATUS          current
    DESCRIPTION     
            "The number of inbound call attempts on this trunk
             group for the specified interval."
    ::= { sonusTrunkGroupIntervalEntry 7 }

sonusTrunkGroupIntervalOutCallAttempts OBJECT-TYPE
    SYNTAX          PerfIntervalCount
    MAX-ACCESS      read-only
    STATUS          current
    DESCRIPTION     
            "The number of outbound call attempts on this trunk
             group for the specified interval."
    ::= { sonusTrunkGroupIntervalEntry 8 }

sonusTrunkGroupIntervalMaxCompletedCalls OBJECT-TYPE
    SYNTAX          PerfIntervalCount
    MAX-ACCESS      read-only
    STATUS          current
    DESCRIPTION     
            "The maximum number of completed calls
             in the inbound and outbound direction for this trunk group
             for the specified interval."
    ::= { sonusTrunkGroupIntervalEntry 9 }

sonusTrunkGroupIntervalCallSetupTime OBJECT-TYPE
    SYNTAX          PerfIntervalCount
    MAX-ACCESS      read-only
    STATUS          current
    DESCRIPTION     
            "The total call setup time for all completed calls
             in the inbound and outbound directions for this trunk group
             for the specified interval measured in hundredths of a second.
             This object can be used as the numerator for calculating 
             average call setup time."
    ::= { sonusTrunkGroupIntervalEntry 10 }

sonusTrunkGroupIntervalCallSetups OBJECT-TYPE
    SYNTAX          PerfIntervalCount
    MAX-ACCESS      read-only
    STATUS          current
    DESCRIPTION     
            "The total number of calls setup but not necessarily
             completed in the inbound and outbound directions for 
             this trunk group for the specified interval.  This object 
             can be used as the denominator for calculating average 
             call setup time."
    ::= { sonusTrunkGroupIntervalEntry 11 }

sonusTrunkGroupIntervalInCallFailNoRoutes OBJECT-TYPE
    SYNTAX          PerfIntervalCount
    MAX-ACCESS      read-only
    STATUS          current
    DESCRIPTION     
            "The number of inbound failed calls because there was no
             route available for this trunk group for the specified 
             interval."
    ::= { sonusTrunkGroupIntervalEntry 12 }

sonusTrunkGroupIntervalInCallFailNoResources OBJECT-TYPE
    SYNTAX          PerfIntervalCount
    MAX-ACCESS      read-only
    STATUS          current
    DESCRIPTION     
            "The number of inbound failed calls because there was an
             unavailable resource for this trunk group for the 
             specified interval."
    ::= { sonusTrunkGroupIntervalEntry 13 }

sonusTrunkGroupIntervalInCallFailNoService OBJECT-TYPE
    SYNTAX          PerfIntervalCount
    MAX-ACCESS      read-only
    STATUS          current
    DESCRIPTION     
            "The number of inbound failed calls because there was an
             unavailable service for this trunk group for the 
             specified interval."
    ::= { sonusTrunkGroupIntervalEntry 14 }

sonusTrunkGroupIntervalInCallFailInvalidCall OBJECT-TYPE
    SYNTAX          PerfIntervalCount
    MAX-ACCESS      read-only
    STATUS          current
    DESCRIPTION     
            "The number of inbound failed calls because there was an
             invalid call attempt for this trunk group for the 
             specified interval."
    ::= { sonusTrunkGroupIntervalEntry 15 }

sonusTrunkGroupIntervalInCallFailNetworkFailure OBJECT-TYPE
    SYNTAX          PerfIntervalCount
    MAX-ACCESS      read-only
    STATUS          current
    DESCRIPTION     
            "The number of inbound failed calls because there was a
             network failure for this trunk group for the specified 
             interval."
    ::= { sonusTrunkGroupIntervalEntry 16 }

sonusTrunkGroupIntervalInCallFailProtocolError OBJECT-TYPE
    SYNTAX          PerfIntervalCount
    MAX-ACCESS      read-only
    STATUS          current
    DESCRIPTION     
            "The number of inbound failed calls because there was a
             protocol error for this trunk group for the specified 
             interval."
    ::= { sonusTrunkGroupIntervalEntry 17 }

sonusTrunkGroupIntervalInCallFailUnspecified OBJECT-TYPE
    SYNTAX          PerfIntervalCount
    MAX-ACCESS      read-only
    STATUS          current
    DESCRIPTION     
            "The number of inbound failed calls for an unspecified
             reason for this trunk group for the specified interval."
    ::= { sonusTrunkGroupIntervalEntry 18 }

sonusTrunkGroupIntervalOutCallFailNoRoutes OBJECT-TYPE
    SYNTAX          PerfIntervalCount
    MAX-ACCESS      read-only
    STATUS          current
    DESCRIPTION     
            "The number of outbound failed calls because there was no
             route available for this trunk group for the specified 
             interval."
    ::= { sonusTrunkGroupIntervalEntry 19 }

sonusTrunkGroupIntervalOutCallFailNoResources OBJECT-TYPE
    SYNTAX          PerfIntervalCount
    MAX-ACCESS      read-only
    STATUS          current
    DESCRIPTION     
            "The number of outbound failed calls because there was an
             unavailable resource for this trunk group for the 
             specified interval."
    ::= { sonusTrunkGroupIntervalEntry 20 }

sonusTrunkGroupIntervalOutCallFailNoService OBJECT-TYPE
    SYNTAX          PerfIntervalCount
    MAX-ACCESS      read-only
    STATUS          current
    DESCRIPTION     
            "The number of outbound failed calls because there was an
             unavailable service for this trunk group for the 
             specified interval."
    ::= { sonusTrunkGroupIntervalEntry 21 }

sonusTrunkGroupIntervalOutCallFailInvalidCall OBJECT-TYPE
    SYNTAX          PerfIntervalCount
    MAX-ACCESS      read-only
    STATUS          current
    DESCRIPTION     
            "The number of outbound failed calls because there was an
             invalid call attempt for this trunk group for the 
             specified interval."
    ::= { sonusTrunkGroupIntervalEntry 22 }

sonusTrunkGroupIntervalOutCallFailNetworkFailure OBJECT-TYPE
    SYNTAX          PerfIntervalCount
    MAX-ACCESS      read-only
    STATUS          current
    DESCRIPTION     
            "The number of outbound failed calls because there was a
             network failure for this trunk group for the specified 
             interval."
    ::= { sonusTrunkGroupIntervalEntry 23 }

sonusTrunkGroupIntervalOutCallFailProtocolError OBJECT-TYPE
    SYNTAX          PerfIntervalCount
    MAX-ACCESS      read-only
    STATUS          current
    DESCRIPTION     
            "The number of outbound failed calls because there was a
             protocol error for this trunk group for the specified 
             interval."
    ::= { sonusTrunkGroupIntervalEntry 24 }

sonusTrunkGroupIntervalOutCallFailUnspecified OBJECT-TYPE
    SYNTAX          PerfIntervalCount
    MAX-ACCESS      read-only
    STATUS          current
    DESCRIPTION     
            "The number of outbound failed calls for an unspecified
             reason for this trunk group for the specified interval."
    ::= { sonusTrunkGroupIntervalEntry 25 }

sonusTrunkGroupIntervalTime OBJECT-TYPE
    SYNTAX          TimeTicks
    MAX-ACCESS      read-only
    STATUS          current
    DESCRIPTION     
            "This variable contains the end of interval time
             stamp for the specified interval."
    ::= { sonusTrunkGroupIntervalEntry 26 }

sonusTrunkGroupIntervalValidData OBJECT-TYPE
    SYNTAX          TruthValue
    MAX-ACCESS      read-only
    STATUS          current
    DESCRIPTION     
            "This variable indicates if the data for this
             interval is valid."
    ::= { sonusTrunkGroupIntervalEntry 27 }

END -- end of module SONUS-PERFORMANCE-STATISTICS-MIB.
