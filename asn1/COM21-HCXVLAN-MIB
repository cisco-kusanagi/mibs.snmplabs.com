--
--  Copyright 1996, Com21 Inc.  All Rights Reserved.
--
 
COM21-HCXVLAN-MIB DEFINITIONS ::= BEGIN
  IMPORTS
        MODULE-IDENTITY, OBJECT-TYPE, NOTIFICATION-TYPE, Integer32,
        IpAddress, Gauge32, TimeTicks
            FROM SNMPv2-SMI
        DisplayString, MacAddress
            FROM SNMPv2-TC
        com21, com21Hcx
            FROM COM21-HCX-MIB
        hcxAlmSeverity, hcxEventLogTime
            FROM COM21-HCXALM-MIB;
 
 
        com21HcxVlan MODULE-IDENTITY
                LAST-UPDATED "9701080000Z"
                ORGANIZATION "Com21, Inc."
                CONTACT-INFO
                "       Network Management
                                Postal: Paul Gordon
                                Com21, Inc.
                                750 Tasman Drive
                                Milpitas, California 95035
                                USA
                                Tel: +1 408 953 9100
                                Fax: +1 408 953 9299
                                E-mail: pgordon@com21.com"

                DESCRIPTION
                        "This is the Com21 ComController Vlan
                         MIB module. COM21 Part# 005-0025-00"
                ::= { com21Hcx 80 }
 


        com21HcxVlanCtrlGroup      OBJECT IDENTIFIER ::= {com21Hcx 81}
        com21HcxVlanStatsGroup     OBJECT IDENTIFIER ::= {com21Hcx 82}
        com21HcxOc3VlanStatsGroup  OBJECT IDENTIFIER ::= {com21Hcx 83}

        PrimServiceState ::= INTEGER { is(1), oos(2) }
        Com21RowStatus   ::= INTEGER { active(1),
                                       create(2),
                                       destroy(3),
                                       deactive(4) }

        -- -- -- -- -- -- -- -- -- -- -- -- -- -- -- -- -- -- -- -- -- -- -- --
        -- -- -- -- -- -- -- -- -- -- -- -- -- -- -- -- -- -- -- -- -- -- -- --
        --
        -- COM21 ComController Enterprise MIB
        --
        -- This MIB contains SNMP Groups and Attributes definitions for COM21
        -- specific management.
        -- Also supported by the ComController shall be the MIB II for the
        -- SNMP interface and the MIB II Interfaces Group for both the
        -- ComController and ComPort Ethernet interfaces.
        -- This Enterprise MIB contains many elements of the ATM UNI 2.1 ILMI
        -- MIB. This full MIB is not presently supported by the COM21 equipment
        -- as there are no external UNI interfaces. When this changes then the
        -- full MIB should be supported and the related Enterprise MIB entries
        -- removed.
        --
        --   com21HcxVlanCtrlGroup  - defines all VLAN related
        --                                 management parameters.
        --
        --   com21HcxVlanStatsGroup - this group encapsulates the VLAN
        --                                 based statistics.
        --
        -- -- -- -- -- -- -- -- -- -- -- -- -- -- -- -- -- -- -- -- -- -- -- --
        -- -- -- -- -- -- -- -- -- -- -- -- -- -- -- -- -- -- -- -- -- -- -- --



        -- -- -- -- -- -- -- -- -- -- -- -- -- -- -- -- -- -- -- -- -- -- -- --
        -- -- -- -- -- -- -- -- -- -- -- -- -- -- -- -- -- -- -- -- -- -- -- --
        --
        -- com21HcxVlanCtrlGroup
        --
        -- defines the attributes related to the management of the VLANs
        -- on HCX
        --
        -- -- -- -- -- -- -- -- -- -- -- -- -- -- -- -- -- -- -- -- -- -- -- --
        -- -- -- -- -- -- -- -- -- -- -- -- -- -- -- -- -- -- -- -- -- -- -- --
 
 
        com21HcxVlanCtrlTable OBJECT-TYPE
                SYNTAX SEQUENCE OF HcxVlanCtrlEntry
                MAX-ACCESS not-accessible
                STATUS current
                DESCRIPTION "."
                ::= { com21HcxVlanCtrlGroup 1 }
 
 
        com21HcxVlanCtrlEntry OBJECT-TYPE
                SYNTAX HcxVlanCtrlEntry
                MAX-ACCESS not-accessible
                STATUS current
                DESCRIPTION "."
                INDEX { hcxVlanCtrlId }
                ::= { com21HcxVlanCtrlTable 1 }
 
        HcxVlanCtrlEntry ::= SEQUENCE {
                hcxVlanCtrlId                INTEGER,
		hcxVlanCtrlName		     DisplayString,
                hcxVlanShelf                 INTEGER,
                hcxVlanSlot                  INTEGER,
                hcxVlanCardType              INTEGER,
                hcxVlanPort                  INTEGER,
	        hcxVlanVpi		     INTEGER,
		hcxVlanVci		     INTEGER,	
		hcxVlanRate		     Integer32,	
                hcxVlanPriStatus             Com21RowStatus,
                hcxVlanSecStatus             INTEGER,
                hcxVlanType                  INTEGER,
                hcxVlanPeerToPeerFlag        INTEGER,
                hcxVlanMcastDnstrmRate       INTEGER,
		hcxVlanIpArpFiltEnbl         INTEGER,	
		hcxVlanIpSrcFiltEnbl   	     INTEGER,	
		hcxVlanIpDstFiltEnbl         INTEGER,	
		hcxVlanIpBootpReqFiltEnbl    INTEGER,	
		hcxVlanIpBootpReplyFiltEnbl  INTEGER,	
		hcxVlanIpDhcpSnoopFiltEnbl   INTEGER,
                hcxVlanL2SnapFiltEnbl         INTEGER,
                hcxVlanL2NonSnapFiltEnbl      INTEGER,
                hcxVlanL2EnetFiltEnbl         INTEGER,
                hcxVlanL2ArpIpv4FiltEnbl      INTEGER,
                hcxVlanL2Ipv4FiltEnbl         INTEGER,
                hcxVlanL2Ipv6FiltEnbl         INTEGER,
                hcxVlanL2IpxFiltEnbl          INTEGER,
                hcxVlanL2AppletalkFiltEnbl    INTEGER,
                hcxVlanL2OthersFiltEnbl       INTEGER,
                hcxVlanIpNetbiosFiltEnbl      INTEGER,
		hcxVPNNum		      Integer32}
 
        hcxVlanCtrlId OBJECT-TYPE
                SYNTAX INTEGER (1..64)
                MAX-ACCESS read-only
                STATUS current
                DESCRIPTION "
                        Specifies the associated Vlan Id."
                ::= { com21HcxVlanCtrlEntry 1 }

        hcxVlanCtrlName OBJECT-TYPE
                SYNTAX DisplayString (SIZE (32))
                MAX-ACCESS read-write
                STATUS current
                DESCRIPTION "
                        contains a descriptive name for the VLAN."
                ::= { com21HcxVlanCtrlEntry 2 }
 
         hcxVlanShelf OBJECT-TYPE
                SYNTAX INTEGER (1)
                MAX-ACCESS read-write
                STATUS current
                DESCRIPTION "
                        Specifies the Shelf to which the Vlan is attached
                        to. Shelf/Slot/CardType/Port will uniquely identify
                        the port to which this Vlan is attached to"
                ::=  { com21HcxVlanCtrlEntry 3 }
 
         hcxVlanSlot OBJECT-TYPE
                SYNTAX Integer32
                MAX-ACCESS read-write
                STATUS current
                DESCRIPTION "
                        Specifies the Slot to which the Vlan is attached
                        to. Shelf/Slot/CardType/Port will uniquely identify
                        the port to which this Vlan is attached to"
                ::=  { com21HcxVlanCtrlEntry 4 }
 
         hcxVlanCardType OBJECT-TYPE
                SYNTAX INTEGER { tenBaseT (1),
				 onehundredBaseT (2),
				 oc3 (3) }
                MAX-ACCESS read-write
                STATUS current
                DESCRIPTION "
                        Specifies the CardType to which the Vlan is attached
                        to. Shelf/Slot/CardType/Port will uniquely identify
                        the port to which this Vlan is attached to"
                ::=  { com21HcxVlanCtrlEntry 5 }

         hcxVlanPort OBJECT-TYPE
                SYNTAX Integer32
                MAX-ACCESS read-write
                STATUS current
                DESCRIPTION "
                        Specifies the Port to which the Vlan is attached
                        to. Shelf/Slot/CardType/Port will uniquely identify
                        the port to which this Vlan is attached to"
                ::=  { com21HcxVlanCtrlEntry 6 }
 
 
        hcxVlanPriStatus OBJECT-TYPE
                SYNTAX Com21RowStatus
                MAX-ACCESS read-create
                STATUS current
                DESCRIPTION "
                        lets the user Create a Vlan instance. If already
                        created it lets the user Enable, Disable or Delete
                        the Vlan. Note that the VLAN cannot be Enabled or
			Disabled until the attributes hcxVlanShelf,
			hcxVlanSlot, hcxVlanCardType and hcxVlanPort have
			valid values."
                ::=  { com21HcxVlanCtrlEntry 7 }
 
        hcxVlanSecStatus OBJECT-TYPE
                SYNTAX INTEGER { online (1), offline(2) }
                MAX-ACCESS read-only
                STATUS current
                DESCRIPTION "
                        Indicates whether the Vlan is ONLINE or OFFLINE."
                ::=  { com21HcxVlanCtrlEntry 8 }
 
 
        hcxVlanType  OBJECT-TYPE
                SYNTAX INTEGER { internal(1), external(2) }
                MAX-ACCESS read-write
                STATUS current
                DESCRIPTION "
                        Specifies whether the Vlan is an internal Vlan or
                        external Vlan. internal Vlan does not allow traffic
                        to leave the Vlan or enter the Vlan.
                        external Vlan allows traffic in both directions.
                        default is external. Note that this attribute is
			not applicable to 10bT card."
                ::=  { com21HcxVlanCtrlEntry 9 }
 
        hcxVlanPeerToPeerFlag OBJECT-TYPE
                SYNTAX INTEGER { true (1), false (2) }
                MAX-ACCESS read-write
                STATUS current
                DESCRIPTION "
                        Specifies whether STU to STU communication is allowed
                        in the Vlan. If false, STU to STU communication is
                        not allowed and has to go through an external router.
                        If true direct STU to STU communication is allowed
                        without the intervention of an external router. This
                        attribute is not applicable to VLANs on 10bT Card
			and defaults to a read-only value of true.
		        Default for 100bT/OC3 is false. "
                ::=  { com21HcxVlanCtrlEntry 10 }
 
 
        hcxVlanMcastDnstrmRate OBJECT-TYPE
                SYNTAX INTEGER (0..10000000)
                MAX-ACCESS read-write
                STATUS current
                DESCRIPTION "
                        Specifies the downstream multicast rate associated with
                        this Vlan. Defined in bits per second. The multicast
                        rate is ondemand (not guaranteed if enough bandwidth
                        is not available). 0 stops all broadcast forwarding.
                        Default 100000.
                        If a twoWay modem of model CP1000, CP1000A, CP1000B or
                        CP1000C is acquired in the system or a teleRet modem is
                        configured then the multicast rate will be dynamically
                        lowered to not exceed 1000000. Under that condition an
                        attempt to set the rate to greater than 1000000 will be
                        rejected. The rate wil remain at 1000000 even if the
                        condition clears eventually (all the modems of model
                        CP1000, CP1000A, CP1000B or CP1000C get deacquired and
                        no more teleRet modems are configured)."
                ::=  { com21HcxVlanCtrlEntry 11 }
 
        hcxVlanIpArpFiltEnbl OBJECT-TYPE
                SYNTAX INTEGER { true (1), false (2) }
                MAX-ACCESS read-write
                STATUS current
                DESCRIPTION "
                        Specifies whether ARP authentication filtering
                        should be enabled on this VLAN. This filter is
                        applicable to 10BT, 100BT, and OC3 cards.  It
                        filters traffic in the upstream direction.
                        Default is false.  This filter can also be
                        enabled for a specific ComPort via the MIB
                        attribute hcxStuIpArpFiltEnable."
                ::=  { com21HcxVlanCtrlEntry 12 }

        hcxVlanIpSrcFiltEnbl OBJECT-TYPE
                SYNTAX INTEGER { true (1), false (2) }
                MAX-ACCESS read-write
                STATUS current
                DESCRIPTION "
                        Specifies whether IP source address filtering
                        should be enabled on this VLAN. This filter
                        is applicable to 100BT, and OC3 cards.  It
                        is not applicable to 10BT card.  It filters
                        traffic in the upstream direction.  Default
                        is false.  This filter can also be enabled
                        for a specific ComPort via the MIB attribute
                        hcxStuIpSrcFiltEnable."
                ::=  { com21HcxVlanCtrlEntry 13 }

        hcxVlanIpDstFiltEnbl OBJECT-TYPE
                SYNTAX INTEGER { true (1), false (2) }
                MAX-ACCESS read-write
                STATUS current
                DESCRIPTION "
                        Specifies whether IP destination address
                        filtering should be enabled on this VLAN.
                        This filter is applicable to 100BT, and OC3
                        cards.  It is not applicable to to 10BT card.
                        It filters traffic in the upstream direction.
                        Default is false.  This filter can also be
                        enabled for a specific ComPort via the MIB
                        attribute hcxStuIpDstFiltEnable."
                ::=  { com21HcxVlanCtrlEntry 14 }

        hcxVlanIpBootpReqFiltEnbl OBJECT-TYPE
                SYNTAX INTEGER { true (1), false (2) }
                MAX-ACCESS read-write
                STATUS current
                DESCRIPTION "
                        Specifies whether BOOTP requests, or DHCPDISCOVER,
                        or DHCPREQUEST, or DHCPRELEASE packets should be
                        filtered on this VLAN. This filter is applicable
                        to 100BT, and OC3 cards.  It is not applicable to
                        10BT card.  It filters traffic in the downstream
                        direction. Default is true.  This filter cannot
                        be controlled per ComPort."
                ::=  { com21HcxVlanCtrlEntry 15 }

        hcxVlanIpBootpReplyFiltEnbl OBJECT-TYPE
                SYNTAX INTEGER { true (1), false (2) }
                MAX-ACCESS read-write
                STATUS current
                DESCRIPTION "
                        Specifies whether BOOTP replies, or DHCPOFFER,
                        or DHCPACK packets should be filtered on this
                        VLAN. This filter is applicable to 100BT, and
                        OC3 cards.  It it not applicable to 10BT card.
                        It filters traffic in the upstream direction.
                        Default is true.  This filter can also be
                        enabled for a specific ComPort via the MIB
                        attribute hcxStuIpBootpReplyFiltEnbl."
                ::=  { com21HcxVlanCtrlEntry 16 }

        hcxVlanIpDhcpSnoopFiltEnbl OBJECT-TYPE
                SYNTAX INTEGER { true (1), false (2) }
                MAX-ACCESS read-write
                STATUS current
                DESCRIPTION "
                        Specifies whether DHCP snooping should be
                        enabled on this VLAN. This filter is applicable
                        to 100BT, and OC3 cards.  It is not applicable
                        to 10BT card.  It snoops traffic in the downstream
                        direction for DHCPACK packets, and in the upstream
                        direction for DHCPDECLINE or DHCPRELEASE packets.
                        Dynamic IP address assigments thus learned are
                        stored in the valid source IP address table
                        (com21HcxStuSrcIpAddrGroup.) Default is false.
                        This filter can also be enabled for a specific
                        ComPort via the MIB attribute
                        hcxStuIpDhcpSnoopFiltEnbl."
                ::=  { com21HcxVlanCtrlEntry 17 }

        hcxVlanL2SnapFiltEnbl OBJECT-TYPE
                SYNTAX INTEGER { true (1), false (2) }
                MAX-ACCESS read-write
                STATUS current
                DESCRIPTION "
                        Specifies whether SNAP-encoded IEEE 802.3 packets
                        should be filtered on this VLAN. This filter is
                        applicable to 100BT, and OC3 cards.  It is not
                        applicable to 10BT card.  It filters traffic
                        in both upstream and downstream directions.
                        Default is false.  This filter can also be
                        enabled for a specific ComPort via the MIB
                        attribute hcxStuL2SnapFiltEnbl."
                ::=  { com21HcxVlanCtrlEntry 18 }
 
        hcxVlanL2NonSnapFiltEnbl OBJECT-TYPE
                SYNTAX INTEGER { true (1), false (2) }
                MAX-ACCESS read-write
                STATUS current
                DESCRIPTION "
                        Specifies whether non-SNAP-encoded IEEE 802.3
                        packets should be filtered on this VLAN. This
                        filter is applicable to 10BT, 100BT, and OC3
                        cards.  It filters traffic in both upstream
                        and downstream directions.  Default is false.
                        This filter can also be enabled for a specific
                        ComPort via the MIB attribute hcxStuL2NonSnapFiltEnbl."
                ::=  { com21HcxVlanCtrlEntry 19 }
 
        hcxVlanL2EnetFiltEnbl OBJECT-TYPE
                SYNTAX INTEGER { true (1), false (2) }
                MAX-ACCESS read-write
                STATUS deprecated
                DESCRIPTION "
			Specifies whether Ethernet packets should be 
			filtered on this VLAN. This filter is applicable
			to 100BT and OC3 cards. It is not applicable to
			10BT Card. It filters traffic in both upstream
			and downstream directions. Default is false.
			This filter can also be enabled for a specific
			ComPort via the MIB attribute hcxStuL2EnetFiltEnbl."
                ::=  { com21HcxVlanCtrlEntry 20 }
 
        hcxVlanL2ArpIpv4FiltEnbl OBJECT-TYPE
                SYNTAX INTEGER { true (1), false (2) }
                MAX-ACCESS read-write
                STATUS deprecated
                DESCRIPTION "
			Specifies whether ARP packets should be filtered
			on this VLAN. This filter is applicable to 100BT
			and OC3 cards. It is not applicable to 10BT card.
			It filters traffic in both upstream and downstream
			directions. Default is false. This filter can 
			also be enabled for a specific ComPort via the
			MIB attribute hcxStuL2ArpIpv4FiltEnbl."
                ::=  { com21HcxVlanCtrlEntry 21 }
 
        hcxVlanL2Ipv4FiltEnbl OBJECT-TYPE
                SYNTAX INTEGER { true (1), false (2) }
                MAX-ACCESS read-write
                STATUS deprecated
                DESCRIPTION "
			Specifies whether IPv4 packets should be filtered
			on this VLAN. This filter is applicable to 100BT
			and OC3 cards. It is not applicable to 10BT card.
			It filters traffic in both upstream and downstream
			directions. Default is false. This filter can
			also be enabled for a specific ComPort via the
			MIB attribute hcxStuL2Ipv4FiltEnbl."
                ::=  { com21HcxVlanCtrlEntry 22 }
 
        hcxVlanL2Ipv6FiltEnbl OBJECT-TYPE
                SYNTAX INTEGER { true (1), false (2) }
                MAX-ACCESS read-write
                STATUS deprecated
                DESCRIPTION "
			Specifies whether IPv6 packets should be filtered
			on this VLAN. This filter is applicable to 100BT
			and OC3 cards. It is not applicable to 10BT card.
			It filters traffic in both upstream and downstream
			directions. Default is false. This filter can also
			be enabled for a specific ComPort via the MIB
			attribute hcxStuL2Ipv6FiltEnbl."
                ::=  { com21HcxVlanCtrlEntry 23 }

        hcxVlanL2IpxFiltEnbl OBJECT-TYPE
                SYNTAX INTEGER { true (1), false (2) }
                MAX-ACCESS read-write
                STATUS deprecated
                DESCRIPTION "
                        Specifies whether IPX packets should be filtered
                        on this VLAN. This filter is applicable to 100BT
                        and OC3 cards. It is not applicable to 10BT card.
                        It filters traffic in both upstream and downstream
                        directions. Default is false. This filter can also
                        be enabled for a specific ComPort via the MIB
                        attribute hcxStuL2IpxFiltEnbl."
                ::=  { com21HcxVlanCtrlEntry 24 }
 
        hcxVlanL2AppletalkFiltEnbl OBJECT-TYPE
                SYNTAX INTEGER { true (1), false (2) }
                MAX-ACCESS read-write
                STATUS deprecated
                DESCRIPTION "
                        Specifies whether AppleTalk packets should be filtered
                        on this VLAN. This filter is applicable to 100BT
                        and OC3 cards. It is not applicable to 10BT card.
                        It filters traffic in both upstream and downstream
                        directions. Default is false. This filter can also
                        be enabled for a specific ComPort via the MIB
                        attribute hcxStuL2AppletalkFiltEnbl."
                ::=  { com21HcxVlanCtrlEntry 25 }
 
        hcxVlanL2OthersFiltEnbl OBJECT-TYPE
                SYNTAX INTEGER { true (1), false (2) }
                MAX-ACCESS read-write
                STATUS deprecated
                DESCRIPTION "
			Specifies whether all layer 2 packets that are
			none of the above (ARP, IPv4, IPv6, IPX, AppleTalk)
			should be filtered on this VLAN. This filter is
			applicable to 100BT and OC3 cards. It is not applicable
			to 10BT card. It filters traffic in both upstream
			and downstream directions. Default is false.
			This filter can also be enabled for a  specific
			ComPort via the MIB attribute hcxStuL2OthersFiltEnbl."
                ::=  { com21HcxVlanCtrlEntry 26 }
 
        hcxVlanIpNetbiosFiltEnbl OBJECT-TYPE
                SYNTAX INTEGER { true (1), false (2) }
                MAX-ACCESS read-write
                STATUS current
                DESCRIPTION "
                        Specifies whether NetBIOS-over-IP packets
                        should be filtered on this VLAN. This filter
                        is applicable to 100BT and OC3 cards.  It is
                        not applicable to 10BT card.  It filters
                        traffic in the upstream direction.  Default
                        is false.  This filter can also be enabled
                        for a specific ComPort via the MIB attribute
                        hcxStuIpNetbiosFiltEnbl."
                ::=  { com21HcxVlanCtrlEntry 27 }

        hcxVPNNum OBJECT-TYPE
                SYNTAX Integer32 
                MAX-ACCESS read-write
                STATUS current
                DESCRIPTION "
			Specifies the Virtual Private Network to
			which this Vlan belongs to. If this is 
			not set, it defaults to 0. If a ComPort
			which belongs to this Vlan has to be configured
			to support Voice, then a VPN Number has to
			be defined.
                        Default is 0."
                ::=  { com21HcxVlanCtrlEntry 28 }

        hcxVlanVpi OBJECT-TYPE
                SYNTAX INTEGER (0..64)
                MAX-ACCESS read-write
                STATUS current
                DESCRIPTION "
			Specifies the VPI to use if this vlan
			is on an OC3 Port. This attribute is
			not used if vlan is not on a oc3 Port.
                        Default is 0."
                ::=  { com21HcxVlanCtrlEntry 29 }

        hcxVlanVci OBJECT-TYPE
                SYNTAX INTEGER (1..255)
                MAX-ACCESS read-write
                STATUS current
                DESCRIPTION "
                        Specifies the VCI to use if this vlan
                        is on an OC3 Port. This attribute is 
                        not used if vlan is not on a oc3 Port.
			If the hcxVlanVpi value is set to 0, the
			valid range for this attribute is
			38 to 255
                        Default is 0."
                ::=  { com21HcxVlanCtrlEntry 30 }


        hcxVlanRate OBJECT-TYPE
                SYNTAX Integer32 
                MAX-ACCESS read-write
                STATUS current
                DESCRIPTION "
			Specifies the Maximum Rate at which
			this Vlan can operate. This attribute
			is used only if the vlan is on an
			OC3 Port. 
			Default is 10,000,000 bps"
                ::=  { com21HcxVlanCtrlEntry 31 }


 
 
        -- -- -- -- -- -- -- -- -- -- -- -- -- -- -- -- -- -- -- -- -- -- -- --
        -- -- -- -- -- -- -- -- -- -- -- -- -- -- -- -- -- -- -- -- -- -- -- --
        --
        -- com21HcxVlanStatsGroup
        --
        -- defines the Statistics stored for each Vlan. Note that this
        -- information is not applicable to 10bT .
        -- 
        -- -- -- -- -- -- -- -- -- -- -- -- -- -- -- -- -- -- -- -- -- -- -- --
        -- -- -- -- -- -- -- -- -- -- -- -- -- -- -- -- -- -- -- -- -- -- -- --
 
        com21HcxVlanStatsTable OBJECT-TYPE
                SYNTAX SEQUENCE OF HcxVlanStatsEntry
                MAX-ACCESS not-accessible
                STATUS current
                DESCRIPTION "."
                ::= { com21HcxVlanStatsGroup 1 }
 
        com21HcxVlanStatsEntry OBJECT-TYPE
                SYNTAX  HcxVlanStatsEntry
                MAX-ACCESS  not-accessible
                STATUS  current
                DESCRIPTION "."
                INDEX { hcxVlanStatsId }
                ::= { com21HcxVlanStatsTable 1 }
 

        HcxVlanStatsEntry ::= SEQUENCE {
                hcxVlanStatsId                     INTEGER,
                hcxVlanCurrMcastTxPkts             Gauge32,
                hcxVlanCurrMcastDroppedPkts        Gauge32,
		hcxVlanIpCurrArpFiltStat	   Gauge32,	
		hcxVlanIpCurrSrcFiltStat	   Gauge32,
		hcxVlanIpCurrDstFiltStat	   Gauge32,
		hcxVlanIpCurrBootpReqFiltStat	   Gauge32,
		hcxVlanIpCurrBootpReplyFiltStat	   Gauge32,
		hcxVlanIpCurrDhcpSnoopFiltStat	   Gauge32,
                hcxVlanL2CurrSnapFiltStat          Gauge32,
                hcxVlanL2CurrNonSnapFiltStat       Gauge32,
                hcxVlanL2CurrEnetFiltStat          Gauge32,
                hcxVlanL2CurrArpIpv4FiltStat       Gauge32,
                hcxVlanL2CurrIpv4FiltStat          Gauge32,
                hcxVlanL2CurrIpv6FiltStat          Gauge32,
                hcxVlanL2CurrIpxFiltStat           Gauge32,
                hcxVlanL2CurrAppletalkFiltStat     Gauge32,
                hcxVlanL2CurrOthersFiltStat        Gauge32,
                hcxVlanIpCurrNetbiosFiltStat       Gauge32,
                hcxVlanPrevMcastTxPkts             Gauge32,
                hcxVlanPrevMcastDroppedPkts        Gauge32,
                hcxVlanIpPrevArpFiltStat           Gauge32,       
                hcxVlanIpPrevSrcFiltStat           Gauge32,
                hcxVlanIpPrevDstFiltStat           Gauge32,
                hcxVlanIpPrevBootpReqFiltStat      Gauge32,
                hcxVlanIpPrevBootpReplyFiltStat    Gauge32,
                hcxVlanIpPrevDhcpSnoopFiltStat     Gauge32,
                hcxVlanL2PrevSnapFiltStat          Gauge32,
                hcxVlanL2PrevNonSnapFiltStat       Gauge32,
                hcxVlanL2PrevEnetFiltStat          Gauge32,
                hcxVlanL2PrevArpIpv4FiltStat       Gauge32,
                hcxVlanL2PrevIpv4FiltStat          Gauge32,
                hcxVlanL2PrevIpv6FiltStat          Gauge32,
                hcxVlanL2PrevIpxFiltStat           Gauge32,
                hcxVlanL2PrevAppletalkFiltStat     Gauge32,
                hcxVlanL2PrevOthersFiltStat        Gauge32,
                hcxVlanIpPrevNetbiosFiltStat       Gauge32,
		hcxVlanClearStats  		   INTEGER }
 
        hcxVlanStatsId   OBJECT-TYPE
                SYNTAX  INTEGER (1..64)
                MAX-ACCESS  read-only
                STATUS  current
                DESCRIPTION "
                        Is used as an Index to read the Statistics of a given
                        Vlan."
                ::= { com21HcxVlanStatsEntry 1 }
 
        hcxVlanCurrMcastTxPkts OBJECT-TYPE
                SYNTAX  Gauge32
                MAX-ACCESS  read-only
                STATUS  current
                DESCRIPTION "
                        contains the number of Multicast net packets sent
                        downstream over the Vlan in the current 15min
                        period."
                ::= { com21HcxVlanStatsEntry 2 }
 
 
        hcxVlanCurrMcastDroppedPkts OBJECT-TYPE
                SYNTAX  Gauge32
                MAX-ACCESS  read-only
                STATUS  current
                DESCRIPTION "
                        contains the number of Multicast downstream
                        packets dropped in the current 15min period."
                ::= { com21HcxVlanStatsEntry 3 }
 

        hcxVlanIpCurrArpFiltStat OBJECT-TYPE
		SYNTAX	Gauge32
		MAX-ACCESS	read-only
		STATUS	current
		DESCRIPTION "
			contains the number of ARP packets from this 
		Vlan dropped due to authentication filtering in the
		current 15minute collection period"
                ::= { com21HcxVlanStatsEntry 4 }

        hcxVlanIpCurrSrcFiltStat OBJECT-TYPE   
                SYNTAX  Gauge32
                MAX-ACCESS  read-only      
                STATUS  current      
                DESCRIPTION "  
                        Contains the number of IP packets from this VLAN
                        dropped due to source address filtering in the
                        current 15 minute collection period."
                ::= { com21HcxVlanStatsEntry 5 }

        hcxVlanIpCurrDstFiltStat OBJECT-TYPE   
                SYNTAX  Gauge32 
                MAX-ACCESS  read-only      
                STATUS  current      
                DESCRIPTION "  
                        Contains the number of IP packets from this VLAN
                        dropped due to destination address filtering in the
                        current 15 minute collection period."
                ::= { com21HcxVlanStatsEntry 6 }

        hcxVlanIpCurrBootpReqFiltStat OBJECT-TYPE   
                SYNTAX  Gauge32 
                MAX-ACCESS  read-only      
                STATUS  current      
                DESCRIPTION "  
                        Contains the number of Bootp Req packets from this VLAN
                        dropped due to filtering in the current 15 minute
                        collection period."
                ::= { com21HcxVlanStatsEntry 7 }
 
        hcxVlanIpCurrBootpReplyFiltStat OBJECT-TYPE   
                SYNTAX  Gauge32 
                MAX-ACCESS  read-only      
                STATUS  current      
                DESCRIPTION "  
                        Contains the number of Bootp Reply packets from 
			this VLAN dropped due to filtering in the current 
			15 minute collection period."
                ::= { com21HcxVlanStatsEntry 8 }
 
        hcxVlanIpCurrDhcpSnoopFiltStat OBJECT-TYPE   
                SYNTAX  Gauge32 
                MAX-ACCESS  read-only      
                STATUS  current      
                DESCRIPTION "  
                        Contains the number of DHCP Ack packets from this VLAN
                        snooped due to filtering in the current 15 minute
                        collection period."
                ::= { com21HcxVlanStatsEntry 9 }
 
        hcxVlanPrevMcastTxPkts OBJECT-TYPE
                SYNTAX  Gauge32
                MAX-ACCESS  read-only
                STATUS  current
                DESCRIPTION "
                        contains the number of Multicast net packets sent
                        downstream over the Vlan in the previous 15min
                        period."
                ::= { com21HcxVlanStatsEntry 10 }
 
        hcxVlanPrevMcastDroppedPkts OBJECT-TYPE
                SYNTAX  Gauge32
                MAX-ACCESS  read-only
                STATUS  current
                DESCRIPTION "
                        contains the number of Multicast downstream
                        packets dropped in the previous 15min period."
                ::= { com21HcxVlanStatsEntry 11 }

        hcxVlanIpPrevArpFiltStat OBJECT-TYPE
                SYNTAX  Gauge32
                MAX-ACCESS  read-only
                STATUS  current
                DESCRIPTION "
                        contains the number of ARP packets from this
                Vlan dropped due to authentication filtering in the
                previous 15minute collection period"
                ::= { com21HcxVlanStatsEntry 12 }
 
        hcxVlanIpPrevSrcFiltStat OBJECT-TYPE
                SYNTAX  Gauge32
                MAX-ACCESS  read-only
                STATUS  current
                DESCRIPTION "
                        Contains the number of IP packets from this VLAN
                        dropped due to source address filtering in the
                        previous 15 minute collection period."
                ::= { com21HcxVlanStatsEntry 13 }
 
        hcxVlanIpPrevDstFiltStat OBJECT-TYPE
                SYNTAX  Gauge32
                MAX-ACCESS  read-only
                STATUS  current
                DESCRIPTION "
                        Contains the number of IP packets from this VLAN
                        dropped due to destination address filtering in the
                        previous 15 minute collection period."
                ::= { com21HcxVlanStatsEntry 14 }
 
        hcxVlanIpPrevBootpReqFiltStat OBJECT-TYPE
                SYNTAX  Gauge32
                MAX-ACCESS  read-only   
                STATUS  current
                DESCRIPTION "
                        Contains the number of Bootp Req packets from this VLAN
                        dropped due to filtering in the previous 15 minute
                        collection period."
                ::= { com21HcxVlanStatsEntry 15 }
 
        hcxVlanIpPrevBootpReplyFiltStat OBJECT-TYPE
                SYNTAX  Gauge32
                MAX-ACCESS  read-only
                STATUS  current
                DESCRIPTION "
                        Contains the number of Bootp Reply packets from 
                        this VLAN dropped due to filtering in the previous 
                        15 minute collection period."
                ::= { com21HcxVlanStatsEntry 16 }
 
        hcxVlanIpPrevDhcpSnoopFiltStat OBJECT-TYPE
                SYNTAX  Gauge32
                MAX-ACCESS  read-only
                STATUS  current
                DESCRIPTION "
                        Contains the number of DHCP Ack packets from this VLAN
                        snooped due to filtering in the previous 15 minute
                        collection period."
                ::= { com21HcxVlanStatsEntry 17 }

        hcxVlanClearStats OBJECT-TYPE
                SYNTAX INTEGER { nil(1), clear(2) }
                MAX-ACCESS read-write
                STATUS current
                DESCRIPTION "
                        This attribute is used to clear the all VLAN
                        statistics counters in this group. This operation
                        is only possible if the hcxStatsControl attribute
                        is set to wrapCurr."
                ::= { com21HcxVlanStatsEntry 18 }
 

        hcxVlanL2CurrSnapFiltStat OBJECT-TYPE
                SYNTAX  Gauge32
                MAX-ACCESS  read-only
                STATUS  current
                DESCRIPTION "
                        Contains the number of SNAP-encoded IEEE 802.3 packets
			filtered from this VLAN in the current 15 minute
                        collection period."
                ::= { com21HcxVlanStatsEntry 19 }

        hcxVlanL2CurrNonSnapFiltStat OBJECT-TYPE
                SYNTAX  Gauge32
                MAX-ACCESS  read-only
                STATUS  current
                DESCRIPTION "
                        Contains the number of non-SNAP-encoded IEEE 802.3 packets
                        filtered from this VLAN in the current 15 minute
                        collection period."
                ::= { com21HcxVlanStatsEntry 20 }

        hcxVlanL2CurrEnetFiltStat OBJECT-TYPE
                SYNTAX  Gauge32
                MAX-ACCESS  read-only
                STATUS  deprecated
                DESCRIPTION "
                        Contains the number of Ethernet packets
                        filtered from this VLAN in the current 15 minute
                        collection period."
                ::= { com21HcxVlanStatsEntry 21 }

        hcxVlanL2CurrArpIpv4FiltStat OBJECT-TYPE
                SYNTAX  Gauge32
                MAX-ACCESS  read-only
                STATUS  deprecated
                DESCRIPTION "
                        Contains the number of IPv4 ARP packets
                        filtered from this VLAN in the current 15 minute
                        collection period."
                ::= { com21HcxVlanStatsEntry 22 }


        hcxVlanL2CurrIpv4FiltStat OBJECT-TYPE
                SYNTAX  Gauge32
                MAX-ACCESS  read-only
                STATUS  deprecated
                DESCRIPTION "
                        Contains the number of IPv4 packets
                        filtered from this VLAN in the current 15 minute
                        collection period."
                ::= { com21HcxVlanStatsEntry 23 }


        hcxVlanL2CurrIpv6FiltStat OBJECT-TYPE
                SYNTAX  Gauge32
                MAX-ACCESS  read-only
                STATUS  deprecated
                DESCRIPTION "
                        Contains the number of IPv6  packets
                        filtered from this VLAN in the current 15 minute
                        collection period."
                ::= { com21HcxVlanStatsEntry 24 }

        hcxVlanL2CurrIpxFiltStat OBJECT-TYPE
                SYNTAX  Gauge32
                MAX-ACCESS  read-only
                STATUS  deprecated
                DESCRIPTION "
                        Contains the number of IPX  packets
                        filtered from this VLAN in the current 15 minute
                        collection period."
                ::= { com21HcxVlanStatsEntry 25 }

        hcxVlanL2CurrAppletalkFiltStat OBJECT-TYPE
                SYNTAX  Gauge32
                MAX-ACCESS  read-only
                STATUS  deprecated
                DESCRIPTION "
                        Contains the number of AppleTalk  packets
                        filtered from this VLAN in the current 15 minute
                        collection period."
                ::= { com21HcxVlanStatsEntry 26 }


        hcxVlanL2CurrOthersFiltStat OBJECT-TYPE
                SYNTAX  Gauge32
                MAX-ACCESS  read-only
                STATUS  deprecated
                DESCRIPTION "
                        Contains the number of  packets that are
			none of the above type of filters that are
                        filtered from this VLAN in the current 15 minute
                        collection period."
                ::= { com21HcxVlanStatsEntry 27 }


        hcxVlanIpCurrNetbiosFiltStat OBJECT-TYPE
                SYNTAX  Gauge32
                MAX-ACCESS  read-only
                STATUS  current
                DESCRIPTION "
                        Contains the number of  NetBIOS-over-IP packets that are
                        filtered from this VLAN in the current 15 minute
                        collection period."
                ::= { com21HcxVlanStatsEntry 28 }

        hcxVlanL2PrevSnapFiltStat OBJECT-TYPE
                SYNTAX  Gauge32
                MAX-ACCESS  read-only
                STATUS  current
                DESCRIPTION "
                        Contains the number of SNAP-encoded IEEE 802.3 packets
                        filtered from this VLAN in the previous 15 minute
                        collection period."
                ::= { com21HcxVlanStatsEntry 29 }
 
        hcxVlanL2PrevNonSnapFiltStat OBJECT-TYPE
                SYNTAX  Gauge32
                MAX-ACCESS  read-only
                STATUS  current
                DESCRIPTION "
                        Contains the number of non-SNAP-encoded IEEE 802.3 packets
                        filtered from this VLAN in the previous 15 minute
                        collection period."
                ::= { com21HcxVlanStatsEntry 30 }
 
        hcxVlanL2PrevEnetFiltStat OBJECT-TYPE
                SYNTAX  Gauge32
                MAX-ACCESS  read-only
                STATUS  deprecated
                DESCRIPTION "
                        Contains the number of Ethernet packets
                        filtered from this VLAN in the previous 15 minute
                        collection period."
                ::= { com21HcxVlanStatsEntry 31 }
 
        hcxVlanL2PrevArpIpv4FiltStat OBJECT-TYPE
                SYNTAX  Gauge32
                MAX-ACCESS  read-only
                STATUS  deprecated
                DESCRIPTION "
                        Contains the number of IPv4 ARP packets
                        filtered from this VLAN in the previous 15 minute
                        collection period."
                ::= { com21HcxVlanStatsEntry 32 }
 
 
        hcxVlanL2PrevIpv4FiltStat OBJECT-TYPE
                SYNTAX  Gauge32
                MAX-ACCESS  read-only
                STATUS  deprecated
                DESCRIPTION "
                        Contains the number of IPv4 packets
                        filtered from this VLAN in the previous 15 minute
                        collection period."
                ::= { com21HcxVlanStatsEntry 33 }
 
 
        hcxVlanL2PrevIpv6FiltStat OBJECT-TYPE
                SYNTAX  Gauge32
                MAX-ACCESS  read-only
                STATUS  deprecated
                DESCRIPTION "
                        Contains the number of IPv6  packets
                        filtered from this VLAN in the previous 15 minute
                        collection period."
                ::= { com21HcxVlanStatsEntry 34 }
 
        hcxVlanL2PrevIpxFiltStat OBJECT-TYPE
                SYNTAX  Gauge32
                MAX-ACCESS  read-only
                STATUS  deprecated
                DESCRIPTION "
                        Contains the number of IPX  packets
                        filtered from this VLAN in the previous 15 minute
                        collection period."
                ::= { com21HcxVlanStatsEntry 35 }
 
        hcxVlanL2PrevAppletalkFiltStat OBJECT-TYPE
                SYNTAX  Gauge32
                MAX-ACCESS  read-only
                STATUS  deprecated
                DESCRIPTION "
                        Contains the number of AppleTalk  packets
                        filtered from this VLAN in the previous 15 minute
                        collection period."
                ::= { com21HcxVlanStatsEntry 36 }
 
 
        hcxVlanL2PrevOthersFiltStat OBJECT-TYPE
                SYNTAX  Gauge32
                MAX-ACCESS  read-only
                STATUS  deprecated
                DESCRIPTION "
                        Contains the number of  packets that are
                        none of the above type of filters that are
                        filtered from this VLAN in the previous 15 minute
                        collection period."
                ::= { com21HcxVlanStatsEntry 37 }
 
 
        hcxVlanIpPrevNetbiosFiltStat OBJECT-TYPE
                SYNTAX  Gauge32
                MAX-ACCESS  read-only
                STATUS  current
                DESCRIPTION "
                        Contains the number of  NetBIOS-over-IP packets that are
                        filtered from this VLAN in the previous 15 minute
                        collection period."
                ::= { com21HcxVlanStatsEntry 38 }
 


        -- -- -- -- -- -- -- -- -- -- -- -- -- -- -- -- -- -- -- -- -- -- -- --
        -- -- -- -- -- -- -- -- -- -- -- -- -- -- -- -- -- -- -- -- -- -- -- --
        --
        -- com21HcxOc3VlanStatsGroup
        --
        -- This group provides the capability to retrieve Statistics
        -- collected on the WAN side for vlans on the OC3 Card.
        --
        -- Refer to 'com21HcxVlanCtrlGroup' for Vlan Configuration
        --
        -- -- -- -- -- -- -- -- -- -- -- -- -- -- -- -- -- -- -- -- -- -- -- --
        -- -- -- -- -- -- -- -- -- -- -- -- -- -- -- -- -- -- -- -- -- -- -- --
 
 
        com21HcxOc3VlanStatsTable OBJECT-TYPE
                SYNTAX SEQUENCE OF HcxOc3VlanStatsEntry
                MAX-ACCESS not-accessible
                STATUS current
                DESCRIPTION "."
                ::= { com21HcxOc3VlanStatsGroup 1 }
 
        com21HcxOc3VlanStatsEntry OBJECT-TYPE
                SYNTAX HcxOc3VlanStatsEntry
                MAX-ACCESS not-accessible
                STATUS current
                DESCRIPTION "."
                INDEX { hcxOc3VlanStatsVlanId }
                ::= { com21HcxOc3VlanStatsTable 1 }
 
        HcxOc3VlanStatsEntry ::= SEQUENCE {
                hcxOc3VlanStatsVlanId                 INTEGER,
                hcxOc3VlanStatsCurrTxPkts                  Integer32,
                hcxOc3VlanStatsCurrRxPkts                  Integer32,
                hcxOc3VlanStatsCurrCrcPkts                 Integer32,
                hcxOc3VlanStatsPrevTxPkts                  Integer32,
                hcxOc3VlanStatsPrevRxPkts                  Integer32,
                hcxOc3VlanStatsPrevCrcPkts                 Integer32,
                hcxOc3VlanStatsClear                   INTEGER }
 
        hcxOc3VlanStatsVlanId OBJECT-TYPE
                SYNTAX INTEGER (1..64)
                MAX-ACCESS read-only
                STATUS current
                DESCRIPTION "
                        Specifies the index into this table. An entry 
			exists for each vlan which is on the Oc3 Port."
                ::= { com21HcxOc3VlanStatsEntry 1 }
 
        hcxOc3VlanStatsCurrTxPkts OBJECT-TYPE
                SYNTAX Integer32
                MAX-ACCESS read-only
                STATUS current
                DESCRIPTION "
                        Specifies the number of Pkts. Transmitted on
                        the VPI/VCI value associated with this entry in
                        the current 15-min time period."
                ::= { com21HcxOc3VlanStatsEntry 2 }
 
 
        hcxOc3VlanStatsCurrRxPkts OBJECT-TYPE
                SYNTAX Integer32
                MAX-ACCESS read-only
                STATUS current
                DESCRIPTION "
                        Specifies the number of Pkts. Received on
                        the VPI/VCI value associated with this entry in
                        the current 15-min time period."
                ::= { com21HcxOc3VlanStatsEntry 3 }
 
        hcxOc3VlanStatsCurrCrcPkts OBJECT-TYPE
                SYNTAX Integer32
                MAX-ACCESS read-only
                STATUS current
                DESCRIPTION "
                        Specifies the number of Pkts. Received with
                        CRC error on the VPI/VCI value associated
                        with this entry in the current 15-min time period."
                ::= { com21HcxOc3VlanStatsEntry 4 }
 
        hcxOc3VlanStatsPrevTxPkts OBJECT-TYPE
                SYNTAX Integer32
                MAX-ACCESS read-only
                STATUS current
                DESCRIPTION "
                        Specifies the number of Pkts. Transmitted on
                        the VPI/VCI value associated with this entry in
                        the previous 15-min time period."
                ::= { com21HcxOc3VlanStatsEntry 5 }
 
 
        hcxOc3VlanStatsPrevRxPkts OBJECT-TYPE
                SYNTAX Integer32
                MAX-ACCESS read-only
                STATUS current
                DESCRIPTION "
                        Specifies the number of Pkts. Received on
                        the VPI/VCI value associated with this entry in
                        the previous 15-min time period."
                ::= { com21HcxOc3VlanStatsEntry 6 }
 
        hcxOc3VlanStatsPrevCrcPkts OBJECT-TYPE
                SYNTAX Integer32
                MAX-ACCESS read-only
                STATUS current
                DESCRIPTION "
                        Specifies the number of Pkts. Received with
                        CRC error on the VPI/VCI value associated
                        with this entry in the previous 15-min time period."
                ::= { com21HcxOc3VlanStatsEntry 7 }
 
        hcxOc3VlanStatsClear OBJECT-TYPE
                SYNTAX INTEGER { nil (1), clear(2) }
                MAX-ACCESS read-write
                STATUS current
                DESCRIPTION "
                        Provides the capability to clear the
                        statistics. Clearing of Statistics is allowed
                        only if  hcxStatsControl attribute is set
                        to wrapCurr."
                ::= { com21HcxOc3VlanStatsEntry 8 }
 


END
