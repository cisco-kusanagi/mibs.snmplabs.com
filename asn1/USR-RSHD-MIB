USR-RSHD-MIB DEFINITIONS ::= BEGIN
    IMPORTS
        IpAddress, Counter32 , OBJECT-TYPE, MODULE-IDENTITY
			FROM  SNMPv2-SMI
        common, UsrUserName
            FROM USR-DEFINITIONS-MIB;
    usrRsh MODULE-IDENTITY
         LAST-UPDATED "200202212020Z"
         ORGANIZATION "CommWorks Corporation, a 3Com Company"
         CONTACT-INFO "Customer Support"
         DESCRIPTION
                 "The commWorks enterprise defined MIB objects for rshd"
--      REVISION   "20020022102020Z"
--      DESCRIPTION
--              "Converted to SNMPv2"
         ::= { common 74 }
	usrRshHostsTable OBJECT-TYPE
    SYNTAX  SEQUENCE OF USRRshHostsTableEntry
    MAX-ACCESS  not-accessible
    STATUS  current
    DESCRIPTION
        "Table of ip address and user name for connection authentication."
    ::= { usrRsh 1 }
    usrRshHostsTableEntry    OBJECT-TYPE
    SYNTAX  USRRshHostsTableEntry
    MAX-ACCESS  not-accessible
    STATUS  current
    DESCRIPTION
        "An entry of an ip address and user name for connection authentication."
    INDEX   { usrRshHostsTableIpAddress, usrRshHostsTableUserName}
    ::= { usrRshHostsTable 1 }
    USRRshHostsTableEntry ::= SEQUENCE {
         usrRshHostsTableUserName        UsrUserName,
         usrRshHostsTableIpAddress    IpAddress,
         usrRshHostsTableStatus      INTEGER
         }
    usrRshHostsTableUserName OBJECT-TYPE
    SYNTAX  UsrUserName
    MAX-ACCESS  not-accessible
    STATUS  current
    DESCRIPTION
        "The users name"
    ::= { usrRshHostsTableEntry 1 }
    usrRshHostsTableIpAddress OBJECT-TYPE
    SYNTAX  IpAddress
    MAX-ACCESS  not-accessible
    STATUS  current
    DESCRIPTION
        "The ip address of the remote hosts"
    ::= { usrRshHostsTableEntry 2 }
    usrRshHostsTableStatus   OBJECT-TYPE
    SYNTAX  INTEGER {
        delete(1),
        add(2)
        }
	MAX-ACCESS  read-write
    STATUS  current
    DESCRIPTION
        "If set to 2 user name and the ip address is added to this pool. If
                 set to delet(1) this table is  deleted"
        --CONFIGURABLE
    ::= { usrRshHostsTableEntry 3 }
	usrRshTotalConnections OBJECT-TYPE
        SYNTAX Counter32
        MAX-ACCESS read-only
        STATUS current
        DESCRIPTION
                "The total number of connections made"
        ::= { usrRsh 2 }
	 usrRshTotalRSHConnections OBJECT-TYPE
        SYNTAX Counter32
        MAX-ACCESS read-only
        STATUS current
        DESCRIPTION
              "The total number of rsh requests"
        ::= { usrRsh 3 }
	 usrRshTotalRcpConnections OBJECT-TYPE
        SYNTAX Counter32
        MAX-ACCESS read-only
        STATUS current
        DESCRIPTION
              "The total number of rcp requests"
        ::= { usrRsh 4 }
	 usrRshTotalAuthFailed OBJECT-TYPE
        SYNTAX Counter32
        MAX-ACCESS read-only
        STATUS current
        DESCRIPTION
              "The total number of auth failed"
        ::= { usrRsh 5 }
	 usrRshTotalNASDropped OBJECT-TYPE
        SYNTAX Counter32
        MAX-ACCESS read-only
        STATUS current
        DESCRIPTION
              "The total number of NAS dropped connections"
        ::= { usrRsh 6 }
END
