ANTIVIRUS-MIB DEFINITIONS ::= BEGIN

IMPORTS
	TRAP-TYPE FROM RFC-1215
        OBJECT-TYPE FROM RFC1155-SMI
		  nai, naiTrapSeverity, naiTrapGMTTime, naiTrapLocalTime,
        naiTrapDescription, naiTrapAlarmSourceDNSName, naiTrapAgentVersion,
        naiTrapAgent, naiTrapURL, naiTrapPseudoID,
        naiTrapAlarmSourceAddress
        FROM NAI-MIB; 

naiAntiVirus                 OBJECT IDENTIFIER ::= { nai 4 }
--naiAntiVirus MODULE-IDENTITY
--        LAST-UPDATED "9809231430Z"
--        ORGANIZATION "Network Associates Inc."
--        CONTACT-INFO
--          "Postal:   Network Associates, Inc.
--                     3965 Freedom Circle
--                     Santa Clara, CA  95054
--          Phone:     +1 408 988-3832
--          Internet:  www.nai.com"
--       DESCRIPTION
--          "Network Associate Alert Manager MIB module."
--       ::= { nai 4 }

naiAntiVirusTrapAgentUser OBJECT-TYPE
        SYNTAX          OCTET STRING
        ACCESS          read-only
        STATUS          mandatory
        DESCRIPTION     
          "This information identifies the user account which is causing the alarm."
        ::= { naiAntiVirus 1 }

naiAntiVirusTrapInfectedFile OBJECT-TYPE
        SYNTAX          OCTET STRING
        ACCESS          read-only
        STATUS          mandatory
        DESCRIPTION     
          "This information idenifies the infected file which is causing the alarm."
        ::= { naiAntiVirus 2 }

naiAntiVirusTrapVirusName OBJECT-TYPE
        SYNTAX          OCTET STRING
        ACCESS          read-only
        STATUS          mandatory
        DESCRIPTION     
          "This information identifies the virus which is causing the alarm."
        ::= { naiAntiVirus 3 }

naiAntiVirusTrapTaskName OBJECT-TYPE
        SYNTAX          OCTET STRING
        ACCESS          read-only
        STATUS          mandatory
        DESCRIPTION     
          "This information identifies the task which generated the alarm."
        ::= { naiAntiVirus 4 }

naiAntiVirusTrapStatus OBJECT-TYPE
        SYNTAX          INTEGER
        ACCESS          read-only
        STATUS          optional
        DESCRIPTION     
          "This information identifies the status of the file for which the trap is sent."
        ::= { naiAntiVirus 5 }

naiAntiVirusTrapOS OBJECT-TYPE
        SYNTAX          OCTET STRING
        ACCESS          read-only
        STATUS          mandatory
        DESCRIPTION     
          "This information identifies the platform of the machine from which the trap is sent."
        ::= { naiAntiVirus 6 }

naiAntiVirusTrapEngineVersion OBJECT-TYPE
        SYNTAX          OCTET STRING
        ACCESS          read-only
        STATUS          mandatory
        DESCRIPTION     
          "This information identifies the version of the Scan engine on the machine for which the trap is sent."
        ::= { naiAntiVirus 7 }

naiAntiVirusTrapDATVersion OBJECT-TYPE
        SYNTAX          OCTET STRING
        ACCESS          read-only
        STATUS          mandatory
        DESCRIPTION     
          "This information identifies the the version of the DAT files on the machine for which the trap is sent."
        ::= { naiAntiVirus 8 }


naiAntiVirusTrap TRAP-TYPE
        ENTERPRISE naiAntiVirus
        VARIABLES
        {
                naiTrapAgent,
		naiTrapAgentVersion,
                naiTrapSeverity,
                naiTrapDescription,
                naiTrapAlarmSourceAddress,
                naiTrapAlarmSourceDNSName,
                naiTrapGMTTime,
                naiTrapLocalTime,
                naiTrapURL,
		naiTrapPseudoID,
                naiAntiVirusTrapAgentUser,
                naiAntiVirusTrapInfectedFile,
                naiAntiVirusTrapVirusName,
                naiAntiVirusTrapTaskName,
		naiAntiVirusTrapStatus,
                naiAntiVirusTrapOS,
 		naiAntiVirusTrapEngineVersion,
 		naiAntiVirusTrapDATVersion
        }
        DESCRIPTION
          "The NAI AntiVirus alarm information."
        ::= 1

END
