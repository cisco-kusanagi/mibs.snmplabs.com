--			Ascend mibshash MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBSHASH-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibsHashProfile  OBJECT IDENTIFIER ::= { configuration 108}

	-- The mibsHashProfile table
	--
	-- This table contains parameters for the mibsHashProfile profile
	--

    mibsHashProfileTable	OBJECT-TYPE
	SYNTAX		SEQUENCE OF MibsHashProfileEntry
	ACCESS		not-accessible
	STATUS		mandatory
	DESCRIPTION	"A list of mibsHashProfile profile entries."
	::= { mibsHashProfile 1 }

    mibsHashProfileEntry	OBJECT-TYPE
	SYNTAX		MibsHashProfileEntry
	ACCESS		not-accessible
	STATUS		mandatory
	DESCRIPTION	"A mibsHashProfile entry containing objects that
			 maps to the parameters of mibsHashProfile profile."
	INDEX		{ sHashProfile-Index-o }
	::= { mibsHashProfileTable 1 }

    MibsHashProfileEntry ::=
	SEQUENCE {
	    sHashProfile-Index-o
		INTEGER,
	    sHashProfile-Ipsec
		DisplayString,
	    sHashProfile-Action-o
		INTEGER
	}

    sHashProfile-Index-o	OBJECT-TYPE
	SYNTAX	INTEGER
	ACCESS	read-only
	STATUS	mandatory
	DESCRIPTION	""
	::= { mibsHashProfileEntry 1 }

    sHashProfile-Ipsec	OBJECT-TYPE
	SYNTAX	DisplayString
	ACCESS	read-write
	STATUS	mandatory
	DESCRIPTION	"IP Security hash code"
	::= { mibsHashProfileEntry 2 }

    sHashProfile-Action-o	OBJECT-TYPE
	SYNTAX	INTEGER {
		    noAction (1),
		    createProfile (2),
		    deleteProfile (3)
		}
	ACCESS	read-write
	STATUS	mandatory
	DESCRIPTION	""
	::= { mibsHashProfileEntry 3 }

END
