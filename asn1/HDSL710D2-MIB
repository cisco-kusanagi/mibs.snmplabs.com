-- Copyright 1996 General DataComm Inc., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.

-- Revision History
-- Version   Date			Name		Description
-- 1.00A     30-Jan-1996  		S.Sankaran 	 Initial Revision

-- 
HDSL710D2-MIB DEFINITIONS ::= BEGIN

IMPORTS
	OBJECT-TYPE			FROM RFC-1212
	DisplayString			FROM RFC1213-MIB
	hdsl710D2          		FROM GDCHDSL-MIB;

hdsl710D2System          OBJECT IDENTIFIER ::= { hdsl710D2 1 }
hdsl710D2Version         OBJECT IDENTIFIER ::= { hdsl710D2System 1 }

-- This MIB is a subset of the HDSL MIB for the 710D2 product.

gdc710D2SystemMIBversion OBJECT-TYPE
     	SYNTAX DisplayString (SIZE (5))
     	ACCESS read-only
     	STATUS mandatory
     	DESCRIPTION
     		"Identifies the version of the MIB. The format of the version
     		is x.yzT, where 'x' identifies the major revision number, 'y'
     		identifies the minor revision number, 'z' identifies the
     		typographical revision, and T identifies the test revision.
     		Acceptable values for the individual revision components are
     		as follows:
 
     		x: 1 - 9
     		y: 0 - 9
     		z: 0 - 9
     		T: A - Z
 
     		Upon formal release, no designation for the test revision will
     		be present."
     	::= { hdsl710D2Version 1 }

-- ********************************************************************
-- GDC HDSL Alarm Object Identifier Definitions
-- ********************************************************************
hdsl710D2Alarms          		OBJECT IDENTIFIER ::= { hdsl710D2 2 }

hdsl710D2NoResponseAlm	 		OBJECT IDENTIFIER ::= { hdsl710D2Alarms 1 }
hdsl710D2DiagRxErrAlm			OBJECT IDENTIFIER ::= { hdsl710D2Alarms 2 }
hdsl710D2PowerUpAlm			OBJECT IDENTIFIER ::= { hdsl710D2Alarms 3 }
hdsl710D2UnitFailure        		OBJECT IDENTIFIER ::= { hdsl710D2Alarms 4 }
hdsl710D2ChecksumCorrupt  		OBJECT IDENTIFIER ::= { hdsl710D2Alarms 5 }
hdsl710D2LossofSignal			OBJECT IDENTIFIER ::= { hdsl710D2Alarms 6 }
hdsl710D2UnavailableSec			OBJECT IDENTIFIER ::= { hdsl710D2Alarms 7 }
hdsl710D2ErrorSec			OBJECT IDENTIFIER ::= { hdsl710D2Alarms 8 }
hdsl710D2LossofSyncWord			OBJECT IDENTIFIER ::= { hdsl710D2Alarms 9 }
hdsl710D2MajorBER			OBJECT IDENTIFIER ::= { hdsl710D2Alarms 10 }
hdsl710D2MinorBER			OBJECT IDENTIFIER ::= { hdsl710D2Alarms 11 } 
 


-- ALARM			Maskable	Valid Interfaces
--===============================================================
--hdslNoResponseAlm		No		Unit
--hdslDiagRxErrAlm      	No      	Unit
--hdslPowerUpAlm		No		Unit
--hdslUnitFailure       	No     	 	Unit
--hdslChecksumCorrupt   	No      	Unit
--hdslLossofSignal		Yes		L1, L2 
--hdslUnavailableSec		Yes		L1, L2
--hdslErrorSec			Yes		L1, L2
--hdslLossofSyncWord		Yes		L1, L2
--hdslMajorBER          	Yes   		L1, L2 
--hdslMinorBER          	Yes    		L1, L2





END
