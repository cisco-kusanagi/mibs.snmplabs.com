ChrComIfSonetSonetLine-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComIfSonet				FROM  Chromatis-MIB
	ifIndex					FROM  RFC1213-MIB
	STSrates				FROM  SonetTypes-MIB
	TADMdeviceNo				FROM  SonetTypes-MIB
	SDHSonetType				FROM  SonetTypes-MIB
	Lloopback				FROM  SonetTypes-MIB
	TruthValue				FROM  SonetTypes-MIB;

-- chrComIfSonetSonetLine Table

chrComIfSonetSonetLineTable		OBJECT-TYPE
	SYNTAX		SEQUENCE OF ChrComIfSonetSonetLineEntry
	MAX-ACCESS	not-accessible
	STATUS		current
	DESCRIPTION
	"The Sonet Line private Table"
	::= { chrComIfSonet 5}

chrComIfSonetSonetLineEntry		OBJECT-TYPE
	SYNTAX		ChrComIfSonetSonetLineEntry
	MAX-ACCESS	not-accessible
	STATUS		current
	DESCRIPTION
	""
	INDEX  {  ifIndex }

--DEFAULT  get-function-async  MNIL_GetRoutine
--DEFAULT  set-function-async  MNIL_SetRoutine
--DEFAULT  next-function-async MNIL_NextRoutine
--DEFAULT  test-function-async MNIL_TestRoutine
--DEFAULT  cookie "SonetLine"
	::= { chrComIfSonetSonetLineTable  1 }

ChrComIfSonetSonetLineEntry  ::=
	SEQUENCE  {
	chrComIfSonetlineRate		STSrates,
	chrComIfSonetTDMXcElement		TADMdeviceNo,
	chrComIfSonetbackplaneStream		Unsigned32	(0..4294967295),
	chrComIfSonetreceivedTimeMarker	Unsigned32	(0..4294967295),
	chrComIfSonetSDHSonet		SDHSonetType,
	chrComIfSonetLineSFThreshold		Integer32	(3..5),
	chrComIfSonetLineSDThreashold	Integer32	(6..9),
	chrComIfSonetLineLoopback		Lloopback,
	chrComIfSonetForceLineAIS		TruthValue,
	chrComIfSonetForcelineRDI		TruthValue,
	chrComIfSonetAlarmVector		Integer32	(0..65535),
	chrComIfSonetAlarmSeverityIndex	Unsigned32	(0..4294967295)
}

chrComIfSonetlineRate 	OBJECT-TYPE
	SYNTAX		STSrates
	MAX-ACCESS 	read-only
	STATUS 		current
	DESCRIPTION
	""
	::= { chrComIfSonetSonetLineEntry  1 }

chrComIfSonetTDMXcElement 	OBJECT-TYPE
	SYNTAX		TADMdeviceNo
	MAX-ACCESS 	read-only
	STATUS 		current
	DESCRIPTION
	""
	::= { chrComIfSonetSonetLineEntry  2 }

chrComIfSonetbackplaneStream 	OBJECT-TYPE
	SYNTAX		Unsigned32	(0..4294967295)
	MAX-ACCESS 	read-only
	STATUS 		current
	DESCRIPTION
	""
	::= { chrComIfSonetSonetLineEntry  3 }

chrComIfSonetreceivedTimeMarker 	OBJECT-TYPE
	SYNTAX		Unsigned32	(0..4294967295)
	MAX-ACCESS 	read-only
	STATUS 		current
	DESCRIPTION
	""
	::= { chrComIfSonetSonetLineEntry  4 }

chrComIfSonetSDHSonet 	OBJECT-TYPE
	SYNTAX		SDHSonetType
	MAX-ACCESS 	read-write
	STATUS 		current
	DESCRIPTION
	""
	::= { chrComIfSonetSonetLineEntry  5 }

chrComIfSonetLineSFThreshold 	OBJECT-TYPE
	SYNTAX		Integer32	(3..5)
	MAX-ACCESS 	read-write
	STATUS 		current
	DESCRIPTION
	"The threshold of B2 errors for declaring L-SFBER"
	::= { chrComIfSonetSonetLineEntry  6 }

chrComIfSonetLineSDThreashold 	OBJECT-TYPE
	SYNTAX		Integer32	(6..9)
	MAX-ACCESS 	read-write
	STATUS 		current
	DESCRIPTION
	"The threshold of B2 errors for declaring L-SDBER"
	::= { chrComIfSonetSonetLineEntry  7 }

chrComIfSonetLineLoopback 	OBJECT-TYPE
	SYNTAX		Lloopback
	MAX-ACCESS 	read-write
	STATUS 		current
	DESCRIPTION
	""
	::= { chrComIfSonetSonetLineEntry  8 }

chrComIfSonetForceLineAIS 	OBJECT-TYPE
	SYNTAX		TruthValue
	MAX-ACCESS 	read-write
	STATUS 		current
	DESCRIPTION
	"Activates the force AIS mode , TruthValue"
	::= { chrComIfSonetSonetLineEntry  9 }

chrComIfSonetForcelineRDI 	OBJECT-TYPE
	SYNTAX		TruthValue
	MAX-ACCESS 	read-write
	STATUS 		current
	DESCRIPTION
	"Activates line force RDI mode TruthValue"
	::= { chrComIfSonetSonetLineEntry  10 }

chrComIfSonetAlarmVector 	OBJECT-TYPE
	SYNTAX		Integer32	(0..65535)
	MAX-ACCESS 	read-only
	STATUS 		current
	DESCRIPTION
	"16 bit field.  the Sonet Section Alarm Vector field. "
	::= { chrComIfSonetSonetLineEntry  11 }

chrComIfSonetAlarmSeverityIndex 	OBJECT-TYPE
	SYNTAX		Unsigned32	(0..4294967295)
	MAX-ACCESS 	read-write
	STATUS 		current
	DESCRIPTION
	""
	::= { chrComIfSonetSonetLineEntry  12 }


END
