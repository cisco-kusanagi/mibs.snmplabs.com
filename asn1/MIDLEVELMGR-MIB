MIDLEVELMGR-MIB DEFINITIONS ::= BEGIN

IMPORTS
          enterprises, Counter, Gauge, TimeTicks, IpAddress
                  FROM RFC1155-SMI
          DisplayString
                  FROM RFC1213-MIB
          OBJECT-TYPE
                  FROM RFC-1212;

-- This MIB module uses the extended OBJECT-TYPE macro as
-- defined in RFC 1212.

--
--  The TME 10 NetView MLM Agent Subtree, Version 5
--

-- These Extension groups follow the structure of MIB-II

-- Actual definition of MIB Subtree:

ibm                            OBJECT IDENTIFIER ::= { enterprises 2 }
ibmProd                        OBJECT IDENTIFIER ::= { ibm 6 }
systemsMonitor6000             OBJECT IDENTIFIER ::= { ibmProd 12 }

smProgramInformation           OBJECT IDENTIFIER ::= { systemsMonitor6000 1 }
smMlmNetworkInformation        OBJECT IDENTIFIER ::= { systemsMonitor6000 3 }
smMlmThreshold                 OBJECT IDENTIFIER ::= { systemsMonitor6000 5 }
smMlmAnalysis                  OBJECT IDENTIFIER ::= { systemsMonitor6000 6 }
smMlmFilter                    OBJECT IDENTIFIER ::= { systemsMonitor6000 7 }
smMlmAlias                     OBJECT IDENTIFIER ::= { systemsMonitor6000 8 }
smMlmTrapDestination           OBJECT IDENTIFIER ::= { systemsMonitor6000 9 }
smMlmAdministration            OBJECT IDENTIFIER ::= { systemsMonitor6000 10 }
smMlmStatusMonitor             OBJECT IDENTIFIER ::= { systemsMonitor6000 12 }
smMlmDiscovery                 OBJECT IDENTIFIER ::= { systemsMonitor6000 13 }

--
-- The Program Group Subtree
--

smMlmProgramData               OBJECT IDENTIFIER ::= { smProgramInformation 1 }
smMlmResourceUsage             OBJECT IDENTIFIER ::= { smProgramInformation 2 }
smMlmProgramMessages           OBJECT IDENTIFIER ::= { smProgramInformation 3 }
smMlmProgramEnvironmentVars    OBJECT IDENTIFIER ::= { smProgramInformation 4 }

smMlmProgramDescription        OBJECT IDENTIFIER ::= { smMlmProgramData 1 }
smMlmProgramControl            OBJECT IDENTIFIER ::= { smMlmProgramData 2 }
smMlmProgramLog                OBJECT IDENTIFIER ::= { smMlmProgramData 3 }
smMlmProgramDataCollection     OBJECT IDENTIFIER ::= { smMlmProgramData 4 }
smMlmProgramSetableTestObjects OBJECT IDENTIFIER ::= { smMlmProgramData 5 }
smMlmProgramTrapLog            OBJECT IDENTIFIER ::= { smMlmProgramData 6 }

--
--  Program Description Group - information about the Mid-Level
--  Manager agent itself.  Useful for getting version information, etc.
--

smMlmProgramName OBJECT-TYPE
        SYNTAX  DisplayString
        ACCESS  read-only
        STATUS  mandatory
        DESCRIPTION
                "Official name of the Mid-Level Manager."
        ::= { smMlmProgramDescription 1}

smMlmProgramNumber OBJECT-TYPE
        SYNTAX  DisplayString
        ACCESS  read-only
        STATUS  mandatory
        DESCRIPTION
                "Program number for the Mid-Level Manager."
        ::= { smMlmProgramDescription 2}

smMlmProgramVersion OBJECT-TYPE
        SYNTAX  DisplayString
        ACCESS  read-only
        STATUS  mandatory
        DESCRIPTION
                "Version number of the Mid-Level Manager."
        ::= { smMlmProgramDescription 3}


smMlmProgramCompilationDate OBJECT-TYPE
        SYNTAX  DisplayString
        ACCESS  read-only
        STATUS  mandatory
        DESCRIPTION
                "Date and time when the Mid-Level Manager
                 was compiled."
        ::= { smMlmProgramDescription 4}

smMlmProgramUpTime OBJECT-TYPE
    SYNTAX  TimeTicks
    ACCESS  read-only
    STATUS  mandatory
    DESCRIPTION
            "Time (in hundredths of a second) since the
             Mid-Level Manager was last re-initialized."
    ::= { smMlmProgramDescription 5 }

smMlmProgramContact OBJECT-TYPE
    SYNTAX  DisplayString
    ACCESS  read-write
    STATUS  mandatory
    DESCRIPTION
            "Textual identification of the contact person
             for the Mid-Level Manager on this managed node
             and information on how to contact this person."
    ::= { smMlmProgramDescription 6 }

--
-- Program Control Group
--
--  This group contains those variables used to modify operation of the
--  systems monitor
--

smMlmProgramControlLocalConfigurationFile OBJECT-TYPE
        SYNTAX  DisplayString
        ACCESS  read-write
        STATUS  mandatory
        DESCRIPTION
                "Name of a local configuration file.  When this field is
                set to a file name and smMlmProgramControlSaveConfiguration
                is set to true, a local configuration file is written
                to the path specified.  When the Mid-Level Manager is
                reinitialized this file may be used as a configuration
                file if the '-i' option is used in conjunction with a
                '-c <configpath>', where the <configpath> corresponds to the
                path of this local configuration file.

                This can be thought of as a 'Save As...'
                file to record the current configuration for future
                rollback if necessary."
        ::= { smMlmProgramControl 1}

smMlmProgramControlSavedFlags OBJECT-TYPE
        SYNTAX  DisplayString
        ACCESS  read-write
        STATUS  mandatory
        DESCRIPTION
                "Saved flags which will be used to start the agent.
                 This field can be modified to be used with the
                 smMlmProgramControlReInitializeMonitor function.
                 The flags are saved in the file: /usr/etc/midmand.flags.

                 On NT the flags are saved in the file:
                 smv2/mlmv2.flg (for mlmv2)."
        ::= { smMlmProgramControl 2 }

smMlmProgramControlAgentAddress OBJECT-TYPE
        SYNTAX  IpAddress
        ACCESS  read-write
        STATUS  mandatory
        DESCRIPTION
                "Address of the box where MLM is running.  This address
                 is used while generating traps."
        ::= { smMlmProgramControl 3}

smMlmProgramControlMaxTcpTrapQueue OBJECT-TYPE
        SYNTAX  INTEGER (0..4294967295)
        ACCESS  read-write
        STATUS  mandatory
        DESCRIPTION
                "Maximum number of Tcp traps which are queued when
                 the Tcp connection is down.
                 Default value is 2048."
        ::= { smMlmProgramControl 4}

smMlmProgramControlPercentMultiplier OBJECT-TYPE
        SYNTAX  INTEGER
        ACCESS  read-write
        STATUS  mandatory
        DESCRIPTION
                "reserved."
        ::= { smMlmProgramControl 5}

smMlmProgramControlSamplesPerInterval OBJECT-TYPE
        SYNTAX  INTEGER (1..4294967295)
        ACCESS  read-write
        STATUS  mandatory
        DESCRIPTION
                "The number of samples per interval to use
                 for baselining and statistics.
                 Default value is 10."
        ::= { smMlmProgramControl 6}

smMlmProgramControlMaxOutstandingPingRequests OBJECT-TYPE
        SYNTAX  INTEGER (1..4294967295)
        ACCESS  read-write
        STATUS  mandatory
        DESCRIPTION
                "The maximum number of outstanding ping requests
                 allowed for status checking.
                 Default is 32."
        ::= { smMlmProgramControl 7}

smMlmProgramControlRetryCount OBJECT-TYPE
        SYNTAX  INTEGER
        ACCESS  read-write
        STATUS  mandatory
        DESCRIPTION
                "Default number of retries for actions that can be
                 retried.

                 Not implemented."
        ::= { smMlmProgramControl 8}

smMlmProgramControlTimeout OBJECT-TYPE
        SYNTAX  TimeTicks
        ACCESS  read-write
        STATUS  mandatory
        DESCRIPTION
                "Default number of timeout for actions that can timeout.

                 Not implemented."
        ::= { smMlmProgramControl 9}

smMlmProgramControlCurrentFlags OBJECT-TYPE
        SYNTAX  DisplayString
        ACCESS  read-only
        STATUS  mandatory
        DESCRIPTION
                "Current flags which were used to start or re-initialize
                 the agent."
        ::= { smMlmProgramControl 10 }

smMlmProgramControlReinitFlags OBJECT-TYPE
        SYNTAX  DisplayString
        ACCESS  read-write
        STATUS  mandatory
        DESCRIPTION
                "Re-intialize flags which will be used to start the agent.
                 This field can be modified to be used with the
                 smMlmProgramControlReInitializeMonitor function.

                 For NT, this variable provides the time the
                 Mid-Level Manager was last initialized.
                 A SET to this will reinitialize the program.  New
                 command-line parameters can optionally be provided
                 on the set.  If no value is passed on the set (or if
                 the 'last initialized' time string is passed), the
                 Mid-Level Manager will reinitialize using
                 original command-line parameters."
        ::= { smMlmProgramControl 11 }

smMlmProgramControlReInitializeMonitor OBJECT-TYPE
        SYNTAX  INTEGER {
                false(1),
                trueReinit(2),
                trueSaved(3)
                }
        ACCESS  read-write
        STATUS  mandatory
        DESCRIPTION
                "Allows the re-initializaton of the Mid-Level Manager Agent.
                 Setting to trueReinit(2) uses the flags in
                 smMlmProgramControlReinitFlags as the
                 start-up flags.  Setting to trueSaved(3) uses the flags
                 in smMlmProgramControlSavedFlags as the start-up
                 flags.  The value of this variable returns to false
                 once the re-start has occurred."
        ::= { smMlmProgramControl 12}

smMlmProgramControlSaveConfiguration OBJECT-TYPE
        SYNTAX  INTEGER {
                false(1),
                true(2)
                }
        ACCESS  read-write
        STATUS  mandatory
        DESCRIPTION
                "Setting this variable to true(2) results in the current
                 Mid-Level Manager Agent configuration being saved
                 to the file specified by the value of the smMlmProgramControl
                 LocalConfigurationFile variable.  The value of this variable
                 returns to false once the configuration is saved."
        ::= { smMlmProgramControl 13 }

--
--  Program Log Settings - information about the logging being done
--  by the Mid-Level Manager.
--

smMlmProgramLogFileName OBJECT-TYPE
        SYNTAX  DisplayString
        ACCESS  read-write
        STATUS  mandatory
        DESCRIPTION
                "File name for logging information in the Mid-Level
                 Manager Agent.  The type of information being logged
                 depends on the trace mask (ie. smMlmProgramLogMask)."
        ::= { smMlmProgramLog 1 }

smMlmProgramLogFileSize OBJECT-TYPE
        SYNTAX  INTEGER
        ACCESS  read-only
        STATUS  mandatory
        DESCRIPTION
                "Current size of the log file in bytes."
        ::= { smMlmProgramLog 2 }

smMlmProgramLogMaxFileSize OBJECT-TYPE
        SYNTAX  INTEGER
        ACCESS  read-write
        STATUS  mandatory
        DESCRIPTION
                "Maximum size of the log file in kilobytes."
        ::= { smMlmProgramLog 3 }

smMlmProgramLogNumFiles OBJECT-TYPE
        SYNTAX  INTEGER
        ACCESS  read-write
        STATUS  mandatory
        DESCRIPTION
                "Maximum number of log files to keep.  When the data
                 log file is full, it is rolled over to <logFilename>1.  Files are
                 rolled up until the number of files specified by this field
                 exists (ie. <LogFilename>1 becomes <LogFilename>2, etc.)."
        ::= { smMlmProgramLog 4 }

smMlmProgramLogFileBehavior OBJECT-TYPE
        SYNTAX  INTEGER {
                wrapFlush(1), -- wrap and flush
                wrapNoflush(2), -- wrap and don't flush
                nowrapFlush(3), -- don't wrap and flush
                nowrapNoflush(4) -- don't wrap and don't flush
                }
        ACCESS  read-write
        STATUS  mandatory
        DESCRIPTION
                "This field determines what is done when the maximum
                 file size is exceeded and the number of log files specified
                 already exists.  If wrap is specified, then the oldest
                 log file is removed, all other files are rolled up, and
                 logging continues into a new file.

                 If nowrap is specified, no more data will be logged
                 until either the log file name is changed or
                 the existing files are renamed (or removed).

                 Flushing refers to whether or not each log entry is
                 immediately written to the log file or whether the log
                 data is written out in large chunks containing multiple
                 log entries.  Flushing allows the log file to always contain
                 the latest log entries.  However, CPU time can be saved
                 if flushing is not activated."
        ::= { smMlmProgramLog 5 }

smMlmProgramLogMask OBJECT-TYPE
        SYNTAX  DisplayString
        ACCESS  read-write
        STATUS  mandatory
        DESCRIPTION
                "The log mask field is used to indicate the type of
                 information that is being logged.

     The log mask may contain the following literals:

        none          logs nothing
        inform        logs informational messages
        warning       logs warning messages
        error         logs error messages
        base          logs Remote Manager base information
        command       logs command table information
        filter        logs filter table information
        analysis      logs analysis table information
        threshold     logs threshold table information
        polling       logs MIB variable polling information
        smux          logs SMUX interface traffic
        binary        logs packets sent/received in binary
        call          logs all internal functions called
        all           logs all information

     For NT the log mask may contain the following literals:

        binary -       logs packets sent/received in binary
                         also invokes the call literal,
        call   -       logs all internal functions called,
        all    -       logs all information,
        screen -       logs information to the screen"

        ::= { smMlmProgramLog 6 }

--
--  Program Data Collection Settings - information about the data collection being
--  done by the threshold table.
--

smMlmProgramDataCollectionFileName OBJECT-TYPE
        SYNTAX  DisplayString
        ACCESS  read-write
        STATUS  mandatory
        DESCRIPTION
                "The data collection filename refers to the file used to
                 store the data associated with the entries in the threshold
                 table.  The corresponding threshold table entry must have
                 it's state set to enabledStoreOnly or enabledThresholdStore
                 in order for data to be collected."
        ::= { smMlmProgramDataCollection 1 }

smMlmProgramDataCollectionFileSize OBJECT-TYPE
        SYNTAX  INTEGER
        ACCESS  read-only
        STATUS  mandatory
        DESCRIPTION
                "This field contains the current size of the collection
                 file in bytes."
        ::= { smMlmProgramDataCollection 2 }

smMlmProgramDataCollectionMaxFileSize OBJECT-TYPE
        SYNTAX  INTEGER
        ACCESS  read-write
        STATUS  mandatory
        DESCRIPTION
                "Maximum size of the data collection file in kilobytes.  The
                 action taken when the collection file contains this
                 MaxFileSize Kbytes is determined by the data
                 collection FileBehavior MIB variable."
        ::= { smMlmProgramDataCollection 3 }

smMlmProgramDataCollectionNumFiles OBJECT-TYPE
        SYNTAX  INTEGER
        ACCESS  read-write
        STATUS  mandatory
        DESCRIPTION
                "This field refers to the number of collection files to keep.

                 When the data collection file is full, <collFilename> is
                 rolled up to <collFilename>1 (where <collFilename>
                 refers to the file defined by the DataCollectionFileName
                 MIB variable).  Files are 'rolled up' until the number
                 of files specified by this field exists (ie. <collFilename>1
                 becomes <collFilename>2, etc.)."
        ::= { smMlmProgramDataCollection 4 }

smMlmProgramDataCollectionFileBehavior OBJECT-TYPE
        SYNTAX  INTEGER {
                wrapFlush(1), -- wrap and flush
                wrapNoflush(2), -- wrap and don't flush
                nowrapFlush(3), -- don't wrap and flush
                nowrapNoflush(4) -- don't wrap and don't flush
                }
        ACCESS  read-write
        STATUS  mandatory
        DESCRIPTION
                "This field determines what is done when the maximum
                 file size is exceeded AND the number of collection files
                 specified already exists.  If wrap is specified, then
                 the oldest collection file is removed, all other files are
                 rolled up, and collection continues into a new file.

                 If nowrap is specified, no more data will be collected
                 until either the collection file name is changed
                 or the existing files are renamed (or removed).

                 Flushing refers to whether or not each collection entry is
                 immediately written to the log file or whether the
                 collection data is written out in large chunks containing
                 multiple collection entries.  Flushing allows the collection
                 file to always contain the latest collection entries.
                 However, CPU time can be saved if flushing is not activated."
        ::= { smMlmProgramDataCollection 5 }

--
--  Program Trap Log Settings - information about the trap logging being done
--  by the Mid-Level Manager.
--

smMlmProgramTrapLogFileName OBJECT-TYPE
        SYNTAX  DisplayString
        ACCESS  read-write
        STATUS  mandatory
        DESCRIPTION
                "File name for logging information about traps that
                 are received by the Mid-Level Manager.
                 The type of information being logged depends on the trace
                 mask (ie. smMlmProgramTrapLogMask)."
        ::= { smMlmProgramTrapLog 1 }

smMlmProgramTrapLogFileSize OBJECT-TYPE
        SYNTAX  INTEGER
        ACCESS  read-only
        STATUS  mandatory
        DESCRIPTION
                "Current size of the trap log file in bytes."
        ::= { smMlmProgramTrapLog 2 }

smMlmProgramTrapLogMaxFileSize OBJECT-TYPE
        SYNTAX  INTEGER
        ACCESS  read-write
        STATUS  mandatory
        DESCRIPTION
                "Maximum size of the trap log file in kilobytes."
        ::= { smMlmProgramTrapLog 3 }

smMlmProgramTrapLogNumFiles OBJECT-TYPE
        SYNTAX  INTEGER
        ACCESS  read-write
        STATUS  mandatory
        DESCRIPTION
                "Maximum number of trap log files to keep.  When the
                 log file is full, it is rolled over to <traplogFilename>1.  Files are
                 rolled up until the number of files specified by this field
                 exists (ie. <trapLogFilename>1 becomes <trapLogFilename>2, etc.)."
        ::= { smMlmProgramTrapLog 4 }

smMlmProgramTrapLogFileBehavior OBJECT-TYPE
        SYNTAX  INTEGER {
                wrapFlush(1), -- wrap and flush
                wrapNoflush(2), -- wrap and don't flush
                nowrapFlush(3), -- don't wrap and flush
                nowrapNoflush(4) -- don't wrap and don't flush
                }
        ACCESS  read-write
        STATUS  mandatory
        DESCRIPTION
                "This field determines what is done when the maximum
                 file size is exceeded and the number of trap log
                 files specified already exists.  If wrap is specified,
                 then the oldest trap log file is removed, all other
                 files are rolled up, and logging continues into a new file.

                 If nowrap is specified, no more data will be logged
                 until either the trap log file name is changed or
                 the existing files are renamed (or removed).

                 Flushing refers to whether or not each log entry is
                 immediately written to the trap log file or whether the log
                 data is written out in large chunks containing multiple
                 log entries.  Flushing allows the trap log file to always
                 contain the latest log entries.  However, CPU time can be
                 saved if flushing is not activated."
        ::= { smMlmProgramTrapLog 5 }

smMlmProgramTrapLogMask OBJECT-TYPE
        SYNTAX  DisplayString
        ACCESS  read-write
        STATUS  mandatory
        DESCRIPTION
            " Not yet implemented ."
        ::= { smMlmProgramTrapLog 6 }


--
-- The Remote Manager Settable Test objects group
--
-- This group is used only for internal test purposes, and has no function
--

smMlmProgramControlSetableInteger OBJECT-TYPE
        SYNTAX  INTEGER
        ACCESS  read-write
        STATUS  mandatory
        DESCRIPTION
                "A settable integer with no function."
        ::= { smMlmProgramSetableTestObjects 1}

smMlmProgramControlSetableCounter OBJECT-TYPE
        SYNTAX  Counter
        ACCESS  read-write
        STATUS  mandatory
        DESCRIPTION
                "A settable counter with no function."
        ::= { smMlmProgramSetableTestObjects 2}

smMlmProgramControlSetableGauge OBJECT-TYPE
        SYNTAX  Gauge
        ACCESS  read-write
        STATUS  mandatory
        DESCRIPTION
                "A settable gauge with no function."
        ::= { smMlmProgramSetableTestObjects 3}

smMlmProgramControlSetableIpAddress OBJECT-TYPE
        SYNTAX  IpAddress
        ACCESS  read-write
        STATUS  mandatory
        DESCRIPTION
                "A settable IP address with no function."
        ::= { smMlmProgramSetableTestObjects 4}

smMlmProgramControlSetableTimeTicks OBJECT-TYPE
        SYNTAX  TimeTicks
        ACCESS  read-write
        STATUS  mandatory
        DESCRIPTION
                "A settable TimeTicks with no function."
        ::= { smMlmProgramSetableTestObjects 5}

smMlmProgramControlSetableOctetString OBJECT-TYPE
        SYNTAX  DisplayString
        ACCESS  read-write
        STATUS  mandatory
        DESCRIPTION
                "A settable DisplayString with no function."
        ::= { smMlmProgramSetableTestObjects 6}


--
-- The Remote Manager Self-Monitoring Group
--
--  This group is used to see how much of the system resources the
--  system monitor itself is using up
--

smMlmResourceUsageTable OBJECT-TYPE
        SYNTAX  SEQUENCE OF SmMlmResourceUsageEntry
        ACCESS  not-accessible
        STATUS  mandatory
        DESCRIPTION
                "Mid-Level Manager resource utilization table."
        ::= { smMlmResourceUsage 1 }

smMlmResourceUsageEntry OBJECT-TYPE
        SYNTAX  SmMlmResourceUsageEntry
        ACCESS  not-accessible
        STATUS  mandatory
        DESCRIPTION
                "Each entry contains a different resource summary."
  INDEX { smMlmResourceUsageName }
        ::= { smMlmResourceUsageTable 1 }

SmMlmResourceUsageEntry ::= SEQUENCE {
  smMlmResourceUsageName
        DisplayString,
  smMlmResourceUsageUserTime
        TimeTicks,
  smMlmResourceUsageSystemTime
        TimeTicks,
  smMlmResourceUsageTotalTime
        TimeTicks,
  smMlmResourceUsageMaxrss
        Counter,
  smMlmResourceUsageIxrss
        Counter,
  smMlmResourceUsageIdrss
        Counter,
  smMlmResourceUsageIsrss
        Counter,
  smMlmResourceUsageMinflt
        Counter,
  smMlmResourceUsageMajflt
        Counter,
  smMlmResourceUsageNSwap
        Counter,
  smMlmResourceUsageInBlock
        Counter,
  smMlmResourceUsageOutBlock
        Counter,
  smMlmResourceUsageMsgsnd
        Counter,
  smMlmResourceUsageMsgrcv
        Counter,
  smMlmResourceUsageNSignals
        Counter,
  smMlmResourceUsageVcsw
        Counter,
  smMlmResourceUsageIcsw
        Counter
}

smMlmResourceUsageName OBJECT-TYPE
        SYNTAX  DisplayString
        ACCESS  read-only
        STATUS  mandatory
        DESCRIPTION
          "Self, child, and total."
        ::= { smMlmResourceUsageEntry 1 }

smMlmResourceUsageUserTime OBJECT-TYPE
        SYNTAX  TimeTicks
        ACCESS  read-only
        STATUS  mandatory
        DESCRIPTION
          "Amount of CPU time in user mode since start-up."
        ::= { smMlmResourceUsageEntry 2 }

smMlmResourceUsageSystemTime OBJECT-TYPE
        SYNTAX  TimeTicks
        ACCESS  read-only
        STATUS  mandatory
        DESCRIPTION
           "Amount of CPU time in system mode since start-up."
        ::= { smMlmResourceUsageEntry 3 }

smMlmResourceUsageTotalTime OBJECT-TYPE
        SYNTAX  TimeTicks
        ACCESS  read-only
        STATUS  mandatory
        DESCRIPTION
                "Total CPU time for process since start-up."
        ::= { smMlmResourceUsageEntry 4 }

smMlmResourceUsageMaxrss OBJECT-TYPE
        SYNTAX  Counter
        ACCESS  read-only
        STATUS  mandatory
        DESCRIPTION
                "Maximum resident set size."
        ::= { smMlmResourceUsageEntry 5 }

smMlmResourceUsageIxrss OBJECT-TYPE
        SYNTAX  Counter
        ACCESS  read-only
        STATUS  mandatory
        DESCRIPTION
                "Integral size (kilobyte-seconds)."
        ::= { smMlmResourceUsageEntry 6 }

smMlmResourceUsageIdrss OBJECT-TYPE
        SYNTAX  Counter
        ACCESS  read-only
        STATUS  mandatory
        DESCRIPTION
                "Unshared resident set size (kilobyte-seconds)."
        ::= { smMlmResourceUsageEntry 7 }

smMlmResourceUsageIsrss OBJECT-TYPE
        SYNTAX  Counter
        ACCESS  read-only
        STATUS  mandatory
        DESCRIPTION
                "Unshared stack set size (kilobyte-seconds).

                 Not supported on HP-UX"
        ::= { smMlmResourceUsageEntry 8 }

smMlmResourceUsageMinflt OBJECT-TYPE
        SYNTAX  Counter
        ACCESS  read-only
        STATUS  mandatory
        DESCRIPTION
                "Page faults serviced without I/O activity."
        ::= { smMlmResourceUsageEntry 9 }

smMlmResourceUsageMajflt OBJECT-TYPE
        SYNTAX  Counter
        ACCESS  read-only
        STATUS  mandatory
        DESCRIPTION
                "Page faults serviced with I/O activity."
        ::= { smMlmResourceUsageEntry 10 }

smMlmResourceUsageNSwap OBJECT-TYPE
        SYNTAX  Counter
        ACCESS  read-only
        STATUS  mandatory
        DESCRIPTION
                "Number of times a process swapped."
        ::= { smMlmResourceUsageEntry 11 }

smMlmResourceUsageInBlock OBJECT-TYPE
        SYNTAX  Counter
        ACCESS  read-only
        STATUS  mandatory
        DESCRIPTION
                "Number of times a file system performed input."
        ::= { smMlmResourceUsageEntry 12 }

smMlmResourceUsageOutBlock OBJECT-TYPE
        SYNTAX  Counter
        ACCESS  read-only
        STATUS  mandatory
        DESCRIPTION
                "Number of times a file system performed output."
        ::= { smMlmResourceUsageEntry 13 }

smMlmResourceUsageMsgsnd OBJECT-TYPE
        SYNTAX  Counter
        ACCESS  read-only
        STATUS  mandatory
        DESCRIPTION
                "Number of IPC messages sent."
        ::= { smMlmResourceUsageEntry 14 }

smMlmResourceUsageMsgrcv OBJECT-TYPE
        SYNTAX  Counter
        ACCESS  read-only
        STATUS  mandatory
        DESCRIPTION
                "Number of IPC messages received."
        ::= { smMlmResourceUsageEntry 15 }

smMlmResourceUsageNSignals OBJECT-TYPE
        SYNTAX  Counter
        ACCESS  read-only
        STATUS  mandatory
        DESCRIPTION
                "Number of signals received."
        ::= { smMlmResourceUsageEntry 16 }

smMlmResourceUsageVcsw OBJECT-TYPE
        SYNTAX  Counter
        ACCESS  read-only
        STATUS  mandatory
        DESCRIPTION
                "Number of voluntary context switches."
        ::= { smMlmResourceUsageEntry 17 }

smMlmResourceUsageIcsw OBJECT-TYPE
        SYNTAX  Counter
        ACCESS  read-only
        STATUS  mandatory
        DESCRIPTION
                "Number of involuntary context switches."
        ::= { smMlmResourceUsageEntry 18 }


--
--  The Remote Manager Message Group
--  Information and error messages are available here, most recent first
--

smMlmProgramMessagesTable OBJECT-TYPE
        SYNTAX  SEQUENCE OF SmMlmProgramMessagesEntry
        ACCESS  not-accessible
        STATUS  mandatory
        DESCRIPTION
                "Mid-Level Manager information and
                 error messages."
        ::= { smMlmProgramMessages 1 }

smMlmProgramMessagesEntry OBJECT-TYPE
        SYNTAX  SmMlmProgramMessagesEntry
        ACCESS  not-accessible
        STATUS  mandatory
        DESCRIPTION
                "Each entry contains a different message summary."
  INDEX { smMlmProgramMessagesRowNumber }
        ::= { smMlmProgramMessagesTable 1 }

SmMlmProgramMessagesEntry ::= SEQUENCE {
  smMlmProgramMessagesRowNumber
        INTEGER,
  smMlmProgramMessagesTime
        DisplayString,
  smMlmProgramMessagesText
        DisplayString,
  smMlmProgramMessagesTimeStamp
        INTEGER
}

smMlmProgramMessagesRowNumber OBJECT-TYPE
        SYNTAX  INTEGER
        ACCESS  read-only
        STATUS  mandatory
        DESCRIPTION
          "Table index - no real meaning."
        ::= { smMlmProgramMessagesEntry 1 }

smMlmProgramMessagesTime OBJECT-TYPE
        SYNTAX  DisplayString
        ACCESS  read-only
        STATUS  mandatory
        DESCRIPTION
                "Time at which the message was generated."
        ::= { smMlmProgramMessagesEntry 2 }

smMlmProgramMessagesText OBJECT-TYPE
        SYNTAX  DisplayString
        ACCESS  read-only
        STATUS  mandatory
        DESCRIPTION
                "Text of the message.  Truncated after 80 bytes"
        ::= { smMlmProgramMessagesEntry 3 }

smMlmProgramMessagesTimeStamp OBJECT-TYPE
        SYNTAX  INTEGER
        ACCESS  read-only
        STATUS  mandatory
        DESCRIPTION
           "Time (in seconds) at which message was generated."
        ::= { smMlmProgramMessagesEntry 4 }

--
-- Table for viewing Data Collect Log messages
--

smMlmProgramDataCollectTable OBJECT-TYPE
        SYNTAX  SEQUENCE OF SmMlmProgramDataCollectEntry
        ACCESS  not-accessible
        STATUS  mandatory
        DESCRIPTION
                "Mid-Level Manager information
                 and error messages."
        ::= { smMlmProgramMessages 2 }

smMlmProgramDataCollectEntry OBJECT-TYPE
        SYNTAX  SmMlmProgramDataCollectEntry
        ACCESS  not-accessible
        STATUS  mandatory
        DESCRIPTION
                "Each entry contains a different message summary."
  INDEX { smMlmProgramDataCollectRowNumber }
        ::= { smMlmProgramDataCollectTable 1 }

SmMlmProgramDataCollectEntry ::= SEQUENCE {
  smMlmProgramDataCollectRowNumber
        INTEGER,
  smMlmProgramDataCollectTime
        DisplayString,
  smMlmProgramDataCollectText
        DisplayString,
  smMlmProgramDataCollectTimeStamp
        INTEGER
}

smMlmProgramDataCollectRowNumber OBJECT-TYPE
        SYNTAX  INTEGER
        ACCESS  read-only
        STATUS  mandatory
        DESCRIPTION
                "Table index - no real meaning."
        ::= { smMlmProgramDataCollectEntry 1 }

smMlmProgramDataCollectTime OBJECT-TYPE
        SYNTAX  DisplayString
        ACCESS  read-only
        STATUS  mandatory
        DESCRIPTION
                "Time at which the message was generated."
        ::= { smMlmProgramDataCollectEntry 2 }

smMlmProgramDataCollectText OBJECT-TYPE
        SYNTAX  DisplayString
        ACCESS  read-only
        STATUS  mandatory
        DESCRIPTION
                "Text of the message.  Truncated after 80 bytes"
        ::= { smMlmProgramDataCollectEntry 3 }

smMlmProgramDataCollectTimeStamp OBJECT-TYPE
        SYNTAX  INTEGER
        ACCESS  read-only
        STATUS  mandatory
        DESCRIPTION
                "Time (in seconds) at which message was generated."
        ::= { smMlmProgramDataCollectEntry 4 }


--
-- Trap table for viewing the traps logged.
--

smMlmProgramTrapTable OBJECT-TYPE
        SYNTAX  SEQUENCE OF SmMlmProgramTrapEntry
        ACCESS  not-accessible
        STATUS  mandatory
        DESCRIPTION
                "Mid-Level Manager information and
                 error messages."
        ::= { smMlmProgramMessages 3 }

smMlmProgramTrapEntry OBJECT-TYPE
        SYNTAX  SmMlmProgramTrapEntry
        ACCESS  not-accessible
        STATUS  mandatory
        DESCRIPTION
                "Each entry contains a different message summary."
  INDEX { smMlmProgramTrapRowNumber }
        ::= { smMlmProgramTrapTable 1 }

SmMlmProgramTrapEntry ::= SEQUENCE {
  smMlmProgramTrapRowNumber
        INTEGER,
  smMlmProgramTrapTime
        DisplayString,
  smMlmProgramTrapText
        DisplayString,
  smMlmProgramTrapTimeStamp
        INTEGER
}

smMlmProgramTrapRowNumber OBJECT-TYPE
        SYNTAX  INTEGER
        ACCESS  read-only
        STATUS  mandatory
        DESCRIPTION
                "Table index - no real meaning."
        ::= { smMlmProgramTrapEntry 1 }

smMlmProgramTrapTime OBJECT-TYPE
        SYNTAX  DisplayString
        ACCESS  read-only
        STATUS  mandatory
        DESCRIPTION
                "Time at which the message was generated."
        ::= { smMlmProgramTrapEntry 2 }

smMlmProgramTrapText OBJECT-TYPE
        SYNTAX  DisplayString
        ACCESS  read-only
        STATUS  mandatory
        DESCRIPTION
                "Text of the message.  Truncated after 80 bytes"
        ::= { smMlmProgramTrapEntry 3 }

smMlmProgramTrapTimeStamp OBJECT-TYPE
        SYNTAX  INTEGER
        ACCESS  read-only
        STATUS  mandatory
        DESCRIPTION
                "Time (in seconds) at which message was generated."
        ::= { smMlmProgramTrapEntry 4 }

--
-- MIB variables corresponding to the environment variables carried in Trap,
-- whenever a threshold condition is met.
--

smMlmProgramEnvHostAddress OBJECT-TYPE
        SYNTAX  DisplayString
        ACCESS  not-accessible
        STATUS  mandatory
        DESCRIPTION
                "Host Address of the system running Mid-Level Manager."
        ::= { smMlmProgramEnvironmentVars 1}

smMlmProgramEnvHostName    OBJECT-TYPE
        SYNTAX  DisplayString
        ACCESS  not-accessible
        STATUS  mandatory
        DESCRIPTION
                "Host name of the system running Mid-Level Manager."
        ::= { smMlmProgramEnvironmentVars 2}

smMlmProgramEnvHostDomainName  OBJECT-TYPE
        SYNTAX  DisplayString
        ACCESS  not-accessible
        STATUS  mandatory
        DESCRIPTION
                "Domain name of the Mid-Level Manager."
        ::= { smMlmProgramEnvironmentVars 3}

smMlmProgramEnvTableVars  OBJECT IDENTIFIER ::= {smMlmProgramEnvironmentVars 4}
smMlmProgramEnvThresholdTableVars OBJECT IDENTIFIER ::= { smMlmProgramEnvTableVars 5 }

--
--  The Threshold Environment Variables
--

smMlmProgramEnvThresholdName OBJECT-TYPE
        SYNTAX  DisplayString
        ACCESS  not-accessible
        STATUS  mandatory
        DESCRIPTION
                "This field is not accessible. It is
                 inserted in MIB to obtain an object id
                 for the environment variable containing
                 the threshold table entry command name.
                 The object id of the environment variable
                 is carried in the threshold trap."
        ::= { smMlmProgramEnvThresholdTableVars 1 }

smMlmProgramEnvThresholdArmState OBJECT-TYPE
        SYNTAX  DisplayString
        ACCESS  not-accessible
        STATUS  mandatory
        DESCRIPTION
                "This field is not accessible. It is
                 inserted in MIB to obtain an object id
                 for the environment variable that indicates
                 whether the threshold is in arm or rearm state.
                 The object id of the environment variable
                 is carried in the threshold trap."
        ::= { smMlmProgramEnvThresholdTableVars 2 }

smMlmProgramEnvThresholdCondition OBJECT-TYPE
        SYNTAX  DisplayString
        ACCESS  not-accessible
        STATUS  mandatory
        DESCRIPTION
                "This field is not accessible. It is
                 inserted in MIB to obtain an object id
                 for the environment variable containing
                 the condition operation for threshold value.
                 The object id of the environment variable
                 is carried in the threshold trap."
        ::= { smMlmProgramEnvThresholdTableVars 3 }

smMlmProgramEnvThresholdValue OBJECT-TYPE
        SYNTAX  DisplayString
        ACCESS  not-accessible
        STATUS  mandatory
        DESCRIPTION
                "This field is not accessible. It is
                 inserted in MIB to obtain an object id
                 for the environment variable containing
                 the value of the condition against which
                 the variable value is tested.
                 The object id of the environment variable
                 is carried in the threshold trap."
        ::= { smMlmProgramEnvThresholdTableVars 4 }

smMlmProgramEnvThresholdNode OBJECT-TYPE
        SYNTAX  DisplayString
        ACCESS  not-accessible
        STATUS  mandatory
        DESCRIPTION
                "This field is not accessible. It is
                 inserted in MIB to obtain an object id
                 for the environment variable containing
                 the name of the node which was polled.
                 The object id of the environment variable
                 is carried in the threshold trap."
        ::= { smMlmProgramEnvThresholdTableVars 5 }

smMlmProgramEnvThresholdProxy OBJECT-TYPE
        SYNTAX  DisplayString
        ACCESS  not-accessible
        STATUS  mandatory
        DESCRIPTION
                "This field is not accessible. It is
                 inserted in MIB to obtain an object id
                 for the environment variable containing
                 the name of the proxy on the node which
                 was polled.  Null if not a proxy.
                 The object id of the environment variable
                 is carried in the threshold trap."
        ::= { smMlmProgramEnvThresholdTableVars 6 }


smMlmProgramEnvThresholdAddressNode OBJECT-TYPE
        SYNTAX  DisplayString
        ACCESS  not-accessible
        STATUS  mandatory
        DESCRIPTION
                "This field is not accessible. It is
                 inserted in MIB to obtain an object id
                 for the environment variable containing
                 the address of the node which was polled.
                 The object id of the environment variable
                 is carried in the threshold trap."
        ::= { smMlmProgramEnvThresholdTableVars 7 }


smMlmProgramEnvThresholdDomainName OBJECT-TYPE
        SYNTAX  DisplayString
        ACCESS  not-accessible
        STATUS  mandatory
        DESCRIPTION
                "This field is not accessible. It is
                 inserted in MIB to obtain an object id
                 for the environment variable containing
                 the domain name of the node which was polled.
                 The object id of the environment variable
                 is carried in the threshold trap."
        ::= { smMlmProgramEnvThresholdTableVars 8 }

smMlmProgramEnvThresholdPort OBJECT-TYPE
        SYNTAX  INTEGER
        ACCESS  not-accessible
        STATUS  mandatory
        DESCRIPTION
                "This field is not accessible. It is
                 inserted in MIB to obtain an object id
                 for the environment variable containing
                 the port corresponding to the subagent
                 or the proxy agent at the node which
                 was polled.
                 The object id of the environment variable
                 is carried in the threshold trap."
        ::= { smMlmProgramEnvThresholdTableVars 9 }

smMlmProgramEnvThresholdVarId OBJECT-TYPE
        SYNTAX  DisplayString
        ACCESS  not-accessible
        STATUS  mandatory
        DESCRIPTION
                "This field is not accessible. It is
                 inserted in MIB to obtain an object id
                 for the environment variable containing
                 the object Identifier of the variable polled.
                 The object id of the environment variable
                 is carried in the threshold trap."
        ::= { smMlmProgramEnvThresholdTableVars 10 }

smMlmProgramEnvThresholdVarType OBJECT-TYPE
        SYNTAX  DisplayString
        ACCESS  not-accessible
        STATUS  mandatory
        DESCRIPTION
                "This field is not accessible. It is
                 inserted in MIB to obtain an object id
                 for the environment variable containing
                 the type of the variable polled.
                 The object id of the environment variable
                 is carried in the threshold trap."
        ::= { smMlmProgramEnvThresholdTableVars 11 }

smMlmProgramEnvThresholdVarValue OBJECT-TYPE
        SYNTAX  DisplayString
        ACCESS  not-accessible
        STATUS  mandatory
        DESCRIPTION
                "This field is not accessible. It is
                 inserted in MIB to obtain an object id
                 for the environment variable containing
                 the value of the variable polled.
                 The object id of the environment variable
                 is carried in the threshold trap."
        ::= { smMlmProgramEnvThresholdTableVars 12 }

smMlmProgramEnvThresholdSeverity OBJECT-TYPE
        SYNTAX  DisplayString
        ACCESS  not-accessible
        STATUS  mandatory
        DESCRIPTION
                "This field is not accessible. It is
                 inserted in MIB to obtain an object id
                 for the environment variable containing
                 the value of the rearm or arm severity.
                 The object id of the environment variable
                 is carried in the threshold trap."
        ::= { smMlmProgramEnvThresholdTableVars 13 }

smMlmProgramEnvThresholdVarInstance OBJECT-TYPE
        SYNTAX  DisplayString
        ACCESS  not-accessible
        STATUS  mandatory
        DESCRIPTION
                "This field is not accessible. It is
                 inserted in MIB to obtain an object id
                 for the environment variable containing
                 the object Identifier instance of the variable
                 polled.  The object id of the environment
                 variable is carried in the threshold trap."
        ::= { smMlmProgramEnvThresholdTableVars 14 }

--
--  Session information
--

smMlmNetworkSessionInformation OBJECT IDENTIFIER ::= { smMlmNetworkInformation 1 }
smMlmNetworkIfStatusInformation OBJECT IDENTIFIER ::= { smMlmNetworkInformation 2 }

smMlmNetworkSessionCount OBJECT-TYPE
        SYNTAX  INTEGER
        ACCESS  read-only
        STATUS  mandatory
        DESCRIPTION
                "The number of open sessions."
        ::= { smMlmNetworkSessionInformation 1 }

--
--  The Session Table
--

smMlmNetworkSessionTable OBJECT-TYPE
        SYNTAX  SEQUENCE OF SmMlmNetworkSessionEntry
        ACCESS  not-accessible
        STATUS  mandatory
        DESCRIPTION
                "Session table - list of nodes with which this agent
                 is communicating."
        ::= { smMlmNetworkSessionInformation 2 }

smMlmNetworkSessionEntry OBJECT-TYPE
        SYNTAX  SmMlmNetworkSessionEntry
        ACCESS  not-accessible
        STATUS  mandatory
        DESCRIPTION
                "Each entry contains objects for a particular device"
        INDEX { smMlmNetworkSessionName }
        ::= { smMlmNetworkSessionTable 1 }

SmMlmNetworkSessionEntry ::= SEQUENCE {
    smMlmNetworkSessionName
        DisplayString,
    smMlmNetworkSessionCurrentState
        INTEGER,
    smMlmNetworkSessionLastStateChange
        DisplayString,
    smMlmNetworkSessionLastPollAttempt
        DisplayString,
    smMlmNetworkSessionAddressFamily
        INTEGER,
    smMlmNetworkSessionNetAddress
        DisplayString,
    smMlmNetworkSessionTransmitAttempts
        Counter,
    smMlmNetworkSessionPacketsReceived
        Counter,
    smMlmNetworkSessionLastTransmitTime
        DisplayString,
    smMlmNetworkSessionLastReceiveTime
        DisplayString,
    smMlmNetworkSessionMinimumResponseTime
        INTEGER,
    smMlmNetworkSessionRecentAverageResponseTime
        INTEGER,
    smMlmNetworkSessionLifeTimeAverageResponseTime
        INTEGER,
    smMlmNetworkSessionMaximumResponseTime
        INTEGER,
    smMlmNetworkSessionMinimumResponseTimeStamp
        DisplayString,
    smMlmNetworkSessionMaximumResponseTimeStamp
        DisplayString,
   smMlmNetworkSessionProxyAddress
        DisplayString,
    smMlmNetworkSessionPort
        INTEGER,
    smMlmNetworkSessionDomainName
        DisplayString
}

smMlmNetworkSessionName OBJECT-TYPE
        SYNTAX  DisplayString
        ACCESS  read-only
        STATUS  mandatory
        DESCRIPTION
                "Name or IP address of the node in the Mid-Level
                 Manager monitor session."
        ::= { smMlmNetworkSessionEntry 1 }

smMlmNetworkSessionCurrentState OBJECT-TYPE
        SYNTAX  INTEGER {
                down(1),  -- session down
                up(2)     -- session up
                }
        ACCESS  read-only
        STATUS  mandatory
        DESCRIPTION
                "Last known state of session"
        ::= { smMlmNetworkSessionEntry 2 }

smMlmNetworkSessionLastStateChange OBJECT-TYPE
        SYNTAX  DisplayString
        ACCESS  read-only
        STATUS  mandatory
        DESCRIPTION
                "Time at which session state last changed."
        ::= { smMlmNetworkSessionEntry 3 }

smMlmNetworkSessionLastPollAttempt OBJECT-TYPE
        SYNTAX  DisplayString
        ACCESS  read-only
        STATUS  mandatory
        DESCRIPTION
                "Time at which session was last polled."
        ::= { smMlmNetworkSessionEntry 4 }

smMlmNetworkSessionAddressFamily OBJECT-TYPE
        SYNTAX  INTEGER {
                unix(1),          -- local to host (pipes, portals)
                inet(2),          -- internetwork: UDP, TCP, etc.
                implink(3),       -- arpanet imp addresses
                pup(4),           -- pup protocols: e.g. BSP
                chaos(5),         -- mit CHAOS protocols
                ns(6),            -- XEROX NS protocols
                osi(7),           -- ISO protocols
                ecma(8),          -- european computer manufacturers
                datakit(9),       -- datakit protocols
                ccitt(10),        -- CCITT protocols, X.25 etc
                sna(11),          -- IBM SNA
                decnet(12),       -- DECnet
                dli(13),          -- DEC Direct data link interface
                lat(14),          -- LAT
                hylink(15),       -- NSC Hyperchannel
                appletalk(16),    -- Apple Talk
                route(17),        -- Internal Routing Protocol
                link(18),         -- Link layer interface
                xtpPseudo(19),    -- eXpress Transfer Protocol (no AF)
                intf(20),         -- Debugging use only
                rif(21),          -- raw interface
                netware(22),      -- netware interface
                reserved23(23),   -- reserved
                reserved24(24),   -- reserved
                reserved25(25),   -- reserved
                reserved26(26),   -- reserved
                reserved27(27),   -- reserved
                reserved28(28),   -- reserved
                reserved29(29),   -- reserved
                reserved30(30),   -- reserved
                reserved31(31),   -- reserved
                reserved32(32),   -- reserved
                unknown(65535)    -- unknown
                }
        ACCESS  read-only
        STATUS  mandatory
        DESCRIPTION
                "Address family used to communicate with session"
        ::= { smMlmNetworkSessionEntry 5 }

smMlmNetworkSessionNetAddress OBJECT-TYPE
        SYNTAX  DisplayString
        ACCESS  read-only
        STATUS  mandatory
        DESCRIPTION
                "Remote Address of session."
        ::= { smMlmNetworkSessionEntry 6 }

smMlmNetworkSessionTransmitAttempts OBJECT-TYPE
        SYNTAX  Counter
        ACCESS  read-only
        STATUS  mandatory
        DESCRIPTION
                "Number of send transmit attempts made on session."
        ::= { smMlmNetworkSessionEntry 7 }

smMlmNetworkSessionPacketsReceived OBJECT-TYPE
        SYNTAX  Counter
        ACCESS  read-only
        STATUS  mandatory
        DESCRIPTION
                "Number of packets received on session."
        ::= { smMlmNetworkSessionEntry 8 }

smMlmNetworkSessionLastTransmitTime OBJECT-TYPE
        SYNTAX  DisplayString
        ACCESS  read-only
        STATUS  mandatory
        DESCRIPTION
                "Last Time at which a transmission was sent"
        ::= { smMlmNetworkSessionEntry 9 }

smMlmNetworkSessionLastReceiveTime OBJECT-TYPE
        SYNTAX  DisplayString
        ACCESS  read-only
        STATUS  mandatory
        DESCRIPTION
                "Last Time at which a packet was received"
        ::= { smMlmNetworkSessionEntry 10 }

smMlmNetworkSessionMinimumResponseTime OBJECT-TYPE
        SYNTAX  INTEGER
        ACCESS  read-only
        STATUS  mandatory
        DESCRIPTION
                "Minimum round-trip time to session since start-up."
        ::= { smMlmNetworkSessionEntry 11 }

smMlmNetworkSessionRecentAverageResponseTime OBJECT-TYPE
        SYNTAX  INTEGER
        ACCESS  read-only
        STATUS  mandatory
        DESCRIPTION
                "Average response time for the most recent queries."
        ::= { smMlmNetworkSessionEntry 12 }

smMlmNetworkSessionLifeTimeAverageResponseTime OBJECT-TYPE
        SYNTAX  INTEGER
        ACCESS  read-only
        STATUS  mandatory
        DESCRIPTION
                "Average response time since start-up."
        ::= { smMlmNetworkSessionEntry 13 }

smMlmNetworkSessionMaximumResponseTime OBJECT-TYPE
        SYNTAX  INTEGER
        ACCESS  read-only
        STATUS  mandatory
        DESCRIPTION
                "Maximum round-trip time to session since start-up."
        ::= { smMlmNetworkSessionEntry 14 }

smMlmNetworkSessionMinimumResponseTimeStamp OBJECT-TYPE
        SYNTAX  DisplayString
        ACCESS  read-only
        STATUS  mandatory
        DESCRIPTION
                "Time stamp at which the SessionMinimumResponseTime
                 was set."
        ::= { smMlmNetworkSessionEntry 15 }

smMlmNetworkSessionMaximumResponseTimeStamp OBJECT-TYPE
        SYNTAX  DisplayString
        ACCESS  read-only
        STATUS  mandatory
        DESCRIPTION
                "Time stamp at which the SessionMaximumResponseTime
                 was set."
        ::= { smMlmNetworkSessionEntry 16 }

smMlmNetworkSessionProxyAddress OBJECT-TYPE
        SYNTAX  DisplayString
        ACCESS  read-only
        STATUS  mandatory
        DESCRIPTION
                "Proxy Address of session, if session is with a proxy agent."
        ::= { smMlmNetworkSessionEntry 17 }

smMlmNetworkSessionPort OBJECT-TYPE
        SYNTAX INTEGER
        ACCESS  read-only
        STATUS  mandatory
        DESCRIPTION
                "Remote port of session."
        ::= { smMlmNetworkSessionEntry 18 }

smMlmNetworkSessionDomainName OBJECT-TYPE
        SYNTAX  DisplayString
        ACCESS  read-only
        STATUS  mandatory
        DESCRIPTION
                "Domain Name of session."
        ::= { smMlmNetworkSessionEntry 19 }

--
--  The Network Interface Status Table
--

smMlmNetworkIfStatusTable OBJECT-TYPE
        SYNTAX  SEQUENCE OF SmMlmNetworkIfStatusEntry
        ACCESS  not-accessible
        STATUS  mandatory
        DESCRIPTION
                "Interface status table.  This table is used to
                 store the status and status checking protocol
                 (ie. ICMP for IP) for each interface.  This table
                 is populated as a direct result of entries in the
                 smMlmStatusMonitorTable."
        ::= { smMlmNetworkIfStatusInformation 1 }

smMlmNetworkIfStatusEntry OBJECT-TYPE
        SYNTAX  SmMlmNetworkIfStatusEntry
        ACCESS  not-accessible
        STATUS  mandatory
        DESCRIPTION
                "Each entry contains objects for a status checking
                 policy.  The configuration specified is applied to
                 all nodes and interfaces in the specified host."
        INDEX { smMlmNetworkIfStatusAddressFamily,
                smMlmNetworkIfStatusRawNetAddress }
        ::= { smMlmNetworkIfStatusTable 1 }

SmMlmNetworkIfStatusEntry ::= SEQUENCE {
    smMlmNetworkIfStatusAddressFamily
        INTEGER,
    smMlmNetworkIfStatusRawNetAddress
        OCTET STRING,
    smMlmNetworkIfStatusNetAddress
        DisplayString,
    smMlmNetworkIfStatusHostName
        DisplayString,
    smMlmNetworkIfStatusMonitorEntryName
        DisplayString,
    smMlmNetworkIfStatusMonitorFrequency
        DisplayString,
    smMlmNetworkIfStatusCurrentState
        INTEGER,
    smMlmNetworkIfStatusLastStateChange
        DisplayString,
    smMlmNetworkIfStatusLastStatusCheck
        DisplayString,
    smMlmNetworkIfStatusLastResponseTime
        DisplayString,
    smMlmNetworkIfStatusResetRoundTripStats
        INTEGER,
    smMlmNetworkIfStatusLastRoundTripTime
        TimeTicks,
    smMlmNetworkIfStatusNumRequestsTransmitted
        Counter,
    smMlmNetworkIfStatusNumResponsesReceived
        Counter,
    smMlmNetworkIfStatusAvgRoundTripTime
        TimeTicks,
    smMlmNetworkIfStatusMinRoundTripTime
        TimeTicks,
    smMlmNetworkIfStatusMinRoundTripTimeStamp
        DisplayString,
    smMlmNetworkIfStatusMaxRoundTripTime
        TimeTicks,
    smMlmNetworkIfStatusMaxRoundTripTimeStamp
        DisplayString,
    smMlmNetworkIfStatusLastUp
        DisplayString,
    smMlmNetworkIfStatusLastDown
        DisplayString
}

smMlmNetworkIfStatusAddressFamily OBJECT-TYPE
        SYNTAX  INTEGER {
                unix(1),          -- local to host (pipes, portals)
                inet(2),          -- internetwork: UDP, TCP, etc.
                implink(3),       -- arpanet imp addresses
                pup(4),           -- pup protocols: e.g. BSP
                chaos(5),         -- mit CHAOS protocols
                ns(6),            -- XEROX NS protocols
                osi(7),           -- ISO protocols
                ecma(8),          -- european computer manufacturers
                datakit(9),       -- datakit protocols
                ccitt(10),        -- CCITT protocols, X.25 etc
                sna(11),          -- IBM SNA
                decnet(12),       -- DECnet
                dli(13),          -- DEC Direct data link interface
                lat(14),          -- LAT
                hylink(15),       -- NSC Hyperchannel
                appletalk(16),    -- Apple Talk
                route(17),        -- Internal Routing Protocol
                link(18),         -- Link layer interface
                xtpPseudo(19),    -- eXpress Transfer Protocol (no AF)
                intf(20),         -- Debugging use only
                rif(21),          -- raw interface
                netware(22),      -- netware interface
                reserved23(23),   -- reserved
                reserved24(24),   -- reserved
                reserved25(25),   -- reserved
                reserved26(26),   -- reserved
                reserved27(27),   -- reserved
                reserved28(28),   -- reserved
                reserved29(29),   -- reserved
                reserved30(30),   -- reserved
                reserved31(31),   -- reserved
                reserved32(32),   -- reserved
                unknown(65535)    -- unknown
                }
        ACCESS  read-only
        STATUS  mandatory
        DESCRIPTION
                "This indicates the transport protocol used
                 and determines the status checking protocol
                 to be used."
        ::= { smMlmNetworkIfStatusEntry 1 }

smMlmNetworkIfStatusRawNetAddress OBJECT-TYPE
        SYNTAX  OCTET STRING
        ACCESS  read-only
        STATUS  mandatory
        DESCRIPTION
               "This field specifies the address of the interface
                in octets."
        ::= { smMlmNetworkIfStatusEntry 2 }

smMlmNetworkIfStatusNetAddress OBJECT-TYPE
        SYNTAX  DisplayString
        ACCESS  read-only
        STATUS  mandatory
        DESCRIPTION
               "This field specifies the address of the interface
                as a printable string."
        ::= { smMlmNetworkIfStatusEntry 3 }

smMlmNetworkIfStatusHostName OBJECT-TYPE
        SYNTAX  DisplayString
        ACCESS  read-only
        STATUS  mandatory
        DESCRIPTION
               "This field specifies the hostname that corresponds
                to the address specified in the smMlmNetworkIfStatusNetAddress
                field."
        ::= { smMlmNetworkIfStatusEntry 4 }

smMlmNetworkIfStatusMonitorEntryName OBJECT-TYPE
        SYNTAX  DisplayString
        ACCESS  read-only
        STATUS  mandatory
        DESCRIPTION
                "This field is used to correlate this entry with
                 the status monitor entry that governs the status
                 checking of this interface."
        ::= { smMlmNetworkIfStatusEntry 5 }

smMlmNetworkIfStatusMonitorFrequency OBJECT-TYPE
        SYNTAX  DisplayString
        ACCESS  read-only
        STATUS  mandatory
        DESCRIPTION
                "The frequency at which the interface is being
                 status checked.  This field reflects the frequency
                 configured in the governing status monitoring entry.
                 It is displayed for information purposes only.
                 In order to change this field the corresponding
                 governing status entry's frequency must be changed
                 or a new status entry may be introduced for this
                 interface which overrides the existing entry."
        ::= { smMlmNetworkIfStatusEntry 6 }

smMlmNetworkIfStatusCurrentState OBJECT-TYPE
        SYNTAX  INTEGER {
                unknown(1),  -- initial status of interface
                down(2),  -- interface down
                up(3)     -- interface up
                }
        ACCESS  read-only
        STATUS  mandatory
        DESCRIPTION
                "This indicates the current status of the interface."
        ::= { smMlmNetworkIfStatusEntry 7 }

smMlmNetworkIfStatusLastStateChange OBJECT-TYPE
        SYNTAX  DisplayString
        ACCESS  read-only
        STATUS  mandatory
        DESCRIPTION
                "This field displays the date/time string of the
                 last state change."
        ::= { smMlmNetworkIfStatusEntry 8 }

smMlmNetworkIfStatusLastStatusCheck OBJECT-TYPE
        SYNTAX  DisplayString
        ACCESS  read-only
        STATUS  mandatory
        DESCRIPTION
                "This field displays the date/time string of the
                 last time the interface status was checked."
        ::= { smMlmNetworkIfStatusEntry 9 }

smMlmNetworkIfStatusLastResponseTime OBJECT-TYPE
        SYNTAX  DisplayString
        ACCESS  read-only
        STATUS  mandatory
        DESCRIPTION
                "This field displays the date/time string of the
                 last time the status response was received."
        ::= { smMlmNetworkIfStatusEntry 10 }

smMlmNetworkIfStatusResetRoundTripStats OBJECT-TYPE
        SYNTAX  INTEGER {
                false(1), -- allow statistics to accumulate
                true(2)   -- reset statistics
                }
        ACCESS  read-write
        STATUS  mandatory
        DESCRIPTION
                "Setting this field to true(1) will reset the counts
                 for packets sent/received and last/max/min/avg
                 roundtrip times."
        ::= { smMlmNetworkIfStatusEntry 11 }

smMlmNetworkIfStatusNumRequestsTransmitted OBJECT-TYPE
        SYNTAX  Counter
        ACCESS  read-only
        STATUS  mandatory
        DESCRIPTION
                "This field contains a count of the total number
                 of status request packets sent since the entry was
                 instantiated (or the statistics were reset)."
        ::= { smMlmNetworkIfStatusEntry 12 }

smMlmNetworkIfStatusNumResponsesReceived OBJECT-TYPE
        SYNTAX  Counter
        ACCESS  read-only
        STATUS  mandatory
        DESCRIPTION
                "This field contains a count of the total number
                 of status response packets received since the
                 entry was instantiated (or the statistics were
                 reset)."
        ::= { smMlmNetworkIfStatusEntry 13 }

smMlmNetworkIfStatusLastRoundTripTime OBJECT-TYPE
        SYNTAX  TimeTicks
        ACCESS  read-only
        STATUS  mandatory
        DESCRIPTION
                "This field contains the number of time ticks
                 from the time the status packet was sent until
                 its response was received."
        ::= { smMlmNetworkIfStatusEntry 14 }

smMlmNetworkIfStatusAvgRoundTripTime OBJECT-TYPE
        SYNTAX  TimeTicks
        ACCESS  read-only
        STATUS  mandatory
        DESCRIPTION
                "This field contains the average round trip time
                 of the status packets received since the entry was
                 instantiated (or the statistics were reset)."
        ::= { smMlmNetworkIfStatusEntry 15 }

smMlmNetworkIfStatusMinRoundTripTime OBJECT-TYPE
        SYNTAX  TimeTicks
        ACCESS  read-only
        STATUS  mandatory
        DESCRIPTION
                "This field contains the minimum round trip time
                 of the status packets received since the entry was
                 instantiated (or the statistics were reset)."
        ::= { smMlmNetworkIfStatusEntry 16 }

smMlmNetworkIfStatusMinRoundTripTimeStamp OBJECT-TYPE
        SYNTAX  DisplayString
        ACCESS  read-only
        STATUS  mandatory
        DESCRIPTION
                "This field contains the time stamp for the
                 minimum round trip time."
        ::= { smMlmNetworkIfStatusEntry 17 }

smMlmNetworkIfStatusMaxRoundTripTime OBJECT-TYPE
        SYNTAX  TimeTicks
        ACCESS  read-only
        STATUS  mandatory
        DESCRIPTION
                "This field contains the maximum round trip time
                 of the status packets received since the entry was
                 instantiated (or the statistics were reset)."
        ::= { smMlmNetworkIfStatusEntry 18 }

smMlmNetworkIfStatusMaxRoundTripTimeStamp OBJECT-TYPE
        SYNTAX  DisplayString
        ACCESS  read-only
        STATUS  mandatory
        DESCRIPTION
                "This field contains the time stamp for the
                 maximum round trip time."
        ::= { smMlmNetworkIfStatusEntry 19 }

smMlmNetworkIfStatusLastUp OBJECT-TYPE
        SYNTAX  DisplayString
        ACCESS  read-only
        STATUS  mandatory
        DESCRIPTION
                "This field displays the date/time string of the
                 last up time."
        ::= { smMlmNetworkIfStatusEntry 20 }

smMlmNetworkIfStatusLastDown OBJECT-TYPE
        SYNTAX  DisplayString
        ACCESS  read-only
        STATUS  mandatory
        DESCRIPTION
                "This field displays the date/time string of the
                 last down time."
        ::= { smMlmNetworkIfStatusEntry 21 }

--
--  The Threshold and Collection Table
--

smMlmThresholdTable OBJECT-TYPE
        SYNTAX  SEQUENCE OF SmMlmThresholdEntry
        ACCESS  not-accessible
        STATUS  mandatory
        DESCRIPTION
                "Threshold table."
        ::= { smMlmThreshold 1 }

smMlmThresholdEntry OBJECT-TYPE
        SYNTAX  SmMlmThresholdEntry
        ACCESS  not-accessible
        STATUS  mandatory
        DESCRIPTION
                "Each entry contains objects for a particular threshold."
  INDEX { smMlmThresholdName }
        ::= { smMlmThresholdTable 1 }

SmMlmThresholdEntry ::= SEQUENCE {
    smMlmThresholdState
        INTEGER,
    smMlmThresholdName
        DisplayString,
    smMlmThresholdDescription
        DisplayString,
    smMlmThresholdOwnerID
        DisplayString,
    smMlmThresholdLocalRemoteMIBVariable
        DisplayString,
    smMlmThresholdCondition
        DisplayString,
    smMlmThresholdValue
        DisplayString,
    smMlmThresholdPollTime
        DisplayString,
    smMlmThresholdLastValue
        DisplayString,
    smMlmThresholdIntegerDataMin
        INTEGER,
    smMlmThresholdIntegerDataMax
        INTEGER,
    smMlmThresholdIntegerDataAvg
        INTEGER,
    smMlmThresholdArmSeverity
        INTEGER,
    smMlmThresholdReArmSeverity
        INTEGER,
    smMlmThresholdResultIndex
        INTEGER,
    smMlmThresholdResultsTableState
        INTEGER,
    smMlmThresholdTrapDescription
        DisplayString,
    smMlmThresholdArmEnterprise
        DisplayString,
    smMlmThresholdSpecificTrap
        INTEGER,
    smMlmThresholdCommandToExecute
        DisplayString,
    smMlmThresholdReArmCondition
        DisplayString,
    smMlmThresholdReArmValue
        DisplayString,
    smMlmThresholdReArmTrapDescription
        DisplayString,
    smMlmThresholdReArmSpecificTrap
        INTEGER,
    smMlmThresholdReArmEnterprise
        DisplayString,
    smMlmThresholdReArmCommandToExecute
        DisplayString,
    smMlmThresholdLastChangedSession
        DisplayString,
    smMlmThresholdStandardError
        DisplayString,
    smMlmThresholdLastResponseTime
        DisplayString,
    smMlmThresholdResponseCount
        Counter,
    smMlmThresholdTimeoutCount
        Counter,
    smMlmThresholdNoValueCount
        Counter,
    smMlmThresholdArmConditionMetCount
        Counter,
    smMlmThresholdReArmConditionMetCount
        Counter,
    smMlmThresholdThrottleArmCount
        INTEGER,
    smMlmThresholdThrottleReArmCount
        INTEGER,
    smMlmThresholdParticipationState
        INTEGER,
    smMlmThresholdActivationTime
        DisplayString,
    smMlmThresholdActivationDayOfWeek
        DisplayString,
    smMlmThresholdDeactivationTime
        DisplayString,
    smMlmThresholdDeactivationDayOfWeek
        DisplayString
}

smMlmThresholdState OBJECT-TYPE
        SYNTAX  INTEGER {
                enabledThresholdOnly(3),  -- threshold enabled only
                enabledStoreOnly(4),      -- store enabled only
                enabledThresholdStore(5), -- threshold and store enabled
                disabled(1),              -- threshold disabled
                invalid(2)                -- an invalidated threshold
                }
        ACCESS  read-write
        STATUS  mandatory
        DESCRIPTION
                "State for the threshold operation.  The store operation allows
                 the saving of the MIB variable data in a file during the
                 threshold polling process.  The threshold operation checks
                 the value of retrieved variables against a threshold; these
                 operations can be combined.
                 When the threshold entry is enabled, it may participate based
                 on threshold activation or deactivation times.  The threshold
                 entry is participating if the smMlmThresholdParticipationState
                 is set to active."
        ::= { smMlmThresholdEntry 1 }

smMlmThresholdName OBJECT-TYPE
        SYNTAX  DisplayString
        ACCESS  read-write
        STATUS  mandatory
        DESCRIPTION
                "This field is used as a label and as the SNMP instance
                 identifier for variables in this row.  The threshold name is
                 appended to the row variable to uniquely identify the instance
                 variable.  For example, the instance of smMlmThresholdState
                 (object ID .1.3.6.1.4.1.2.6.12.5.1.1.1) for a threshold
                 entry named A is 65, with the full object identifier
                 being .1.3.6.1.4.1.2.6.12.5.1.1.1.65.  Each octet in
                 in smMlmThresholdName is a value in dot notation for the
                 variable."
        ::= { smMlmThresholdEntry 2 }

smMlmThresholdDescription OBJECT-TYPE
        SYNTAX  DisplayString
        ACCESS  read-write
        STATUS  mandatory
        DESCRIPTION
                "This is a description of the threshold being performed for
                 the benefit of administrators only; it is not used by the
                 agent."
        ::= { smMlmThresholdEntry 3 }

smMlmThresholdOwnerID OBJECT-TYPE
        SYNTAX  DisplayString
        ACCESS  read-write
        STATUS  mandatory
        DESCRIPTION
                "Owner ID (IP address or hostname) who generated this
                 entry (not currently used)."
        ::= { smMlmThresholdEntry 4 }

smMlmThresholdLocalRemoteMIBVariable OBJECT-TYPE
        SYNTAX  DisplayString
        ACCESS  read-write
        STATUS  mandatory
        DESCRIPTION
                "This field specifies the MIB variable or expression on which
                 thresholding is to be performed, in dotted numeric notation,
                 followed by an instance identifier.  For example, to perform
                 threshold checking mib-2.interfaces.ifTable.ifEntry.ifInErrors
                 (object ID .1.3.6.1.2.1.2.2.1.14) for interface 1, this
                 field would contain .1.3.6.1.2.1.2.2.1.14.1.  To perform
                 threshold checking on all instances of a variable, an
                 asterisk can be used.  In the previous example, to perform
                 threshold checking on all interfaces, the object ID
                 .1.3.6.1.2.1.2.2.1.14.* would be entered.  The instance ID
                 can also be a non-numeric string, in which case each octet
                 in the string is converted to an object identifier.  For
                 example, to threshold on the smMlmSystemFileSystemPercentUsed
                 variable (object ID .1.3.6.1.4.1.2.6.12.2.5.2.1.4) for the
                 /usr directory, .1.3.6.1.4.1.2.6.12.2.5.2.1.4./usr would be
                 placed in this field since the Remote Manager filesystem
                 table uses the directory name as the index.  Most of the
                 tables supported by the Remote Manager use a name as an
                 index, so using the character form of the name provides a
                 simple way to specify an instance identifier.

                 Threshold MIB variable expressions can be any expression
                 comprised of local or remote node MIB variables with the
                 following high to low precedence and left to right associativity
                 of operators:

                     () : grouping
                     -  : unary minus
                     *  : multiplication, / : division, % : remainder
                     +  : addition, - : subtraction
                     << : bitwise left shift, >> : bitwise right shift
                     &  : bitwise AND
                     ^  : bitwise exclusive OR
                     |  : bitwise inclusive OR

                 Expression evaluation/operators are based on standard
                 c program execution.

                 Counter MIB variables default to the delta value, calculated
                 by subtracting the old MIB value from the current MIB value.
                 Integer and gauge MIB variables default to the current value
                 returned.  The two functions @delta() and @value() can be used
                 to override the above defaults.  Displaystrings can be converted
                 to a real value using the @delta() and @value() functions.

                 Built-in functions available within expressions include:

                     @sum(MIB variable expression, MIB variable expression, ...) -
                      returns the sum of all values.
                     @avg(MIB variable expression, MIB variable expression, ...) -
                      returns the average of all values.
                     @min(MIB variable expression, MIB variable expression, ...) -
                      returns the minimum of all values.
                     @max(MIB variable expression, MIB variable expression, ...) -
                      returns the maximum of all values.
                     @diff(MIB variable expression, MIB variable expression) -
                      returns the positive difference in the two expressions.
                     @delta(MIB variable expression) - uses the delta value
                      calculated by subtracting the last returned MIB variable
                      value from the current MIB variable value.  This function
                      can be used to force delta calculations on integer, gauge,
                      and displaystring MIB variables.
                     @value(MIB variable expression) - uses the current MIB
                      variable value.  This function can be used to force the
                      use of actual values for counter MIB variables.
                     @numInst(MIB variable expression) - returns the number
                      of instances found for the MIB variable expression.
                     @abs(MIB variable expression) - returns the positive
                       value of the expression.
                     @rand() - returns a random number between 0 and
                       42949667295.

                 The \ character can be used as an escape character in the
                 object ID to input the special character: period(.).  For
                 example: .1.3.6.1.2.1.2.2.1.14.1.\. replaces the \. with
                 the integer 46, the ASCII decimal value for period(.).

                 Agent Policy Manager (APM) uses the special string: {NV_x.x.x.x}
                 as part of the object ID and the periods within the string ARE
                 converted to the ASCII decimal value of 46.  In other words,
                 the periods are treated as characters instead of object ID
                 delimiters.

                 When using the Mid-Level Manager, if a name followed by a
                 colon is prepended to the object identifier, it is taken
                 to be an alias for a group of nodes (if defined in the Remote
                 Manager Alias Table) or the name of a remote node.  For
                 example, entering aixnm007:1.3.6.1.2.1.2.2.1.14.* will cause
                 threshold checking to be performed on all instances of
                 ifInErrors on machine aixnm007.  If aixnm007 is defined in the
                 Alias Table as an alias for a group of machines, threshold
                 checking of these variables will be done for every machine in
                 the group."
         ::= { smMlmThresholdEntry 5 }

smMlmThresholdCondition OBJECT-TYPE
        SYNTAX  DisplayString
        ACCESS  read-write
        STATUS  mandatory
        DESCRIPTION
                "Condition operation for the threshold value.

                      [type keyword] [statistics keyword] condition

                 Allowed conditions are: =, >, >=, >+, <, <=, <-, !=, !,
                 ~, ~=, !~, !~=, &, |, changes, doesNotChange, exists,
                 and doesNotExist.

                 The ~(LIKE) condition is for extended regular expression
                 checking on strings.  The style of the regular expression
                 is of the format for the ed or egrep command.  The ~(LIKE)
                 is case insensitive, while the ~=(LIKE CASE) is case sensitive.

                 The >+ and <- condition checks for a value increase(>+) above
                 or a value decrease(<-) below the threshold value on
                 consecutive polls.  Once the condition is met the rearm
                 condition is also checked on consecutive polls.

                 The change condition causes a watchdog operation to be
                 performed.  That is, if the value changes between
                 consecutive polls, the condition is satisfied.  (The
                 threshold value is ignored in this case).

                 Similarly, the exist/doesNotExist checks for the actual
                 existence of the MIB variable;  this is useful for
                 checking for the existence of rows in a table.

                 The & and | conditions cause the MIB variable value to
                 be ANDed/Ored with threshold value; if the result is
                 nonzero, the condition is met and the trap and/or
                 command to execute is performed.

                 NOTE: Thresholds for Counter variables are computed by
                 calculating the change(delta) in the sampled values and
                 comparing this against the threshold value.  In the case of
                 Gauge and INTEGER variables, the actual value of the
                 variable is checked against the threshold value.

                 The statistics keywords 'iMax', 'iMin', 'iAvg', 'iSd', 'iVar',
                 'iRate', 'Max', 'Min', 'Avg', 'Sd', and 'Var' if placed in
                 front of the condition (and separated from if by a space) allows
                 the use of the interval or lifetime maximum, minimum, average,
                 standard deviation, variance, and rate.  These values are
                 calculated for each MIB variable returned in the threshold.
                 For the interval keywords the sampling interval is defined
                 by the MIB variable: smMlmProgramControlSamplesPerInterval.
                 For example, if the smMlmProgramControlSamplesPerInterval is 10
                 then the 'iAvg' keyword is the average value of the last ten
                 samples returned to the threshold for each MIB value.

                 The type keywords 'delta' and 'value', if placed in front of the
                 condition or statistics keywords (and separated from it by
                 a space) will override this default behavior.  For example,
                 a condition of 'value >' will cause threshold checking to be
                 performed against the actual value rather than the change in
                 the value even if the selected MIB variable is a Counter; a
                 condition of 'delta >' causes the change in the variable
                 (from the previous value) to be checked against the threshold,
                 regardless of the type of the variable."
        ::= { smMlmThresholdEntry 6 }

smMlmThresholdValue OBJECT-TYPE
        SYNTAX  DisplayString
        ACCESS  read-write
        STATUS  mandatory
        DESCRIPTION
               "This field specifies the value against which retrieved
                variables are checked.  The type of check which is done
                depends on the type of the retrieved variable.  If the
                variable is numeric (INTEGER, Counter, etc.) this field is
                presumed to be a number, and a numeric comparison is performed
                using the specified threshold condition.  If the retrieved
                variable is a DisplayString (OCTET STRING) and the 'value'
                keyword is used on the condition then both the
                retrieved variable and this field can be converted to a
                floating point number, a floating-point comparison is done;
                otherwise a string comparison is done.

	        If the ~(LIKE) or ~=(LIKE CASE) condition is used then
                the value can be an extended regular expression.

                A value expression is also allowed to be specified.  The
                expression can be any expression comprised of the following
                functions:

                   'Min'   - lifetime minimum    'iMin'   - interval minimum
                   'Max'   - lifetime maximum    'iMax'   - interval maximum
                   'Avg'   - lifetime average    'iAvg'   - interval average
                   'Sd'    - lifetime standard   'iSd'    - interval standard
                             deviation                      deviation
                   'Var'   - lifetime variance   'iVar'   - interval variance
                   'Smpls' - lifetime samples    'iSmpls' - interval samples
                   'sTime' - sample time in secs 'iTime'  - interval time in secs
                                                 'iRate'  - rate of change over the
                                                            interval
                 The interval is defined by the MIB variable:
                 smMlmProgramControlSamplesPerInterval.

                 The expression has the following high to low precedence and left
                 to right associativity of operators:

                     () : grouping
                     -  : unary minus
                     *  : multiplication, / : division, % : remainder
                     +  : addition, - : subtraction
                     << : bitwise left shift, >> : bitwise right shift
                     &  : bitwise AND
                     ^  : bitwise exclusive OR
                     |  : bitwise inclusive OR

                 Expression evaluation/operators are based on standard
                 c program execution.

                 For example: Avg+2*Sd is the average value over the
                              lifetime of the threshold plus two times
                              the standard deviation."
        ::= { smMlmThresholdEntry 7 }

smMlmThresholdPollTime OBJECT-TYPE
        SYNTAX  DisplayString
        ACCESS  read-write
        STATUS  mandatory
        DESCRIPTION
                "Threshold polling time.  Polling units are decimal values
                 appended by the unit: d - day, h - hour, m - minute, or
                 s - second.  If no unit is appended, the value is minutes.
                 Multiple values/units are allowed (i.e. 1h45m = 1 hour,
                 45 minutes).
                 The default poll time is 1 minute."
        ::= { smMlmThresholdEntry 8 }

smMlmThresholdLastValue OBJECT-TYPE
        SYNTAX  DisplayString
        ACCESS  read-only
        STATUS  mandatory
        DESCRIPTION
                "Last threshold value retrieved, in human-readable form.
                 If more than one numeric value was retrieved for the
                 threshold (because an alias was used or because multiple
                 instances were retrieved), this field contains a note
                 to see the Threshold Results Table for multiple results."
        ::= { smMlmThresholdEntry 9 }

smMlmThresholdIntegerDataMax OBJECT-TYPE
        SYNTAX  INTEGER
        ACCESS  read-only
        STATUS  obsolete
        DESCRIPTION
                "Not Implemented."
        ::= { smMlmThresholdEntry 10 }

smMlmThresholdIntegerDataMin OBJECT-TYPE
        SYNTAX  INTEGER
        ACCESS  read-only
        STATUS  obsolete
        DESCRIPTION
                "Not Implemented."
        ::= { smMlmThresholdEntry 11 }

smMlmThresholdIntegerDataAvg OBJECT-TYPE
        SYNTAX  INTEGER
        ACCESS  read-only
        STATUS  obsolete
        DESCRIPTION
                "Not Implemented."
        ::= { smMlmThresholdEntry 12 }

smMlmThresholdArmSeverity OBJECT-TYPE
        SYNTAX  INTEGER (0..4294967295)
        ACCESS  read-write
        STATUS  mandatory
        DESCRIPTION
                "This field specifies the severity for the trap
                 which is to be sent when an arm condition is
                 met.  Default is 1."
        ::= { smMlmThresholdEntry 13 }

smMlmThresholdReArmSeverity OBJECT-TYPE
        SYNTAX  INTEGER (0..4294967295)
        ACCESS  read-write
        STATUS  mandatory
        DESCRIPTION
                "This field specifies the severity for the trap
                 which is to be sent when a rearm condition is
                 met.  Default is 0."
        ::= { smMlmThresholdEntry 14 }

smMlmThresholdResultIndex OBJECT-TYPE
        SYNTAX  INTEGER {
                integer(2),  -- result is integer
                counter(3),  -- result is counter
                gauge(4)     -- result is gauge
                }
        ACCESS  read-write
        STATUS  mandatory
        DESCRIPTION
                "Index to point to the expression result type.  The index
                 defines how the expression is evaluated, either using signed
                 arithmetic for integer or unsigned arithmetic for counter
                 and gauge.  The result for counter wraps on overflow or
                 underflow; the result for gauge latches at 0 for underflow
                 or 4294967295 for overflow.  Default value is integer."
        ::= { smMlmThresholdEntry 15 }

smMlmThresholdResultsTableState OBJECT-TYPE
        SYNTAX  INTEGER {
                enabled(1),  -- Threshold Results and Statistics enabled
                disabled(2)  -- Threshold Results and Statistics disabled
                }
        ACCESS  read-write
        STATUS  mandatory
        DESCRIPTION
                "When enabled the threshold result(s) are stored in the
                 Threshold Result Table.  When disabled, no entries are
                 generated for the Threshold Result Table.

                 Default is enabled."
        ::= { smMlmThresholdEntry 16 }

smMlmThresholdTrapDescription OBJECT-TYPE
        SYNTAX  DisplayString
        ACCESS  read-write
        STATUS  mandatory
        DESCRIPTION
               "A human-readable description for the trap to be generated;
                this description is sent in the trap for operator use.
                The environment variables listed below, pre-appended with a $
                sign, are allowed in the trap description field.

                   SM6K_HOSTNAME={hostname running subagent}
                   SM6K_DOMAIN_NAME={fully qualified hostname}
                   SM6K_HOST_ADDRESS={ip address}
                   SM6K_INSTANCE_NAME={instance string of row}
                   SM6K_INSTANCE_ID={instance ASCII octet value of row}
                   SM6K_THRESHOLD_CONDITION={condition in the threshold}
                   SM6K_THRESHOLD_VALUE={threshold value}
                   SM6K_THRESHOLD_ARMSTATE={-1 for arm, 0 for rearm}
                   SM6K_THRESHOLD_THROTTLE_COUNT={count for arm or rearm}
                   SM6K_THRESHOLD_NODE={node on which threshold condition was met}
                   SM6K_THRESHOLD_VAR_OID={Object ID of variable for the threshold}
                   SM6K_THRESHOLD_VAR_INSTANCE={instance for Object ID}
                   SM6K_THRESHOLD_VAR_TYPE={Integer|Counter|Gauge}
                   SM6K_THRESHOLD_VAR_VALUE={value of variable for the threshold}
                   SM6K_THRESHOLD_VAR_OLDVALUE={previous value of variable}
                   SM6K_THRESHOLD_SEVERITY={severity of threshold condition}"

        ::= { smMlmThresholdEntry 17 }

smMlmThresholdArmEnterprise OBJECT-TYPE
        SYNTAX  DisplayString
        ACCESS  read-write
        STATUS  mandatory
        DESCRIPTION
                "This field specifies the SNMP enterprise id for the trap
                 which is to be sent when a threshold condition is met.  If
                 this is not set, a default will be used."
        ::= { smMlmThresholdEntry 18 }

smMlmThresholdSpecificTrap OBJECT-TYPE
        SYNTAX  INTEGER
        ACCESS  read-write
        STATUS  mandatory
        DESCRIPTION
               "This field specifies a specific trap number to be sent
                when a threshold condition is met.  If this value is zero,
                no trap will be sent."
        ::= { smMlmThresholdEntry 19 }

smMlmThresholdCommandToExecute OBJECT-TYPE
        SYNTAX  DisplayString
        ACCESS  read-write
        STATUS  mandatory
        DESCRIPTION
                "Command to execute when threshold is met.  A value of
                 blank means no command is to be executed on a threshold
                 met condition. Environment variables which are available
                 on execution are:

                   SM6K_HOSTNAME={hostname running subagent}
                   SM6K_DOMAIN_NAME={fully qualified hostname}
                   SM6K_HOST_ADDRESS={ip address}
                   SM6K_INSTANCE_NAME={instance string of row}
                   SM6K_INSTANCE_ID={instance ASCII octet value of row}
                   SM6K_EXECUTION_REASON=Threshold
                   SM6K_THRESHOLD_CONDITION={condition in the threshold}
                   SM6K_THRESHOLD_VALUE={threshold value}
                   SM6K_THRESHOLD_ARMSTATE={-1 for arm, 0 for rearm}
                   SM6K_THRESHOLD_THROTTLE_COUNT={count for arm or rearm}
                   SM6K_THRESHOLD_NODE={node on which threshold condition was met}
                   SM6K_THRESHOLD_VAR_OID={Object ID of variable for the threshold}
                   SM6K_THRESHOLD_VAR_INSTANCE={instance for Object ID}
                   SM6K_THRESHOLD_VAR_TYPE={Integer|Counter|Gauge}
                   SM6K_THRESHOLD_VAR_VALUE={value of variable for the threshold}
                   SM6K_THRESHOLD_VAR_OLDVALUE={previous value of variable}
                   SM6K_THRESHOLD_SEVERITY={severity of threshold condition}"
        ::= { smMlmThresholdEntry 20 }

smMlmThresholdReArmCondition OBJECT-TYPE
        SYNTAX  DisplayString
        ACCESS  read-write
        STATUS  mandatory
        DESCRIPTION
                "Condition operation for the rearm threshold value.

                      [type keyword] [statistics keyword] condition

                 Allowed conditions are: =, >, >=, >+, <, <=, <-, !=, !,
                 ~, ~=, !~, !~=, &, |, changes, doesNotChange, exists,
                 and doesNotExist.

                 Checking against the rearm condition is started when a
                 threshold is reached and is stopped when the rearm condition
                 is met.  Once the rearm condition is met, the threshold
                 condition operation is restarted.

                 The ~(LIKE) condition is for extended regular expression
                 checking on strings.  The style of the regular expression
                 is of the format for the ed or egrep command.  The ~(LIKE)
                 is case insensitive, while the ~=(LIKE CASE) is case sensitive.

                 The >+ and <- condition checks for a value increase(>+) above
                 or a value decrease(<-) below the threshold value on
                 consecutive polls.  Once the condition is met the arm
                 condition is also checked on consecutive polls.

                 NOTE: Thresholds for Counter variables are computed by
                 calculating the change per second in the sampled values and
                 comparing these against the threshold value.  In the case of
                 Gauge and INTEGER variables, the actual value of the variable
                 is checked against the threshold value.

                 The statistics keywords 'iMax', 'iMin', 'iAvg', 'iSd', 'iVar',
                 'iRate', 'Max', 'Min', 'Avg', 'Sd', and 'Var' if placed in
                 front of the condition (and separated from if by a space) allows
                 the use of the interval or lifetime maximum, minimum, average,
                 standard deviation, variance, and rate.  These values are
                 calculated for each MIB variable returned in the threshold.
                 For the interval keywords the sampling interval is defined
                 by the MIB variable: smMlmProgramControlSamplesPerInterval.
                 For example, if the smMlmProgramControlSamplesPerInterval is 10
                 then the 'iAvg' keyword is the average value of the last ten
                 samples returned to the threshold for each MIB value.

                 The type keywords 'delta' and 'value', if placed in front of the
                 condition or statistics keywords (and separated from it by
                 a space) will override this default behavior.  For example,
                 a condition of 'value >' will cause threshold checking to be
                 performed against the actual value rather than the change in
                 the value even if the selected MIB variable is a Counter; a
                 condition of 'delta >' causes the change in the variable
                 (from the previous value) to be checked against the threshold,
                 regardless of the type of the variable."
        ::= { smMlmThresholdEntry 21 }

smMlmThresholdReArmValue OBJECT-TYPE
        SYNTAX  DisplayString
        ACCESS  read-write
        STATUS  mandatory
        DESCRIPTION
               "This field specifies the value against which retrieved
                variables are checked.  The type of check which is done
                depends on the type of the retrieved variable.  If the
                variable is numeric (INTEGER, Counter, etc.) this field is
                presumed to be a number, and a numeric comparison is performed
                using the specified threshold condition.  If the retrieved
                variable is a DisplayString (OCTET STRING) and the 'value'
                keyword is used on the condition then both the
                retrieved variable and this field can be converted to a
                floating point number, a floating-point comparison is done;
                otherwise a string comparison is done.

	        If the ~(LIKE) or ~=(LIKE CASE) condition is used then
                the value can be an extended regular expression.

                A value expression is also allowed to be specified.  The
                expression can be any expression comprised of the following
                functions:

                   'Min'   - lifetime minimum    'iMin'   - interval minimum
                   'Max'   - lifetime maximum    'iMax'   - interval maximum
                   'Avg'   - lifetime average    'iAvg'   - interval average
                   'Sd'    - lifetime standard   'iSd'    - interval standard
                             deviation                      deviation
                   'Var'   - lifetime variance   'iVar'   - interval variance
                   'Smpls' - lifetime samples    'iSmpls' - interval samples
                   'sTime' - sample time in secs 'iTime'  - interval time in secs
                                                 'iRate'  - rate of change over the
                                                            interval
                 The interval is defined by the MIB variable:
                 smMlmProgramControlSamplesPerInterval.

                 The expression has the following high to low precedence and left
                 to right associativity of operators:

                     () : grouping
                     -  : unary minus
                     *  : multiplication, / : division, % : remainder
                     +  : addition, - : subtraction
                     << : bitwise left shift, >> : bitwise right shift
                     &  : bitwise AND
                     ^  : bitwise exclusive OR
                     |  : bitwise inclusive OR

                 Expression evaluation/operators are based on standard
                 c program execution.

                 For example: Avg+2*Sd is the average value over the
                              lifetime of the threshold plus two times
                              the standard deviation."
        ::= { smMlmThresholdEntry 22 }

smMlmThresholdReArmTrapDescription OBJECT-TYPE
        SYNTAX  DisplayString
        ACCESS  read-write
        STATUS  mandatory
        DESCRIPTION
                "Trap description for the generated rearm trap.
                 The environment variables listed below, pre-appended with a $
                 sign, are allowed in the trap description field.

                   SM6K_HOSTNAME={hostname running subagent}
                   SM6K_DOMAIN_NAME={fully qualified hostname}
                   SM6K_HOST_ADDRESS={ip address}
                   SM6K_INSTANCE_NAME={instance string of row}
                   SM6K_INSTANCE_ID={instance ASCII octet value of row}
                   SM6K_THRESHOLD_CONDITION={condition in the threshold}
                   SM6K_THRESHOLD_VALUE={threshold value}
                   SM6K_THRESHOLD_ARMSTATE={-1 for arm, 0 for rearm}
                   SM6K_THRESHOLD_THROTTLE_COUNT={count for arm or rearm}
                   SM6K_THRESHOLD_NODE={node on which threshold condition was met}
                   SM6K_THRESHOLD_VAR_OID={Object ID of variable for the threshold}
                   SM6K_THRESHOLD_VAR_INSTANCE={instance for Object ID}
                   SM6K_THRESHOLD_VAR_TYPE={Integer|Counter|Gauge}
                   SM6K_THRESHOLD_VAR_VALUE={value of variable for the threshold}
                   SM6K_THRESHOLD_VAR_OLDVALUE={previous value of variable}
                   SM6K_THRESHOLD_SEVERITY={severity of threshold condition}"
        ::= { smMlmThresholdEntry 23 }

smMlmThresholdReArmEnterprise OBJECT-TYPE
        SYNTAX  DisplayString
        ACCESS  read-write
        STATUS  mandatory
        DESCRIPTION
                "This field specifies the SNMP enterprise id for the trap
                 which is to be sent when a rearm condition is met.  If
                 this is not set, a default will be used."
        ::= { smMlmThresholdEntry 24 }

smMlmThresholdReArmSpecificTrap OBJECT-TYPE
        SYNTAX  INTEGER
        ACCESS  read-write
        STATUS  mandatory
        DESCRIPTION
               "This field specifies a specific trap number to be sent
                when a rearm condition is met.  If this value is zero,
                no trap will be sent."
        ::= { smMlmThresholdEntry 25 }

smMlmThresholdReArmCommandToExecute OBJECT-TYPE
        SYNTAX  DisplayString
        ACCESS  read-write
        STATUS  mandatory
        DESCRIPTION
                "Command to execute when the rearm threshold is met.
                 A value of blank means no command will be executed
                 on a rearm threshold met condition.  Environment
                 variables which are available on execution are:

                   SM6K_HOSTNAME={hostname running subagent}
                   SM6K_DOMAIN_NAME={fully qualified hostname}
                   SM6K_HOST_ADDRESS={ip address}
                   SM6K_INSTANCE_NAME={instance string of row}
                   SM6K_INSTANCE_ID={instance ASCII octet value of row}
                   SM6K_EXECUTION_REASON=Threshold
                   SM6K_THRESHOLD_CONDITION={condition in the threshold}
                   SM6K_THRESHOLD_VALUE={threshold value}
                   SM6K_THRESHOLD_ARMSTATE={-1 for arm, 0 for rearm}
                   SM6K_THRESHOLD_THROTTLE_COUNT={count for arm or rearm}
                   SM6K_THRESHOLD_NODE={node on which threshold condition was met}
                   SM6K_THRESHOLD_VAR_OID={Object ID of variable for the threshold}
                   SM6K_THRESHOLD_VAR_INSTANCE={instance for Object ID}
                   SM6K_THRESHOLD_VAR_TYPE={integer|counter|gauge}
                   SM6K_THRESHOLD_VAR_VALUE={value of variable for the threshold}
                   SM6K_THRESHOLD_VAR_OLDVALUE={previous value of variable}
                   SM6K_THRESHOLD_SEVERITY={severity of threshold condition}"
        ::= { smMlmThresholdEntry 26 }

smMlmThresholdLastChangedSession OBJECT-TYPE
        SYNTAX  DisplayString
        ACCESS  read-only
        STATUS  mandatory
        DESCRIPTION
               "This field contains the name of the last node for which a
                threshold arm/rearm condition was met."
        ::= { smMlmThresholdEntry 27 }

smMlmThresholdStandardError OBJECT-TYPE
        SYNTAX  DisplayString
        ACCESS  read-only
        STATUS  mandatory
        DESCRIPTION
               "This field contains informational and error messages for
                this threshold entry."
        ::= { smMlmThresholdEntry 28 }

smMlmThresholdLastResponseTime OBJECT-TYPE
        SYNTAX  DisplayString
        ACCESS  read-only
        STATUS  mandatory
        DESCRIPTION
               "This field contains the last time a (valid or invalid)
                response was received to a poll request."
        ::= { smMlmThresholdEntry 29 }

smMlmThresholdResponseCount OBJECT-TYPE
        SYNTAX  Counter
        ACCESS  read-only
        STATUS  mandatory
        DESCRIPTION
                "Number of responses received to date."
        ::= { smMlmThresholdEntry 30 }

smMlmThresholdTimeoutCount OBJECT-TYPE
        SYNTAX  Counter
        ACCESS  read-only
        STATUS  mandatory
        DESCRIPTION
                "Number of timeout conditions, indicating no response or an
                 overrun condition (polling speed faster than the response
                 time from the node(s) being queried)."
        ::= { smMlmThresholdEntry 31 }

smMlmThresholdNoValueCount OBJECT-TYPE
        SYNTAX  Counter
        ACCESS  read-only
        STATUS  mandatory
        DESCRIPTION
               "Number of responses received containing no values.  These
                responses may be caused by an invalid community name, by
                a remote SNMP subagent being down, or by a thresholding on
                a variable for which no instances exist."
        ::= { smMlmThresholdEntry 32 }

smMlmThresholdArmConditionMetCount OBJECT-TYPE
        SYNTAX  Counter
        ACCESS  read-only
        STATUS  mandatory
        DESCRIPTION
               "This field contains the total count that the arm condition
                has been met."
        ::= { smMlmThresholdEntry 33 }

smMlmThresholdReArmConditionMetCount OBJECT-TYPE
        SYNTAX  Counter
        ACCESS  read-only
        STATUS  mandatory
        DESCRIPTION
               "This field contains the total count that the rearm condition
                has been met."
        ::= { smMlmThresholdEntry 34 }

smMlmThresholdThrottleArmCount OBJECT-TYPE
        SYNTAX  INTEGER (0..4294967295)
        ACCESS  read-write
        STATUS  mandatory
        DESCRIPTION
                "This field specifies the number of consecutive arm
                 conditions which must be met before the threshold
                 is armed.  The ThresholdPollTime times the
                 ThresholdThrottleArmCount minus 1 is the time
                 interval in which the arm condition has been met.
                 A value of 0 defaults to 1."
        ::= { smMlmThresholdEntry 35 }

smMlmThresholdThrottleReArmCount OBJECT-TYPE
        SYNTAX  INTEGER (0..4294967295)
        ACCESS  read-write
        STATUS  mandatory
        DESCRIPTION
                "This field specifies the number of consecutive rearm
                 conditions which must be met before the threshold
                 is rearmed.  The ThresholdPollTime times the
                 ThresholdThrottleReArmCount minus 1 is the time
                 interval in which the rearm condition has been met.
                 A value of 0 defaults to 1."
        ::= { smMlmThresholdEntry 36 }

smMlmThresholdParticipationState OBJECT-TYPE
        SYNTAX  INTEGER {
                active(2),      -- threshold is participating
                notEnabled(1),  -- thresholding not enabled in smMlmThresholdState
                inactive(3)     -- threshold is dormant
                }
        ACCESS  read-only
        STATUS  mandatory
        DESCRIPTION
                "This field indicates whether or not the entry is participating
                 in the threshold.  When the threshold entry is active,
                 it is participating.  When the threshold rule is inactive,
                 it is not participating in the threshold, but will
                 be participating when the activation time arrives.

                 The participation state can be inactive only if
                 activation/deactivation days are specified.  Otherwise,
                 the participation state is activated when the
                 smMlmThresholdState field is set to enabled.  If this field
                 is set to notEnabled, the smMlmThresholdState field is not
                 set to enabled."
        ::= { smMlmThresholdEntry 37 }

smMlmThresholdActivationTime OBJECT-TYPE
        SYNTAX  DisplayString
        ACCESS  read-write
        STATUS  mandatory
        DESCRIPTION
                "This field specifies the time to activate the threshold
                 (ie. change the participation state from inactive to active).
                 The format should be HH:MM where HH represents the hour
                 (integer between 0 and 23) and MM represents the minute
                 (integer between 0 and 59) to activate the threshold.  A value
                 all blanks will be interpreted as 00:00."
        ::= { smMlmThresholdEntry 38 }

smMlmThresholdActivationDayOfWeek OBJECT-TYPE
        SYNTAX  DisplayString
        ACCESS  read-write
        STATUS  mandatory
        DESCRIPTION
                "This field specifies the days of the week to activate
                 the threshold at the time specified in the ActivationTime field
                 (ie. change the participation state from inactive to active).
                 The day of the week may be one of three literals:
                     none      -  Doesn't Activate
                     weekdays  -  Activates threshold entry on MTWThF
                     all       -  Activates threshold entry every day SuMTWThFS

                 Alternatively, the days of the week may be specified as a
                 list of numbers between 0 and 6 (Sunday = 0, Monday = 1, ...,
                 Saturday = 6).  The expression '1,3,5' would activate the
                 threshold entry at the specified time on MWF."
        ::= { smMlmThresholdEntry 39 }

smMlmThresholdDeactivationTime OBJECT-TYPE
        SYNTAX  DisplayString
        ACCESS  read-write
        STATUS  mandatory
        DESCRIPTION
                "This field specifies the time to deactivate the threshold
                 (ie. change the participation state from active to inactive).
                 The format should be HH:MM where HH represents the hour
                 (integer between 0 and 23) and MM represents the minute
                 (integer between 0 and 59) to deactivate the threshold.  A value
                 all blanks will be interpreted as 00:00."
        ::= { smMlmThresholdEntry 40 }

smMlmThresholdDeactivationDayOfWeek OBJECT-TYPE
        SYNTAX  DisplayString
        ACCESS  read-write
        STATUS  mandatory
        DESCRIPTION
                "This field specifies the days of the week to deactivate
                 the threshold at the time specified in the DeactivationTime field
                 (ie. change the participation state from active to inactive).
                 The day of the week may be one of three literals:
                   none      -  Doesn't deactivate
                   weekdays  -  Dectivates threshold entry on MTWThF
                   all       -  Deactivates threshold entry every day SuMTWThFS

                 Alternatively, the days of the week may be specified as a
                 list of numbers between 0 and 6 (Sunday = 0, Monday = 1, ...,
                 Saturday = 6).  The expression '1,3,5' would deactivate the
                 threshold entry at the specified time on MWF."
        ::= { smMlmThresholdEntry 41 }

--
--  The Threshold Arm Info Table
--

smMlmThresholdArmInfoTable OBJECT-TYPE
        SYNTAX  SEQUENCE OF SmMlmThresholdArmInfoEntry
        ACCESS  not-accessible
        STATUS  mandatory
        DESCRIPTION
                "Threshold Arm Information table.  This table provides the
                 threshold arm status information.  The table will be updated
                 based on the results of the threshold condition checking.
                 possible actions are as follows:
                   * adds a new entry
                     if in arm condition, threshold met, and no entry found.
                   * removes an entry
                     if in arm condition, threshold not met, and entry found,
                        or
                     if in rearm condition, and threshold met"
        ::= { smMlmThreshold 2 }

smMlmThresholdArmInfoEntry OBJECT-TYPE
        SYNTAX  SmMlmThresholdArmInfoEntry
        ACCESS  not-accessible
        STATUS  mandatory
        DESCRIPTION
                "Each entry contains the threshold name, node's IP address,
                 and the mib's oid."
        INDEX { smMlmThresholdArmInfoName,
                smMlmThresholdArmInfoIpAddress,
                smMlmThresholdArmInfoIndex }
        ::= { smMlmThresholdArmInfoTable 1 }

SmMlmThresholdArmInfoEntry ::= SEQUENCE {
    smMlmThresholdArmInfoName
        DisplayString,
    smMlmThresholdArmInfoIpAddress
        IpAddress,
    smMlmThresholdArmInfoObjectID
        OBJECT IDENTIFIER,
    smMlmThresholdArmInfoIndex
        INTEGER
}

smMlmThresholdArmInfoName OBJECT-TYPE
        SYNTAX  DisplayString
        ACCESS  read-only
        STATUS  mandatory
        DESCRIPTION
                "This field is the name of the threshold."
        ::= { smMlmThresholdArmInfoEntry 1 }

smMlmThresholdArmInfoIpAddress OBJECT-TYPE
        SYNTAX  IpAddress
        ACCESS  read-only
        STATUS  mandatory
        DESCRIPTION
                "The IP address of the node."
        ::= { smMlmThresholdArmInfoEntry 2 }

smMlmThresholdArmInfoObjectID OBJECT-TYPE
        SYNTAX  OBJECT IDENTIFIER
        ACCESS  read-only
        STATUS  mandatory
        DESCRIPTION
                "The oid of the mib variable."
        ::= { smMlmThresholdArmInfoEntry 3 }

smMlmThresholdArmInfoIndex OBJECT-TYPE
        SYNTAX  INTEGER (0..4294967295)
        ACCESS  read-only
        STATUS  mandatory
        DESCRIPTION
                "This field is simply used to append to the threshold
                 name and IP address for uniqueness."
        ::= { smMlmThresholdArmInfoEntry 4 }

--
--  The Threshold Results Table
--

smMlmThresholdResultsTable OBJECT-TYPE
        SYNTAX  SEQUENCE OF SmMlmThresholdResultsEntry
        ACCESS  not-accessible
        STATUS  mandatory
        DESCRIPTION
                "Threshold results table.  This table provides the
                 value results from the threshold table.  The table is updated
                 based on the results of the threshold table calculations.
                 Possible actions are as follows:
                   * adds a new entry
                     if a new node/instance is found for the calculation.
                   * removes an entry
                     if a node/instance is not found for the previous calculation."
        ::= { smMlmThreshold 3 }

smMlmThresholdResultsEntry OBJECT-TYPE
        SYNTAX  SmMlmThresholdResultsEntry
        ACCESS  not-accessible
        STATUS  mandatory
        DESCRIPTION
                "Each entry contains the threshold name,
                 node's IP address, and the mib var's instance."
        INDEX { smMlmThresholdResultsName,
                smMlmThresholdResultsIpAddress,
                smMlmThresholdResultsIndex }
        ::= { smMlmThresholdResultsTable 1 }

SmMlmThresholdResultsEntry ::= SEQUENCE {
    smMlmThresholdResultsName
        DisplayString,
    smMlmThresholdResultsIpAddress
        IpAddress,
    smMlmThresholdResultsInstanceID
        DisplayString,
    smMlmThresholdResultsIndex
        INTEGER,
    smMlmThresholdResultsResultTimeStamp
        DisplayString,
    smMlmThresholdResultsResultIndex
        INTEGER,
    smMlmThresholdResultsIntegerResult
        INTEGER,
    smMlmThresholdResultsCounterResult
        Counter,
    smMlmThresholdResultsGaugeResult
        Gauge,
    smMlmThresholdResultsDisplayStringResult
        DisplayString,
    smMlmThresholdResultsResetStats
        INTEGER,
    smMlmThresholdResultsLifeTimeIntegerMin
        INTEGER,
    smMlmThresholdResultsLifeTimeIntegerMax
        INTEGER,
    smMlmThresholdResultsLifeTimeIntegerAvg
        INTEGER,
    smMlmThresholdResultsLifeTimeIntegerStdDeviation
        INTEGER,
    smMlmThresholdResultsLifeTimeCounterGaugeMin
        Gauge,
    smMlmThresholdResultsLifeTimeCounterGaugeMax
        Gauge,
    smMlmThresholdResultsLifeTimeCounterGaugeAvg
        Gauge,
    smMlmThresholdResultsLifeTimeCounterGaugeStdDeviation
        INTEGER,
    smMlmThresholdResultsLifeTimeSamples
        Counter,
    smMlmThresholdResultsLifeTimeSeconds
        Counter,
    smMlmThresholdResultsLifeTimeMinTimeStamp
        DisplayString,
    smMlmThresholdResultsLifeTimeMaxTimeStamp
        DisplayString,
    smMlmThresholdResultsIntervalIntegerMin
        INTEGER,
    smMlmThresholdResultsIntervalIntegerMax
        INTEGER,
    smMlmThresholdResultsIntervalIntegerAvg
        INTEGER,
    smMlmThresholdResultsIntervalIntegerStdDeviation
        INTEGER,
    smMlmThresholdResultsIntervalCounterGaugeMin
        Gauge,
    smMlmThresholdResultsIntervalCounterGaugeMax
        Gauge,
    smMlmThresholdResultsIntervalCounterGaugeAvg
        Gauge,
    smMlmThresholdResultsIntervalCounterGaugeStdDeviation
        INTEGER,
    smMlmThresholdResultsIntervalSamples
        Counter,
    smMlmThresholdResultsIntervalSeconds
        Counter,
    smMlmThresholdResultsIntervalRate
        Gauge
}

smMlmThresholdResultsName OBJECT-TYPE
        SYNTAX  DisplayString
        ACCESS  read-only
        STATUS  mandatory
        DESCRIPTION
                "This field is the name of the threshold results."
        ::= { smMlmThresholdResultsEntry 1 }

smMlmThresholdResultsIpAddress OBJECT-TYPE
        SYNTAX  IpAddress
        ACCESS  read-only
        STATUS  mandatory
        DESCRIPTION
                "The IP address of the node."
        ::= { smMlmThresholdResultsEntry 2 }

smMlmThresholdResultsInstanceID OBJECT-TYPE
        SYNTAX  DisplayString
        ACCESS  read-only
        STATUS  mandatory
        DESCRIPTION
                "The instance identifier of the mib variable."
        ::= { smMlmThresholdResultsEntry 3 }

smMlmThresholdResultsIndex OBJECT-TYPE
        SYNTAX  INTEGER (0..4294967295)
        ACCESS  read-only
        STATUS  mandatory
        DESCRIPTION
                "This field is simply used to append to the threshold
                 name and IP address for uniqueness."
        ::= { smMlmThresholdResultsEntry 4 }

smMlmThresholdResultsResultTimeStamp OBJECT-TYPE
        SYNTAX  DisplayString
        ACCESS  read-only
        STATUS  mandatory
        DESCRIPTION
                "This field contains the date when the
                 result was updated."
        ::= { smMlmThresholdResultsEntry 5 }

smMlmThresholdResultsResultIndex OBJECT-TYPE
        SYNTAX  INTEGER {
                displaystring(1),  -- result is string
                integer(2),        -- result is integer
                counter(3),        -- result is counter
                gauge(4)           -- result is gauge
                }
        ACCESS  read-only
        STATUS  mandatory
        DESCRIPTION
                "Index to point to output result type.  The index
                 defines how the expression is evaluated, either using signed
                 arithmetic for integer or unsigned arithmetic for counter
                 and gauge.  The result for counter wraps on overflow or
                 underflow; the result for gauge latches at 0 for underflow
                 or 4294967295 for overflow.  If the result is a string then
                 the statistic information is not applicable."
        ::= { smMlmThresholdResultsEntry 6 }

smMlmThresholdResultsIntegerResult OBJECT-TYPE
        SYNTAX  INTEGER
        ACCESS  read-only
        STATUS  mandatory
        DESCRIPTION
                "Integer result based on signed arithmetic."
        ::= { smMlmThresholdResultsEntry 7 }

smMlmThresholdResultsCounterResult OBJECT-TYPE
        SYNTAX  Counter
        ACCESS  read-only
        STATUS  mandatory
        DESCRIPTION
                "Counter result based on unsigned arithmetic; this wraps
                 at the maximum or minimum value."
        ::= { smMlmThresholdResultsEntry 8 }

smMlmThresholdResultsGaugeResult OBJECT-TYPE
        SYNTAX  Gauge
        ACCESS  read-only
        STATUS  mandatory
        DESCRIPTION
                "Gauge result based on unsigned arithmetic; this
                 latches at the maximum or minimum value."
        ::= { smMlmThresholdResultsEntry 9 }

smMlmThresholdResultsDisplayStringResult OBJECT-TYPE
        SYNTAX  DisplayString
        ACCESS  read-only
        STATUS  mandatory
        DESCRIPTION
                "Display result as a displayable string.  This string
                 is generated based on the ResultsIndex for the type
                 of the resultant expression: integer, counter, or gauge."
        ::= { smMlmThresholdResultsEntry 10 }

smMlmThresholdResultsResetStats OBJECT-TYPE
        SYNTAX  INTEGER {
                false(1), -- allow statistics to accumulate
                true(2)   -- reset statistics
                }
        ACCESS  read-write
        STATUS  mandatory
        DESCRIPTION
                "Setting this field to true(1) will reset all the
                 statistics information for this result."
        ::= { smMlmThresholdResultsEntry 11 }

smMlmThresholdResultsLifeTimeIntegerMin OBJECT-TYPE
        SYNTAX  INTEGER
        ACCESS  read-only
        STATUS  mandatory
        DESCRIPTION
                "Results life time integer minimum"
        ::= { smMlmThresholdResultsEntry 12 }

smMlmThresholdResultsLifeTimeIntegerMax OBJECT-TYPE
        SYNTAX  INTEGER
        ACCESS  read-only
        STATUS  mandatory
        DESCRIPTION
                "Results life time integer maximum"
        ::= { smMlmThresholdResultsEntry 13 }

smMlmThresholdResultsLifeTimeIntegerAvg OBJECT-TYPE
        SYNTAX  INTEGER
        ACCESS  read-only
        STATUS  mandatory
        DESCRIPTION
                "Results life time integer data average"
        ::= { smMlmThresholdResultsEntry 14 }

smMlmThresholdResultsLifeTimeIntegerStdDeviation OBJECT-TYPE
        SYNTAX  INTEGER
        ACCESS  read-only
        STATUS  mandatory
        DESCRIPTION
                "Results life time integer standard deviation"
        ::= { smMlmThresholdResultsEntry 15 }

smMlmThresholdResultsLifeTimeCounterGaugeMin OBJECT-TYPE
        SYNTAX  Gauge
        ACCESS  read-only
        STATUS  mandatory
        DESCRIPTION
                "Results life time counter/gauge minimum"
        ::= { smMlmThresholdResultsEntry 16 }

smMlmThresholdResultsLifeTimeCounterGaugeMax OBJECT-TYPE
        SYNTAX  Gauge
        ACCESS  read-only
        STATUS  mandatory
        DESCRIPTION
                "Results life time counter/gauge maximum"
        ::= { smMlmThresholdResultsEntry 17 }

smMlmThresholdResultsLifeTimeCounterGaugeAvg OBJECT-TYPE
        SYNTAX  Gauge
        ACCESS  read-only
        STATUS  mandatory
        DESCRIPTION
                "Results life time counter/gauge data average"
        ::= { smMlmThresholdResultsEntry 18 }

smMlmThresholdResultsLifeTimeCounterGaugeStdDeviation OBJECT-TYPE
        SYNTAX  INTEGER
        ACCESS  read-only
        STATUS  mandatory
        DESCRIPTION
                "Results life time counter/gauge standard deviation"
        ::= { smMlmThresholdResultsEntry 19 }

smMlmThresholdResultsLifeTimeSamples OBJECT-TYPE
        SYNTAX  Counter
        ACCESS  read-only
        STATUS  mandatory
        DESCRIPTION
                "Results life time samples"
        ::= { smMlmThresholdResultsEntry 20 }

smMlmThresholdResultsLifeTimeSeconds OBJECT-TYPE
        SYNTAX  Counter
        ACCESS  read-only
        STATUS  mandatory
        DESCRIPTION
                "Results life time seconds"
        ::= { smMlmThresholdResultsEntry 21 }

smMlmThresholdResultsLifeTimeMinTimeStamp OBJECT-TYPE
        SYNTAX  DisplayString
        ACCESS  read-only
        STATUS  mandatory
        DESCRIPTION
               "This field contains the date when the life time
                integer or counter/gauge minimum value was recorded."
        ::= { smMlmThresholdResultsEntry 22 }

smMlmThresholdResultsLifeTimeMaxTimeStamp OBJECT-TYPE
        SYNTAX  DisplayString
        ACCESS  read-only
        STATUS  mandatory
        DESCRIPTION
               "This field contains the date when the lifetime
                integer or counter/gauge maximum value was recorded."
        ::= { smMlmThresholdResultsEntry 23 }

smMlmThresholdResultsIntervalIntegerMin OBJECT-TYPE
        SYNTAX  INTEGER
        ACCESS  read-only
        STATUS  mandatory
        DESCRIPTION
                "Results interval integer minimum"
        ::= { smMlmThresholdResultsEntry 24 }

smMlmThresholdResultsIntervalIntegerMax OBJECT-TYPE
        SYNTAX  INTEGER
        ACCESS  read-only
        STATUS  mandatory
        DESCRIPTION
                "Results interval integer maximum"
        ::= { smMlmThresholdResultsEntry 25 }

smMlmThresholdResultsIntervalIntegerAvg OBJECT-TYPE
        SYNTAX  INTEGER
        ACCESS  read-only
        STATUS  mandatory
        DESCRIPTION
                "Results interval integer data average"
        ::= { smMlmThresholdResultsEntry 26 }

smMlmThresholdResultsIntervalIntegerStdDeviation OBJECT-TYPE
        SYNTAX  INTEGER
        ACCESS  read-only
        STATUS  mandatory
        DESCRIPTION
                "Results interval integer standard deviation"
        ::= { smMlmThresholdResultsEntry 27 }

smMlmThresholdResultsIntervalCounterGaugeMin OBJECT-TYPE
        SYNTAX  Gauge
        ACCESS  read-only
        STATUS  mandatory
        DESCRIPTION
                "Results interval counter/gauge minimum"
        ::= { smMlmThresholdResultsEntry 28 }

smMlmThresholdResultsIntervalCounterGaugeMax OBJECT-TYPE
        SYNTAX  Gauge
        ACCESS  read-only
        STATUS  mandatory
        DESCRIPTION
                "Results interval counter/gauge maximum"
        ::= { smMlmThresholdResultsEntry 29 }

smMlmThresholdResultsIntervalCounterGaugeAvg OBJECT-TYPE
        SYNTAX  Gauge
        ACCESS  read-only
        STATUS  mandatory
        DESCRIPTION
                "Results interval counter/gauge data average"
        ::= { smMlmThresholdResultsEntry 30 }

smMlmThresholdResultsIntervalCounterGaugeStdDeviation OBJECT-TYPE
        SYNTAX  INTEGER
        ACCESS  read-only
        STATUS  mandatory
        DESCRIPTION
                "Results interval counter/gauge standard deviation"
        ::= { smMlmThresholdResultsEntry 31 }

smMlmThresholdResultsIntervalSamples OBJECT-TYPE
        SYNTAX  Counter
        ACCESS  read-only
        STATUS  mandatory
        DESCRIPTION
                "Results interval samples"
        ::= { smMlmThresholdResultsEntry 32 }

smMlmThresholdResultsIntervalSeconds OBJECT-TYPE
        SYNTAX  Counter
        ACCESS  read-only
        STATUS  mandatory
        DESCRIPTION
                "Results interval seconds"
        ::= { smMlmThresholdResultsEntry 33 }

smMlmThresholdResultsIntervalRate OBJECT-TYPE
        SYNTAX  Gauge
        ACCESS  read-only
        STATUS  mandatory
        DESCRIPTION
                "Results interval seconds rate of change"
        ::= { smMlmThresholdResultsEntry 34 }

--
--  The Filter Table
--

smMlmFilterDefaultAction OBJECT-TYPE
        SYNTAX  INTEGER {
                sendTraps(1),  -- send all traps not matching a filter
                blockTraps(2)  -- block traps that don't match a filter
                }
        ACCESS  read-write
        STATUS  mandatory
        DESCRIPTION
                "Global default as to whether or not the traps
                 received are to be sent or blocked.  If the trap
                 matches a filter entry, the action specified is taken.
                 If the trap doesn't match a filter entry and sendTraps
                 is specified, the trap destinations from the trap
                 destination table are used."
        ::= { smMlmFilter 1 }

smMlmFilterUdpTrapReception OBJECT-TYPE
        SYNTAX  INTEGER {
                enabled(1),  -- MLM connect to the udp trap socket
                disabled(2)  -- MLM does not receive any traps
                }
        ACCESS  read-write
        STATUS  mandatory
        DESCRIPTION
                "Indicator of whether or not the Mid-Level
                 Manager Agent should connect to the snmp trap socket using UDP.

                 If enabled (1), the traps will be read from the udp port.
                 If disabled (2), only traps generated by the Mid-Level
                 Manager (e.g. thresholding, status, discovery
                 traps) and traps read from the tcp socket will be filtered
                 by the Mid-Level Manager.

                 Note:  This field cannot be set to enabled if another
                 process on the host is already receiving traps (ie. the
                 manager).  Conversely, another process on the host
                 (ie. the manager) will not be able to receive traps
                 if this field is set to enabled.
                 Therefore, if a manager is running on the same host as
                 the Mid-Level Manager, this field should
                 be set to disabled.

                 If this field is set to enabled and any other process is
                 connected to the port specified by the UdpTrapReceptionPort
                 then UpdTrapReceptionStatus variable is set to portBusy.

                 To check the availability of the port, this field
                 should be disabled and then set to enabled."
        ::= { smMlmFilter 2 }

smMlmFilterTotalTrapsReceived OBJECT-TYPE
        SYNTAX  Counter
        ACCESS  read-only
        STATUS  mandatory
        DESCRIPTION
                "Current count of the number of traps that have
                 been received by the Mid-Level
                 Manager.

                 This count is reset to zero whenever
                 both the UdpTrapReception MIB variable and
                 the TcpTrapReception MIB variable are set
                 to disabled (from a enabled state)."
        ::= { smMlmFilter 3 }

--
--  The Filter Table
--

smMlmFilterTable OBJECT-TYPE
        SYNTAX  SEQUENCE OF SmMlmFilterEntry
        ACCESS  not-accessible
        STATUS  mandatory
        DESCRIPTION
                "Entries defining a particular
                 filter.  Each entry may be thought of as a single filter.
                 Each filter is evaluated against each incoming trap.  When
                 the filter criteria matches the trap, the corresponding
                 filter actions are taken.  The table is indexed by the
                 smMlmFilterName field."
        ::= { smMlmFilter 4 }

smMlmFilterEntry OBJECT-TYPE
        SYNTAX  SmMlmFilterEntry
        ACCESS  not-accessible
        STATUS  mandatory
        DESCRIPTION
                "Each entry contains the components for a particular filter."
  INDEX { smMlmFilterName }
        ::= { smMlmFilterTable 1 }

SmMlmFilterEntry ::= SEQUENCE {
    smMlmFilterState
        INTEGER,
    smMlmFilterParticipationState
        INTEGER,
    smMlmFilterName
        DisplayString,
    smMlmFilterDescription
        DisplayString,
    smMlmFilterAction
        INTEGER,
    smMlmFilterEntryEnterpriseExpression
        DisplayString,
    smMlmFilterAgentAddrExpression
        DisplayString,
    smMlmFilterGenericExpression
        DisplayString,
    smMlmFilterSpecificExpression
        DisplayString,
    smMlmFilterVariableExpression
        DisplayString,
    smMlmFilterTotalTrapsMatched
        Counter,
    smMlmFilterActivationTime
        DisplayString,
    smMlmFilterActivationDayOfWeek
        DisplayString,
    smMlmFilterDeactivationTime
        DisplayString,
    smMlmFilterDeactivationDayOfWeek
        DisplayString,
    smMlmFilterTrapDestinations
        DisplayString,
    smMlmFilterMatchedCommand
        DisplayString,
    smMlmFilterMatchedTrapDescription
        DisplayString,
    smMlmFilterMatchedTrapEnterprise
        DisplayString,
    smMlmFilterMatchedSpecificTrap
        INTEGER,
    smMlmFilterThrottleType
        INTEGER,
    smMlmFilterThrottleArmTrapCount
        INTEGER,
    smMlmFilterThrottleArmedCommand
        DisplayString,
    smMlmFilterThrottleArmedTrapDescription
        DisplayString,
    smMlmFilterThrottleArmedTrapEnterprise
        DisplayString,
    smMlmFilterThrottleArmedSpecificTrap
        INTEGER,
    smMlmFilterThrottleDisarmTimer
        DisplayString,
    smMlmFilterThrottleDisarmTrapCount
        INTEGER,
    smMlmFilterThrottleDisarmedCommand
        DisplayString,
    smMlmFilterThrottleDisarmedTrapDescription
        DisplayString,
    smMlmFilterThrottleDisarmedTrapEnterprise
        DisplayString,
    smMlmFilterThrottleDisarmedSpecificTrap
        INTEGER,
    smMlmFilterThrottleState
        INTEGER,
    smMlmFilterThrottleTimeStarted
        DisplayString,
    smMlmFilterThrottleTrapCount
        INTEGER,
    smMlmFilterMessages
        DisplayString,
    smMlmFilterThrottleCriteria
        INTEGER,
    smMlmFilterThrottleVariables
        DisplayString

}

smMlmFilterState OBJECT-TYPE
        SYNTAX  INTEGER {
                enabled(3),   -- filter enabled
                disabled(1),  -- filter disabled
                invalid(2)    -- removes filter entry
                }
        ACCESS  read-write
        STATUS  mandatory
        DESCRIPTION
                "State for the filter rule.  When the state is set to
                 invalid, the filter is deleted.  When the filter
                 entry is set to disabled, the filter is dormant.  When
                 the filter rule is enabled, it may participate in the
                 filter rule base.  The filter rule is participating if
                 the smMlmFilterParticipationState is set to active."
        ::= { smMlmFilterEntry 1 }

smMlmFilterParticipationState OBJECT-TYPE
        SYNTAX  INTEGER {
                active(2),      -- filter is participating
                notEnabled(1),  -- filtering not enabled in smMlmFilterState
                inactive(3)     -- filter is dormant
                }
        ACCESS  read-only
        STATUS  mandatory
        DESCRIPTION
                "This field indicates whether or not the rule is participating
                 in the filter rule base.  When the filter rule is active,
                 it is participating.  When the filter rule is inactive,
                 it is not participating in the filter rule base, but will
                 be participating when the activation time arrives.

                 The participation state can be inactive only if
                 activation/deactivation days are specified.  Otherwise,
                 the participation state is activated when the
                 smMlmFilterState field is set to enabled.  If this field
                 is set to notEnabled, the smMlmFilterState field is not
                 set to enabled."
        ::= { smMlmFilterEntry 2 }

smMlmFilterName OBJECT-TYPE
        SYNTAX  DisplayString
        ACCESS  read-write
        STATUS  mandatory
        DESCRIPTION
                "This field contains the name for a particular filter.
                 The instance identifier associated with every field
                 in the filter entry is derived from the name
                 (dot separated ASCII codes).  Therefore, this name
                 must be unique among all other filter names."
        ::= { smMlmFilterEntry 3 }

smMlmFilterDescription OBJECT-TYPE
        SYNTAX  DisplayString
        ACCESS  read-write
        STATUS  mandatory
        DESCRIPTION
                "Description of the filter.  This field should
                 contain a general description of what the filter
                 accomplishes.  A user should be able to read this
                 information and know what filtering is being
                 done as well as why it is being done."
        ::= { smMlmFilterEntry 4 }

smMlmFilterAction OBJECT-TYPE
        SYNTAX  INTEGER {
                sendTraps(1),    -- send traps matching this filter rule
                blockTraps(2),   -- don't send traps match this filter rule
                throttleTraps(3) -- throttle traps matching this filter rule
                }
        ACCESS  read-write
        STATUS  mandatory
        DESCRIPTION
                "This field is used to determine whether or not the matching
                 trap is forwarded on to a manager station.  If sendTraps
                 is specified, then the trap destinations specified in the
                 filter are included in the list of destinations to which
                 the trap is forwarded.  If blockTraps is specified, then
                 the trap will not be forwarded unless another filter
                 is matched that specifies the trap is to be sent.  When
                 this field is set to ThrottleTraps, the throttle expression
                 needs to be evaluated in order to decide whether to send
                 or block the received trap."
        ::= { smMlmFilterEntry 5 }

smMlmFilterEntryEnterpriseExpression OBJECT-TYPE
        SYNTAX  DisplayString
        ACCESS  read-write
        STATUS  mandatory
        DESCRIPTION
                "This field is used to match the rule against the enterpriseID
                 contained in the received trap.  This is the default enterpriseID
                 expression. If in the specific trap expression, this particular specific
                 trap number does not have any enterpriseID associated with it for matching
                 then the trap is matched with this rule.

                 The entry may be an alias name (from the smMlmAlias table),
                 an enterpriseID in dot notation, or an enterpriseID with a wildcard
                 value (terminated by an asterisk).  The enterpriseID in dot notation
                 should be fully qualified.  An enterpriseID with a wildcard value
                 matches any enterpriseID with the same partial enterpriseID."
        ::= { smMlmFilterEntry 6 }

smMlmFilterAgentAddrExpression OBJECT-TYPE
        SYNTAX  DisplayString
        ACCESS  read-write
        STATUS  mandatory
        DESCRIPTION
               "This field is used to match against the address of the
                agent that generated the trap.
                For the Mid-Level Manager, the agent address expression
                is a comma separated list of:

                  1) an smMlmAliasName (from the smMlmAlias table)
                  2) a resolvable hostname
                  3) an ipAddress expression.

                If the agent address expression contains an smMlmAliasName
                or hostname, the addresses to check the trap against are
                determined each time a trap is received.

                An ipAddress expression contains four dot separated
                sub-expressions that can be either:

                  1) a decimal number between 0 and 255
                  2) an inclusive range of numbers between 0 and 255
                     specified by [#-#] (ie. [0-127])
                  3) an asterisk (which is simply interpreted as [0-255]).

                An example ipAddress expression is '9.67.[128-130].*'."
         ::= { smMlmFilterEntry 7 }

smMlmFilterGenericExpression OBJECT-TYPE
        SYNTAX  DisplayString
        ACCESS  read-write
        STATUS  mandatory
        DESCRIPTION
                "This field is used to match against the generic trap number
                 contained in the received trap.  This field allows a comma
                 separated list of generic trap numbers.  If specific trap
                 numbers are to be checked, a 6 (ie. enterprise-specific
                 trap) must be encoded in the generic expression.

                 The generic traps are:

                   0 - Cold Start
                   1 - Warm Start
                   2 - Link Down
                   3 - Link Up
                   4 - Authentication Failure
                   5 - EGP Neighbor Loss
                   6 - Enterprise Specific"

        ::= { smMlmFilterEntry 8 }

smMlmFilterSpecificExpression OBJECT-TYPE
        SYNTAX  DisplayString
        ACCESS  read-write
        STATUS  mandatory
        DESCRIPTION
                "This field is used to match against the specific trap number
                 contained in the received trap along with the enterpriseID.
                 This allows specific traps numbers to be grouped with
                 enterpriseID.

                 This field allows a comma separated list of specific groups
                 or specific trap numbers or range of specific traps.

                 A range of specific trap numbers may be specified by using
                 the range format of '[#-#]' (ie. [100-199]).

                 A group of specific trap numbers or range with EnterpriseID
                 can be specified using the grouping format
                 'EnterpriseID(x,y,[a-b])'

                 example: .1.3.6.1.4.1.2.6.12( 15, 20, [100-199])

                 This field will only be checked if a 6
                 (ie. enterprise-specific trap) is contained in the generic
                 trap expression."
        ::= { smMlmFilterEntry 9 }

smMlmFilterVariableExpression OBJECT-TYPE
        SYNTAX  DisplayString
        ACCESS  read-write
        STATUS  mandatory
        DESCRIPTION
                "This field is used to match trap against the
                 environment variables, set on the basis of MIB variables
                 and other information flowing in the trap.

                 The expression can be any expression with left operand as
                 environment variable name( prepended with $) and right operand
                 as values of variables or regular expression, with
                 the following operators:

                     () : grouping
                     && : logical and
                     || : logical or
                     == : equal to
                     != : not equal to
                     <  : less than
                     <= : less than equal to
                     >  : greater than
                     >= : greater than equal to
                     !  : negation

                 The precedence and associativity of operators is
                 same as in c language and expression evaluation
                 is based on standard c program execution.

                 Set of environment variables that can be used in
                 the expression are:
                   SM6K_HOSTNAME={hostname running subagent}
                   SM6K_DOMAIN_NAME={fully qualified hostname}
                   SM6K_HOST_ADDRESS={ip address}
                   SM6K_INSTANCE_NAME={instance string of row}
                   SM6K_INSTANCE_ID={instance ASCII octet value of row}
                   SM6K_EXECUTION_REASON=Filter_Matched|Filter_Armed|
                                         Filter_Disarmed

                   SM6K_TRAP_ENTERPRISE={enterprise ID from the trap}
                   SM6K_TRAP_AGENT_ADDRESS={IP address of the sending agent}
                   SM6K_TRAP_GENERIC_NUM={generic trap number of the trap}
                   SM6K_TRAP_SPECIFIC_NUM={specific trap number of the trap}
                   SM6K_TRAP_TIME_TICKS={time ticks since the sending agent
                                         was started}
                   SM6K_NUM_TRAP_VARS={number of MIB variables in the trap}
                   SM6K_TRAP_VAR_OBJ_ID#={Object ID for MIB variable in trap}
                   SM6K_TRAP_VAR_TYPE#=INTEGER|Counter|Gauge|TimeTicks|
                                       IpAddress|OCTET_STRING|Opaque|
                                       OBJECT_IDENTIFIER|NULL|Unknown
                   SM6K_TRAP_VAR_VALUE#={value of the MIB object}

                 where the # is replaced by the trap variable's positional
                 number in the trap (starting at 1).

                 Values can be in the form of integer, dot notation or string
                 or hex string.
                 If it is a string it should be within quotes.

                 Format of regular expression is: RE:expression (within
                 double quotes), where 'expression' is the extended regular
                 expression in the style of ed or egrep command.

                   example:

                   Check for trap number 22 from System Information Agent.
                   ( $SM6K_TRAP_ENTERPRISE == .1.3.6.1.4.1.2.6.12) &&
                   ( $SM6K_TRAP_SPECIFIC_NUM == 22 )

                   If the expression evaluates to TRUE, then the
                   trap is matched."
        ::= { smMlmFilterEntry 10 }

smMlmFilterTotalTrapsMatched OBJECT-TYPE
        SYNTAX  Counter
        ACCESS  read-only
        STATUS  mandatory
        DESCRIPTION
                "This field contains the number of traps that have
                 matched this filter.  This count is reset to zero
                 whenever the filter entry's state is set to enabled
                 (from the disabled state)."
        ::= { smMlmFilterEntry 11 }

smMlmFilterActivationTime OBJECT-TYPE
        SYNTAX  DisplayString
        ACCESS  read-write
        STATUS  mandatory
        DESCRIPTION
                "This field specifies the time to activate the filter
                 (ie. change the participation state from inactive to active).
                 The format should be HH:MM where HH represents the hour
                 (integer between 0 and 23) and MM represents the minute
                 (integer between 0 and 59) to activate the filter.  A value
                 all blanks will be interpreted as 00:00."
        ::= { smMlmFilterEntry 12 }

smMlmFilterActivationDayOfWeek OBJECT-TYPE
        SYNTAX  DisplayString
        ACCESS  read-write
        STATUS  mandatory
        DESCRIPTION
                "This field specifies the days of the week to activate
                 the filter at the time specified in the ActivationTime field
                 (ie. change the participation state from inactive to active).
                 The day of the week may be one of three literals:
                     none      -  Doesn't Activate
                     weekdays  -  Activates filter entry on MTWThF
                     all       -  Activates filter entry every day SuMTWThFS

                 Alternatively, the days of the week may be specified as a
                 list of numbers between 0 and 6 (Sunday = 0, Monday = 1, ...,
                 Saturday = 6).  The expression '1,3,5' would activate the
                 filter entry at the specified time on MWF."
        ::= { smMlmFilterEntry 13 }

smMlmFilterDeactivationTime OBJECT-TYPE
        SYNTAX  DisplayString
        ACCESS  read-write
        STATUS  mandatory
        DESCRIPTION
                "This field specifies the time to deactivate the filter
                 (ie. change the participation state from active to inactive).
                 The format should be HH:MM where HH represents the hour
                 (integer between 0 and 23) and MM represents the minute
                 (integer between 0 and 59) to deactivate the filter.  A value
                 all blanks will be interpreted as 00:00."
        ::= { smMlmFilterEntry 14 }

smMlmFilterDeactivationDayOfWeek OBJECT-TYPE
        SYNTAX  DisplayString
        ACCESS  read-write
        STATUS  mandatory
        DESCRIPTION
                "This field specifies the days of the week to deactivate
                 the filter at the time specified in the DeactivationTime field
                 (ie. change the participation state from active to inactive).
                 The day of the week may be one of three literals:
                   none      -  Doesn't deactivate
                   weekdays  -  Dectivates filter entry on MTWThF
                   all       -  Deactivates filter entry every day SuMTWThFS

                 Alternatively, the days of the week may be specified as a
                 list of numbers between 0 and 6 (Sunday = 0, Monday = 1, ...,
                 Saturday = 6).  The expression '1,3,5' would deactivate the
                 filter entry at the specified time on MWF."
        ::= { smMlmFilterEntry 15 }

smMlmFilterTrapDestinations OBJECT-TYPE
        SYNTAX  DisplayString
        ACCESS  read-write
        STATUS  mandatory
        DESCRIPTION
                "This field specifies the destinations for any traps
                 that match the filter criteria specified.  This field allows
                 ip addresses, alias names (from the smMlmAlias table) or
                 resolvable hostnames separated by commas.  If this
                 field is left blank, the trap will be sent to the trap
                 destinations specified in the smMlmTrapDestination table.

                 Each host listed can specify a destination port number
                 and protocol (tcp or udp ) or service name
                 using the format:

                 x+y/z where x can be ip address or hostname or alias name
                             y can be port number or protocol or service name
                             z can be port number or protocol.

                 example: testhost+162/tcp  or 9.67.162.81+udp/162

                 If the port or protocol is not specified then default
                 value is used. The default port number is '162' and
                 default protocol is 'udp'."

        ::= { smMlmFilterEntry 16 }

smMlmFilterMatchedCommand OBJECT-TYPE
        SYNTAX  DisplayString
        ACCESS  read-write
        STATUS  mandatory
        DESCRIPTION
                "This field specifies the command to be executed when a
                 received trap matches the filter.  A set of environment
                 variables are defined that contain information from the
                 received trap.  They may be used by the command that is
                 executed.

                 The following environment variables pertain to the
                 Mid-Level Manager filter:

                     SM6K_HOSTNAME={hostname running subagent}
                     SM6K_DOMAIN_NAME={fully qualified hostname}
                     SM6K_HOST_ADDRESS={ip address}
                     SM6K_INSTANCE_NAME={instance string of row}
                     SM6K_INSTANCE_ID={instance ASCII octet value of row}
                     SM6K_EXECUTION_REASON=Filter_Matched|Filter_Armed|
                                         Filter_Disarmed

                 The following environment variables pertain to the received
                 trap:

                     SM6K_TRAP_ENTERPRISE={enterprise ID from the trap}
                     SM6K_TRAP_AGENT_ADDRESS={IP address of the sending agent}
                     SM6K_TRAP_GENERIC_NUM={generic trap number of the trap}
                     SM6K_TRAP_SPECIFIC_NUM={specific trap number of the trap}
                     SM6K_TRAP_TIME_TICKS={time ticks since the sending agent
                                         was started}
                     SM6K_NUM_TRAP_VARS={number of MIB variables in the trap}

                  In addition, for each variable flowing in the trap:

                     SM6K_TRAP_VAR_OBJ_ID#={Object ID for MIB variable in trap}
                     SM6K_TRAP_VAR_TYPE#=INTEGER|Counter|Gauge|TimeTicks|
                                       IpAddress|OCTET_STRING|Opaque|
                                       OBJECT_IDENTIFIER|NULL|Unknown
                     SM6K_TRAP_VAR_VALUE#={value of the MIB object}

                   where the # is replaced by the trap variable's positional
                   number in the trap (starting at 1)

                   For more information see the accompanying documentation."
        ::= { smMlmFilterEntry 17 }

smMlmFilterMatchedTrapDescription OBJECT-TYPE
        SYNTAX  DisplayString
        ACCESS  read-write
        STATUS  mandatory
        DESCRIPTION
                "Not implemented"
        ::= { smMlmFilterEntry 18 }

smMlmFilterMatchedTrapEnterprise OBJECT-TYPE
        SYNTAX  DisplayString
        ACCESS  read-write
        STATUS  mandatory
        DESCRIPTION
                "Not implemented"
        ::= { smMlmFilterEntry 19 }

smMlmFilterMatchedSpecificTrap OBJECT-TYPE
        SYNTAX  INTEGER
        ACCESS  read-write
        STATUS  mandatory
        DESCRIPTION
                "Not implemented"
        ::= { smMlmFilterEntry 20 }

smMlmFilterThrottleType OBJECT-TYPE
        SYNTAX  INTEGER {
                sendFirstN(1), -- send first N traps
                sendAfterN(2)  -- send traps only after N received
                }
        ACCESS  read-write
        STATUS  mandatory
        DESCRIPTION
                "This field is used to indicate whether the throttle sends
                 the first N matching traps (sendFirstN) or sends after
                 receiving N matching traps (sendAfterN).  The value of N
                 is specified by the smMlmFilterThrottleArmTrapCount."
        ::= { smMlmFilterEntry 21 }

smMlmFilterThrottleArmTrapCount OBJECT-TYPE
        SYNTAX  INTEGER
        ACCESS  read-write
        STATUS  mandatory
        DESCRIPTION
                "This field specifies the number of matching traps to
                 receive before throttling is armed.  This is the N
                 referred to in the FilterThrottleType field."
        ::= { smMlmFilterEntry 22 }

smMlmFilterThrottleArmedCommand OBJECT-TYPE
        SYNTAX  DisplayString
        ACCESS  read-write
        STATUS  mandatory
        DESCRIPTION
                "This field specifies the command to execute when the
                 ThrottleArmTrapCount number of traps have been received
                 (ie. when the throttle is ARMED). A set of environment
                 variables are defined that contain information from
                 the received trap.  They may be used by the command that
                 is executed.

                 The following environment variables pertain to the
                 Mid-Level Manager filter:

                   SM6K_HOSTNAME={hostname running subagent}
                   SM6K_DOMAIN_NAME={fully qualified hostname}
                   SM6K_HOST_ADDRESS={ip address}
                   SM6K_INSTANCE_NAME={instance string of row}
                   SM6K_INSTANCE_ID={instance ASCII octet value of row}
                   SM6K_EXECUTION_REASON=Filter_Armed
                   SM6K_THROTTLE_ARM_COUNT={value of ThrottleArmTrapCount}
                   SM6K_THROTTLE_DISARM_COUNT={value of ThrottleDisarmTrapCount}
                   SM6K_THROTTLE_DISARM_TIMER={value of ThrottleDisarmTimer}

                 The following environment variables pertain to the received
                 trap:

                   SM6K_TRAP_ENTERPRISE={enterprise ID from the trap}
                   SM6K_TRAP_AGENT_ADDRESS={IP address of the sending agent}
                   SM6K_TRAP_GENERIC_NUM={generic trap number of the trap}
                   SM6K_TRAP_SPECIFIC_NUM={specific trap number of the trap}
                   SM6K_TRAP_TIME_TICKS={time ticks since the sending agent
                                         was started}
                   SM6K_NUM_TRAP_VARS={number of MIB variables in the trap}

                In addition, for each variable flowing in the trap:

                   SM6K_TRAP_VAR_OBJ_ID#={Object ID for MIB variable in trap}
                   SM6K_TRAP_VAR_TYPE#=INTEGER|Counter|Gauge|TimeTicks|
                                       IpAddress|OCTET_STRING|Opaque|
                                       OBJECT_IDENTIFIER|NULL|Unknown
                   SM6K_TRAP_VAR_VALUE#={value of the MIB object}

                 where the # is replaced by the trap variable's positional
                 number in the trap (starting at 1)."
        ::= { smMlmFilterEntry 23 }

smMlmFilterThrottleArmedTrapDescription OBJECT-TYPE
        SYNTAX  DisplayString
        ACCESS  read-write
        STATUS  mandatory
        DESCRIPTION
                "Not implemented"
        ::= { smMlmFilterEntry 24 }

smMlmFilterThrottleArmedTrapEnterprise OBJECT-TYPE
        SYNTAX  DisplayString
        ACCESS  read-write
        STATUS  mandatory
        DESCRIPTION
                "Not implemented"
        ::= { smMlmFilterEntry 25 }

smMlmFilterThrottleArmedSpecificTrap OBJECT-TYPE
        SYNTAX  INTEGER
        ACCESS  read-write
        STATUS  mandatory
        DESCRIPTION
                "Not implemented"
        ::= { smMlmFilterEntry 26 }

smMlmFilterThrottleDisarmTimer OBJECT-TYPE
        SYNTAX  DisplayString
        ACCESS  read-write
        STATUS  mandatory
        DESCRIPTION
                "This field specifies the time period to elapse before
                 the throttle is disarmed (reset).  It is important to note
                 that if smMlmThrottleDisarmTrapCount is set to a value
                 greater than 0, the amount of time specified may not
                 elapse before the throttle is disarmed.

                 This time period is from the time the throttle is started
                 (ie. from the time the first matching trap is received),
                 not from the time the throttle is armed.  Therefore, it is
                 possible that the throttle will not be armed before the
                 throttle is disarmed (reset).  In this case, the disarm
                 command is NOT executed."
        ::= { smMlmFilterEntry 27 }

smMlmFilterThrottleDisarmTrapCount OBJECT-TYPE
        SYNTAX  INTEGER
        ACCESS  read-write
        STATUS  mandatory
        DESCRIPTION
               "This field specifies the delta number of traps to receive
                before the throttle is disarmed.  This field value is a
                delta and only refers to the number of matching traps
                received AFTER the throttle has been armed.  It is important
                to note that if the smMlmThrottleDisarmTimer is set, the
                number of matching traps specified may not occur before
                the throttle is disarmed."
        ::= { smMlmFilterEntry 28 }

smMlmFilterThrottleDisarmedCommand OBJECT-TYPE
        SYNTAX  DisplayString
        ACCESS  read-write
        STATUS  mandatory
        DESCRIPTION
                "This field specifies the command to execute when the throttle
                 is DISARMED.  The throttle is disarmed when either
                   1)  the smMlmThrottleDisarmTrapCount matching traps have
                       occurred after the throttle was armed, or
                   2)  the smMlmFilterThrottleDisarmTimer has expired.

                 NOTE: If the above mentioned timer expires and the throttle
                       is NOT currently ARMED, the throttle is reset, but
                       this disarm command is NOT executed.  So, the disarm
                       command is only executed if the throttle is armed
                       before being disarmed.

                 A set of environment variables are defined that contain
                 information from the received trap.  They may be used by
                 the command that is executed.

                 The following environment variables pertain to the
                 Mid-Level Manager filter:

                   SM6K_HOSTNAME={hostname running subagent}
                   SM6K_DOMAIN_NAME={fully qualified hostname}
                   SM6K_HOST_ADDRESS={ip address}
                   SM6K_INSTANCE_NAME={instance string of row}
                   SM6K_INSTANCE_ID={instance ASCII octet value of row}
                   SM6K_EXECUTION_REASON=Filter_Disarmed
                   SM6K_THROTTLE_ARM_COUNT={value of ThrottleArmTrapCount}
                   SM6K_THROTTLE_DISARM_COUNT={value of ThrottleDisarmTrapCount}
                   SM6K_THROTTLE_DISARM_TIMER={value of ThrottleDisarmTimer}

                 The following environment variables pertain to the received
                 trap:

                   SM6K_TRAP_ENTERPRISE={enterprise ID from the trap}
                   SM6K_TRAP_AGENT_ADDRESS={IP address of the sending agent}
                   SM6K_TRAP_GENERIC_NUM={generic trap number of the trap}
                   SM6K_TRAP_SPECIFIC_NUM={specific trap number of the trap}
                   SM6K_TRAP_TIME_TICKS={time ticks since the sending agent
                                         was started}
                   SM6K_NUM_TRAP_VARS={number of MIB variables in the trap}

                  In addition, for each variable flowing in the trap:

                    SM6K_TRAP_VAR_OBJ_ID#={Object ID for MIB variable in trap}
                    SM6K_TRAP_VAR_TYPE#=INTEGER|Counter|Gauge|TimeTicks|
                                       IpAddress|OCTET_STRING|Opaque|
                                       OBJECT_IDENTIFIER|NULL|Unknown
                    SM6K_TRAP_VAR_VALUE#={value of the MIB object}

                  where the # is replaced by the trap variable's positional
                  number in the trap (starting at 1)."
        ::= { smMlmFilterEntry 29 }

smMlmFilterThrottleDisarmedTrapDescription OBJECT-TYPE
        SYNTAX  DisplayString
        ACCESS  read-write
        STATUS  mandatory
        DESCRIPTION
                "Not implemented"
        ::= { smMlmFilterEntry 30 }

smMlmFilterThrottleDisarmedTrapEnterprise OBJECT-TYPE
        SYNTAX  DisplayString
        ACCESS  read-write
        STATUS  mandatory
        DESCRIPTION
                "Not implemented"
        ::= { smMlmFilterEntry 31 }

smMlmFilterThrottleDisarmedSpecificTrap OBJECT-TYPE
        SYNTAX  INTEGER
        ACCESS  read-write
        STATUS  mandatory
        DESCRIPTION
                "Not implemented"
        ::= { smMlmFilterEntry 32 }

smMlmFilterThrottleState OBJECT-TYPE
        SYNTAX  INTEGER {
                disarmed(1), -- throttleArmTrapCount traps have not occurred
                armed(2)     -- throttleArmTrapCount traps have been received
                }
        ACCESS  read-only
        STATUS  mandatory
        DESCRIPTION
                "This field is not supported."
        ::= { smMlmFilterEntry 33 }

smMlmFilterThrottleTimeStarted OBJECT-TYPE
        SYNTAX  DisplayString
        ACCESS  read-only
        STATUS  mandatory
        DESCRIPTION
                "This field is not supported."
        ::= { smMlmFilterEntry 34 }

smMlmFilterThrottleTrapCount OBJECT-TYPE
        SYNTAX  INTEGER
        ACCESS  read-only
        STATUS  mandatory
        DESCRIPTION
                "This field is not supported."
        ::= { smMlmFilterEntry 35 }

smMlmFilterMessages OBJECT-TYPE
        SYNTAX  DisplayString
        ACCESS  read-only
        STATUS  mandatory
        DESCRIPTION
               "Contains informational and error messages for
                this filter rule."
        ::= { smMlmFilterEntry 36 }

smMlmFilterThrottleCriteria OBJECT-TYPE
        SYNTAX  INTEGER {
                byNodeAndTrapType(1), --throttle on the basis of node and trap type
                byNode(2),  -- throttle on the basis of node only
                byTrapType(3), -- throttle on the basis of trap type only
                byNone(4) -- throttle traps not using node or trap type
                }
        ACCESS  read-write
        STATUS  mandatory
        DESCRIPTION
                "This field is used to indicate whether the throttle is to
                 be applied on a per node and trap type basis (byNodeAndTrapType)
                 or only per node basis (byNode) or only per trap type
                 basis (byTrapType) or on all traps that match the filter
                 rule (byNone)."
        ::= { smMlmFilterEntry 37 }

smMlmFilterThrottleVariables OBJECT-TYPE
        SYNTAX  DisplayString
        ACCESS  read-write
        STATUS  mandatory
        DESCRIPTION
                "This field is used to set additional criteria for variables
                 of which the traps will be throttled. These variables are
                 contained in the trap and the position of the variable or
                 variables is specified as a comma seperated list.  A range
                 of specific trap variables may be specified by using the
                 range format of '[#-#]' (ie. [100-199]).  For example,
                 1,[4-10],15, means the throttle uses variable binding
                 postitions 1,4,5,6,7,8,9,10, and 15 as the additional
                 throttle criteria."
        ::= { smMlmFilterEntry 38 }

--
--  The Trap Reception Settings
--

smMlmFilterTcpTrapReception OBJECT-TYPE
        SYNTAX  INTEGER {
                enabled(1),  -- MLM will connect to the tcp trap socket
                disabled(2)  -- MLM will not receive any tcp traps
                }
        ACCESS  read-write
        STATUS  mandatory
        DESCRIPTION
                "Indicator of whether or not the Mid-Level
                 Manager should connect to the tcp trap socket.
                 If enabled(1), the traps will be read from the socket.
                 If disabled(2), only traps generated by the Mid-Level
                 Manager (e.g. thresholding, status,
                 discovery traps) and traps received from the UDP socket
                 will be filtered by the Mid-Level Manager.

                 Note:  This field cannot be set to enabled if another
                 process on the host is already listening to the
                 configured TCP port (i.e. the manager).  Conversely,
                 another process on the host (ie. the manager) will not
                 be able to receive traps if this field is set to enabled.
                 Therefore, if a manager is running on the same host as
                 the Mid-Level Manager, this field should
                 be set to disabled.

                 If this field is set to enabled and any other process is
                 connected to the port specified by the TcpTrapReceptionPort
                 then TcpTrapReceptionStatus variable is set to portBusy.

                 To recheck the availability of the port, this field should be
                 disabled and then reset to enabled."
        ::= { smMlmFilter 5 }

smMlmFilterTcpReceptionStatus OBJECT-TYPE
        SYNTAX  INTEGER {
                enabled(1),  -- MLM is connected to the tcp trap socket
                disabled(2), -- MLM is not receiving  any tcp traps
                portBusy(3)  -- MLM could not connect to tcp port
                }
        ACCESS  read-only
        STATUS  mandatory
        DESCRIPTION
                "The status is set to enabled if TcpTrapReception is enabled
                 if the Mid-Level Manager is able to connect to
                 the TCP port.

                 If TcpTrapReception is disabled then this status is set to
                 disabled.

                 This field is to portBusy when TcpTrapReception is enabled, but
                 the Mid-Level Manager could not connect to the
                 TcpTrapReceptionPort."
         ::= { smMlmFilter 6 }

smMlmFilterUdpReceptionStatus OBJECT-TYPE
        SYNTAX  INTEGER {
                enabled(1),  -- MLM is connected to the udp trap socket
                disabled(2), -- MLM is not receiving any ucp traps
                portBusy(3)  -- MLM could not connect to upd port
                }
        ACCESS  read-only
        STATUS  mandatory
        DESCRIPTION
                "The status is set to enabled if UdpTrapReception is enabled
                 if the Mid-Level Manager is able to connect
                 to the UDP port.

                 If UdpTrapReception is disabled then this status is set to
                 disabled.

                 This field is to portBusy when UdpTrapReception is enabled, but
                 the Mid-Level Manager could not connect to the
                 UdpTrapReceptionPort."
         ::= { smMlmFilter 7 }

smMlmFilterUdpTrapReceptionPort OBJECT-TYPE
        SYNTAX  INTEGER
        ACCESS  read-write
        STATUS  mandatory
        DESCRIPTION
                "This field specifies the port number on which the
                 MLM receives snmp traps via UDP."
        ::= { smMlmFilter 8 }

smMlmFilterTcpTrapReceptionPort OBJECT-TYPE
        SYNTAX  INTEGER
        ACCESS  read-write
        STATUS  mandatory
        DESCRIPTION
                "This field specifies the port number on which the
                 MLM receives snmp traps via TCP."
        ::= { smMlmFilter 9 }

smMlmFilterTrapReceptionMessages OBJECT-TYPE
        SYNTAX  DisplayString
        ACCESS  read-only
        STATUS  mandatory
        DESCRIPTION
                "Contains informational and error messages about
                 trap reception fields."
        ::= { smMlmFilter 10 }

--
--  The Alias Table
--

smMlmAliasTable OBJECT-TYPE
        SYNTAX  SEQUENCE OF SmMlmAliasEntry
        ACCESS  not-accessible
        STATUS  mandatory
        DESCRIPTION
                "Alias table."
        ::= { smMlmAlias 1 }

smMlmAliasEntry OBJECT-TYPE
        SYNTAX  SmMlmAliasEntry
        ACCESS  not-accessible
        STATUS  mandatory
        DESCRIPTION
                "Each entry contains objects for a particular alias."
  INDEX { smMlmAliasName }
        ::= { smMlmAliasTable 1 }

SmMlmAliasEntry ::= SEQUENCE {
    smMlmAliasState
        INTEGER,
    smMlmAliasName
        DisplayString,
    smMlmAliasList
        DisplayString,
    smMlmAliasResolvedList
        DisplayString
}

smMlmAliasState OBJECT-TYPE
        SYNTAX  INTEGER {
                enabled(3),   -- enabled alias entry
                invalid(2),   -- an invalidated alias entry
                disabled(1)   -- disabled alias entry
                }
        ACCESS  read-write
        STATUS  mandatory
        DESCRIPTION
                "State of the alias entry: disabled (1), invalid (2),
                 or enabled (3)."
        ::= { smMlmAliasEntry 1 }

smMlmAliasName OBJECT-TYPE
        SYNTAX  DisplayString
        ACCESS  read-write
        STATUS  mandatory
        DESCRIPTION
                "Name that can be used in the threshold and analysis MIB
                 variable definitions to allow multiple remote node
                 retrieval of the MIB variable value."
        ::= { smMlmAliasEntry 2 }

smMlmAliasList OBJECT-TYPE
        SYNTAX  DisplayString
        ACCESS  read-write
        STATUS  mandatory
        DESCRIPTION
                "List of alias names, host names, or IP addresses separated
                 by white space or commas."
        ::= { smMlmAliasEntry 3 }

smMlmAliasResolvedList OBJECT-TYPE
        SYNTAX  DisplayString
        ACCESS  read-only
        STATUS  mandatory
        DESCRIPTION
                "Expanded alias."
        ::= { smMlmAliasEntry 4 }

--
--  The Trap Destination Table
--

smMlmTrapDestinationTable OBJECT-TYPE
        SYNTAX  SEQUENCE OF SmMlmTrapDestinationEntry
        ACCESS  not-accessible
        STATUS  mandatory
        DESCRIPTION
                "Trap destination table.  This table is used to define
                 the trap destinations for traps to be forwarded by
                 the filtering piece of the subagent.  It does not
                 replace or update filtering entries in the snmpd.conf
                 file.  If filtering is being used, the snmpd.conf file
                 should be setup to send traps to loopback."
        ::= { smMlmTrapDestination 1 }

smMlmTrapDestinationEntry OBJECT-TYPE
        SYNTAX  SmMlmTrapDestinationEntry
        ACCESS  not-accessible
        STATUS  mandatory
        DESCRIPTION
                "Each entry contains objects for a particular trap
                 destination."
  INDEX { smMlmTrapDestinationName }
        ::= { smMlmTrapDestinationTable 1 }

SmMlmTrapDestinationEntry ::= SEQUENCE {
    smMlmTrapDestinationState
        INTEGER,
    smMlmTrapDestinationName
        DisplayString,
    smMlmTrapDestinationHost
        DisplayString,
    smMlmTrapDestinationMask
        INTEGER,
    smMlmTrapDestinationParticipationState
        INTEGER,
    smMlmTrapDestinationActivationTime
        DisplayString,
    smMlmTrapDestinationActivationDayOfWeek
        DisplayString,
    smMlmTrapDestinationDeactivationTime
        DisplayString,
    smMlmTrapDestinationDeactivationDayOfWeek
        DisplayString,
    smMlmTrapDestinationMessages
        DisplayString
}

smMlmTrapDestinationState OBJECT-TYPE
        SYNTAX  INTEGER {
                enabled(3),   -- enabled trap destination
                disabled(1),  -- disabled trap destination
                invalid(2)    -- an invalidated trap destination
                }
        ACCESS  read-write
        STATUS  mandatory
        DESCRIPTION
                "State for the trap destination entry.  Enabling this
                 trap destination causes the traps being filtered to use
                 this destination as a default destination (ie. the
                 filtering entry may override where traps are to be
                 sent)."
        ::= { smMlmTrapDestinationEntry 1 }

smMlmTrapDestinationName OBJECT-TYPE
        SYNTAX  DisplayString
        ACCESS  read-write
        STATUS  mandatory
        DESCRIPTION
                "This field is simply used as the name of this entry."
        ::= { smMlmTrapDestinationEntry 2 }

smMlmTrapDestinationHost OBJECT-TYPE
        SYNTAX  DisplayString
        ACCESS  read-write
        STATUS  mandatory
        DESCRIPTION
               "This field specifies the hosts to which filtered traps
                are forwarded.  It may be a list containing alias names
                (contained in the smMlmAlias table), resolvable hostnames,
                or IP Addresses.
                Each name in the list should be separated by a comma
                or white space.

                 Each host listed can specify a destination port number
                 and protocol (tcp or udp ) or service name
                 using the format:

                 x+y/z where x can be ip address or hostname or alias name
                             y can be port number or protocol or service name
                             z can be port number or protocol.

                 example: testhost+162/tcp  or 9.67.162.81+udp/162

                 If the port or protocol is not specified then default
                  value is used. The default port number is '162' and
                  default protocol is 'udp'."
        ::= { smMlmTrapDestinationEntry 3 }

smMlmTrapDestinationMask OBJECT-TYPE
        SYNTAX  INTEGER
        ACCESS  read-write
        STATUS  mandatory
        DESCRIPTION
                "This mask is used as a global filtering mechanism.  The
                 mask is used to indicate which traps are to be sent
                 to the Destination Host.  Bits 0 through 6, when read from
                 LEFT to RIGHT, correspond to generic trap numbers 0 through
                 6.  The generic traps are as follows:

                   0 - Cold Start
                   1 - Warm Start
                   2 - Link Down
                   3 - Link Up
                   4 - Authentication Failure
                   5 - EGP Neighbor Loss
                   6 - Enterprise Specific

                 This field should be set to 254 to send all traps
                 that the filter passes to the trap destination table.
                 To send only linkDown (2) and linkUp (3) traps, the mask
                 could be set to 48 (ie. 0011 0000)."
        ::= { smMlmTrapDestinationEntry 4 }

smMlmTrapDestinationParticipationState OBJECT-TYPE
        SYNTAX  INTEGER {
                active(2),      -- destination is participating
                notEnabled(1),  -- destination not enabled in smMlmTrapDestinationState
                inactive(3)     -- destination is dormant
                }
        ACCESS  read-only
        STATUS  mandatory
        DESCRIPTION
                "This field indicates whether or not the destination
                 is participating in the trap forwarding.  When the destination
                 is active, it is participating.  When the destination is inactive,
                 it is not participating, but will be participating when the
                 activation time arrives.

                 The participation state can be inactive only if
                 activation/deactivation days are specified.  Otherwise,
                 the participation state is activated when the
                 smMlmTrapDestinationState field is set to enabled. If this
                 field is set to notEnabled, the smMlmTrapDestinationState
                 field is not set to enabled."
        ::= { smMlmTrapDestinationEntry 5 }

smMlmTrapDestinationActivationTime OBJECT-TYPE
        SYNTAX  DisplayString
        ACCESS  read-write
        STATUS  mandatory
        DESCRIPTION
                "This field specifies the time to activate the trap
                 destination. (i.e. changes the participation state from
                 inactive to active).

                 The format should be HH:MM where HH represents the hour
                 (integer between 0 and 23) and MM represents the minute
                 (integer between 0 and 59) to activate the destination.
                 A value of all blanks will be interpreted as 00:00."
        ::= { smMlmTrapDestinationEntry 6 }

smMlmTrapDestinationActivationDayOfWeek OBJECT-TYPE
        SYNTAX  DisplayString
        ACCESS  read-write
        STATUS  mandatory
        DESCRIPTION
         "This field specifies the days of the week to activate
         the trap destination at the time specified in the
         ActivationTime field (ie. change the participation
         state from inactive to active).
         The day of the week may be one of three literals:
             none      -  Doesn't activate
             weekdays  -  Activates destination entry on MTWThF
             all       -  Activates destination entry every day SuMTWThFS

         Alternatively, the days of the week may be specified as a
         list of numbers between 0 and 6 (Sunday = 0, Monday = 1, ...,
         Saturday = 6).  The expression '1,3,5' would activate the
         destination entry at the specified time on MWF."
         ::= { smMlmTrapDestinationEntry 7 }

smMlmTrapDestinationDeactivationTime OBJECT-TYPE
        SYNTAX  DisplayString
        ACCESS  read-write
        STATUS  mandatory
        DESCRIPTION
                "This field specifies the time to deactivate the destination.
                 (ie. change the participation state from active to inactive).
                 The format should be HH:MM where HH represents the hour
                 (integer between 0 and 23) and MM represents the minute
                 (integer between 0 and 59) to deactivate the destination.  A value
                 all blanks will be interpreted as 00:00."
        ::= { smMlmTrapDestinationEntry 8 }

smMlmTrapDestinationDeactivationDayOfWeek OBJECT-TYPE
        SYNTAX  DisplayString
        ACCESS  read-write
        STATUS  mandatory
        DESCRIPTION
                "This field specifies the days of the week to deactivate
                 the trap destination at the time specified in the
                 DeactivationTime field (ie. change the participation
                 state from active to inactive).
                 The day of the week may be one of three literals:
                   none      -  Doesn't deactivate
                   weekdays  -  Dectivates destination on MTWThF
                   all       -  Deactivates destination every day SuMTWThFS

                 Alternatively, the days of the week may be specified as a
                 list of numbers between 0 and 6 (Sunday = 0, Monday = 1, ...,
                 Saturday = 6).  The expression '1,3,5' would deactivate the
                 destination entry at the specified time on MWF."
        ::= { smMlmTrapDestinationEntry 9 }

smMlmTrapDestinationMessages OBJECT-TYPE
        SYNTAX  DisplayString
        ACCESS  read-only
        STATUS  mandatory
        DESCRIPTION
                "Contains informational and error messages for
                 this trap destination entry."
        ::= { smMlmTrapDestinationEntry 10 }

--
--  The Administration Table
--  This table is for the convenience of the end user.  It may be
--  used to store any desired administrative information
--

smMlmAdministrationTable OBJECT-TYPE
        SYNTAX  SEQUENCE OF SmMlmAdministrationEntry
        ACCESS  not-accessible
        STATUS  mandatory
        DESCRIPTION
                "Table of user information."
        ::= { smMlmAdministration 1 }

smMlmAdministrationEntry OBJECT-TYPE
        SYNTAX  SmMlmAdministrationEntry
        ACCESS  not-accessible
        STATUS  mandatory
        DESCRIPTION
                "Each entry contains objects for a particular
                 administrative community."
        INDEX { smMlmAdministrationFieldName }
        ::= { smMlmAdministrationTable 1 }

SmMlmAdministrationEntry ::= SEQUENCE {
        smMlmAdministrationFieldState
            INTEGER,
        smMlmAdministrationFieldName
            DisplayString,
        smMlmAdministrationFieldOwner
            DisplayString,
        smMlmAdministrationFieldDescription
            DisplayString,
        smMlmAdministrationFieldValue
            DisplayString
}

smMlmAdministrationFieldState OBJECT-TYPE
        SYNTAX  INTEGER {
                valid(1),    -- Valid information
                invalid(2),  -- used to delete an entry
                outDated(3)  -- Obsolete data
                }
        ACCESS  read-write
        STATUS  mandatory
        DESCRIPTION
                "Indication that administrative information is either
                 valid (1), invalid (2), or outdated (3).
                 Note:  Setting state to invalid will delete the row."
        ::= { smMlmAdministrationEntry 1 }

smMlmAdministrationFieldName OBJECT-TYPE
        SYNTAX  DisplayString
        ACCESS  read-write
        STATUS  mandatory
        DESCRIPTION
          "Name of administrative information.  There should be a
           corporate-wide policy on naming information in order to avoid
           possible naming conflicts."
        ::= { smMlmAdministrationEntry 2 }

smMlmAdministrationFieldOwner OBJECT-TYPE
        SYNTAX  DisplayString
        ACCESS  read-write
        STATUS  mandatory
        DESCRIPTION
           "Owner of this piece of administrative information."
        ::= { smMlmAdministrationEntry 3 }

smMlmAdministrationFieldDescription OBJECT-TYPE
        SYNTAX  DisplayString
        ACCESS  read-write
        STATUS  mandatory
        DESCRIPTION
           "Description of the administrative information."
        ::= { smMlmAdministrationEntry 4 }

smMlmAdministrationFieldValue OBJECT-TYPE
        SYNTAX  DisplayString
        ACCESS  read-write
        STATUS  mandatory
        DESCRIPTION
                "The actual administrative information."
        ::= { smMlmAdministrationEntry 5 }

--
--  The Status Monitor Table
--

smMlmStatusMonitorTable OBJECT-TYPE
        SYNTAX  SEQUENCE OF SmMlmStatusMonitorEntry
        ACCESS  not-accessible
        STATUS  mandatory
        DESCRIPTION
                "Status monitor table.  This table is used to define
                 the status checking policies for interfaces."
        ::= { smMlmStatusMonitor 1 }

smMlmStatusMonitorEntry OBJECT-TYPE
        SYNTAX  SmMlmStatusMonitorEntry
        ACCESS  not-accessible
        STATUS  mandatory
        DESCRIPTION
                "Each entry contains objects for a status checking
                 policy.  The configuration specified is applied to
                 all nodes and interfaces in the specified host."
  INDEX { smMlmStatusMonitorName }
        ::= { smMlmStatusMonitorTable 1 }

SmMlmStatusMonitorEntry ::= SEQUENCE {
    smMlmStatusMonitorState
        INTEGER,
    smMlmStatusMonitorName
        DisplayString,
    smMlmStatusMonitorDescription
        DisplayString,
    smMlmStatusMonitorAddressFamily
        INTEGER,
    smMlmStatusMonitorGroup
        DisplayString,
    smMlmStatusMonitorResolvedGroup
        DisplayString,
    smMlmStatusMonitorUnresolvedGroup
        DisplayString,
    smMlmStatusMonitorFrequency
        DisplayString,
    smMlmStatusMonitorTimeout
        DisplayString,
    smMlmStatusMonitorMaxAttempts
        INTEGER,
    smMlmStatusMonitorMessages
        DisplayString
}

smMlmStatusMonitorState OBJECT-TYPE
        SYNTAX  INTEGER {
                enabled(3),   -- enabled status monitor entry
                disabled(1),  -- disabled status monitor entry
                invalid(2)   -- an invalidated status monitor entry
                }
        ACCESS  read-write
        STATUS  mandatory
        DESCRIPTION
                "State for the status monitor entry.  Enabling this
                 status monitor entry causes the interfaces
                 contained in the host (or group) specified to
                 be checked using the specified parameters
                 (eg. interval, timeout, retries, ...)."
        ::= { smMlmStatusMonitorEntry 1 }

smMlmStatusMonitorName OBJECT-TYPE
        SYNTAX  DisplayString
        ACCESS  read-write
        STATUS  mandatory
        DESCRIPTION
                "This field is simply used as the name of this entry."
        ::= { smMlmStatusMonitorEntry 2 }

smMlmStatusMonitorDescription OBJECT-TYPE
        SYNTAX  DisplayString
        ACCESS  read-write
        STATUS  mandatory
        DESCRIPTION
                "This field is used to describe the entry.
                 Used for annotative purposes only."
        ::= { smMlmStatusMonitorEntry 3 }

smMlmStatusMonitorAddressFamily OBJECT-TYPE
        SYNTAX  INTEGER {
                inet(2),          -- internetwork: UDP, TCP, etc.
                unix(1),          -- local to host (pipes, portals)
                implink(3),       -- arpanet imp addresses
                pup(4),           -- pup protocols: e.g. BSP
                chaos(5),         -- mit CHAOS protocols
                ns(6),            -- XEROX NS protocols
                osi(7),           -- ISO protocols
                ecma(8),          -- european computer manufacturers
                datakit(9),       -- datakit protocols
                ccitt(10),        -- CCITT protocols, X.25 etc
                sna(11),          -- IBM SNA
                decnet(12),       -- DECnet
                dli(13),          -- DEC Direct data link interface
                lat(14),          -- LAT
                hylink(15),       -- NSC Hyperchannel
                appletalk(16),    -- Apple Talk
                route(17),        -- Internal Routing Protocol
                link(18),         -- Link layer interface
                xtpPseudo(19),    -- eXpress Transfer Protocol (no AF)
                intf(20),         -- Debugging use only
                rif(21),          -- raw interface
                netware(22),      -- netware interface
                reserved23(23),   -- reserved
                reserved24(24),   -- reserved
                reserved25(25),   -- reserved
                reserved26(26),   -- reserved
                reserved27(27),   -- reserved
                reserved28(28),   -- reserved
                reserved29(29),   -- reserved
                reserved30(30),   -- reserved
                reserved31(31),   -- reserved
                reserved32(32),   -- reserved
                unknown(65535)    -- unknown
                }
        ACCESS  read-only
        STATUS  mandatory
        DESCRIPTION
                "This indicates the address family of the address
                 specified.  Currently, only inet(2) is supported.
                 Any other address family will be treated as an
                 invalid value."
        ::= { smMlmStatusMonitorEntry 4 }

smMlmStatusMonitorGroup OBJECT-TYPE
        SYNTAX  DisplayString
        ACCESS  read-write
        STATUS  mandatory
        DESCRIPTION
               "This field specifies the group of interfaces to
                which the status monitor entry is applied.  It may be an
                alias name (contained in the smMlmAlias table),
                resolvable hostname, or network address."
        ::= { smMlmStatusMonitorEntry 5 }

smMlmStatusMonitorResolvedGroup OBJECT-TYPE
        SYNTAX  DisplayString
        ACCESS  read-only
        STATUS  mandatory
        DESCRIPTION
               "This field shows the resolved group of interfaces to
                which the status monitor entry is applied.  If the entry
                is disabled, this field is blank."
        ::= { smMlmStatusMonitorEntry 6 }

smMlmStatusMonitorUnresolvedGroup OBJECT-TYPE
        SYNTAX  DisplayString
        ACCESS  read-only
        STATUS  mandatory
        DESCRIPTION
               "This field shows the group of interfaces that
                the status monitor entry was not able to resolve.
                This field contains any string entered that either did
                not match an alias name, was not a host name or an
                IP address.  It is possible that a name shown in this
                field is the result of resolving an alias name and
                the resulting names were not hostnames or IP addresses."
        ::= { smMlmStatusMonitorEntry 7 }

smMlmStatusMonitorFrequency OBJECT-TYPE
        SYNTAX  DisplayString
        ACCESS  read-write
        STATUS  mandatory
        DESCRIPTION
                "This indicates how often to status check the
                 interfaces that this policy governs.

                 Frequency units are decimal values
                 appended by the unit:  d - day, h - hour, m - minute,
                 s - second, u - millisecond.  If no unit is appended,
                 the value is minutes.  Multiple values/units are
                 allowed (i.e. 1m30s = 1 minute, 30 seconds).

                 The default frequency is 5 minutes."
        ::= { smMlmStatusMonitorEntry 8 }

smMlmStatusMonitorTimeout OBJECT-TYPE
        SYNTAX  DisplayString
        ACCESS  read-write
        STATUS  mandatory
        DESCRIPTION
                "This indicates the number of seconds wait for a
                 response to the status request before retrying
                 the request.  The default timeout is 1 second."
        ::= { smMlmStatusMonitorEntry 9 }

smMlmStatusMonitorMaxAttempts OBJECT-TYPE
        SYNTAX  INTEGER (0..4294967295)
        ACCESS  read-write
        STATUS  mandatory
        DESCRIPTION
                "This indicates the total number of times to try
                 the status request if no response is received.
                 The default is 3 attempts."
        ::= { smMlmStatusMonitorEntry 10 }

smMlmStatusMonitorMessages OBJECT-TYPE
        SYNTAX  DisplayString
        ACCESS  read-only
        STATUS  mandatory
        DESCRIPTION
               "This field contains informational and error messages for
                this status monitor entry."
        ::= { smMlmStatusMonitorEntry 11 }

--
--  The Node Discovery Settings
--

smMlmDiscoveryState OBJECT-TYPE
        SYNTAX  INTEGER {
                disabled(1),  -- turns off discovery
                enabled(2)  -- enables discovery to occur
                }
        ACCESS  read-write
        STATUS  mandatory
        DESCRIPTION
                "This variable is used to indicate whether the
                 Mid-Level Manager should engage in discovery
                 activity.  Once enabled(2), the MLM will discover any
                 nodes with which it communicates.  However, additional
                 discovery capabilities may be configured using the
                 Sensor and BroadcastSearch fields."
        ::= { smMlmDiscovery 1 }

smMlmDiscoverySensor OBJECT-TYPE
        SYNTAX  INTEGER {
                disabled(1),  -- Don't even watch packets
                passiveSensing(2), -- Watch network packets for new nodes
                activeSensing(3) -- While watching packets, investigate unknowns
                }
        ACCESS  read-write
        STATUS  mandatory
        DESCRIPTION
                "This field indicates whether or not the
                 Mid-Level Manager should watch network packets
                 in order to ascertain which nodes are currently on the
                 network.  This field is only used if the DiscoverySwitch
                 field is enabled.

                 If this field is set to passiveSensing(2), then
                 only packets received will be examined for new nodes.

                 If this field is set to activeSensing(3), then
                 not only will received packets be examined, but any
                 hints contained in those received packets will be
                 investigated by querying those hint addresses.

                 It is recommended that activeSensing(3) be used
                 to more rapidly discover your network."
        ::= { smMlmDiscovery 2 }

smMlmDiscoverySensorMaxReads OBJECT-TYPE
        SYNTAX  INTEGER (8..512)
        ACCESS  read-write
        STATUS  mandatory
        DESCRIPTION
               "Maximum number of packets which discovery reads at one time.
                The higher this number is, the faster nodes will be
                discovered, but the more processing time will be required.
                The default for this field is 128."
        ::= { smMlmDiscovery 3 }

smMlmDiscoverySensorMaxInterval OBJECT-TYPE
        SYNTAX  DisplayString
        ACCESS  read-write
        STATUS  mandatory
        DESCRIPTION
               "Discovery uses an adaptive algorithm in deciding how often
                to search for new nodes; as more nodes are discovered,
                the frequency at which the discovery process listens
                decreases.  This variable sets the maximum time
                between listening intervals.

                The maximum read interval is specified using decimal values
                appended by the unit:  d - day, h - hour, m - minute,
                s - second, u - millisecond.  If no unit is appended,
                the value is minutes.  Multiple values/units are
                allowed (i.e. 1m30s = 1 minute, 30 seconds).  The default
                for this field is 5m (5 minutes)."
       ::= { smMlmDiscovery 4 }

smMlmDiscoveryBroadcastSearch OBJECT-TYPE
        SYNTAX  INTEGER {
                disabled(1),       -- No broadcast search will be used
                enabledOnce(2),    -- Perform the broadcast search only once,
                                   -- at the first scheduled time
                enabledRepeated(3) -- Perform the broadcast search periodically
                }
        ACCESS  read-write
        STATUS  mandatory
        DESCRIPTION
                "Indicator of whether or not the AIX Mid-Level Manager
                 should perform a broadcast query to determine which
                 machines are on the network at the configured
                 BroadcastSearchTime, on the configured BroadcastSearchDays.

                 It is a good idea to perform a broadcast search to discover
                 nodes that are not initiating communication
                 (e.g. file servers, bridges, hubs, etc.).  In addition,
                 this should be done at least as often as the
                 NodeExpirationPeriod to avoid deleting them from
                 the DiscoveryTable.

                 If enabledOnce(2), then the broadcast search is only
                 done once - at the next configured time and day.  This
                 field is then automatically set back to disabled(1) after
                 the broadcast search is initiated.

                 If enabledRepeated, then the broadcast search is done
                 periodically at each configured time and day.

                 The time and day to perform the broadcast search are
                 configured using the ActiveSearchTime and ActiveSearchDay
                 fields.

                 It is a good idea to configure a broadcast search to
                 be done at least as often as the configured
                 NodeExpirationPeriod."
        ::= { smMlmDiscovery 5 }

smMlmDiscoveryBroadcastSearchTime OBJECT-TYPE
        SYNTAX  DisplayString
        ACCESS  read-write
        STATUS  mandatory
        DESCRIPTION
                "This field specifies the time to perform a broadcast
                 request to determine who is on the network.  This will
                 cause a traffic burst to occur, so ideally it should be
                 done at a time when low traffic levels are expected on the
                 local network.

                 The format should be HH:MM where HH represents the hour
                 (integer between 0 and 23) and MM represents the minute
                 (integer between 0 and 59) to perform the active
                 search.

                 If this field is set to all blanks, it will be interpreted
                 as 00:00 (midnight)."
        ::= { smMlmDiscovery 6 }

smMlmDiscoveryBroadcastSearchDays OBJECT-TYPE
        SYNTAX  DisplayString
        ACCESS  read-write
        STATUS  mandatory
        DESCRIPTION
                "This field specifies the days of the week to perform
                 the broadcast search at the time specified in the
                 BroadcastSearchTime field (ie. send out an active request).
                 The day of the week may be one of three literals:
                     none      -  Broadcast search will never be done
                     weekdays  -  Broadcast search on MTWThF
                     all       -  Broadcast search every day SuMTWThFS

                 Alternatively, the days of the week may be specified as a
                 list of numbers between 0 and 6 (Sunday = 0, Monday = 1, ...,
                 Saturday = 6).  The expression '1,3,5' would cause a
                 broadcast search to be done at the specified time on
                 Monday, Wednesday, and Friday."
        ::= { smMlmDiscovery 7 }

smMlmDiscoveryBroadcastSearchNow OBJECT-TYPE
        SYNTAX  INTEGER {
                false(1), -- Automatically rolls back to false
                true(2)  -- Causes a broadcast search to be done immediately
                }
        ACCESS  read-write
        STATUS  mandatory
        DESCRIPTION
                "When set to true(2), a broadcast search for which machines
                 are on the network is initiated immediately. It may take
                 up to 15 seconds to realize results from this operation
                 if the Sensor is not enabled.

                 Setting this field when the DiscoverySwitch is set to
                 disabled causes the broadcast query to be done, but no
                 responses are recorded."
        ::= { smMlmDiscovery 8 }

smMlmDiscoveryNodeExpirationPeriod OBJECT-TYPE
        SYNTAX  DisplayString
        ACCESS  read-write
        STATUS  mandatory
        DESCRIPTION
                "This field specifies the amount of time a node remains
                 in the table of discovered nodes.  Setting this field
                 allows nodes that have not been heard from to be removed
                 from the discovered nodes table.  If this field is blank,
                 nodes are NEVER removed from the discovered nodes table.
                 However, if the same Network Address is used with a new
                 MAC Address, the MAC address of the existing entry
                 is changed and a trap is sent.

                 The node expiration period is specified using decimal values
                 appended by the unit:  d - day, h - hour, m - minute,
                 s - second, u - millisecond.  If no unit is appended,
                 the value is minutes.  Multiple values/units are
                 allowed (i.e. 1h45m = 1 hour, 45 minutes).  The default
                 for this field is 7d (7 days).

                 It is a good idea to perform an active search at least
                 as often as this node expiration time period to avoid
                 losing nodes that are not initiating communication
                 (e.g. file servers, bridges, hubs, etc.).  However,
                 nodes of this type that are being status checked by
                 the status checker table will continue to exist."
        ::= { smMlmDiscovery 9 }

smMlmDiscoveryNotificationFrequency OBJECT-TYPE
        SYNTAX  DisplayString
        ACCESS  read-write
        STATUS  mandatory
        DESCRIPTION
                "This field specifies the amount of time before a
                 new/old node trap is sent.  This allows many new
                 nodes to be sent in the same trap, thus reducing
                 notification traffic.  The default is 1m (1 minute)."
        ::= { smMlmDiscovery 10 }

smMlmDiscoveryNumberOfAddresses OBJECT-TYPE
        SYNTAX  INTEGER
        ACCESS  read-only
        STATUS  mandatory
        DESCRIPTION
               "This field contains the number of addresses that have been
                discovered (i.e. the number of entries in the DiscoveryTable)."
        ::= { smMlmDiscovery 11 }

smMlmDiscoveryMaxBridges OBJECT-TYPE
        SYNTAX  INTEGER
        ACCESS  read-write
        STATUS  mandatory
        DESCRIPTION
               "This field contains the maximum number of rings away
                from the current ring that a node can be on and still
                be discovered.  For example, if this number is 0, only
                nodes on the local ring will be discovered.

                Note that this is only effective for token rings;
                Ethernet frames do not contain routing information
                in the MAC frame header."
        ::= { smMlmDiscovery 12 }

smMlmDiscoveryMessages OBJECT-TYPE
        SYNTAX  DisplayString
        ACCESS  read-only
        STATUS  mandatory
        DESCRIPTION
               "This field contains messages concerning the discovery
                component of Mid-Level Manager."
        ::= { smMlmDiscovery 13 }

--
--  The Node Discovery Table
--

smMlmDiscoveryTable OBJECT-TYPE
        SYNTAX  SEQUENCE OF SmMlmDiscoveryEntry
        ACCESS  not-accessible
        STATUS  mandatory
        DESCRIPTION
                "Entries define a node that was detected to occur on the
                 local network.
                 The table is indexed by the smMlmDiscoveryAddressFamily,
                 smMlmDiscoveryNetAddress fields."
        ::= { smMlmDiscovery 50 }

smMlmDiscoveryEntry OBJECT-TYPE
        SYNTAX  SmMlmDiscoveryEntry
        ACCESS  not-accessible
        STATUS  mandatory
        DESCRIPTION
                "Each entry contains the nodes detected on the local
                 network."
  INDEX { smMlmDiscoveryAddressFamily, smMlmDiscoveryRawNetAddress }
        ::= { smMlmDiscoveryTable 1 }

SmMlmDiscoveryEntry ::= SEQUENCE {
    smMlmDiscoveryAddressFamily
        INTEGER,
    smMlmDiscoveryRawNetAddress
        OCTET STRING,
    smMlmDiscoveryNetAddress
        DisplayString,
    smMlmDiscoveryRawMACAddress
        OCTET STRING,
    smMlmDiscoveryMACAddress
        DisplayString,
    smMlmDiscoveryRawTransposedMACAddress
        OCTET STRING,
    smMlmDiscoveryTransposedMACAddress
        DisplayString,
    smMlmDiscoveryTimeLastSeen
        DisplayString,
    smMlmDiscoveryRawRoutingInformation
        OCTET STRING,
    smMlmDiscoveryRoutingInformation
        DisplayString
}

smMlmDiscoveryAddressFamily OBJECT-TYPE
        SYNTAX  INTEGER {
                unix(1),          -- local to host (pipes, portals)
                inet(2),          -- internetwork: UDP, TCP, etc.
                implink(3),       -- arpanet imp addresses
                pup(4),           -- pup protocols: e.g. BSP
                chaos(5),         -- mit CHAOS protocols
                ns(6),            -- XEROX NS protocols
                osi(7),           -- ISO protocols
                ecma(8),          -- european computer manufacturers
                datakit(9),       -- datakit protocols
                ccitt(10),        -- CCITT protocols, X.25 etc
                sna(11),          -- IBM SNA
                decnet(12),       -- DECnet
                dli(13),          -- DEC Direct data link interface
                lat(14),          -- LAT
                hylink(15),       -- NSC Hyperchannel
                appletalk(16),    -- Apple Talk
                route(17),        -- Internal Routing Protocol
                link(18),         -- Link layer interface
                xtpPseudo(19),    -- eXpress Transfer Protocol (no AF)
                intf(20),         -- Debugging use only
                rif(21),          -- raw interface
                netware(22),      -- netware interface
                reserved23(23),   -- reserved
                reserved24(24),   -- reserved
                reserved25(25),   -- reserved
                reserved26(26),   -- reserved
                reserved27(27),   -- reserved
                reserved28(28),   -- reserved
                reserved29(29),   -- reserved
                reserved30(30),   -- reserved
                reserved31(31),   -- reserved
                reserved32(32),   -- reserved
                unknown(65535)    -- unknown
                }
        ACCESS  read-only
        STATUS  mandatory
        DESCRIPTION
                "This indicates the transport protocol used
                 and determines the output format of the
                 network address."
        ::= { smMlmDiscoveryEntry 1 }

smMlmDiscoveryRawNetAddress OBJECT-TYPE
        SYNTAX  OCTET STRING
        ACCESS  read-only
        STATUS  mandatory
        DESCRIPTION
               "This field specifies the address of the discovered
                node as octets."
        ::= { smMlmDiscoveryEntry 2 }

smMlmDiscoveryNetAddress OBJECT-TYPE
        SYNTAX  DisplayString
        ACCESS  read-only
        STATUS  mandatory
        DESCRIPTION
               "This field specifies the printable address of the
                discovered node."
        ::= { smMlmDiscoveryEntry 3 }

smMlmDiscoveryRawMACAddress OBJECT-TYPE
        SYNTAX  OCTET STRING
        ACCESS  read-only
        STATUS  mandatory
        DESCRIPTION
               "This field specifies the MAC Address of the
                discovered node as octets."
        ::= { smMlmDiscoveryEntry 4 }

smMlmDiscoveryMACAddress OBJECT-TYPE
        SYNTAX  DisplayString
        ACCESS  read-only
        STATUS  mandatory
        DESCRIPTION
               "This field specifies the printable MAC Address
                of the node."
        ::= { smMlmDiscoveryEntry 5 }

smMlmDiscoveryRawTransposedMACAddress OBJECT-TYPE
        SYNTAX  OCTET STRING
        ACCESS  read-only
        STATUS  mandatory
        DESCRIPTION
               "The transposed MAC address is the MAC address
                with the bits in each byte of the address reversed, so
                that the least significant bit is now the most significant
                bit and vice versa.  This is useful for token ring
                addresses since these addresses are usually represented
                in non-canonical form rather than the canonical form
                specified in the IEEE 802 specification and used by
                Ethernet, where the bit that travels first on the LAN
                is placed in the least significant bit as it appears
                in memory."
        ::= { smMlmDiscoveryEntry 6 }

smMlmDiscoveryTransposedMACAddress OBJECT-TYPE
        SYNTAX  DisplayString
        ACCESS  read-only
        STATUS  mandatory
        DESCRIPTION
               "This field is the printable form of the transposed MAC
                address."
        ::= { smMlmDiscoveryEntry 7 }

smMlmDiscoveryTimeLastSeen OBJECT-TYPE
        SYNTAX  DisplayString
        ACCESS  read-only
        STATUS  mandatory
        DESCRIPTION
               "This field specifies the last time that the discovery
                process encountered this address.  Addresses that are
                are not seen for the period of time defined in the
                smMlmDiscoveryExpirationTime parameter are removed from
                this table."
        ::= { smMlmDiscoveryEntry 8 }

smMlmDiscoveryRawRoutingInformation OBJECT-TYPE
        SYNTAX  OCTET STRING
        ACCESS  read-only
        STATUS  mandatory
        DESCRIPTION
               "This field specifies the routing information to a node;
                it is valid only for token ring interfaces.  It contains
                multiple routing information segments separated with two
                zero bytes.  The length of each segment is present in the
                routing control field (the first byte of each segment)."
        ::= { smMlmDiscoveryEntry 9 }

smMlmDiscoveryRoutingInformation OBJECT-TYPE
        SYNTAX  DisplayString
        ACCESS  read-only
        STATUS  mandatory
        DESCRIPTION
               "This field displays the known routes to a node,
                in the form: [Route 1] [Route 2] ... [Route n].
                Each route entry has the form:
                [RCF: (Ring)/Bridge->(Ring)/Bridge->...(Ring)] where
                RCF is the hexadecimal representation of the route
                control field in the packet from which this route
                was discovered (in hexadecimal), Ring is the bridge
                number, and Bridge is the bridge number.  Note that
                this information is only displayed for token rings."
        ::= { smMlmDiscoveryEntry 10 }

-- End definition of MIB Subtree

--
--  The Analysis Table
--

smMlmAnalysisTable OBJECT-TYPE
        SYNTAX  SEQUENCE OF SmMlmAnalysisEntry
        ACCESS  not-accessible
        STATUS  obsolete
        DESCRIPTION
                "Analysis table."
        ::= { smMlmAnalysis 1 }

smMlmAnalysisEntry OBJECT-TYPE
        SYNTAX  SmMlmAnalysisEntry
        ACCESS  not-accessible
        STATUS  obsolete
        DESCRIPTION
                "Each entry contains objects for a particular analysis."
  INDEX { smMlmAnalysisName }
        ::= { smMlmAnalysisTable 1 }

SmMlmAnalysisEntry ::= SEQUENCE {
    smMlmAnalysisState
        INTEGER,
    smMlmAnalysisName
        DisplayString,
    smMlmAnalysisDescription
        DisplayString,
    smMlmAnalysisOwnerID
        DisplayString,
    smMlmAnalysisLocalRemoteMIBVariableExpression
        DisplayString,
    smMlmAnalysisPollTime
        DisplayString,
    smMlmAnalysisResultIndex
        INTEGER,
    smMlmAnalysisIntegerResult
        INTEGER,
    smMlmAnalysisCounterResult
        Counter,
    smMlmAnalysisGaugeResult
        Gauge,
    smMlmAnalysisDisplayStringResult
        DisplayString,
    smMlmAnalysisReturnCode
        INTEGER,
    smMlmAnalysisStandardError
        DisplayString
}

smMlmAnalysisState OBJECT-TYPE
        SYNTAX  INTEGER {
                enabled(3),  -- analysis enabled, no store
                disabled(1), -- analysis disabled
                invalid(2)  -- an invalidated analysis
                }
        ACCESS  read-write
        STATUS  obsolete
        DESCRIPTION
                "State for the analysis operation: disabled (1),
                 invalid (2), or enabled (3)."
        ::= { smMlmAnalysisEntry 1 }

smMlmAnalysisName OBJECT-TYPE
        SYNTAX  DisplayString
        ACCESS  read-write
        STATUS  obsolete
        DESCRIPTION
                "Analysis name for use as a label and row instance.
                 The selection of a row in the table uses the analysis name as
                 the instance for row selection.  The analysis name is
                 appended to the row variable to uniquely identify the instance
                 variable.  For example, the instance of smMlmAnalysisState is
                 smMlmAnalysisState.smMlmAnalysisName, where each octet in
                 smMlmAnalysisName is a value in dot notation for the variable."
        ::= { smMlmAnalysisEntry 2 }

smMlmAnalysisDescription OBJECT-TYPE
        SYNTAX  DisplayString
        ACCESS  read-write
        STATUS  obsolete
        DESCRIPTION
                "Analysis description for the analysis operation."
        ::= { smMlmAnalysisEntry 3 }

smMlmAnalysisOwnerID OBJECT-TYPE
        SYNTAX  DisplayString
        ACCESS  read-write
        STATUS  obsolete
        DESCRIPTION
                "Owner ID (IP address or hostname) who generated the
                 command entry.  This must be initialized by the user."
        ::= { smMlmAnalysisEntry 4 }

smMlmAnalysisLocalRemoteMIBVariableExpression OBJECT-TYPE
        SYNTAX  DisplayString
        ACCESS  read-write
        STATUS  obsolete
        DESCRIPTION
                "Analysis MIB variable expression.  The expression can be any
                 expression comprised of local or remote (MLM only) node MIB
                 variables with the following high to low precedence and left
                 to right associativity of operators:

                     () : grouping
                     -  : unary minus
                     *  : multiplication, / : division, % : remainder
                     +  : addition, - : subtraction
                     << : bitwise left shift, >> : bitwise right shift
                     &  : bitwise AND
                     ^  : bitwise exclusive OR
                     |  : bitwise inclusive OR

                 Expression evaluation/operators are based on standard
                 c program execution.

                 Counter MIB variables default to the delta value, calculated
                 by subtracting the old MIB value from the current MIB value.
                 Integer and gauge MIB variables default to the current value
                 returned.  The two functions @delta() and @value() can be used
                 to override the above defaults.  Displaystrings can be converted
                 to a real value using the @delta() and @value() functions.

                 Built-in functions available within expressions include:

                     @sum(MIB variable expression, MIB variable expression, ...) -
                      returns the sum of all values.
                     @avg(MIB variable expression, MIB variable expression, ...) -
                      returns the average of all values.
                     @min(MIB variable expression, MIB variable expression, ...) -
                      returns the minimum of all values.
                     @max(MIB variable expression, MIB variable expression, ...) -
                      returns the maximum of all values.
                     @diff(MIB variable expression, MIB variable expression) -
                      returns the positive difference in the two expressions.
                     @delta(MIB variable expression) - uses the delta value
                      calculated by subtracting the last returned MIB variable
                      value from the current MIB variable value.  This function
                      can be used to force delta calculations on integer, gauge,
                      and displaystring MIB variables.
                     @value(MIB variable expression) - uses the current MIB
                      variable value.  This function can be used to force the
                      use of actual values for counter MIB variables.
                     @numInst(MIB variable expression) - returns the number
                      of instances found for the MIB variable expression.
                     @abs(MIB variable expression) - returns the positive
                       value of the expression.
                     @rand() - returns a random number between 0 and
                       42949667295.

                 To use remote MIB variables, the alias name, host name, or
                 IP address can be pre-appended to the MIB variable binding.
                 Also, the object ID can accept a wildcard value (*).

                 When MIB variables resolve to multiple values or nodes
                 outside of the built-in functions, all resolved values
                 are averaged before use in the expression.  For example,
                 routers:.1.2.3.4.5.0/100, would result in the averaging
                 of all values returned for this aliased MIB variable
                 before the division by 100 operation is performed."
        ::= { smMlmAnalysisEntry 5 }

smMlmAnalysisPollTime OBJECT-TYPE
        SYNTAX  DisplayString
        ACCESS  read-write
        STATUS  obsolete
        DESCRIPTION
                "Analysis polling time.  Polling units are decimal values
                 appended by the unit:  d - day, h - hour, m - minute,
                 s - second, or u - millisecond.  If no unit is appended,
                 the value is minutes.  Multiple values/units are allowed
                 (i.e. 1h45m = 1 hour, 45 minutes).

                 The default and minimum poll time is 1 minute.  This polling
                 value is used only by the MIB variable polling center for
                 retrieval of the local or remote MIB variable for caching.
                 This is required so that the MIB variable values are cached
                 and not requested with GET requests when the expression is
                 evaluated."
        ::= { smMlmAnalysisEntry 6 }

smMlmAnalysisResultIndex OBJECT-TYPE
        SYNTAX  INTEGER {
                integer(2),  -- result is integer
                counter(3),  -- result is counter
                gauge(4)     -- result is gauge
                }
        ACCESS  read-write
        STATUS  obsolete
        DESCRIPTION
                "Index to point to command output result type.  The index
                 defines how the expression is evaluated, either using signed
                 arithmetic for integer or unsigned arithmetic for counter
                 and gauge.  The result for counter wraps on overflow or
                 underflow; the result for gauge latches at 0 for underflow
                 or 4294967295 for overflow."
        ::= { smMlmAnalysisEntry 7 }

smMlmAnalysisIntegerResult OBJECT-TYPE
        SYNTAX  INTEGER
        ACCESS  read-only
        STATUS  obsolete
        DESCRIPTION
                "Integer result based on signed arithmetic."
        ::= { smMlmAnalysisEntry 8 }

smMlmAnalysisCounterResult OBJECT-TYPE
        SYNTAX  Counter
        ACCESS  read-only
        STATUS  obsolete
        DESCRIPTION
                "Counter result based on unsigned arithmetic; this wraps
                 at the maximum or minimum value."
        ::= { smMlmAnalysisEntry 9 }

smMlmAnalysisGaugeResult OBJECT-TYPE
        SYNTAX  Gauge
        ACCESS  read-only
        STATUS  obsolete
        DESCRIPTION
                "Gauge result based on unsigned arithmetic; this
                 latches at the maximum or minimum value."
        ::= { smMlmAnalysisEntry 10 }

smMlmAnalysisDisplayStringResult OBJECT-TYPE
        SYNTAX  DisplayString
        ACCESS  read-only
        STATUS  obsolete
        DESCRIPTION
                "Display result as a displayable string.  This string
                 is generated based on the ResultIndex for the type
                 of the resultant expression: integer, counter, or gauge."
        ::= { smMlmAnalysisEntry 11 }

smMlmAnalysisReturnCode OBJECT-TYPE
        SYNTAX  INTEGER
        ACCESS  read-only
        STATUS  obsolete
        DESCRIPTION
                "Return code from the evaluation of the expression."
        ::= { smMlmAnalysisEntry 12 }

smMlmAnalysisStandardError OBJECT-TYPE
        SYNTAX  DisplayString
        ACCESS  read-only
        STATUS  obsolete
        DESCRIPTION
                "Standard error output from the evaluation of the expression."
        ::= { smMlmAnalysisEntry 13 }

-- End definition of EUI MIB Subtree

END
