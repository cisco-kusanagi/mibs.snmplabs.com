--   ***********************************************************
             --    *********************************************************
             --    **                                                     **
             --    **   The ICN WN BA E12 SNMP-Team proudly presents:     **
             --    **                                                     **
             --    **                  The XLDV20 MIB                     **
             --    **                                                     **
             --    *********************************************************
             --   ***********************************************************
             --  *************************************************************
             -- ***************************************************************
             --
             --



             -- The XLDV20-MIB comprises managed entities for different versions of XLD.
             -- The snmpAgent of the DSLAM implements the features of the XLD version.
             -- Therefore the MIB objects are labeled with the corresponding XLD Version.
             -- Managed objects with no labels are objects which have been already defined
             -- in the xldv1.mib. The labels are the following :
             --
             --      XLDV2.0  SNMP IF for TMN45020
             --      XLDV2.x  (late feature not yet supported).
             --
             -- include header files needed by the method routines
             --
             XLDV20-MIB              DEFINITIONS ::= BEGIN

             IMPORTS
	Counter32, Gauge32, Unsigned32, Integer32 FROM SNMPv2-SMI				 
	TEXTUAL-CONVENTION FROM SNMPv2-TC
                 IpAddress, TimeTicks
                       FROM RFC1155-SMI
                 OBJECT-TYPE
                       FROM RFC-1212
                 TRAP-TYPE
                       FROM RFC-1215
                 onu 
                    FROM AN-MIB ;


       -- ***************
       -- Ip Addres is defined as: 
       -- IpAddress ::=                    ( in network byte order )
       -- [APPLICATION 0]
       -- IMPLICIT OCTET STRING ( SIZE (4) )
       -- ************


             --  VERSION XLDV2.0 and following
             --  ORGANIZATION "Siemens AG, ICN WN BA E"
             --  CONTACT-INFO
             --  "      Angelika Svoboda
             --         ICN WN BA E12
             --         Tel.: +49 89 722 48063
             --
             --         Thomas Vetter
             --         ICN WN BA E12
             --         Tel.: +49 89 722 44323
             --
             -- **************************************************************
             --                      Versions and Revisions
             -- **************************************************************
             -- Date      Changes                                    MR/Author
             -- --------------------------------------------------------------
             -- 00-12-01 MOD:    kbps224Cps528 (7)  to            MR2872/Muhn
             --                  kbps208Cps490 (7)  in       
             --                Xldv20SdslDataRate and    
             --                Xldv20SdslDataRateCurrent
             -- --------------------------------------------------------------
             -- 00-11-30 ADD: new values to Xldv20SdslDataRate    MR2872/tv  
             --               u,nd Xldv20SdslDataRateCurrent 
             --                  kbps400Cps943     (  13 )
             --                  kbps784Cps1849    (  25 )
             --                  kbps1168Cps2754   (  37 )
             --                  kbps1552Cps3660   (  49 )
             -- --------------------------------------------------------------
             -- 00-10-23 ADD: new type                             MR2757/asvo
	     --               Xldv20AdslDataRateDownCurrent 
	     --               Xldv20AdslDataRateUpCurrent 
	     --               add new value rateInvalid (32767)
	     --               to be used for current rate attributes :
	     --               - xldv20AdcDataRateDown
	     --               - xldv20AdcDataRateUp
	     --          ADD: new type Xldv20SdslDataRateCurrent
	     --               add new value rateInvalid (32767)
	     --               to be used for current rate attribute :
	     --               - xldv20SdcDataRate
             -- --------------------------------------------------------------
             -- 00-10-18 CHG: type Xldv20Latency                   MR2725/asvo
	     --               values are now :
	     --               - interleavedLow
	     --               - interleavedHigh
	     --               - fast
             -- --------------------------------------------------------------
             -- 00-10-17 ADD: new attributes to xldv20SdcPPTPTable MR2726/asvo
	     --               - xldv20SdcTransceiverOutputPower,
	     --               - xldv20SdcXdslServiceType
	     --          CHG: Xldv20SdslDataRate : delete values
	     --               (as not supported by the HW)
	     --          ADD: new values                           MR2729/asvo
	     --               - marginNotApplicable (32766)
	     --               - attenuationNotApplicable (32766)
             -- --------------------------------------------------------------
             -- 00-10-10 ADD: new value  to Xldv20ControlReq:      MR2709/asvo
	     --               - sucAlreadyLoaded
             -- --------------------------------------------------------------
             -- 00-10-04 ADD: new values to Xldv20XdslInitStatus:  MR2682/asvo
	     --               - gliteModeNotPossibleInPCM,
	     --               - alarmsDetected,
	     --               - initStatusUnknown
             -- --------------------------------------------------------------
             -- 00-10-04 CHG: default value for subCarrier         MR2558/asvo
	     --               to 64 (up) and 256 (downstream)
             -- --------------------------------------------------------------
             -- 00-09-28 CHG: sequence of trap variable of         MR2674/Muhn
	     --               atmLayerMultiAlarm trap         
             --          CHG: new size of xldv20AlmIndex:1..700    MR2669/Muhn
             -- --------------------------------------------------------------
             -- 00-09-26 ADD: define new type                      MR2558/asvo
	     --                  Xldv20AdslOutputPower,
	     --               add new  attributes                 
	     --                  xldv20AdcTransceiverOutputPower,
	     --                  xldv20AdcFirstUsedSubCarrierUpstream,
	     --                  xldv20AdcFirstUsedSubCarrierDownstream,
	     --                  xldv20AdcLastUsedSubCarrierUpstream,
	     --                  xldv20AdcLastUsedSubCarrierDownstream,
	     --          ADD: add new attribute                    MR2569/asvo
	     --                  xldv20AdcXdslServiceType       
	     --               define new type 
	     --                  Xldv20XdslServiceTypeCurrent
             -- --------------------------------------------------------------
             -- 00-09-20 ADD: define new type Xldv20AdslMinMargin  MR2619/asvo
	     --               for Xldv20AdcCtrlMinMarginUp/Dn
             -- --------------------------------------------------------------
             -- 00-09-12 ADD: for Xldv20XdslServiceType            MR2556/asvo
             --               new value gDotAll (4)
	     --          ADD: define new types Xldv20AdslMargin for  MR2564
	     --               xldv20AdcMarginUp,
	     --               xldv20AdcMarginDn,
	     --               xldv20SdcMarginUp,
	     --               xldv20SdcMarginDn,
	     --               define new type Xldv20AdslAttenuation for
	     --               xldv20AdcAttenuationUp,
	     --               xldv20AdcAttenuationDn,
	     --               xldv20SdcAttenuationUp,
	     --               xldv20SdcAttenuationDn,
             -- --------------------------------------------------------------
             -- 00-09-05 ADD:  xldv20VpcEthVpcIndex                MR2525/tv
             --                xldv20VpcAtmfVplIndex
             -- --------------------------------------------------------------
             -- 00-09-04 ADD:  HPOV comment tags for HPVO - tools ....../tv
             -- --------------------------------------------------------------
             -- 00-08-30 CHG:  extend range of CDVT attributes    MR2518/tv
	     --                   to 504.000.000 microsecs
             -- --------------------------------------------------------------
             -- 00-08-17 ADD : new attribute                      MR2473/asvo
	     --                xldv20ActCDVTAutoConfig
             -- --------------------------------------------------------------
             -- 00-08-02 CHG : Xldv20StartupType                  MR2411/asvo
	     --                change enumeration values as sent by STARTUP
             -- --------------------------------------------------------------
             -- 00-08-02 CHG : type of xldv20TvCallpObjectType    MR2410/asvo
             --                to Xldv20RepSource
             -- --------------------------------------------------------------
             -- 00-07-20 CHG : Xldv20SdslDataRate                 MR2327/asvo
	     --                correct Cps values :
             --                   kbps2320Cps5471   (  72 )
	     --                   kbps1744Cps4113   (  54 ),
             -- --------------------------------------------------------------
             -- 00-07-19 CHG : xldv20SdslDataRate                 MR2327/asvo
             --               add new value kbps2320Cps5433   (  72 )
	     --               modify value  kbps1744Cps4075   (  54 ),
	     --               NOTE : both are not multiples of 32kbps 
             --          ADD : new attributes                     MR2326/asvo
	     --                xldv20SdcCtrlMinMarginUp,
	     --                xldv20SdcMinMarginUpCfg,
             --          CHG : routing info SET to tm of
	     --                xldv20ImaGroupTxImaId 
             -- --------------------------------------------------------------
             -- 00-07-17 MR2303 :                                   V2.0 asvo
	     --          CHG : change range to 32..127 of  
	     --                   xldv20ActInbandVci
	     --          CHG : type of xldv20TvRestoreResult to
	     --                   Xldv20ControlReq      
             -- --------------------------------------------------------------
             -- 00-07-10 MR2210 :                                    V2.0 asvo
             --          CHG: change rate to 32..3500 of
	     --                  xldv20VccVciValue 
	     --                  xldv20VclVciValue 
	     --          CHG: change range to 5..71 of SDSL data rate
	     --               xldv20SdcCtrlRate  
	     --               xldv20SdcRateCfg
	     --               Xldv20SdslDataRate
             -- --------------------------------------------------------------
             -- 00-07-05 IUS version for LUIMADS1                    V2.0 asvo
             --              Use new typesXldv20AdslDataRateDown/Up  MR2223
	     --              for attributes :
             --                  xldv20AdcRateDn
             --                  xldv20AdcRateUp
             -- --------------------------------------------------------------
             -- 00-06-26 IUS version for LUIMADS1                    V2.0 asvo
	     --          Changes according review comments :
	     --          ADD: for trap xldv20TrRAI add new value 
	     --               in Xldv20AlarmState : rai (413),
	     --               in Xldv20TrapIds    : trRAI (413)
	     --          CHG: make trap results and ControlReqResult 
	     --               consistent : replace following types of
	     --               trap variables by Xldv20ControlReq :
	     --               Xldv20CACProblemType (TvCACProblemType), 
	     --               Xldv20DbuReadStatus (TvDbuxxxLogReadResult),
	     --               Xldv20HwuControlResult (TvHwuControlResult),
	     --          DEL: in Xldv20ControlReq: delete value
	     --               actMaxNrOfCcsExceeded
	     --          ADD: in Xldv20ControlReq: add values
	     --               actMaxNrOfCcsInDbExceeded,
	     --               actMaxNrOfCcsOnHwExceeded
             --          ADD: for xldv20StcTelnetAccess add comment that
	     --               feature is currently not supported.
	     --          CHG: range 32..3500 for 
	     --                  xldv20ActVciNni,
	     --                  xldv20ActVciUni,
             --               range 0..255 of 
	     --                  xldv20ActInbandVpi 
             --               range 32..3500 of
	     --                  xldv20ActInbandVci
             -- --------------------------------------------------------------
	     --          Changes according MR's :
	     --          ADD: New type for ADSL/SDSL data rate       MR 2210,
	     --               with reduced ranges :                  MR 2223
	     --               Xldv20AdslDataRateDown : 1..253
	     --               Xldv20AdslDataRateUp   : 1..24
             --               Use these types for attributes :
             --                  xldv20AdcCtrlMinRateDn
             --                  xldv20AdcCtrlMinRateUp
             --                  xldv20AdcCtrlMaxRateDn
             --                  xldv20AdcCtrlMaxRateUp
             --                  xldv20AdcMinRateDnCfg
             --                  xldv20AdcMinRateUpCfg
             --                  xldv20AdcMaxRateDnCfg
             --                  xldv20AdcMaxRateUpCfg
	     --               Xldv20SdslDataRate : 5..253
             --                  xldv20SdcCtrlRate
             --                  xldv20SdcRateCfg
             --                  xldv20SdcRate
             -- --------------------------------------------------------------
             -- 00-06-08 ADD: new value in Xldv20ControlReq  MR1934  V2.0 Muhn
	     --               hwuUpgradeRunning (3116)
             -- --------------------------------------------------------------
             -- 00-06-07 ADD: new trap for LUIMADS1          MR2013  V2.0 asvo
	     --               xldv20TrRAI for d1nIma
	     --          CHG: range to 1..512 of 
	     --               xldv20HwContainedUnitAddr
	     --               xldv20HwuContainedUnitAddr (former Integer32
	     --               to avoid SimpleTester problems in Test22,23)
	     --               xldv20TvHwContainedUnitAddr
	     --          CHG: correct the enum-value for
             --               gmt12FidschiKamtschatkaMarschallIslands (44)        
	     --          CHG: type of xldv20ImaControlGroupIndex to
	     --               INTEGER (1..2147483647) (former Integer32
	     --               to avoid SimpleTester problems in Test22,23)
             -- --------------------------------------------------------------
             -- 00-05-29 CHG: rename xldv20ActNumberOfVcs to  MR2073 V2.0 asvo
	     --               xldv20ActMaxVciValue
	     --               change range to 32..3500
             -- --------------------------------------------------------------
             -- 00-05-17 ADD: new type Xldv20TimeZone         MR1933 V2.0 asvo
	     --               for attribute xldv20NeTimeZone;
	     --               new attribute xldv20NeSummerTime
	     --               new type Xldv20DayLightSavingTime
	     --          ADD: new enum values 
             --               actSegmentEndPointNtFaulty      (2142)
             --               continuityCheckTrafficDirectionConflict (2356)
             -- --------------------------------------------------------------
             -- 00-05-16 ADD: new MIB table                   MR2033 V2.0 asvo
	     --               xldv20HwUnitMappingTable
	     --          ADD: new PIU type LUIMADS1           MR2013
	     --               (comment only)
             -- --------------------------------------------------------------
             -- 00-05-09 CHG: ranges for COH attributes of type      V2.0 asvo
             --               xldv20xxxCellDelayVariationToleranceUpstream
             --               xldv20xxxCellDelayVariationToleranceDownstream :
	     --               2..200000 micro seconds, default 3000
             -- --------------------------------------------------------------
             -- 00-05-03 CHG: ranges for COH attributes of type      V2.0 asvo
             --               xldv20xxxVbrCDVTUpstream 
             --               xldv20xxxVbrCDVTDownstream  :
	     --               2..200000 micro seconds, default 3000
             -- --------------------------------------------------------------
             -- 00-04-25 ADD: new hwm controlreq values                V2.0 tv  
             --                        changeHwUnitForced        and 
             --                        hwuForcedChangeNotAllowed
             -- --------------------------------------------------------------
             -- 00-04-25 CHG: change the name of ...ServiceType values V2.0 tv  
             -- --------------------------------------------------------------
             -- 00-04-19 ADD: Define new type Xldv20SdslServiceType  V2.0 asvo
	     --               to be used for attributes :
	     --               xldv20SdcCtrlXdslServiceType,
	     --               xldv20SdcXdslServiceTypeCfg
             -- --------------------------------------------------------------
             -- 00-04-18 CHG: Delete Xldv2oControlReqResult type,    V2.0 asvo
	     --               use Xldv20ControlReq instead (as in V1.3)
	     --               add command result values to Xldv20ControlReq
             -- --------------------------------------------------------------
             -- 00-04-17 CHG: ranges of                              V2.0 asvo
	     --               xldv20AccVpiNniIndex : 1..2000
	     --               xldv20VpcIndex,
             --               xldv20VclVpcIndex ,
             --               xldv20AccEthVpcIndex,
             --               xldv20VccVpcIndex,
             --               xldv20VcxEthVpcIndex : 1..2000
	     --               xldv20VplIndex ,
             --               xldv20AccAtmfVplIndex ,
             --               xldv20VcxAtmfVplIndex : 1..4000
	     --          ADD: new values vplCC, vclCC in Xldv20RepSource
             -- --------------------------------------------------------------
             -- 00-04-12 ADD: TCON as marker for TEXTUAL CONVENTIONS  V2.0 TV
             --               for snmpinfo.dat tool                          
             -- --------------------------------------------------------------
             -- 00-04-06 CHG:  range of xldv20ActVpiUni to 0..63     V2.0 asvo
             --          DEL:  value in xldv20TrapIds : trHistoryDayCounters
	     --          CHG:  correct name of trap of
             --                xldv20TrUnsufficientLinksFe to        
	     --                xldv20TrInsufficientLinksFe
	     --          ADD: routing info for ..S3nPathTraceSendDefault,
	     --                ..S3PathTraceTIMDetectionActivate
             -- --------------------------------------------------------------
             -- 00-04-04 ADD:  new values in Xldv20XdslInitStatus    V2.0 asvo
             --		    ,trainingBlockedBySu               (16)
             --		    ,trainingBlockedByCi               (17)
             --		    ,ntNotPresentDetectedOnCi          (18)
             -- --------------------------------------------------------------
	     --          I U S V e r s i o n for S D S L, N T 4 5 0 0 :
             -- 00-03-29 CHG:  'UPL' to 'UPL:A'                      V2.0 asvo
             -- --------------------------------------------------------------
             -- 00-03-22 CHG:  OID-sequence from onu 5 to onu 4       V2.0  tv 
	     --          ADD:  sucLoadTypeUnknown  (10)
             -- --------------------------------------------------------------
             -- 00-03-20 DEL: value line in Xldv20RepSource    V20        asvo
	     --          CHG: Default of xldv20S3nSDThreshold to exp10E5
	     --          CHG: range of xldv20VplCvpIndexSegment to 0..2000
             -- 00-03-14 ADD: cacMbsScrError   (2562)          V20        asvo
             --               cacInternalError (2563)                            
	     --          CHG: Adjust Xldv20AlarmState values 450-457
	     --               to values of Xldv20TrapIds
	     --          CHG: Default of xldv20S1nSDThreshold to exp10E5
             -- --------------------------------------------------------------
             -- 00-02-28 CHG: xldv20ExtAlarmIndex range 1..3   V20        asvo
	     --               change description in xldv20ExtAlarmName
	     --          CHG: xxxControlTimer type to Unsigned32
             -- --------------------------------------------------------------
	     --          A F I  V e r s i o n for S D S L, N T 4 5 0 0 :
             -- 00-02-16 SDSL specific extensions :            V20        asvo
             --          ADD: xldv20SdcControl, xldv20SdcPPTPTable
             --          ADD: sdc, sdr to Xldv20IfType
             -- --------------------------------------------------------------
             -- 00-02-16 NT4500 specific extensions :          V20        asvo
             --          Feature : Specify segment end point at NT :
             --          ADD: xldv20ActSegmentEndPointNt,
             --          ADD: pointer to additional VplTp at Atmf port of NT :
             --               xldv20AccAtmfVplIndex,
             --               xldv20VcxAtmfVplIndex
             --          Feature : Continuity Check at NT :
             --          ADD: new value continuityCheckNotSupportedOnNt
             --          ADD: xldv20ActTestTypeNt,
             --               xldv20ActContinuityCheckNt,
             --               xldv20ActEndpointTypeNt
             --          ADD: trap variable xldv20TvVplTpIndex within traps:
             --               TrVplCcCreation,
             --               TrVplCcDeletion,
             --               TrVclCcCreation,
             --               TrVclCcDeletion
             --          Feature : Enable/Disable VP-AIS filtering at NT :
             --          ADD: xldv20IbmVpAISFiltering
             -- --------------------------------------------------------------
             -- 00-02-17 ADD: xldv20NeExternalTime45020 as in V13  MR1925 asvo
             -- --------------------------------------------------------------
             -- 00-02-15 DEL: trap TrStartup, TrTimingMismatch V20 MR1904 asvo
	     --          ADD: xldv20SutTimeStamp in SEQUENCE 
	     --          ADD: add info-VALUE line in xldv20SutPiuType 
	     --          ADD: add info-VALUE line in xldv20ImaGroupMappingIndex
             -- --------------------------------------------------------------
             -- **************************************************************
             -- **************************************************************


             -- **************************************************************
             --             Information Block for Version Control
             --             of MIB nodes and attributes (template)
             -- **************************************************************
             --
             -- info-TRAPTYPE:  alarm/event            ==>> for traps only
             -- info-VALUE:     minValue..maxValue; attrValue[(V2.0->)]
             -- info-ROU:       GET  SET [db,gf,up,tm,hm,ut,so,sn,cp]
             -- info-FAILEDSRC: hwm, tlm, callp       ==>> for alarm traps only
             -- info-FAILEDOBJ: [hwm] LU155,LUDSX3,LUPON,CI ,SUAD,
             -- info-FAILEDOBJ: [hwm] LIETH,LI25,NTAD,
             -- info-FAILEDOBJ: [tlm] S1n(= STM-1 NePPTP),S1f,S3n,E3n,D3n,S3f,
             -- info-FAILEDOBJ: [tlm] D3f,E3f,Pon,Adc(= Adc-PPTP),Adr,Vdc,Vdr,
             -- info-FAILEDOBJ: [tlm] Ibm(= Ibm-PPTP),Eth,Tca  
             -- info-FAILEDOBJ: [callp] VpcTP, VccTP  
             -- info-IMPL:      [V2.0,V2.x]:[rw,ro,*]
             -- info-IMPL:      e.g.: V1.1U-> (= all vers. begin. with V1.1U)
             -- info-IMPL:      e.g.: V1.0->V1.1U V1.2B:rw->V1.3A V1.3B 
             -- info-VERCTRL:   [GET,SET [db,asw,agent,blocked] or "-" 
             --                             (blocked == blocked by SNMP agent)
             --                             ("-"     == no special handling)
             -- **************************************************************



             xldv20 OBJECT IDENTIFIER
                -- info-IMPL:    V2.0->
                -- info-VERCTRL: -
             ::= { onu 4 }

             -- **************************************************************
             --             TEXTUAL-CONVENTIONs for XLDV20-MIB
             --
             -- use of textual convention syntax necessary for the exported
             -- types Xldv20ControlStatus, Xldv20AdminState, Unsigned16 and
             -- Xldv20FlowDirection in order to create the file snmpinfo.dat
             -- For load production the textual convention definitions are
             -- hidden by comment signs.
             --
             -- ATTENTION  use TCON: after comment sign for mosy tools
             --            to prepare the snmpinfo.dat file           

             -- **************************************************************
             --
             -- --------------------------------------------------------------
             --                            States
             -- --------------------------------------------------------------

             -- The control status of an entity.
             --
             --TCON: Xldv20ControlStatus ::= TEXTUAL-CONVENTION
             --TCON:      STATUS current
             --TCON:      DESCRIPTION
             --TCON:        "This data type is used as the syntax for the control status 
             --TCON:         attributes."
             --TCON:      SYNTAX INTEGER {
             --TCON:        requestIdle(1),
             --TCON:        requestBusy(2),
             --TCON:        requestPassed(3),
             --TCON:        requestFailed(4)
             --TCON:      }

             Xldv20ControlStatus ::=
                 INTEGER {
                     requestIdle(1),
                     requestBusy(2),
                     requestPassed(3),
                     requestFailed(4)
                 }

             -- The operating state of an entity.
             --
             Xldv20OperState ::=
                 INTEGER {
                     enabled(1),
                     disabled(2)
                 }

             -- Indicates whether a slot is empty or not.
             --
             Xldv20SlotStatus ::=
                 INTEGER {
                     unknown(0),
                     used(1),
                     empty(2)
                 }

             -- The administrative state of an entity.
             --
             --TCON: Xldv20AdminState ::= TEXTUAL-CONVENTION
             --TCON:      STATUS current
             --TCON:      DESCRIPTION
             --TCON:        "This data type is used as the syntax for the admin state 
             --TCON:         attributes. "
             --TCON:      SYNTAX INTEGER {
             --TCON:        unlocked(1),
             --TCON:        locked(2)
             --TCON:      }

             Xldv20AdminState ::=
                 INTEGER {
                     unlocked(1),
                     locked(2)
                 }

             -- The availability status of a hardware unit
             --
             Xldv20AvailStatus ::=
                 INTEGER {
                         available(1),
                         failed(2),
                         degraded(3),
                         offline(4),
                         notInstalled(5),
                         dependency(7)
            -- only internal states
            --               noDependency(6),
            --               noRestart(8),
            --               warmRestart(9),
            --               coldRestart(10),
            --               reloadRestart(11),
            --               noUpgrade(12),
            --               upgrade(13)
                }

             -- The attribute reflects upon the internal states of the
             -- Central Office Modem.
             --
             Xldv20LinkState ::=
                 INTEGER {
                     quiet(0),
                     idle(1),
                     train(2),
                     active(3),
                     download(4),
                     remoteDownload(6),
                     sleepMode(7),
                     unknown(255)
                 }

             -- The log read status.
             --
             Xldv20DbuReadStatus ::=
                 INTEGER {
                    dbuReadComplete                     (7081),
                    dbuReadFailed                       (7082),
                    dbuFileCreationFailed               (7083),
                    dbuFileTransmissionFailed           (7084)
                 }
     
             -- The access mode of a telnet session
             --
             Xldv20TelnetAccess ::=
                 INTEGER {
                     read(1),
                     trace(2),
                     write(3),
                     noAccess(4)
                 }

             -- The status of a telnet session
             --
             Xldv20TvTelnetSessionStatus ::=
                 INTEGER {
                     running(1),
                     stopped(2)
                 }

             -- The type of endpoint for continuity check
             --
             Xldv20EndpointType ::=
                 INTEGER { 
                     source  (1),
                     sink    (2),
                     both    (3)
                     }

             -- The type of reset result
             --
             Xldv20RstResult ::=
                 INTEGER { 
                     requestFailed (4)
                     }

             -- State of IMA group
             --
             Xldv20ImaGroupState ::=
                 INTEGER {
                   notConfigured(1),
                   startUp(2),
                   startUpAck(3),
                   configAbortUnsupported(4),
                   configAbortIncompatibleSymmetry(5),
                   configAbortOther(6),
                   insufficientLinks(7),
                   blocked(8),
                   operational(9),
                   configAbortUnsupportedImaVersion(10) }
 
              -- Failure Reason of an IMA group
              -- ATM Forum IMA v1.1, Section 10.2.1, page 55
              --
              Xldv20ImaGroupFailureStatus ::=
                  INTEGER {
                    noFailure(1), -- unit is up
                    startUpNe(2),
                    startUpFe(3),
                    invalidValueNe(4),
                    invalidValueFe(5),
                    failedAssymetricNe(6),
                    failedAssymetricFe(7),
                    insufficientLinksNe(8),
                    insufficientLinksFe(9),
                    blockedNe(10),
                    blockedFe(11),
                    otherFailure(12),
                    invalidImaVersionNe(13),
                    invalidImaVersionFe(14) }
 
              -- Failure Reason of an IMA group
              -- Indicate the transmit clock mode of the IMA group.
              -- There are two possible modes: the Common Transmit
              -- Clock (CTC) and the Independent Transmit Clock (ITC).
              -- The CTC mode corresponds to the case when the transmit clock
              -- of all IMA links are derived from the same source.  The ITC
              -- configuration corresponds to the case where there is at least
              -- one IMA link whose transmit clock is derived from a source
              -- different than at least another link transmit clock. "
              -- ATM Forum IMA v1.1, Section 7 on page 38
              --
              Xldv20ImaGroupTxClkMode  ::=
                  INTEGER {
                    ctc(1),
                    itc(2) }
 
              -- Group Symmetry of IMA group
              -- adjusted during group start-up
              -- ATM Forum IMA v1.1, Section 5.2.2.7 on page 35
              --
              Xldv20ImaGroupSymmetry ::=
                  INTEGER {
                    symmetricOperation(1),
                    asymmetricOperation(2),
                    asymmetricConfiguration(3) }
 
              -- Length of the IMA frames
              -- ATM Forum IMA v1.1, Section 5.2.2.4.2 on page 34
              --
              Xldv20ImaFrameLength ::=
                  INTEGER {
                    m32(32),
                    m64(64),
                    m128(128),
                    m256(256) }
 
              -- State of IMA link
              -- ATM Forum IMA v1.1, Section 10.1.2 on page 48
              --
              Xldv20ImaLinkState ::=
                  INTEGER {
                    notInGroup(1),
                    unusableNoGivenReason(2),
                    unusableFault(3),
                    unusableMisconnected(4),
                    unusableInhibited(5),
                    unusableFailed(6),
                    usable(7),
                    active(8) }
 
              -- Local Failure status of an IMA link
              -- ATM Forum IMA v1.1, Section 10.1.2 on page 48
              --
              Xldv20ImaLinkFailureStatus ::=
                  INTEGER {
                    noFailure(1),
                    imaLinkFailure(2),
                    lifFailure(3),
                    lodsFailure(4),
                    misConnected(5),
                    blocked(6),
                    fault(7),
                    farEndTxLinkUnusable(8),
                    farEndRxLinkUnusable(9) }


             -- --------------------------------------------------------------
             --                           Types
             -- --------------------------------------------------------------

             --
             --
             -- The textual convention like SNMPv2-TC. See rfc1903.
             -- In the Xld system we terminate all strings with '\0'.
             --
             --
             DisplayString ::= OCTET STRING (SIZE (0..255))




             -- The textual convention for a 32 bit integer index , 
              -- positive, beginning with value 1.
                      Unsigned16 ::= TEXTUAL-CONVENTION
                         STATUS current
                         DESCRIPTION
                           "Textual convention for a 16 bit integer value. "
                         SYNTAX INTEGER (0..65535)
 

             -- Following type as in IMA-MIB
             --
             MilliSeconds ::= Integer32

             -- The following types as in SNMPv2-SMIi
             -- (IMPORT makes problems during compilation)
             --

             -- A general hardware unit type identifier.
             --
             Xldv20HwUnitType ::=
                 INTEGER {
                     equipment(1),
                     equipmentHolder(2),
                     plugInUnit(3)
                 }

             -- The type of a TLM interface.
             --
             Xldv20IfType ::=
                 INTEGER {
                     s1n(1),         -- stm1nePPTP
                     s1f(2),         -- stm1fePPTP
                     adc(3),         -- adslcPPTP
                     adr(4),         -- adslrPPTP
                     ibm(5),         -- ibmPPTP
                     tca(6),         -- TC Adaptors
                     pon(7),         -- BPON           not supported
                     vdc(8),         -- vdslcPPTP      not supported
                     vdr(9),         -- vdslrPPTP      not supported
                     eth(10),        -- LIETH PPTP
                     d3n(11),        -- d3nePPTP
                     d3f(12),        -- d3fePPTP
                     e3n(13),        -- e3nePPTP
                     e3f(14),        -- e3fePPTP
                     s3n(15),        -- sts3nePPTP
                     s3f(16),        -- sts3fePPTP
                     e1nIma(20),     -- E1 near end
                     e1fIma(21),     -- E1 far end
                     d1nIma(22),     -- Ds1 near end   not supported
                     d1fIma(23),     -- Ds1 far end    not supported
                     sdc(24),        -- sdslcPPTP
                     sdr(25),        -- sdslrPPTP
                                     --
                     atmIma(107)     -- IMA group (value according
                                     -- AF-Phy-0086.000)
                 }

             -- The alarm state of a TLM entity.
             --
             Xldv20AlarmState ::=
                 INTEGER {
                     noAlarm                       (0),
                     hpEBER                        (1),
                     hpUNEQ                        (2),
                     lcd                           (3),
                     lof                           (4),
                     lop                           (5),
                     los                           (6),
                     msAIS                         (7),
                     msEBER                        (8),
                     msRDI                         (9),
                     msSD                          (10),
                     pAIS                          (11),
                     pRDI                          (12),
                     rsEBER                        (13),
                     slm                           (14),
                     tim                           (15),
                     actFault                      (16),
                     xmissionErr                   (105),
                     ais                           (114),
                     rdi                           (115),
                     plcpLof                       (116),
                     plcpRDI                       (117),
                     internalFault                 (123),
                     immMNR                        (130),          
                     lpr                           (131),
                     lol                           (132),
                     wrongServiceConfigData        (141),

                     -- E1/Ds1 near-end
                     excBER                        ( 407 ),
                     lif                           ( 408 ),
                     lods                          ( 409 ),
                           
                     -- E1/Ds1 far-end
                     txUnusableFe                  ( 410 ),
                     rxUnusableFe                  ( 411 ),
                     rfiIma                        ( 412 ),
		     rai                           ( 413 ),

                     -- IMA group 
                    startUpFe                     ( 450 ),
                    configAbort                   ( 451 ),
                    configAbortFe                 ( 452 ),
                    insufficientLinks             ( 453 ),
                    insufficientLinksFe           ( 454 ),
                    blockedFe                     ( 455 ),
                    imaMinNumOfLinks              ( 456)
                 }

             -- This type selects the mode for the trap flow control :
             --   noTraps  : no traps are sent
             --   allTraps : all traps are sent
             --   noEvents : only alarms but no events are sent
             --   noAlarms : only events but no alarms are sent
             --
             Xldv20SuppressionType ::=
                 INTEGER {
                     noTraps(1),
                     allTraps(2),
                     noEvents(3),
                     noAlarms(4)
                 }
             --
             -- This type selects the traffic type of a VPC.    
             -- for the trap flow control
             --
             Xldv20TrafficType ::=
                 INTEGER {
                     cbr    (1),              -- constant bit rate, default
                     ubr    (2),              -- unspecified bit rate,
                     nrtVbr (3),              
                     rtVbr  (4)              
                 }


             --  this type selects the traffic direction
             --
            Xldv20TrafficDirection ::=
                   INTEGER {
                         bidirectional (1),
                         upstream      (2),
                         downstream    (3) }

             -- 
             -- This type selects the equipment holder type.    
             --
             Xldv20EqhType ::=
                 INTEGER {
                     shelf(1),    -- unused 
                     slot(2),   
                     basicShelf(3),
                     extendedShelf(4),
                     ntAdslShelf(5), 
                     ntVdslShelf(6),
                     cpeShelf(7)
                 }
             --
             --
             -- This type specifies the different line types
             --
             Xldv20LineType ::=
                 INTEGER {
                     other(1),
                     shortSingleMode(2),          -- s1n, s3n
                     mediumSingleMode(3),         -- s1n, s3n
                     longSingleMode(4),           -- s1n, s3n
                     coax(5),                     -- s1n, s3n
                     utp(6),                      -- s1n, s3n
                     e3direct(7),                 -- e3n 
                     ds3plcp(8)                   -- d3n
                 }

         
              -- Default value of all current xldv20Adc... attributes of table
              -- xldv20AdcPPTPTable
              --
              -- THIS CUR DEFAULT WILL NOT BE USED IN THE MIB, BUT WILL BE USED BY 
              -- THE DSLAM SW TO SIGNALIZE A DEFAULT VALUE TO THE TMN_OS
              -- Xldv20AdcCurDefault ::=
              --     INTEGER {
              --             adcCurDefault(32767)
              --          }


             -- TLM S1n/S3n excessive bit error check threshold
             --
             Xldv20S1nS3nEberThreshold ::=
                 INTEGER {
                     exp10E3(1),
                     exp10E4(2),
                     exp10E5(3),
                     noSupervision(255)
                 }

             -- TLM S1n/S3n signal degration check threshold
             --
             Xldv20S1nS3nSDThreshold ::=
                 INTEGER {
                     exp10E5(3),
                     exp10E6(4),
                     exp10E7(5),
                     exp10E8(6),
                     exp10E9(7),
                     noSupervision(255)
                 }

             -- The value of this object identifies the severity
             -- of an alarm that has occured.
             --
             Xldv20AlarmSeverity ::=
                 INTEGER {
                     critical(1),
                     major(2),
                     minor(3),
                     warning(4),
                     noAlarming(5)
                 }

             -- The value of this object identifies the range
             -- of the alarm severity index.
             --
             Xldv20AlmSevProfileIndex ::= INTEGER (1..40) 

             -- The value of this object identifies the range
             -- of the alarm filtering index.
             --
             Xldv20AlmFiltProfileIndex ::= INTEGER (1..40) 

             -- This type specifies remote inventory result type
             --
             Xldv20RiResultType ::=
                 INTEGER {
                     riRemoteInventoryComplete(1),
                     riFileCreationFailed(2),
                     riFileTransmissionFailed(3)
                 }
             --
             -- This type specifies row status type
             --
             Xldv20RowStatus ::=
                 INTEGER {
                     create(1),
                     delete(2)
                 }

             --
             -- This type specifies the coding type of a E3/Ds3 interface
             --
             Xldv20CodingType ::=
                 INTEGER {
                     e3HDB3(1),
                     dsx3B3ZS(2)
                 }
             --
             -- This type specifies the external alarm state
             --
             Xldv20ExtAlarmActivityState ::=
                 INTEGER {
                     undeterminate(0),
                     on(1),
                     off(2)
                 }

             -- This type specifies the empty cell variant
             --
             Xldv20EmptyCellType ::=
                 INTEGER {
                     idle(1),
                     unassigned(2)
                 }

             -- Indicates the log to be read.
             --
             Xldv20LogType ::=
                 INTEGER {
                      hwmLog(1),
                      sweLog(2),
                      swTraceLog(3)
                 }

             -- Indicates the validity of a request.
             --
             Xldv20SucAllOfType ::=
                 INTEGER {
                      sucUpgrSingle (1),
                      sucUpgrAll    (2),
                      sucLoadTypeUnknown (10)
                 }

             -- Indicates the validity of a request.
             --
             Xldv20ResetLevel ::=
                 INTEGER {
                      plugInUnit(3),
                      system(4)
                 }

             -- Indicates the downstream data rate.
             --
             Xldv20VdcRateDn ::=
                 INTEGER { rateDn2(2),
                           rateDn4(4),
                           rateDn6(6),
                           rateDn8(8),
                           rateDn12(12),
                           rateDn16(16),
                           rateDn24(24),
                           rateDn32(32),
                           rateDn48(48),
                           rateDn64(64) }

             -- Indicates the upstream data rate.
             --
             Xldv20VdcRateUp ::=
                 INTEGER { rateUp1(1),
                           rateUp2(2),
                           rateUp4(4),
                           rateUp8(8),
                           rateUp12(12),
                           rateUp16(16) }

             -- Indicates the latency period in downstream direction.
             --
             Xldv20VdcLatencyDn ::=
                 INTEGER { latencyDn0(0),
                           latencyDn2(2),
                           latencyDn4(4),
                           latencyDn8(8),
                           latencyDn12(12),
                           latencyDn16(16),
                           latencyDn20(20),
                           latencyDn32(32) }

             -- Indicates the latency period in upstream direction.
             --
             Xldv20VdcLatencyUp ::=
                 INTEGER { latencyUp0(0),
                           latencyUp2(2),
                           latencyUp4(4),
                           latencyUp8(8),
                           latencyUp10(10),
                           latencyUp20(20) }

             -- Indicates the configured power boost mode/power adaptation option.
             --
             Xldv20VdcPowerBoostAdaptationType ::=
                 INTEGER { suEnabled(1),
                           ntEnabled(2),
                           bothEnabled(3),
                           bothDisabled(4) }

             -- Indicates the configured VDSL mode option.
             --
             Xldv20VdcVdslMode ::=
                 INTEGER { adslFriendly(1),
                           vdslEfficient(2) }

             -- Indicates the configured PSD mask option.
             --
             Xldv20VdcPsdMask ::=
                 INTEGER { m1(1),
                           m2(2) }

             -- This type represents the Ethernet NT modes
             --
             Xldv20EthNtMode ::=
                 INTEGER { bridging    (1),
                           routing     (2),
                           currentConfiguration (4)} 
            
             -- This type represents the received payload types
             -- of e3n interface
             --
             Xldv20E3nPayloadType ::=
                 INTEGER { unequipped  (1),
                           nonSpecific (2),
                           atm         (3)}

             -- This type represents the alarm state for COH objects
             --
             Xldv20CallpAlarmState ::=
                 INTEGER {  noAlarm      (1),
                            alarmPresent (2) }

             -- This type represents the alarm state for COH termination point objects
             --
             Xldv20TpAlarmState ::=
                 INTEGER {  noAlarm              (1),
                            upstreamAlarm        (2),
                            downstreamAlarm      (3),
                            upAndDownstreamAlarm (4) }

             -- This type represents the latency for ADSL modems
             --
             Xldv20Latency ::=
                 INTEGER {  interleavedLow        (0),
                            interleavedHigh       (1),
			    fast                 (256) }
             
             -- This type represents test type for OAM functions
             --
             Xldv20TestType ::=
                 INTEGER {  segment                  (1),
                            endToEnd                 (2) }

             -- A type which selects the flow direction of 
             -- OAM cells during ATM loop test
             --
             --TCON: Xldv20FlowDirection ::= TEXTUAL-CONVENTION
             --TCON:      STATUS current
             --TCON:      DESCRIPTION
             --TCON:        "This data type is used as the syntax for
             --TCON:         the flow direction attributes. "
             --TCON:      SYNTAX INTEGER {
             --TCON:        undefined (1),
             --TCON:        inwards (2),
             --TCON:        outwards (3)
             --TCON:      }

             Xldv20FlowDirection ::=
                  INTEGER { undefined         (1),
                            inwards           (2),
                            outwards          (3) }

             -- A type which selects the OAM level       
             -- for OAM functions
             --
             Xldv20OamLevel ::=
                  INTEGER { undefined         (0),
                            f1                (1),
                            f2                (2),
                            f3                (3),
                            f4                (4),
                            f5                (5)  }

             -- This type represents the traps and their IDs
             --
             Xldv20TrapIds ::=
                 INTEGER { trNoTrapId                ( 0 ),  
                           trHpExcBER                ( 1 ),
                           trHpUNEQ                  ( 2 ),
                           trLcd                     ( 3 ),
                           trLof                     ( 4 ),
                           trLop                     ( 5 ),
                           trLos                     ( 6 ),
                           trMsAIS                   ( 7 ),
                           trMsExcBER                ( 8 ),
                           trMsRDI                   ( 9 ),
                           trMsSD                    ( 10 ),
                           trPAIS                    ( 11 ),
                           trPRDI                    ( 12 ),
                           trRsExcBER                ( 13 ),
                           trSlm                     ( 14 ),
                           trTim                     ( 15 ),
                           trActFault                ( 16 ),
                           trReplaceableUnitTypeMismatch ( 17 ),
                           trReplaceableUnitFailure      ( 18 ),
                           trReplaceableUnitProblem      ( 19 ),
                           trReplaceableUnitNotInstalled ( 20 ),
                           trReplaceableUnitSwMismatch   ( 21 ),
                           trReplaceableUnitReset        ( 22 ),
                           trReplaceableUnitResetEnd     ( 23 ),
                           trStartupEnd           ( 24 ),
                           trLctSession           ( 25 ),
                           trAgentRunning         ( 26 ),
                           trRstResult            ( 27 ),
                           trPltTestResult        ( 28 ),
                           trStateChangeAdmin     ( 29 ),

                           trStateChangeOper      ( 30 ),
                           trChangeRate           ( 31 ),
                           trCmuReadyForReset     ( 32 ),
                           trAltTestResult        ( 33 ),
                           trActivateLoadResult   ( 34 ),
                           trPUUpgradeSucc        ( 35 ),
                           trUpgradeCancelled     ( 36 ),

                           trFtpError             ( 38 ),

                           trSweLogRead           ( 40 ),
                           trHwmLogRead           ( 41 ),
                           trTraceLogRead         ( 42 ),

                           trActCcReload          ( 44 ),
                           trVplCcCreation        ( 45 ),
                           trVplCcDeletion        ( 46 ),

                           trObjCreate                  ( 100 ),
                           trObjDelete                  ( 101 ),
                           trXmissionErr                ( 105 ),
                           trExternalAlarm              ( 110 ),
                           trUnitReadyForReset          ( 111 ),
                           trHwuControl                 ( 112 ),
                           trReplaceableUnitRemoved     ( 113 ),
                           trAIS                        ( 114 ),
                           trRDI                        ( 115 ),
                           trPlcpLof                    ( 116 ),
                           trPlcpRDI                    ( 117 ),
                           trRemInvReady                ( 118 ),
                           trDbBackup                   ( 119 ),
                           trSwVersionSet               ( 120 ),
                           trReadSAPSContentFileReady   ( 121 ),
                           trReplaceableUnitSwMissing   ( 122 ),
                           trInternalFault              ( 123 ),
                           trAttributeValueChange       ( 124 ),

                           trVclCcCreation              ( 127 ),
                           trVclCcDeletion              ( 128 ),

                           trImmMNR                     ( 130 ),
                           trLpr                        ( 131 ),
                           trLol                        ( 132 ),
                           trAtmLayerMultiAlarm         ( 135 ),
                           trTelnetSession              ( 136 ),

                           trVplCACProblem              ( 137 ),

                           trVclCACProblem              ( 139 ),
                           trVplTpReload                ( 140 ),
                           trWrongServiceConfigData     ( 141 ),
                           trReplaceableUnitPlugged     ( 142 ),
                           trReplaceableUnitUnplugged   ( 143 ),
                           trStateChangeOperExt         ( 144 ),
                           trLOC                        ( 145 ),

                           trDbRestore                   ( 150 ), 
                           trUpgradeEndRequestResult     ( 151 ), 
                           trUnitUpgradeNotRequested     ( 152 ), 


                           -- trap ID's for Performance Management
                           trThresholdCrossingAlert     ( 200 ),

                           -- trap ID's for Version 2.0
                           trVpcTpCreation                 ( 400 ),
                           trVpcTpDeletion                 ( 401 ),
                           trVpcTpCACProblem               ( 402 ),
                           trContinuityCheckVpEntryCreated ( 403 ),
                           trContinuityCheckVpEntryDeleted ( 404 ),
                           trContinuityCheckVcEntryCreated ( 405 ),
                           trContinuityCheckVcEntryDeleted ( 406 ),
                           
                           -- trap ID's for LUIMA
                           -- E1/Ds1 near-end
                           trExcBER                        ( 407 ),
                           trLif                           ( 408 ),
                           trLods                          ( 409 ),
                           
                           -- E1/Ds1 far-end
                           trTxUnusableFe                  ( 410 ),
                           trRxUnusableFe                  ( 411 ),
                           trRfiIma                        ( 412 ),
                           trRAI                           ( 413 ),

                           -- IMA group 
                           trStartUpFe                     ( 450 ),
                           trConfigAbort                   ( 451 ),
                           trConfigAbortFe                 ( 452 ),
                           trInsufficientLinks             ( 453 ),
                           trInsufficientLinksFe           ( 454 ),
                           trBlockedFe                     ( 455 ),
                           trImaMinNumOfLinks              ( 456 ),

                           -- HWM
                           trStateChangeAvail              ( 457),

                           -- LAST TABLE ENTRY FOR RANGE CHECK
                           -- CORRECT THIS AND 
			   -- ADD NEW VALUES ABOVE THIS LINE
                           trMaxTrapId                     ( 458 )
                           }

             -- Specifies the requesting unit of a SW upgrade task
             --
             Xldv20Requester ::=
                 INTEGER {
                     tmn (1),
                     hwm (2)
                          }

             -- Specifies the time zones
             -- GMT : Greenwich Mean Time
	     -- gmt-12 means DMT minus 12 hours
	     -- gmt1 means GMT plus 1 hour
	     --
             Xldv20TimeZone ::=
                 INTEGER {
                     gmt-12Eniwetok                           ( 1),
                     gmt-11MidwayIslandsSamoa                 ( 2),
		     gmt-10Hawaii                             ( 3),
                     gmt-9Alaska                              ( 4),
                     gmt-8TijuanaLosAngelesSeattleVancouver   ( 5),
                     gmt-7ArizonaDenverSaltLakeCityCalgary    ( 6),
                     gmt-6ChicagoDallasKansasCityWinnipeg     ( 7),
                     gmt-6MexicoCityTegucigalpaSaskatchewan   ( 8),
                     gmt-5BogotaLimaQuito                     ( 9),
                     gmt-5IndianaEast                         (10),
                     gmt-5NewYorkMiamiAtlantaDetroitToronto   (11),
                     gmt-4CaracasLaPazMontrealQuebec          (12),
                     gmt-330Neufundland                       (13),
                     gmt-3BrasiliaBuenosAiresGeorgetown       (14),
                     gmt-2MiddleAtlantic                      (15),
                     gmt-1AzorenKaverdIslands                 (16),
                     gmtCasablancaDublinLissabonLondon        (17),
                     gmt1AmsterdamMadridParisBelgradZagreb   (18),
                     gmt1BerlinBernRomeStockholmVienna       (19),
                     gmt1BudapestPrahaBratislavaWarschau     (20),
                     gmt2AthensIstanbulMinskBukarest         (21),
                     gmt2HararePretoriaHelsinkiRevalRiga     (22),
                     gmt2IsraelKairo                         (23),
                     gmt3BagdadKuwaitErRiad                  (24),
                     gmt3MoskowStPetersburgWolgograd         (25),
                     gmt3Nairobi                             (26),
                     gmt330Teheran                           (27),
                     gmt4AbuDhabiMuskatBakuTiflis            (28),
                     gmt430Kabul                             (29),
                     gmt5IslamabadKarartschiTaschkent        (30),
                     gmt5Jekaterinburg                       (31),
                     gmt530BombayKaluttaMadrasNewDehli       (32),
                     gmt6AkmolaAlmaAtaDhakaColombo           (33),
                     gmt7BangkokHanoiJakarta                 (34),
                     gmt8PekingChongqingHongkongUrumchi      (35),
                     gmt8PerthSingapurTaipeh                 (36),
                     gmt9IrkutskOsakaSapporoTokyoSeoul       (37),
                     gmt930AdelaideDarwin                    (38),
                     gmt10BrisbaneCanberraMlebourneSydney    (39),
                     gmt10GuamPortMoresbyHobart              (40),
                     gmt10Wladiwostok                        (41),
                     gmt11MagadanSalomonenNewCaledonia       (42),
                     gmt12AucklandWellington                 (43),
                     gmt12FidschiKamtschatkaMarschallIslands (44)        
                          }

             -- This type specifies the day light saving time
             --
             Xldv20DayLightSavingTime ::=
                 INTEGER {
                     summerTime1 ( 1),
                     summerTime2 ( 2),
                     winterTime  (10)
                 }

             -- The type of ADSL margins                             
             --
             Xldv20AdslMargin ::=
                 INTEGER {
                    dB-127    (-127),
                    dB-126    (-126),
                    dB-125    (-125),
                    dB-124    (-124),
                    dB-123    (-123),
                    dB-122    (-122),
                    dB-121    (-121),
                    dB-120    (-120),
                    dB-119    (-119),
                    dB-118    (-118),
                    dB-117    (-117),
                    dB-116    (-116),
                    dB-115    (-115),
                    dB-114    (-114),
                    dB-113    (-113),
                    dB-112    (-112),
                    dB-111    (-111),
                    dB-110    (-110),
                    dB-109    (-109),
                    dB-108    (-108),
                    dB-107    (-107),
                    dB-106    (-106),
                    dB-105    (-105),
                    dB-104    (-104),
                    dB-103    (-103),
                    dB-102    (-102),
                    dB-101    (-101),
                    dB-100    (-100),
                    dB-99     (-99),
                    dB-98     (-98),
                    dB-97     (-97),
                    dB-96     (-96),
                    dB-95     (-95),
                    dB-94     (-94),
                    dB-93     (-93),
                    dB-92     (-92),
                    dB-91     (-91),
                    dB-90     (-90),
                    dB-89     (-89),
                    dB-88     (-88),
                    dB-87     (-87),
                    dB-86     (-86),
                    dB-85     (-85),
                    dB-84     (-84),
                    dB-83     (-83),
                    dB-82     (-82),
                    dB-81     (-81),
                    dB-80     (-80),
                    dB-79     (-79),
                    dB-78     (-78),
                    dB-77     (-77),
                    dB-76     (-76),
                    dB-75     (-75),
                    dB-74     (-74),
                    dB-73     (-73),
                    dB-72     (-72),
                    dB-71     (-71),
                    dB-70     (-70),
                    dB-69     (-69),
                    dB-68     (-68),
                    dB-67     (-67),
                    dB-66     (-66),
                    dB-65     (-65),
                    dB-64     (-64),
                    dB-63     (-63),
                    dB-62     (-62),
                    dB-61     (-61),
                    dB-60     (-60),
                    dB-59     (-59),
                    dB-58     (-58),
                    dB-57     (-57),
                    dB-56     (-56),
                    dB-55     (-55),
                    dB-54     (-54),
                    dB-53     (-53),
                    dB-52     (-52),
                    dB-51     (-51),
                    dB-50     (-50),
                    dB-49     (-49),
                    dB-48     (-48),
                    dB-47     (-47),
                    dB-46     (-46),
                    dB-45     (-45),
                    dB-44     (-44),
                    dB-43     (-43),
                    dB-42     (-42),
                    dB-41     (-41),
                    dB-40     (-40),
                    dB-39     (-39),
                    dB-38     (-38),
                    dB-37     (-37),
                    dB-36     (-36),
                    dB-35     (-35),
                    dB-34     (-34),
                    dB-33     (-33),
                    dB-32     (-32),
                    dB-31     (-31),
                    dB-30     (-30),
                    dB-29     (-29),
                    dB-28     (-28),
                    dB-27     (-27),
                    dB-26     (-26),
                    dB-25     (-25),
                    dB-24     (-24),
                    dB-23     (-23),
                    dB-22     (-22),
                    dB-21     (-21),
                    dB-20     (-20),
                    dB-19     (-19),
                    dB-18     (-18),
                    dB-17     (-17),
                    dB-16     (-16),
                    dB-15     (-15),
                    dB-14     (-14),
                    dB-13     (-13),
                    dB-12     (-12),
                    dB-11     (-11),
                    dB-10     (-10),
                    dB-9      (-9),
                    dB-8      (-8),
                    dB-7      (-7),
                    dB-6      (-6),
                    dB-5      (-5),
                    dB-4      (-4),
                    dB-3      (-3),
                    dB-2      (-2),
                    dB-1      (-1),
                    dB0       (0 ),
                    dB1      (1 ),
                    dB2      (2 ),
                    dB3      (3 ),
                    dB4      (4 ),
                    dB5      (5 ),
                    dB6      (6 ),
                    dB7      (7 ),
                    dB8      (8 ),
                    dB9      (9 ),
                    dB10     (10),
                    dB11     (11),
                    dB12     (12),
                    dB13     (13),
                    dB14     (14),
                    dB15     (15),
                    dB16     (16),
                    dB17     (17),
                    dB18     (18),
                    dB19     (19),
                    dB20     (20),
                    dB21     (21),
                    dB22     (22),
                    dB23     (23),
                    dB24     (24),
                    dB25     (25),
                    dB26     (26),
                    dB27     (27),
                    dB28     (28),
                    dB29     (29),
                    dB30     (30),
                    dB31     (31),
                    dB32     (32),
                    dB33     (33),
                    dB34     (34),
                    dB35     (35),
                    dB36     (36),
                    dB37     (37),
                    dB38     (38),
                    dB39     (39),
                    dB40     (40),
                    dB41     (41),
                    dB42     (42),
                    dB43     (43),
                    dB44     (44),
                    dB45     (45),
                    dB46     (46),
                    dB47     (47),
                    dB48     (48),
                    dB49     (49),
                    dB50     (50),
                    dB51     (51),
                    dB52     (52),
                    dB53     (53),
                    dB54     (54),
                    dB55     (55),
                    dB56     (56),
                    dB57     (57),
                    dB58     (58),
                    dB59     (59),
                    dB60     (60),
                    dB61     (61),
                    dB62     (62),
                    dB63     (63),
                    dB64     (64),
                    dB65     (65),
                    dB66     (66),
                    dB67     (67),
                    dB68     (68),
                    dB69     (69),
                    dB70     (70),
                    dB71     (71),
                    dB72     (72),
                    dB73     (73),
                    dB74     (74),
                    dB75     (75),
                    dB76     (76),
                    dB77     (77),
                    dB78     (78),
                    dB79     (79),
                    dB80     (80),
                    dB81     (81),
                    dB82     (82),
                    dB83     (83),
                    dB84     (84),
                    dB85     (85),
                    dB86     (86),
                    dB87     (87),
                    dB88     (88),
                    dB89     (89),
                    dB90     (90),
                    dB91     (91),
                    dB92     (92),
                    dB93     (93),
                    dB94     (94),
                    dB95     (95),
                    dB96     (96),
                    dB97     (97),
                    dB98     (98),
                    dB99     (99),
                    dB100    (100),
                    dB101    (101),
                    dB102    (102),
                    dB103    (103),
                    dB104    (104),
                    dB105    (105),
                    dB106    (106),
                    dB107    (107),
                    dB108    (108),
                    dB109    (109),
                    dB110    (110),
                    dB111    (111),
                    dB112    (112),
                    dB113    (113),
                    dB114    (114),
                    dB115    (115),
                    dB116    (116),
                    dB117    (117),
                    dB118    (118),
                    dB119    (119),
                    dB120    (120),
                    dB121    (121),
                    dB122    (122),
                    dB123    (123),
                    dB124    (124),
                    dB125    (125),
                    dB126    (126),
                    dB127    (127),
                    dB128    (128),
	            marginNotApplicable (32766),
                    marginInvalid       (32767)
                  }

          
             -- The type of ADSL attenuation
	     -- in steps of 0.5 decibel
             --
             Xldv20AdslAttenuation ::=
                 INTEGER {
                    dB0             (0 ),
                    dB0Dot5         (1 ),
                    dB1             (2 ),
                    dB1Dot5         (3 ),
                    dB2             (4 ),
                    dB2Dot5         (5 ),
                    dB3             (6 ),
                    dB3Dot5         (7 ),
                    dB4             (8 ),
                    dB4Dot5         (9 ),
                    dB5             (10),
                    dB5Dot5         (11),
                    dB6             (12),
                    dB6Dot5         (13),
                    dB7             (14),
                    dB7Dot5         (15),
                    dB8             (16),
                    dB8Dot5         (17),
                    dB9             (18),
                    dB9Dot5         (19),
                    dB10            (20),
                    dB10Dot5        (21),
                    dB11            (22),
                    dB11Dot5        (23),
                    dB12            (24),
                    dB12Dot5        (25),
                    dB13            (26),
                    dB13Dot5        (27),
                    dB14            (28),
                    dB14Dot5        (29),
                    dB15            (30),
                    dB15Dot5        (31),
                    dB16            (32),
                    dB16Dot5        (33),
                    dB17            (34),
                    dB17Dot5        (35),
                    dB18            (36),
                    dB18Dot5        (37),
                    dB19            (38),
                    dB19Dot5        (39),
                    dB20            (40),
                    dB20Dot5        (41),
                    dB21            (42),
                    dB21Dot5        (43),
                    dB22            (44),
                    dB22Dot5        (45),
                    dB23            (46),
                    dB23Dot5        (47),
                    dB24            (48),
                    dB24Dot5        (49),
                    dB25            (50),
                    dB25Dot5        (51),
                    dB26            (52),
                    dB26Dot5        (53),
                    dB27            (54),
                    dB27Dot5        (55),
                    dB28            (56),
                    dB28Dot5        (57),
                    dB29            (58),
                    dB29Dot5        (59),
                    dB30            (60),
                    dB30Dot5        (61),
                    dB31            (62),
                    dB31Dot5        (63),
                    dB32            (64),
                    dB32Dot5        (65),
                    dB33            (66),
                    dB33Dot5        (67),
                    dB34            (68),
                    dB34Dot5        (69),
                    dB35            (70),
                    dB35Dot5        (71),
                    dB36            (72),
                    dB36Dot5        (73),
                    dB37            (74),
                    dB37Dot5        (75),
                    dB38            (76),
                    dB38Dot5        (77),
                    dB39            (78),
                    dB39Dot5        (79),
                    dB40            (80),
                    dB40Dot5        (81),
                    dB41            (82),
                    dB41Dot5        (83),
                    dB42            (84),
                    dB42Dot5        (85),
                    dB43            (86),
                    dB43Dot5        (87),
                    dB44            (88),
                    dB44Dot5        (89),
                    dB45            (90),
                    dB45Dot5        (91),
                    dB46            (92),
                    dB46Dot5        (93),
                    dB47            (94),
                    dB47Dot5        (95),
                    dB48            (96),
                    dB48Dot5        (97),
                    dB49            (98),
                    dB49Dot5        (99),
                    dB50            (100),
                    dB50Dot5        (101),
                    dB51            (102),
                    dB51Dot5        (103),
                    dB52            (104),
                    dB52Dot5        (105),
                    dB53            (106),
                    dB53Dot5        (107),
                    dB54            (108),
                    dB54Dot5        (109),
                    dB55            (110),
                    dB55Dot5        (111),
                    dB56            (112),
                    dB56Dot5        (113),
                    dB57            (114),
                    dB57Dot5        (115),
                    dB58            (116),
                    dB58Dot5        (117),
                    dB59            (118),
                    dB59Dot5        (119),
                    dB60            (120),
                    dB60Dot5        (121),
                    dB61            (122),
                    dB61Dot5        (123),
                    dB62            (124),
                    dB62Dot5        (125),
                    dB63            (126),
                    dB63Dot5        (127),
                    dB64            (128),
                    dB64Dot5        (129),
                    dB65            (130),
                    dB65Dot5        (131),
                    dB66            (132),
                    dB66Dot5        (133),
                    dB67            (134),
                    dB67Dot5        (135),
                    dB68            (136),
                    dB68Dot5        (137),
                    dB69            (138),
                    dB69Dot5        (139),
                    dB70            (140),
                    dB70Dot5        (141),
                    dB71            (142),
                    dB71Dot5        (143),
                    dB72            (144),
                    dB72Dot5        (145),
                    dB73            (146),
                    dB73Dot5        (147),
                    dB74            (148),
                    dB74Dot5        (149),
                    dB75            (150),
                    dB75Dot5        (151),
                    dB76            (152),
                    dB76Dot5        (153),
                    dB77            (154),
                    dB77Dot5        (155),
                    dB78            (156),
                    dB78Dot5        (157),
                    dB79            (158),
                    dB79Dot5        (159),
                    dB80            (160),
                    dB80Dot5        (161),
                    dB81            (162),
                    dB81Dot5        (163),
                    dB82            (164),
                    dB82Dot5        (165),
                    dB83            (166),
                    dB83Dot5        (167),
                    dB84            (168),
                    dB84Dot5        (169),
                    dB85            (170),
                    dB85Dot5        (171),
                    dB86            (172),
                    dB86Dot5        (173),
                    dB87            (174),
                    dB87Dot5        (175),
                    dB88            (176),
                    dB88Dot5        (177),
                    dB89            (178),
                    dB89Dot5        (179),
                    dB90            (180),
                    dB90Dot5        (181),
                    dB91            (182),
                    dB91Dot5        (183),
                    dB92            (184),
                    dB92Dot5        (185),
                    dB93            (186),
                    dB93Dot5        (187),
                    dB94            (188),
                    dB94Dot5        (189),
                    dB95            (190),
                    dB95Dot5        (191),
                    dB96            (192),
                    dB96Dot5        (193),
                    dB97            (194),
                    dB97Dot5        (195),
                    dB98            (196),
                    dB98Dot5        (197),
                    dB99            (198),
                    dB99Dot5        (199),
                    dB100           (200),
                    dB100Dot5       (201),
                    dB101           (202),
                    dB101Dot5       (203),
                    dB102           (204),
                    dB102Dot5       (205),
                    dB103           (206),
                    dB103Dot5       (207),
                    dB104           (208),
                    dB104Dot5       (209),
                    dB105           (210),
                    dB105Dot5       (211),
                    dB106           (212),
                    dB106Dot5       (213),
                    dB107           (214),
                    dB107Dot5       (215),
                    dB108           (216),
                    dB108Dot5       (217),
                    dB109           (218),
                    dB109Dot5       (219),
                    dB110           (220),
                    dB110Dot5       (221),
                    dB111           (222),
                    dB111Dot5       (223),
                    dB112           (224),
                    dB112Dot5       (225),
                    dB113           (226),
                    dB113Dot5       (227),
                    dB114           (228),
                    dB114Dot5       (229),
                    dB115           (230),
                    dB115Dot5       (231),
                    dB116           (232),
                    dB116Dot5       (233),
                    dB117           (234),
                    dB117Dot5       (235),
                    dB118           (236),
                    dB118Dot5       (237),
                    dB119           (238),
                    dB119Dot5       (239),
                    dB120           (240),
                    dB120Dot5       (241),
                    dB121           (242),
                    dB121Dot5       (243),
                    dB122           (244),
                    dB122Dot5       (245),
                    dB123           (246),
                    dB123Dot5       (247),
                    dB124           (248),
                    dB124Dot5       (249),
                    dB125           (250),
                    dB125Dot5       (251),
                    dB126           (252),
                    dB126Dot5       (253),
                    dB127           (254),
                    dB127Dot5       (255),
	            attenuationNotApplicable (32766),
                    attenuationInvalid       (32767)
                  }

             -- Type for configurable minimum ADSL margin
             --
             Xldv20AdslMinMargin ::=
                 INTEGER {
                    dB-6      (-6),
                    dB-5      (-5),
                    dB-4      (-4),
                    dB-3      (-3),
                    dB-2      (-2),
                    dB-1      (-1),
                    dB0       (0 ),
                    dB1      (1 ),
                    dB2      (2 ),
                    dB3      (3 ),
                    dB4      (4 ),
                    dB5      (5 ),
                    dB6      (6 ),
                    dB7      (7 ),
                    dB8      (8 ),
                    dB9      (9 ),
                    dB10     (10),
                    dB11     (11),
                    dB12     (12),
		    auto     (255)
                  }

             -- Type for ADSL output power
             --
            Xldv20AdslOutputPower ::=
                 INTEGER {
                    dBm-31     (-31),
                    dBm-30     (-30),
                    dBm-29     (-29),
                    dBm-28     (-28),
                    dBm-27     (-27),
                    dBm-26     (-26),
                    dBm-25     (-25),
                    dBm-24     (-24),
                    dBm-23     (-23),
                    dBm-22     (-22),
                    dBm-21     (-21),
                    dBm-20     (-20),
                    dBm-19     (-19),
                    dBm-18     (-18),
                    dBm-17     (-17),
                    dBm-16     (-16),
                    dBm-15     (-15),
                    dBm-14     (-14),
                    dBm-13     (-13),
                    dBm-12     (-12),
                    dBm-11     (-11),
                    dBm-10     (-10),
                    dBm-9      (-9),
                    dBm-8      (-8),
                    dBm-7      (-7),
                    dBm-6      (-6),
                    dBm-5      (-5),
                    dBm-4      (-4),
                    dBm-3      (-3),
                    dBm-2      (-2),
                    dBm-1      (-1),
                    dBm0       (0 ),
                    dBm1       (1 ),
                    dBm2       (2 ),
                    dBm3       (3 ),
                    dBm4       (4 ),
                    dBm5       (5 ),
                    dBm6       (6 ),
                    dBm7       (7 ),
                    dBm8       (8 ),
                    dBm9       (9 ),
                    dBm10      (10),
                    dBm11      (11),
                    dBm12      (12),
                    dBm13      (13),
                    dBm14      (14),
                    dBm15      (15),
                    dBm16      (16),
                    dBm17      (17),
                    dBm18      (18),
                    dBm19      (19),
                    dBm20      (20),
                    dBm21      (21),
                    dBm22      (22),
                    dBm23      (23),
                    dBm24      (24),
                    dBm25      (25),
                    dBm26      (26),
                    dBm27      (27),
                    dBm28      (28),
                    dBm29      (29),
                    dBm30      (30),
                    dBm31      (31),
                    dBm32      (32),
		    outputPowerInvalid (32767)
                  }

             -- --------------------------------------------------------------
             --                       Trap Var values
             -- --------------------------------------------------------------

             -- Describes the result of a startup.
             --
             Xldv20StartupResult ::=
                 INTEGER {
                     suFinished(1),
                     suFailed(2),
                     suStandaloneStartupFinished(3),
                     suInProgress(4)
                 }

             -- Indicates the startup type.
             -- Do not change enumeration !!!
	     --
             Xldv20StartupType ::=
                 INTEGER {
                     warm         (6300),
                     cold         (6301),
                     reload       (6302),
                     cmuUpgrade   (6303),
                     powerUp      (6304)
                 }

             -- Indicates a session with a connected LCT.
             --
             Xldv20SnmLctSession ::=
                 INTEGER {
                     connected(1),
                     disconnected(2),
                     sessionCancelled(3),
                     sessionTimeout(4),
                     onuCutSession(5)
                 }

             -- Indicates the source of a reporting entity.
             --
             Xldv20RepSource ::=
                 INTEGER {
                     hwm(1),
                     tlm(2),
                     vplNni(3),
                     vplUni(4),
                     extAlarm(5),
                     vccTp(6),
                     vpcTp(7),
                     vclTp(9),
                     vplTp(10),
                     vclNni(11),
                     vclUni(12),
		     vplCC(13),
		     vclCC(14)
                 }

             -- Type of polling flags
             --
             Xldv20PollingFlagType ::=
                 INTEGER {
                     flagSet(1),
                     flagNotSet(2)
                 }

             -- Type of Terminal
             --
             Xldv20TerminalType ::=
                 INTEGER {
                     tmn(1),
                     lct(2),
                     unknown(10)
                 }

             -- Type of communication channel
             --
             Xldv20ChannelType ::=
                 INTEGER {
                     inband(1),
                     outband(2),
                     unknown(10)
                 }

             -- the configurable service modes of ADSL modem according to ITU norm
             -- gDotHsMode (handshake mode) for automatic link up either 
             -- to ADSL equipment or to UDSL equipment
             -- or ansiT1Dot413 for ADSL equipment
             -- or gDotLiteMode for UDSL equipment
	     -- or gDotAll for automatic configuration (depending on HW)
             --
             Xldv20XdslServiceType ::=
                 INTEGER {
                     gDotHsMode   (1), -- handshake mode, ITU G.994.1
                     ansiT1Dot413 (2), -- full rate mode, ADSL,  ITU G.992.1
                     gDotLiteMode (3), -- UDSL ITU G.992.2
                     gDotAll      (4)  -- allows any service type
                 }

             -- the current service mode of ADSL modem according to ITU norm
             --
             Xldv20XdslServiceTypeCurrent ::=
                 INTEGER {
                     gDotDmtMode  (1),
                     ansiT1Dot413 (2),
                     gDotLiteMode (3),
	             serviceTypeUnknown (10)
                 }

             -- loop modes of ATM loopback point
             --
             Xldv20LoopMode ::=
                 INTEGER {
                     forward(1),
                     loopAndForward(2) 
                 }

             -- The initialization status field type
             -- of an XDSL line
             --
             Xldv20XdslInitStatus ::=
                 INTEGER {
                     ntNotPresent                      (1)  
                    ,communicationFailed               (2)
                    ,fastRetrainProfileError           (3)
                    ,rateParameterConfigurationError   (4)
                    ,serviceTypeAdrRequestRejected     (5)
                    ,serviceTypeAdcRequestRejected     (6)
                    ,configuredRatesOutOfRange         (7)      -- not in g.992.2 range
                    ,configuredMinMaxRelationInvalid   (8)
                    ,channelRatesExceedsSystemLimits   (9)
                    ,adaptationCombinationInvalid      (10)
                    ,configuredDualChannelInvalid      (11)
                    ,marginLessThanMinMargin           (12)
                    ,adrNotCapableOfDualLatency        (13)
                    ,reserved1                         (14)
                    ,reserved2                         (15)
		    ,trainingBlockedBySu               (16)
		    ,trainingBlockedByCi               (17)
		    ,ntNotPresentDetectedOnCi          (18)
	            ,gliteModeNotPossibleInPCM         (19)
	            ,alarmsDetected                    (20)
	            ,initStatusUnknown                 (21)
                    ,noInitError                       (255)    -- default value
                 }

             -- The initialization status field type
             -- of an XDSL line
             --
             Xldv20AdcTrainingMode ::=
                 INTEGER {
                     enableParallelTraining(1),
                     avoidParallelTrainingOnCI(2),
                     avoidParallelTrainingOnSU(3),
                     combinedTraining(4)
                 }

	     -- The SDSL service type
	     --
             Xldv20SdslServiceType ::=
                 INTEGER {
		    diamondLaneFraming  ( 1 ),
		    clearChannelFraming ( 2 ),
		    ituFraming          ( 3 )
                 }

	     -- Type for ADSLLL nd downstream data rates .
	     -- The enumeration shows the mapping
	     -- Bitrates in kbits/sec (kbps) and 
	     -- ATM Cellrate in cells/sec (cps).
	     -- k means 1000. 
	     -- The bit rate of an ATM cell is 424=53*8 bits/sec.
	     --
	     Xldv20AdslDataRateDown ::=
               INTEGER {
                 kbps32Cps75       (   1 ),
                 kbps64Cps150      (   2 ),
                 kbps96Cps226      (   3 ),
                 kbps128Cps301     (   4 ),
                 kbps160Cps377     (   5 ),
                 kbps192Cps452     (   6 ),
                 kbps224Cps528     (   7 ),
                 kbps256Cps603     (   8 ),
                 kbps288Cps679     (   9 ),
                 kbps320Cps754     (  10 ),
                 kbps352Cps830     (  11 ),
                 kbps384Cps905     (  12 ),
                 kbps416Cps981     (  13 ),
                 kbps448Cps1056    (  14 ),
                 kbps480Cps1132    (  15 ),
                 kbps512Cps1207    (  16 ),
                 kbps544Cps1283    (  17 ),
                 kbps576Cps1358    (  18 ),
                 kbps608Cps1433    (  19 ),
                 kbps640Cps1509    (  20 ),
                 kbps672Cps1584    (  21 ),
                 kbps704Cps1660    (  22 ),
                 kbps736Cps1735    (  23 ),
                 kbps768Cps1811    (  24 ),
                 kbps800Cps1886    (  25 ),
                 kbps832Cps1962    (  26 ),
                 kbps864Cps2037    (  27 ),
                 kbps896Cps2113    (  28 ),
                 kbps928Cps2188    (  29 ),
                 kbps960Cps2264    (  30 ),
                 kbps992Cps2339    (  31 ),
                 kbps1024Cps2415   (  32 ),
                 kbps1056Cps2490   (  33 ),
                 kbps1088Cps2566   (  34 ),
                 kbps1120Cps2641   (  35 ),
                 kbps1152Cps2716   (  36 ),
                 kbps1184Cps2792   (  37 ),
                 kbps1216Cps2867   (  38 ),
                 kbps1248Cps2943   (  39 ),
                 kbps1280Cps3018   (  40 ),
                 kbps1312Cps3094   (  41 ),
                 kbps1344Cps3169   (  42 ),
                 kbps1376Cps3245   (  43 ),
                 kbps1408Cps3320   (  44 ),
                 kbps1440Cps3396   (  45 ),
                 kbps1472Cps3471   (  46 ),
                 kbps1504Cps3547   (  47 ),
                 kbps1536Cps3622   (  48 ),
                 kbps1568Cps3698   (  49 ),
                 kbps1600Cps3773   (  50 ),
                 kbps1632Cps3849   (  51 ),
                 kbps1664Cps3924   (  52 ),
                 kbps1696Cps4000   (  53 ),
                 kbps1728Cps4075   (  54 ),
                 kbps1760Cps4150   (  55 ),
                 kbps1792Cps4226   (  56 ),
                 kbps1824Cps4301   (  57 ),
                 kbps1856Cps4377   (  58 ),
                 kbps1888Cps4452   (  59 ),
                 kbps1920Cps4528   (  60 ),
                 kbps1952Cps4603   (  61 ),
                 kbps1984Cps4679   (  62 ),
                 kbps2016Cps4754   (  63 ),
                 kbps2048Cps4830   (  64 ),
                 kbps2080Cps4905   (  65 ),
                 kbps2112Cps4981   (  66 ),
                 kbps2144Cps5056   (  67 ),
                 kbps2176Cps5132   (  68 ),
                 kbps2208Cps5207   (  69 ),
                 kbps2240Cps5283   (  70 ),
                 kbps2272Cps5358   (  71 ),
                 kbps2304Cps5433   (  72 ),
                 kbps2336Cps5509   (  73 ),
                 kbps2368Cps5584   (  74 ),
                 kbps2400Cps5660   (  75 ),
                 kbps2432Cps5735   (  76 ),
                 kbps2464Cps5811   (  77 ),
                 kbps2496Cps5886   (  78 ),
                 kbps2528Cps5962   (  79 ),
                 kbps2560Cps6037   (  80 ),
                 kbps2592Cps6113   (  81 ),
                 kbps2624Cps6188   (  82 ),
                 kbps2656Cps6264   (  83 ),
                 kbps2688Cps6339   (  84 ),
                 kbps2720Cps6415   (  85 ),
                 kbps2752Cps6490   (  86 ),
                 kbps2784Cps6566   (  87 ),
                 kbps2816Cps6641   (  88 ),
                 kbps2848Cps6716   (  89 ),
                 kbps2880Cps6792   (  90 ),
                 kbps2912Cps6867   (  91 ),
                 kbps2944Cps6943   (  92 ),
                 kbps2976Cps7018   (  93 ),
                 kbps3008Cps7094   (  94 ),
                 kbps3040Cps7169   (  95 ),
                 kbps3072Cps7245   (  96 ),
                 kbps3104Cps7320   (  97 ),
                 kbps3136Cps7396   (  98 ),
                 kbps3168Cps7471   (  99 ),
                 kbps3200Cps7547   ( 100 ),
                 kbps3232Cps7622   ( 101 ),
                 kbps3264Cps7698   ( 102 ),
                 kbps3296Cps7773   ( 103 ),
                 kbps3328Cps7849   ( 104 ),
                 kbps3360Cps7924   ( 105 ),
                 kbps3392Cps8000   ( 106 ),
                 kbps3424Cps8075   ( 107 ),
                 kbps3456Cps8150   ( 108 ),
                 kbps3488Cps8226   ( 109 ),
                 kbps3520Cps8301   ( 110 ),
                 kbps3552Cps8377   ( 111 ),
                 kbps3584Cps8452   ( 112 ),
                 kbps3616Cps8528   ( 113 ),
                 kbps3648Cps8603   ( 114 ),
                 kbps3680Cps8679   ( 115 ),
                 kbps3712Cps8754   ( 116 ),
                 kbps3744Cps8830   ( 117 ),
                 kbps3776Cps8905   ( 118 ),
                 kbps3808Cps8981   ( 119 ),
                 kbps3840Cps9056   ( 120 ),
                 kbps3872Cps9132   ( 121 ),
                 kbps3904Cps9207   ( 122 ),
                 kbps3936Cps9283   ( 123 ),
                 kbps3968Cps9358   ( 124 ),
                 kbps4000Cps9433   ( 125 ),
                 kbps4032Cps9509   ( 126 ),
                 kbps4064Cps9584   ( 127 ),
                 kbps4096Cps9660   ( 128 ),
                 kbps4128Cps9735   ( 129 ),
                 kbps4160Cps9811   ( 130 ),
                 kbps4192Cps9886   ( 131 ),
                 kbps4224Cps9962   ( 132 ),
                 kbps4256Cps10037  ( 133 ),
                 kbps4288Cps10113  ( 134 ),
                 kbps4320Cps10188  ( 135 ),
                 kbps4352Cps10264  ( 136 ),
                 kbps4384Cps10339  ( 137 ),
                 kbps4416Cps10415  ( 138 ),
                 kbps4448Cps10490  ( 139 ),
                 kbps4480Cps10566  ( 140 ),
                 kbps4512Cps10641  ( 141 ),
                 kbps4544Cps10716  ( 142 ),
                 kbps4576Cps10792  ( 143 ),
                 kbps4608Cps10867  ( 144 ),
                 kbps4640Cps10943  ( 145 ),
                 kbps4672Cps11018  ( 146 ),
                 kbps4704Cps11094  ( 147 ),
                 kbps4736Cps11169  ( 148 ),
                 kbps4768Cps11245  ( 149 ),
                 kbps4800Cps11320  ( 150 ),
                 kbps4832Cps11396  ( 151 ),
                 kbps4864Cps11471  ( 152 ),
                 kbps4896Cps11547  ( 153 ),
                 kbps4928Cps11622  ( 154 ),
                 kbps4960Cps11698  ( 155 ),
                 kbps4992Cps11773  ( 156 ),
                 kbps5024Cps11849  ( 157 ),
                 kbps5056Cps11924  ( 158 ),
                 kbps5088Cps12000  ( 159 ),
                 kbps5120Cps12075  ( 160 ),
                 kbps5152Cps12150  ( 161 ),
                 kbps5184Cps12226  ( 162 ),
                 kbps5216Cps12301  ( 163 ),
                 kbps5248Cps12377  ( 164 ),
                 kbps5280Cps12452  ( 165 ),
                 kbps5312Cps12528  ( 166 ),
                 kbps5344Cps12603  ( 167 ),
                 kbps5376Cps12679  ( 168 ),
                 kbps5408Cps12754  ( 169 ),
                 kbps5440Cps12830  ( 170 ),
                 kbps5472Cps12905  ( 171 ),
                 kbps5504Cps12981  ( 172 ),
                 kbps5536Cps13056  ( 173 ),
                 kbps5568Cps13132  ( 174 ),
                 kbps5600Cps13207  ( 175 ),
                 kbps5632Cps13283  ( 176 ),
                 kbps5664Cps13358  ( 177 ),
                 kbps5696Cps13433  ( 178 ),
                 kbps5728Cps13509  ( 179 ),
                 kbps5760Cps13584  ( 180 ),
                 kbps5792Cps13660  ( 181 ),
                 kbps5824Cps13735  ( 182 ),
                 kbps5856Cps13811  ( 183 ),
                 kbps5888Cps13886  ( 184 ),
                 kbps5920Cps13962  ( 185 ),
                 kbps5952Cps14037  ( 186 ),
                 kbps5984Cps14113  ( 187 ),
                 kbps6016Cps14188  ( 188 ),
                 kbps6048Cps14264  ( 189 ),
                 kbps6080Cps14339  ( 190 ),
                 kbps6112Cps14415  ( 191 ),
                 kbps6144Cps14490  ( 192 ),
                 kbps6176Cps14566  ( 193 ),
                 kbps6208Cps14641  ( 194 ),
                 kbps6240Cps14716  ( 195 ),
                 kbps6272Cps14792  ( 196 ),
                 kbps6304Cps14867  ( 197 ),
                 kbps6336Cps14943  ( 198 ),
                 kbps6368Cps15018  ( 199 ),
                 kbps6400Cps15094  ( 200 ),
                 kbps6432Cps15169  ( 201 ),
                 kbps6464Cps15245  ( 202 ),
                 kbps6496Cps15320  ( 203 ),
                 kbps6528Cps15396  ( 204 ),
                 kbps6560Cps15471  ( 205 ),
                 kbps6592Cps15547  ( 206 ),
                 kbps6624Cps15622  ( 207 ),
                 kbps6656Cps15698  ( 208 ),
                 kbps6688Cps15773  ( 209 ),
                 kbps6720Cps15849  ( 210 ),
                 kbps6752Cps15924  ( 211 ),
                 kbps6784Cps16000  ( 212 ),
                 kbps6816Cps16075  ( 213 ),
                 kbps6848Cps16150  ( 214 ),
                 kbps6880Cps16226  ( 215 ),
                 kbps6912Cps16301  ( 216 ),
                 kbps6944Cps16377  ( 217 ),
                 kbps6976Cps16452  ( 218 ),
                 kbps7008Cps16528  ( 219 ),
                 kbps7040Cps16603  ( 220 ),
                 kbps7072Cps16679  ( 221 ),
                 kbps7104Cps16754  ( 222 ),
                 kbps7136Cps16830  ( 223 ),
                 kbps7168Cps16905  ( 224 ),
                 kbps7200Cps16981  ( 225 ),
                 kbps7232Cps17056  ( 226 ),
                 kbps7264Cps17132  ( 227 ),
                 kbps7296Cps17207  ( 228 ),
                 kbps7328Cps17283  ( 229 ),
                 kbps7360Cps17358  ( 230 ),
                 kbps7392Cps17433  ( 231 ),
                 kbps7424Cps17509  ( 232 ),
                 kbps7456Cps17584  ( 233 ),
                 kbps7488Cps17660  ( 234 ),
                 kbps7520Cps17735  ( 235 ),
                 kbps7552Cps17811  ( 236 ),
                 kbps7584Cps17886  ( 237 ),
                 kbps7616Cps17962  ( 238 ),
                 kbps7648Cps18037  ( 239 ),
                 kbps7680Cps18113  ( 240 ),
                 kbps7712Cps18188  ( 241 ),
                 kbps7744Cps18264  ( 242 ),
                 kbps7776Cps18339  ( 243 ),
                 kbps7808Cps18415  ( 244 ),
                 kbps7840Cps18490  ( 245 ),
                 kbps7872Cps18566  ( 246 ),
                 kbps7904Cps18641  ( 247 ),
                 kbps7936Cps18716  ( 248 ),
                 kbps7968Cps18792  ( 249 ),
                 kbps8000Cps18867  ( 250 ),
                 kbps8032Cps18943  ( 251 ),
                 kbps8064Cps19018  ( 252 ),
                 kbps8096Cps19094  ( 253 )
                 }

	     
	     Xldv20AdslDataRateUp ::=
               INTEGER {
                 kbps32Cps75       (   1 ),
                 kbps64Cps150      (   2 ),
                 kbps96Cps226      (   3 ),
                 kbps128Cps301     (   4 ),
                 kbps160Cps377     (   5 ),
                 kbps192Cps452     (   6 ),
                 kbps224Cps528     (   7 ),
                 kbps256Cps603     (   8 ),
                 kbps288Cps679     (   9 ),
                 kbps320Cps754     (  10 ),
                 kbps352Cps830     (  11 ),
                 kbps384Cps905     (  12 ),
                 kbps416Cps981     (  13 ),
                 kbps448Cps1056    (  14 ),
                 kbps480Cps1132    (  15 ),
                 kbps512Cps1207    (  16 ),
                 kbps544Cps1283    (  17 ),
                 kbps576Cps1358    (  18 ),
                 kbps608Cps1433    (  19 ),
                 kbps640Cps1509    (  20 ),
                 kbps672Cps1584    (  21 ),
                 kbps704Cps1660    (  22 ),
                 kbps736Cps1735    (  23 ),
                 kbps768Cps1811    (  24 )
                 }

	     Xldv20AdslDataRateDownCurrent ::=
               INTEGER {
                 kbps32Cps75       (   1 ),
                 kbps64Cps150      (   2 ),
                 kbps96Cps226      (   3 ),
                 kbps128Cps301     (   4 ),
                 kbps160Cps377     (   5 ),
                 kbps192Cps452     (   6 ),
                 kbps224Cps528     (   7 ),
                 kbps256Cps603     (   8 ),
                 kbps288Cps679     (   9 ),
                 kbps320Cps754     (  10 ),
                 kbps352Cps830     (  11 ),
                 kbps384Cps905     (  12 ),
                 kbps416Cps981     (  13 ),
                 kbps448Cps1056    (  14 ),
                 kbps480Cps1132    (  15 ),
                 kbps512Cps1207    (  16 ),
                 kbps544Cps1283    (  17 ),
                 kbps576Cps1358    (  18 ),
                 kbps608Cps1433    (  19 ),
                 kbps640Cps1509    (  20 ),
                 kbps672Cps1584    (  21 ),
                 kbps704Cps1660    (  22 ),
                 kbps736Cps1735    (  23 ),
                 kbps768Cps1811    (  24 ),
                 kbps800Cps1886    (  25 ),
                 kbps832Cps1962    (  26 ),
                 kbps864Cps2037    (  27 ),
                 kbps896Cps2113    (  28 ),
                 kbps928Cps2188    (  29 ),
                 kbps960Cps2264    (  30 ),
                 kbps992Cps2339    (  31 ),
                 kbps1024Cps2415   (  32 ),
                 kbps1056Cps2490   (  33 ),
                 kbps1088Cps2566   (  34 ),
                 kbps1120Cps2641   (  35 ),
                 kbps1152Cps2716   (  36 ),
                 kbps1184Cps2792   (  37 ),
                 kbps1216Cps2867   (  38 ),
                 kbps1248Cps2943   (  39 ),
                 kbps1280Cps3018   (  40 ),
                 kbps1312Cps3094   (  41 ),
                 kbps1344Cps3169   (  42 ),
                 kbps1376Cps3245   (  43 ),
                 kbps1408Cps3320   (  44 ),
                 kbps1440Cps3396   (  45 ),
                 kbps1472Cps3471   (  46 ),
                 kbps1504Cps3547   (  47 ),
                 kbps1536Cps3622   (  48 ),
                 kbps1568Cps3698   (  49 ),
                 kbps1600Cps3773   (  50 ),
                 kbps1632Cps3849   (  51 ),
                 kbps1664Cps3924   (  52 ),
                 kbps1696Cps4000   (  53 ),
                 kbps1728Cps4075   (  54 ),
                 kbps1760Cps4150   (  55 ),
                 kbps1792Cps4226   (  56 ),
                 kbps1824Cps4301   (  57 ),
                 kbps1856Cps4377   (  58 ),
                 kbps1888Cps4452   (  59 ),
                 kbps1920Cps4528   (  60 ),
                 kbps1952Cps4603   (  61 ),
                 kbps1984Cps4679   (  62 ),
                 kbps2016Cps4754   (  63 ),
                 kbps2048Cps4830   (  64 ),
                 kbps2080Cps4905   (  65 ),
                 kbps2112Cps4981   (  66 ),
                 kbps2144Cps5056   (  67 ),
                 kbps2176Cps5132   (  68 ),
                 kbps2208Cps5207   (  69 ),
                 kbps2240Cps5283   (  70 ),
                 kbps2272Cps5358   (  71 ),
                 kbps2304Cps5433   (  72 ),
                 kbps2336Cps5509   (  73 ),
                 kbps2368Cps5584   (  74 ),
                 kbps2400Cps5660   (  75 ),
                 kbps2432Cps5735   (  76 ),
                 kbps2464Cps5811   (  77 ),
                 kbps2496Cps5886   (  78 ),
                 kbps2528Cps5962   (  79 ),
                 kbps2560Cps6037   (  80 ),
                 kbps2592Cps6113   (  81 ),
                 kbps2624Cps6188   (  82 ),
                 kbps2656Cps6264   (  83 ),
                 kbps2688Cps6339   (  84 ),
                 kbps2720Cps6415   (  85 ),
                 kbps2752Cps6490   (  86 ),
                 kbps2784Cps6566   (  87 ),
                 kbps2816Cps6641   (  88 ),
                 kbps2848Cps6716   (  89 ),
                 kbps2880Cps6792   (  90 ),
                 kbps2912Cps6867   (  91 ),
                 kbps2944Cps6943   (  92 ),
                 kbps2976Cps7018   (  93 ),
                 kbps3008Cps7094   (  94 ),
                 kbps3040Cps7169   (  95 ),
                 kbps3072Cps7245   (  96 ),
                 kbps3104Cps7320   (  97 ),
                 kbps3136Cps7396   (  98 ),
                 kbps3168Cps7471   (  99 ),
                 kbps3200Cps7547   ( 100 ),
                 kbps3232Cps7622   ( 101 ),
                 kbps3264Cps7698   ( 102 ),
                 kbps3296Cps7773   ( 103 ),
                 kbps3328Cps7849   ( 104 ),
                 kbps3360Cps7924   ( 105 ),
                 kbps3392Cps8000   ( 106 ),
                 kbps3424Cps8075   ( 107 ),
                 kbps3456Cps8150   ( 108 ),
                 kbps3488Cps8226   ( 109 ),
                 kbps3520Cps8301   ( 110 ),
                 kbps3552Cps8377   ( 111 ),
                 kbps3584Cps8452   ( 112 ),
                 kbps3616Cps8528   ( 113 ),
                 kbps3648Cps8603   ( 114 ),
                 kbps3680Cps8679   ( 115 ),
                 kbps3712Cps8754   ( 116 ),
                 kbps3744Cps8830   ( 117 ),
                 kbps3776Cps8905   ( 118 ),
                 kbps3808Cps8981   ( 119 ),
                 kbps3840Cps9056   ( 120 ),
                 kbps3872Cps9132   ( 121 ),
                 kbps3904Cps9207   ( 122 ),
                 kbps3936Cps9283   ( 123 ),
                 kbps3968Cps9358   ( 124 ),
                 kbps4000Cps9433   ( 125 ),
                 kbps4032Cps9509   ( 126 ),
                 kbps4064Cps9584   ( 127 ),
                 kbps4096Cps9660   ( 128 ),
                 kbps4128Cps9735   ( 129 ),
                 kbps4160Cps9811   ( 130 ),
                 kbps4192Cps9886   ( 131 ),
                 kbps4224Cps9962   ( 132 ),
                 kbps4256Cps10037  ( 133 ),
                 kbps4288Cps10113  ( 134 ),
                 kbps4320Cps10188  ( 135 ),
                 kbps4352Cps10264  ( 136 ),
                 kbps4384Cps10339  ( 137 ),
                 kbps4416Cps10415  ( 138 ),
                 kbps4448Cps10490  ( 139 ),
                 kbps4480Cps10566  ( 140 ),
                 kbps4512Cps10641  ( 141 ),
                 kbps4544Cps10716  ( 142 ),
                 kbps4576Cps10792  ( 143 ),
                 kbps4608Cps10867  ( 144 ),
                 kbps4640Cps10943  ( 145 ),
                 kbps4672Cps11018  ( 146 ),
                 kbps4704Cps11094  ( 147 ),
                 kbps4736Cps11169  ( 148 ),
                 kbps4768Cps11245  ( 149 ),
                 kbps4800Cps11320  ( 150 ),
                 kbps4832Cps11396  ( 151 ),
                 kbps4864Cps11471  ( 152 ),
                 kbps4896Cps11547  ( 153 ),
                 kbps4928Cps11622  ( 154 ),
                 kbps4960Cps11698  ( 155 ),
                 kbps4992Cps11773  ( 156 ),
                 kbps5024Cps11849  ( 157 ),
                 kbps5056Cps11924  ( 158 ),
                 kbps5088Cps12000  ( 159 ),
                 kbps5120Cps12075  ( 160 ),
                 kbps5152Cps12150  ( 161 ),
                 kbps5184Cps12226  ( 162 ),
                 kbps5216Cps12301  ( 163 ),
                 kbps5248Cps12377  ( 164 ),
                 kbps5280Cps12452  ( 165 ),
                 kbps5312Cps12528  ( 166 ),
                 kbps5344Cps12603  ( 167 ),
                 kbps5376Cps12679  ( 168 ),
                 kbps5408Cps12754  ( 169 ),
                 kbps5440Cps12830  ( 170 ),
                 kbps5472Cps12905  ( 171 ),
                 kbps5504Cps12981  ( 172 ),
                 kbps5536Cps13056  ( 173 ),
                 kbps5568Cps13132  ( 174 ),
                 kbps5600Cps13207  ( 175 ),
                 kbps5632Cps13283  ( 176 ),
                 kbps5664Cps13358  ( 177 ),
                 kbps5696Cps13433  ( 178 ),
                 kbps5728Cps13509  ( 179 ),
                 kbps5760Cps13584  ( 180 ),
                 kbps5792Cps13660  ( 181 ),
                 kbps5824Cps13735  ( 182 ),
                 kbps5856Cps13811  ( 183 ),
                 kbps5888Cps13886  ( 184 ),
                 kbps5920Cps13962  ( 185 ),
                 kbps5952Cps14037  ( 186 ),
                 kbps5984Cps14113  ( 187 ),
                 kbps6016Cps14188  ( 188 ),
                 kbps6048Cps14264  ( 189 ),
                 kbps6080Cps14339  ( 190 ),
                 kbps6112Cps14415  ( 191 ),
                 kbps6144Cps14490  ( 192 ),
                 kbps6176Cps14566  ( 193 ),
                 kbps6208Cps14641  ( 194 ),
                 kbps6240Cps14716  ( 195 ),
                 kbps6272Cps14792  ( 196 ),
                 kbps6304Cps14867  ( 197 ),
                 kbps6336Cps14943  ( 198 ),
                 kbps6368Cps15018  ( 199 ),
                 kbps6400Cps15094  ( 200 ),
                 kbps6432Cps15169  ( 201 ),
                 kbps6464Cps15245  ( 202 ),
                 kbps6496Cps15320  ( 203 ),
                 kbps6528Cps15396  ( 204 ),
                 kbps6560Cps15471  ( 205 ),
                 kbps6592Cps15547  ( 206 ),
                 kbps6624Cps15622  ( 207 ),
                 kbps6656Cps15698  ( 208 ),
                 kbps6688Cps15773  ( 209 ),
                 kbps6720Cps15849  ( 210 ),
                 kbps6752Cps15924  ( 211 ),
                 kbps6784Cps16000  ( 212 ),
                 kbps6816Cps16075  ( 213 ),
                 kbps6848Cps16150  ( 214 ),
                 kbps6880Cps16226  ( 215 ),
                 kbps6912Cps16301  ( 216 ),
                 kbps6944Cps16377  ( 217 ),
                 kbps6976Cps16452  ( 218 ),
                 kbps7008Cps16528  ( 219 ),
                 kbps7040Cps16603  ( 220 ),
                 kbps7072Cps16679  ( 221 ),
                 kbps7104Cps16754  ( 222 ),
                 kbps7136Cps16830  ( 223 ),
                 kbps7168Cps16905  ( 224 ),
                 kbps7200Cps16981  ( 225 ),
                 kbps7232Cps17056  ( 226 ),
                 kbps7264Cps17132  ( 227 ),
                 kbps7296Cps17207  ( 228 ),
                 kbps7328Cps17283  ( 229 ),
                 kbps7360Cps17358  ( 230 ),
                 kbps7392Cps17433  ( 231 ),
                 kbps7424Cps17509  ( 232 ),
                 kbps7456Cps17584  ( 233 ),
                 kbps7488Cps17660  ( 234 ),
                 kbps7520Cps17735  ( 235 ),
                 kbps7552Cps17811  ( 236 ),
                 kbps7584Cps17886  ( 237 ),
                 kbps7616Cps17962  ( 238 ),
                 kbps7648Cps18037  ( 239 ),
                 kbps7680Cps18113  ( 240 ),
                 kbps7712Cps18188  ( 241 ),
                 kbps7744Cps18264  ( 242 ),
                 kbps7776Cps18339  ( 243 ),
                 kbps7808Cps18415  ( 244 ),
                 kbps7840Cps18490  ( 245 ),
                 kbps7872Cps18566  ( 246 ),
                 kbps7904Cps18641  ( 247 ),
                 kbps7936Cps18716  ( 248 ),
                 kbps7968Cps18792  ( 249 ),
                 kbps8000Cps18867  ( 250 ),
                 kbps8032Cps18943  ( 251 ),
                 kbps8064Cps19018  ( 252 ),
                 kbps8096Cps19094  ( 253 ),
                 rateInvalid       (32767)
                 }

	     
	     Xldv20AdslDataRateUpCurrent ::=
               INTEGER {
                 kbps32Cps75       (   1 ),
                 kbps64Cps150      (   2 ),
                 kbps96Cps226      (   3 ),
                 kbps128Cps301     (   4 ),
                 kbps160Cps377     (   5 ),
                 kbps192Cps452     (   6 ),
                 kbps224Cps528     (   7 ),
                 kbps256Cps603     (   8 ),
                 kbps288Cps679     (   9 ),
                 kbps320Cps754     (  10 ),
                 kbps352Cps830     (  11 ),
                 kbps384Cps905     (  12 ),
                 kbps416Cps981     (  13 ),
                 kbps448Cps1056    (  14 ),
                 kbps480Cps1132    (  15 ),
                 kbps512Cps1207    (  16 ),
                 kbps544Cps1283    (  17 ),
                 kbps576Cps1358    (  18 ),
                 kbps608Cps1433    (  19 ),
                 kbps640Cps1509    (  20 ),
                 kbps672Cps1584    (  21 ),
                 kbps704Cps1660    (  22 ),
                 kbps736Cps1735    (  23 ),
                 kbps768Cps1811    (  24 ),
                 rateInvalid       (32767)
                 }

	     -- Type for SDSL up and downstream data rates .
	     -- The enumeration shows the mapping
	     -- Bitrates in kbits/sec (kbps) and 
	     -- ATM Cellrate in cells/sec (cps).
	     -- k means 1000. 
	     -- The bit rate of an ATM cell is 424=53*8 bits/sec.
	     --
	     Xldv20SdslDataRate ::= 
               INTEGER {
                 kbps160Cps377     (   5 ),
                 kbps192Cps452     (   6 ),
                 kbps208Cps490     (   7 ),
                 kbps256Cps603     (   8 ),
                 kbps288Cps679     (   9 ),
                 kbps320Cps754     (  10 ),
                 kbps352Cps830     (  11 ),
                 kbps384Cps905     (  12 ),
                 kbps400Cps943     (  13 ),
                 kbps768Cps1811    (  24 ),
                 kbps784Cps1849    (  25 ),
                 kbps1152Cps2716   (  36 ),
                 kbps1168Cps2754   (  37 ),
                 kbps1536Cps3622   (  48 ),
                 kbps1552Cps3660   (  49 ),
                 kbps1744Cps4113   (  54 ), 
                 kbps2320Cps5471   (  72 )
                 }


	     Xldv20SdslDataRateCurrent ::=
               INTEGER {
                 kbps160Cps377     (   5 ),
                 kbps192Cps452     (   6 ),
                 kbps208Cps490     (   7 ),
                 kbps256Cps603     (   8 ),
                 kbps288Cps679     (   9 ),
                 kbps320Cps754     (  10 ),
                 kbps352Cps830     (  11 ),
                 kbps384Cps905     (  12 ),
                 kbps400Cps943     (  13 ),
                 kbps768Cps1811    (  24 ),
                 kbps784Cps1849    (  25 ),
                 kbps1152Cps2716   (  36 ),
                 kbps1168Cps2754   (  37 ),
                 kbps1536Cps3622   (  48 ),
                 kbps1552Cps3660   (  49 ),
                 kbps1744Cps4113   (  54 ), 
                 kbps2320Cps5471   (  72 ),
                 rateInvalid       (32767)
                 }



             -- --------------------------------------------------------------
             --                          Commands
             -- --------------------------------------------------------------


             -- This type specifies the user commands (control requests) 
	     -- from the TMN-OS or LCT
	     -- and the results of user commands
	     -- 


         Xldv20ControlReq ::=
            INTEGER {

              -- GENERAL VALUES FOR USER COMMAND HANDLING
              --
              noRequest                         (1) 
              ,commExecStarted                  (5) 
              ,paramFaulty                      (11)
              ,requestBusy                      (12)
              ,setDataFailed                    (13)
              ,aswTimeout                       (14)
              ,commandFailed                    (15)
              ,commandSucceeded                 (16)

              -- S N M P

              ,snmUpdateSnmpConfigFile          (1000)

              ,snmUpdateComplete                (1051)
              ,snmUpdateFailed                  (1052)
              ,snmFtpError                      (1053)
              ,snmUpFtpIpAddrFailed             (1054)
              ,snmUpFtpAccountFailed            (1055)
              ,snmUpFtpPasswdFailed             (1056)
              ,snmUpFtpDescPathFailed           (1057)

              -- C O H  CONNECTION HANDLING

              ,createVplCC                      (2001)
              ,deleteVplCC                      (2002)

              ,createEthVplCC                   (2003)
              ,deleteEthVplCC                   (2004)

              ,createVpcTp                      (2005)
              ,deleteVpcTp                      (2006)

              ,createEthVpcTp                   (2007)
              ,deleteEthVpcTp                   (2008)
              
              ,createVclCC                      (2009)
              ,deleteVclCC                      (2010)

              ,createEthVclCC                   (2011)
              ,deleteEthVclCC                   (2012)

              ,modifyNumberOfVcs                (2013)


              ,actVpiNniFaulty                  (2100)
              ,actVpiUniFaulty                  (2101)
              ,actPortLocationIdFaulty          (2102)
              ,actControlReqFaulty              (2103)

              ,actPeakCellRateUpstreamFaulty    (2106)
              ,actPeakCellRateDownstreamFaulty  (2107)
              ,actCellDelayVariationUpstreamFaulty  (2108)
              ,actCellDelayVariationDownstreamFaulty(2109)
              ,actTrafficTypeFaulty             (2110)

              ,actSCRUpstreamFaulty             (2114)
              ,actSCRDownstreamFaulty           (2115)
              ,actMBSUpstreamFaulty             (2116)
              ,actMBSDownstreamFaulty           (2117)
              ,actVpcTpNotExisting              (2118)
              ,actTrafficDirectionFaulty        (2119)
              ,actVciNniFaulty                  (2120)
              ,actVciUniFaulty                  (2121)
              ,actLineBlocked                   (2122)
              ,actVpcTpExists                   (2123)

              ,actWrongLiType                   (2132)
              ,actSegmentEndPointUniFaulty      (2133)
              ,actSegmentEndPointNniFaulty      (2134)
              ,actVclCCExists                   (2135)
              ,actNumberOfVcsFaulty             (2136)
              ,actVbrCDVTUpstreamFaulty         (2137)
              ,actVbrCDVTDownstreamFaulty       (2138)

              ,actMaxCcsPerPortExceeded         (2140)
              ,actMaxNumberOfVcsToSmall         (2141)
              ,actSegmentEndPointNtFaulty       (2142)
              ,actMaxNrOfCcsInDbExceeded        (2143)
              ,actMaxNrOfCcsOnHwExceeded        (2144)

              ,lineNotEnabled                   (2150)
              ,ccExists                         (2151)

              ,vpiUniNotExisting                (2152)
              ,vciTrafficTypeInvalid            (2153)
              

             -- C A L L P  ETHERNET CONFIGURATION

              ,configEth                         (2200)

              ,configEthFailed                   (2251)
              ,ethModeInvalid                    (2252)
              ,ethVpiUniNotExisting              (2253)
              ,ethVciUniNotExisting              (2254)
              ,ethVciTrafficTypeFaulty           (2255)
              ,ethVciPeakCellRateUpstreamFaulty  (2256)
              ,actEthVpcTpDeletionNotAllowed     (2257)

             -- C A L L P  Continuity Check

             ,continuityCheckRequest             (2300)

             ,continuityCheckAlreadyEnabled      (2351)
             ,continuityCheckAlreadyDisabled     (2352)
             ,continuityCheckReject              (2353)
             ,continuityCheckTestTypeConflict    (2354)
             ,continuityCheckNotSupportedOnNt    (2355)
             ,continuityCheckTrafficDirectionConflict (2356)

            -- C A L L P  CONFIGURATION INBAND Vpi/Vci

             ,configInbandTmn                    (2400)

             ,configInbandTmnFailed              (2451)
             ,inbandVpiExists                    (2452)
             ,inbandVciExists                    (2453)

            -- C A L L P  CONNECTION ADMISSION CONTROL

             ,cacBwOverflowUp                    (2551)
             ,cacBwOverflowDown                  (2552)
             ,cacLineBlockedByTlm                (2553)
             ,cacTrafficTypeConflict             (2554)
             ,cacTrafficDirectionConflict        (2555)
             ,cacMbsOverflowUp                   (2556)
             ,cacMbsOverflowDown                 (2557)
             ,cacBwWarningUp                     (2558)
             ,cacBwWarningDown                   (2559)
             ,cacMbsWarningUp                    (2560)
             ,cacMbsWarningDown                  (2561)
             ,cacMbsScrError                     (2562)
             ,cacInternalError                   (2563)                            

              -- H W M

             ,createHwUnit                       (3000)
             ,deleteHwUnit                       (3001)
             ,changeHwUnitForced                 (3002) 

             ,hwuParamFaulty                     (3100)
             ,hwuCommandFailed                   (3101)
             ,hwuObjExists                       (3102)
             ,hwuEquTypeNotAvail                 (3103)
             ,hwuEqhTypeNotAvail                 (3104)
             ,hwuPiuTypeNotAvail                 (3105)
             ,hwuPiuTypeNotAccepted              (3106)
             ,hwuContainingUnitNotAvail          (3107)
             ,hwuObjNotAvail                     (3108)
             ,hwuObjNotEmpty                     (3109)
             ,hwuObjNotLocked                    (3110)
             ,hwuObjNotValid                     (3111)
             ,hwuOk                              (3112)
             ,hwuCreateHwUnitComplete            (3113)
             ,hwuCcExisting                      (3114)
             ,hwuForcedChangeNotAllowed          (3115)
             ,hwuUpgradeRunning                  (3116)


             -- H W M  R E M O T E  I N V E N T O R Y

             ,riSingleBoard                      (4000)
             ,riAllData                          (4001)

             -- T L M

             ,activateData                       (5000)

             ,resourceProblem                    (5150)
             ,vpProblem                          (5151)
             ,resourceProblemUpstream            (5152)
             ,resourceProblemDownstream          (5153)
             ,vpProblemUpstream                  (5154)
             ,vpProblemDownstream                (5155)
             ,bandwidthUpstreamWarning           (5156)
             ,bandwidthDownstreamWarning         (5157)
             ,mbsUpstreamWarning                 (5158)
             ,mbsDownstreamWarning               (5119)
             ,wrongAdminState                    (5161)
             ,wrongXdslServiceType               (5162)

             -- T L M  PHYSICAL  LOOP TEST
              
             ,loopDiagRequest                    (5500)
             

             -- T L M  ATM  LOOP TEST
              
             ,loopTestRequest                    (5600)

             -- T L M  Physical/ATM  LOOP TEST RESULT
              
             ,loopTestReject                     (5901)
             ,loopTestBusy                       (5902)
 
             -- A L A R M I N G  ALARM LIST HANDLING

             ,updateAlmList                      (6000)
             ,updateFiltList                     (6211)
             ,startSendingAlarms                 (6213)
             ,noCurrentAlarms                    (6214)
 
              -- A L A R M I N G  RESET  HANDLING

             ,warm                               (6300)
             ,cold                               (6301)
             ,reload                             (6302)
             ,dbReload                           (6303)
             
             ,rjUpgRunning                       (6353)
             ,rjRstRunning                       (6354)
             ,rjPiuNotAvail                      (6355)
             ,rjResetNotSupported                (6356)

             -- values for control request result
             -- from long running commands (traps) 
             ,rstRequestFailed                   (6980)

             -- S W M  L O G H A N D L E R

             ,dbuReadRequest                     (7000)

            -- values for control request result
            -- from long running commands (traps) 
            ,dbuReadComplete                     (7081)
            ,dbuReadFailed                       (7082)
            ,dbuFileCreationFailed               (7083)
            ,dbuFileTransmissionFailed           (7084)


             -- S W M  S W  U P G R A D E

            ,sucUpgrStartRequest                 (8000)
            ,sucActivateLoad                     (8001)
            ,sucReadSAPSContentFile              (8003) 
            ,sucGetSwVersions                    (8004)
            ,sucUpgrEndRequest                   (8006)
            
            ,sucUpgrTaskCreationFault            (8050)
            ,sucUpgrDbAccessFault                (8051)
            ,sucGetSwVersionsFailed              (8052)
            ,sucUpgrMissParameter                (8053)
            ,sucAlreadyLoaded                    (8054)

             -- values for control request result
             -- from long running commands (traps) 
            ,sucOk                               (8320)
            ,sucNotOk                            (8321)
            ,sucDbAccessFailed                   (8322)
            ,sucPiuUnlocked                      (8323)
            ,sucTransmissionError                (8324)
            ,sucWrongSwVersion                   (8325)
            ,sucUnitTypeMismatch                 (8326)
            ,sucFtpTransError                    (8327)
            ,sucFtpCrcError                      (8328)
            ,sucSwHwMismatch                     (8329)
            ,sucUpgrWrongAvState                 (8330)
            ,sucFepromCopyFault                  (8331)
            ,sucUpdateDescFileFailed             (8332)
            ,sucFtpServerNoteAvailable           (8333)
            ,sucFtpSendError                     (8334)
            ,sucDbBackupFault                    (8335)
            ,sucUpgradeComplete                  (8336) 
            ,sucUpgradeNotComplete               (8337)
 
             -- values for SW Upgrade task states
            ,sutInitialized                      (8400) -- MR1731
            ,sutToDo                             (8401)
            ,sutStarted                          (8402)
            ,sutCrashed                          (8404)
            ,sutFtpDone                          (8408)
            ,sutDone                             (8416)
            ,sutReadyForReset                    (8432)
            ,sutObsolete                         (8464)


             -- D B M

             ,backupDb                           (9000)

             ,localBackupOk                      (9050)
             ,remoteBackupOk                     (9051)
             ,localBackupFailed                  (9052)
             ,remoteBackupFailed                 (9053)
             ,flashAccessFailed                  (9054)
             ,dbReadFailed                       (9055)

             -- values for control request result
             -- from long running commands (traps) 

             ,dbmLocalBackupOk                   (9100)
             ,dbmRemoteBackupOk                  (9101)
             ,dbmLocalBackupFailed               (9102)
             ,dbmRemoteBackupFailed              (9103)
             ,dbmFlashAccessFailed               (9104)
             ,dbmDbReadFailed                    (9105)
             ,dbmLocalBackupFileFaulty           (9106)
             ,dbmRemoteBackupFileFaulty          (9107)
             ,dbmRestoreFailed                   (9108)
             ,dbmRestoreOk                       (9109)
              
             -- IMA control request and results
             ,imaSetMinNumTxLinks                (9200) -- (command)
             ,imaBwError                         (9201) -- (CAC)
             ,imaSetMinNumOk                     (9202)
             ,imaSetMinNumFailed                 (9203)

             }


         -- ==============================================================
         --       M a i n   g r o u p s  of the  X L D V 2 0 - M I B
         -- ==============================================================

         xldv20SnmpMgmt OBJECT IDENTIFIER 
            -- info-IMPL:    V2.0->
            -- info-VERCTRL: -
	 ::= { xldv20 1 }

         xldv20CallP    OBJECT IDENTIFIER 
            -- info-IMPL:    V2.0->
            -- info-VERCTRL: -
	 ::= { xldv20 2 }

         xldv20Hwm      OBJECT IDENTIFIER 
            -- info-IMPL:    V2.0->
            -- info-VERCTRL: -
	 ::= { xldv20 3 }

         xldv20Tlm      OBJECT IDENTIFIER 
            -- info-IMPL:    V2.0->
            -- info-VERCTRL: -
	 ::= { xldv20 4 }

         xldv20TlmOam   OBJECT IDENTIFIER 
            -- info-IMPL:    V2.0->
            -- info-VERCTRL: -
	 ::= { xldv20 5 }

         xldv20Alarming OBJECT IDENTIFIER 
            -- info-IMPL:    V2.0->
            -- info-VERCTRL: -
	 ::= { xldv20 6 }

         xldv20Swm      OBJECT IDENTIFIER 
            -- info-IMPL:    V2.0->
            -- info-VERCTRL: -
	 ::= { xldv20 7 }

         xldv20Dbm      OBJECT IDENTIFIER 
            -- info-IMPL:    V2.0->
            -- info-VERCTRL: -
	 ::= { xldv20 8 }

         xldv20TlmIma   OBJECT IDENTIFIER 
            -- info-IMPL:    V2.0->
            -- info-VERCTRL: -
	 ::= { xldv20 9 }

         xldv20Traps    OBJECT IDENTIFIER 
            -- info-IMPL:    V2.0->
            -- info-VERCTRL: -
	 ::= { xldv20 10 }


         -- ==============================================================
         --          S N M P   M a n a g e m e n t   G r o u p 
         -- ==============================================================
         --
         --
         xldv20SnmpControl OBJECT IDENTIFIER ::= { xldv20SnmpMgmt 1 }
            -- info-IMPL:    V2.0->
            -- info-VERCTRL: -

         -- This managed entity manages contains the SNMP relevant
         -- attributes.

         xldv20SnmTmnTrapFlowControl OBJECT-TYPE
            -- info-VALUE:   noTraps(1), allTraps(2),
            -- info-VALUE:   noEvents(3), noAlarms(4)
            -- info-ROU:     GET db  SET db 
            -- info-IMPL:    V2.0->
            -- info-VERCTRL: -
            SYNTAX        Xldv20SuppressionType
            ACCESS        read-write
            STATUS        mandatory
            DESCRIPTION
                 " TMN specific flag to suppress or not autonomous messages to TMN-OS.
                 Default is noTraps after reload or first time power up. "
            --DEFAULT test-function-async     fsnSnmTest
            --DEFAULT next-function-async     fsnSnmNext
            --DEFAULT set-function-async      fsnSnmSet
            --DEFAULT get-function-async      fsnSnmGet
            ::= { xldv20SnmpControl 1 }

         xldv20SnmLctTrapFlowControl OBJECT-TYPE
            -- info-VALUE:   noTraps(1), allTraps(2),
            -- info-VALUE:   noEvents(3), noAlarms(4)
            -- info-ROU:     GET db  SET db
            -- info-IMPL:    V2.0->
            -- info-VERCTRL: -
            SYNTAX        Xldv20SuppressionType
            ACCESS        read-write
            STATUS        mandatory
            DESCRIPTION
                 " TMN specific flag to suppress or not autonomous messages to LCT.
                 Default is noTraps after reload or first time power up. "
            --DEFAULT test-function-async     fsnSnmTest
            --DEFAULT next-function-async     fsnSnmNext
            --DEFAULT set-function-async      fsnSnmSet
            --DEFAULT get-function-async      fsnSnmGet
            ::= { xldv20SnmpControl 2 }

         xldv20SnmControlReq OBJECT-TYPE
            -- info-VALUE:   snmUpdateSnmpConfigFile
            -- info-ROU:     GET db  SET sn 
            -- info-IMPL:    V2.0->
            -- info-VERCTRL: -
            SYNTAX        Xldv20ControlReq
            ACCESS        read-write
            STATUS        mandatory
            DESCRIPTION
                 " The user command to start an update of 
		 SNMP configuration file . "
            --DEFAULT test-function-async     fsnSnmTest
            --DEFAULT next-function-async     fsnSnmNext
            --DEFAULT set-function-async      fsnSnmSet
            --DEFAULT get-function-async      fsnSnmGet
            ::= { xldv20SnmpControl 3 }

         xldv20SnmControlStatus OBJECT-TYPE
            -- info-VALUE:   requestIdle(1), requestBusy(2), requestPassed(3)
            -- info-VALUE:   requestFailed(4)
            -- info-ROU:     GET db 
            -- info-IMPL:    V2.0->
            -- info-VERCTRL: -
            SYNTAX        Xldv20ControlStatus
            ACCESS        read-only
            STATUS        mandatory
            DESCRIPTION
                 " The status of control request.
                   The start of an update of the configuration file will
                   only be started if the SnmControlStatus is not requestBusy.  "
            --DEFAULT next-function-async     fsnSnmNext
            --DEFAULT get-function-async      fsnSnmGet
            ::= { xldv20SnmpControl 4 }

         xldv20SnmLctConnected OBJECT-TYPE   
            -- info-VALUE:   yes(1)..no(2) 
            -- info-ROU:     GET db  SET sn 
            -- info-IMPL:    V2.0->
            -- info-VERCTRL: -
            SYNTAX        INTEGER {
                             yes(1),
                             no(2) }
            ACCESS        read-write
            STATUS        mandatory
            DESCRIPTION
                 " If a LCT is connected to the DSLAM the attribute will be set . "
            --DEFAULT test-function-async     fsnSnmTest
            --DEFAULT next-function-async     fsnSnmNext
            --DEFAULT set-function-async      fsnSnmSet
            --DEFAULT get-function-async      fsnSnmGet
            ::= { xldv20SnmpControl 5 }

         xldv20SnmTmnConnected OBJECT-TYPE   
            -- info-VALUE:   yes(1)..no(2)
            -- info-ROU:     GET db  SET sn 
            -- info-IMPL:    V2.0->
            -- info-VERCTRL: -
            SYNTAX        INTEGER {
                             yes(1),
                             no(2) }
            ACCESS        read-write
            STATUS        mandatory
            DESCRIPTION
                 " The attribute is set by TMN-OS to indicate the receipt
                   of the trap 'startupEnd' . "
            --DEFAULT test-function-async     fsnSnmTest
            --DEFAULT next-function-async     fsnSnmNext
            --DEFAULT set-function-async      fsnSnmSet
            --DEFAULT get-function-async      fsnSnmGet
            ::= { xldv20SnmpControl 6 }

         xldv20SnmMaxResponseTime OBJECT-TYPE   
            -- info-VALUE:   -2147483648..2147483647
            -- info-ROU:     GET db 
            -- info-IMPL:    V2.0->
            -- info-VERCTRL: -
            SYNTAX        Integer32
            ACCESS        read-only
            STATUS        mandatory
            DESCRIPTION
                 " TMN-OS maximum wait time in seconds for responses . "
            --DEFAULT next-function-async     fsnSnmNext
            --DEFAULT get-function-async      fsnSnmGet
            ::= { xldv20SnmpControl 7 }

         xldv20SnmTmnMaxNumber OBJECT-TYPE   
            -- info-VALUE:   range according to number of TMNs in
            -- info-VALUE:   SNMP configuration file
            -- info-ROU:     GET db 
            -- info-IMPL:    V2.0->
            -- info-VERCTRL: -
            SYNTAX        Unsigned16
            ACCESS        read-only
            STATUS        mandatory
            DESCRIPTION
                 " The maximum number of TMNs which can be connected. "
            --DEFAULT next-function-async     fsnSnmNext
            --DEFAULT get-function-async      fsnSnmGet
            ::= { xldv20SnmpControl 8 }

         xldv20SnmTmnSpecificIndex OBJECT-TYPE  
            -- info-VALUE:   range according to number of TMNs in
            -- info-VALUE:   SNMP configuration file
            -- info-ROU:     GET db 
            -- info-IMPL:    V2.0->
            -- info-VERCTRL: -
            SYNTAX        Unsigned16
            ACCESS        read-only
            STATUS        mandatory
            DESCRIPTION
                 " The specific index of a TMN which can be connected. "
            --DEFAULT next-function-async     fsnSnmNext
            --DEFAULT get-function-async      fsnSnmGet
            ::= { xldv20SnmpControl 9 }

         -- The following two polling flag attributes are used
         -- in the context of polling, discovery and alarm processing scenario.
         -- Discovery is a process where the TMN reads out the NE data to
         -- perform data sychronization between its own and the NE data.
         -- The NE sets these attributes when alarm traps have been sent or
         -- an LCT session has been terminated. 
         -- Under the assumption that traps can get lost these polling flags
         -- inform about DSLAM data changes and the TMN can discover the NE
         -- data.
         
         xldv20SnmCallpPollingFlag OBJECT-TYPE   
            -- info-VALUE:   flagSet(1), flagNotSet(2)
            -- info-ROU:     GET db
            -- info-IMPL:    V2.0->
            -- info-VERCTRL: -
            SYNTAX        Xldv20PollingFlagType
            ACCESS        read-only
            STATUS        mandatory
            DESCRIPTION
                 " The TMN can poll this global alarm flag to see whether for
                 any COH object an alarm is present. "
            --DEFAULT next-function-async     fsnSnmNext
            --DEFAULT get-function-async      fsnSnmGet
            ::= { xldv20SnmpControl 10 }

         xldv20SnmLctSessionPollingFlag OBJECT-TYPE   
            -- info-VALUE:   flagSet(1), flagNotSet(2)
            -- info-ROU:     GET db SET sn
            -- info-IMPL:    V2.0->
            -- info-VERCTRL: -
            SYNTAX        Xldv20PollingFlagType
            ACCESS        read-write
            STATUS        mandatory
            DESCRIPTION
                 " The TMN can poll this flag to see whether an LCT session
                 has been terminated within the last polling period (value set).
                 During the LCT session DSLAM configuration data may have been
                 changed and therefore the TMN database is inconsistent.
                 The TMN can perform a discovery to sychronize the data.
                 The TMN should set the value to notSet before the discovery.
		 "
            --DEFAULT test-function-async     fsnSnmTest
            --DEFAULT next-function-async     fsnSnmNext
            --DEFAULT set-function-async      fsnSnmSet
            --DEFAULT get-function-async      fsnSnmGet
            ::= { xldv20SnmpControl 11 }

         xldv20SnmControlReqResult OBJECT-TYPE
            -- info-VALUE:   snmUpdateComplete, aswTimeout
            -- info-VALUE:   snmUpdateFailed, snmFtpError       
            -- info-ROU:     GET db
            -- info-IMPL:    V2.0->
            -- info-VERCTRL: -
            SYNTAX        Xldv20ControlReq
            ACCESS        read-only
            STATUS        mandatory
            DESCRIPTION
               " Result of the last user command. "
             --DEFAULT next-function-async     fsnSnmNext
             --DEFAULT get-function-async      fsnSnmGet
             ::= { xldv20SnmpControl 12 }

         xldv20SnmStartupResult OBJECT-TYPE
            -- info-VALUE:   suFinished, suFailed,
            -- info-VALUE:   suStandaloneStartupFinished,
            -- info-VALUE:   suInProgress
            -- info-ROU:     GET db
            -- info-IMPL:    V2.0->
            -- info-VERCTRL: -
            SYNTAX        Xldv20StartupResult
            ACCESS        read-only
            STATUS        mandatory
            DESCRIPTION
               " Result of the last startup . "
             --DEFAULT next-function-async     fsnSnmNext
             --DEFAULT get-function-async      fsnSnmGet
             ::= { xldv20SnmpControl 13 }

         xldv20SnmControlTimeStamp OBJECT-TYPE
            -- info-VALUE:   0..2Giga
            -- info-ROU:     GET db
            -- info-IMPL:    V2.0->
            -- info-VERCTRL: -
            SYNTAX        TimeTicks
            ACCESS        read-only
            STATUS        mandatory
            DESCRIPTION
               " The time stamp of the last command (end of command). "
             --DEFAULT next-function-async     fsnSnmNext
             --DEFAULT get-function-async      fsnSnmGet
             ::= { xldv20SnmpControl 14 }
         ------------------------------------------------------------------
         --
         -- This table holds TMN specific attributes. 
         --
         ------------------------------------------------------------------

         xldv20TmnTable OBJECT-TYPE
            -- info-IMPL:    V2.0->
            -- info-VERCTRL: -
            SYNTAX        SEQUENCE OF Xldv20TmnEntry
            ACCESS        not-accessible
            STATUS        mandatory
            DESCRIPTION
                 " Table for TMN specific data.
                   Instances of this managed entity shall be automatically
                   SNMP configuration file has been read. "
            --DEFAULT next-function-async     fsnTmnEntryNext
            --DEFAULT get-function-async      fsnTmnEntryGet
            ::= { xldv20SnmpMgmt 2 }

         xldv20TmnEntry OBJECT-TYPE
            -- info-IMPL:    V2.0->
            -- info-VERCTRL: -
            SYNTAX        Xldv20TmnEntry
            ACCESS        not-accessible
            STATUS        mandatory
            DESCRIPTION
                 " An entry in the xldv20TmnTable.
                   Notifications : none. "
            INDEX         { xldv20TmnIndex }
            ::= { xldv20TmnTable 1 }

         Xldv20TmnEntry ::=
            SEQUENCE { xldv20TmnIndex                 INTEGER,
                       xldv20TmnOrLctTerminal         Xldv20TerminalType,
                       xldv20TmnInOrOutBand           Xldv20ChannelType,
                       xldv20TmnConnected             INTEGER,
                       xldv20TmnTrapFlowControl       Xldv20SuppressionType,
                       xldv20TmnLctSessionPollingFlag Xldv20PollingFlagType
                       }

         xldv20TmnIndex OBJECT-TYPE
            -- info-VALUE:   1..11 
            -- info-ROU:     GET db
            -- info-IMPL:    V2.0->
            -- info-VERCTRL: -
            SYNTAX        INTEGER (1..11)
            ACCESS        read-only
            STATUS        mandatory
            DESCRIPTION
                 " Index of TmnTable.
                 Entries of the table with same index belong to the same TMN.  "
            ::= { xldv20TmnEntry 1 }

         xldv20TmnOrLctTerminal OBJECT-TYPE
            -- info-VALUE:   tmn(1), lct(2), unknown(10)
            -- info-ROU:     GET db
            -- info-IMPL:    V2.0->
            -- info-VERCTRL: -
            SYNTAX        Xldv20TerminalType
            ACCESS        read-only
            STATUS        mandatory
            DESCRIPTION
                 " Specifies a LCT or TMN terminal. "
            ::= { xldv20TmnEntry 2 }
     
         xldv20TmnInOrOutBand OBJECT-TYPE
            -- info-VALUE:   inband(1), outband(2), unknown(10)
            -- info-ROU:     GET db
            -- info-IMPL:    V2.0->
            -- info-VERCTRL: -
            SYNTAX        Xldv20ChannelType
            ACCESS        read-only
            STATUS        mandatory
            DESCRIPTION
                 " Specifies whether communication is in or outband. "
            ::= { xldv20TmnEntry 3 }
     
         xldv20TmnConnected OBJECT-TYPE
            -- info-VALUE:   yes(1)..no(2) (default)
            -- info-ROU:     GET db
            -- info-IMPL:    V2.0->
            -- info-VERCTRL: -
            SYNTAX        INTEGER {
                             yes(1),
                             no(2) }
            ACCESS        read-only
            STATUS        mandatory
            DESCRIPTION
                 " The attribute indicates whether this TMN/LCT is connected.
		 "
            ::= { xldv20TmnEntry 4 }

         xldv20TmnTrapFlowControl OBJECT-TYPE
            -- info-VALUE:   noTraps(1) (default), allTraps(2),
            -- info-VALUE:   noEvents(3), noAlarms(4)
            -- info-ROU:     GET db
            -- info-IMPL:    V2.0->
            -- info-VERCTRL: -
            SYNTAX        Xldv20SuppressionType
            ACCESS        read-only
            STATUS        mandatory
            DESCRIPTION
                 " To suppress or not autonomous messages to TMN-OS.
                 Default : noTraps after reload or first time power up. "
            ::= { xldv20TmnEntry 5 }

         xldv20TmnLctSessionPollingFlag OBJECT-TYPE
            -- info-VALUE:   flagSet(1), flagNotSet(2) (default)
            -- info-ROU:     GET db
            -- info-IMPL:    V2.0->
            -- info-VERCTRL: -
            SYNTAX        Xldv20PollingFlagType
            ACCESS        read-only
            STATUS        mandatory
            DESCRIPTION
                 " TMN specific LCT session polling flag. "
            ::= { xldv20TmnEntry 6 }

         -- ==============================================================
         --           C o n n e c t i o n  H a n d l i n g  G r o u p
         -- ==============================================================

         -- --------------------------------------------------------------
         --           ATM Cross Connection Command Control subgroup
         -- --------------------------------------------------------------

         xldv20AtmCcControl OBJECT IDENTIFIER ::= { xldv20CallP 1 }
            -- info-IMPL:    V2.0->
            -- info-VERCTRL: -

         -- This managed entity manages the establishment and release
         -- of VP cross-connections ( e.g. VPI ) in the ATM NE.
         --
         -- An instance of this managed entity shall be automatically
         -- created by the ATM NE imnmediately following ATM NE initialization.

         xldv20ActOperationalState OBJECT-TYPE
            -- info-VALUE:   enabled(1)..disabled(2)
            -- info-ROU:     GET db 
            -- info-IMPL:    V2.0->
            -- info-VERCTRL: -
            SYNTAX        Xldv20OperState
            ACCESS        not-accessible
            STATUS        mandatory
            DESCRIPTION
                 " Unused. "
            --DEFAULT next-function-async     fsnActNext
            --DEFAULT get-function-async      fsnActGet
            ::= { xldv20AtmCcControl 1 }

         xldv20ActControlReq OBJECT-TYPE
            -- info-VALUE:   createVplCC, deleteVplCC
            -- info-VALUE:
            -- info-VALUE:   createEthVplCC, deleteEthVplCC
            -- info-VALUE:
            -- info-VALUE:   createVpcTp(V2.0->) ,deleteVpcTp(V2.0->)
            -- info-VALUE:
            -- info-VALUE:   createEthVpcTp(V2.0->), deleteEthVpcTp(V2.0->)
            -- info-VALUE:
            -- info-VALUE:   createVclCC, deleteVclCC
            -- info-VALUE:
            -- info-VALUE:   createEthVclCC, deleteEthVclCC
            -- info-VALUE:
            -- info-VALUE:   configEth
            -- info-VALUE:   configInbandTmn
            -- info-VALUE:
            -- info-VALUE:   modifyNumberOfVcs(V2.0->)
            -- info-VALUE:
            -- info-ROU:     GET db  SET cp 
            -- info-IMPL:    V2.0->
            -- info-VERCTRL: - 
            SYNTAX        Xldv20ControlReq
            ACCESS        read-write
            STATUS        mandatory
            DESCRIPTION
                 " COH (Connection Handling) user commands.
                   Notifications :
                      xldv20TrStateChangeOper.
                      xldv20TrActCcCreation.
                      xldv20TrActCcDeletion.
                      xldv20TrActCcReload . "
            --DEFAULT test-function-async     fsnActTest
            --DEFAULT next-function-async     fsnActNext
            --DEFAULT set-function-async      fsnActSet
            --DEFAULT get-function-async      fsnActGet
            ::= { xldv20AtmCcControl 2 }

         xldv20ActControlStatus OBJECT-TYPE
            -- info-VALUE:   requestIdle(1), requestBusy(2), requestPassed(3)
            -- info-VALUE:   requestFailed(4)
            -- info-ROU:     GET db 
            -- info-IMPL:    V2.0->
            -- info-VERCTRL: -
            SYNTAX        Xldv20ControlStatus
            ACCESS        read-only
            STATUS        mandatory
            DESCRIPTION
                 " Indicates the status of a control request. "
            --DEFAULT next-function-async     fsnActNext
            --DEFAULT get-function-async      fsnActGet
            ::= { xldv20AtmCcControl 3 }

         xldv20ActVpiNni OBJECT-TYPE
            -- info-VALUE:   0..4095
            -- info-ROU:     GET db  SET db 
            -- info-IMPL:    V2.0->
            -- info-VERCTRL: -
            SYNTAX        INTEGER (0..4095)
            ACCESS        read-write
            STATUS        mandatory
            DESCRIPTION
                 " Identifies the VPI value associated with
                   the Local Exchange. "
            --DEFAULT test-function-async     fsnActTest
            --DEFAULT next-function-async     fsnActNext
            --DEFAULT set-function-async      fsnActSet
            --DEFAULT get-function-async      fsnActGet
            ::= { xldv20AtmCcControl 4 }

         xldv20ActVpiUni OBJECT-TYPE
            -- info-VALUE:   0..63
            -- info-ROU:     GET db  SET db 
            -- info-IMPL:    V2.0->
            -- info-VERCTRL: -
            SYNTAX        INTEGER (0..63)
            ACCESS        read-write
            STATUS        mandatory
            DESCRIPTION
                 " The VPI value associated with the Network Termination. "
            --DEFAULT test-function-async     fsnActTest
            --DEFAULT next-function-async     fsnActNext
            --DEFAULT set-function-async      fsnActSet
            --DEFAULT get-function-async      fsnActGet
            ::= { xldv20AtmCcControl 5 }

         xldv20ActVciNni OBJECT-TYPE
            -- info-VALUE:   32..3500
            -- info-ROU:     GET db  SET db 
            -- info-IMPL:    V2.0->
            -- info-VERCTRL: -
            SYNTAX        INTEGER (32..3500)
            ACCESS        read-write
            STATUS        mandatory
            DESCRIPTION
                 " The VCI value associated with the Local Exchange. "
            --DEFAULT test-function-async     fsnActTest
            --DEFAULT next-function-async     fsnActNext
            --DEFAULT set-function-async      fsnActSet
            --DEFAULT get-function-async      fsnActGet
            ::= { xldv20AtmCcControl 6 }

         xldv20ActVciUni OBJECT-TYPE
            -- info-VALUE:   32..3500
            -- info-ROU:     GET db  SET db 
            -- info-IMPL:    V2.0->
            -- info-VERCTRL: -
            SYNTAX        INTEGER (32..3500)
            ACCESS        read-write
            STATUS        mandatory
            DESCRIPTION
                 " The VCI value associated with the Network Termination. "
            --DEFAULT test-function-async     fsnActTest
            --DEFAULT next-function-async     fsnActNext
            --DEFAULT set-function-async      fsnActSet
            --DEFAULT get-function-async      fsnActGet
            ::= { xldv20AtmCcControl 7 }

         xldv20ActIfIndex OBJECT-TYPE
            -- info-VALUE:   0..65535
            -- info-ROU:     GET db  SET db 
            -- info-IMPL:    V2.0->
            -- info-VERCTRL: -
            SYNTAX        Unsigned16
            ACCESS        read-write
            STATUS        mandatory
            DESCRIPTION
                 " The relevant interface index of the connected PPTP . "
            --DEFAULT test-function-async     fsnActTest
            --DEFAULT next-function-async     fsnActNext
            --DEFAULT set-function-async      fsnActSet
            --DEFAULT get-function-async      fsnActGet
            ::= { xldv20AtmCcControl 8 }

         xldv20ActPeakCellRateUpstream OBJECT-TYPE
            -- info-VALUE:   0..160 000 000 (default: 192 000)
            -- info-ROU:     GET db  SET db 
            -- info-IMPL:    V2.0->
            -- info-VERCTRL: -
            SYNTAX        INTEGER (0..160000000)
            ACCESS        read-write
            STATUS        mandatory
            DESCRIPTION
                 " The upstream peak cell rate in bit/sec of the cross connect.
                   ( Bit rate per ATM cell is 53*8 bit/sec ). "
            --DEFAULT test-function-async     fsnActTest
            --DEFAULT next-function-async     fsnActNext
            --DEFAULT set-function-async      fsnActSet
            --DEFAULT get-function-async      fsnActGet
            ::= { xldv20AtmCcControl 9 }

         xldv20ActPeakCellRateDownstream OBJECT-TYPE
            -- info-VALUE:   0..160 000 000 (default: 2 000 000)
            -- info-ROU:     GET db  SET db 
            -- info-IMPL:    V2.0->
            -- info-VERCTRL: -
            SYNTAX        INTEGER (0..160000000)
            ACCESS        read-write
            STATUS        mandatory
            DESCRIPTION
                 " The peak cell rate in downstream direction of the cross connect. "
            --DEFAULT test-function-async     fsnActTest
            --DEFAULT next-function-async     fsnActNext
            --DEFAULT set-function-async      fsnActSet
            --DEFAULT get-function-async      fsnActGet
            ::= { xldv20AtmCcControl 10 }

         xldv20ActCellDelayVariationToleranceUpstream OBJECT-TYPE
            -- info-VALUE:   2..200000 (default: 3000 )
            -- info-ROU:     GET db  SET db 
            -- info-IMPL:    V2.0->
            -- info-VERCTRL: -
            SYNTAX        INTEGER(2..200000)
            ACCESS        read-write
            STATUS        mandatory
            DESCRIPTION
                 " The cell delay variation tolerance (in micro seconds)
		 in upstream direction of the cross connect. "
            --DEFAULT test-function-async     fsnActTest
            --DEFAULT next-function-async     fsnActNext
            --DEFAULT set-function-async      fsnActSet
            --DEFAULT get-function-async      fsnActGet
            ::= { xldv20AtmCcControl 11 }

         xldv20ActCellDelayVariationToleranceDownstream OBJECT-TYPE
            -- info-VALUE:   2..200000 (default: 3000 )
            -- info-ROU:     GET db  SET db 
            -- info-IMPL:    V2.0->
            -- info-VERCTRL: -
            SYNTAX        INTEGER(2..200000)
            ACCESS        read-write
            STATUS        mandatory
            DESCRIPTION
                 " The cell delay variation tolerance (in micro seconds)
                   in downstream direction of the cross connect. "
            --DEFAULT test-function-async     fsnActTest
            --DEFAULT next-function-async     fsnActNext
            --DEFAULT set-function-async      fsnActSet
            --DEFAULT get-function-async      fsnActGet
            ::= { xldv20AtmCcControl 12 }

         xldv20ActTrafficType OBJECT-TYPE
            -- info-VALUE:   cbr,ubr, nrtVbr
            -- info-VALUE:   rtVbr, (default: ubr)
            -- info-ROU:     GET db  SET db 
            -- info-IMPL:    V2.0->
            -- info-VERCTRL: -
            SYNTAX        Xldv20TrafficType
            ACCESS        read-write
            STATUS        mandatory
            DESCRIPTION
                 " The traffic type of the cross connect. 
                   Supported traffic types are :
                         cbr    : Constant bit rate.
                         ubr    : Unspecified bit rate.
                         nrtVbr : Non real time variable bit rate.
                         rtVbr  : Real time variable bit rate. "
            --DEFAULT test-function-async     fsnActTest
            --DEFAULT next-function-async     fsnActNext
            --DEFAULT set-function-async      fsnActSet
            --DEFAULT get-function-async      fsnActGet
            ::= { xldv20AtmCcControl 13 }

         xldv20ActTrafficDirection OBJECT-TYPE
            -- info-VALUE:   bidirectional, upstream, downstream
            -- info-VALUE:   (default: bidirectional)
            -- info-ROU:     GET db  SET db 
            -- info-IMPL:    V2.0->
            -- info-VERCTRL: -
            SYNTAX        Xldv20TrafficDirection
            ACCESS        read-write
            STATUS        mandatory
            DESCRIPTION
                 "  The traffic direction. "
            --DEFAULT test-function-async     fsnActTest
            --DEFAULT next-function-async     fsnActNext
            --DEFAULT set-function-async      fsnActSet
            --DEFAULT get-function-async      fsnActGet
            ::= { xldv20AtmCcControl 14 }

         xldv20ActSustainableCellRateUpstream OBJECT-TYPE
            -- info-VALUE:   0..155000000 (default: 100 000)
            -- info-ROU:     GET db  SET db 
            -- info-IMPL:    V2.0->
            -- info-VERCTRL: -
            SYNTAX        INTEGER (0..155000000)
            ACCESS        read-write
            STATUS        mandatory
            DESCRIPTION
                 "  The upstream sustainable cell rate in bit/sec
                    for nrtVbr traffic. "
            --DEFAULT test-function-async     fsnActTest
            --DEFAULT next-function-async     fsnActNext
            --DEFAULT set-function-async      fsnActSet
            --DEFAULT get-function-async      fsnActGet
            ::= { xldv20AtmCcControl 15 }

         xldv20ActSustainableCellRateDownstream OBJECT-TYPE
            -- info-VALUE:   0..155000000 (default: 100 000)
            -- info-ROU:     GET db  SET db 
            -- info-IMPL:    V2.0->
            -- info-VERCTRL: -
            SYNTAX        INTEGER (0..155000000)
            ACCESS        read-write
            STATUS        mandatory
            DESCRIPTION
                 "  The downstream sustainable cell rate in bit/sec
                    for nrtVbr traffic. "
            --DEFAULT test-function-async     fsnActTest
            --DEFAULT next-function-async     fsnActNext
            --DEFAULT set-function-async      fsnActSet
            --DEFAULT get-function-async      fsnActGet
            ::= { xldv20AtmCcControl 16 }

         xldv20ActMaximumBurstSizeUpstream OBJECT-TYPE
            -- info-VALUE:   0..1500 (default: 32)
            -- info-ROU:     GET db  SET db 
            -- info-IMPL:    V2.0->
            -- info-VERCTRL: -
            SYNTAX        INTEGER(0..1500)
            ACCESS        read-write
            STATUS        mandatory
            DESCRIPTION
                 "  The upstream maximum burst size in cells
                    for nrtVbr traffic. "
            --DEFAULT test-function-async     fsnActTest
            --DEFAULT next-function-async     fsnActNext
            --DEFAULT set-function-async      fsnActSet
            --DEFAULT get-function-async      fsnActGet
            ::= { xldv20AtmCcControl 17 }

         xldv20ActMaximumBurstSizeDownstream OBJECT-TYPE
            -- info-VALUE:   1..1500 (default: 32)
            -- info-ROU:     GET db  SET db 
            -- info-IMPL:    V2.0->
            -- info-VERCTRL: -
            SYNTAX        INTEGER(1..1500)
            ACCESS        read-write
            STATUS        mandatory
            DESCRIPTION
                 "  The downstream maximum burst size in cells
                    for nrtVbr traffic. "
            --DEFAULT test-function-async     fsnActTest
            --DEFAULT next-function-async     fsnActNext
            --DEFAULT set-function-async      fsnActSet
            --DEFAULT get-function-async      fsnActGet
            ::= { xldv20AtmCcControl 18 }

         xldv20ActSegmentEndPointNni OBJECT-TYPE
            -- info-VALUE:   yes..no (default: no)
            -- info-ROU:     GET db  SET db
            -- info-IMPL:    V2.0->
            -- info-VERCTRL: -
            SYNTAX        INTEGER { yes(1), 
                                    no (2)    }
            ACCESS        read-write
            STATUS        mandatory
            DESCRIPTION
                 "  Specifies whether the NNI VplTp/VclTp/VpcTp is
                    a segment endpoint (yes) or a connecting point (no) "
            --DEFAULT test-function-async     fsnActTest
            --DEFAULT next-function-async     fsnActNext
            --DEFAULT set-function-async      fsnActSet
            --DEFAULT get-function-async      fsnActGet
            ::= { xldv20AtmCcControl 19 }

         xldv20ActSegmentEndPointUni OBJECT-TYPE
            -- info-VALUE:   yes..no (default: no)
            -- info-ROU:     GET db  SET db
            -- info-IMPL:    V2.0->
            -- info-VERCTRL: -
            SYNTAX        INTEGER { yes(1), 
                                    no (2)    }
            ACCESS        read-write
            STATUS        mandatory
            DESCRIPTION
                 "  Specifies whether the UNI VplTp/VclTp/VpcTp is
                    a segment endpoint (yes) or a connecting point (no) "
            --DEFAULT test-function-async     fsnActTest
            --DEFAULT next-function-async     fsnActNext
            --DEFAULT set-function-async      fsnActSet
            --DEFAULT get-function-async      fsnActGet
            ::= { xldv20AtmCcControl 20 }

         xldv20ActEthMode OBJECT-TYPE
            -- info-VALUE:   bridging, routing
            -- info-VALUE:   currentConfiguration (default)
            -- info-ROU:     GET db  SET db
            -- info-IMPL:    V2.0->
            -- info-VERCTRL: -
            SYNTAX        Xldv20EthNtMode
            ACCESS        read-write
            STATUS        mandatory
            DESCRIPTION
                  " The operational mode of the ethernet configuration:
                    Available modes: bridging, routing, currentCofiguration
		    (default) .
                    In version V20 the Ethernet configuration is performed
                    already when a NT is created. 
                    The option currentConfiguration keeps the
                    current configuration data during cross connect creation. "
            --DEFAULT test-function-async     fsnActTest
            --DEFAULT next-function-async     fsnActNext
            --DEFAULT set-function-async      fsnActSet
            --DEFAULT get-function-async      fsnActGet
            ::= { xldv20AtmCcControl 21 }

         xldv20ActEthE164Isp     OBJECT-TYPE
            -- info-VALUE:   -
            -- info-ROU:     GET db SET db
            -- info-IMPL:    V2.0->
            -- info-VERCTRL: -
            SYNTAX            OCTET STRING ( SIZE (0..20) ) 
            ACCESS            read-write
            STATUS            mandatory
            DESCRIPTION
                  " The telephon number of the Internet Service Provider. "
            --DEFAULT test-function-async     fsnActTest
            --DEFAULT next-function-async     fsnActNext
            --DEFAULT set-function-async      fsnActSet
            --DEFAULT get-function-async      fsnActGet
            ::= { xldv20AtmCcControl 22 }

         xldv20ActEthIpAddressNt   OBJECT-TYPE
            -- info-VALUE:   Default: 0.0.0.0
            -- info-ROU:     GET db SET db
            -- info-IMPL:    V2.0->
            -- info-VERCTRL: -
            SYNTAX            IpAddress
            ACCESS            read-write
            STATUS            mandatory
            DESCRIPTION
                  " The IP Address of the NT."
            --DEFAULT test-function-async     fsnActTest
            --DEFAULT next-function-async     fsnActNext
            --DEFAULT set-function-async      fsnActSet
            --DEFAULT get-function-async      fsnActGet
            ::= { xldv20AtmCcControl 23 }

         xldv20ActEthIpAddressSubnetMaskNt   OBJECT-TYPE
            -- info-VALUE:   Default: 0.0.0.0
            -- info-ROU:     GET db SET db
            -- info-IMPL:    V2.0->
            -- info-VERCTRL: -
            SYNTAX                IpAddress
            ACCESS            read-write
            STATUS            mandatory
            DESCRIPTION
                  " The subnet mask of the NT. "
            --DEFAULT test-function-async     fsnActTest
            --DEFAULT next-function-async     fsnActNext
            --DEFAULT set-function-async      fsnActSet
            --DEFAULT get-function-async      fsnActGet
            ::= { xldv20AtmCcControl 24 }

         xldv20ActEthIpAddressCo   OBJECT-TYPE
            -- info-VALUE:   Default: 0.0.0.0
            -- info-ROU:     GET db SET db
            -- info-IMPL:    V2.0->
            -- info-VERCTRL: -
            SYNTAX                IpAddress
            ACCESS            read-write
            STATUS            mandatory
            DESCRIPTION
                  " The IP Address of the destination NT (office side). "
            --DEFAULT test-function-async     fsnActTest
            --DEFAULT next-function-async     fsnActNext
            --DEFAULT set-function-async      fsnActSet
            --DEFAULT get-function-async      fsnActGet
            ::= { xldv20AtmCcControl 25 }

         xldv20ActEthIpAddressSubnetMaskCo   OBJECT-TYPE
            -- info-VALUE:   Default: 0.0.0.0
            -- info-ROU:     GET db SET db
            -- info-IMPL:    V2.0->
            -- info-VERCTRL: -
            SYNTAX            IpAddress
            ACCESS            read-write
            STATUS            mandatory
            DESCRIPTION
                  " The subnet mask of the CO. "
            --DEFAULT test-function-async     fsnActTest
            --DEFAULT next-function-async     fsnActNext
            --DEFAULT set-function-async      fsnActSet
            --DEFAULT get-function-async      fsnActGet
            ::= { xldv20AtmCcControl 26 }

         xldv20ActEthIpAddressRemoteRouter    OBJECT-TYPE
            -- info-VALUE:   Default: 0.0.0.0
            -- info-ROU:     GET db SET db
            -- info-IMPL:    V2.0->
            -- info-VERCTRL: -
            SYNTAX            IpAddress
            ACCESS            read-write
            STATUS            mandatory
            DESCRIPTION
                  " The subnet mask of the ISP router. "
            --DEFAULT test-function-async     fsnActTest
            --DEFAULT next-function-async     fsnActNext
            --DEFAULT set-function-async      fsnActSet
            --DEFAULT get-function-async      fsnActGet
            ::= { xldv20AtmCcControl 27 }

         -- for continuity check
         
         xldv20ActTestTypeNni OBJECT-TYPE
            -- info-VALUE:   segment(1), endToEnd(2) 
            -- info-ROU:     GET db  SET db 
            -- info-IMPL:    V2.0->
            -- info-VERCTRL: -
            SYNTAX        Xldv20TestType
            ACCESS        read-write
            STATUS        mandatory
            DESCRIPTION
                 " The type of continuity check on NNI side.
		 On F5 level (VC) segment only . "
            --DEFAULT test-function-async     fsnActTest
            --DEFAULT next-function-async     fsnActNext
            --DEFAULT set-function-async      fsnActSet
            --DEFAULT get-function-async      fsnActGet
            ::= { xldv20AtmCcControl 28 }

         xldv20ActContinuityCheckNni OBJECT-TYPE
            -- info-VALUE:   enabled(1)..disabled(2)
            -- info-ROU:     GET db  SET db 
            -- info-IMPL:    V2.0->
            -- info-VERCTRL: -
            SYNTAX        Xldv20OperState
            ACCESS        read-write
            STATUS        mandatory
            DESCRIPTION
                 " Specifies whether or not the continuity check at NNI side
		 should be enabled for this instance of the 
		 ATM Cross Connection managed entity . "
            --DEFAULT test-function-async     fsnActTest
            --DEFAULT next-function-async     fsnActNext
            --DEFAULT set-function-async      fsnActSet
            --DEFAULT get-function-async      fsnActGet
            ::= { xldv20AtmCcControl 29 }

         xldv20ActEndpointTypeNni OBJECT-TYPE
            -- info-VALUE:   source (1), sink (2)
            -- info-VALUE:   both (3)
            -- info-ROU:     GET db  SET db 
            -- info-IMPL:    V2.0->
            -- info-VERCTRL: -
            SYNTAX        Xldv20EndpointType 
            ACCESS        read-write
            STATUS        mandatory
            DESCRIPTION
                 " Specifies whether the NNI termination point 
                 VplTp/VclTp/VpcTp during countinuity check should be a
                 source or sink or both (bidirectional connection only). "
            --DEFAULT test-function-async     fsnActTest
            --DEFAULT next-function-async     fsnActNext
            --DEFAULT set-function-async      fsnActSet
            --DEFAULT get-function-async      fsnActGet
            ::= { xldv20AtmCcControl 30 }

         xldv20ActTestTypeUni OBJECT-TYPE
            -- info-VALUE:   segment(1), endToEnd(2) 
            -- info-ROU:     GET db  SET db 
            -- info-IMPL:    V2.0->
            -- info-VERCTRL: -
            SYNTAX        Xldv20TestType
            ACCESS        read-write
            STATUS        mandatory
            DESCRIPTION
                 " The type of continuity check on UNI side.
                 On F5 level (VC) only segment. "   
            --DEFAULT test-function-async     fsnActTest
            --DEFAULT next-function-async     fsnActNext
            --DEFAULT set-function-async      fsnActSet
            --DEFAULT get-function-async      fsnActGet
            ::= { xldv20AtmCcControl 31 }

         xldv20ActContinuityCheckUni OBJECT-TYPE
            -- info-VALUE:   enabled(1)..disabled(2)
            -- info-ROU:     GET db  SET db 
            -- info-IMPL:    V2.x->
            -- info-VERCTRL: -
            SYNTAX        Xldv20OperState
            ACCESS        read-write
            STATUS        mandatory
            DESCRIPTION
                 " Specifies whether or not the continuity check at UNI 
		   should be enabled for this instance of
                   the ATM Cross Connection managed entity. "
            --DEFAULT test-function-async     fsnActTest
            --DEFAULT next-function-async     fsnActNext
            --DEFAULT set-function-async      fsnActSet
            --DEFAULT get-function-async      fsnActGet
            ::= { xldv20AtmCcControl 32 }

         xldv20ActEndpointTypeUni OBJECT-TYPE
            -- info-VALUE:   source (1), sink (2)
            -- info-VALUE:   both (3)
            -- info-ROU:     GET db  SET db 
            -- info-IMPL:    V2.x->
            -- info-VERCTRL: -
            SYNTAX        Xldv20EndpointType
            ACCESS        read-write
            STATUS        mandatory
            DESCRIPTION
                 " Specifies whether the UNI termination point 
                 VplTp/VclTp/VpcTp during countinuity check should be 
                 source or sink or both (bidirectional connection only). "
            --DEFAULT test-function-async     fsnActTest
            --DEFAULT next-function-async     fsnActNext
            --DEFAULT set-function-async      fsnActSet
            --DEFAULT get-function-async      fsnActGet
            ::= { xldv20AtmCcControl 33 }

         xldv20ActControlReqResult OBJECT-TYPE
            -- info-VALUE:   COMMANDS:
            -- info-VALUE:   createVplCC, deleteVplCC
            -- info-VALUE:
            -- info-VALUE:   createEthVplCC, deleteEthVplCC
            -- info-VALUE:
            -- info-VALUE:   createVpcTp(V2.0->) ,deleteVpcTp(V2.0->)
            -- info-VALUE:
            -- info-VALUE:   createEthVpcTp(V2.0->), deleteEthVpcTp(V2.0->)
            -- info-VALUE:
            -- info-VALUE:   createVclCC, deleteVclCC
            -- info-VALUE:
            -- info-VALUE:   createEthVclCC, deleteEthVclCC
            -- info-VALUE:
            -- info-VALUE:   configEth
            -- info-VALUE:   configInbandTmn
            -- info-VALUE:
            -- info-VALUE:   modifyNumberOfVcs(V2.0->)
            -- info-VALUE:
            -- info-VALUE:   RESULTS:
            -- info-VALUE:
            -- info-VALUE:   actVpiNniFaulty
            -- info-VALUE:   actVpiUniFaulty ,actPortLocationIdFaulty
            -- info-VALUE:   actControlReqFaulty   ,lineNotEnabled       
            -- info-VALUE:   ccExists            
            -- info-VALUE:   actPeakCellRateUpstreamFaulty
            -- info-VALUE:   actPeakCellRateDownstreamFaulty 
            -- info-VALUE:   actCellDelayVariationUpstreamFaulty
            -- info-VALUE:   actCellDelayVariationDownstreamFaulty
            -- info-VALUE:   actTrafficTypeFaulty
            -- info-VALUE:   actSCRUpstreamFaulty
            -- info-VALUE:   actSCRDownstreamFaulty ,actMBSUpstreamFaulty 
            -- info-VALUE:   actMBSDownstreamFaulty
            -- info-VALUE:   actVpcTpNotExisting, actVpcTpExists 
            -- info-VALUE:   actTrafficDirectionFaulty ,actVciNniFaulty
            -- info-VALUE:   actVciUniFaulty ,actLineBlocked
            -- info-VALUE:   vpiUniNotExisting
            -- info-VALUE:   vciTrafficTypeInvalid ,vciUniValueFaulty    
            -- info-VALUE:   actWrongLiType
            -- info-VALUE:   actSegmentEndPointUniFaulty  
            -- info-VALUE:   actSegmentEndPointNniFaulty 
            -- info-VALUE:   actSegmentEndPointNtFaulty
            -- info-VALUE:   actVclCCExists             
            -- info-VALUE:   actNumberOfVcsFaulty
            -- info-VALUE:   actMaxCcsPerPortExceeded
            -- info-VALUE:   actMaxNrOfCcsInDbExceeded
            -- info-VALUE:   actMaxNrOfCcsOnHwExceeded
            -- info-VALUE:   actMaxNumberOfVcsToSmall
            -- info-VALUE:   configEthFailed ,ethModeInvalid 
            -- info-VALUE:   ethVpiUniNotExisting ,ethVciUniNotExisting
            -- info-VALUE:   ethVciTrafficTypeFaulty  
            -- info-VALUE:   ethVciPeakCellRateUpstreamFaulty
            -- info-VALUE:   actEthVpcTpDeletionNotAllowed  
            -- info-VALUE:   continuityCheckRequest
            -- info-VALUE:   continuityCheckAlreadyEnabled
            -- info-VALUE:   continuityCheckAlreadyDisabled
            -- info-VALUE:   continuityCheckTestTypeConflict
            -- info-VALUE:   continuityCheckNotSupportedOnNt
            -- info-VALUE:   continuityCheckReject
            -- info-VALUE:   continuityCheckTrafficDirectionConflict
            -- info-VALUE:   configInbandTmn ,configInbandTmnFailed 
            -- info-VALUE:   inbandVpiExists ,inbandVciExists
            -- info-VALUE:   cacBwOverflowUp
            -- info-VALUE:   cacBwOverflowDown ,cacLineBlockedByTlm
            -- info-VALUE:   cacTrafficTypeConflict 
            -- info-VALUE:   cacTrafficDirectionConflict
            -- info-VALUE:   cacMbsOverflowUp ,cacMbsOverflowDown
            -- info-VALUE:   cacBwWarningUp, cacBwWarningDown
            -- info-VALUE:   cacMbsWarningUp, cacMbsWarningDown
            -- info-VALUE:   cacMbsScrError ,cacInternalError
            -- info-ROU:     GET db
            -- info-IMPL:    V2.0->
            -- info-VERCTRL: -
            SYNTAX        Xldv20ControlReq
            ACCESS        read-only
            STATUS        mandatory
            DESCRIPTION
                 " The result of the last user command. "
            --DEFAULT next-function-async     fsnActNext
            --DEFAULT get-function-async      fsnActGet
            ::= { xldv20AtmCcControl 34 }

         xldv20ActInbandVpi OBJECT-TYPE
            -- info-VALUE:   0..255, default 255
            -- info-ROU:     GET db SET db
            -- info-IMPL:    V2.0->
            -- info-VERCTRL: -
            SYNTAX        INTEGER (0..255)
            ACCESS        read-write
            STATUS        mandatory
            DESCRIPTION
                 " The value of the configured inband Vpi.
                 The configured Vpi will be effective only after next reload.  "
            --DEFAULT test-function-async     fsnActTest
            --DEFAULT next-function-async     fsnActNext
            --DEFAULT set-function-async      fsnActSet
            --DEFAULT get-function-async      fsnActGet
            ::= { xldv20AtmCcControl 35 }

         xldv20ActInbandVci OBJECT-TYPE
            -- info-VALUE:   32..127, default 32
            -- info-ROU:     GET db SET db
            -- info-IMPL:    V2.0->
            -- info-VERCTRL: -
            SYNTAX        INTEGER (32..127)
            ACCESS        read-write
            STATUS        mandatory
            DESCRIPTION
                 " The value of the configured inband Vci.
                 The configured Vci will be effective only after next reload.  "
            --DEFAULT test-function-async     fsnActTest
            --DEFAULT next-function-async     fsnActNext
            --DEFAULT set-function-async      fsnActSet
            --DEFAULT get-function-async      fsnActGet
            ::= { xldv20AtmCcControl 36 }

         xldv20ActCallpTableIndex OBJECT-TYPE
            -- info-VALUE:   1..4144
            -- info-ROU:     GET db
            -- info-IMPL:    V2.0->
            -- info-VERCTRL: -
            SYNTAX        INTEGER (1..4144)
            ACCESS        read-only
            STATUS        mandatory
            DESCRIPTION
                 " After a successfull creation or deletion of a cross connect
                 COH provides the index of the created or deleted object. "
            --DEFAULT next-function-async     fsnActNext
            --DEFAULT get-function-async      fsnActGet
            ::= { xldv20AtmCcControl 37 }

         xldv20ActMaxVciValue OBJECT-TYPE
            -- info-VALUE:   32..3500
            -- info-ROU:     GET db  SET db 
            -- info-IMPL:    V2.0->
            -- info-VERCTRL: -
            SYNTAX        INTEGER (32..3500)
            ACCESS        read-write
            STATUS        mandatory
            DESCRIPTION
                 " Configures the amount of VC's and their VCI values 
		 which are created within a VpcTp.
		 Minimum VCI value is 32. 
		 Maximum VCI value is 3500 (due to HW limits). "
            --DEFAULT test-function-async     fsnActTest
            --DEFAULT next-function-async     fsnActNext
            --DEFAULT set-function-async      fsnActSet
            --DEFAULT get-function-async      fsnActGet
            ::= { xldv20AtmCcControl 38 }

         xldv20ActVbrCDVTUpstream OBJECT-TYPE
            -- info-VALUE:   2..504000000 (default: 3000 )
            -- info-ROU:     GET db  SET db 
            -- info-IMPL:    V2.0->
            -- info-VERCTRL: -
            SYNTAX        INTEGER(2..504000000)
            ACCESS        read-write
            STATUS        mandatory
            DESCRIPTION
                 " The cell delay variation (in micro seconds)
                   for VBR traffic in upstream direction. "
            --DEFAULT test-function-async     fsnActTest
            --DEFAULT next-function-async     fsnActNext
            --DEFAULT set-function-async      fsnActSet
            --DEFAULT get-function-async      fsnActGet
            ::= { xldv20AtmCcControl 39 }

         xldv20ActVbrCDVTDownstream OBJECT-TYPE
            -- info-VALUE:   2..504000000 (default: 3000 )
            -- info-ROU:     GET db  SET db 
            -- info-IMPL:    V2.0->
            -- info-VERCTRL: -
            SYNTAX        INTEGER(2..504000000)
            ACCESS        read-write
            STATUS        mandatory
            DESCRIPTION
                 " The cell delay variation (in micro seconds)
                   for VBR traffic in downstream direction. "
            --DEFAULT test-function-async     fsnActTest
            --DEFAULT next-function-async     fsnActNext
            --DEFAULT set-function-async      fsnActSet
            --DEFAULT get-function-async      fsnActGet
            ::= { xldv20AtmCcControl 40 }

         xldv20ActControlTimeStamp OBJECT-TYPE
            -- info-VALUE:   0..2Giga
            -- info-ROU:     GET db
            -- info-IMPL:    V2.0->
            -- info-VERCTRL: -
            SYNTAX        TimeTicks
            ACCESS        read-only
            STATUS        mandatory
            DESCRIPTION
               " The time stamp of the last command (end of command). "
            --DEFAULT next-function-async     fsnActNext
            --DEFAULT get-function-async      fsnActGet
            ::= { xldv20AtmCcControl 41 }

         -- For OAM function at NT with version >= NT4500
         --
         xldv20ActSegmentEndPointNt OBJECT-TYPE
            -- info-VALUE:   yes..no (default: no)
            -- info-ROU:     GET db  SET db
            -- info-IMPL:    V2.0->
            -- info-VERCTRL: -
            SYNTAX        INTEGER { yes(1),
                                    no (2)    }
            ACCESS        read-write
            STATUS        mandatory
            DESCRIPTION
              "  Specifies whether the VplTp/VpcTp at the
              NT is a segment endpoint (yes) or a connecting point (no). "
            --DEFAULT test-function-async     fsnActTest
            --DEFAULT next-function-async     fsnActNext
            --DEFAULT set-function-async      fsnActSet
            --DEFAULT get-function-async      fsnActGet
            ::= { xldv20AtmCcControl 42 }
 
         -- enabling/disabling continuity check at NT
         -- when creating a VP or VC cross connect
 
         xldv20ActTestTypeNt  OBJECT-TYPE
            -- info-VALUE:   segment(1), endToEnd(2)
            -- info-ROU:     GET db  SET db
            -- info-IMPL:    V2.0->
            -- info-VERCTRL: -
            SYNTAX        Xldv20TestType
            ACCESS        read-write
            STATUS        mandatory
            DESCRIPTION
              " The type of continuity check at NT (segment or endToEnd) . "
            --DEFAULT test-function-async     fsnActTest
            --DEFAULT next-function-async     fsnActNext
            --DEFAULT set-function-async      fsnActSet
            --DEFAULT get-function-async      fsnActGet
            ::= { xldv20AtmCcControl 43 }
 
         xldv20ActContinuityCheckNt  OBJECT-TYPE
            -- info-VALUE:   enabled(1)..disabled(2)
            -- info-ROU:     GET db  SET db
            -- info-IMPL:    V2.0->
            -- info-VERCTRL: -
            SYNTAX        Xldv20OperState
            ACCESS        read-write
            STATUS        mandatory
            DESCRIPTION
              " Specifies whether or not the continuity check at NT
	      should be enabled . 
	      NOTE : continuity check not supported at VccTp (F5 level) ."
            --DEFAULT test-function-async     fsnActTest
            --DEFAULT next-function-async     fsnActNext
            --DEFAULT set-function-async      fsnActSet
            --DEFAULT get-function-async      fsnActGet
            ::= { xldv20AtmCcControl 44 }
 
         xldv20ActEndpointTypeNt  OBJECT-TYPE
            -- info-VALUE:   source (1), sink (2)
            -- info-VALUE:   both (3)
            -- info-ROU:     GET db  SET db
            -- info-IMPL:    V2.0->
            -- info-VERCTRL: -
            SYNTAX        Xldv20EndpointType
            ACCESS        read-write
            STATUS        mandatory
            DESCRIPTION
              " Specifies whether the endpoint VplTp/VpcTp at NT
	      should be a source or sink or both (bidirectional connection only)
              for continuity check cells. "
            --DEFAULT test-function-async     fsnActTest
            --DEFAULT next-function-async     fsnActNext
            --DEFAULT set-function-async      fsnActSet
            --DEFAULT get-function-async      fsnActGet
            ::= { xldv20AtmCcControl 45 }

         xldv20ActCDVTAutoConfig OBJECT-TYPE
            -- info-VALUE:   yes(1) (default), no(2)
            -- info-ROU:     GET db  SET db 
            -- info-IMPL:    V2.0->
            -- info-VERCTRL: -
            SYNTAX        INTEGER {
                             yes(1),
                             no(2) }
            ACCESS        read-write
            STATUS        mandatory
            DESCRIPTION
                 " If yes is selected the policing parameter
		 CDVT (cell delay variation tolerance)
                 is determined automatically depending on
		 the configured cell rate. "
            --DEFAULT test-function-async     fsnActTest
            --DEFAULT next-function-async     fsnActNext
            --DEFAULT set-function-async      fsnActSet
            --DEFAULT get-function-async      fsnActGet
            ::= { xldv20AtmCcControl 46 }

         -- --------------------------------------------------------------
         --            ATM Cross Connect Table for VPL Cross Connection
         -- -------------------------------------------------------------

         xldv20AtmCrossConnectTable OBJECT-TYPE
            -- info-IMPL:    V2.0->
            -- info-VERCTRL: -
            SYNTAX        SEQUENCE OF Xldv20AtmCrossConnectEntry
            ACCESS        not-accessible
            STATUS        mandatory
            DESCRIPTION
                 " The ATM VP cross connect table.
                   This managed entity is used to represent
                   the cross-connect relationship between two Vpl termination
                   points.
                   Instances of this managed entity shall be automatically
                   created and deleted during ATM Connect and ATM Disconnect
		   actions. "
            --DEFAULT test-function-async     fsnAccEntryTest
            --DEFAULT next-function-async     fsnAccEntryNext
            --DEFAULT set-function-async      fsnAccEntrySet
            --DEFAULT get-function-async      fsnAccEntryGet
            ::= { xldv20CallP 2 }

         xldv20AtmCrossConnectEntry OBJECT-TYPE
            -- info-IMPL:    V2.0->
            -- info-VERCTRL: -
            SYNTAX        Xldv20AtmCrossConnectEntry
            ACCESS        not-accessible
            STATUS        mandatory
            DESCRIPTION
                 " An entry in the ATM cross connect table.  "
            INDEX         { xldv20AccVpiNniIndex }
            ::= { xldv20AtmCrossConnectTable 1 }

         Xldv20AtmCrossConnectEntry ::=
            SEQUENCE { xldv20AccOperationalState   Xldv20OperState,
                       xldv20AccTerminationPointA  INTEGER,
                       xldv20AccTerminationPointZ  INTEGER,
                       xldv20AccLineIndex          Unsigned16,
                       xldv20AccEthVpcIndex        INTEGER,
                       xldv20AccEthVccIndex        INTEGER,
                       xldv20AccVpiNniIndex        INTEGER,
                       xldv20AccAlarmState         Xldv20CallpAlarmState,
                       xldv20AccAdminState         Xldv20AdminState,
                       xldv20AccAtmfVplIndex       INTEGER
                       }

         xldv20AccOperationalState OBJECT-TYPE
            -- info-VALUE:   enabled(1)..disabled(2)
            -- info-ROU:     GET db
            -- info-IMPL:    V2.0->
            -- info-VERCTRL: -
            SYNTAX        Xldv20OperState
            ACCESS        read-only
            STATUS        mandatory
            DESCRIPTION
                 " Identifies whether or not this instance of
                   the ATM Cross Connection managed entity is capable of
                   performing its normal function ( i.e. switching cells ).
                   Altering this attribute is without reporting this state
                   change via the trap 'xldv20TrStateChangeOper'. "
            ::= { xldv20AtmCrossConnectEntry 1 }

         xldv20AccTerminationPointA OBJECT-TYPE
            -- info-VALUE:   1..4096
            -- info-ROU:     GET db
            -- info-IMPL:    V2.0->
            -- info-VERCTRL: -
            SYNTAX        INTEGER (1..4096)
            ACCESS        read-only
            STATUS        mandatory
            DESCRIPTION
                 " The instance of the VPL termination point within the DSLAM at the LE side. "
            ::= { xldv20AtmCrossConnectEntry 2 }

         xldv20AccTerminationPointZ OBJECT-TYPE
            -- info-VALUE:   1..4096
            -- info-ROU:     GET db
            -- info-IMPL:    V2.0->
            -- info-VERCTRL: -
            SYNTAX        INTEGER (1..4096)
            ACCESS        read-only
            STATUS        mandatory
            DESCRIPTION
                 " The instance of the VPL termination point within the DSLAM 
		 at the NT side. "
            ::= { xldv20AtmCrossConnectEntry 3 }

         xldv20AccLineIndex OBJECT-TYPE
            -- info-VALUE:   0..65535
            -- info-ROU:     GET db
            -- info-IMPL:    V2.0->
            -- info-VERCTRL: -
            SYNTAX        Unsigned16
            ACCESS        read-only
            STATUS        mandatory
            DESCRIPTION
                 " The external line index. The TLM interfaces (see IFTable)
		 with same line index blong to the same line. "
            ::= { xldv20AtmCrossConnectEntry 4 }

         xldv20AccEthVpcIndex OBJECT-TYPE
            -- info-VALUE:   0..2000
            -- info-ROU:     GET db
            -- info-IMPL:    V2.0->
            -- info-VERCTRL: -
            SYNTAX        INTEGER (0..2000)
            ACCESS        read-only
            STATUS        mandatory
            DESCRIPTION
                 " For cross connects at the LIETH a pointer to the
                   belonging VpcTp. The value is the entry number in the
                   xldv20VpcTpTable.
                   For all other cross connects the value is always 0. "
            ::= { xldv20AtmCrossConnectEntry 5 }

         xldv20AccEthVccIndex OBJECT-TYPE
            -- info-VALUE:   0..1000
            -- info-ROU:     GET db
            -- info-IMPL:    V2.0->
            -- info-VERCTRL: -
            SYNTAX        INTEGER (0..1000)
            ACCESS        read-only
            STATUS        mandatory
            DESCRIPTION
                 " For cross connects at the LIETH a pointer to the
                   belonging VccTp. The value is the entry number in the
                   xldv20VccTpTable.
                   For all other cross connects the value is always 0. "
            ::= { xldv20AtmCrossConnectEntry 6 }
     
         xldv20AccVpiNniIndex OBJECT-TYPE
            -- info-VALUE:   1..2000
            -- info-ROU:     GET db
            -- info-IMPL:    V2.0->
            -- info-VERCTRL: -
            SYNTAX        INTEGER (1..2000)
            ACCESS        read-only
            STATUS        mandatory
            DESCRIPTION
                 " Index of this table. "
            ::= { xldv20AtmCrossConnectEntry 7 }

         xldv20AccAlarmState OBJECT-TYPE
            -- info-VALUE:   noAlarm(1), alarmPresent(2)
            -- info-ROU:     GET db
            -- info-IMPL:    V2.0->
            -- info-VERCTRL: -
            SYNTAX        Xldv20CallpAlarmState
            ACCESS        read-only
            STATUS        mandatory
            DESCRIPTION
                 " Indicates whether for the cross connect
                   an alarm is present or not. "
            ::= { xldv20AtmCrossConnectEntry 8 }

         xldv20AccAdminState OBJECT-TYPE
            -- info-VALUE:   unlocked(1), locked(2)
            -- info-ROU:     GET db  SET cp 
            -- info-IMPL:    V2.0->
            -- info-VERCTRL: -
            SYNTAX        Xldv20AdminState
            ACCESS        read-write
            STATUS        mandatory
            DESCRIPTION
                 " This attribute is used to activate (unlock) and deactivate
                   (lock) the VPL cross connection. The cross connect is
                   removed within the ATM ASIC, the configuration data of the
                   cross connect are still available within the DSLAM . "
            ::= { xldv20AtmCrossConnectEntry 9 }

         xldv20AccAtmfVplIndex OBJECT-TYPE
            -- info-VALUE:   0..4000
            -- info-ROU:     GET db
            -- info-IMPL:    V2.0->
            -- info-VERCTRL: -
            SYNTAX        INTEGER (0..4000)
            ACCESS        read-only
            STATUS        mandatory
            DESCRIPTION
                 " For cross connects at the ATMF port of NT this value
                 identifies the belonging VplTp . The value is the 
                 entry number in the xldv20VplTpTable.
                 For all other cross connects the value is always 0. "
            ::= { xldv20AtmCrossConnectEntry 10 }


         -- --------------------------------------------------------------
         --                        VPL TP Table
         -- --------------------------------------------------------------

         xldv20VplTpTable OBJECT-TYPE
            -- info-IMPL:    V2.0->
            -- info-VERCTRL: -
            SYNTAX        SEQUENCE OF Xldv20VplTpEntry
            ACCESS        not-accessible
            STATUS        mandatory
            DESCRIPTION
                 " This table contains the entries for Vpl termination
                 points (VplTp). "
            --DEFAULT test-function-async     fsnVplEntryTest
            --DEFAULT next-function-async     fsnVplEntryNext
            --DEFAULT set-function-async      fsnVplEntrySet
            --DEFAULT get-function-async      fsnVplEntryGet
            ::= { xldv20CallP 3 }

         xldv20VplTpEntry OBJECT-TYPE
            -- info-IMPL:    V2.0->
            -- info-VERCTRL: -
            SYNTAX        Xldv20VplTpEntry
            ACCESS        not-accessible
            STATUS        mandatory
            DESCRIPTION
                 " Represent the VPL termination points on an ATM NE. "
            INDEX         { xldv20VplIndex }
            ::= { xldv20VplTpTable 1 }

         Xldv20VplTpEntry ::=
            SEQUENCE { xldv20VplOperationalState          Xldv20OperState,
                       xldv20VplVpiValue                  INTEGER,
                       xldv20VplHwUnitIndex               Unsigned16,
                       xldv20VplIfIndex                   Unsigned16,
                       xldv20VplPeakCellRateUpstream      Unsigned32,
                       xldv20VplPeakCellRateDownstream    Unsigned32,
                       xldv20VplCellDelayVariationToleranceUpstream  INTEGER,
                       xldv20VplCellDelayVariationToleranceDownstream  INTEGER,
                       xldv20VplTrafficType                   Xldv20TrafficType,
                       xldv20VplTrafficDirection              Xldv20TrafficDirection,
                       xldv20VplConnectivityPointer           Unsigned16,
                       xldv20VplLineIndex                     Unsigned16,
                       xldv20VplSegmentEndPoint               INTEGER,
                       xldv20VplSustainableCellRateUpstream   Unsigned32,
                       xldv20VplSustainableCellRateDownstream Unsigned32,
                       xldv20VplMaximumBurstSizeUpstream      INTEGER,
                       xldv20VplMaximumBurstSizeDownstream    INTEGER,
                       xldv20VplAlarmSeverityIndex            Xldv20AlmSevProfileIndex,
                       xldv20VplAlarmFilteringIndex           Xldv20AlmFiltProfileIndex,
                       xldv20VplCvpIndexSegment               INTEGER,    -- continuity check
                       xldv20VplIndex                         INTEGER,
                       xldv20VplLOCAlarm                  Xldv20TpAlarmState,
                       xldv20VplVbrCDVTUpstream               INTEGER,
                       xldv20VplVbrCDVTDownstream             INTEGER
                       }

         xldv20VplOperationalState OBJECT-TYPE
            -- info-VALUE:   enabled(1)..disabled(2)
            -- info-ROU:     GET db  SET db 
            -- info-IMPL:    V2.0->
            -- info-VERCTRL: -
            SYNTAX        Xldv20OperState
            ACCESS        read-only
            STATUS        mandatory
            DESCRIPTION
                 " This read-only attribute identifies whether or not the VPL
                   termination is capable of performing its normal functions
                   (in-service or out-of-service). "
            ::= { xldv20VplTpEntry 1 }

         xldv20VplVpiValue OBJECT-TYPE
            -- info-VALUE:   0..4095
            -- info-ROU:     GET db
            -- info-IMPL:    V2.0->
            -- info-VERCTRL: -
            SYNTAX        INTEGER (0..4095)
            ACCESS        read-only
            STATUS        mandatory
            DESCRIPTION
                 " The VPI value associated with the VP link being terminated. "
            ::= { xldv20VplTpEntry 2 }

         xldv20VplHwUnitIndex OBJECT-TYPE
            -- info-VALUE:   0..65535
            -- info-ROU:     GET db
            -- info-IMPL:    V2.0->
            -- info-VERCTRL: -
            SYNTAX        Unsigned16 
            ACCESS        read-only
            STATUS        mandatory
            DESCRIPTION
                 " The HwUnitIndex of HWM sublayer:
                   LU for VplNNi or SU for VplUNI. "
            ::= { xldv20VplTpEntry 3 }

         xldv20VplIfIndex OBJECT-TYPE
            -- info-VALUE:   0..65535
            -- info-ROU:     GET db
            -- info-IMPL:    V2.0->
            -- info-VERCTRL: -
            SYNTAX        Unsigned16 
            ACCESS        read-only
            STATUS        mandatory
            DESCRIPTION
                  " The TLM interface index of the connected PPTP. "
            ::= { xldv20VplTpEntry 4 }

         xldv20VplPeakCellRateUpstream OBJECT-TYPE
            -- info-VALUE:   0..2147483647 (default: 192 000)
            -- info-ROU:     GET db
            -- info-IMPL:    V2.0->
            -- info-VERCTRL: -
            SYNTAX        Unsigned32
            ACCESS        read-only
            STATUS        mandatory
            DESCRIPTION
                 " The upstream peak cell rate in bit/sec. "
            ::= { xldv20VplTpEntry 5 }

         xldv20VplPeakCellRateDownstream OBJECT-TYPE
            -- info-VALUE:   0..2147483647 (default: 2 000 000)
            -- info-ROU:     GET db
            -- info-IMPL:    V2.0->
            -- info-VERCTRL: -
            SYNTAX        Unsigned32
            ACCESS        read-only
            STATUS        mandatory
            DESCRIPTION
                 " The downstream peak cell rate in bit/sec. "
            ::= { xldv20VplTpEntry 6 }

         xldv20VplCellDelayVariationToleranceUpstream OBJECT-TYPE
            -- info-VALUE:   2..200000 (default: 3000 )
            -- info-ROU:     GET db
            -- info-IMPL:    V2.0->
            -- info-VERCTRL: -
            SYNTAX        INTEGER(2..200000)
            ACCESS        read-only
            STATUS        mandatory
            DESCRIPTION
                 " The cell delay variation (in micro seconds). "
            ::= { xldv20VplTpEntry 7 }

         xldv20VplCellDelayVariationToleranceDownstream OBJECT-TYPE
            -- info-VALUE:   2..200000 (default: 3000 )
            -- info-ROU:     GET db
            -- info-IMPL:    V2.0->
            -- info-VERCTRL: -
            SYNTAX        INTEGER(2..200000)
            ACCESS        read-only
            STATUS        mandatory
            DESCRIPTION
                 " The cell delay variation (in micro seconds). "
            ::= { xldv20VplTpEntry 8 }

         xldv20VplTrafficType OBJECT-TYPE
            -- info-VALUE:   cbr, ubr, nrtVbr
            -- info-VALUE:   rtVbr (default: ubr)
            -- info-ROU:     GET db
            -- info-IMPL:    V2.0->
            -- info-VERCTRL: -
            SYNTAX        Xldv20TrafficType
            ACCESS        read-only
            STATUS        mandatory
            DESCRIPTION
                 " The traffic type. "
            ::= { xldv20VplTpEntry 9 }

         xldv20VplTrafficDirection OBJECT-TYPE
            -- info-VALUE:   bidirectional, upstream, downstream (default: bidirectional)
            -- info-ROU:     GET db
            -- info-IMPL:    V2.0->
            -- info-VERCTRL: -
            SYNTAX        Xldv20TrafficDirection
            ACCESS        read-only
            STATUS        mandatory
            DESCRIPTION
                 " The traffic direction. "
            ::= { xldv20VplTpEntry 10 }

         xldv20VplConnectivityPointer OBJECT-TYPE
            -- info-VALUE:   0..65535
            -- info-ROU:     GET db
            -- info-IMPL:    V2.0->
            -- info-VERCTRL: -
            SYNTAX        Unsigned16
            ACCESS        read-only
            STATUS        mandatory
            DESCRIPTION
                 " This attribute serves as a pointer to the instance of the
                   VPL termination point managed entity instance (in the ATM
                   NE) it is cross connected to. "
            ::= { xldv20VplTpEntry 11 }

         xldv20VplLineIndex OBJECT-TYPE
            -- info-VALUE:   0..65535
            -- info-ROU:     GET db
            -- info-IMPL:    V2.0->
            -- info-VERCTRL: -
            SYNTAX        Unsigned16
            ACCESS        read-only
            STATUS        mandatory
            DESCRIPTION
                 " This value identifies the belonging line. "
            ::= { xldv20VplTpEntry 12 }

         xldv20VplSegmentEndPoint    OBJECT-TYPE
            -- info-VALUE:   yes(1)..no (2)
            -- info-ROU:     GET db
            -- info-IMPL:    V2.0->
            -- info-VERCTRL: -
            SYNTAX        INTEGER { yes(1), 
                                    no (2)    }
            ACCESS        read-only
            STATUS        mandatory
            DESCRIPTION
                 "  This value specifies whether the VplTp is 
                    a segment endpoint (yes) or a connecting point (no). "
            ::= { xldv20VplTpEntry 13 }

         xldv20VplSustainableCellRateUpstream OBJECT-TYPE
            -- info-VALUE:   0..2147483647 (default: 100 000)
            -- info-ROU:     GET db
            -- info-IMPL:    V2.0->
            -- info-VERCTRL: -
            SYNTAX        Unsigned32
            ACCESS        read-only
            STATUS        mandatory
            DESCRIPTION
                 "  The sustainable upstream cell rate in bits/sec 
                    for nrtVbr traffic. "
            ::= { xldv20VplTpEntry  14 }

         xldv20VplSustainableCellRateDownstream OBJECT-TYPE
            -- info-VALUE:   0..2147483647 (default: 1 Mega)
            -- info-ROU:     GET db
            -- info-IMPL:    V2.0->
            -- info-VERCTRL: -
            SYNTAX        Unsigned32
            ACCESS        read-only
            STATUS        mandatory
            DESCRIPTION
                 "  The sustainable downstream cell rate in bits/sec 
                    for nrtVbr traffic. "
            ::= { xldv20VplTpEntry  15}

         xldv20VplMaximumBurstSizeUpstream OBJECT-TYPE
            -- info-VALUE:   0..1500 (default: 32)
            -- info-ROU:     GET db
            -- info-IMPL:    V2.0->
            -- info-VERCTRL: -
            SYNTAX        INTEGER(0..1500)
            ACCESS        read-only
            STATUS        mandatory
            DESCRIPTION
                 "  The maximum upstream burst size tolerance in cells 
                    for nrtVbr traffic. "
            ::= { xldv20VplTpEntry  16 }

         xldv20VplMaximumBurstSizeDownstream OBJECT-TYPE
            -- info-VALUE:   0..1500 (default: 32)
            -- info-ROU:     GET db
            -- info-IMPL:    V2.0->
            -- info-VERCTRL: -
            SYNTAX        INTEGER(0..1500)
            ACCESS        read-only
            STATUS        mandatory
            DESCRIPTION
                 "  The maximum downstream burst size tolerance in cells 
                    for nrtVbr traffic. "
            ::= { xldv20VplTpEntry  17 }

         xldv20VplAlarmSeverityIndex OBJECT-TYPE  -- continuity check
            -- info-VALUE:   1..40 (Default is 1)
            -- info-ROU:     GET db SET db
            -- info-IMPL:    V2.0->
            -- info-VERCTRL: -
            SYNTAX        Xldv20AlmSevProfileIndex
            ACCESS        read-write
            STATUS        mandatory
            DESCRIPTION
                 " It is a pointer to the instance of the alarm severity
                   assignment profile managed entity that contains the severity
                   assignments for the alarms reported by this managed entity.
		   "
            ::= { xldv20VplTpEntry 18 }

         xldv20VplAlarmFilteringIndex OBJECT-TYPE
            -- info-VALUE:   1..40
            -- info-ROU:     GET db
            -- info-IMPL:    V2.x
            -- info-VERCTRL: -
            SYNTAX        Xldv20AlmFiltProfileIndex
            ACCESS        not-accessible
            STATUS        mandatory
            DESCRIPTION
                 " It is a pointer to the instance of the alarm filtering
                   assignment profile managed entity that contains the filtering
                   assignments for the alarms reported by this managed entity.
                   (Not implemented) "
            ::= { xldv20VplTpEntry 19 }

            xldv20VplCvpIndexSegment OBJECT-TYPE
            -- info-VALUE:   0..2000
            -- info-VALUE:   Default 0 (COC not enabled)
            -- info-ROU:     GET db
            -- info-IMPL:    V2.0->
            -- info-VERCTRL: -
            SYNTAX        INTEGER (0..2000)
            ACCESS        read-only
            STATUS        mandatory
            DESCRIPTION
                 "  The index of of the related entry in the ContinuityCheckVpTable.
                 The entry is created when the COC is enabled (via command or 
                 during cross connect creation). "
            ::= { xldv20VplTpEntry  20 }

         xldv20VplIndex OBJECT-TYPE
            -- info-VALUE:   1..4000
            -- info-ROU:     GET db
            -- info-IMPL:    V2.0->
            -- info-VERCTRL: -
            SYNTAX        INTEGER (1..4000)
            ACCESS        read-only
            STATUS        mandatory
            DESCRIPTION
                 " The Index of this table. "
            ::= { xldv20VplTpEntry 21 }

         xldv20VplLOCAlarm OBJECT-TYPE
            -- info-VALUE:   noAlarm(1), upstreamAlarm(2),
            -- info-VALUE:   downstreamAlarm(3), upAndDownstreamAlarm(4)
            -- info-ROU:     GET db
            -- info-IMPL:    V2.0->
            -- info-VERCTRL: -
            SYNTAX        Xldv20TpAlarmState
            ACCESS        read-only
            STATUS        mandatory
            DESCRIPTION
                 " Indicates an LOC alarm and its direction. "
            ::= { xldv20VplTpEntry 22 }

         xldv20VplVbrCDVTUpstream OBJECT-TYPE
            -- info-VALUE:   2..504000000 (default: 3000 )
            -- info-ROU:     GET db
            -- info-IMPL:    V2.0->
            -- info-VERCTRL: -
            SYNTAX        INTEGER(2..504000000)
            ACCESS        read-only
            STATUS        mandatory
            DESCRIPTION
                 " The cell delay variation (in micro seconds)
                   for VBR traffic in upstream direction of the VP cross connect. "
            ::= { xldv20VplTpEntry 23 }

         xldv20VplVbrCDVTDownstream OBJECT-TYPE
            -- info-VALUE:   2..504000000 (default: 3000 )
            -- info-ROU:     GET db
            -- info-IMPL:    V2.0->
            -- info-VERCTRL: -
            SYNTAX        INTEGER(2..504000000)
            ACCESS        read-only
            STATUS        mandatory
            DESCRIPTION
                 " The cell delay variation (in micro seconds)
                   for VBR traffic in downstream direction of the VP cross connect. "
            ::= { xldv20VplTpEntry 24 }

         -- --------------------------------------------------------------
         --                        VPC TP Table
         -- --------------------------------------------------------------

         xldv20VpcTpTable OBJECT-TYPE
            -- info-IMPL:    V2.0->
            -- info-VERCTRL: -
            SYNTAX        SEQUENCE OF Xldv20VpcTpEntry
            ACCESS        not-accessible
            STATUS        mandatory
            DESCRIPTION
                 " This table contains the entries for VPC termination points. "
            --DEFAULT test-function-async     fsnVpcEntryTest
            --DEFAULT next-function-async     fsnVpcEntryNext
            --DEFAULT set-function-async      fsnVpcEntrySet
            --DEFAULT get-function-async      fsnVpcEntryGet
            ::= { xldv20CallP 4 }

         xldv20VpcTpEntry OBJECT-TYPE
            -- info-IMPL:    V2.0->
            -- info-VERCTRL: -
            SYNTAX        Xldv20VpcTpEntry
            ACCESS        not-accessible
            STATUS        mandatory
            DESCRIPTION
                   "Each entry represents the point in the switch
                   where the VPC and its associated overhead (F4 OAM cells) are 
                   terminated or originated.
                   Instances of this managed entity may be created automatically
                   by the ATM NE when VP or VC cross connects are created at
                   at an Ethernet port. Or they are created by command.
                   Similarly instances of this managed entity may be deleted
                   automatically by the ATM NE or as a result of an ATM Cross
                   Connect release request.
                   Notifications : 
                   xldv20TrRDI.
                   xldv20TrAIS alarms when fault is detected or cleared.
                   xldv20TrStateChangeOper. "
            INDEX         { xldv20VpcIndex }
            ::= { xldv20VpcTpTable 1 }

         Xldv20VpcTpEntry ::=
            SEQUENCE { xldv20VpcOperationalState              Xldv20OperState,
                       xldv20VpcVpiValue                      INTEGER,
                       xldv20VpcHwUnitIndex                   Unsigned16,
                       xldv20VpcIfIndex                       Unsigned16,
                       xldv20VpcPeakCellRateUpstream          Unsigned32,
                       xldv20VpcPeakCellRateDownstream        Unsigned32,
                       xldv20VpcCellDelayVariationToleranceUpstream  INTEGER,
                       xldv20VpcCellDelayVariationToleranceDownstream  INTEGER,
                       xldv20VpcTrafficType                   Xldv20TrafficType,
                       xldv20VpcTrafficDirection              Xldv20TrafficDirection,
                       xldv20VpcLineIndex                     Unsigned16,
                       xldv20VpcSegmentEndPoint               INTEGER,
                       xldv20VpcSustainableCellRateUpstream   Unsigned32,
                       xldv20VpcSustainableCellRateDownstream Unsigned32,
                       xldv20VpcMaximumBurstSizeUpstream      INTEGER,
                       xldv20VpcMaximumBurstSizeDownstream    INTEGER,
                       xldv20VpcAlarmSeverityIndex            Xldv20AlmSevProfileIndex,
                       xldv20VpcAlarmFilteringIndex           Xldv20AlmFiltProfileIndex,
                       xldv20VpcCvpIndexSegment               INTEGER,    -- continuity check
                       xldv20VpcCvpIndexEndToEnd              INTEGER,    -- continuity check
                       xldv20VpcIndex                         INTEGER,
                       xldv20VpcAISAlarm                      Xldv20TpAlarmState,
                       xldv20VpcRDIAlarm                      Xldv20TpAlarmState,
                       xldv20VpcLOCAlarm                      Xldv20TpAlarmState,
                       xldv20VpcNumberOfVcs                   INTEGER,
                       xldv20VpcVbrCDVTUpstream               INTEGER,
                       xldv20VpcVbrCDVTDownstream             INTEGER,
                       xldv20VpcEmSpecific                    Unsigned16,
                       xldv20VpcEthVpcIndex                   INTEGER,   -- new MR 2525
                       xldv20VpcAtmfVplIndex                  INTEGER    -- new MR 2525
                       }

         xldv20VpcOperationalState OBJECT-TYPE
            -- info-VALUE:   enabled(1)..disabled(2)
            -- info-ROU:     GET db  SET db 
            -- info-IMPL:    V2.0->
            -- info-VERCTRL: -
            SYNTAX        Xldv20OperState
            ACCESS        read-only
            STATUS        mandatory
            DESCRIPTION
                 " The operational state identifies whether or not the VpcTp
		 is capable of performing its normal functions. "
            ::= { xldv20VpcTpEntry 1 }

         xldv20VpcVpiValue OBJECT-TYPE
            -- info-VALUE:   0..4095
            -- info-ROU:     GET db
            -- info-IMPL:    V2.0->
            -- info-VERCTRL: -
            SYNTAX        INTEGER (0..4095)
            ACCESS        read-only
            STATUS        mandatory
            DESCRIPTION
                 " Identifies the VPI value associated with the
                   VP link being terminated. "
            ::= { xldv20VpcTpEntry 2 }

         xldv20VpcHwUnitIndex OBJECT-TYPE
            -- info-VALUE:   0..65535
            -- info-ROU:     GET db
            -- info-IMPL:    V2.0->
            -- info-VERCTRL: -
            SYNTAX        Unsigned16 
            ACCESS        read-only
            STATUS        mandatory
            DESCRIPTION
                 " The unique identifier for hardware units,
                   here the HWM sublayer (LU* or or SU or LI*). "
            ::= { xldv20VpcTpEntry 3 }

         xldv20VpcIfIndex OBJECT-TYPE
            -- info-VALUE:   0..65535
            -- info-ROU:     GET db
            -- info-IMPL:    V2.0->
            -- info-VERCTRL: -
            SYNTAX        Unsigned16
            ACCESS        read-only
            STATUS        mandatory
            DESCRIPTION
                  " The interface index of the connected PPTP.
		  For Vpc at LU the PPTP in the LU.
                  For Vpc at SU and LI the PPTP at the LI. "
            ::= { xldv20VpcTpEntry 4 }

         xldv20VpcPeakCellRateUpstream OBJECT-TYPE
            -- info-VALUE:   0..2147483647 (default: 192 000)
            -- info-ROU:     GET db
            -- info-IMPL:    V2.0->
            -- info-VERCTRL: -
            SYNTAX        Unsigned32
            ACCESS        read-only
            STATUS        mandatory
            DESCRIPTION
                 " The upstream peak cell rate
                   in bit/sec of the VP cross connect. "
            ::= { xldv20VpcTpEntry 5 }

         xldv20VpcPeakCellRateDownstream OBJECT-TYPE
            -- info-VALUE:   0..2147483647 (default: 2 000 000)
            -- info-ROU:     GET db
            -- info-IMPL:    V2.0->
            -- info-VERCTRL: -
            SYNTAX        Unsigned32
            ACCESS        read-only
            STATUS        mandatory
            DESCRIPTION
                 " The downstream peak cell rate
                   in bit/sec of the VP cross connect. 
                   "
            ::= { xldv20VpcTpEntry 6 }

         xldv20VpcCellDelayVariationToleranceUpstream OBJECT-TYPE
            -- info-VALUE:   2..200000 (default: 3000 )
            -- info-ROU:     GET db
            -- info-IMPL:    V2.0->
            -- info-VERCTRL: -
            SYNTAX        INTEGER(2..200000)
            ACCESS        read-only
            STATUS        mandatory
            DESCRIPTION
                 " The upstream cell delay variation (in micro seconds)
                   of the VpcTp . "
            ::= { xldv20VpcTpEntry 7 }

         xldv20VpcCellDelayVariationToleranceDownstream OBJECT-TYPE
            -- info-VALUE:   2..200000 (default: 3000 )
            -- info-ROU:     GET db
            -- info-IMPL:    V2.0->
            -- info-VERCTRL: -
            SYNTAX        INTEGER(2..200000)
            ACCESS        read-only
            STATUS        mandatory
            DESCRIPTION
                 " The downstream cell delay variation (in micro seconds)
                   of the VpcTp. "
            ::= { xldv20VpcTpEntry 8 }

         xldv20VpcTrafficType OBJECT-TYPE
            -- info-VALUE:   cbr, ubr, nrtVbr
            -- info-VALUE:   rtVbr (default: ubr)
            -- info-ROU:     GET db
            -- info-IMPL:    V2.0->
            -- info-VERCTRL: -
            SYNTAX        Xldv20TrafficType
            ACCESS        read-only
            STATUS        mandatory
            DESCRIPTION
                 " The traffic type. "
            ::= { xldv20VpcTpEntry 9 }

         xldv20VpcTrafficDirection OBJECT-TYPE
            -- info-VALUE:   bidirectional, upstream, downstream (default: bidirectional)
            -- info-ROU:     GET db
            -- info-IMPL:    V2.0->
            -- info-VERCTRL: -
            SYNTAX        Xldv20TrafficDirection
            ACCESS        read-only
            STATUS        mandatory
            DESCRIPTION
                 " The traffic direction. "
            ::= { xldv20VpcTpEntry 10 }

         xldv20VpcLineIndex OBJECT-TYPE
            -- info-VALUE:   0..65535
            -- info-ROU:     GET db
            -- info-IMPL:    V2.0->
            -- info-VERCTRL: -
            SYNTAX        Unsigned16
            ACCESS        read-only
            STATUS        mandatory
            DESCRIPTION
                 " The belonging line. "
            ::= { xldv20VpcTpEntry 11 }

         xldv20VpcSegmentEndPoint    OBJECT-TYPE
            -- info-VALUE:   yes(1)..no (2)
            -- info-ROU:     GET db
            -- info-IMPL:    V2.0->
            -- info-VERCTRL: -
            SYNTAX        INTEGER { yes(1), 
                                    no (2)    }
            ACCESS        read-only
            STATUS        mandatory
            DESCRIPTION
                 "  This value specifies whether the VpcTp is 
                    a segment endpoint (yes) or a connecting point (no). "
            ::= { xldv20VpcTpEntry 12 }

         xldv20VpcSustainableCellRateUpstream OBJECT-TYPE
            -- info-VALUE:   0..2147483647 (default: 100 000)
            -- info-ROU:     GET db
            -- info-IMPL:    V2.0->
            -- info-VERCTRL: -
            SYNTAX        Unsigned32
            ACCESS        read-only
            STATUS        mandatory
            DESCRIPTION
                 "  The sustainable upstream cell rate in bits/sec 
                    for nrtVbr traffic.  "
            ::= { xldv20VpcTpEntry  13 }

         xldv20VpcSustainableCellRateDownstream OBJECT-TYPE
            -- info-VALUE:   0..2147483647 (default: 100 000 )
            -- info-ROU:     GET db
            -- info-IMPL:    V2.0->
            -- info-VERCTRL: -
            SYNTAX        Unsigned32
            ACCESS        read-only
            STATUS        mandatory
            DESCRIPTION
                 "  The sustainable downstream cell rate in cells/sec 
                    for nrtVbr traffic.  "
            ::= { xldv20VpcTpEntry  14 }

         xldv20VpcMaximumBurstSizeUpstream OBJECT-TYPE
            -- info-VALUE:   0..1500 (default: 32)
            -- info-ROU:     GET db
            -- info-IMPL:    V2.0->
            -- info-VERCTRL: -
            SYNTAX        INTEGER(0..1500)
            ACCESS        read-only
            STATUS        mandatory
            DESCRIPTION
                 "  The maximum upstream burst size tolerance in cells 
                    for nrtVbr traffic.  "
            ::= { xldv20VpcTpEntry  15 }

         xldv20VpcMaximumBurstSizeDownstream OBJECT-TYPE
            -- info-VALUE:   0..1500 (default: 32)
            -- info-ROU:     GET db
            -- info-IMPL:    V2.0->
            -- info-VERCTRL: -
            SYNTAX        INTEGER(0..1500)
            ACCESS        read-only
            STATUS        mandatory
            DESCRIPTION
                 "  The maximum downstream burst size tolerance in cells
                    for nrtVbr traffic.  "
            ::= { xldv20VpcTpEntry  16 }

         xldv20VpcAlarmSeverityIndex OBJECT-TYPE  -- continuity check
            -- info-VALUE:   1..40
            -- info-VALUE:   Default is 1
            -- info-ROU:     GET db SET db
            -- info-IMPL:    V2.0->
            -- info-VERCTRL: -
            SYNTAX        Xldv20AlmSevProfileIndex
            ACCESS        read-write
            STATUS        mandatory
            DESCRIPTION
                 " It is a pointer to the instance of the alarm severity
                   assignment profile managed entity that contains the severity
                   assignments for the alarms reported by this managed entity.  "
            ::= { xldv20VpcTpEntry 17 }

         xldv20VpcAlarmFilteringIndex OBJECT-TYPE
            -- info-VALUE:   1..40
            -- info-ROU:     GET db
            -- info-IMPL:    V2.x
            -- info-VERCTRL: -
            SYNTAX        Xldv20AlmFiltProfileIndex
            ACCESS        not-accessible
            STATUS        mandatory
            DESCRIPTION
                 " It is a pointer to the instance of the alarm filtering
                   assignment profile managed entity that contains the filtering
                   assignments for the alarms reported by this managed entity.
                   (Not implemented) "
            ::= { xldv20VpcTpEntry 18 }

            xldv20VpcCvpIndexSegment OBJECT-TYPE
            -- info-VALUE:   0..2000   
            -- info-VALUE:   Default 0 (COC not enabled)
            -- info-ROU:     GET db
            -- info-IMPL:    V2.0->
            -- info-VERCTRL: -
            SYNTAX        INTEGER (0..2000)
            ACCESS        read-only
            STATUS        mandatory
            DESCRIPTION
                 "  The index of related entry in ContinuityCheckVpcTpTable
                 concerning an enabled continuity check on segment level.  "
            ::= { xldv20VpcTpEntry  19 }

            xldv20VpcCvpIndexEndToEnd OBJECT-TYPE
            -- info-VALUE:   0..2000
            -- info-VALUE:   Default 0 (COC not enabled)
            -- info-ROU:     GET db
            -- info-IMPL:    V2.0->
            -- info-VERCTRL: -
            SYNTAX        INTEGER (0..2000)
            ACCESS        read-only
            STATUS        mandatory
            DESCRIPTION
                 "  The index of related entry in ContinuityCheckVpcTpTable
                 concerning a enabled endToEnd continuity check. "
            ::= { xldv20VpcTpEntry  20 }

         xldv20VpcIndex OBJECT-TYPE
            -- info-VALUE:   1..2000
            -- info-ROU:     GET db
            -- info-IMPL:    V2.0->
            -- info-VERCTRL: -
            SYNTAX        INTEGER (1..2000)
            ACCESS        read-only
            STATUS        mandatory
            DESCRIPTION
                 " The Index of this table. "
            ::= { xldv20VpcTpEntry 21 }

         xldv20VpcAISAlarm OBJECT-TYPE
            -- info-VALUE:   noAlarm(1), upstreamAlarm(2),
            -- info-VALUE:   downstreamAlarm(3), upAndDownstreamAlarm(4)
            -- info-ROU:     GET db
            -- info-IMPL:    V2.0->
            -- info-VERCTRL: -
            SYNTAX        Xldv20TpAlarmState
            ACCESS        read-only
            STATUS        mandatory
            DESCRIPTION
                 " Indicates an AIS alarm and its direction. "
            ::= { xldv20VpcTpEntry 22 }

         xldv20VpcRDIAlarm OBJECT-TYPE
            -- info-VALUE:   noAlarm(1), upstreamAlarm(2),
            -- info-VALUE:   downstreamAlarm(3), upAndDownstreamAlarm(4)
            -- info-ROU:     GET db
            -- info-IMPL:    V2.0->
            -- info-VERCTRL: -
            SYNTAX        Xldv20TpAlarmState
            ACCESS        read-only
            STATUS        mandatory
            DESCRIPTION
                 " Indicates an RDI alarm and its direction.  "
            ::= { xldv20VpcTpEntry 23 }
         
         xldv20VpcLOCAlarm OBJECT-TYPE
            -- info-VALUE:   noAlarm(1), upstreamAlarm(2),
            -- info-VALUE:   downstreamAlarm(3), upAndDownstreamAlarm(4)
            -- info-ROU:     GET db
            -- info-IMPL:    V2.0->
            -- info-VERCTRL: -
            SYNTAX        Xldv20TpAlarmState
            ACCESS        read-only
            STATUS        mandatory
            DESCRIPTION
                 " Indicates an LOC alarm and its direction. "
            ::= { xldv20VpcTpEntry 24 }

         xldv20VpcNumberOfVcs OBJECT-TYPE
            -- info-VALUE:   1..3469
            -- info-ROU:     GET db
            -- info-IMPL:    V2.0->
            -- info-VERCTRL: -
            SYNTAX        INTEGER (1..3469)
            ACCESS        read-only
            STATUS        mandatory
            DESCRIPTION
                 " The number of VCs which are created within the VpcTp.
		 The range of VCI values : 32 plus this number - 1."
            ::= { xldv20VpcTpEntry 25 }

         xldv20VpcVbrCDVTUpstream OBJECT-TYPE
            -- info-VALUE:   2..504000000 (default: 3000 )
            -- info-ROU:     GET db
            -- info-IMPL:    V2.0->
            -- info-VERCTRL: -
            SYNTAX        INTEGER(2..504000000)
            ACCESS        read-only
            STATUS        mandatory
            DESCRIPTION
                 " The cell delay variation (in micro seconds)
                   for VBR traffic in upstream direction of the VpcTp.  "
            ::= { xldv20VpcTpEntry 26 }

         xldv20VpcVbrCDVTDownstream OBJECT-TYPE
            -- info-VALUE:   2..504000000 (default: 3000 )
            -- info-ROU:     GET db
            -- info-IMPL:    V2.0->
            -- info-VERCTRL: -
            SYNTAX        INTEGER(2..504000000)
            ACCESS        read-only
            STATUS        mandatory
            DESCRIPTION
                 " The cell delay variation (in micro seconds)
                   for VBR traffic in downstream direction of the VpcTp. "
            ::= { xldv20VpcTpEntry 27 }

     xldv20VpcEmSpecific OBJECT-TYPE
        -- info-VALUE:   Default 0
        -- info-ROU:     GET db SET db
        -- info-IMPL:    V2.0->
        -- info-VERCTRL: -
        SYNTAX        Unsigned16
        ACCESS        read-write
        STATUS        mandatory
        DESCRIPTION
             " EM 45020 specific attribute.  "
           ::= { xldv20VpcTpEntry 28 }



     xldv20VpcEthVpcIndex  OBJECT-TYPE
            -- info-VALUE:   0..2000
            -- info-ROU:     GET db
            -- info-IMPL:    V2.0->
            -- info-VERCTRL: -
            SYNTAX        INTEGER (0..2000)
            ACCESS        read-only
            STATUS        mandatory
            DESCRIPTION
                 "  Used to address the corresponding entry 
                    in the VpcTpTable. Default is 0. "
           ::= { xldv20VpcTpEntry 29 }


      xldv20VpcAtmfVplIndex OBJECT-TYPE
            -- info-VALUE:   0..4000
            -- info-ROU:     GET db
            -- info-IMPL:    V2.0->
            -- info-VERCTRL: -
            SYNTAX        INTEGER (0..4000)
            ACCESS        read-only
            STATUS        mandatory
            DESCRIPTION
                 "  Used to address the corresponding entry 
                    in the VplTpTable. Default is 0. "
           ::= { xldv20VpcTpEntry 30 }


         -- --------------------------------------------------------------
         --                   VCC TP Table
         -- --------------------------------------------------------------

         xldv20VccTpTable OBJECT-TYPE
            -- info-IMPL:    V2.0->
            -- info-VERCTRL: -
            SYNTAX        SEQUENCE OF Xldv20VccTpEntry
            ACCESS        not-accessible
            STATUS        mandatory
            DESCRIPTION
                " VccTp table for VC termination points.
                  Entries are created for Ethernet NTs
                  when cross connects are created.
                  Entries are deleted with the cross connect. "
        --DEFAULT test-function-async     fsnVccEntryTest
        --DEFAULT next-function-async     fsnVccEntryNext
        --DEFAULT set-function-async      fsnVccEntrySet
        --DEFAULT get-function-async      fsnVccEntryGet
            ::= { xldv20CallP 5 }

         xldv20VccTpEntry OBJECT-TYPE
            -- info-IMPL:    V2.0->
            -- info-VERCTRL: -
            SYNTAX        Xldv20VccTpEntry
            ACCESS        not-accessible
            STATUS        mandatory
            DESCRIPTION
                   "Each entry represents the point in the switch
                   where the VCC and its associated overhead (F4 OAM cells) are 
                   terminated or originated.
                   Instances of this managed entity may be created automatically
                   by the ATM NE or as a result of an Vpl and Vcl cross connect request
		   at an Ethernet port.
                   Similarly instances of this managed entity may be deleted
                   automatically by the ATM NE as a result of an cross
                   connect deletion request.
                   Notifications : 
                     xldv20TrStateChangeOper. 
                     xldv20TrObjCreate.
                     xldv20TrObjDelete.
                     xldv20TrRDI.
                     xldv20TrAIS.
                     xldv20TrLOC alarms when fault is detected or cleared. "
            INDEX         { xldv20VccIndex }
            ::= { xldv20VccTpTable 1 }

         Xldv20VccTpEntry ::=
            SEQUENCE { xldv20VccOperationalState     Xldv20OperState,
                       xldv20VccVciValue             INTEGER,
                       xldv20VccVpcIndex             INTEGER,
                       xldv20VccHwUnitIndex          Unsigned16,
                       xldv20VccAlarmSeverityIndex   Xldv20AlmSevProfileIndex,
                       xldv20VccAlarmFilteringIndex  Xldv20AlmFiltProfileIndex,
                       xldv20VccLineIndex            Unsigned16,
                       xldv20VccIndex                INTEGER,
                       xldv20VccAISAlarm             Xldv20TpAlarmState,
                       xldv20VccRDIAlarm             Xldv20TpAlarmState,
                       xldv20VccLOCAlarm             Xldv20TpAlarmState,
                       xldv20VccCvcIndexSegment      Unsigned16,
                       xldv20VccCvcIndexEndToEnd     Unsigned16
                       }

     xldv20VccOperationalState OBJECT-TYPE
        -- info-VALUE:   enabled, disabled
        -- info-ROU:     GET db
        -- info-IMPL:    V2.0->
        -- info-VERCTRL: -
        SYNTAX        Xldv20OperState
        ACCESS        read-only
        STATUS        mandatory
        DESCRIPTION
             " The operational state identifies whether or not the VPL
               termination is capable of performing its normal functions
               (in-service or out-of-service). "
        ::= { xldv20VccTpEntry 1 }

         xldv20VccVciValue OBJECT-TYPE
            -- info-VALUE:   32..3500
            -- info-ROU:     GET db
            -- info-IMPL:    V2.0->
            -- info-VERCTRL: -
            SYNTAX        INTEGER (32..3500)
            ACCESS        read-only
            STATUS        mandatory
            DESCRIPTION
                 " This attribute identifies the VCI value associated with the
                   VC link being terminated. "
            ::= { xldv20VccTpEntry 2 }

         xldv20VccVpcIndex OBJECT-TYPE
            -- info-VALUE:   1..2000
            -- info-ROU:     GET db
            -- info-IMPL:    V2.0->
            -- info-VERCTRL: -
            SYNTAX        INTEGER (1..2000)
            ACCESS        read-only
            STATUS        mandatory
            DESCRIPTION
                 " Index of the related VpcTp. "
            ::= { xldv20VccTpEntry 3 }

     xldv20VccHwUnitIndex OBJECT-TYPE
        -- info-VALUE:   0..65535
        -- info-VALUE:   -
        -- info-ROU:     GET db
        -- info-IMPL:    V2.0->
        -- info-VERCTRL: -
        SYNTAX        Unsigned16
        ACCESS        read-only
        STATUS        mandatory
        DESCRIPTION
             " HwUnitIndex of the dependent PIU (LI). "
        ::= { xldv20VccTpEntry 4 }

     xldv20VccAlarmSeverityIndex OBJECT-TYPE
        -- info-VALUE:   1..40
        -- info-VALUE:   Default is 1
        -- info-ROU:     GET db SET db
        -- info-IMPL:    V2.0->
        -- info-VERCTRL: -
        SYNTAX        Xldv20AlmSevProfileIndex
        ACCESS        read-write
        STATUS        mandatory
        DESCRIPTION
             " It is a pointer to the instance of the alarm severity
               assignment profile managed entity that contains the severity
               assignments for the alarms reported by this managed entity.  "
        ::= { xldv20VccTpEntry 5 }

     xldv20VccAlarmFilteringIndex OBJECT-TYPE
        -- info-VALUE:   1..40
        -- info-ROU:     GET db
        -- info-IMPL:    V2.x
        -- info-VERCTRL: -
        SYNTAX        Xldv20AlmFiltProfileIndex
        ACCESS        read-only
        STATUS        mandatory
        DESCRIPTION
             " It is a pointer to the instance of the alarm filtering
               assignment profile managed entity that contains the filtering
               assignments for the alarms reported by this managed entity.
               (Not supported yet). "
        ::= { xldv20VccTpEntry 6 }

     xldv20VccLineIndex OBJECT-TYPE
        -- info-VALUE:   -
        -- info-ROU:     GET db
        -- info-IMPL:    V2.0->
        -- info-VERCTRL: -
        SYNTAX        Unsigned16
        ACCESS        read-only
        STATUS        mandatory
        DESCRIPTION
             " This value identifies the belonging line . "
        ::= { xldv20VccTpEntry 7 }

         xldv20VccIndex OBJECT-TYPE
            -- info-VALUE:   1..1000
            -- info-ROU:     GET db SET db
            -- info-IMPL:    V2.0->
            -- info-VERCTRL: -
            SYNTAX        INTEGER (1..1000)
            ACCESS        read-only
            STATUS        mandatory
            DESCRIPTION
                 " A unique value to identify an entry in the VCC TP table. "
            ::= { xldv20VccTpEntry 8 }

         xldv20VccAISAlarm OBJECT-TYPE
            -- info-VALUE:   noAlarm(1), upstreamAlarm(2),
            -- info-VALUE:   downstreamAlarm(3), upAndDownstreamAlarm(4)
            -- info-ROU:     GET db
            -- info-IMPL:    V2.0->
            -- info-VERCTRL: -
            SYNTAX        Xldv20TpAlarmState
            ACCESS        read-only
            STATUS        mandatory
            DESCRIPTION
                 " Indicates an AIS alarm and its direction. "
            ::= { xldv20VccTpEntry 9 }

         xldv20VccRDIAlarm OBJECT-TYPE
            -- info-VALUE:   noAlarm(1), upstreamAlarm(2),
            -- info-VALUE:   downstreamAlarm(3), upAndDownstreamAlarm(4)
            -- info-ROU:     GET db
            -- info-IMPL:    V2.0->
            -- info-VERCTRL: -
            SYNTAX        Xldv20TpAlarmState
            ACCESS        read-only
            STATUS        mandatory
            DESCRIPTION
                 " Indicates an RDI alarm and its direction. "
            ::= { xldv20VccTpEntry 10 }

         xldv20VccLOCAlarm OBJECT-TYPE
            -- info-VALUE:   noAlarm(1), upstreamAlarm(2),
            -- info-VALUE:   downstreamAlarm(3), upAndDownstreamAlarm(4)
            -- info-ROU:     GET db
            -- info-IMPL:    V2.0->
            -- info-VERCTRL: -
            SYNTAX        Xldv20TpAlarmState
            ACCESS        read-only
            STATUS        mandatory
            DESCRIPTION
                 " Indicates an LOC alarm and its direction. "
            ::= { xldv20VccTpEntry 11 }

            xldv20VccCvcIndexSegment OBJECT-TYPE
            -- info-VALUE:   0..65535 
            -- info-VALUE:   Default 0 (not enabled)
            -- info-ROU:     GET db
            -- info-IMPL:    V2.0->
            -- info-VERCTRL: -
            SYNTAX        Unsigned16
            ACCESS        read-only
            STATUS        mandatory
            DESCRIPTION
                 "  The index of the related entry in the xldv20ContinuityCheckVcTable
                 for an enabled continuity check on segment level.  "
            ::= { xldv20VccTpEntry 12 }

            xldv20VccCvcIndexEndToEnd OBJECT-TYPE
            -- info-VALUE:   0..65535
            -- info-VALUE:   Default 0 (not enabled)
            -- info-ROU:     GET db
            -- info-IMPL:    V2.0->
            -- info-VERCTRL: -
            SYNTAX        Unsigned16
            ACCESS        read-only
            STATUS        mandatory
            DESCRIPTION
                 "  The index of the related entry in the xldv20ContinuityCheckVcTable
                 for an enabled endToEnd continuity check. "
            ::= { xldv20VccTpEntry  13 }
         
         -- --------------------------------------------------------------
         --                VCX Table for Vcl cross connections
         -- --------------------------------------------------------------

         xldv20VcCrossConnectTable OBJECT-TYPE
            -- info-IMPL:    V2.0->
            -- info-VERCTRL: -
            SYNTAX        SEQUENCE OF Xldv20VcCrossConnectEntry
            ACCESS        not-accessible
            STATUS        mandatory
            DESCRIPTION
                 " The VC cross connect table for Virtual Channel
                    point-to-point cross connections. 
                   This managed entity is used to represent
                   the VC-cross-connect relationship between two termination
                   points.
                   Instances of this managed entity shall be automatically
                   created and deleted on VCX Connect and VCX Disconnect
		   actions . "
            --DEFAULT test-function-async     fsnVcxEntryTest
            --DEFAULT next-function-async     fsnVcxEntryNext
            --DEFAULT set-function-async      fsnVcxEntrySet
            --DEFAULT get-function-async      fsnVcxEntryGet
            ::= { xldv20CallP 6 }

         xldv20VcCrossConnectEntry OBJECT-TYPE
            -- info-IMPL:    V2.0->
            -- info-VERCTRL: -
            SYNTAX        Xldv20VcCrossConnectEntry
            ACCESS        not-accessible
            STATUS        mandatory
            DESCRIPTION
                 " An entry in the VC cross connect table.
                   Notifications : xldv20TrStateChangeOper. "
            INDEX         { xldv20VcxIndex }
            ::= { xldv20VcCrossConnectTable 1 }

         Xldv20VcCrossConnectEntry ::=
            SEQUENCE { xldv20VcxOperationalState   Xldv20OperState,
                       xldv20VcxTerminationPointA  INTEGER,
                       xldv20VcxTerminationPointZ  INTEGER,
                       xldv20VcxLineIndex          Unsigned16,
                       xldv20VcxEthVpcIndex        INTEGER,
                       xldv20VcxEthVccIndex        INTEGER,
                       xldv20VcxVpcNniIndex        Unsigned16,
                       xldv20VcxVpcUniIndex        Unsigned16,
                       xldv20VcxIndex              INTEGER,
                       xldv20VcxAlarmState         Xldv20CallpAlarmState,
                       xldv20VcxAdminState         Xldv20AdminState,
                       xldv20VcxAtmfVplIndex       INTEGER }

         xldv20VcxOperationalState OBJECT-TYPE
            -- info-VALUE:   enabled, disabled
            -- info-ROU:     GET db
            -- info-IMPL:    V2.0->
            -- info-VERCTRL: -
            SYNTAX        Xldv20OperState
            ACCESS        read-only
            STATUS        mandatory
            DESCRIPTION
                 " The Operational State of Vc cross connect. "
            ::= { xldv20VcCrossConnectEntry 1 }

         xldv20VcxTerminationPointA OBJECT-TYPE
            -- info-VALUE:   1..4096
            -- info-ROU:     GET db
            -- info-IMPL:    V2.0->
            -- info-VERCTRL: -
            SYNTAX        INTEGER (1..4096)
            ACCESS        read-only
            STATUS        mandatory
            DESCRIPTION
                 " Identifies the instance of the VCL termination point that represents
                   the VCL at the LE side. "
            ::= { xldv20VcCrossConnectEntry 2 }

         xldv20VcxTerminationPointZ OBJECT-TYPE
            -- info-VALUE:   1..4096
            -- info-ROU:     GET db
            -- info-IMPL:    V2.0->
            -- info-VERCTRL: -
            SYNTAX        INTEGER (1..4096)
            ACCESS        read-only
            STATUS        mandatory
            DESCRIPTION
                 " Identifies the instance of the VCL termination point that represents
                   the VCL at the NT side. "
            ::= { xldv20VcCrossConnectEntry 3 }

         xldv20VcxLineIndex OBJECT-TYPE
            -- info-VALUE:   -
            -- info-ROU:     GET db
            -- info-IMPL:    V2.0->
            -- info-VERCTRL: -
            SYNTAX        Unsigned16
            ACCESS        read-only
            STATUS        mandatory
            DESCRIPTION
                   " The belonging line index. "
            ::= { xldv20VcCrossConnectEntry 4 }

         xldv20VcxEthVpcIndex OBJECT-TYPE
            -- info-VALUE:   0..2000
            -- info-ROU:     GET db
            -- info-IMPL:    V2.0->
            -- info-VERCTRL: -
            SYNTAX        INTEGER (0..2000)
            ACCESS        read-only
            STATUS        mandatory
            DESCRIPTION
                 "  Used to address the corresponding entry 
                    in the VpcTpTable. Default is 0. "
            ::= { xldv20VcCrossConnectEntry 5 }

         xldv20VcxEthVccIndex OBJECT-TYPE
            -- info-VALUE:   0..1000
            -- info-ROU:     GET db
            -- info-IMPL:    V2.0->
            -- info-VERCTRL: -
            SYNTAX        INTEGER (0..1000)
            ACCESS        read-only
            STATUS        mandatory
            DESCRIPTION
                 "  Used to address the corresponding entry 
                    in the VccTP Table. Default is 0. "
            ::= { xldv20VcCrossConnectEntry 6 }

         xldv20VcxVpcNniIndex OBJECT-TYPE
            -- info-VALUE:   -
            -- info-ROU:     GET db
            -- info-IMPL:    V2.0->
            -- info-VERCTRL: -
            SYNTAX        Unsigned16
            ACCESS        read-only
            STATUS        mandatory
            DESCRIPTION
                 "  Used to address the corresponding entry at NNI
                    in the VpcTpTable. Default is 0. "
            ::= { xldv20VcCrossConnectEntry 7 }

         xldv20VcxVpcUniIndex OBJECT-TYPE
            -- info-VALUE:   -
            -- info-ROU:     GET db
            -- info-IMPL:    V2.0->
            -- info-VERCTRL: -
            SYNTAX        Unsigned16
            ACCESS        read-only
            STATUS        mandatory
            DESCRIPTION
                 "  Used to address the corresponding entry  at UNI
                    in the VpcTP Table. Default is 0. "
            ::= { xldv20VcCrossConnectEntry 8 }

         xldv20VcxIndex   OBJECT-TYPE
            -- info-VALUE:   1..2000
            -- info-ROU:     GET db
            -- info-IMPL:    V2.0->
            -- info-VERCTRL: -
            SYNTAX        INTEGER (1..2000)
            ACCESS        read-only
            STATUS        mandatory
            DESCRIPTION
                 "  Index of VcCrossConnectTable. "
            ::= { xldv20VcCrossConnectEntry 9 }

         xldv20VcxAlarmState OBJECT-TYPE
            -- info-VALUE:   noAlarm(1), alarmPresent(2)
            -- info-ROU:     GET db
            -- info-IMPL:    V2.0->
            -- info-VERCTRL: -
            SYNTAX        Xldv20CallpAlarmState
            ACCESS        read-only
            STATUS        mandatory
            DESCRIPTION
                 " This attribute indicates whether for the cross connect
                   an alarm is present or not. "
            ::= { xldv20VcCrossConnectEntry 10 }

         xldv20VcxAdminState OBJECT-TYPE
            -- info-VALUE:   unlocked(1), locked(2)
            -- info-ROU:     GET db  SET cp 
            -- info-IMPL:    V2.0->
            -- info-VERCTRL: -
            SYNTAX        Xldv20AdminState
            ACCESS        read-write
            STATUS        mandatory
            DESCRIPTION
                 " This attribute is used to activate (unlock) and deactivate
                   (lock) the VCL cross connection. The cross connect is
                   removed within the ATM ASIC, the configuration data of the
                   cross connect are still available within the DSLAM . "
            ::= { xldv20VcCrossConnectEntry 11 }

         xldv20VcxAtmfVplIndex OBJECT-TYPE
            -- info-VALUE:   0..4000
            -- info-ROU:     GET db
            -- info-IMPL:    V2.0->
            -- info-VERCTRL: -
            SYNTAX        INTEGER (0..4000)
            ACCESS        read-only
            STATUS        mandatory
            DESCRIPTION
                 " For cross connects at the ATMF port of NT this value
                 identifies the belonging VplTp .
                 The value is the entry number in the xldv20VplTpTable.
                 For all other cross connects the value is always 0. "
            ::= { xldv20VcCrossConnectEntry 12 }


         -- --------------------------------------------------------------
         --                        VCL TP Table
         -- --------------------------------------------------------------

         xldv20VclTpTable OBJECT-TYPE
            -- info-IMPL:    V2.0->
            SYNTAX        SEQUENCE OF Xldv20VclTpEntry
            ACCESS        not-accessible
            STATUS        mandatory
            DESCRIPTION
                 " This table contains the entries for the VC links. "
            --DEFAULT test-function-async     fsnVclEntryTest
            --DEFAULT next-function-async     fsnVclEntryNext
            --DEFAULT set-function-async      fsnVclEntrySet
            --DEFAULT get-function-async      fsnVclEntryGet
            ::= { xldv20CallP 7 }

         xldv20VclTpEntry OBJECT-TYPE
            -- info-VALUE:   -
            -- info-ROU:     -
            -- info-IMPL:    V2.0->
            -- info-VERCTRL: -
            SYNTAX        Xldv20VclTpEntry
            ACCESS        not-accessible
            STATUS        mandatory
            DESCRIPTION
                 " The entries represent the termination of VCLs on an ATM NE.
                   An instance of the VC Cross Connection managed entity may be
                   used to relate two instances of the VCL Termination Point
                   managed entity (i.e. for point-to-point cross connection).
                   Instances of this managed entity may be created automatically
                   by the ATM NE or as a result of an VC cross connect request.
                   Similarly instances of this managed entity may be deleted
                   automatically by the ATM NE or as a result of an VC  Cross
                   Connect release request.
                   Notifications: xldv20TrStateChangeOper. "
            INDEX         { xldv20VclIndex }
            ::= { xldv20VclTpTable 1 }

         Xldv20VclTpEntry ::=
            SEQUENCE { xldv20VclOperationalState          Xldv20OperState,
                       xldv20VclVpiValue                  INTEGER,
                       xldv20VclVciValue                  INTEGER,
                       xldv20VclHwUnitIndex               Unsigned16,
                       xldv20VclIfIndex                   Unsigned16,
                       xldv20VclPeakCellRateUpstream      Unsigned32,
                       xldv20VclPeakCellRateDownstream    Unsigned32,
                       xldv20VclCellDelayVariationToleranceUpstream    INTEGER,
                       xldv20VclCellDelayVariationToleranceDownstream  INTEGER,
                       xldv20VclTrafficType               Xldv20TrafficType,
                       xldv20VclTrafficDirection          Xldv20TrafficDirection,
                       xldv20VclConnectivityPointer       Unsigned16,
                       xldv20VclLineIndex                 Unsigned16,
                       xldv20VclSegmentEndPoint           INTEGER,
                       xldv20VclSustainableCellRateUpstream   Unsigned32,
                       xldv20VclSustainableCellRateDownstream Unsigned32,
                       xldv20VclMaximumBurstSizeUpstream      INTEGER,
                       xldv20VclMaximumBurstSizeDownstream    INTEGER,
                       xldv20VclAlarmSeverityIndex            Xldv20AlmSevProfileIndex,
                       xldv20VclAlarmFilteringIndex           Xldv20AlmFiltProfileIndex,
                       xldv20VclCvcIndexSegment               Unsigned16, -- continuity check
                       xldv20VclIndex                         INTEGER,
                       xldv20VclLOCAlarm                  Xldv20TpAlarmState,
                       xldv20VclVpcIndex                      INTEGER,
                       xldv20VclVbrCDVTUpstream               INTEGER,
                       xldv20VclVbrCDVTDownstream             INTEGER
                       }

         xldv20VclOperationalState OBJECT-TYPE
            -- info-VALUE:   enabled, disabled
            -- info-ROU:     GET db
            -- info-IMPL:    V2.0->
            -- info-VERCTRL: -
            SYNTAX        Xldv20OperState
            ACCESS        read-only
            STATUS        mandatory
            DESCRIPTION
                 " The operational state of VclTp. "
            ::= { xldv20VclTpEntry 1 }

         xldv20VclVpiValue OBJECT-TYPE
            -- info-VALUE:   0..4095
            -- info-ROU:     GET db
            -- info-IMPL:    V2.0->
            -- info-VERCTRL: -
            SYNTAX        INTEGER (0..4095)
            ACCESS        read-only
            STATUS        mandatory
            DESCRIPTION
                 " The VPI value associated with the VC link being terminated. "
            ::= { xldv20VclTpEntry 2 }

         xldv20VclVciValue OBJECT-TYPE
            -- info-VALUE:   32..3500
            -- info-ROU:     GET db
            -- info-IMPL:    V2.0->
            -- info-VERCTRL: -
            SYNTAX        INTEGER (32..3500)
            ACCESS        read-only
            STATUS        mandatory
            DESCRIPTION
                 " The VCI value associated with the
                   VC link being terminated. "
            ::= { xldv20VclTpEntry 3 }

         xldv20VclHwUnitIndex OBJECT-TYPE
            -- info-VALUE:   0..65535
            -- info-ROU:     GET db
            -- info-IMPL:    V2.0->
            -- info-VERCTRL: -
            SYNTAX        Unsigned16 
            ACCESS        read-only
            STATUS        mandatory
            DESCRIPTION
                 "  The HwUnitIndex of the dependent HW unit.
                   Here the HWM sublayer: the SU for VclUni or the LU for
                   VclNni . "
            ::= { xldv20VclTpEntry 4 }

         xldv20VclIfIndex OBJECT-TYPE
            -- info-VALUE:   0..65535
            -- info-ROU:     GET db
            -- info-IMPL:    V2.0->
            -- info-VERCTRL: -
            SYNTAX        Unsigned16 
            ACCESS        read-only
            STATUS        mandatory
            DESCRIPTION
                 " The interface index of the connected PPTP.
		  It is the PPTP at the LU for VclUni.
		  The PPTP at the LI for VclNni. "
            ::= { xldv20VclTpEntry 5 }

         xldv20VclPeakCellRateUpstream OBJECT-TYPE
            -- info-VALUE:   0..2147483647 ( default: 192 000 )
            -- info-ROU:     GET db
            -- info-IMPL:    V2.0->
            -- info-VERCTRL: -
            SYNTAX        Unsigned32
            ACCESS        read-only
            STATUS        mandatory
            DESCRIPTION
                 "  The upstream peak cell rate 
                    in bit/sec of the VC cross connect. "
            ::= { xldv20VclTpEntry 6 }

         xldv20VclPeakCellRateDownstream OBJECT-TYPE
            -- info-VALUE:   0..2147483647 (default: 2 000 000)
            -- info-ROU:     GET db
            -- info-IMPL:    V2.0->
            -- info-VERCTRL: -
            SYNTAX        Unsigned32
            ACCESS        read-only
            STATUS        mandatory
            DESCRIPTION
                 "  The downstream peak cell rate 
                    in bit/sec of the VC cross connect.
                    "
            ::= { xldv20VclTpEntry 7 }

         xldv20VclCellDelayVariationToleranceUpstream OBJECT-TYPE
            -- info-VALUE:   2..200000 (default: 3000 )
            -- info-ROU:     GET db
            -- info-IMPL:    V2.0->
            -- info-VERCTRL: -
            SYNTAX        INTEGER(2..200000)
            ACCESS        read-only
            STATUS        mandatory
            DESCRIPTION
                 "  The upstream cell delay variation (in micro seconds)
		 of the VC cross connect. "
            ::= { xldv20VclTpEntry 8 }

         xldv20VclCellDelayVariationToleranceDownstream OBJECT-TYPE
            -- info-VALUE:   2..200000 (default: 3000 )
            -- info-ROU:     GET db
            -- info-IMPL:    V2.0->
            -- info-VERCTRL: -
            SYNTAX        INTEGER(2..200000)
            ACCESS        read-only
            STATUS        mandatory
            DESCRIPTION
                 "  The downstream cell delay variation (in micro seconds)
		 of the VC cross connect. "
            ::= { xldv20VclTpEntry 9 }

         xldv20VclTrafficType OBJECT-TYPE
            -- info-VALUE:   cbr (default), ubr
            -- info-VALUE:   nrtVbr, rtVbr
            -- info-ROU:     GET db
            -- info-IMPL:    V2.0->
            -- info-VERCTRL: -
            SYNTAX        Xldv20TrafficType
            ACCESS        read-only
            STATUS        mandatory
            DESCRIPTION
                 " This attribute identifies the traffic type of the
                   VC cross connect.  "
            ::= { xldv20VclTpEntry 10 }

         xldv20VclTrafficDirection OBJECT-TYPE
            -- info-VALUE:   bidirectional (default), upstream, downstream
            -- info-ROU:     GET db
            -- info-IMPL:    V2.0->
            -- info-VERCTRL: -
            SYNTAX        Xldv20TrafficDirection
            ACCESS        read-only
            STATUS        mandatory
            DESCRIPTION
                 " The traffic direction. "
            ::= { xldv20VclTpEntry 11 }

         xldv20VclConnectivityPointer OBJECT-TYPE
            -- info-VALUE:   -
            -- info-ROU:     GET db
            -- info-IMPL:    V2.0->
            -- info-VERCTRL: -
            SYNTAX        Unsigned16
            ACCESS        read-only
            STATUS        mandatory
            DESCRIPTION
                 " A pointer to the instance of VclTp 
                  it is cross connected to. "
            ::= { xldv20VclTpEntry 12 }

         xldv20VclLineIndex OBJECT-TYPE
            -- info-VALUE:   -
            -- info-ROU:     GET db
            -- info-IMPL:    V2.0->
            -- info-VERCTRL: -
            SYNTAX        Unsigned16
            ACCESS        read-only
            STATUS        mandatory
            DESCRIPTION
                 " Identifies the belonging line. "
            ::= { xldv20VclTpEntry 13 }

         xldv20VclSegmentEndPoint    OBJECT-TYPE
            -- info-VALUE:   1..2 
            -- info-ROU:     GET db
            -- info-IMPL:    V2.0->
            -- info-VERCTRL: -
            SYNTAX        INTEGER { yes(1), 
                                    no (2)    }
            ACCESS        read-only
            STATUS        mandatory
            DESCRIPTION
                 "  Specifies whether the VclTp is 
                    a segment endpoint (yes) or a connecting point (no). "
            ::= { xldv20VclTpEntry 14 }

         xldv20VclSustainableCellRateUpstream OBJECT-TYPE
            -- info-VALUE:   0..2147483647 (default: 100 000)
            -- info-ROU:     GET db
            -- info-IMPL:    V2.0->
            -- info-VERCTRL: -
            SYNTAX        Unsigned32
            ACCESS        read-only
            STATUS        mandatory
            DESCRIPTION
                 "  The sustainable upstream cell rate in bits/sec 
                    for nrtVbr traffic.
                    "
            ::= { xldv20VclTpEntry  15 }

         xldv20VclSustainableCellRateDownstream OBJECT-TYPE
            -- info-VALUE:   0..2147483647 (default: 100 000 )
            -- info-ROU:     GET db
            -- info-IMPL:    V2.0->
            -- info-VERCTRL: -
            SYNTAX        Unsigned32
            ACCESS        read-only
            STATUS        mandatory
            DESCRIPTION
                 "  The sustainable downstream cell rate in bits/sec 
                    for nrtVbr traffic.
                    "
            ::= { xldv20VclTpEntry  16 }

         xldv20VclMaximumBurstSizeUpstream  OBJECT-TYPE
            -- info-VALUE:   0..1500 (default: 32)
            -- info-ROU:     GET db
            -- info-IMPL:    V2.0->
            -- info-VERCTRL: -
            SYNTAX        INTEGER(0..1500)
            ACCESS        read-only
            STATUS        mandatory
            DESCRIPTION
                 "  The maximum upstream burst size tolerance in cells
                    for nrtVbr traffic.
                    "
            ::= { xldv20VclTpEntry  17 }

         xldv20VclMaximumBurstSizeDownstream  OBJECT-TYPE
            -- info-VALUE:   0..1500 (default: 32)
            -- info-ROU:     GET db
            -- info-IMPL:    V2.0->
            -- info-VERCTRL: -
            SYNTAX        INTEGER(0..1500)
            ACCESS        read-only
            STATUS        mandatory
            DESCRIPTION
                 "  The maximum downstream burst size tolerance in cells
                    for nrtVbr traffic.
                    "
            ::= { xldv20VclTpEntry  18 }

         xldv20VclAlarmSeverityIndex OBJECT-TYPE
            -- info-VALUE:   1..40
            -- info-VALUE:   Default is 1
            -- info-ROU:     GET db SET db
            -- info-IMPL:    V2.0->
            -- info-VERCTRL: -
            SYNTAX        Xldv20AlmSevProfileIndex
            ACCESS        read-write
            STATUS        mandatory
            DESCRIPTION
                 " It is a pointer to the instance of the alarm severity
                   assignment profile managed entity that contains the severity
                   assignments for the alarms reported by this managed entity.
		   "
            ::= { xldv20VclTpEntry 19 }

         xldv20VclAlarmFilteringIndex OBJECT-TYPE
            -- info-VALUE:   1..40
            -- info-ROU:     GET db
            -- info-IMPL:    V2.x
            SYNTAX        Xldv20AlmFiltProfileIndex
            ACCESS        not-accessible
            STATUS        mandatory
            DESCRIPTION
                 " It is a pointer to the instance of the alarm filtering
                   assignment profile managed entity that contains the filtering
                   assignments for the alarms reported by this managed entity.
                   (Not implemented) "
            ::= { xldv20VclTpEntry 20 }

            xldv20VclCvcIndexSegment OBJECT-TYPE
            -- info-VALUE:   0..65535
            -- info-VALUE:   Default 0 (not enabled)
            -- info-ROU:     GET db
            -- info-IMPL:    V2.0->
            -- info-VERCTRL: -
            SYNTAX        Unsigned16
            ACCESS        read-only
            STATUS        mandatory
            DESCRIPTION
                 "  The index of iof the related entry in the 
                 xldv20ContinuityCheckVclTpTable. The entry is created when
                 the continuity check is enabled on segment level. "
            ::= { xldv20VclTpEntry  21 }

         xldv20VclIndex OBJECT-TYPE
            -- info-VALUE:   1..4000
            -- info-ROU:     GET db
            -- info-IMPL:    V2.0->
            -- info-VERCTRL: -
            SYNTAX        INTEGER (1..4000)
            ACCESS        read-only
            STATUS        mandatory
            DESCRIPTION
                 "  Index of this table. "
            ::= { xldv20VclTpEntry 22 }

         xldv20VclLOCAlarm OBJECT-TYPE
            -- info-VALUE:   noAlarm(1), upstreamAlarm(2),
            -- info-VALUE:   downstreamAlarm(3), upAndDownstreamAlarm(4)
            -- info-ROU:     GET db
            -- info-IMPL:    V2.0->
            -- info-VERCTRL: -
            SYNTAX        Xldv20TpAlarmState
            ACCESS        read-only
            STATUS        mandatory
            DESCRIPTION
                 " Indicates an LOC alarm and its direction. "
            ::= { xldv20VclTpEntry 23 }

         xldv20VclVpcIndex OBJECT-TYPE
            -- info-VALUE:   1..2000
            -- info-ROU:     GET db
            -- info-IMPL:    V2.0->
            -- info-VERCTRL: -
            SYNTAX        INTEGER (1..2000)
            ACCESS        read-only
            STATUS        mandatory
            DESCRIPTION
                 " A pointer to the belonging VpcTP in the VpcTp table. "
            ::= { xldv20VclTpEntry 24 }

         xldv20VclVbrCDVTUpstream OBJECT-TYPE
            -- info-VALUE:   2..504000000 (default: 3000 )
            -- info-ROU:     GET db
            -- info-IMPL:    V2.0->
            -- info-VERCTRL: -
            SYNTAX        INTEGER(2..504000000)
            ACCESS        read-only
            STATUS        mandatory
            DESCRIPTION
                 " The cell delay variation (in micro seconds)
                   for VBR traffic in upstream direction of the VclTp. "
            ::= { xldv20VclTpEntry 25 }

         xldv20VclVbrCDVTDownstream OBJECT-TYPE
            -- info-VALUE:   2..504000000 (default: 3000 )
            -- info-ROU:     GET db
            -- info-IMPL:    V2.0->
            -- info-VERCTRL: -
            SYNTAX        INTEGER(2..504000000)
            ACCESS        read-only
            STATUS        mandatory
            DESCRIPTION
                 " The cell delay variation (in micro seconds)
                   for VBR traffic in downstream direction of the VclTp. "
            ::= { xldv20VclTpEntry 26 }

         -- --------------------------------------------------------------
         -- E T H E R N E T  configuration table
         -- --------------------------------------------------------------

         xldv20EthernetConfigTable OBJECT-TYPE
            -- info-IMPL:    V2.0->
            -- info-VERCTRL: -
            SYNTAX        SEQUENCE OF Xldv20EthernetConfigEntry
            ACCESS        not-accessible
            STATUS        mandatory
            DESCRIPTION
                 " The Ethernet Configuration Table. "
            --DEFAULT get-function-async      fsnEthConfigEntryGet
            --DEFAULT next-function-async     fsnEthConfigEntryNext
            ::= { xldv20CallP 10 }

         xldv20EthernetConfigEntry OBJECT-TYPE
            -- info-IMPL:    V2.0->
            -- info-VERCTRL: -
            SYNTAX        Xldv20EthernetConfigEntry
            ACCESS        not-accessible
            STATUS        mandatory
            DESCRIPTION
                 " The entry of the Ethernet Configuration Table. "
            INDEX         { xldv20IfIndex }
            ::= { xldv20EthernetConfigTable 1 }

          Xldv20EthernetConfigEntry ::=
            SEQUENCE { xldv20EthMode              Xldv20EthNtMode,
                       xldv20EthE164Isp           OCTET STRING,
                       xldv20EthIpAddressNt       IpAddress,
                       xldv20EthIpAddressSubnetMaskNt IpAddress,
                       xldv20EthIpAddressCo               IpAddress,
                       xldv20EthIpAddressSubnetMaskCo IpAddress,
                       xldv20EthIpAddressRemoteRouter IpAddress
                       }

         xldv20EthMode    OBJECT-TYPE
            -- info-VALUE:   bridging, routing
            -- info-VALUE:   default: bridging
            -- info-ROU:     GET db
            -- info-IMPL:    V2.0->
            -- info-VERCTRL: -
            SYNTAX        Xldv20EthNtMode 
            ACCESS        read-only
            STATUS        mandatory
            DESCRIPTION
                  " The operational mode of the ethernet configuration:
                    Available modes: bridging, routing.
                    "
            ::= { xldv20EthernetConfigEntry 1 }

         xldv20EthE164Isp     OBJECT-TYPE
            -- info-VALUE:   -
            -- info-ROU:     GET db
            -- info-IMPL:    V2.0->
            -- info-VERCTRL: -
            SYNTAX            OCTET STRING ( SIZE (0..20) ) 
            ACCESS            read-only
            STATUS            mandatory
            DESCRIPTION
                  " The telephon number of the Internet Service Provider,
                    parameter for ipForwarding- mode"
            ::= { xldv20EthernetConfigEntry 2 }

         xldv20EthIpAddressNt   OBJECT-TYPE
            -- info-VALUE:   Default: 0.0.0.0
            -- info-ROU:     GET db
            -- info-IMPL:    V2.0->
            -- info-VERCTRL: -
            SYNTAX           IpAddress
            ACCESS           read-only
            STATUS           mandatory
            DESCRIPTION
                  " The IP Address of the NT,
                    parameter for ipForwarding - mode. "
            ::= { xldv20EthernetConfigEntry 3 }

         xldv20EthIpAddressSubnetMaskNt   OBJECT-TYPE
            -- info-VALUE:   Default: 0.0.0.0
            -- info-ROU:     GET db
            -- info-IMPL:    V2.0->
            -- info-VERCTRL: -
            SYNTAX           IpAddress
            ACCESS           read-only
            STATUS           mandatory
            DESCRIPTION
                  " The subnet mask of the NT ,
                    parameter for ipForwarding- mode. "
            ::= { xldv20EthernetConfigEntry 4 }


         xldv20EthIpAddressCo   OBJECT-TYPE
            -- info-VALUE:   Default: 0.0.0.0
            -- info-ROU:     GET db
            -- info-IMPL:    V2.0->
            -- info-VERCTRL: -
            SYNTAX           IpAddress
            ACCESS           read-only
            STATUS           mandatory
            DESCRIPTION
                  " The IP Address of the destination NT (office side),
                    parameter for ipForwarding- mode. "
            ::= { xldv20EthernetConfigEntry 5 }

         xldv20EthIpAddressSubnetMaskCo   OBJECT-TYPE
            -- info-VALUE:   Default: 0.0.0.0
            -- info-ROU:     GET db
            -- info-IMPL:    V2.0->
            -- info-VERCTRL: -
            SYNTAX            IpAddress
            ACCESS            read-only
            STATUS            mandatory
            DESCRIPTION
                  " The subnet mask of the CO  ,
                    parameter for ipForwarding- mode. "
            ::= { xldv20EthernetConfigEntry 6 }

         xldv20EthIpAddressRemoteRouter    OBJECT-TYPE
            -- info-VALUE:   Default: 0.0.0.0
            -- info-ROU:     GET db
            -- info-IMPL:    V2.0->
            -- info-VERCTRL: -
            SYNTAX            IpAddress
            ACCESS            read-only
            STATUS            mandatory
            DESCRIPTION
                  " The subnet mask of the ISP router  ,
                    parameter for ipForwarding- mode. "
            ::= { xldv20EthernetConfigEntry 7 }


           -- --------------------------------------------------------------
           --                        CONTINUITY CHECK  
           -- --------------------------------------------------------------
           
           -- --------------------------------------------------------------
           --        Continuity Check Configuration (COC) Table 
           --        for COC on VP level
           -- --------------------------------------------------------------
      
           -- XLDV2.0 : This table was renamed (former xldv20ContinuityCheckVpTable)
           -- with the redesign of Callp objects.
           
           xldv20ContinuityCheckVpTable OBJECT-TYPE
              -- info-IMPL:    V2.0->
              -- info-VERCTRL: -
            SYNTAX        SEQUENCE OF Xldv20ContinuityCheckVpEntry
            ACCESS        not-accessible
            STATUS        mandatory
            DESCRIPTION
                 " The Continuity Check VP table.
		 Holds entries for enabled continuity checks at VP level.
		 Entries are created when Vpl cross connects 
                 or VpcTps with enabled continuity check are created or 
                 when continuity check is enabled via command.
                 Entries are deleted when the continuity check is disabled 
                 (via xldv20ContinuityCheckControl) . "
              --DEFAULT next-function-async     fsnCvpEntryNext
              --DEFAULT get-function-async      fsnCvpEntryGet
            ::= { xldv20CallP 11 }
      
           xldv20ContinuityCheckVpEntry OBJECT-TYPE
            -- info-IMPL:    V2.0->
            -- info-VERCTRL: -
              SYNTAX        Xldv20ContinuityCheckVpEntry
            ACCESS        not-accessible
            STATUS        mandatory
            DESCRIPTION
                 " The entry represents the attributes of an enabled
                   continuity check at a VplTp or VpcTp.
                     Notifications : none. "
            INDEX         { xldv20CvpIndex }
            ::= { xldv20ContinuityCheckVpTable 1 }
      
      
            Xldv20ContinuityCheckVpEntry ::=
            SEQUENCE { xldv20CvpIndex                     Unsigned16,
                       xldv20CvpEndpointType          Xldv20EndpointType,
                       xldv20CvpTestType              Xldv20TestType,
                       xldv20CvpOperationalState      Xldv20OperState,
                       xldv20CvpVpTpIndex                 INTEGER,
                       xldv20CvpObjectType            Xldv20RepSource}
      
           xldv20CvpIndex    OBJECT-TYPE
              -- info-VALUE:   0..65535
              -- info-ROU:     GET db
              -- info-IMPL:    V2.0->
              -- info-VERCTRL: -
            SYNTAX        Unsigned16
            ACCESS        read-only
            STATUS        mandatory
            DESCRIPTION
                  " The Index of this table. "
            ::= { xldv20ContinuityCheckVpEntry 1 }
      
         xldv20CvpEndpointType OBJECT-TYPE
            -- info-VALUE:   source (1), sink (2), both(3)
            -- info-ROU:     GET db
            -- info-IMPL:    V2.0->
            -- info-VERCTRL: -
            SYNTAX        Xldv20EndpointType
            ACCESS        read-only
            STATUS        mandatory
            DESCRIPTION
                 " The configured endpoint type (source or sink or
                 both) for countinuity check . "
            ::= { xldv20ContinuityCheckVpEntry 2 }

           xldv20CvpTestType OBJECT-TYPE
              -- info-VALUE:   segment(1), endToEnd(2) 
              -- info-ROU:     GET db
              -- info-IMPL:    V2.0->
              -- info-VERCTRL: -
            SYNTAX        Xldv20TestType
            ACCESS        read-only
            STATUS        mandatory
            DESCRIPTION
                 " The configured type of continuity check (segment or endToEnd) . "   
            ::= { xldv20ContinuityCheckVpEntry 3 }
      
           xldv20CvpOperationalState OBJECT-TYPE
              -- info-VALUE:   enabled(1)..disabled(2)
              -- info-ROU:     GET db
              -- info-IMPL:    V2.0->
              -- info-VERCTRL: -
            SYNTAX        Xldv20OperState
            ACCESS        read-only
            STATUS        mandatory
            DESCRIPTION
                 " Identifies whether an enabled continuity check is
		   is working (value enabled) or not. "
            ::= { xldv20ContinuityCheckVpEntry 4 }
      
           xldv20CvpVpTpIndex    OBJECT-TYPE
              -- info-VALUE:   1..5000
              -- info-ROU:     GET db
              -- info-IMPL:    V2.0->
              -- info-VERCTRL: -
            SYNTAX        INTEGER (1..5000)
            ACCESS        read-only
            STATUS        mandatory
            DESCRIPTION
                  " Index of the related VplTp or VpcTp . "
            ::= { xldv20ContinuityCheckVpEntry 5 }

           xldv20CvpObjectType OBJECT-TYPE
              -- info-VALUE:   vplTp, vpcTp
              -- info-ROU:     GET db
            -- info-IMPL:    V2.0->
            -- info-VERCTRL: -
            SYNTAX        Xldv20RepSource
            ACCESS        read-only
            STATUS        mandatory
            DESCRIPTION
                  " Specifies the type of related COH object
                  ( VplTp or VpcTp ) . "
            ::= { xldv20ContinuityCheckVpEntry 6 }

           -- --------------------------------------------------------------
           --             Continuity Check Configuration (COC) Table 
           --             for COC on VC level
           -- --------------------------------------------------------------
           --
           -- XLDV2.0 : This table was renamed (former xldv20ContinuityCheckVcTable)
           -- with the redesign of COH objects.
      
           xldv20ContinuityCheckVcTable OBJECT-TYPE
              -- info-IMPL:    V2.0->
              -- info-VERCTRL: -
            SYNTAX        SEQUENCE OF Xldv20ContinuityCheckVcEntry
            ACCESS        not-accessible
            STATUS        mandatory
            DESCRIPTION
                 " The continuity check configuration table for
		 COC on VC level.
		 Entries in this table are created when Vcl cross connects with
                 enabled continuity check are created or 
                 when the continuity check is enabled via command.
                 Entries are deleted when the continuity check is disabled 
                 (via xldv20ContinuityCheckControl) . "
            --DEFAULT get-function-async      fsnCvcEntryGet
            --DEFAULT next-function-async     fsnCvcEntryNext
            ::= { xldv20CallP 12 }
      
           xldv20ContinuityCheckVcEntry OBJECT-TYPE
              -- info-IMPL:    V2.0->
              -- info-VERCTRL: -
              SYNTAX        Xldv20ContinuityCheckVcEntry
            ACCESS        not-accessible
            STATUS        mandatory
            DESCRIPTION
                 " The entry represents the attributes of an enabled
                   continuity check .
                     Notifications : none. "
            INDEX         { xldv20CvcIndex }
            ::= { xldv20ContinuityCheckVcTable 1 }
      
            Xldv20ContinuityCheckVcEntry ::=
            SEQUENCE { xldv20CvcIndex                 Unsigned16,
                       xldv20CvcEndpointType          Xldv20EndpointType,
                       xldv20CvcTestType              Xldv20TestType,
                       xldv20CvcOperationalState      Xldv20OperState,
                       xldv20CvcVcTpIndex             INTEGER,
                       xldv20CvcObjectType            Xldv20RepSource}
      
           xldv20CvcIndex    OBJECT-TYPE
              -- info-VALUE:   0..65535
              -- info-ROU:     GET db
              -- info-IMPL:    V2.0->
              -- info-VERCTRL: -
            SYNTAX        Unsigned16
            ACCESS        read-only
            STATUS        mandatory
            DESCRIPTION
                  " Index of table. "
            ::= { xldv20ContinuityCheckVcEntry 1 }
      
         xldv20CvcEndpointType OBJECT-TYPE
            -- info-VALUE:   source (1), sink (2), both (3)
            -- info-ROU:     GET db
            -- info-IMPL:    V2.0->
            -- info-VERCTRL: -
            SYNTAX        Xldv20EndpointType
            ACCESS        read-only
            STATUS        mandatory
            DESCRIPTION
                 " The configured endpoint type ( source or sink
                 or both) for countinuity check . "
            ::= { xldv20ContinuityCheckVcEntry 2 }

           xldv20CvcTestType OBJECT-TYPE
              -- info-VALUE:   segment(1), endToEnd(2) 
              -- info-ROU:     GET db
              -- info-IMPL:    V2.0->
              -- info-VERCTRL: -
            SYNTAX        Xldv20TestType
            ACCESS        read-only
            STATUS        mandatory
            DESCRIPTION
                 " The type of continuity check segment or endToEnd . "   
            ::= { xldv20ContinuityCheckVcEntry 3 }
      
           xldv20CvcOperationalState OBJECT-TYPE
              -- info-VALUE:   enabled(1)..disabled(2)
              -- info-ROU:     GET db
              -- info-IMPL:    V2.0->
              -- info-VERCTRL: -
            SYNTAX        Xldv20OperState
            ACCESS        read-only
            STATUS        mandatory
            DESCRIPTION
                 " This read-only attribute identifies whether or not a
                 continuitycheck is enabled . "
            ::= { xldv20ContinuityCheckVcEntry 4 }
           
           xldv20CvcVcTpIndex    OBJECT-TYPE
              -- info-VALUE:   1..4000
              -- info-ROU:     GET db
              -- info-IMPL:    V2.0->
              -- info-VERCTRL: -
            SYNTAX        INTEGER (1..4000)
            ACCESS        read-only
            STATUS        mandatory
            DESCRIPTION
                  " Index of the related VC object (currently VclTp only) . "
            ::= { xldv20ContinuityCheckVcEntry 5 }

           xldv20CvcObjectType OBJECT-TYPE
              -- info-VALUE:   vclTp
              -- info-IMPL:    V2.0->
              -- info-VERCTRL: -
            SYNTAX        Xldv20RepSource
            ACCESS        read-only
            STATUS        mandatory
            DESCRIPTION
                  " Specifies the type of related COH VC object ( VclTp ) . "
            ::= { xldv20ContinuityCheckVcEntry 6 }

           -- --------------------------------------------------------------
           --                    continuity check control group
           -- --------------------------------------------------------------
      
           xldv20ContinuityCheckControl OBJECT IDENTIFIER ::= { xldv20CallP 13 }
            -- info-IMPL:    V2.0->
            -- info-VERCTRL: -
      
           -- This group handles the TMN control request for activating/deactivating 
           -- the continuity check function .
           --
      
           xldv20CocControlReq OBJECT-TYPE
              -- info-VALUE:   noRequest(command), continuityCheckRequest(command)  
              -- info-ROU:     GET db  SET cp 
            -- info-IMPL:    V2.0->
            SYNTAX        Xldv20ControlReq
            ACCESS        read-write
            STATUS        mandatory
            DESCRIPTION
                 "Control group for activating/deactivating
		  the continuity check at the source/sink of
		  a VPL or VCL connection.
		 The user command attribute to activate a continuity check
                   (continuityCheckRequest) or to deactivate (noRequest).
                     Notifications : none . "
            --DEFAULT test-function-async     fsnCocTest
            --DEFAULT next-function-async     fsnCocNext
            --DEFAULT set-function-async      fsnCocSet
            --DEFAULT get-function-async      fsnCocGet
            ::= { xldv20ContinuityCheckControl 1 }
      
           xldv20CocControlStatus OBJECT-TYPE
              -- info-VALUE:   requestIdle(1), requestBusy(2), requestPassed(3)
              -- info-VALUE:   requestFailed(4)
              -- info-ROU:     GET db
            -- info-IMPL:    V2.0->
            -- info-VERCTRL: -
            SYNTAX        Xldv20ControlStatus
            ACCESS        read-only
            STATUS        mandatory
            DESCRIPTION
                 " The status of the control request. The value requestIdle will be
                   set after startup/recovery or after a running test was aborted by
                   the SNMP manager. "
            --DEFAULT next-function-async     fsnCocNext
            --DEFAULT get-function-async      fsnCocGet
            ::= { xldv20ContinuityCheckControl 2 }
      
           xldv20CocEndpointType OBJECT-TYPE
              -- info-VALUE:   source (1), sink (2)
              -- info-VALUE:   both (3)
              -- info-ROU:     GET db  SET db 
            -- info-IMPL:    V2.0->
            -- info-VERCTRL: -
            SYNTAX        Xldv20EndpointType
            ACCESS        read-write
            STATUS        mandatory
            DESCRIPTION
                 " This attribute specifies whether the source or sink of a
                 should be enabled/disabled for countinuity check . "
            --DEFAULT test-function-async     fsnCocTest
            --DEFAULT next-function-async     fsnCocNext
            --DEFAULT set-function-async      fsnCocSet
            --DEFAULT get-function-async      fsnCocGet
            ::= { xldv20ContinuityCheckControl 3 }
           
           xldv20CocObjectType OBJECT-TYPE
              -- info-VALUE:   vplTp,vpcTp,vclTp
              -- info-ROU:     GET db  SET db 
            -- info-IMPL:    V2.0->
            -- info-VERCTRL: -
            SYNTAX        Xldv20RepSource
            ACCESS        read-write
            STATUS        mandatory
            DESCRIPTION
                 " Selects the type of COH object. "
            --DEFAULT test-function-async     fsnCocTest
            --DEFAULT next-function-async     fsnCocNext
            --DEFAULT set-function-async      fsnCocSet
            --DEFAULT get-function-async      fsnCocGet
            ::= { xldv20ContinuityCheckControl 4 }
           
           xldv20CocTestType OBJECT-TYPE
              -- info-VALUE:   segment(1), endToEnd(2) 
              -- info-ROU:     GET db  SET db 
            -- info-IMPL:    V2.0->
            -- info-VERCTRL: -
            SYNTAX        Xldv20TestType
            ACCESS        read-write
            STATUS        mandatory
            DESCRIPTION
                 " The type of continuity check (segment or endToEnd) . "   
            --DEFAULT test-function-async     fsnCocTest
            --DEFAULT next-function-async     fsnCocNext
            --DEFAULT set-function-async      fsnCocSet
            --DEFAULT get-function-async      fsnCocGet
            ::= { xldv20ContinuityCheckControl 5 }
           
           xldv20CocIndex OBJECT-TYPE
              -- info-VALUE:   0..65535
              -- info-ROU:     GET db  SET db
              -- info-IMPL:    V2.0->
              -- info-VERCTRL: -
            SYNTAX        Unsigned16
            ACCESS        read-write
            STATUS        mandatory
            DESCRIPTION
                   " If the continuity check should be enabled it is
                   the index of the selected COH object.
                   If the continuity check should be disabled it is
                   the index xldv20VplCvpIndexSegment or xldv20VpcCvpIndexSegment.
                   xldv20VpcCvpIndexEndToEnd or xldv20VclCvcIndexSegment. "
            --DEFAULT test-function-async     fsnCocTest
            --DEFAULT next-function-async     fsnCocNext
            --DEFAULT set-function-async      fsnCocSet
            --DEFAULT get-function-async      fsnCocGet
            ::= { xldv20ContinuityCheckControl 6 }
      
         xldv20CocControlReqResult OBJECT-TYPE
            -- info-VALUE:   noRequest (disable command)
            -- info-VALUE:   continuityCheckRequest(enable command)  
            -- info-VALUE:   paramFaulty, continuityCheckBusy, 
            -- info-VALUE:   continuityCheckAlreadyEnabled
            -- info-VALUE:   continuityCheckAlreadyDisabled
            -- info-VALUE:   continuityCheckReject
            -- info-VALUE:   continuityCheckTestTypeConflict
            -- info-VALUE:   continuityCheckNotSupportedOnNt
            -- info-VALUE:   requestBusy, setDataFailed
            -- info-VALUE:   aswTimeout, commandFailed, commandSucceeded
            -- info-ROU:     GET db
            -- info-IMPL:    V2.0->
            -- info-VERCTRL: -
            SYNTAX        Xldv20ControlReq
            ACCESS        read-only
            STATUS        mandatory
            DESCRIPTION
                 " The result of the last user command. "
            --DEFAULT next-function-async     fsnCocNext
            --DEFAULT get-function-async      fsnCocGet
            ::= { xldv20ContinuityCheckControl 7 }

         xldv20CocControlTimeStamp OBJECT-TYPE
            -- info-VALUE:   0..2Giga
            -- info-ROU:     GET db
            -- info-IMPL:    V2.0->
            -- info-VERCTRL: -
            SYNTAX        TimeTicks
            ACCESS        read-only
            STATUS        mandatory
            DESCRIPTION
               " The time stamp of the last command (end of command). "
            --DEFAULT next-function-async     fsnCocNext
            --DEFAULT get-function-async      fsnCocGet
            ::= { xldv20ContinuityCheckControl 8 }

           -- --------------------------------------------------------------
           --            Inband TMN Vpi/Vci configuration
           -- --------------------------------------------------------------
           --
           -- This group holds the configuration data for inband TMN
           --
           xldv20InbandTmn OBJECT IDENTIFIER ::= { xldv20CallP 14 }
            -- info-IMPL:    V2.0->
            -- info-VERCTRL: -
           
           -- This group holds the configuration data for inband TMN
           xldv20InbandVpiCurrent OBJECT-TYPE
              -- info-VALUE:   0..4095
              -- info-ROU:     GET db
            -- info-IMPL:    V2.0->
              -- info-VERCTRL: -
            SYNTAX        INTEGER (0..4095)
            ACCESS        read-only
            STATUS        mandatory
            DESCRIPTION
                 " Inband TMN configuration object.
                   Identifies the current VPI value of inband TMN channel. "
            --DEFAULT next-function-async     fsnInbNext
            --DEFAULT get-function-async      fsnInbGet
            ::= { xldv20InbandTmn 1 }
      
           xldv20InbandVciCurrent OBJECT-TYPE
              -- info-VALUE:   0..65535
              -- info-ROU:     GET db
            -- info-IMPL:    V2.0->
            -- info-VERCTRL: -
            SYNTAX        INTEGER (0..65535)
            ACCESS        read-only
            STATUS        mandatory
            DESCRIPTION
                 " Identifies the current Vci value of inband TMN channel. "
            --DEFAULT next-function-async     fsnInbNext
            --DEFAULT get-function-async      fsnInbGet
            ::= { xldv20InbandTmn 2 }

           xldv20InbandVpiConfig OBJECT-TYPE
              -- info-VALUE:   0..4095
              -- info-ROU:     GET db
            -- info-IMPL:    V2.0->
            -- info-VERCTRL: -
            SYNTAX        INTEGER (0..4095)
            ACCESS        read-only
            STATUS        mandatory
            DESCRIPTION
                 " Identifies the configured Vpi value of inband TMN channel
                 which becomes effective only after reload. "
            --DEFAULT next-function-async     fsnInbNext
            --DEFAULT get-function-async      fsnInbGet
            ::= { xldv20InbandTmn 3 }
      
           xldv20InbandVciConfig OBJECT-TYPE
              -- info-VALUE:   0..65535
              -- info-ROU:     GET db
            -- info-IMPL:    V2.0->
            -- info-VERCTRL: -
            SYNTAX        INTEGER (0..65535)
            ACCESS        read-only
            STATUS        mandatory
            DESCRIPTION
                 " Identifies the configured Vci value of inband TMN channel
                 which becomes effective only after reload. "
            --DEFAULT next-function-async     fsnInbNext
            --DEFAULT get-function-async      fsnInbGet
            ::= { xldv20InbandTmn 4 }


         -- ==============================================================
         --      H a r d w a r e   M a i n t e n a n c e   G r o u p
         -- ==============================================================
         --
         -- XLDV2.0 : 
         --    Instances of managed entities shall be automatically
         --    created by the ATM NE immediately after system
         --    initialization is complete.
         --    In state locked the manager can change the configuration
         --    when overwritiing the value of the
         --    attribute xldv20PiuType using the command createHwUnit of 
         --    xldv20HwuControl.
         -- XLDV2.x : 
         --    Instances of HWM managed entity shall be automatically
         --    created by the ATM NE immediately after system.
         --    Initialization is complete and immediately following the 
         --    insertion of the plugIn unit into the equipment slot.
         --    Instances can also be created or deleted by the manager
         --    (createHwUnit, deleteHwUnit) . "


         -- --------------------------------------------------------------
         --                         ATM NE subgroup
         -- --------------------------------------------------------------

         xldv20AtmNe OBJECT IDENTIFIER ::= { xldv20Hwm 1 }
            -- info-IMPL:    V2.0->
            -- info-VERCTRL: -

         xldv20NeLocation OBJECT-TYPE
            -- info-VALUE:   -
            -- info-ROU:     GET db  SET db
            -- info-IMPL:    V2.0->
            -- info-VERCTRL: -
            SYNTAX        OCTET STRING ( SIZE (0..80) )
            ACCESS        read-write
            STATUS        mandatory
            DESCRIPTION
                 " Describes the location of the NetElement, e.g. Hofmannstr. 51 . "
            --DEFAULT test-function-async     fsnNeTest
            --DEFAULT next-function-async     fsnNeNext
            --DEFAULT set-function-async      fsnNeSet
            --DEFAULT get-function-async      fsnNeGet
            ::= { xldv20AtmNe 1 }

         xldv20NeVendor   OBJECT-TYPE
            -- info-VALUE:   -
            -- info-ROU:     GET db
            -- info-IMPL:    V2.0->
            -- info-VERCTRL: -
            SYNTAX        DisplayString
            ACCESS        read-only
            STATUS        mandatory
            DESCRIPTION
                 " Contains the vendor of the NetElement, Siemens AG . "
            --DEFAULT next-function-async     fsnNeNext
            --DEFAULT get-function-async      fsnNeGet
            ::= { xldv20AtmNe 2 }

         xldv20NeVersion  OBJECT-TYPE
            -- info-VALUE:   -
            -- info-ROU:     GET db
            -- info-IMPL:    V2.0->
            -- info-VERCTRL: -
            SYNTAX        DisplayString
            ACCESS        read-only
            STATUS        mandatory
            DESCRIPTION
                 " Contains the version of the NetElement, XLD V20 "
            --DEFAULT next-function-async     fsnNeNext
            --DEFAULT get-function-async      fsnNeGet
            ::= { xldv20AtmNe 3 }

         xldv20NeExternalTime  OBJECT-TYPE
            -- info-VALUE:   0..2Giga
            -- info-ROU:     GET sn SET sn
            -- info-IMPL:    V2.0->
            -- info-VERCTRL: -
            SYNTAX        TimeTicks
            ACCESS        read-write
            STATUS        mandatory
            DESCRIPTION
                 " The external Time of the NetElement in seconds from January 1st 1970.
		 The TMN-OS should set this time after firsttime power up, coldstart,
		 warmstart or reload and to refresh it once a day. "
            --DEFAULT test-function-async     fsnNeTest
            --DEFAULT next-function-async     fsnNeNext
            --DEFAULT set-function-async      fsnNeSet
            --DEFAULT get-function-async      fsnNeGet
            ::= { xldv20AtmNe 4 }

         xldv20NeTimeZone  OBJECT-TYPE
            -- info-VALUE:   gmt-12Eniwetok
            -- info-VALUE:   gmt-11MidwayIslandsSamoa              
            -- info-VALUE:   gmt-10Hawaii                          
            -- info-VALUE:   gmt-9Alaska                           
            -- info-VALUE:   gmt-8TijuanaLosAngelesSeattleVancouver
            -- info-VALUE:   gmt-7ArizonaDenverSaltLakeCityCalgary        
            -- info-VALUE:   gmt-6ChicagoDallasKansasCityWinnipeg  
            -- info-VALUE:   gmt-6MexicoCityTegucigalpaSaskatchewan
            -- info-VALUE:   gmt-5BogotaLimaQuito                  
            -- info-VALUE:   gmt-5IndianaEast                      
            -- info-VALUE:   gmt-5NewYorkMiamiAtlantaDetroitToronto
            -- info-VALUE:   gmt-4CaracasLaPazMontrealQuebec       
            -- info-VALUE:   gmt-330Neufundland                    
            -- info-VALUE:   gmt-3BrasiliaBuenosAiresGeorgetown    
            -- info-VALUE:   gmt-2MiddleAtlantic                   
            -- info-VALUE:   gmt-1AzorenKaverdIslands              
            -- info-VALUE:   gmtCasablancaDublinLissabonLondon     
            -- info-VALUE:   gmt1AmsterdamMadridParisBelgradZagreb
            -- info-VALUE:   gmt1BerlinBernRomeStockholmVienna    
            -- info-VALUE:   gmt1BudapestPrahaBratislavaWarschau  
            -- info-VALUE:   gmt2AthensIstanbulMinskBukarest      
            -- info-VALUE:   gmt2HararePretoriaHelsinkiRevalRiga  
            -- info-VALUE:   gmt2IsraelKairo                      
            -- info-VALUE:   gmt3BagdadKuwaitErRiad               
            -- info-VALUE:   gmt3MoskowStPetersburgWolgograd      
            -- info-VALUE:   gmt3Nairobi                          
            -- info-VALUE:   gmt330Teheran                        
            -- info-VALUE:   gmt4AbuDhabiMuskatBakuTiflis         
            -- info-VALUE:   gmt430Kabul                          
            -- info-VALUE:   gmt5IslamabadKarartschiTaschkent     
            -- info-VALUE:   gmt5Jekaterinburg                    
            -- info-VALUE:   gmt530BombayKaluttaMadrasNewDehli    
            -- info-VALUE:   gmt6AkmolaAlmaAtaDhakaColombo        
            -- info-VALUE:   gmt7BangkokHanoiJakarta              
            -- info-VALUE:   gmt8PekingChongqingHongkongUrumchi   
            -- info-VALUE:   gmt8PerthSingapurTaipeh              
            -- info-VALUE:   gmt9IrkutskOsakaSapporoTokyoSeoul    
            -- info-VALUE:   gmt930AdelaideDarwin                 
            -- info-VALUE:   gmt10BrisbaneCanberraMlebourneSydney 
            -- info-VALUE:   gmt10GuamPortMoresbyHobart           
            -- info-VALUE:   gmt10Wladiwostok                     
            -- info-VALUE:   gmt11MagadanSalomonenNewCaledonia    
            -- info-VALUE:   gmt12AucklandWellington              
            -- info-VALUE:   gmt12FidschiKamtschatkaMarschallIslands     
            -- info-ROU:     GET db  SET sn
            -- info-IMPL:    V2.0->
            -- info-VERCTRL: -
            SYNTAX        Xldv20TimeZone 
            ACCESS        read-write
            STATUS        mandatory
            DESCRIPTION
                 " Specifies the time zone of the netelement
                 as time difference to Greenwich Mean Time (GMT),
                 e.g. GMT+1 or GMT-5. "
            --DEFAULT test-function-async     fsnNeTest
            --DEFAULT next-function-async     fsnNeNext
            --DEFAULT set-function-async      fsnNeSet
            --DEFAULT get-function-async      fsnNeGet
            ::= { xldv20AtmNe 5 }

         xldv20NeDescriptorFileName  OBJECT-TYPE
            -- info-VALUE:   -
            -- info-ROU:     GET db
            -- info-IMPL:    V2.0->
            -- info-VERCTRL: -
            SYNTAX        DisplayString
            ACCESS        read-only
            STATUS        mandatory
            DESCRIPTION
                 " The name of the descriptor file. Initialized after
                   reload by SW upgrade . "
            --DEFAULT next-function-async     fsnNeNext
            --DEFAULT get-function-async      fsnNeGet
            ::= { xldv20AtmNe 6 }

     xldv20NeExternalTime45020  OBJECT-TYPE
        -- info-VALUE:   0..4Giga
        -- info-ROU:     GET sn SET sn
        -- info-IMPL:    V2.0->
        -- info-VERCTRL: -
        SYNTAX        TimeTicks
        ACCESS        read-write
        STATUS        mandatory
        DESCRIPTION
             " The external Time of the NetElement in seconds.
	     The TMN-45020 sets this time after first time power up, coldstart,
             warmstart or reload and refreshes the time in a
             period of 24h . The basis is January 1st 1999, 0:00"
        --DEFAULT test-function-async     fsnNeTest
        --DEFAULT next-function-async     fsnNeNext
        --DEFAULT set-function-async      fsnNeSet
        --DEFAULT get-function-async      fsnNeGet
        ::= { xldv20AtmNe 7 }

     xldv20NeSummerTime  OBJECT-TYPE
        -- info-VALUE:   summerTime1 ( 1),
        -- info-VALUE:   summerTime2 ( 2),
        -- info-VALUE:   winterTime  (10) (default)
        -- info-ROU:     GET sn SET sn
        -- info-IMPL:    V2.0->
        -- info-VERCTRL: -
        SYNTAX        Xldv20DayLightSavingTime
        ACCESS        read-write
        STATUS        mandatory
        DESCRIPTION
             " Specifies whether summer time (day light saving time DST)
             or winter time is valid. Normally the clock is turned 
             1 hour ahead at begin of summer time and 1 hour back 
             at end. Default is winterTime."
        --DEFAULT test-function-async     fsnNeTest
        --DEFAULT next-function-async     fsnNeNext
        --DEFAULT set-function-async      fsnNeSet
        --DEFAULT get-function-async      fsnNeGet
        ::= { xldv20AtmNe 8 }



         -- --------------------------------------------------------------
         --               Hardware Unit Table 
         -- --------------------------------------------------------------

         xldv20HwUnitTable OBJECT-TYPE
            -- info-IMPL:    V2.0->
            -- info-VERCTRL: -
            SYNTAX        SEQUENCE OF Xldv20HwUnitEntry
            ACCESS        not-accessible
            STATUS        mandatory
            DESCRIPTION
                 " The XLD hardware unit table. This table models the Equipment,
                   Equipment Holder and Plug-In Unit management entities . "
            --DEFAULT next-function-async     fsnHwUnitEntryNext
            --DEFAULT get-function-async      fsnHwUnitEntryGet
            ::= { xldv20Hwm 2 }

         xldv20HwUnitEntry OBJECT-TYPE
            -- info-IMPL:    V2.0->
            -- info-VERCTRL: -
            SYNTAX        Xldv20HwUnitEntry
            ACCESS        not-accessible
            STATUS        mandatory
            DESCRIPTION
                 " An entry in the xldv20HwUnitTable.
                   Notifications : none. "
            INDEX { xldv20HwUnitIndex }
            ::= { xldv20HwUnitTable 1 }

         Xldv20HwUnitEntry ::=
            SEQUENCE { xldv20HwUnitIndex    Unsigned16,
                       xldv20HwUnitType     Xldv20HwUnitType }

         xldv20HwUnitIndex OBJECT-TYPE
            -- info-VALUE:   0..65535
            -- info-ROU:     GET db
            -- info-IMPL:    V2.0->
            -- info-VERCTRL: -
            SYNTAX        Unsigned16
            ACCESS        read-only
            STATUS        mandatory
            DESCRIPTION
                 " A unique value to identify a hardware unit within
                   the ATM agent. It is used as index for the tables
                   xldv20HwEquipTable, xldv20HwEquipHolderTable and
                   xldv20HwPlugInUnitTable . "
            ::= { xldv20HwUnitEntry 1 }

         xldv20HwUnitType OBJECT-TYPE
            -- info-VALUE:   equipment(1), equipmentHolder(2), plugInUnit(3)
            -- info-ROU:     GET db
            -- info-IMPL:    V2.0->
            -- info-VERCTRL: -
            SYNTAX        Xldv20HwUnitType
            ACCESS        read-only
            STATUS        mandatory
            DESCRIPTION
                 " Identifies the general type of this hardware unit.
                   The values are equipment, equipmentHolder and plugInUnit . "
            ::= { xldv20HwUnitEntry 2 }


         -- --------------------------------------------------------------
         --            Hardware Containment Table
         -- --------------------------------------------------------------

         xldv20HwContainmentTable OBJECT-TYPE
            -- info-IMPL:    V2.0->
            -- info-VERCTRL: -
            SYNTAX        SEQUENCE OF Xldv20HwContainmentEntry
            ACCESS        not-accessible
            STATUS        mandatory
            DESCRIPTION
                 " The hardware unit containment table. This table describes
                   the containment relationships that maintain between Equipment,
                   Equipment Holder and Plug-In Unit entities . "
            --DEFAULT next-function-async     fsnHwContEntryNext
            --DEFAULT get-function-async      fsnHwContEntryGet
            ::= { xldv20Hwm 3 }

         xldv20HwContainmentEntry OBJECT-TYPE
            -- info-IMPL:    V2.0->
            -- info-VERCTRL: -
            SYNTAX        Xldv20HwContainmentEntry
            ACCESS        not-accessible
            STATUS        mandatory
            DESCRIPTION
                 " An entry in the hardware unit containment table. Each entry
                   of this type identifies two hardware units, one of which is
                   contained directly within the other .
                   Notifications : none. "
            INDEX { xldv20HwContainingUnitIndex,
                    xldv20HwContainedUnitAddr }
            ::= { xldv20HwContainmentTable 1 }

         Xldv20HwContainmentEntry ::=
            SEQUENCE { xldv20HwContainingUnitIndex Unsigned16,
                       xldv20HwContainedUnitAddr   INTEGER,
                       xldv20HwContainedUnitIndex  Unsigned16 }

         xldv20HwContainingUnitIndex OBJECT-TYPE
            -- info-VALUE:   0..65535
            -- info-ROU:     GET db
            -- info-IMPL:    V2.0->
            -- info-VERCTRL: -
            SYNTAX        Unsigned16
            ACCESS        read-only
            STATUS        mandatory
            DESCRIPTION
                 " The HwUnitIndex (in the xldv20HwUnitTable), of the containing hardware
                   unit in this pair . "
            ::= { xldv20HwContainmentEntry 1 }

         xldv20HwContainedUnitAddr OBJECT-TYPE
            -- info-VALUE:   1..512
            -- info-ROU:     GET db
            -- info-IMPL:    V2.0->
            -- info-VERCTRL: -
            SYNTAX        INTEGER (1..512)
            ACCESS        read-only
            STATUS        mandatory
            DESCRIPTION
                 " A number uniquely identifying, within the containing hardware
                   unit, the contained unit.
                   Contained unit should be addressed starting at 1. If the
                   contained component is an Equipment Holder, this object
                   represents its physical location (e.g.  slot number). If a
                   single piece of Equipment contains both Equipment Holder and
                   other Equipment objects, the Equipment Holders should have
                   the lowest-valued addresses, so this relationship can be
                   maintained. A Plug-In Unit always has an address of 1 .  "

            ::= { xldv20HwContainmentEntry 2 }

         xldv20HwContainedUnitIndex OBJECT-TYPE
            -- info-VALUE:   0..65535
            -- info-ROU:     GET db
            -- info-IMPL:    V2.0->
            -- info-VERCTRL: -
            SYNTAX        Unsigned16
            ACCESS        read-only
            STATUS        mandatory
            DESCRIPTION
                 " The hwUnitIndex of the contained unit. "
            ::= { xldv20HwContainmentEntry 3 }


         -- --------------------------------------------------------------
         --                  Hardware Equipment Table
         -- --------------------------------------------------------------

         xldv20HwEquipTable OBJECT-TYPE
            -- info-IMPL:    V2.0->
            -- info-VERCTRL: -
            SYNTAX        SEQUENCE OF Xldv20HwEquipEntry
            ACCESS        not-accessible
            STATUS        mandatory
            DESCRIPTION
                 " The hardware equipment table. "
            --DEFAULT test-function-async     fsnEquEntryTest
            --DEFAULT next-function-async     fsnEquEntryNext
            --DEFAULT set-function-async      fsnEquEntrySet
            --DEFAULT get-function-async      fsnEquEntryGet
            ::= { xldv20Hwm 4 }

         xldv20HwEquipEntry OBJECT-TYPE
            -- info-IMPL:    V2.0->
            -- info-VERCTRL: -
            SYNTAX        Xldv20HwEquipEntry
            ACCESS        not-accessible
            STATUS        mandatory
            DESCRIPTION
                 "  Entry of the HW equipment table.
		 The entries represent the various manageable physical
                   components of the ATM NE that are not modelled via the
                   Plug-In Unit managed entity.
                   An instance of this managed entity shall be automati-
                   cally created by the ATM NE immediately following the
                   initialization/installation of the externally
                   manageable physical component in the ATM NE.
                   Notifications : 
		   xldv20TrObjCreate.
		   xldv20TrObjDelete . "
            INDEX         { xldv20HwUnitIndex }
            ::= { xldv20HwEquipTable 1 }

         Xldv20HwEquipEntry ::=
            SEQUENCE { xldv20EquType               DisplayString,
                       xldv20EquLocation           OCTET STRING,
                       xldv20EquUserLabel          OCTET STRING,
                       xldv20EquConnectedPiuIndex  Unsigned16,
                       xldv20EquConnectedPiuPort   INTEGER }

         xldv20EquType OBJECT-TYPE
            -- info-VALUE:   onu, ntAdsl, ntVdsl, ntCpe
            -- info-ROU:     GET db
            -- info-IMPL:    V2.0->
            -- info-VERCTRL: -
            SYNTAX        DisplayString (SIZE (0..10))
            ACCESS        read-only
            STATUS        mandatory
            DESCRIPTION
                 " Indicates whether the equipment is a DSLAM,
                   ntAdsl, ntVdsl or a ntCpe ( customer premise equipment) . "
            ::= { xldv20HwEquipEntry 1 }

         xldv20EquLocation OBJECT-TYPE
            -- info-VALUE:   e.g.: "Rack 23"
            -- info-ROU:     GET db  SET db
            -- info-IMPL:    V2.0->
            -- info-VERCTRL: -
            SYNTAX        OCTET STRING ( SIZE (0..80) )
            ACCESS        read-write
            STATUS        mandatory
            DESCRIPTION
                 " Identifies the specific or general location of the
                   ATM NE component . "
            ::= { xldv20HwEquipEntry 2 }

         xldv20EquUserLabel OBJECT-TYPE
            -- info-VALUE:   e.g.: "XLD Testbed"
            -- info-ROU:     GET db  SET db
            -- info-IMPL:    V2.0->
            -- info-VERCTRL: -
            SYNTAX        OCTET STRING ( SIZE (0..80) )
            ACCESS        read-write
            STATUS        mandatory
            DESCRIPTION
                 " Assignis user friendly name to the
                   associated managed entity . "
            ::= { xldv20HwEquipEntry 3 }

         xldv20EquConnectedPiuIndex OBJECT-TYPE
            -- info-VALUE:   0..65535
            -- info-ROU:     GET db
            -- info-IMPL:    V2.0->
            -- info-VERCTRL: -
            SYNTAX        Unsigned16
            ACCESS        read-only
            STATUS        mandatory
            DESCRIPTION
                 " This attribute is used to show the PIU to which the NT is
                   connected (HwUnitIndex) . In case of DSLAM value is 0. "
            ::= { xldv20HwEquipEntry 4 }

         xldv20EquConnectedPiuPort OBJECT-TYPE
            -- info-VALUE:   0..255
            -- info-VALUE:   Default value: 0
            -- info-ROU:     GET db
            -- info-IMPL:    V2.0->
            SYNTAX        INTEGER (0..255)
            ACCESS        read-only
            STATUS        mandatory
            DESCRIPTION
                 " The port ID of the connected PIU.  "
            ::= { xldv20HwEquipEntry 5 }


         -- --------------------------------------------------------------
         --             Hardware Equipment Holder Table
         -- --------------------------------------------------------------

         xldv20HwEquipHolderTable OBJECT-TYPE
            -- info-IMPL:    V2.0->
            -- info-VERCTRL: -
            SYNTAX        SEQUENCE OF Xldv20HwEquipHolderEntry
            ACCESS        not-accessible
            STATUS        mandatory
            DESCRIPTION
                 " The equipment holder table . "
            --DEFAULT test-function-async     fsnEqhEntryTest
            --DEFAULT next-function-async     fsnEqhEntryNext
            --DEFAULT set-function-async      fsnEqhEntrySet
            --DEFAULT get-function-async      fsnEqhEntryGet
            ::= { xldv20Hwm 5 }

         xldv20HwEquipHolderEntry OBJECT-TYPE
            -- info-IMPL:    V2.0->
            -- info-VERCTRL: -
            SYNTAX        Xldv20HwEquipHolderEntry
            ACCESS        not-accessible
            STATUS        mandatory
            DESCRIPTION
                 " Entry of the equipment holder table.
		 The entries represent physical resources of the ATM NE
                   holding other physical resources. Examples of resources
                   represented by instances of this managed entity are
                   shelves and slots.
                   An instance of this managed entity shall exist for each
                   shelf and slot of the ATM NE. Instances shall be auto-
                   matically created and reported by the ATM NE once
                   system initialization is complete.
                   Notifications :
		   xldv20TrObjCreate .
                   xldv20TrObjDelete .
                   xldv20TrSwVersionSet when xldv20EqhSwVersion.
                   xldv20EqhMnemoCode,xldv20EqhFwItemNumber set. "
            INDEX         { xldv20HwUnitIndex }
            ::= { xldv20HwEquipHolderTable 1 }

         Xldv20HwEquipHolderEntry ::=
            SEQUENCE { xldv20EqhType            Xldv20EqhType,
                       xldv20EqhAccPiuTypes     DisplayString,
                       xldv20EqhSlotStatus      Xldv20SlotStatus,
                       xldv20EqhSwVersion       OCTET STRING,
                       xldv20EqhMnemoCode       OCTET STRING,
                       xldv20EqhFwCode          OCTET STRING,
                       xldv20EqhRiMnemoCode     DisplayString,
                       xldv20EqhRiFwItemNumber  DisplayString,
                       xldv20EqhRiFwIssue       DisplayString,
                       xldv20EqhRiHwItemNumber  DisplayString,
                       xldv20EqhRiHwIssue       DisplayString, 
                       xldv20EqhRiSerialNumber  DisplayString } 


         xldv20EqhType OBJECT-TYPE
            -- info-VALUE:   slot, basicShelf
            -- info-VALUE:   extendedShelf, ntAdslShelf
            -- info-VALUE:   cpeShelf  (for CPE customer premise equipment)
            -- info-VALUE:   ntVdslShelf(V2.x->) 
            -- info-ROU:     GET db
            -- info-IMPL:    V2.0->
            -- info-VERCTRL: -
            SYNTAX        Xldv20EqhType
            ACCESS        read-only
            STATUS        mandatory
            DESCRIPTION
                 " Type of the equipment holder. "
            ::= { xldv20HwEquipHolderEntry 1 }

         xldv20EqhAccPiuTypes OBJECT-TYPE
            -- info-VALUE:   'CI:A'
            -- info-VALUE:   'LU155:OS', 'LU155:OL', 'LU155:C', 'LUDSX3:C'
            -- info-VALUE:   'LUIMAE1:C', 'LUIMADS1:C'
            -- info-VALUE:   'SUADSL:16P' (POTS), 'SUADSL:16I' (ISDN),
            -- info-VALUE:   'SUSDSL:16'
            -- info-VALUE:   'NTAD:1I', 'NTAD:1P'
            -- info-VALUE:   'LIETH25:11', 'LI25:1L' (loadable),
            -- info-VALUE:   'CPE'
            -- info-VALUE:   'UPL:A'
            -- info-ROU:     GET db
            -- info-IMPL:    V2.0->
            -- info-VERCTRL: -
            SYNTAX        DisplayString (SIZE (0..200))
            ACCESS        read-only
            STATUS        mandatory
            DESCRIPTION
                 " Accepted PIU Types of this slot.
		   This attribute identifies the types of Plug-In Units to be
                   supported by this slot. They are separated by newline
                   characters. That means 'CR LF'.
                   This attribute only supplies if the Equipment holder
                   instance represents a slot.  "
            ::= { xldv20HwEquipHolderEntry 2 }

         xldv20EqhSlotStatus OBJECT-TYPE
            -- info-VALUE:   unknown(0) (default), used(1), empty(2)
            -- info-ROU:     GET db
            -- info-IMPL:    V2.0->
            -- info-VERCTRL: -
            SYNTAX        Xldv20SlotStatus
            ACCESS        read-only
            STATUS        mandatory
            DESCRIPTION
                 " Indicates whether a slot is empty or used.
                   This attribute only supplies if the Equipment holder
                   instance represents a slot. "
            ::= { xldv20HwEquipHolderEntry 3 }

         xldv20EqhSwVersion OBJECT-TYPE
            -- info-VALUE:   Version of SW load
            -- info-ROU:     GET db
            -- info-IMPL:    V2.0->
            -- info-VERCTRL: -
            SYNTAX        OCTET STRING ( SIZE (0..10) )
            ACCESS        read-only
            STATUS        mandatory
            DESCRIPTION
                 " Identifies the software load of this PIU.
		 This attribute identifies the software load, if there
                   is any, which is currently designated as the one to
                   be loaded to the plug-in-unit whenever an automatic
                   reload of software is needed.
                   This attribute only applies if the equipment holder
                   instance represents a slot.
                   Default value for not loadable units is \0 . "
            ::= { xldv20HwEquipHolderEntry 4 }

         xldv20EqhMnemoCode OBJECT-TYPE
            -- info-VALUE:   Mnemo Code of PIU.
            -- info-ROU:     GET db
            -- info-IMPL:    V2.0->
            -- info-VERCTRL: -
            SYNTAX        OCTET STRING ( SIZE (0..19) )
            ACCESS        read-only
            STATUS        mandatory
            DESCRIPTION
                 " The mnemo code used to retrieve the SW
                   loadfile for the plug-in unit.
                   Default value for not loadable units is \0 . "
            ::= { xldv20HwEquipHolderEntry 5 }

         xldv20EqhFwCode OBJECT-TYPE
            -- info-VALUE:   FW code
            -- info-ROU:     GET db
            -- info-IMPL:    V2.0->
            -- info-VERCTRL: -
            SYNTAX        OCTET STRING ( SIZE (0..10) )
            ACCESS        read-only
            STATUS        mandatory
            DESCRIPTION
                 " The FW code used to retrieve the SW
                   loadfile for the plug-in unit.
                   Default value for not loadable units is \0 . "
            ::= { xldv20HwEquipHolderEntry 6 }

         xldv20EqhRiMnemoCode OBJECT-TYPE
            -- info-VALUE:   Default: "\0"
            -- info-ROU:     GET hm
            -- info-IMPL:    V2.0->
            -- info-VERCTRL: -
            SYNTAX        DisplayString (SIZE (0..20))
            ACCESS        read-only
            STATUS        mandatory
            DESCRIPTION
                 " This attribute specifies the mnemo code of the currently plugged
                   PIU. "
            ::= { xldv20HwEquipHolderEntry 7 }

         xldv20EqhRiFwItemNumber OBJECT-TYPE
            -- info-VALUE:   Default: "\0"
            -- info-ROU:     GET hm
            -- info-IMPL:    V2.0->
            -- info-VERCTRL: -
            SYNTAX        DisplayString (SIZE (0..20))
            ACCESS        read-only
            STATUS        mandatory
            DESCRIPTION
                 " This attribute specifies the FW item number of the currently
                   plugged PIU. "
            ::= { xldv20HwEquipHolderEntry 8 }

         xldv20EqhRiFwIssue OBJECT-TYPE
            -- info-VALUE:   Default: "\0"
            -- info-ROU:     GET hm
            -- info-IMPL:    V2.0->
            -- info-VERCTRL: -
            SYNTAX        DisplayString (SIZE (0..10))
            ACCESS        read-only
            STATUS        mandatory
            DESCRIPTION
                 " This attribute specifies the FW item issue of the currently
                   plugged PIU. "
            ::= { xldv20HwEquipHolderEntry 9 }

         xldv20EqhRiHwItemNumber OBJECT-TYPE
            -- info-VALUE:   Default: "\0"
            -- info-ROU:     GET hm 
            -- info-IMPL:    V2.0->
            -- info-VERCTRL: -
            SYNTAX        DisplayString (SIZE (0..20))
            ACCESS        read-only
            STATUS        mandatory
            DESCRIPTION
                 " This attribute specifies the HW item number of the currently
                   plugged PIU. "
            ::= { xldv20HwEquipHolderEntry 10 }

         xldv20EqhRiHwIssue OBJECT-TYPE
            -- info-VALUE:   Default: "\0"
            -- info-ROU:     GET hm 
            -- info-IMPL:    V2.0->
            -- info-VERCTRL: -
            SYNTAX        DisplayString (SIZE (0..10))
            ACCESS        read-only
            STATUS        mandatory
            DESCRIPTION
                 " This attribute specifies the HW item issue of the currently
                   plugged PIU. "
            ::= { xldv20HwEquipHolderEntry 11 }

         xldv20EqhRiSerialNumber OBJECT-TYPE
            -- info-VALUE:   Default: "\0"
            -- info-ROU:     GET hm 
            -- info-IMPL:    V2.0->
            -- info-VERCTRL: -
            -- info-VERCTRL: -
            SYNTAX        DisplayString (SIZE (0..10))
            ACCESS        read-only
            STATUS        mandatory
            DESCRIPTION
                 " This attribute specifies the Serial Number of the currently
                   plugged PIU. "
            ::= { xldv20HwEquipHolderEntry 12 }


         -- --------------------------------------------------------------
         --            Hardware Plug-In Unit Table
         -- --------------------------------------------------------------

         xldv20HwPlugInUnitTable OBJECT-TYPE
            -- info-IMPL:    V2.0->
            -- info-VERCTRL: -
            SYNTAX        SEQUENCE OF Xldv20HwPlugInUnitEntry
            ACCESS        not-accessible
            STATUS        mandatory
            DESCRIPTION
                 " Table containing the plug-in unit entries . "
            --DEFAULT test-function-async     fsnPiuEntryTest
            --DEFAULT next-function-async     fsnPiuEntryNext
            --DEFAULT set-function-async      fsnPiuEntrySet
            --DEFAULT get-function-async      fsnPiuEntryGet
            ::= { xldv20Hwm 6 }

         xldv20HwPlugInUnitEntry OBJECT-TYPE
            -- info-IMPL:    V2.0->
            -- info-VERCTRL: -
            SYNTAX        Xldv20HwPlugInUnitEntry
            ACCESS        not-accessible
            STATUS        mandatory
            DESCRIPTION
                 " Entry of plug in unit table.
		 Each entry is used to represent equipment that is inserted
                   (plugged into) and removed from slots of the ATM NE .
                   Notifications : 
                     xldv20TrStateChangeOper.
                     xldv20TrStateChangeAdmin.
                     xldv20TrTrObjCreate.
		     xldv20TrObjDelete.
                     Alarm traps when a fault has been detected or cleared. "
            INDEX { xldv20HwUnitIndex }
            ::= { xldv20HwPlugInUnitTable 1 }

         Xldv20HwPlugInUnitEntry ::=
            SEQUENCE { xldv20PiuAdminState          Xldv20AdminState,
                       xldv20PiuAvailStatus         Xldv20AvailStatus,
                       xldv20PiuOperState           Xldv20OperState,
                       xldv20PiuType                DisplayString,
                       xldv20PiuAlarmSeverityIndex  Xldv20AlmSevProfileIndex,
                       xldv20PiuAlarmFilteringIndex Xldv20AlmFiltProfileIndex,
                       xldv20PiuUpgradeResult       Xldv20ControlReq
                     }

         xldv20PiuAdminState OBJECT-TYPE
            -- info-VALUE:   unlocked(1), locked(2)
            -- info-ROU:     GET db  SET hm 
            -- info-IMPL:    V2.0->
            -- info-VERCTRL: -
            SYNTAX        Xldv20AdminState
            ACCESS        read-write
            STATUS        mandatory
            DESCRIPTION
                 " This attribute is used to activate (unlock) and deactivate
                   (lock) the functions performed by the plug-in unit.
                   Default is locked except for LU155:OM, LU155:OL, LUPON:O,
                   LUDSX3:C. For LU155:OM, LU155:OL, LUPON:O, LUDSX3:C locking
                   is only allowed from LCT.
                   In the transition from lock to unlock the Plug-In Unit is
                   diagnosed. "
            ::= { xldv20HwPlugInUnitEntry 1 }

         xldv20PiuAvailStatus OBJECT-TYPE
            -- info-VALUE:   available(1), failed(2), degraded(3), offline(4)
            -- info-VALUE:   notInstalled(5), dependency(7)
            -- info-ROU:     GET db
            -- info-IMPL:    V2.0->
            -- info-VERCTRL: -
            SYNTAX        Xldv20AvailStatus
            ACCESS        read-only
            STATUS        mandatory
            DESCRIPTION
                 " The availability status of a plug-in unit is described with
                   this attribute. "
            ::= { xldv20HwPlugInUnitEntry 2 }

         xldv20PiuOperState OBJECT-TYPE
            -- info-VALUE:   enabled(1), disabled(2)
            -- info-ROU:     GET db
            -- info-IMPL:    V2.0->
            -- info-VERCTRL: -
            SYNTAX        Xldv20OperState
            ACCESS        read-only
            STATUS        mandatory
            DESCRIPTION
                 " The operational state of plug in unit. "
            ::= { xldv20HwPlugInUnitEntry 3 }

         xldv20PiuType OBJECT-TYPE
            -- info-VALUE:   see xldv20EqhAccPiuTypes
            -- info-ROU:     GET db
            -- info-IMPL:    V2.0->
            -- info-VERCTRL: -
            SYNTAX        DisplayString (SIZE (0..20))
            ACCESS        read-only 
            STATUS        mandatory
            DESCRIPTION
                 " Identifier for the type of a plug-in unit. 
                   See description of xldv20EqhAccPiuTypes for possible string values. "
            ::= { xldv20HwPlugInUnitEntry 4 }

         xldv20PiuAlarmSeverityIndex OBJECT-TYPE
            -- info-VALUE:   1..40
            -- info-ROU:     GET db  SET db
            -- info-IMPL:    V2.0->
            -- info-VERCTRL: -
            SYNTAX        Xldv20AlmSevProfileIndex
            ACCESS        read-write
            STATUS        mandatory
            DESCRIPTION
                 " It is a pointer to the instance of the alarm severity
                   assignment profile managed entity that contains the severity
                   assignments for the alarms reported by this managed entity.
                   Default is 1. "
            ::= { xldv20HwPlugInUnitEntry 5 }

         xldv20PiuAlarmFilteringIndex OBJECT-TYPE
            -- info-VALUE:   1..40
            -- info-ROU:     GET db
            -- info-IMPL:    V2.0->
            -- info-VERCTRL: -
            SYNTAX        Xldv20AlmFiltProfileIndex
            ACCESS        read-only
            STATUS        mandatory
            DESCRIPTION
                 " It is a pointer to the instance of the alarm filtering
                   assignment profile managed entity that contains the filtering
                   assignments for the alarms reported by this managed entity.
                   (Not implemented yet) . "
            ::= { xldv20HwPlugInUnitEntry 6 }

    xldv20PiuUpgradeResult OBJECT-TYPE
       -- info-VALUE:   SW upgrade task states :
       -- info-VALUE:   sutInitialized,sutToDo
       -- info-VALUE:   sutStarted,sutCrashed 
       -- info-VALUE:   sutFtpDone,sutDone
       -- info-VALUE:   sutReadyForReset,sutObsolete
       -- info-VALUE:   Result values at end of task :
       -- info-VALUE:   sucUpgrStartRequest,
       -- info-VALUE:   sucActivateLoad, sucReadSAPSContentFile,
       -- info-VALUE:   sucGetSwVersions, sucUpgrMissParameter,
       -- info-VALUE:   sucGetSwVersionsFailed
       -- info-VALUE:   sucOk ,sucNotOk
       -- info-VALUE:   sucDbAccessFailed ,sucPiuUnlocked
       -- info-VALUE:   sucTransmissionError ,sucWrongSwVersion
       -- info-VALUE:   sucUnitTypeMismatch
       -- info-VALUE:   sucFtpTransError ,sucFtpCrcError
       -- info-VALUE:   sucSwHwMismatch ,sucUpgrWrongAvState
       -- info-VALUE:   sucFepromCopyFault ,sucUpdateDescFileFailed
       -- info-VALUE:   sucFtpServerNoteAvailable ,sucFtpSendError
       -- info-VALUE:   sucDbBackupFault ,sucUpgradeComplete
       -- info-VALUE:   sucUpgradeNotComplete
       -- info-VALUE:   sucUpgrTaskCreationFault
       -- info-VALUE:   sucUpgrDbAccessFault
       -- info-ROU:     GET db
       -- info-IMPL:    V2.0->
       -- info-VERCTRL: -
       SYNTAX        Xldv20ControlReq
       ACCESS        read-only
       STATUS        mandatory
       DESCRIPTION
          " Informs about the status of the SW upgrade task during
	  loading and the result at the end of loading the current plug-in unit. "
        ::= { xldv20HwPlugInUnitEntry 7 }


         -- --------------------------------------------------------------
         --                    HW Unit control subgroup
         -- --------------------------------------------------------------

         xldv20HwuControl OBJECT IDENTIFIER ::= { xldv20Hwm 7 }
            -- info-IMPL:    V2.0->
            -- info-VERCTRL: -

         -- This managed entity manages the creation and deletion of Hw Units.
         -- XLDV2.0 : The XLD NE starts with static pre-configuration of HWM and
         -- TLM tables. 
         -- Only the command createHwUnit for HwUnits of type plugInUnit is supported.
         -- This command only modifies the xldv20PiuType attribute.
         -- Command deleteHwUnit is not supported.

         xldv20HwuControlReq OBJECT-TYPE
            -- info-VALUE:   createHwUnit, deleteHwUnit
            -- info-ROU:     GET db  SET hm
            -- info-IMPL:    V2.0->
            -- info-VERCTRL: -
            SYNTAX        Xldv20ControlReq
            ACCESS        read-write
            STATUS        mandatory
            DESCRIPTION
	         " This attribute identifies the control command for creating or
                   deleting a HW unit.
                   Notifications : xldv20TrHwuControl when command is finished. "
            --DEFAULT test-function-async     fsnHwuTest
            --DEFAULT next-function-async     fsnHwuNext
            --DEFAULT set-function-async      fsnHwuSet
            --DEFAULT get-function-async      fsnHwuGet
            ::= { xldv20HwuControl 1 }

         xldv20HwuControlStatus OBJECT-TYPE
            -- info-VALUE:   requestIdle(1), requestBusy(2), requestPassed(3)
            -- info-VALUE:   requestFailed(4)
            -- info-ROU:     GET db
            -- info-IMPL:    V2.0->
            -- info-VERCTRL: -
            SYNTAX        Xldv20ControlStatus
            ACCESS        read-only
            STATUS        mandatory
            DESCRIPTION
                 " The status of a control request. "
            --DEFAULT next-function-async     fsnHwuNext
            --DEFAULT get-function-async      fsnHwuGet
            ::= { xldv20HwuControl 2 }

         xldv20HwuUnitType OBJECT-TYPE
            -- info-VALUE:   equipment(V2.0->), equipmentHolder(V2.0->), plugInUnit
            -- info-ROU:     GET db SET db
            -- info-IMPL:    V2.0->
            -- info-VERCTRL: -
            SYNTAX        Xldv20HwUnitType
            ACCESS        read-write
            STATUS        mandatory
            DESCRIPTION
                 " Identifies the type of hardware unit which should be created.
                   The values are equipment, equipmentHolder and plugInUnit .
                   The following entities can not be created: 
		   atmNe.
                   equipment (DSLAM). 
		   equipmentHolder (basic shelf).
                   equipmentHolder (slot1-slot32 of basic shelf). "
            --DEFAULT test-function-async     fsnHwuTest
            --DEFAULT next-function-async     fsnHwuNext
            --DEFAULT set-function-async      fsnHwuSet
            --DEFAULT get-function-async      fsnHwuGet
            ::= { xldv20HwuControl 3 }

         xldv20HwuEquType OBJECT-TYPE
        -- info-VALUE:   ntAdsl, ntVdsl, ntCpe
        -- info-ROU:     GET db  SET db
        -- info-IMPL:    V2.0->
        -- info-VERCTRL: -
        SYNTAX        OCTET STRING ( SIZE (0..21) )
        ACCESS        read-only
        STATUS        mandatory
        DESCRIPTION
             " Indicates the equipment which should be created
               (ntAdsl or ntVdsl or ntCpe). Default is \0. "
        --DEFAULT next-function-async     fsnHwuNext
        --DEFAULT get-function-async      fsnHwuGet
        ::= { xldv20HwuControl 4 }

     xldv20HwuEqhType OBJECT-TYPE
        -- info-VALUE:   extendedShelf(4), ntAdslShelf(5), ntVdslShelf(6)
        -- info-VALUE:   cpeShelf(7)
        -- info-ROU:     GET db  SET db
        -- info-VERCTRL: -
        SYNTAX        Xldv20EqhType
        ACCESS        read-only
        STATUS        mandatory
        DESCRIPTION
             " Indicates the equipmentHolder which should be created (extendedShelf or
               ntAdslShelf or ntVdslShelf) . "
        --DEFAULT get-function-async      fsnHwuGet
        --DEFAULT next-function-async     fsnHwuNext
        ::= { xldv20HwuControl 5 }

     xldv20HwuPiuType OBJECT-TYPE
        -- info-VALUE:   any PIU, but not CI* and LU*
        -- info-ROU:     GET db  SET db
        -- info-IMPL:    V2.0->
        -- info-VERCTRL: -
        SYNTAX        OCTET STRING ( SIZE (0..200) ) 
        ACCESS        read-write
        STATUS        mandatory
        DESCRIPTION
             " Identifies the type of a plug-in unit which should be created.
               The following entities cannot be created or deleted : LU*, and CI .
               Default is \0. "
        --DEFAULT test-function-async     fsnHwuTest
        --DEFAULT next-function-async     fsnHwuNext
        --DEFAULT set-function-async      fsnHwuSet
        --DEFAULT get-function-async      fsnHwuGet
        ::= { xldv20HwuControl 6 }

     xldv20HwuContainingUnitIndex OBJECT-TYPE
        -- info-VALUE:   0..65535
        -- info-ROU:     GET db  SET db
        -- info-IMPL:    V2.0->
        -- info-VERCTRL: -
        SYNTAX        Unsigned16
        ACCESS        read-write
        STATUS        mandatory
        DESCRIPTION
             " Identifies the managed entity which contains the created unit . "
        --DEFAULT test-function-async     fsnHwuTest
        --DEFAULT next-function-async     fsnHwuNext
        --DEFAULT set-function-async      fsnHwuSet
        --DEFAULT get-function-async      fsnHwuGet
        ::= { xldv20HwuControl 7 }

     xldv20HwuContainedUnitAddr OBJECT-TYPE
        -- info-VALUE:   1..512
        -- info-ROU:     GET db  SET db
        -- info-IMPL:    V2.0->
        -- info-VERCTRL: -
        SYNTAX        INTEGER(1..512)
        ACCESS        read-write
        STATUS        mandatory
        DESCRIPTION
             " Identifies the index of the contained unit, which should be created,
	     within the containing unit . "
        --DEFAULT test-function-async     fsnHwuTest
        --DEFAULT next-function-async     fsnHwuNext
        --DEFAULT set-function-async      fsnHwuSet
        --DEFAULT get-function-async      fsnHwuGet
        ::= { xldv20HwuControl 8 }

     xldv20HwuUnitIndex OBJECT-TYPE
        -- info-VALUE:   0..65535
        -- info-ROU:     GET db  SET db
        -- info-IMPL:    V2.0->
        -- info-VERCTRL: -
        SYNTAX        Unsigned16
        ACCESS        read-write
        STATUS        mandatory
        DESCRIPTION
             " Identifies the HW Unit which should be deleted . "
        --DEFAULT test-function-async     fsnHwuTest
        --DEFAULT next-function-async     fsnHwuNext
        --DEFAULT set-function-async      fsnHwuSet
        --DEFAULT get-function-async      fsnHwuGet
        ::= { xldv20HwuControl 9 }

     xldv20HwuControlTimer OBJECT-TYPE
        -- info-VALUE:   0..2147483647
        -- info-ROU:     GET db
        -- info-IMPL:    V2.0->
        -- info-VERCTRL: -
        SYNTAX        Unsigned32
        ACCESS        read-only
        STATUS        mandatory
        DESCRIPTION
              " The maximum wait time for the manager when a create
                or delete HW unit request cannot be executed
                immediately ( value commExecStarted in GetResponse
                for xldv20HwuControlReq ). "
        --DEFAULT next-function-async     fsnHwuNext
        --DEFAULT get-function-async      fsnHwuGet
        ::= { xldv20HwuControl 10 }

         xldv20HwuControlReqResult OBJECT-TYPE
            -- info-VALUE:   createHwUnit(command), deleteHwUnit(command)
            -- info-VALUE:   noRequest, commExecStarted,
            -- info-VALUE:   requestBusy, setDataFailed,
            -- info-VALUE:   aswTimeout, commandFailed, commandSucceeded, 
            -- info-VALUE:   hwuParamFaulty, hwuCommandFailed,
            -- info-VALUE:   hwuObjExists, hwuEquTypeNotAvail,
            -- info-VALUE:   hwuEqhTypeNotAvail, hwuPiuTypeNotAvail,
            -- info-VALUE:   hwuPiuTypeNotAccepted(1007),
            -- info-VALUE:   hwuContainingUnitNotAvail(1008),
            -- info-VALUE:   hwuObjNotAvail, hwuObjNotEmpty,
            -- info-VALUE:   hwuObjNotLocked, hwuObjNotValid
            -- info-VALUE:   hwuCreateHwUnitComplete
            -- info-VALUE:   hwuCcExisting,hwuUpgradeRunning
            -- info-ROU:     GET db
            -- info-IMPL:    V2.0->
            -- info-VERCTRL: -
            SYNTAX        Xldv20ControlReq
            ACCESS        read-only
            STATUS        mandatory
            DESCRIPTION
                 " The result of the last user command. "
            --DEFAULT next-function-async     fsnHwuNext
            --DEFAULT get-function-async      fsnHwuGet
        ::= { xldv20HwuControl 11 }

         xldv20HwuControlTimeStamp OBJECT-TYPE
            -- info-VALUE:   0..2Giga
            -- info-ROU:     GET db
            -- info-IMPL:    V2.0->
            -- info-VERCTRL: -
            SYNTAX        TimeTicks
            ACCESS        read-only
            STATUS        mandatory
            DESCRIPTION
               " The time stamp of the last command (end of command). "
            --DEFAULT next-function-async     fsnHwuNext
            --DEFAULT get-function-async      fsnHwuGet
        ::= { xldv20HwuControl 12 }

     -- --------------------------------------------------------------
     --              Remote Inventory subgroup
     -- --------------------------------------------------------------

     xldv20RemoteInventory OBJECT IDENTIFIER ::= { xldv20Hwm 9 }
        -- info-IMPL:    V2.x

     xldv20RiControlReq OBJECT-TYPE
        -- info-VALUE:   riSingleBoard(205)(command),riAllData(206)(command)
        -- info-ROU:     GET db  SET ri
        -- info-IMPL:    V2.x
        SYNTAX        Xldv20ControlReq
        ACCESS        read-write
        STATUS        mandatory
        DESCRIPTION
             " Feature not supported.
	     This attribute identifies the control commands to get
               information about the boards currently plugged into the
               XLD system. On a request from TMN-OS or LCT, the  
               Product Identification Data (PID) and location data 
               (rack, row, slot) of either a single board or of 
               all boards plugged are collected. These data are sent to 
               to a file at the FTP server.
               Notifications : xldv20TrRemInvReady when the remote inventory data
               have been collected and the resulting file has been sent to the
               FTP server. "
        --DEFAULT test-function-async     fsnRiTest
        --DEFAULT next-function-async     fsnRiNext
        --DEFAULT set-function-async      fsnRiSet
        --DEFAULT get-function-async      fsnRiGet
        ::= { xldv20RemoteInventory 1 }

     xldv20RiControlStatus OBJECT-TYPE
        -- info-VALUE:   requestIdle, requestBusy, requestPassed
        -- info-VALUE:   requestFailed
        -- info-ROU:     GET db
        -- info-IMPL:    V2.x
        -- info-VERCTRL: -
        SYNTAX        Xldv20ControlStatus
        ACCESS        read-only
        STATUS        mandatory
        DESCRIPTION
             " The status of a control request. "
        --DEFAULT next-function-async     fsnRiNext
        --DEFAULT get-function-async      fsnRiGet
        ::= { xldv20RemoteInventory 2 }

     xldv20RiControlTimer OBJECT-TYPE
        -- info-VALUE:   0..2147483647
        -- info-ROU:     GET db
        -- info-IMPL:    V2.x
        -- info-VERCTRL: -
        SYNTAX        Unsigned32
        ACCESS        read-only
        STATUS        mandatory
        DESCRIPTION
              " The maximum wait time for the manager when remote
                inventory data retrieve request cannot be executed
                immediately (value commExecStarted in the result attribute
                xldv20RiControlReqResult). 
                The manager reads this value from the DSLAM.
                The end of request indicates the trap xldv20TrRemInvReady . "
        --DEFAULT next-function-async     fsnRiNext
        --DEFAULT get-function-async      fsnRiGet
        ::= { xldv20RemoteInventory 3 }

     xldv20RiResultFilePath OBJECT-TYPE
        -- info-VALUE:   -
        -- info-ROU:     GET db  SET db
        -- info-IMPL:    V2.x
        -- info-VERCTRL: -
        SYNTAX        OCTET STRING ( SIZE (0..200) )
        ACCESS        read-write
        STATUS        mandatory
        DESCRIPTION
             " The destination path where the file containing
               the remote inventory data should be stored on the 
               FTP server. If this attribute does not contain a valid path
               name no remote inventory data will be transmitted . "
        --DEFAULT test-function-async     fsnRiTest
        --DEFAULT next-function-async     fsnRiNext
        --DEFAULT set-function-async      fsnRiSet
        --DEFAULT get-function-async      fsnRiGet
        ::= { xldv20RemoteInventory 4 }

     xldv20RiHwUnitIndex OBJECT-TYPE
        -- info-VALUE:   0..65535
        -- info-ROU:     GET db SET db
        -- info-IMPL:    V2.x
        -- info-VERCTRL: -
        SYNTAX        Unsigned16
        ACCESS        read-write
        STATUS        mandatory
        DESCRIPTION
              " The HwUnitIndex of the requested board.
               if remote inventory data for a single board are requested. "
        --DEFAULT test-function-async     fsnRiTest
        --DEFAULT next-function-async     fsnRiNext
        --DEFAULT set-function-async      fsnRiSet
        --DEFAULT get-function-async      fsnRiGet
        ::= { xldv20RemoteInventory 5 }

     xldv20RiControlReqResult OBJECT-TYPE
        -- info-VALUE:   riSingleBoard(command),riAllData(command)
        -- info-VALUE:   noRequest, commandFailed, commandSucceeded,
        -- info-VALUE:   commExecStarted,paramFaulty
        -- info-VALUE:   requestBusy,setDataFailed,
        -- info-VALUE:   aswTimeout,
        -- info-ROU:     GET db
        -- info-IMPL:    V2.x
        -- info-VERCTRL: -
        SYNTAX        Xldv20ControlReq
        ACCESS        read-only
        STATUS        mandatory
        DESCRIPTION
              " The result of the last user command. "
       --DEFAULT next-function-async     fsnRiNext
       --DEFAULT get-function-async      fsnRiGet
        ::= { xldv20RemoteInventory 6 }

      xldv20RiControlTimeStamp OBJECT-TYPE
         -- info-VALUE:   0..2Giga
         -- info-ROU:     GET db
         -- info-IMPL:    V2.x
         -- info-VERCTRL: -
         SYNTAX        TimeTicks
         ACCESS        read-only
         STATUS        mandatory
         DESCRIPTION
            " The time stamp of the last command (end of command). "
       --DEFAULT next-function-async     fsnRiNext
       --DEFAULT get-function-async      fsnRiGet
        ::= { xldv20RemoteInventory 7 }

         -- --------------------------------------------------------------
         --               Hardware Unit/TLM Interface Mapping Table 
         -- --------------------------------------------------------------

         xldv20HwUnitMappingTable OBJECT-TYPE
            -- info-IMPL:    V2.0->
            -- info-VERCTRL: -
            SYNTAX        SEQUENCE OF Xldv20HwUnitMappingEntry
            ACCESS        not-accessible
            STATUS        mandatory
            DESCRIPTION
                 " The table maps hardware units ('HwUnitIndex') to
		 TLM interfaces ('IfIndex') accociated to this hardware. "
            --DEFAULT next-function-async     fsnHwmEntryNext
            --DEFAULT get-function-async      fsnHwmEntryGet
            ::= { xldv20Hwm 10 }

         xldv20HwUnitMappingEntry OBJECT-TYPE
            -- info-IMPL:    V2.0->
            -- info-VERCTRL: -
            SYNTAX        Xldv20HwUnitMappingEntry
            ACCESS        not-accessible
            STATUS        mandatory
            DESCRIPTION
                 " An entry of the xldv20HwUnitMappingTable.  "
            INDEX { xldv20HwmHwUnitIndex,
	            xldv20HwmIfIndex }
            ::= { xldv20HwUnitMappingTable 1 }

         Xldv20HwUnitMappingEntry ::=
            SEQUENCE { xldv20HwmHwUnitIndex    Unsigned16,
                       xldv20HwmIfIndex        Unsigned16 }

         xldv20HwmHwUnitIndex OBJECT-TYPE
            -- info-VALUE:   0..65535
            -- info-ROU:     GET db
            -- info-IMPL:    V2.0->
            -- info-VERCTRL: -
            SYNTAX        Unsigned16
            ACCESS        read-only
            STATUS        mandatory
            DESCRIPTION
                 " The 'HwUnitIndex' of the selected hardware unit. "
            ::= { xldv20HwUnitMappingEntry 1 }

         xldv20HwmIfIndex OBJECT-TYPE
            -- info-VALUE:   0..65535
            -- info-ROU:     GET db
            -- info-IMPL:    V2.0->
            -- info-VERCTRL: -
            SYNTAX        Unsigned16
            ACCESS        read-only
            STATUS        mandatory
            DESCRIPTION
                 " The 'IfIndex' of a TLM interface
		 on the selected hardware unit. "
            ::= { xldv20HwUnitMappingEntry 2 }

     -- ==============================================================
     --    T r u n k / L i n e   M a i n t e n a n c e   G r o u p
     -- ==============================================================

     -- --------------------------------------------------------------
     --                   TLM Interface Table
     -- --------------------------------------------------------------

     xldv20IfTable OBJECT-TYPE
        -- info-IMPL:    V2.0->
        -- info-VERCTRL: -
        SYNTAX        SEQUENCE OF Xldv20IfEntry
        ACCESS        not-accessible
        STATUS        mandatory
        DESCRIPTION
             " The TLM interface table. "
        --DEFAULT test-function-async     fsnIfEntryTest
        --DEFAULT next-function-async     fsnIfEntryNext
        --DEFAULT set-function-async      fsnIfEntrySet
        --DEFAULT get-function-async      fsnIfEntryGet
        ::= { xldv20Tlm 1 }

     xldv20IfEntry OBJECT-TYPE
        -- info-IMPL:    V2.0->
        -- info-VERCTRL: -
        SYNTAX        Xldv20IfEntry
        ACCESS        not-accessible
        STATUS        mandatory
        DESCRIPTION
             " An entry in the TLM interface table. Each entry represents
               either a physical path termination point (PPTP) or a
               TC adaptor (tcAdaptor).
               Notifications :
               alarm traps when a fault has been detected or cleared.
               xldv20TrStateChangeOper.
               xldv20TrStateChangeAdmin. "
        INDEX         { xldv20IfIndex }
        ::= { xldv20IfTable 1 }

     Xldv20IfEntry ::=
          SEQUENCE { xldv20IfIndex                Unsigned16,
                     xldv20IfType                 Xldv20IfType,
                     xldv20IfLineIndex            Unsigned16,
                     xldv20IfHwUnitIndex          Unsigned16,
                     xldv20IfHwPortId             INTEGER,
                     xldv20IfConnectivityIndex    Unsigned16,
                     xldv20IfOperState            Xldv20OperState,
                     xldv20IfAdminState           Xldv20AdminState,
                     xldv20IfAlarmState           Xldv20AlarmState,
                     xldv20IfAlarmSeverityIndex   Xldv20AlmSevProfileIndex,
                     xldv20IfAlarmFilteringIndex  Xldv20AlmFiltProfileIndex }

     xldv20IfIndex OBJECT-TYPE
        -- info-VALUE:   0..65535
        -- info-ROU:     GET db
        -- info-IMPL:    V2.0->
        -- info-VERCTRL: -
        SYNTAX        Unsigned16
        ACCESS        read-only
        STATUS        mandatory
        DESCRIPTION
             " Index of the table. Identifier of a TLM interface . "
        ::= { xldv20IfEntry 1 }

     xldv20IfType OBJECT-TYPE
        -- info-VALUE:   s1n(1),s1f(2),adc(3),adr(4)
        -- info-VALUE:   ibm(5),tca(6),pon(7) (V2.x) 
        -- info-VALUE:   vdc(8)(V2.x),vdr(9)(V2.x)
        -- info-VALUE:   eth(10)
        -- info-VALUE:   d3n(11),d3f(12)
        -- info-VALUE:   e3n(13), e3f(14)
        -- info-VALUE:   s3n(15), s3f(16)
        -- info-VALUE:   e1nIma(20) (E1 near end)
        -- info-VALUE:   e1fIma(21) (E1 far end)
        -- info-VALUE:   d1nIma(22) (Ds1 near end) (V2.x)
        -- info-VALUE:   d1fIma(23) (Ds1 far end) (V2.x)
        -- info-VALUE:   sdc(24), sdr(25) (SDSL)
        -- info-VALUE:   atmIma(107)  (IMA group)
        -- info-ROU:     GET db
        -- info-IMPL:    V2.0->
        -- info-VERCTRL: -
        SYNTAX        Xldv20IfType
        ACCESS        read-only
        STATUS        mandatory
        DESCRIPTION
             " The type of a TLM interface.
               Supported interface types :
               s1n, s1f. 
               adc, adr.
               ibm, eth.
               s3n, s3f.
               d3n, d3f.
               e3n, e3f.
               e1nIma, e1fIma.
               d1nIma, d1fIma.
               sdc, sdr.
               atmIma  (IMA group).
	       tca.
               In XLDV20 unused :
	       pon.
	       vdc.
	       vdr.
	       d1nIma.
	       d1fIma.  "
        ::= { xldv20IfEntry 2 }

     xldv20IfLineIndex OBJECT-TYPE
        -- info-VALUE:   -
        -- info-ROU:     GET db
        -- info-IMPL:    V2.0->
        -- info-VERCTRL: -
        SYNTAX        Unsigned16
        ACCESS        read-only
        STATUS        mandatory
        DESCRIPTION
             " A unique value to identify interfaces belonging to the
               same line. "
        ::= { xldv20IfEntry 3 }

     xldv20IfHwUnitIndex OBJECT-TYPE
        -- info-VALUE:   0..65535
        -- info-ROU:     GET db
        -- info-IMPL:    V2.0->
        -- info-VERCTRL: -
        SYNTAX        Unsigned16
        ACCESS        read-only
        STATUS        mandatory
        DESCRIPTION
             " The index to identify the hardware unit the physical
               path/TC layer terminates on. "
        ::= { xldv20IfEntry 4 }

     xldv20IfHwPortId OBJECT-TYPE
        -- info-VALUE:   0..255
        -- info-ROU:     GET db
        -- info-IMPL:    V2.0->
        -- info-VERCTRL: -
        SYNTAX        INTEGER (0..255)
        ACCESS        read-only
        STATUS        mandatory
        DESCRIPTION
             " For PPTP it is the associated HW port ID. For TC adaptor
               it is the IfIndex of the PPTP the TC adaptor is connected to. "
        ::= { xldv20IfEntry 5 }

     xldv20IfConnectivityIndex OBJECT-TYPE
        -- info-LEAF:    xldv20ConnectivityIndex
        -- info-TREE:    xldv20Tlm
        -- info-ACC:     ro
        -- info-SYNTAX:  Unsigned16
        -- info-VALUE:   0..65535
        -- info-ROU:     GET db
        -- info-IMPL:    V2.0->
        -- info-VERCTRL: -
        SYNTAX        Unsigned16
        ACCESS        read-only
        STATUS        mandatory
        DESCRIPTION
             " For PPTP it is the associated HW port ID. For TC adaptor
               it is the IfIndex of the PPTP the TC adaptor is connected to. "
        ::= { xldv20IfEntry 6 }

     xldv20IfOperState OBJECT-TYPE
        -- info-VALUE:   enabled(1), disabled(2)
        -- info-ROU:     GET db
        -- info-IMPL:    V2.0->
        -- info-VERCTRL: -
        SYNTAX        Xldv20OperState
        ACCESS        read-only
        STATUS        mandatory
        DESCRIPTION
             " The operational state of this unit. "
        ::= { xldv20IfEntry 7 }

     xldv20IfAdminState OBJECT-TYPE
        -- info-VALUE:   unlocked(1), locked(2)
        -- info-ROU:     GET db  SET tm
        -- info-IMPL:    V2.0->
        -- info-VERCTRL: -
        SYNTAX        Xldv20AdminState
        ACCESS        read-write
        STATUS        mandatory
        DESCRIPTION
             " Activates(unlock) or deactivates(lock) the functionality
               of this managed entity. It must be locked before physical
               looptest has been started. The attribute is not
               configurable during looptest.
               The PPTP of type s1f, s3f, e3f, d3f, e1nIma, e1fIma, 
	       d1nIma, d1fIma and atmIma
	       and the associated tcAdaptors can only be locked from a
               connected LCT. "
        ::= { xldv20IfEntry 8 }

     xldv20IfAlarmState OBJECT-TYPE
        -- info-VALUE:   noAlarm(0), hpEBER(1), hpUNEQ(2), lcd(3)
        -- info-VALUE:   lof(4), lop(5), los(6)
        -- info-VALUE:   msAIS(7), msEBER(8),msSD(10)
        -- info-VALUE:   pAIS(11),pRDI(12), rsEBER(13), slm(14)
        -- info-VALUE:   tim(15), actFault(16),
        -- info-VALUE:   xmissionErr(105), ais(114)
        -- info-VALUE:   plcpLof(116), immMNR(130, lpr(131), lol(132)
        -- info-VALUE:   msRDI(9),
        -- info-VALUE:   rdi(115),plcpRDI(117),internalFault(123)
        -- info-VALUE:   wrongServiceConfigData(141)
        -- info-VALUE:   
        -- info-VALUE:   E1/Ds1 near-end:
        -- info-VALUE:   excBER( 407 ), lif( 408 ), lods( 409 ),
        -- info-VALUE:   
        -- info-VALUE:   E1/Ds1 far-end :
        -- info-VALUE:   txUnusableFe( 410 ), rxUnusableFe( 411 ),
        -- info-VALUE:   rfiIma( 412 ), rai( 413 ),
        -- info-VALUE:   
        -- info-VALUE:   IMA group :
        -- info-VALUE:   startUpFe( 450 ),
        -- info-VALUE:   configAbort( 451 ), configAbortFe( 452 ),
        -- info-VALUE:   insufficientLinks( 453 ), insufficientLinksFe( 454 ),
        -- info-VALUE:   blockedFe( 455 ), imaMinNumOfLinks( 456 )
        -- info-ROU:     GET db
        -- info-IMPL:    V2.0->
        -- info-VERCTRL: -
        SYNTAX        Xldv20AlarmState
        ACCESS        read-only
        STATUS        mandatory
        DESCRIPTION
             " The nature of an alarm at a TLM interface.
	     Values correspond to alarm trap ID`s.
	     Default is noAlarm. "
        ::= { xldv20IfEntry 9 }

     xldv20IfAlarmSeverityIndex OBJECT-TYPE
        -- info-VALUE:   1..40 (default is 1)
        -- info-ROU:     GET db  SET db
        -- info-IMPL:    V2.0->
        -- info-VERCTRL: -
        SYNTAX        Xldv20AlmSevProfileIndex
        ACCESS        read-write
        STATUS        mandatory
        DESCRIPTION
             " The index of the associated entry in the alarm severity
               profile table. These entries contain the severity
               assigments for the alarms reported by this managed
               entity.
               The range of values is:
               1,.., 10: for possible pre-configured alarm severity
                         profiles .
               Default is profile 1. "
        ::= { xldv20IfEntry 10 }

     xldv20IfAlarmFilteringIndex OBJECT-TYPE
        -- info-VALUE:   1..40
        -- info-ROU:     GET db
        -- info-IMPL:    V2.0->
        -- info-VERCTRL: -
        SYNTAX        Xldv20AlmFiltProfileIndex
        ACCESS        read-only
        STATUS        mandatory
        DESCRIPTION
             " It is a pointer to the instance of the alarm filtering
               assignment profile managed entity that contains the filtering
               assignments for the alarms reported by this managed entity. "
        ::= { xldv20IfEntry 11 }

     -- --------------------------------------------------------------
     --              TLM ADSL central control subgroup
     -- --------------------------------------------------------------
     --
     -- This managed entity manages the control commands 
     -- for the ADSL central link.
     --

     xldv20AdcControl OBJECT IDENTIFIER ::= { xldv20Tlm 2 }
            -- info-IMPL:    V2.0->
            -- info-VERCTRL: -

     xldv20AdcCtrlControlReq OBJECT-TYPE
        -- info-VALUE:   activateData
        -- info-ROU:     GET db SET tm  
        -- info-IMPL:    V2.0->
        -- info-VERCTRL: -
        SYNTAX        Xldv20ControlReq
        ACCESS        read-write
        STATUS        mandatory
        DESCRIPTION
             "  ADSL control request object to activate a configured set of
               data (command: activateData), which includes minimum and maximum
               bandwidth in upstream and downstream direction, latency and
               margin. "
        --DEFAULT test-function-async     fsnAdcCtrlTest        
        --DEFAULT next-function-async     fsnAdcCtrlNext
        --DEFAULT set-function-async      fsnAdcCtrlSet
        --DEFAULT get-function-async      fsnAdcCtrlGet
        ::= { xldv20AdcControl 1 }

     xldv20AdcCtrlControlStatus OBJECT-TYPE
        -- info-VALUE:   requestIdle(1), requestBusy(2), requestPassed(3)
        -- info-VALUE:   requestFailed(4)
        -- info-ROU:     GET db
        -- info-IMPL:    V2.0->
        -- info-VERCTRL: -
        SYNTAX        Xldv20ControlStatus
        ACCESS        read-only
        STATUS        mandatory
        DESCRIPTION
             " The status of a control request. "
        --DEFAULT next-function-async     fsnAdcCtrlNext
        --DEFAULT get-function-async      fsnAdcCtrlGet
        ::= { xldv20AdcControl 2 }

     xldv20AdcCtrlIfIndex OBJECT-TYPE
        -- info-VALUE:   0..65535
        -- info-ROU:     GET db SET db
        -- info-IMPL:    V2.0->
        -- info-VERCTRL: -
        SYNTAX        Unsigned16
        ACCESS        read-write
        STATUS        mandatory
        DESCRIPTION
             " It is the relevant interface index of the ADSL central PPTP. "
        --DEFAULT test-function-async     fsnAdcCtrlTest        
        --DEFAULT next-function-async     fsnAdcCtrlNext
        --DEFAULT set-function-async      fsnAdcCtrlSet
        --DEFAULT get-function-async      fsnAdcCtrlGet
        ::= { xldv20AdcControl 3 }

     xldv20AdcCtrlMinRateDn OBJECT-TYPE
        -- info-VALUE:   1..253 (default 1)
        -- info-VALUE:   kbps32Cps75  (   1 ),
        -- info-VALUE:   kbps64Cps150 (   2 ),
        -- info-VALUE:   kbps96Cps226 (   3 ),
        -- info-VALUE:   kbps128Cps301(   4 ),
        -- info-VALUE:   kbps160Cps377(   5 ),
        -- info-VALUE:   kbps192Cps452(   6 ),
        -- info-VALUE:   kbps224Cps528(   7 ),
        -- info-VALUE:   kbps256Cps603(   8 ),
        -- info-VALUE:   kbps288Cps679(   9 ),
        -- info-VALUE:   kbps320Cps754(  10 ),
        -- info-VALUE:   kbps352Cps830(  11 ),
        -- info-VALUE:   kbps384Cps905(  12 ),
        -- info-VALUE:   kbps416Cps981(  13 ),
        -- info-VALUE:   kbps448Cps1056(  14 ),
        -- info-VALUE:   kbps480Cps1132(  15 ),
        -- info-VALUE:   kbps512Cps1207(  16 ),
        -- info-VALUE:   kbps544Cps1283(  17 ),
        -- info-VALUE:   kbps576Cps1358(  18 ),
        -- info-VALUE:   kbps608Cps1433(  19 ),
        -- info-VALUE:   kbps640Cps1509(  20 ),
        -- info-VALUE:   kbps672Cps1584(  21 ),
        -- info-VALUE:   kbps704Cps1660(  22 ),
        -- info-VALUE:   kbps736Cps1735(  23 ),
        -- info-VALUE:   kbps768Cps1811(  24 ),
        -- info-VALUE:   kbps800Cps1886(  25 ),
        -- info-VALUE:   kbps832Cps1962(  26 ),
        -- info-VALUE:   kbps864Cps2037(  27 ),
        -- info-VALUE:   kbps896Cps2113(  28 ),
        -- info-VALUE:   kbps928Cps2188(  29 ),
        -- info-VALUE:   kbps960Cps2264(  30 ),
        -- info-VALUE:   kbps992Cps2339(  31 ),
        -- info-VALUE:   kbps1024Cps2415(  32 ),
        -- info-VALUE:   kbps1056Cps2490(  33 ),
        -- info-VALUE:   kbps1088Cps2566(  34 ),
        -- info-VALUE:   kbps1120Cps2641(  35 ),
        -- info-VALUE:   kbps1152Cps2716(  36 ),
        -- info-VALUE:   kbps1184Cps2792(  37 ),
        -- info-VALUE:   kbps1216Cps2867(  38 ),
        -- info-VALUE:   kbps1248Cps2943(  39 ),
        -- info-VALUE:   kbps1280Cps3018(  40 ),
        -- info-VALUE:   kbps1312Cps3094(  41 ),
        -- info-VALUE:   kbps1344Cps3169(  42 ),
        -- info-VALUE:   kbps1376Cps3245(  43 ),
        -- info-VALUE:   kbps1408Cps3320(  44 ),
        -- info-VALUE:   kbps1440Cps3396(  45 ),
        -- info-VALUE:   kbps1472Cps3471(  46 ),
        -- info-VALUE:   kbps1504Cps3547(  47 ),
        -- info-VALUE:   kbps1536Cps3622(  48 ),
        -- info-VALUE:   kbps1568Cps3698(  49 ),
        -- info-VALUE:   kbps1600Cps3773(  50 ),
        -- info-VALUE:   kbps1632Cps3849(  51 ),
        -- info-VALUE:   kbps1664Cps3924(  52 ),
        -- info-VALUE:   kbps1696Cps4000(  53 ),
        -- info-VALUE:   kbps1728Cps4075(  54 ),
        -- info-VALUE:   kbps1760Cps4150(  55 ),
        -- info-VALUE:   kbps1792Cps4226(  56 ),
        -- info-VALUE:   kbps1824Cps4301(  57 ),
        -- info-VALUE:   kbps1856Cps4377(  58 ),
        -- info-VALUE:   kbps1888Cps4452(  59 ),
        -- info-VALUE:   kbps1920Cps4528(  60 ),
        -- info-VALUE:   kbps1952Cps4603(  61 ),
        -- info-VALUE:   kbps1984Cps4679(  62 ),
        -- info-VALUE:   kbps2016Cps4754(  63 ),
        -- info-VALUE:   kbps2048Cps4830(  64 ),
        -- info-VALUE:   kbps2080Cps4905(  65 ),
        -- info-VALUE:   kbps2112Cps4981(  66 ),
        -- info-VALUE:   kbps2144Cps5056(  67 ),
        -- info-VALUE:   kbps2176Cps5132(  68 ),
        -- info-VALUE:   kbps2208Cps5207(  69 ),
        -- info-VALUE:   kbps2240Cps5283(  70 ),
        -- info-VALUE:   kbps2272Cps5358(  71 ),
        -- info-VALUE:   kbps2304Cps5433(  72 ),
        -- info-VALUE:   kbps2336Cps5509(  73 ),
        -- info-VALUE:   kbps2368Cps5584(  74 ),
        -- info-VALUE:   kbps2400Cps5660(  75 ),
        -- info-VALUE:   kbps2432Cps5735(  76 ),
        -- info-VALUE:   kbps2464Cps5811(  77 ),
        -- info-VALUE:   kbps2496Cps5886(  78 ),
        -- info-VALUE:   kbps2528Cps5962(  79 ),
        -- info-VALUE:   kbps2560Cps6037(  80 ),
        -- info-VALUE:   kbps2592Cps6113(  81 ),
        -- info-VALUE:   kbps2624Cps6188(  82 ),
        -- info-VALUE:   kbps2656Cps6264(  83 ),
        -- info-VALUE:   kbps2688Cps6339(  84 ),
        -- info-VALUE:   kbps2720Cps6415(  85 ),
        -- info-VALUE:   kbps2752Cps6490(  86 ),
        -- info-VALUE:   kbps2784Cps6566(  87 ),
        -- info-VALUE:   kbps2816Cps6641(  88 ),
        -- info-VALUE:   kbps2848Cps6716(  89 ),
        -- info-VALUE:   kbps2880Cps6792(  90 ),
        -- info-VALUE:   kbps2912Cps6867(  91 ),
        -- info-VALUE:   kbps2944Cps6943(  92 ),
        -- info-VALUE:   kbps2976Cps7018(  93 ),
        -- info-VALUE:   kbps3008Cps7094(  94 ),
        -- info-VALUE:   kbps3040Cps7169(  95 ),
        -- info-VALUE:   kbps3072Cps7245(  96 ),
        -- info-VALUE:   kbps3104Cps7320(  97 ),
        -- info-VALUE:   kbps3136Cps7396(  98 ),
        -- info-VALUE:   kbps3168Cps7471(  99 ),
        -- info-VALUE:   kbps3200Cps7547( 100 ),
        -- info-VALUE:   kbps3232Cps7622( 101 ),
        -- info-VALUE:   kbps3264Cps7698( 102 ),
        -- info-VALUE:   kbps3296Cps7773( 103 ),
        -- info-VALUE:   kbps3328Cps7849( 104 ),
        -- info-VALUE:   kbps3360Cps7924( 105 ),
        -- info-VALUE:   kbps3392Cps8000( 106 ),
        -- info-VALUE:   kbps3424Cps8075( 107 ),
        -- info-VALUE:   kbps3456Cps8150( 108 ),
        -- info-VALUE:   kbps3488Cps8226( 109 ),
        -- info-VALUE:   kbps3520Cps8301( 110 ),
        -- info-VALUE:   kbps3552Cps8377( 111 ),
        -- info-VALUE:   kbps3584Cps8452( 112 ),
        -- info-VALUE:   kbps3616Cps8528( 113 ),
        -- info-VALUE:   kbps3648Cps8603( 114 ),
        -- info-VALUE:   kbps3680Cps8679( 115 ),
        -- info-VALUE:   kbps3712Cps8754( 116 ),
        -- info-VALUE:   kbps3744Cps8830( 117 ),
        -- info-VALUE:   kbps3776Cps8905( 118 ),
        -- info-VALUE:   kbps3808Cps8981( 119 ),
        -- info-VALUE:   kbps3840Cps9056( 120 ),
        -- info-VALUE:   kbps3872Cps9132( 121 ),
        -- info-VALUE:   kbps3904Cps9207( 122 ),
        -- info-VALUE:   kbps3936Cps9283( 123 ),
        -- info-VALUE:   kbps3968Cps9358( 124 ),
        -- info-VALUE:   kbps4000Cps9433( 125 ),
        -- info-VALUE:   kbps4032Cps9509( 126 ),
        -- info-VALUE:   kbps4064Cps9584( 127 ),
        -- info-VALUE:   kbps4096Cps9660( 128 ),
        -- info-VALUE:   kbps4128Cps9735( 129 ),
        -- info-VALUE:   kbps4160Cps9811( 130 ),
        -- info-VALUE:   kbps4192Cps9886( 131 ),
        -- info-VALUE:   kbps4224Cps9962( 132 ),
        -- info-VALUE:   kbps4256Cps10037( 133 ),
        -- info-VALUE:   kbps4288Cps10113( 134 ),
        -- info-VALUE:   kbps4320Cps10188( 135 ),
        -- info-VALUE:   kbps4352Cps10264( 136 ),
        -- info-VALUE:   kbps4384Cps10339( 137 ),
        -- info-VALUE:   kbps4416Cps10415( 138 ),
        -- info-VALUE:   kbps4448Cps10490( 139 ),
        -- info-VALUE:   kbps4480Cps10566( 140 ),
        -- info-VALUE:   kbps4512Cps10641( 141 ),
        -- info-VALUE:   kbps4544Cps10716( 142 ),
        -- info-VALUE:   kbps4576Cps10792( 143 ),
        -- info-VALUE:   kbps4608Cps10867( 144 ),
        -- info-VALUE:   kbps4640Cps10943( 145 ),
        -- info-VALUE:   kbps4672Cps11018( 146 ),
        -- info-VALUE:   kbps4704Cps11094( 147 ),
        -- info-VALUE:   kbps4736Cps11169( 148 ),
        -- info-VALUE:   kbps4768Cps11245( 149 ),
        -- info-VALUE:   kbps4800Cps11320( 150 ),
        -- info-VALUE:   kbps4832Cps11396( 151 ),
        -- info-VALUE:   kbps4864Cps11471( 152 ),
        -- info-VALUE:   kbps4896Cps11547( 153 ),
        -- info-VALUE:   kbps4928Cps11622( 154 ),
        -- info-VALUE:   kbps4960Cps11698( 155 ),
        -- info-VALUE:   kbps4992Cps11773( 156 ),
        -- info-VALUE:   kbps5024Cps11849( 157 ),
        -- info-VALUE:   kbps5056Cps11924( 158 ),
        -- info-VALUE:   kbps5088Cps12000( 159 ),
        -- info-VALUE:   kbps5120Cps12075( 160 ),
        -- info-VALUE:   kbps5152Cps12150( 161 ),
        -- info-VALUE:   kbps5184Cps12226( 162 ),
        -- info-VALUE:   kbps5216Cps12301( 163 ),
        -- info-VALUE:   kbps5248Cps12377( 164 ),
        -- info-VALUE:   kbps5280Cps12452( 165 ),
        -- info-VALUE:   kbps5312Cps12528( 166 ),
        -- info-VALUE:   kbps5344Cps12603( 167 ),
        -- info-VALUE:   kbps5376Cps12679( 168 ),
        -- info-VALUE:   kbps5408Cps12754( 169 ),
        -- info-VALUE:   kbps5440Cps12830( 170 ),
        -- info-VALUE:   kbps5472Cps12905( 171 ),
        -- info-VALUE:   kbps5504Cps12981( 172 ),
        -- info-VALUE:   kbps5536Cps13056( 173 ),
        -- info-VALUE:   kbps5568Cps13132( 174 ),
        -- info-VALUE:   kbps5600Cps13207( 175 ),
        -- info-VALUE:   kbps5632Cps13283( 176 ),
        -- info-VALUE:   kbps5664Cps13358( 177 ),
        -- info-VALUE:   kbps5696Cps13433( 178 ),
        -- info-VALUE:   kbps5728Cps13509( 179 ),
        -- info-VALUE:   kbps5760Cps13584( 180 ),
        -- info-VALUE:   kbps5792Cps13660( 181 ),
        -- info-VALUE:   kbps5824Cps13735( 182 ),
        -- info-VALUE:   kbps5856Cps13811( 183 ),
        -- info-VALUE:   kbps5888Cps13886( 184 ),
        -- info-VALUE:   kbps5920Cps13962( 185 ),
        -- info-VALUE:   kbps5952Cps14037( 186 ),
        -- info-VALUE:   kbps5984Cps14113( 187 ),
        -- info-VALUE:   kbps6016Cps14188( 188 ),
        -- info-VALUE:   kbps6048Cps14264( 189 )
        -- info-VALUE:   kbps6080Cps14339( 190 )
        -- info-VALUE:   kbps6112Cps14415( 191 )
        -- info-VALUE:   kbps6144Cps14490( 192 )
        -- info-VALUE:   kbps6176Cps14566( 193 )
        -- info-VALUE:   kbps6208Cps14641( 194 )
        -- info-VALUE:   kbps6240Cps14716( 195 )
        -- info-VALUE:   kbps6272Cps14792( 196 )
        -- info-VALUE:   kbps6304Cps14867( 197 )
        -- info-VALUE:   kbps6336Cps14943( 198 )
        -- info-VALUE:   kbps6368Cps15018( 199 ),
        -- info-VALUE:   kbps6400Cps15094( 200 ),
        -- info-VALUE:   kbps6432Cps15169( 201 ),
        -- info-VALUE:   kbps6464Cps15245( 202 ),
        -- info-VALUE:   kbps6496Cps15320( 203 ),
        -- info-VALUE:   kbps6528Cps15396( 204 ),
        -- info-VALUE:   kbps6560Cps15471( 205 ),
        -- info-VALUE:   kbps6592Cps15547( 206 ),
        -- info-VALUE:   kbps6624Cps15622( 207 ),
        -- info-VALUE:   kbps6656Cps15698( 208 ),
        -- info-VALUE:   kbps6688Cps15773( 209 ),
        -- info-VALUE:   kbps6720Cps15849( 210 ),
        -- info-VALUE:   kbps6752Cps15924( 211 ),
        -- info-VALUE:   kbps6784Cps16000( 212 ),
        -- info-VALUE:   kbps6816Cps16075( 213 ),
        -- info-VALUE:   kbps6848Cps16150( 214 ),
        -- info-VALUE:   kbps6880Cps16226( 215 ),
        -- info-VALUE:   kbps6912Cps16301( 216 ),
        -- info-VALUE:   kbps6944Cps16377( 217 ),
        -- info-VALUE:   kbps6976Cps16452( 218 ),
        -- info-VALUE:   kbps7008Cps16528( 219 ),
        -- info-VALUE:   kbps7040Cps16603( 220 ),
        -- info-VALUE:   kbps7072Cps16679( 221 ),
        -- info-VALUE:   kbps7104Cps16754( 222 ),
        -- info-VALUE:   kbps7136Cps16830( 223 ),
        -- info-VALUE:   kbps7168Cps16905( 224 ),
        -- info-VALUE:   kbps7200Cps16981( 225 ),
        -- info-VALUE:   kbps7232Cps17056( 226 ),
        -- info-VALUE:   kbps7264Cps17132( 227 ),
        -- info-VALUE:   kbps7296Cps17207( 228 ),
        -- info-VALUE:   kbps7328Cps17283( 229 ),
        -- info-VALUE:   kbps7360Cps17358( 230 ),
        -- info-VALUE:   kbps7392Cps17433( 231 ),
        -- info-VALUE:   kbps7424Cps17509( 232 ),
        -- info-VALUE:   kbps7456Cps17584( 233 ),
        -- info-VALUE:   kbps7488Cps17660( 234 ),
        -- info-VALUE:   kbps7520Cps17735( 235 ),
        -- info-VALUE:   kbps7552Cps17811( 236 ),
        -- info-VALUE:   kbps7584Cps17886( 237 ),
        -- info-VALUE:   kbps7616Cps17962( 238 ),
        -- info-VALUE:   kbps7648Cps18037( 239 ),
        -- info-VALUE:   kbps7680Cps18113( 240 ),
        -- info-VALUE:   kbps7712Cps18188( 241 ),
        -- info-VALUE:   kbps7744Cps18264( 242 ),
        -- info-VALUE:   kbps7776Cps18339( 243 ),
        -- info-VALUE:   kbps7808Cps18415( 244 ),
        -- info-VALUE:   kbps7840Cps18490( 245 ),
        -- info-VALUE:   kbps7872Cps18566( 246 ),
        -- info-VALUE:   kbps7904Cps18641( 247 ),
        -- info-VALUE:   kbps7936Cps18716( 248 ),
        -- info-VALUE:   kbps7968Cps18792( 249 ),
        -- info-VALUE:   kbps8000Cps18867( 250 ),
        -- info-VALUE:   kbps8032Cps18943( 251 ),
        -- info-VALUE:   kbps8064Cps19018( 252 ),
        -- info-VALUE:   kbps8096Cps19094( 253 ),
        -- info-ROU:     GET db SET db
        -- info-IMPL:    V2.0->
        -- info-VERCTRL: -
        SYNTAX        Xldv20AdslDataRateDown
        ACCESS        read-write
        STATUS        mandatory
        DESCRIPTION
             " Desired lower limit of downstream data rate. The data rate 
               ranges from 32 to 8096 Kbit/sec and is splitted into units of 32 Kbit/sec.
               This corresponds to a cell rate between 75 and 19094 cells/sec.
               Default is 1 (32 kbps/75 cps). "
        --DEFAULT test-function-async     fsnAdcCtrlTest        
        --DEFAULT next-function-async     fsnAdcCtrlNext
        --DEFAULT set-function-async      fsnAdcCtrlSet
        --DEFAULT get-function-async      fsnAdcCtrlGet
        ::= { xldv20AdcControl 4 }

     xldv20AdcCtrlMinRateUp OBJECT-TYPE
        -- info-VALUE:   1..24 (default 1)
        -- info-VALUE:   for values see Xldv20AdcCtrlMinRateDn
        -- info-ROU:     GET db SET db
        -- info-IMPL:    V2.0->
        -- info-VERCTRL: -
        SYNTAX        Xldv20AdslDataRateUp
        ACCESS        read-write
        STATUS        mandatory
        DESCRIPTION
             " Desired lower limit of upstream data rate. The data rate
               ranges from 32 to 768 Kbit/sec and is splitted into units of 32 Kbit/sec.
               This corresponds to a cell rate between 75 and 1811 cells/sec.
               Default is 1 (32 kbps/75 cps). "
        --DEFAULT test-function-async     fsnAdcCtrlTest        
        --DEFAULT next-function-async     fsnAdcCtrlNext
        --DEFAULT set-function-async      fsnAdcCtrlSet
        --DEFAULT get-function-async      fsnAdcCtrlGet
        ::= { xldv20AdcControl 5 }

     xldv20AdcCtrlMaxRateDn OBJECT-TYPE
        -- info-VALUE:   1..253 (default 253)
        -- info-VALUE:   for values see Xldv20AdcCtrlMinRateDn
        -- info-ROU:     GET db SET db
        -- info-IMPL:    V2.0->
        -- info-VERCTRL: -
        SYNTAX        Xldv20AdslDataRateDown
        ACCESS        read-write
        STATUS        mandatory
        DESCRIPTION
             " Desired upper limit of downstream data rate. The data
	     rate ranges from 32 and 8096 Kbit/sec and 
	     is splitted into units of 32 Kbit/sec.
            This corresponds to a cell rate between 75 and 19094 cells/sec.
            Default is 253 (8096 kbps/19094 cps). "
        --DEFAULT test-function-async     fsnAdcCtrlTest        
        --DEFAULT next-function-async     fsnAdcCtrlNext
        --DEFAULT set-function-async      fsnAdcCtrlSet
        --DEFAULT get-function-async      fsnAdcCtrlGet
        ::= { xldv20AdcControl 6 }

     xldv20AdcCtrlMaxRateUp OBJECT-TYPE
        -- info-VALUE:   1..24 (default 24)
        -- info-VALUE:   for values see Xldv20AdcCtrlMinRateDn
        -- info-ROU:     GET db SET db
        -- info-IMPL:    V2.0->
        -- info-VERCTRL: -
        SYNTAX        Xldv20AdslDataRateUp
        ACCESS        read-write
        STATUS        mandatory
        DESCRIPTION
             " Desired upper limit of upstream data rate. The data rate ranges
               from 32 and 768 Kbit/sec and is splitted into units of 32 Kbit/sec.
               This corresponds to a cell rate between 75 and 1811 cells/sec.
               Default is 24 (768 kbps/1811 cps). "
        --DEFAULT test-function-async     fsnAdcCtrlTest        
        --DEFAULT next-function-async     fsnAdcCtrlNext
        --DEFAULT set-function-async      fsnAdcCtrlSet
        --DEFAULT get-function-async      fsnAdcCtrlGet
        ::= { xldv20AdcControl 7 }

     xldv20AdcCtrlMarginDn OBJECT-TYPE
        -- info-VALUE:   0..15 (default 6)
        -- info-ROU:     GET db SET db
        -- info-IMPL:    V2.0->
        -- info-VERCTRL: -
        SYNTAX        INTEGER (0..15)
        ACCESS        read-write
        STATUS        mandatory
        DESCRIPTION
             " Desired downstream margin in units of dB. "
        --DEFAULT test-function-async     fsnAdcCtrlTest        
        --DEFAULT next-function-async     fsnAdcCtrlNext
        --DEFAULT set-function-async      fsnAdcCtrlSet
        --DEFAULT get-function-async      fsnAdcCtrlGet
        ::= { xldv20AdcControl 8 }

     xldv20AdcCtrlMarginUp OBJECT-TYPE
        -- info-VALUE:   0..15 (default 6)
        -- info-ROU:     GET db SET db
        -- info-IMPL:    V2.0->
        -- info-VERCTRL: -
        SYNTAX        INTEGER (0..15)
        ACCESS        read-write
        STATUS        mandatory
        DESCRIPTION
             " Desired upstream margin in units of dB . "
        --DEFAULT test-function-async     fsnAdcCtrlTest        
        --DEFAULT next-function-async     fsnAdcCtrlNext
        --DEFAULT set-function-async      fsnAdcCtrlSet
        --DEFAULT get-function-async      fsnAdcCtrlGet
        ::= { xldv20AdcControl 9 }

     xldv20AdcCtrlLatencyDn OBJECT-TYPE
        -- info-VALUE:  interleavedLow        (0),
        -- info-VALUE:  interleavedHigh       (1),
        -- info-VALUE:  fast                 (256)
        -- info-VALUE:  (default low)
        -- info-ROU:     GET db SET db
        -- info-IMPL:    V2.0->
        -- info-VERCTRL: -
        SYNTAX        Xldv20Latency
        ACCESS        read-write
        STATUS        mandatory
        DESCRIPTION
             " Selects fast mode or interleaved mode downstream.
               0   = interleavedLow (default).
               1   = interleavedHigh .
	       256 = fast mode. "
        --DEFAULT test-function-async     fsnAdcCtrlTest        
        --DEFAULT next-function-async     fsnAdcCtrlNext
        --DEFAULT set-function-async      fsnAdcCtrlSet
        --DEFAULT get-function-async      fsnAdcCtrlGet
        ::= { xldv20AdcControl 10 }

     xldv20AdcCtrlLatencyUp OBJECT-TYPE
        -- info-VALUE:  interleavedLow        (0),
        -- info-VALUE:  interleavedHigh       (1),
        -- info-VALUE:  fast                 (256)
        -- info-ROU:     GET db SET db
        -- info-IMPL:    V2.0->
        -- info-VERCTRL: -
        SYNTAX        Xldv20Latency
        ACCESS        read-write
        STATUS        mandatory
        DESCRIPTION
             " Selects fast mode or interleaved mode upstream.
               0   = interleavedLow (default).
               1   = interleavedHigh .
	       256 = fast mode. "
        --DEFAULT test-function-async     fsnAdcCtrlTest        
        --DEFAULT next-function-async     fsnAdcCtrlNext
        --DEFAULT set-function-async      fsnAdcCtrlSet
        --DEFAULT get-function-async      fsnAdcCtrlGet
        ::= { xldv20AdcControl 11 }

     xldv20AdcCtrlMinMarginDn OBJECT-TYPE
        -- info-VALUE:   dB-6 (-6),
        -- info-VALUE:   dB-5 (-5),
        -- info-VALUE:   dB-4 (-4),
        -- info-VALUE:   dB-3 (-3),
        -- info-VALUE:   dB-2 (-2),
        -- info-VALUE:   dB-1 (-1),
        -- info-VALUE:   dB0  (0 ),
        -- info-VALUE:   dB1  (1 ),
        -- info-VALUE:   dB2  (2 ),
        -- info-VALUE:   dB3  (3 ),
        -- info-VALUE:   dB4  (4 ),
        -- info-VALUE:   dB5  (5 ),
        -- info-VALUE:   dB6  (6 ),
        -- info-VALUE:   dB7  (7 ),
        -- info-VALUE:   dB8  (8 ),
        -- info-VALUE:   dB9  (9 ),
        -- info-VALUE:   dB10 (10),
        -- info-VALUE:   dB11 (11),
        -- info-VALUE:   dB12 (12),
        -- info-VALUE:   auto (255)
        -- info-ROU:     GET db SET db
        -- info-IMPL:    V2.0->
        -- info-VERCTRL: -
        SYNTAX        Xldv20AdslMinMargin
        ACCESS        read-write
        STATUS        mandatory
        DESCRIPTION
             " Threshold for downstream margin when an alarm
               should be sent. In units of dB.
	       The value auto is the default value and means that 
	       the threshold is calculated from the configured margin :
	       threshold margin down = configured margin down - 6 dB.  "
        --DEFAULT test-function-async     fsnAdcCtrlTest
        --DEFAULT next-function-async     fsnAdcCtrlNext
        --DEFAULT set-function-async      fsnAdcCtrlSet
        --DEFAULT get-function-async      fsnAdcCtrlGet
        ::= { xldv20AdcControl 12 }
 
     xldv20AdcCtrlMinMarginUp OBJECT-TYPE
        -- info-VALUE:   see xldv20AdcCtrlMinMarginDn
        -- info-ROU:     GET db SET db
        -- info-IMPL:    V2.0->
        -- info-VERCTRL: -
        SYNTAX        Xldv20AdslMinMargin
        ACCESS        read-write
        STATUS        mandatory
        DESCRIPTION
             " Threshold for upstream margin when an alarm
               should be sent. In units of dB.
	       The value auto is the default value and means that 
	       the threshold is calculated from the configured margin :
	       threshold margin up = configured margin up - 6 dB.  "
        --DEFAULT test-function-async     fsnAdcCtrlTest
        --DEFAULT next-function-async     fsnAdcCtrlNext
        --DEFAULT set-function-async      fsnAdcCtrlSet
        --DEFAULT get-function-async      fsnAdcCtrlGet
        ::= { xldv20AdcControl 13 }
 
     xldv20AdcCtrlControlReqResult OBJECT-TYPE
        -- info-VALUE:   noRequest, paramFaulty
        -- info-VALUE:   wrongAdminState
        -- info-VALUE:   resourceProblemUpstream, resourceProblemDownstream
        -- info-VALUE:   vpProblemUpstream, vpProblemDownstream
        -- info-VALUE:   bandwidthUpstreamWarning, bandwidthDownstreamWarning
        -- info-VALUE:   mbsUpstreamWarning, mbsDownstreamWarning.
        -- info-VALUE:   requestBusy,setDataFailed
        -- info-VALUE:   aswTimeout, commandFailed, commandSucceeded,
        -- info-VALUE:   wrongXdslServiceType
        -- info-ROU:     GET db
        -- info-IMPL:    V2.0->
        -- info-VERCTRL: -
        SYNTAX        Xldv20ControlReq
        ACCESS        read-only
        STATUS        mandatory
        DESCRIPTION
              " The result of the last user command. "
        --DEFAULT next-function-async     fsnAdcCtrlNext
        --DEFAULT get-function-async      fsnAdcCtrlGet
        ::= { xldv20AdcControl 14 }

     xldv20AdcCtrlXdslServiceType OBJECT-TYPE
        -- info-VALUE:   gDotHsMode (handshake mode, ITU G.994.1)
        -- info-VALUE:   ansiT1Dot413 (full rate mode for ADSL equipment, ITU G.992.1)
        -- info-VALUE:   gDotLiteMode (for UDSL equipment, ITU G.992.2)
        -- info-VALUE:   gDotAll
        -- info-ROU:     GET db SET db
        -- info-IMPL:    V2.0->
        -- info-VERCTRL: -
        SYNTAX        Xldv20XdslServiceType
        ACCESS        read-write
        STATUS        mandatory
        DESCRIPTION
             " The service mode for the DSL line according to ITU norm.
             Supported modes are :
             - gDotHsMode (handshake mode) for automatic link up either to ADSL equipment .
               or to UDSL equipment (G9941).
             - or ansiT1Dot413 for ADSL equipment (fullRateMode, ITU G9921).
             - or gDotLiteMode for UDSL equipment (uawgMode, ITU G9922).
	     - or gDotAll to allow any NT/CPE service type (is determined by the
	       central modem) ."
        --DEFAULT test-function-async     fsnAdcCtrlTest
        --DEFAULT next-function-async     fsnAdcCtrlNext
        --DEFAULT set-function-async      fsnAdcCtrlSet
        --DEFAULT get-function-async      fsnAdcCtrlGet
        ::= { xldv20AdcControl 15 }

      xldv20AdcCtrlControlTimeStamp OBJECT-TYPE
         -- info-VALUE:   0..2Giga
         -- info-ROU:     GET db
         -- info-IMPL:    V2.0->
         -- info-VERCTRL: -
         SYNTAX        TimeTicks
         ACCESS        read-only
         STATUS        mandatory
         DESCRIPTION
            " The time stamp of the last command (end of command). "
        --DEFAULT next-function-async     fsnAdcCtrlNext
        --DEFAULT get-function-async      fsnAdcCtrlGet
        ::= { xldv20AdcControl 16 }

      xldv20AdcCtrlTrainingMode OBJECT-TYPE
         -- info-VALUE:   enableParallelTraining(1),
         -- info-VALUE:   avoidParallelTrainingOnCI(2) (default),
         -- info-VALUE:   avoidParallelTrainingOnSU(3),
         -- info-VALUE:   combinedTraining(4)
         -- info-ROU:     GET db SET db
         -- info-IMPL:    V2.0->
         -- info-VERCTRL: -
         SYNTAX        Xldv20AdcTrainingMode
         ACCESS        read-write
         STATUS        mandatory
         DESCRIPTION
            " Selects between different training modes for ADSL modems. "
        --DEFAULT test-function-async     fsnAdcCtrlTest
        --DEFAULT next-function-async     fsnAdcCtrlNext
        --DEFAULT set-function-async      fsnAdcCtrlSet
        --DEFAULT get-function-async      fsnAdcCtrlGet
        ::= { xldv20AdcControl 17 }
     -- --------------------------------------------------------------
     --                TLM VDSL central control subgroup
     -- --------------------------------------------------------------
     --
     -- This managed entity represents the extension of the VDSL-C interface.
     -- It includes addtional attributes to configure the VDSL link.
     --

     xldv20VdcControl OBJECT IDENTIFIER
        -- info-IMPL:    V2.x
     ::= { xldv20Tlm 3 }

     xldv20VdcCtrlControlReq OBJECT-TYPE
        -- info-VALUE:   activateData
        -- info-ROU:     GET db SET tm  
        -- info-IMPL:    V2.x
        -- info-VERCTRL: -
        SYNTAX        Xldv20ControlReq
        ACCESS        not-accessible
        STATUS        mandatory
        DESCRIPTION
             " Feature not supported.
	     This attribute marks the command to activate a configured set of
             (command: activateData), which includes minimum and maximum
             bandwidth in upstream and downstream direction, latency and some
             additional modem parameters (power boost, warmstart, VDSL mode,
             Sleep mode, PSD mask, power adaptation). "
        --DEFAULT test-function-async     fsnVdcCtrlTest
        --DEFAULT next-function-async     fsnVdcCtrlNext
        --DEFAULT set-function-async      fsnVdcCtrlSet
        --DEFAULT get-function-async      fsnVdcCtrlGet
        ::= { xldv20VdcControl 1 }

     xldv20VdcCtrlControlStatus OBJECT-TYPE
        -- info-VALUE:   requestIdle(1), requestBusy(2), requestPassed(3)
        -- info-VALUE:   requestFailed(4)
        -- info-ROU:     GET db
        -- info-IMPL:    V2.x
        -- info-VERCTRL: -
        SYNTAX        Xldv20ControlStatus
        ACCESS        not-accessible
        STATUS        mandatory
        DESCRIPTION
             " This attribute indicates the status of a control request.
                  requestIdle,
                  requestBusy,
                  requestPassed,
                  requestFailed . "
        --DEFAULT next-function-async     fsnVdcCtrlNext
        --DEFAULT get-function-async      fsnVdcCtrlGet
        ::= { xldv20VdcControl 2 }

     xldv20VdcCtrlIfIndex OBJECT-TYPE
        -- info-VALUE:   0..65535
        -- info-ROU:     GET db SET db
        -- info-IMPL:    V2.x
        -- info-VERCTRL: -
        SYNTAX        Unsigned16
        ACCESS        not-accessible
        STATUS        mandatory
        DESCRIPTION
             " It is the relevant interface index of the VDSL-C PPTP. "
        --DEFAULT test-function-async     fsnVdcCtrlTest
        --DEFAULT next-function-async     fsnVdcCtrlNext
        --DEFAULT set-function-async      fsnVdcCtrlSet
        --DEFAULT get-function-async      fsnVdcCtrlGet
        ::= { xldv20VdcControl 3 }

     xldv20VdcCtrlMinRateDn OBJECT-TYPE
        -- info-VALUE:   (multiples of 810 kbps)
        -- info-VALUE:   2,4,6,8,12,16
        -- info-VALUE:   24,32,48,64
        -- info-ROU:     GET db SET db
        -- info-IMPL:    V2.x
        -- info-VERCTRL: -
        SYNTAX        Xldv20VdcRateDn
        ACCESS        read-write
        STATUS        mandatory
        DESCRIPTION
             " The desired lower limit of the downstream data rate. "
        --DEFAULT test-function-async     fsnVdcCtrlTest
        --DEFAULT next-function-async     fsnVdcCtrlNext
        --DEFAULT set-function-async      fsnVdcCtrlSet
        --DEFAULT get-function-async      fsnVdcCtrlGet
        ::= { xldv20VdcControl 4 }

     xldv20VdcCtrlMinRateUp OBJECT-TYPE
        -- info-VALUE:   (multiples of 810 kbps)
        -- info-VALUE:   1,2,4,8,12,16
        -- info-ROU:     GET db SET db
        -- info-IMPL:    V2.x
        -- info-VERCTRL: -
        SYNTAX        Xldv20VdcRateUp
        ACCESS        not-accessible
        STATUS        mandatory
        DESCRIPTION
             " The desired lower limit of the upstream data rate. "
        --DEFAULT test-function-async     fsnVdcCtrlTest
        --DEFAULT next-function-async     fsnVdcCtrlNext
        --DEFAULT set-function-async      fsnVdcCtrlSet
        --DEFAULT get-function-async      fsnVdcCtrlGet
        ::= { xldv20VdcControl 5 }

     xldv20VdcCtrlMaxRateDn OBJECT-TYPE
        -- info-VALUE:   (multiples of 810 kbps)
        -- info-VALUE:   2,4,6,8,12,16
        -- info-VALUE:   24,32,48,64
        -- info-ROU:     GET db SET db
        -- info-IMPL:    V2.x
        -- info-VERCTRL: -
        SYNTAX        Xldv20VdcRateDn
        ACCESS        not-accessible
        STATUS        mandatory
        DESCRIPTION
             " The upper limit of the downstream data rate. "
        --DEFAULT test-function-async     fsnVdcCtrlTest
        --DEFAULT next-function-async     fsnVdcCtrlNext
        --DEFAULT set-function-async      fsnVdcCtrlSet
        --DEFAULT get-function-async      fsnVdcCtrlGet
        ::= { xldv20VdcControl 6 }

     xldv20VdcCtrlMaxRateUp OBJECT-TYPE
        -- info-VALUE:   (multiples of 810 kbps)
        -- info-VALUE:   1,2,4,8,12,16
        -- info-ROU:     GET db SET db
        -- info-IMPL:    V2.x
        -- info-VERCTRL: -
        SYNTAX        Xldv20VdcRateUp
        ACCESS        not-accessible
        STATUS        mandatory
        DESCRIPTION
             " The upper limit of the upstream data rate. "
        --DEFAULT test-function-async     fsnVdcCtrlTest
        --DEFAULT next-function-async     fsnVdcCtrlNext
        --DEFAULT set-function-async      fsnVdcCtrlSet
        --DEFAULT get-function-async      fsnVdcCtrlGet
        ::= { xldv20VdcControl 7 }

     xldv20VdcCtrlLatencyDn OBJECT-TYPE
        -- info-VALUE:   (delay in msec)
        -- info-VALUE:   0,2,4,8,12,16,20,32
        -- info-ROU:     GET db SET db
        -- info-IMPL:    V2.x
        -- info-VERCTRL: -
        SYNTAX        Xldv20VdcLatencyDn
        ACCESS        not-accessible
        STATUS        mandatory
        DESCRIPTION
              " Selects interleave depth (i.e. latency time) used for
                error correction in downstream direction. "
        --DEFAULT test-function-async     fsnVdcCtrlTest
        --DEFAULT next-function-async     fsnVdcCtrlNext
        --DEFAULT set-function-async      fsnVdcCtrlSet
        --DEFAULT get-function-async      fsnVdcCtrlGet
        ::= { xldv20VdcControl 8 }

     xldv20VdcCtrlLatencyUp OBJECT-TYPE
        -- info-VALUE:   (delay in msec)
        -- info-VALUE:   0,2,4,8,10,20
        -- info-ROU:     GET db SET db
        -- info-IMPL:    V2.x
        -- info-VERCTRL: -
        SYNTAX        Xldv20VdcLatencyUp
        ACCESS        not-accessible
        STATUS        mandatory
        DESCRIPTION
              " Selects interleave depth (i.e. latency time) used for
                error correction in upstream direction. "
        --DEFAULT test-function-async     fsnVdcCtrlTest
        --DEFAULT next-function-async     fsnVdcCtrlNext
        --DEFAULT set-function-async      fsnVdcCtrlSet
        --DEFAULT get-function-async      fsnVdcCtrlGet
        ::= { xldv20VdcControl 9 }

     xldv20VdcCtrlPowerBoost OBJECT-TYPE
        -- info-VALUE:   suEnabled,ntEnabled,bothEnabled,bothDisabled
        -- info-ROU:     GET db SET db
        -- info-IMPL:    V2.x
        -- info-VERCTRL: -
        SYNTAX        Xldv20VdcPowerBoostAdaptationType
        ACCESS        not-accessible
        STATUS        mandatory
        DESCRIPTION
              " Configured power boost mode. "
        --DEFAULT test-function-async     fsnVdcCtrlTest
        --DEFAULT next-function-async     fsnVdcCtrlNext
        --DEFAULT set-function-async      fsnVdcCtrlSet
        --DEFAULT get-function-async      fsnVdcCtrlGet
        ::= { xldv20VdcControl 10 }

     xldv20VdcCtrlWarmStart OBJECT-TYPE
        -- info-VALUE:   enabled, disabled
        -- info-ROU:     GET db SET db
        -- info-IMPL:    V2.x
        -- info-VERCTRL: -
        SYNTAX        Xldv20OperState
        ACCESS        not-accessible
        STATUS        mandatory
        DESCRIPTION
              " Configured warmstart option. "
        --DEFAULT test-function-async     fsnVdcCtrlTest
        --DEFAULT next-function-async     fsnVdcCtrlNext
        --DEFAULT set-function-async      fsnVdcCtrlSet
        --DEFAULT get-function-async      fsnVdcCtrlGet
        ::= { xldv20VdcControl 11 }

     xldv20VdcCtrlVdslMode OBJECT-TYPE
        -- info-VALUE:   adslFriendly, vdslEfficient
        -- info-ROU:     GET db SET db
        -- info-IMPL:    V2.x
        -- info-VERCTRL: -
        SYNTAX        Xldv20VdcVdslMode
        ACCESS        not-accessible
        STATUS        mandatory
        DESCRIPTION
              " Configured VDSL mode option. "
        --DEFAULT test-function-async     fsnVdcCtrlTest
        --DEFAULT next-function-async     fsnVdcCtrlNext
        --DEFAULT set-function-async      fsnVdcCtrlSet
        --DEFAULT get-function-async      fsnVdcCtrlGet
        ::= { xldv20VdcControl 12 }

     xldv20VdcCtrlSleepMode OBJECT-TYPE
        -- info-VALUE:   enabled, disabled
        -- info-ROU:     GET db SET db
        -- info-IMPL:    V2.x
        -- info-VERCTRL: -
        SYNTAX        Xldv20OperState
        ACCESS        not-accessible
        STATUS        mandatory
        DESCRIPTION
              " Configured sleep mode option. "
        --DEFAULT test-function-async     fsnVdcCtrlTest
        --DEFAULT next-function-async     fsnVdcCtrlNext
        --DEFAULT set-function-async      fsnVdcCtrlSet
        --DEFAULT get-function-async      fsnVdcCtrlGet
        ::= { xldv20VdcControl 13 }

     xldv20VdcCtrlPsdMask OBJECT-TYPE
        -- info-VALUE:   m1 (strong effect), m2 (weak effect)
        -- info-ROU:     GET db SET db
        -- info-IMPL:    V2.x
        -- info-VERCTRL: -
        SYNTAX        Xldv20VdcPsdMask
        ACCESS        not-accessible
        STATUS        mandatory
        DESCRIPTION
              " Configured PSD mask option (electro-magnetic interference
                effects, M1 for strong and M2 for weak effects). "
        --DEFAULT test-function-async     fsnVdcCtrlTest
        --DEFAULT next-function-async     fsnVdcCtrlNext
        --DEFAULT set-function-async      fsnVdcCtrlSet
        --DEFAULT get-function-async      fsnVdcCtrlGet
        ::= { xldv20VdcControl 14 }

     xldv20VdcCtrlPowerAdaptation OBJECT-TYPE
        -- info-VALUE:   suEnabled,ntEnabled,bothEnabled,bothDisabled
        -- info-ROU:     GET db SET db
        -- info-IMPL:    V2.x
        -- info-VERCTRL: -
        SYNTAX        Xldv20VdcPowerBoostAdaptationType
        ACCESS        not-accessible
        STATUS        mandatory
        DESCRIPTION
              " Configured power adaptation option. "
        --DEFAULT test-function-async     fsnVdcCtrlTest
        --DEFAULT next-function-async     fsnVdcCtrlNext
        --DEFAULT set-function-async      fsnVdcCtrlSet
        --DEFAULT get-function-async      fsnVdcCtrlGet
        ::= { xldv20VdcControl 15 }

     xldv20VdcCtrlControlReqResult OBJECT-TYPE
        -- info-VALUE:   activateData(command)
        -- info-VALUE:   noRequest, paramFaulty
        -- info-VALUE:   resourceProblem,vpProblem,wrongAdminState
        -- info-VALUE:   requestBusy,setDataFailed
        -- info-VALUE:   aswTimeout, commandFailed, commandSucceeded
        -- info-ROU:     GET db
        -- info-IMPL:    V2.x
        -- info-VERCTRL: -
        SYNTAX        Xldv20ControlReq
        ACCESS        not-accessible
        STATUS        mandatory
        DESCRIPTION
              " This read-only attribute informs about the result of 
                 the last user command. "
        --DEFAULT next-function-async     fsnVdcCtrlNext
        --DEFAULT get-function-async      fsnVdcCtrlGet
        ::= { xldv20VdcControl 16 }

      xldv20VdcCtrlControlTimeStamp OBJECT-TYPE
         -- info-VALUE:   0..2Giga
         -- info-ROU:     GET db
         -- info-IMPL:    V2.x
         -- info-VERCTRL: -
         SYNTAX        TimeTicks
         ACCESS        not-accessible
         STATUS        mandatory
         DESCRIPTION
            " This read-only attribute informs about the time stamp
            of the last command (end of command). "
        --DEFAULT next-function-async     fsnVdcCtrlNext
        --DEFAULT get-function-async      fsnVdcCtrlGet
        ::= { xldv20VdcControl 17 }

     -- --------------------------------------------------------------
     --                 TLM ADSL central PPTP Table
     -- --------------------------------------------------------------

     -- This managed entity represents the extension for the PPTP at
     -- the ADSL central interface. It includes additional attributes to
     -- configure the ADSL link.
     --

     xldv20AdcPPTPTable OBJECT-TYPE
            -- info-IMPL:    V2.0->
            -- info-VERCTRL: -
        SYNTAX        SEQUENCE OF Xldv20AdcPPTPEntry
        ACCESS        not-accessible
        STATUS        mandatory
        DESCRIPTION
             " The physical path termination point table for ADSL Central
	     interface. "
        --DEFAULT test-function-async     fsnAdcEntryTest
        --DEFAULT next-function-async     fsnAdcEntryNext
        --DEFAULT get-function-async      fsnAdcEntryGet
        --DEFAULT set-function-async      fsnAdcEntrySet
        ::= { xldv20Tlm 4 }

     xldv20AdcPPTPEntry OBJECT-TYPE
            -- info-IMPL:    V2.0->
            -- info-VERCTRL: -
        SYNTAX        Xldv20AdcPPTPEntry
        ACCESS        not-accessible
        STATUS        mandatory
        DESCRIPTION
             " An entry describing a termination point in the PPTP table.
               Notifications : see xldv20IfEntry. "
        INDEX         { xldv20IfIndex }
        ::= { xldv20AdcPPTPTable 1 }

     Xldv20AdcPPTPEntry ::=
        SEQUENCE { xldv20AdcMinRateDnCfg                    Xldv20AdslDataRateDown,
                   xldv20AdcMinRateUpCfg                    Xldv20AdslDataRateUp,
                   xldv20AdcMaxRateDnCfg                    Xldv20AdslDataRateDown,
                   xldv20AdcMaxRateUpCfg                    Xldv20AdslDataRateUp,
                   xldv20AdcMarginDnCfg                           INTEGER,
                   xldv20AdcMarginUpCfg                           INTEGER,
                   xldv20AdcMinMarginDnCfg                  Xldv20AdslMinMargin,
                   xldv20AdcMinMarginUpCfg                  Xldv20AdslMinMargin,
                   xldv20AdcLatencyDnCfg                    Xldv20Latency,
                   xldv20AdcLatencyUpCfg                    Xldv20Latency,
                   xldv20AdcRateDn                          Xldv20AdslDataRateDownCurrent,
                   xldv20AdcRateUp                          Xldv20AdslDataRateUpCurrent,
                   xldv20AdcMarginDn                        Xldv20AdslMargin,
                   xldv20AdcMarginUp                        Xldv20AdslMargin,
                   xldv20AdcAttenuationDn                   Xldv20AdslAttenuation,
                   xldv20AdcAttenuationUp                   Xldv20AdslAttenuation,
                   xldv20AdcLinkState                       Xldv20LinkState,
                   xldv20AdcAISOnLOS                        Xldv20OperState,
                   xldv20AdcAISOnACT                        Xldv20OperState ,
                   xldv20AdcGuaranteedBandwidthUsage              INTEGER,
                   xldv20AdcXdslServiceTypeCfg              Xldv20XdslServiceType,
                   xldv20AdcInitStatus                      Xldv20XdslInitStatus,
	           xldv20AdcTransceiverOutputPower          Xldv20AdslOutputPower,
	           xldv20AdcFirstUsedSubCarrierUpstream           INTEGER,
	           xldv20AdcFirstUsedSubCarrierDownstream         INTEGER,
	           xldv20AdcLastUsedSubCarrierUpstream            INTEGER,
	           xldv20AdcLastUsedSubCarrierDownstream          INTEGER,
                   xldv20AdcXdslServiceType                 Xldv20XdslServiceTypeCurrent
                   }

     xldv20AdcMinRateDnCfg OBJECT-TYPE
        -- info-VALUE:   1..253 (default 1)
        -- info-VALUE:   for values see Xldv20AdcCtrlMinRateDn
        -- info-ROU:     GET db
        -- info-IMPL:    V2.0->
        -- info-VERCTRL: -
        SYNTAX        Xldv20AdslDataRateDown
        ACCESS        read-only
        STATUS        mandatory
        DESCRIPTION
             " The desired lower value of the downstream data rate. The data
               rate ranges from 32 to 8096 Kbit/sec and 
	       is splitted into units of 32 Kbit/sec.
               This corresponds to a cell rate between 75 and 19094 cells/sec.
               Default is 1 (32 kbps/75 cps). "
        ::= { xldv20AdcPPTPEntry 1 }

     xldv20AdcMinRateUpCfg OBJECT-TYPE
        -- info-VALUE:   1..24 (default 1)
        -- info-VALUE:   for values see Xldv20AdcCtrlMinRateDn
        -- info-ROU:     GET db
        -- info-IMPL:    V2.0->
        -- info-VERCTRL: -
        SYNTAX        Xldv20AdslDataRateUp
        ACCESS        read-only
        STATUS        mandatory
        DESCRIPTION
             " The desired lower value of the upstream data rate. The data
               rate ranges from 32 and 768 Kbit/sec and 
	       is splitted into units of 32 Kbit/sec.
               This corresponds to a cell rate between 75 and 1811 cells/sec.
               Default is 1 (32 kbps/75 cps). "
        ::= { xldv20AdcPPTPEntry 2 }

     xldv20AdcMaxRateDnCfg OBJECT-TYPE
        -- info-VALUE:   1..253 (default 253)
        -- info-VALUE:   for values see Xldv20AdcCtrlMinRateDn
        -- info-ROU:     GET db
        -- info-IMPL:    V2.0->
        -- info-VERCTRL: -
        SYNTAX        Xldv20AdslDataRateDown
        ACCESS        read-only
        STATUS        mandatory
        DESCRIPTION
             " The desired upper value of the downstream data rate. The data
               rate ranges from 32 and 8160 Kbit/sec and is splitted into units
               of 32 Kbit/sec.
               This corresponds to a cell rate between 75 and 1811 cells/sec.
               Default is 253 (8096 kbps/19094 cps). "
        ::= { xldv20AdcPPTPEntry 3 }

     xldv20AdcMaxRateUpCfg OBJECT-TYPE
        -- info-VALUE:   1..24 (default 24)
        -- info-ROU:     GET db
        -- info-IMPL:    V2.0->
        -- info-VERCTRL: -
        SYNTAX        Xldv20AdslDataRateUp
        ACCESS        read-only
        STATUS        mandatory
        DESCRIPTION
             " The desired upper value of the upstream data rate. The data
               rate ranges from 32 and 768 Kbit/sec and 
               is splitted into units of 32 Kbit/sec.
               This corresponds to a cell rate between 75 and 1811 cells/sec.
               Default is 24 (768 kbps/1811 cps). "
        ::= { xldv20AdcPPTPEntry 4 }

     xldv20AdcMarginDnCfg OBJECT-TYPE
        -- info-VALUE:   0..15 (default 6)
        -- info-ROU:     GET db
        -- info-IMPL:    V2.0->
        -- info-VERCTRL: -
        SYNTAX        INTEGER (0..15)
        ACCESS        read-only
        STATUS        mandatory
        DESCRIPTION
             " Desired downstream margin. The unit of measurement
               is dB.  "
        ::= { xldv20AdcPPTPEntry 5 }

     xldv20AdcMarginUpCfg OBJECT-TYPE
        -- info-VALUE:   0..15 (default 6)
        -- info-ROU:     GET db
        -- info-IMPL:    V2.0->
        -- info-VERCTRL: -
        SYNTAX        INTEGER (0..15)
        ACCESS        read-only
        STATUS        mandatory
        DESCRIPTION
             " Desired upstream margin. The unit of measurement
               is dB. "
        ::= { xldv20AdcPPTPEntry 6 }

     xldv20AdcMinMarginDnCfg OBJECT-TYPE
        -- info-VALUE:   see xldv20AdcCtrlMinMarginDn
        -- info-ROU:     GET db
        -- info-IMPL:    V2.0->
        -- info-VERCTRL: -
        SYNTAX        Xldv20AdslMinMargin
        ACCESS        read-only
        STATUS        mandatory
        DESCRIPTION
             " Desired threshold for downstream margin in units of dB. 
	     If the value auto is selected during configuration
	     the threshold is calculated from the configured margin :
	     threshold margin down = configured margin down - 6 dB.  "
        ::= { xldv20AdcPPTPEntry 7 }

     xldv20AdcMinMarginUpCfg OBJECT-TYPE
        -- info-VALUE:   see xldv20AdcCtrlMinMarginDn
        -- info-ROU:     GET db
        -- info-IMPL:    V2.0->
        -- info-VERCTRL: -
        SYNTAX        Xldv20AdslMinMargin
        ACCESS        read-only
        STATUS        mandatory
        DESCRIPTION
             " Desired threshold for upstream margin in units of dB.
	     If the value auto is selected during configuration
	     the threshold is calculated from the configured margin :
	     threshold margin up = configured margin up - 6 dB.  "
        ::= { xldv20AdcPPTPEntry 8 }

     xldv20AdcLatencyDnCfg OBJECT-TYPE
        -- info-VALUE:   interleavedLow        (0),
        -- info-VALUE:   interleavedHigh       (1),
        -- info-VALUE:   fast                 (256)
        -- info-ROU:     GET db
        -- info-IMPL:    V2.0->
        -- info-VERCTRL: -
        SYNTAX        Xldv20Latency
        ACCESS        read-only
        STATUS        mandatory
        DESCRIPTION
             " The configured fast mode or interleaved mode downstream.
               0   = interleavedLow (default).
               1   = interleavedHigh .
	       256 = fast mode. "
        ::= { xldv20AdcPPTPEntry 10 }

     xldv20AdcLatencyUpCfg OBJECT-TYPE
        -- info-VALUE:   interleavedLow        (0),
        -- info-VALUE:   interleavedHigh       (1),
        -- info-VALUE:   fast                 (256)
        -- info-ROU:     GET db
        -- info-IMPL:    V2.0->
        -- info-VERCTRL: -
        SYNTAX        Xldv20Latency
        ACCESS        read-only
        STATUS        mandatory
        DESCRIPTION
             " The configured fast mode or interleaved mode upstream.
               0   = interleavedLow (default).
               1   = interleavedHigh .
	       256 = fast mode. "
        ::= { xldv20AdcPPTPEntry 11 }

     xldv20AdcRateDn OBJECT-TYPE
        -- info-VALUE:   1..253
        -- info-VALUE:   rateInvalid(32767)
        -- info-VALUE:   for detailed values see Xldv20AdcCtrlMinRateDn
        -- info-ROU:     GET tm
        -- info-IMPL:    V2.0->
        -- info-VERCTRL: -
        SYNTAX        Xldv20AdslDataRateDownCurrent
        ACCESS        read-only
        STATUS        mandatory
        DESCRIPTION
             " The current downstream data rate. The data rate
               ranges from 32 and 8096 Kbit/sec and is splitted into units
               of 32 Kbit/sec. This corresponds to a cell rate between
	       75 and 19094 cells/sec. Default is rateInvalid (32767). "
        ::= { xldv20AdcPPTPEntry 12 }

     xldv20AdcRateUp OBJECT-TYPE
        -- info-VALUE:   1..24
        -- info-VALUE:   rateInvalid(32767)
        -- info-VALUE:   for detailed values see Xldv20AdcCtrlMinRateUp
        -- info-ROU:     GET tm
        -- info-IMPL:    V2.0->
        -- info-VERCTRL: -
        SYNTAX        Xldv20AdslDataRateUpCurrent
        ACCESS        read-only
        STATUS        mandatory
        DESCRIPTION
             " The current upstream data rate. The data rate
               ranges from 32 and 768 kbit/sec and is splitted into units
               of 32 Kbit/sec. This corresponds to a cell rate between
	       75 and 1811 cells/sec. Default is rateInvalid (32767). "
        ::= { xldv20AdcPPTPEntry 13 }

     xldv20AdcMarginDn OBJECT-TYPE
        -- info-VALUE:   dB-127    (-127),
        -- info-VALUE:   dB-126    (-126),
        -- info-VALUE:   dB-125    (-125),
        -- info-VALUE:   dB-124    (-124),
        -- info-VALUE:   dB-123    (-123),
        -- info-VALUE:   dB-122    (-122),
        -- info-VALUE:   dB-121    (-121),
        -- info-VALUE:   dB-120    (-120),
        -- info-VALUE:   dB-119    (-119),
        -- info-VALUE:   dB-118    (-118),
        -- info-VALUE:   dB-117    (-117),
        -- info-VALUE:   dB-116    (-116),
        -- info-VALUE:   dB-115    (-115),
        -- info-VALUE:   dB-114    (-114),
        -- info-VALUE:   dB-113    (-113),
        -- info-VALUE:   dB-112    (-112),
        -- info-VALUE:   dB-111    (-111),
        -- info-VALUE:   dB-110    (-110),
        -- info-VALUE:   dB-109    (-109),
        -- info-VALUE:   dB-108    (-108),
        -- info-VALUE:   dB-107    (-107),
        -- info-VALUE:   dB-106    (-106),
        -- info-VALUE:   dB-105    (-105),
        -- info-VALUE:   dB-104    (-104),
        -- info-VALUE:   dB-103    (-103),
        -- info-VALUE:   dB-102    (-102),
        -- info-VALUE:   dB-101    (-101),
        -- info-VALUE:   dB-100    (-100),
        -- info-VALUE:   dB-99     (-99),
        -- info-VALUE:   dB-98     (-98),
        -- info-VALUE:   dB-97     (-97),
        -- info-VALUE:   dB-96     (-96),
        -- info-VALUE:   dB-95     (-95),
        -- info-VALUE:   dB-94     (-94),
        -- info-VALUE:   dB-93     (-93),
        -- info-VALUE:   dB-92     (-92),
        -- info-VALUE:   dB-91     (-91),
        -- info-VALUE:   dB-90     (-90),
        -- info-VALUE:   dB-89     (-89),
        -- info-VALUE:   dB-88     (-88),
        -- info-VALUE:   dB-87     (-87),
        -- info-VALUE:   dB-86     (-86),
        -- info-VALUE:   dB-85     (-85),
        -- info-VALUE:   dB-84     (-84),
        -- info-VALUE:   dB-83     (-83),
        -- info-VALUE:   dB-82     (-82),
        -- info-VALUE:   dB-81     (-81),
        -- info-VALUE:   dB-80     (-80),
        -- info-VALUE:   dB-79     (-79),
        -- info-VALUE:   dB-78     (-78),
        -- info-VALUE:   dB-77     (-77),
        -- info-VALUE:   dB-76     (-76),
        -- info-VALUE:   dB-75     (-75),
        -- info-VALUE:   dB-74     (-74),
        -- info-VALUE:   dB-73     (-73),
        -- info-VALUE:   dB-72     (-72),
        -- info-VALUE:   dB-71     (-71),
        -- info-VALUE:   dB-70     (-70),
        -- info-VALUE:   dB-69     (-69),
        -- info-VALUE:   dB-68     (-68),
        -- info-VALUE:   dB-67     (-67),
        -- info-VALUE:   dB-66     (-66),
        -- info-VALUE:   dB-65     (-65),
        -- info-VALUE:   dB-64     (-64),
        -- info-VALUE:   dB-63     (-63),
        -- info-VALUE:   dB-62     (-62),
        -- info-VALUE:   dB-61     (-61),
        -- info-VALUE:   dB-60     (-60),
        -- info-VALUE:   dB-59     (-59),
        -- info-VALUE:   dB-58     (-58),
        -- info-VALUE:   dB-57     (-57),
        -- info-VALUE:   dB-56     (-56),
        -- info-VALUE:   dB-55     (-55),
        -- info-VALUE:   dB-54     (-54),
        -- info-VALUE:   dB-53     (-53),
        -- info-VALUE:   dB-52     (-52),
        -- info-VALUE:   dB-51     (-51),
        -- info-VALUE:   dB-50     (-50),
        -- info-VALUE:   dB-49     (-49),
        -- info-VALUE:   dB-48     (-48),
        -- info-VALUE:   dB-47     (-47),
        -- info-VALUE:   dB-46     (-46),
        -- info-VALUE:   dB-45     (-45),
        -- info-VALUE:   dB-44     (-44),
        -- info-VALUE:   dB-43     (-43),
        -- info-VALUE:   dB-42     (-42),
        -- info-VALUE:   dB-41     (-41),
        -- info-VALUE:   dB-40     (-40),
        -- info-VALUE:   dB-39     (-39),
        -- info-VALUE:   dB-38     (-38),
        -- info-VALUE:   dB-37     (-37),
        -- info-VALUE:   dB-36     (-36),
        -- info-VALUE:   dB-35     (-35),
        -- info-VALUE:   dB-34     (-34),
        -- info-VALUE:   dB-33     (-33),
        -- info-VALUE:   dB-32     (-32),
        -- info-VALUE:   dB-31     (-31),
        -- info-VALUE:   dB-30     (-30),
        -- info-VALUE:   dB-29     (-29),
        -- info-VALUE:   dB-28     (-28),
        -- info-VALUE:   dB-27     (-27),
        -- info-VALUE:   dB-26     (-26),
        -- info-VALUE:   dB-25     (-25),
        -- info-VALUE:   dB-24     (-24),
        -- info-VALUE:   dB-23     (-23),
        -- info-VALUE:   dB-22     (-22),
        -- info-VALUE:   dB-21     (-21),
        -- info-VALUE:   dB-20     (-20),
        -- info-VALUE:   dB-19     (-19),
        -- info-VALUE:   dB-18     (-18),
        -- info-VALUE:   dB-17     (-17),
        -- info-VALUE:   dB-16     (-16),
        -- info-VALUE:   dB-15     (-15),
        -- info-VALUE:   dB-14     (-14),
        -- info-VALUE:   dB-13     (-13),
        -- info-VALUE:   dB-12     (-12),
        -- info-VALUE:   dB-11     (-11),
        -- info-VALUE:   dB-10     (-10),
        -- info-VALUE:   dB-9      (-9),
        -- info-VALUE:   dB-8      (-8),
        -- info-VALUE:   dB-7      (-7),
        -- info-VALUE:   dB-6      (-6),
        -- info-VALUE:   dB-5      (-5),
        -- info-VALUE:   dB-4      (-4),
        -- info-VALUE:   dB-3      (-3),
        -- info-VALUE:   dB-2      (-2),
        -- info-VALUE:   dB-1      (-1),
        -- info-VALUE:   dB0       (0 ),
        -- info-VALUE:   dB1      (1 ),
        -- info-VALUE:   dB2      (2 ),
        -- info-VALUE:   dB3      (3 ),
        -- info-VALUE:   dB4      (4 ),
        -- info-VALUE:   dB5      (5 ),
        -- info-VALUE:   dB6      (6 ),
        -- info-VALUE:   dB7      (7 ),
        -- info-VALUE:   dB8      (8 ),
        -- info-VALUE:   dB9      (9 ),
        -- info-VALUE:   dB10     (10),
        -- info-VALUE:   dB11     (11),
        -- info-VALUE:   dB12     (12),
        -- info-VALUE:   dB13     (13),
        -- info-VALUE:   dB14     (14),
        -- info-VALUE:   dB15     (15),
        -- info-VALUE:   dB16     (16),
        -- info-VALUE:   dB17     (17),
        -- info-VALUE:   dB18     (18),
        -- info-VALUE:   dB19     (19),
        -- info-VALUE:   dB20     (20),
        -- info-VALUE:   dB21     (21),
        -- info-VALUE:   dB22     (22),
        -- info-VALUE:   dB23     (23),
        -- info-VALUE:   dB24     (24),
        -- info-VALUE:   dB25     (25),
        -- info-VALUE:   dB26     (26),
        -- info-VALUE:   dB27     (27),
        -- info-VALUE:   dB28     (28),
        -- info-VALUE:   dB29     (29),
        -- info-VALUE:   dB30     (30),
        -- info-VALUE:   dB31     (31),
        -- info-VALUE:   dB32     (32),
        -- info-VALUE:   dB33     (33),
        -- info-VALUE:   dB34     (34),
        -- info-VALUE:   dB35     (35),
        -- info-VALUE:   dB36     (36),
        -- info-VALUE:   dB37     (37),
        -- info-VALUE:   dB38     (38),
        -- info-VALUE:   dB39     (39),
        -- info-VALUE:   dB40     (40),
        -- info-VALUE:   dB41     (41),
        -- info-VALUE:   dB42     (42),
        -- info-VALUE:   dB43     (43),
        -- info-VALUE:   dB44     (44),
        -- info-VALUE:   dB45     (45),
        -- info-VALUE:   dB46     (46),
        -- info-VALUE:   dB47     (47),
        -- info-VALUE:   dB48     (48),
        -- info-VALUE:   dB49     (49),
        -- info-VALUE:   dB50     (50),
        -- info-VALUE:   dB51     (51),
        -- info-VALUE:   dB52     (52),
        -- info-VALUE:   dB53     (53),
        -- info-VALUE:   dB54     (54),
        -- info-VALUE:   dB55     (55),
        -- info-VALUE:   dB56     (56),
        -- info-VALUE:   dB57     (57),
        -- info-VALUE:   dB58     (58),
        -- info-VALUE:   dB59     (59),
        -- info-VALUE:   dB60     (60),
        -- info-VALUE:   dB61     (61),
        -- info-VALUE:   dB62     (62),
        -- info-VALUE:   dB63     (63),
        -- info-VALUE:   dB64     (64),
        -- info-VALUE:   dB65     (65),
        -- info-VALUE:   dB66     (66),
        -- info-VALUE:   dB67     (67),
        -- info-VALUE:   dB68     (68),
        -- info-VALUE:   dB69     (69),
        -- info-VALUE:   dB70     (70),
        -- info-VALUE:   dB71     (71),
        -- info-VALUE:   dB72     (72),
        -- info-VALUE:   dB73     (73),
        -- info-VALUE:   dB74     (74),
        -- info-VALUE:   dB75     (75),
        -- info-VALUE:   dB76     (76),
        -- info-VALUE:   dB77     (77),
        -- info-VALUE:   dB78     (78),
        -- info-VALUE:   dB79     (79),
        -- info-VALUE:   dB80     (80),
        -- info-VALUE:   dB81     (81),
        -- info-VALUE:   dB82     (82),
        -- info-VALUE:   dB83     (83),
        -- info-VALUE:   dB84     (84),
        -- info-VALUE:   dB85     (85),
        -- info-VALUE:   dB86     (86),
        -- info-VALUE:   dB87     (87),
        -- info-VALUE:   dB88     (88),
        -- info-VALUE:   dB89     (89),
        -- info-VALUE:   dB90     (90),
        -- info-VALUE:   dB91     (91),
        -- info-VALUE:   dB92     (92),
        -- info-VALUE:   dB93     (93),
        -- info-VALUE:   dB94     (94),
        -- info-VALUE:   dB95     (95),
        -- info-VALUE:   dB96     (96),
        -- info-VALUE:   dB97     (97),
        -- info-VALUE:   dB98     (98),
        -- info-VALUE:   dB99     (99),
        -- info-VALUE:   dB100    (100),
        -- info-VALUE:   dB101    (101),
        -- info-VALUE:   dB102    (102),
        -- info-VALUE:   dB103    (103),
        -- info-VALUE:   dB104    (104),
        -- info-VALUE:   dB105    (105),
        -- info-VALUE:   dB106    (106),
        -- info-VALUE:   dB107    (107),
        -- info-VALUE:   dB108    (108),
        -- info-VALUE:   dB109    (109),
        -- info-VALUE:   dB110    (110),
        -- info-VALUE:   dB111    (111),
        -- info-VALUE:   dB112    (112),
        -- info-VALUE:   dB113    (113),
        -- info-VALUE:   dB114    (114),
        -- info-VALUE:   dB115    (115),
        -- info-VALUE:   dB116    (116),
        -- info-VALUE:   dB117    (117),
        -- info-VALUE:   dB118    (118),
        -- info-VALUE:   dB119    (119),
        -- info-VALUE:   dB120    (120),
        -- info-VALUE:   dB121    (121),
        -- info-VALUE:   dB122    (122),
        -- info-VALUE:   dB123    (123),
        -- info-VALUE:   dB124    (124),
        -- info-VALUE:   dB125    (125),
        -- info-VALUE:   dB126    (126),
        -- info-VALUE:   dB127    (127),
        -- info-VALUE:   dB128    (128),
        -- info-VALUE:   marginInvalid (32767)
        -- info-ROU:     GET tm
        -- info-IMPL:    V2.0->
        -- info-VERCTRL: -
        SYNTAX        Xldv20AdslMargin   
        ACCESS        read-only
        STATUS        mandatory
        DESCRIPTION
             " The current downstream margin in units of dB.
               Default is marginInvalid. "
        ::= { xldv20AdcPPTPEntry 14 }

     xldv20AdcMarginUp OBJECT-TYPE
        -- info-VALUE:   see xldv20AdcMarginDn
        -- info-ROU:     GET tm
        -- info-IMPL:    V2.0->
        -- info-VERCTRL: -
        SYNTAX        Xldv20AdslMargin   
        ACCESS        read-only
        STATUS        mandatory
        DESCRIPTION
             " The current upstream margin in units of dB.
               Default is marginInvalid. "
        ::= { xldv20AdcPPTPEntry 15 }

     xldv20AdcAttenuationDn OBJECT-TYPE
        -- info-VALUE:            dB0             (0 ),
        -- info-VALUE:            dB0Dot5         (1 ),
        -- info-VALUE:            dB1             (2 ),
        -- info-VALUE:   dB1Dot5         (3 ),
        -- info-VALUE:   dB2             (4 ),
        -- info-VALUE:   dB2Dot5         (5 ),
        -- info-VALUE:   dB3             (6 ),
        -- info-VALUE:   dB3Dot5         (7 ),
        -- info-VALUE:   dB4             (8 ),
        -- info-VALUE:   dB4Dot5         (9 ),
        -- info-VALUE:   dB5             (10),
        -- info-VALUE:   dB5Dot5         (11),
        -- info-VALUE:   dB6             (12),
        -- info-VALUE:   dB6Dot5         (13),
        -- info-VALUE:   dB7             (14),
        -- info-VALUE:   dB7Dot5         (15),
        -- info-VALUE:   dB8             (16),
        -- info-VALUE:   dB8Dot5         (17),
        -- info-VALUE:   dB9             (18),
        -- info-VALUE:   dB9Dot5         (19),
        -- info-VALUE:   dB10            (20),
        -- info-VALUE:   dB10Dot5        (21),
        -- info-VALUE:   dB11            (22),
        -- info-VALUE:   dB11Dot5        (23),
        -- info-VALUE:   dB12            (24),
        -- info-VALUE:   dB12Dot5        (25),
        -- info-VALUE:   dB13            (26),
        -- info-VALUE:   dB13Dot5        (27),
        -- info-VALUE:   dB14            (28),
        -- info-VALUE:   dB14Dot5        (29),
        -- info-VALUE:   dB15            (30),
        -- info-VALUE:   dB15Dot5        (31),
        -- info-VALUE:   dB16            (32),
        -- info-VALUE:   dB16Dot5        (33),
        -- info-VALUE:   dB17            (34),
        -- info-VALUE:   dB17Dot5        (35),
        -- info-VALUE:   dB18            (36),
        -- info-VALUE:   dB18Dot5        (37),
        -- info-VALUE:   dB19            (38),
        -- info-VALUE:   dB19Dot5        (39),
        -- info-VALUE:   dB20            (40),
        -- info-VALUE:   dB20Dot5        (41),
        -- info-VALUE:   dB21            (42),
        -- info-VALUE:   dB21Dot5        (43),
        -- info-VALUE:   dB22            (44),
        -- info-VALUE:   dB22Dot5        (45),
        -- info-VALUE:   dB23            (46),
        -- info-VALUE:   dB23Dot5        (47),
        -- info-VALUE:   dB24            (48),
        -- info-VALUE:   dB24Dot5        (49),
        -- info-VALUE:   dB25            (50),
        -- info-VALUE:   dB25Dot5        (51),
        -- info-VALUE:   dB26            (52),
        -- info-VALUE:   dB26Dot5        (53),
        -- info-VALUE:   dB27            (54),
        -- info-VALUE:   dB27Dot5        (55),
        -- info-VALUE:   dB28            (56),
        -- info-VALUE:   dB28Dot5        (57),
        -- info-VALUE:   dB29            (58),
        -- info-VALUE:   dB29Dot5        (59),
        -- info-VALUE:   dB30            (60),
        -- info-VALUE:   dB30Dot5        (61),
        -- info-VALUE:   dB31            (62),
        -- info-VALUE:   dB31Dot5        (63),
        -- info-VALUE:   dB32            (64),
        -- info-VALUE:   dB32Dot5        (65),
        -- info-VALUE:   dB33            (66),
        -- info-VALUE:   dB33Dot5        (67),
        -- info-VALUE:   dB34            (68),
        -- info-VALUE:   dB34Dot5        (69),
        -- info-VALUE:   dB35            (70),
        -- info-VALUE:   dB35Dot5        (71),
        -- info-VALUE:   dB36            (72),
        -- info-VALUE:   dB36Dot5        (73),
        -- info-VALUE:   dB37            (74),
        -- info-VALUE:   dB37Dot5        (75),
        -- info-VALUE:   dB38            (76),
        -- info-VALUE:   dB38Dot5        (77),
        -- info-VALUE:   dB39            (78),
        -- info-VALUE:   dB39Dot5        (79),
        -- info-VALUE:   dB40            (80),
        -- info-VALUE:   dB40Dot5        (81),
        -- info-VALUE:   dB41            (82),
        -- info-VALUE:   dB41Dot5        (83),
        -- info-VALUE:   dB42            (84),
        -- info-VALUE:   dB42Dot5        (85),
        -- info-VALUE:   dB43            (86),
        -- info-VALUE:   dB43Dot5        (87),
        -- info-VALUE:   dB44            (88),
        -- info-VALUE:   dB44Dot5        (89),
        -- info-VALUE:   dB45            (90),
        -- info-VALUE:   dB45Dot5        (91),
        -- info-VALUE:   dB46            (92),
        -- info-VALUE:   dB46Dot5        (93),
        -- info-VALUE:   dB47            (94),
        -- info-VALUE:   dB47Dot5        (95),
        -- info-VALUE:   dB48            (96),
        -- info-VALUE:   dB48Dot5        (97),
        -- info-VALUE:   dB49            (98),
        -- info-VALUE:   dB49Dot5        (99),
        -- info-VALUE:   dB50            (100),
        -- info-VALUE:   dB50Dot5        (101),
        -- info-VALUE:   dB51            (102),
        -- info-VALUE:   dB51Dot5        (103),
        -- info-VALUE:   dB52            (104),
        -- info-VALUE:   dB52Dot5        (105),
        -- info-VALUE:   dB53            (106),
        -- info-VALUE:   dB53Dot5        (107),
        -- info-VALUE:   dB54            (108),
        -- info-VALUE:   dB54Dot5        (109),
        -- info-VALUE:   dB55            (110),
        -- info-VALUE:   dB55Dot5        (111),
        -- info-VALUE:   dB56            (112),
        -- info-VALUE:   dB56Dot5        (113),
        -- info-VALUE:   dB57            (114),
        -- info-VALUE:   dB57Dot5        (115),
        -- info-VALUE:   dB58            (116),
        -- info-VALUE:   dB58Dot5        (117),
        -- info-VALUE:   dB59            (118),
        -- info-VALUE:   dB59Dot5        (119),
        -- info-VALUE:   dB60            (120),
        -- info-VALUE:   dB60Dot5        (121),
        -- info-VALUE:   dB61            (122),
        -- info-VALUE:   dB61Dot5        (123),
        -- info-VALUE:   dB62            (124),
        -- info-VALUE:   dB62Dot5        (125),
        -- info-VALUE:   dB63            (126),
        -- info-VALUE:   dB63Dot5        (127),
        -- info-VALUE:   dB64            (128),
        -- info-VALUE:   dB64Dot5        (129),
        -- info-VALUE:   dB65            (130),
        -- info-VALUE:   dB65Dot5        (131),
        -- info-VALUE:   dB66            (132),
        -- info-VALUE:   dB66Dot5        (133),
        -- info-VALUE:   dB67            (134),
        -- info-VALUE:   dB67Dot5        (135),
        -- info-VALUE:   dB68            (136),
        -- info-VALUE:   dB68Dot5        (137),
        -- info-VALUE:   dB69            (138),
        -- info-VALUE:   dB69Dot5        (139),
        -- info-VALUE:   dB70            (140),
        -- info-VALUE:   dB70Dot5        (141),
        -- info-VALUE:   dB71            (142),
        -- info-VALUE:   dB71Dot5        (143),
        -- info-VALUE:   dB72            (144),
        -- info-VALUE:   dB72Dot5        (145),
        -- info-VALUE:   dB73            (146),
        -- info-VALUE:   dB73Dot5        (147),
        -- info-VALUE:   dB74            (148),
        -- info-VALUE:   dB74Dot5        (149),
        -- info-VALUE:   dB75            (150),
        -- info-VALUE:   dB75Dot5        (151),
        -- info-VALUE:   dB76            (152),
        -- info-VALUE:   dB76Dot5        (153),
        -- info-VALUE:   dB77            (154),
        -- info-VALUE:   dB77Dot5        (155),
        -- info-VALUE:   dB78            (156),
        -- info-VALUE:   dB78Dot5        (157),
        -- info-VALUE:   dB79            (158),
        -- info-VALUE:   dB79Dot5        (159),
        -- info-VALUE:   dB80            (160),
        -- info-VALUE:   dB80Dot5        (161),
        -- info-VALUE:   dB81            (162),
        -- info-VALUE:   dB81Dot5        (163),
        -- info-VALUE:   dB82            (164),
        -- info-VALUE:   dB82Dot5        (165),
        -- info-VALUE:   dB83            (166),
        -- info-VALUE:   dB83Dot5        (167),
        -- info-VALUE:   dB84            (168),
        -- info-VALUE:   dB84Dot5        (169),
        -- info-VALUE:   dB85            (170),
        -- info-VALUE:   dB85Dot5        (171),
        -- info-VALUE:   dB86            (172),
        -- info-VALUE:   dB86Dot5        (173),
        -- info-VALUE:   dB87            (174),
        -- info-VALUE:   dB87Dot5        (175),
        -- info-VALUE:   dB88            (176),
        -- info-VALUE:   dB88Dot5        (177),
        -- info-VALUE:   dB89            (178),
        -- info-VALUE:   dB89Dot5        (179),
        -- info-VALUE:   dB90            (180),
        -- info-VALUE:   dB90Dot5        (181),
        -- info-VALUE:   dB91            (182),
        -- info-VALUE:   dB91Dot5        (183),
        -- info-VALUE:   dB92            (184),
        -- info-VALUE:   dB92Dot5        (185),
        -- info-VALUE:   dB93            (186),
        -- info-VALUE:   dB93Dot5        (187),
        -- info-VALUE:   dB94            (188),
        -- info-VALUE:   dB94Dot5        (189),
        -- info-VALUE:   dB95            (190),
        -- info-VALUE:   dB95Dot5        (191),
        -- info-VALUE:   dB96            (192),
        -- info-VALUE:   dB96Dot5        (193),
        -- info-VALUE:   dB97            (194),
        -- info-VALUE:   dB97Dot5        (195),
        -- info-VALUE:   dB98            (196),
        -- info-VALUE:   dB98Dot5        (197),
        -- info-VALUE:   dB99            (198),
        -- info-VALUE:   dB99Dot5        (199),
        -- info-VALUE:   dB100           (200),
        -- info-VALUE:   dB100Dot5       (201),
        -- info-VALUE:   dB101           (202),
        -- info-VALUE:   dB101Dot5       (203),
        -- info-VALUE:   dB102           (204),
        -- info-VALUE:   dB102Dot5       (205),
        -- info-VALUE:   dB103           (206),
        -- info-VALUE:   dB103Dot5       (207),
        -- info-VALUE:   dB104           (208),
        -- info-VALUE:   dB104Dot5       (209),
        -- info-VALUE:   dB105           (210),
        -- info-VALUE:   dB105Dot5       (211),
        -- info-VALUE:   dB106           (212),
        -- info-VALUE:   dB106Dot5       (213),
        -- info-VALUE:   dB107           (214),
        -- info-VALUE:   dB107Dot5       (215),
        -- info-VALUE:   dB108           (216),
        -- info-VALUE:   dB108Dot5       (217),
        -- info-VALUE:   dB109           (218),
        -- info-VALUE:   dB109Dot5       (219),
        -- info-VALUE:   dB110           (220),
        -- info-VALUE:   dB110Dot5       (221),
        -- info-VALUE:   dB111           (222),
        -- info-VALUE:   dB111Dot5       (223),
        -- info-VALUE:   dB112           (224),
        -- info-VALUE:   dB112Dot5       (225),
        -- info-VALUE:   dB113           (226),
        -- info-VALUE:   dB113Dot5       (227),
        -- info-VALUE:   dB114           (228),
        -- info-VALUE:   dB114Dot5       (229),
        -- info-VALUE:   dB115           (230),
        -- info-VALUE:   dB115Dot5       (231),
        -- info-VALUE:   dB116           (232),
        -- info-VALUE:   dB116Dot5       (233),
        -- info-VALUE:   dB117           (234),
        -- info-VALUE:   dB117Dot5       (235),
        -- info-VALUE:   dB118           (236),
        -- info-VALUE:   dB118Dot5       (237),
        -- info-VALUE:   dB119           (238),
        -- info-VALUE:   dB119Dot5       (239),
        -- info-VALUE:   dB120           (240),
        -- info-VALUE:   dB120Dot5       (241),
        -- info-VALUE:   dB121           (242),
        -- info-VALUE:   dB121Dot5       (243),
        -- info-VALUE:   dB122           (244),
        -- info-VALUE:   dB122Dot5       (245),
        -- info-VALUE:   dB123           (246),
        -- info-VALUE:   dB123Dot5       (247),
        -- info-VALUE:   dB124           (248),
        -- info-VALUE:   dB124Dot5       (249),
        -- info-VALUE:   dB125           (250),
        -- info-VALUE:   dB125Dot5       (251),
        -- info-VALUE:   dB126           (252),
        -- info-VALUE:   dB126Dot5       (253),
        -- info-VALUE:   dB127           (254),
        -- info-VALUE:   dB127Dot5       (255),
        -- info-VALUE:   attenuationInvalid (32767)
        -- info-ROU:     GET tm
        -- info-IMPL:    V2.0->
        -- info-VERCTRL: -
        SYNTAX        Xldv20AdslAttenuation
        ACCESS        read-only
        STATUS        mandatory
        DESCRIPTION
             " The current downstream attenuation in steps of 0,5 dB.
               Default is attenuationInvalid . "
        ::= { xldv20AdcPPTPEntry 16 }

     xldv20AdcAttenuationUp OBJECT-TYPE
        -- info-VALUE:   see xldv20AdcAttenuationDn
        -- info-ROU:     GET tm
        -- info-IMPL:    V2.0->
        -- info-VERCTRL: -
        SYNTAX        Xldv20AdslAttenuation
        ACCESS        read-only
        STATUS        mandatory
        DESCRIPTION
             " The current upstream attenuation in steps of 0,5 dB.
               Default is attenuationInvalid . "
        ::= { xldv20AdcPPTPEntry 17 }

     xldv20AdcLinkState OBJECT-TYPE
        -- info-VALUE:   unknown,idle,quiet,train,active,
        -- info-VALUE:   download,remoteDownload
        -- info-ROU:     GET tm
        -- info-IMPL:    V2.0->
        -- info-VERCTRL: -
        SYNTAX        Xldv20LinkState
        ACCESS        read-only
        STATUS        mandatory
        DESCRIPTION
             " The attribute reflects upon the internal states of the
               Central Office Modem. "
        ::= { xldv20AdcPPTPEntry 18 }

     xldv20AdcAISOnLOS  OBJECT-TYPE
        -- info-VALUE:   disabled : No VP-AIS generation (default)
        -- info-VALUE:   enabled  :    VP-AIS generation 
        -- info-ROU:     GET db SET tm
        -- info-IMPL:    V2.0->
        -- info-VERCTRL: -
        SYNTAX        Xldv20OperState
        ACCESS        read-write
        STATUS        mandatory
        DESCRIPTION
             " Enables or disables the VP-AIS generation
               after defect LOS. "
        ::= { xldv20AdcPPTPEntry 19 }

     xldv20AdcAISOnACT  OBJECT-TYPE
        -- info-VALUE:   disabled : No VP-AIS generation (default)
        -- info-VALUE:   enabled  :    VP-AIS generation 
        -- info-ROU:     GET db SET tm
        -- info-IMPL:    V2.0->
        -- info-VERCTRL: -
        SYNTAX        Xldv20OperState
        ACCESS        read-write
        STATUS        mandatory
        DESCRIPTION
             " Enables or disables the VP-AIS generation
               after link activation fault. "
        ::= { xldv20AdcPPTPEntry 20 }

        xldv20AdcGuaranteedBandwidthUsage OBJECT-TYPE
        -- info-VALUE:   0..100, default 0
        -- info-ROU:     GET db
        -- info-IMPL:    V2.0->
        -- info-VERCTRL: -
        SYNTAX        INTEGER (0..100)
        ACCESS        read-only
        STATUS        mandatory
        DESCRIPTION
             " Garanteed bandwidth in percent. "
        ::= { xldv20AdcPPTPEntry 21 }

     xldv20AdcXdslServiceTypeCfg OBJECT-TYPE
        -- info-VALUE:   gDotHsMode (handshake mode, ITU G.994.1)
        -- info-VALUE:   ansiT1Dot413 (full rate mode for ADSL equipment, ITU G.992.1)
        -- info-VALUE:   gDotLiteMode (for UDSL equipment, ITU G.992.2)
        -- info-VALUE:   gDotAll
        -- info-ROU:     GET db
        -- info-IMPL:    V2.0->
        -- info-VERCTRL: -
        SYNTAX        Xldv20XdslServiceType
        ACCESS        read-only
        STATUS        mandatory
        DESCRIPTION
             " The configured service mode for XDSL line. "
        ::= { xldv20AdcPPTPEntry 22 }

     xldv20AdcInitStatus OBJECT-TYPE
        -- info-VALUE:   ntNotPresent(1),communicationFailed(2)
        -- info-VALUE:   fastRetrainProfileError(3)
        -- info-VALUE:   rateParameterConfigurationError(4)
        -- info-VALUE:   serviceTypeAdrRequestRejected(5)
        -- info-VALUE:   serviceTypeAdcRequestRejected(6)
        -- info-VALUE:   configuredRatesOutOfRange(7) (not in g.992.2 range)
        -- info-VALUE:   configuredMinMaxRelationInvalid(8)
        -- info-VALUE:   channelRatesExceedsSystemLimits(9)
        -- info-VALUE:   adaptationCombinationInvalid(10)
        -- info-VALUE:   configuredDualChannelInvalid(11)
        -- info-VALUE:   marginLessThanMinMargin(12)
        -- info-VALUE:   adrNotCapableOfDualLatency(13)
        -- info-VALUE:   reserved1(14) ,reserved2(15)
        -- info-VALUE:   trainingBlockedBySu(16)
        -- info-VALUE:   trainingBlockedByCi(17)
        -- info-VALUE:   ntNotPresentDetectedOnCi(18)
        -- info-VALUE:   gliteModeNotPossibleInPCM(19)
        -- info-VALUE:   alarmsDetected(20)
        -- info-VALUE:   initStatusUnknown(21)
        -- info-VALUE:   noInitError(255)  (default value)
        -- info-ROU:     GET db
        -- info-IMPL:    V2.0->
        -- info-VERCTRL: -
        SYNTAX        Xldv20XdslInitStatus
        ACCESS        read-only
        STATUS        mandatory
        DESCRIPTION
             " The initialization status field of an ADSL line.
               Describes the initalization error in case of
               an activation problem on an ADSL line . "
        ::= { xldv20AdcPPTPEntry 23 }

        xldv20AdcTransceiverOutputPower OBJECT-TYPE
        -- info-VALUE:   dBm-31     (-31),
        -- info-VALUE:   dBm-30     (-30),
        -- info-VALUE:   dBm-29     (-29),
        -- info-VALUE:   dBm-28     (-28),
        -- info-VALUE:   dBm-27     (-27),
        -- info-VALUE:   dBm-26     (-26),
        -- info-VALUE:   dBm-25     (-25),
        -- info-VALUE:   dBm-24     (-24),
        -- info-VALUE:   dBm-23     (-23),
        -- info-VALUE:   dBm-22     (-22),
        -- info-VALUE:   dBm-21     (-21),
        -- info-VALUE:   dBm-20     (-20),
        -- info-VALUE:   dBm-19     (-19),
        -- info-VALUE:   dBm-18     (-18),
        -- info-VALUE:   dBm-17     (-17),
        -- info-VALUE:   dBm-16     (-16),
        -- info-VALUE:   dBm-15     (-15),
        -- info-VALUE:   dBm-14     (-14),
        -- info-VALUE:   dBm-13     (-13),
        -- info-VALUE:   dBm-12     (-12),
        -- info-VALUE:   dBm-11     (-11),
        -- info-VALUE:   dBm-10     (-10),
        -- info-VALUE:   dBm-9      (-9),
        -- info-VALUE:   dBm-8      (-8),
        -- info-VALUE:   dBm-7      (-7),
        -- info-VALUE:   dBm-6      (-6),
        -- info-VALUE:   dBm-5      (-5),
        -- info-VALUE:   dBm-4      (-4),
        -- info-VALUE:   dBm-3      (-3),
        -- info-VALUE:   dBm-2      (-2),
        -- info-VALUE:   dBm-1      (-1),
        -- info-VALUE:   dBm0       (0 ),
        -- info-VALUE:   dBm1       (1 ),
        -- info-VALUE:   dBm2       (2 ),
        -- info-VALUE:   dBm3       (3 ),
        -- info-VALUE:   dBm4       (4 ),
        -- info-VALUE:   dBm5       (5 ),
        -- info-VALUE:   dBm6       (6 ),
        -- info-VALUE:   dBm7       (7 ),
        -- info-VALUE:   dBm8       (8 ),
        -- info-VALUE:   dBm9       (9 ),
        -- info-VALUE:   dBm10      (10),
        -- info-VALUE:   dBm11      (11),
        -- info-VALUE:   dBm12      (12),
        -- info-VALUE:   dBm13      (13),
        -- info-VALUE:   dBm14      (14),
        -- info-VALUE:   dBm15      (15),
        -- info-VALUE:   dBm16      (16),
        -- info-VALUE:   dBm17      (17),
        -- info-VALUE:   dBm18      (18),
        -- info-VALUE:   dBm19      (19),
        -- info-VALUE:   dBm20      (20),
        -- info-VALUE:   dBm21      (21),
        -- info-VALUE:   dBm22      (22),
        -- info-VALUE:   dBm23      (23),
        -- info-VALUE:   dBm24      (24),
        -- info-VALUE:   dBm25      (25),
        -- info-VALUE:   dBm26      (26),
        -- info-VALUE:   dBm27      (27),
        -- info-VALUE:   dBm28      (28),
        -- info-VALUE:   dBm29      (29),
        -- info-VALUE:   dBm30      (30),
        -- info-VALUE:   dBm31      (31),
        -- info-VALUE:   dBm32      (32),
        -- info-VALUE:   outputPowerInvalid (32767)
        -- info-ROU:     GET tm
        -- info-IMPL:    V2.0->
        -- info-VERCTRL: -
        SYNTAX        Xldv20AdslOutputPower
        ACCESS        read-only
        STATUS        mandatory
        DESCRIPTION
             " The ADSL tranceiver output power. Granularity 1.0 dBm.
	     Default value is outputPowerInvalid. "
        ::= { xldv20AdcPPTPEntry 24 }

        xldv20AdcFirstUsedSubCarrierUpstream OBJECT-TYPE
        -- info-VALUE:   0..64
        -- info-ROU:     GET tm
        -- info-IMPL:    V2.0->
        -- info-VERCTRL: -
        SYNTAX        INTEGER (0..64)
        ACCESS        read-only
        STATUS        mandatory
        DESCRIPTION
             " The first used sub carrier in upstream direction.
	     Default value is 64 (unknown). "
        ::= { xldv20AdcPPTPEntry 25 }

	xldv20AdcFirstUsedSubCarrierDownstream OBJECT-TYPE
        -- info-VALUE:   0..256
        -- info-ROU:     GET tm
        -- info-IMPL:    V2.0->
        -- info-VERCTRL: -
        SYNTAX        INTEGER (0..256)
        ACCESS        read-only
        STATUS        mandatory
        DESCRIPTION
             " The first used sub carrier in downstream direction.
	     Default value is 256 (unknown). "
        ::= { xldv20AdcPPTPEntry 26 }

        xldv20AdcLastUsedSubCarrierUpstream OBJECT-TYPE
        -- info-VALUE:   0..64
        -- info-ROU:     GET tm
        -- info-IMPL:    V2.0->
        -- info-VERCTRL: -
        SYNTAX        INTEGER (0..64)
        ACCESS        read-only
        STATUS        mandatory
        DESCRIPTION
             " The last used sub carrier in upstream direction.
	     Default value is 64 (unknown). "
        ::= { xldv20AdcPPTPEntry 27 }

	xldv20AdcLastUsedSubCarrierDownstream OBJECT-TYPE
        -- info-VALUE:   0..256
        -- info-ROU:     GET tm
        -- info-IMPL:    V2.0->
        -- info-VERCTRL: -
        SYNTAX        INTEGER (0..256)
        ACCESS        read-only
        STATUS        mandatory
        DESCRIPTION
             " The last used sub carrier in downstream direction.
	     Default value is 256 (unknown). "
        ::= { xldv20AdcPPTPEntry 28 }

	xldv20AdcXdslServiceType OBJECT-TYPE
        -- info-VALUE:   gDotDmtMode  (1),
        -- info-VALUE:   ansiT1Dot413 (2),
        -- info-VALUE:   gDotLiteMode (3)
        -- info-VALUE:   serviceTypeUnknown (10)
        -- info-ROU:     GET tm
        -- info-IMPL:    V2.0->
        -- info-VERCTRL: -
        SYNTAX        Xldv20XdslServiceTypeCurrent
        ACCESS        read-only
        STATUS        mandatory
        DESCRIPTION
             " The current service type resulting from the configured service
	     type. It depends on the actual hardware.
	     Configuring gDotHsMode can result either in gDotLiteMode or gDotDmtMode.
	     gDotAll can result in gDotDmtMode, ansiT1dot413 or gDotLiteMode.
	     Default value is serviceTypeUnknown (10). "
        ::= { xldv20AdcPPTPEntry 29 }


     -- --------------------------------------------------------------
     --                   TLM VDSL central PPTP Table (not used in V2.0)
     -- --------------------------------------------------------------
     --
     -- This managed entity represents the extension for the PPTP at
     -- the VDSL-C interface. It includes additional attributes to
     -- configure the VDSL link.
     --
     xldv20VdcPPTPTable OBJECT-TYPE
        -- info-IMPL:    V2.x->
        SYNTAX        SEQUENCE OF Xldv20VdcPPTPEntry
        ACCESS        not-accessible
        STATUS        mandatory
        DESCRIPTION
             " Feature not supported.
             The physical path termination point table for VDSL C. "
        --DEFAULT next-function-async     fsnVdcEntryNext
        --DEFAULT get-function-async      fsnVdcEntryGet
        ::= { xldv20Tlm 5 }

     xldv20VdcPPTPEntry OBJECT-TYPE
        -- info-IMPL:    V2.x->
        SYNTAX        Xldv20VdcPPTPEntry
        ACCESS        not-accessible
        STATUS        mandatory
        DESCRIPTION
             " An entry describing a termination point in the PPTP table.
               Notifications : see xldv20IfEntry. "
        INDEX         { xldv20IfIndex }
        ::= { xldv20VdcPPTPTable 1 }

     Xldv20VdcPPTPEntry ::=
        SEQUENCE { xldv20VdcMinRateDnCfg        Xldv20VdcRateDn,
                   xldv20VdcMinRateUpCfg        Xldv20VdcRateUp,
                   xldv20VdcMaxRateDnCfg        Xldv20VdcRateDn,
                   xldv20VdcMaxRateUpCfg        Xldv20VdcRateUp,
                   xldv20VdcLatencyDnCfg        Xldv20VdcLatencyDn,
                   xldv20VdcLatencyUpCfg        Xldv20VdcLatencyUp,
                   xldv20VdcPowerBoostCfg       Xldv20VdcPowerBoostAdaptationType,
                   xldv20VdcWarmStartCfg        Xldv20OperState,
                   xldv20VdcVdslModeCfg         Xldv20VdcVdslMode,
                   xldv20VdcSleepModeCfg        Xldv20OperState,
                   xldv20VdcPsdMaskCfg          Xldv20VdcPsdMask,
                   xldv20VdcPowerAdaptationCfg  Xldv20VdcPowerBoostAdaptationType,
                   xldv20VdcRateDn              Xldv20VdcRateDn,
                   xldv20VdcRateUp              Xldv20VdcRateUp,
                   xldv20VdcMarginDn            Integer32,
                   xldv20VdcMarginUp            Integer32,
                   xldv20VdcAttenuationDn       Integer32,
                   xldv20VdcAttenuationUp       Integer32,
                   xldv20VdcLinkState           Xldv20LinkState,
                   xldv20VdcGuaranteedBandwidthUsage INTEGER }

     xldv20VdcMinRateDnCfg OBJECT-TYPE
        -- info-VALUE:   (multiples of 810 kbps)
        -- info-VALUE:   2,4,6,8,12,16
        -- info-VALUE:   24,32,48,64
        -- info-ROU:     GET db
        -- info-IMPL:    V2.x
        -- info-VERCTRL: -
        SYNTAX        Xldv20VdcRateDn
        ACCESS        not-accessible
        STATUS        mandatory
        DESCRIPTION
             " The lower limit of the downstream data rate. "
        ::= { xldv20VdcPPTPEntry 1 }

     xldv20VdcMinRateUpCfg OBJECT-TYPE
        -- info-VALUE:   (multiples of 810 kbps)
        -- info-VALUE:   1,2,4,8,12,16
        -- info-ROU:     GET db
        -- info-IMPL:    V2.x
        -- info-VERCTRL: -
        SYNTAX        Xldv20VdcRateUp
        ACCESS        not-accessible
        STATUS        mandatory
        DESCRIPTION
             " The lower limit of the upstream data rate. "
        ::= { xldv20VdcPPTPEntry 2 }

     xldv20VdcMaxRateDnCfg OBJECT-TYPE
        -- info-VALUE:   (multiples of 810 kbps)
        -- info-VALUE:   2,4,6,8,12,16
        -- info-VALUE:   24,32,48,64
        -- info-ROU:     GET db
        -- info-IMPL:    V2.x
        -- info-VERCTRL: -
        SYNTAX        Xldv20VdcRateDn
        ACCESS        not-accessible
        STATUS        mandatory
        DESCRIPTION
             " The upper limit of the downstream data rate. "
        ::= { xldv20VdcPPTPEntry 3 }

     xldv20VdcMaxRateUpCfg OBJECT-TYPE
        -- info-VALUE:   (multiples of 810 kbps)
        -- info-VALUE:   1,2,4,8,12,16
        -- info-ROU:     GET db
        -- info-IMPL:    V2.x
        -- info-VERCTRL: -
        SYNTAX        Xldv20VdcRateUp
        ACCESS        not-accessible
        STATUS        mandatory
        DESCRIPTION
             " The upper limit of the upstream data rate. "
        ::= { xldv20VdcPPTPEntry 4 }

     xldv20VdcLatencyDnCfg OBJECT-TYPE
        -- info-VALUE:   (delay in msec)
        -- info-VALUE:   0,2,4,8,12,16,20,32
        -- info-ROU:     GET db
        -- info-IMPL:    V2.x
        -- info-VERCTRL: -
        SYNTAX        Xldv20VdcLatencyDn
        ACCESS        not-accessible
        STATUS        mandatory
        DESCRIPTION
              " Desired interleave depth (i.e. latency time) used for
                error correction in downstream direction. "
        ::= { xldv20VdcPPTPEntry 5 }

     xldv20VdcLatencyUpCfg OBJECT-TYPE
        -- info-VALUE:   (delay in msec)
        -- info-VALUE:   0,2,4,8,10,20
        -- info-ROU:     GET db
        -- info-IMPL:    V2.x
        -- info-VERCTRL: -
        SYNTAX        Xldv20VdcLatencyUp
        ACCESS        not-accessible
        STATUS        mandatory
        DESCRIPTION
              " Desired interleave depth (i.e. latency time) used for
                error correction in upstream direction. "
        ::= { xldv20VdcPPTPEntry 6 }

     xldv20VdcPowerBoostCfg OBJECT-TYPE
        -- info-VALUE:   suEnabled,ntEnabled,bothEnabled,bothDisabled
        -- info-ROU:     GET db
        -- info-IMPL:    V2.x
        -- info-VERCTRL: -
        SYNTAX        Xldv20VdcPowerBoostAdaptationType
        ACCESS        not-accessible
        STATUS        mandatory
        DESCRIPTION
              " Desired power boost mode. "
        ::= { xldv20VdcPPTPEntry 7 }

     xldv20VdcWarmStartCfg OBJECT-TYPE
        -- info-VALUE:   enabled, disabled
        -- info-ROU:     GET db
        -- info-IMPL:    V2.x
        -- info-VERCTRL: -
        SYNTAX        Xldv20OperState
        ACCESS        not-accessible
        STATUS        mandatory
        DESCRIPTION
              " Configured warmstart option. "
        ::= { xldv20VdcPPTPEntry 8 }

     xldv20VdcVdslModeCfg OBJECT-TYPE
        -- info-VALUE:   adslFriendly, vdslEfficient
        -- info-ROU:     GET db
        -- info-IMPL:    V2.x
        -- info-VERCTRL: -
        SYNTAX        Xldv20VdcVdslMode
        ACCESS        not-accessible
        STATUS        mandatory
        DESCRIPTION
              " Configured VDSL mode option. "
        ::= { xldv20VdcPPTPEntry 9 }

     xldv20VdcSleepModeCfg OBJECT-TYPE
        -- info-VALUE:   enabled, disabled
        -- info-ROU:     GET db
        -- info-IMPL:    V2.x
        -- info-VERCTRL: -
        SYNTAX        Xldv20OperState
        ACCESS        not-accessible
        STATUS        mandatory
        DESCRIPTION
              " Desired sleep mode option. "
        ::= { xldv20VdcPPTPEntry 10 }

     xldv20VdcPsdMaskCfg OBJECT-TYPE
        -- info-VALUE:   m1 (strong effect), m2 (weak effect)
        -- info-ROU:     GET db
        -- info-IMPL:    V2.x
        -- info-VERCTRL: -
        SYNTAX        Xldv20VdcPsdMask
        ACCESS        not-accessible
        STATUS        mandatory
        DESCRIPTION
              " Desired PSD mask option (electro-magnetic interference
                effects, M1 for strong and M2 for weak effects). "
        ::= { xldv20VdcPPTPEntry 11 }

     xldv20VdcPowerAdaptationCfg OBJECT-TYPE
        -- info-VALUE:   suEnabled,ntEnabled,bothEnabled,bothDisabled
        -- info-ROU:     GET db
        -- info-IMPL:    V2.x
        -- info-VERCTRL: -
        SYNTAX        Xldv20VdcPowerBoostAdaptationType
        ACCESS        not-accessible
        STATUS        mandatory
        DESCRIPTION
              " Desired power adaptation option. "
        ::= { xldv20VdcPPTPEntry 12 }

     xldv20VdcRateDn OBJECT-TYPE
        -- info-VALUE:   (multiples of 810 kbps)
        -- info-VALUE:   2,4,6,8,12,16
        -- info-VALUE:   24,32,48,64
        -- info-ROU:     GET db
        -- info-IMPL:    V2.x
        -- info-VERCTRL: -
        SYNTAX        Xldv20VdcRateDn
        ACCESS        not-accessible
        STATUS        mandatory
        DESCRIPTION
             " The current downstream data rate. "
        ::= { xldv20VdcPPTPEntry 13 }

     xldv20VdcRateUp OBJECT-TYPE
        -- info-VALUE:   (multiples of 810 kbps)
        -- info-VALUE:   1,2,4,8,12,16
        -- info-ROU:     GET db
        -- info-IMPL:    V2.x
        -- info-VERCTRL: -
        SYNTAX        Xldv20VdcRateUp
        ACCESS        not-accessible
        STATUS        mandatory
        DESCRIPTION
             " The current upstream data rate. "
        ::= { xldv20VdcPPTPEntry 14 }

     xldv20VdcMarginDn OBJECT-TYPE
        -- info-VALUE:   -2147483648..2147483647
        -- info-ROU:     GET db
        -- info-IMPL:    V2.x
        -- info-VERCTRL: -
        SYNTAX        Integer32
        ACCESS        not-accessible
        STATUS        mandatory
        DESCRIPTION
             " The current downstream margin in units of dB. "
        ::= { xldv20VdcPPTPEntry 15 }

     xldv20VdcMarginUp OBJECT-TYPE
        -- info-VALUE:   -2147483648..2147483647
        -- info-ROU:     GET db
        -- info-IMPL:    V2.x
        -- info-VERCTRL: -
        SYNTAX        Integer32
        ACCESS        not-accessible
        STATUS        mandatory
        DESCRIPTION
             " The current upstream margin in units of dB. "
        ::= { xldv20VdcPPTPEntry 16 }

     xldv20VdcAttenuationDn OBJECT-TYPE
        -- info-VALUE:   -2147483648..2147483647
        -- info-ROU:     GET db
        -- info-IMPL:    V2.x
        -- info-VERCTRL: -
        SYNTAX        Integer32
        ACCESS        not-accessible
        STATUS        mandatory
        DESCRIPTION
             " The current downstream attenuation in units of dB. "
        ::= { xldv20VdcPPTPEntry 17 }

     xldv20VdcAttenuationUp OBJECT-TYPE
        -- info-VALUE:   -2147483648..2147483647
        -- info-ROU:     GET db
        -- info-IMPL:    V2.x
        -- info-VERCTRL: -
        SYNTAX        Integer32
        ACCESS        not-accessible
        STATUS        mandatory
        DESCRIPTION
             " The current upstream attenuation in units of dB. "
        ::= { xldv20VdcPPTPEntry 18 }

     xldv20VdcLinkState OBJECT-TYPE
        -- info-VALUE:   unknown,idle,quiet,train,active,
        -- info-VALUE:   sleepMode
        -- info-ROU:     GET db
        -- info-IMPL:    V2.x
        -- info-VERCTRL: -
        SYNTAX        Xldv20LinkState
        ACCESS        not-accessible
        STATUS        mandatory
        DESCRIPTION
             " Current internal states of the Central Office VDSL Modem. "
        ::= { xldv20VdcPPTPEntry 19 }

        xldv20VdcGuaranteedBandwidthUsage OBJECT-TYPE
        -- info-VALUE:   0..100, default 0
        -- info-ROU:     GET db
        -- info-IMPL:    V2.x->
        -- info-VERCTRL: -
        SYNTAX        INTEGER (0..100)
        ACCESS        not-accessible
        STATUS        mandatory
        DESCRIPTION
             " used bandwidth in percent. "
        ::= { xldv20VdcPPTPEntry 20 }

     -- --------------------------------------------------------------
     --                   TLM IBM PPTP Table 
     -- --------------------------------------------------------------
     --
     -- This managed entity represents the extension for the PPTP at
     -- the IBM interface.
     --

     xldv20IbmPPTPTable OBJECT-TYPE
        -- info-IMPL:    V2.0->          
        SYNTAX        SEQUENCE OF Xldv20IbmPPTPEntry
        ACCESS        not-accessible
        STATUS        mandatory
        DESCRIPTION
             " The physical path termination point table for the IBM IF. "
        --DEFAULT test-function-async     fsnIbmEntryTest
        --DEFAULT next-function-async     fsnIbmEntryNext
        --DEFAULT set-function-async      fsnIbmEntrySet
        --DEFAULT get-function-async      fsnIbmEntryGet
        ::= { xldv20Tlm 6 }

     xldv20IbmPPTPEntry OBJECT-TYPE
        -- info-IMPL:    V2.0->          
        SYNTAX        Xldv20IbmPPTPEntry
        ACCESS        not-accessible
        STATUS        mandatory
        DESCRIPTION
             " An entry describing a termination point in the IbmPPTP table.
               Notifications : see xldv20IfEntry. "
        INDEX         { xldv20IfIndex }
        ::= { xldv20IbmPPTPTable 1 }

     Xldv20IbmPPTPEntry ::= SEQUENCE {
                xldv20IbmAISOnLOS         Xldv20OperState,
                xldv20IbmVpAISFiltering   Xldv20OperState
                }

     xldv20IbmAISOnLOS  OBJECT-TYPE
        -- info-VALUE:   disabled : No VP-AIS generation (default)
        -- info-VALUE:   enabled  :    VP-AIS generation 
        -- info-ROU:     GET db SET tm
        -- info-IMPL:    V2.0->          
        -- info-VERCTRL: -
        SYNTAX        Xldv20OperState
        ACCESS        read-write
        STATUS        mandatory
        DESCRIPTION
             " To enable/disable (default) the VP-AIS generation on defect LOS. "
        ::= { xldv20IbmPPTPEntry 1 }

     xldv20IbmVpAISFiltering  OBJECT-TYPE
        -- info-VALUE:   disabled : No VP-AIS cell filtering (default)
        -- info-VALUE:   enabled  :    VP-AIS cell filtering
        -- info-ROU:     GET db SET tm
        -- info-IMPL:    V2.0->
        -- info-VERCTRL: -
        SYNTAX        Xldv20OperState
        ACCESS        read-write
        STATUS        mandatory
        DESCRIPTION
             " To enable or disable (default) the VP-AIS cell filtering function
             in the NT. In case of enable no VP-AIS cells are passed
             to the subscriber. "
        ::= { xldv20IbmPPTPEntry 2 }


     -- --------------------------------------------------------------
     --                  TLM DS3 near-end PPTP Table 
     -- --------------------------------------------------------------
     --
     -- This managed entity represents the extension for the PPTP at the
     -- DS3 near-end interface. It includes the additional attributes to
     -- configure the DS3 link.
     --

     xldv20Ds3NePPTPTable OBJECT-TYPE
        -- info-IMPL:    V2.0->          
        SYNTAX        SEQUENCE OF Xldv20Ds3NePPTPEntry
        ACCESS        not-accessible
        STATUS        mandatory
        DESCRIPTION
             " The near end physical path termination point table
	     for the DS3 interface. "
        --DEFAULT test-function-async     fsnD3nEntryTest
        --DEFAULT next-function-async     fsnD3nEntryNext
        --DEFAULT set-function-async      fsnD3nEntrySet
        --DEFAULT get-function-async      fsnD3nEntryGet
        ::= { xldv20Tlm 7 }

     xldv20Ds3NePPTPEntry OBJECT-TYPE
        -- info-IMPL:    V2.0->          
        SYNTAX        Xldv20Ds3NePPTPEntry
        ACCESS        not-accessible
        STATUS        mandatory
        DESCRIPTION
             " An entry describing a termination point in the PPTP table.
               Notifications : see xldv20IfEntry. "
        INDEX         { xldv20IfIndex }
        ::= { xldv20Ds3NePPTPTable 1 }

     Xldv20Ds3NePPTPEntry ::=
        SEQUENCE { xldv20D3nType                       Xldv20LineType,
                   xldv20D3nCodingType                 Xldv20CodingType,
                   xldv20D3nPayloadScramblingActivate  Xldv20OperState,
                   xldv20D3nEmptyCellType              Xldv20EmptyCellType,
                   xldv20D3nBandwidthUsage             INTEGER }

     xldv20D3nType OBJECT-TYPE
        -- info-VALUE:   ds3plcp
        -- info-ROU:     GET db
        -- info-IMPL:    V2.0->          
        -- info-VERCTRL: -
        SYNTAX        Xldv20LineType
        ACCESS        read-only
        STATUS        mandatory
        DESCRIPTION
             " The interface type of the line used for transmission. "
        ::= { xldv20Ds3NePPTPEntry 1 }

     xldv20D3nCodingType OBJECT-TYPE
        -- info-VALUE:   dsx3B3ZS
        -- info-ROU:     GET db
        -- info-IMPL:    V2.0->          
        -- info-VERCTRL: -
        SYNTAX        Xldv20CodingType
        ACCESS        read-only
        STATUS        mandatory
        DESCRIPTION
             " The coding type of the line used for transmission.
               Value: dsx3B3ZS . "
        ::= { xldv20Ds3NePPTPEntry 2 }

     xldv20D3nPayloadScramblingActivate OBJECT-TYPE
        -- info-VALUE:   enabled (default), disabled
        -- info-ROU:     GET db SET tm
        -- info-IMPL:    V2.0->          
        -- info-VERCTRL: -
        SYNTAX        Xldv20OperState
        ACCESS        read-write
        STATUS        mandatory
        DESCRIPTION
             " Enables (default) / disables the payload scrambling . "
        ::= { xldv20Ds3NePPTPEntry 3 }

     xldv20D3nEmptyCellType OBJECT-TYPE
        -- info-VALUE:   idle, unassigned (default)
        -- info-ROU:     GET db SET tm
        -- info-IMPL:    V2.0->          
        -- info-VERCTRL: -
        SYNTAX        Xldv20EmptyCellType 
        ACCESS        read-write
        STATUS        mandatory
        DESCRIPTION
             " The type of empty cells. "
        ::= { xldv20Ds3NePPTPEntry 4 }

        xldv20D3nBandwidthUsage OBJECT-TYPE
        -- info-VALUE:   0..100, default 0
        -- info-ROU:     GET db
        -- info-IMPL:    V2.0->
        -- info-VERCTRL: -
        SYNTAX        INTEGER (0..100)
        ACCESS        read-only
        STATUS        mandatory
        DESCRIPTION
             " Used bandwidth in percent.  "
        ::= { xldv20Ds3NePPTPEntry 5 }

     -- --------------------------------------------------------------
     --                   TLM E3 near-end PPTP Table
     -- --------------------------------------------------------------
     --
     -- This managed entity represents the extension for the PPTP at
     -- the E3 near-end interface. It includes the additional
     -- attributes to configure the E3 link.
     --

     xldv20E3NePPTPTable OBJECT-TYPE
        -- info-IMPL:    V2.0->          
        SYNTAX        SEQUENCE OF Xldv20E3NePPTPEntry
        ACCESS        not-accessible
        STATUS        mandatory
        DESCRIPTION
             " The physical path termination point table for the E3 IF. "
        --DEFAULT test-function-async     fsnE3nEntryTest
        --DEFAULT next-function-async     fsnE3nEntryNext
        --DEFAULT set-function-async      fsnE3nEntrySet
        --DEFAULT get-function-async      fsnE3nEntryGet
        ::= { xldv20Tlm 8 }

     xldv20E3NePPTPEntry OBJECT-TYPE
        -- info-IMPL:    V2.0->          
        SYNTAX        Xldv20E3NePPTPEntry
        ACCESS        not-accessible
        STATUS        mandatory
        DESCRIPTION
             " An entry describing a termination point in the PPTP table.
               Notifications : see xldv20IfEntry. "
        INDEX         { xldv20IfIndex }
        ::= { xldv20E3NePPTPTable 1 }

     Xldv20E3NePPTPEntry ::=
        SEQUENCE { xldv20E3nType                       Xldv20LineType,
                   xldv20E3nCodingType                 Xldv20CodingType,
                   xldv20E3nTrailTraceSend             OCTET STRING,
                   xldv20E3nTrailTraceSendDefault      Xldv20OperState,
                   xldv20E3nTrailTraceExpect           OCTET STRING,
                   xldv20E3nTrailTraceTIMDetectionActivate  Xldv20OperState,
                   xldv20E3nTrailTraceReceive          OCTET STRING,
                   xldv20E3nEmptyCellType              Xldv20EmptyCellType,
                   xldv20E3nPayloadType                Xldv20E3nPayloadType,
                   xldv20E3nBandwidthUsage             INTEGER }

     xldv20E3nType OBJECT-TYPE
        -- info-VALUE:   e3direct
        -- info-ROU:     GET db
        -- info-IMPL:    V2.0->          
        -- info-VERCTRL: -
        SYNTAX        Xldv20LineType
        ACCESS        read-only
        STATUS        mandatory
        DESCRIPTION
             " The interface type of the line used for transmission. "
        ::= { xldv20E3NePPTPEntry 1 }

     xldv20E3nCodingType OBJECT-TYPE
        -- info-VALUE:   e3HDB3
        -- info-ROU:     GET db
        -- info-IMPL:    V2.0->          
        -- info-VERCTRL: -
        SYNTAX        Xldv20CodingType
        ACCESS        read-only
        STATUS        mandatory
        DESCRIPTION
             " The coding type of the line used for transmission. "
        ::= { xldv20E3NePPTPEntry 2 }

     xldv20E3nTrailTraceSend OBJECT-TYPE
        -- info-VALUE:   default : 15 * 0x00
        -- info-VALUE:   15 times [ 0x00 .. 0x7F ]
        -- info-ROU:     GET db SET tm
        -- info-IMPL:    V2.0->          
        -- info-VERCTRL: -
        SYNTAX        OCTET STRING ( SIZE (0..16) )
        ACCESS        read-write
        STATUS        mandatory
        DESCRIPTION
             " The pattern to be sent to LE for the trail
               trace send functionality. "
        ::= { xldv20E3NePPTPEntry 3 }

     xldv20E3nTrailTraceSendDefault OBJECT-TYPE
        -- info-VALUE:   enabled (default), disabled
        -- info-ROU:     GET db SET tm
        -- info-IMPL:    V2.0->          
        -- info-VERCTRL: -
        SYNTAX        Xldv20OperState
        ACCESS        read-write
        STATUS        mandatory
        DESCRIPTION
             " To configure the trail trace send functionality.
	     A default trace value (enabled) or the pattern
               defined in the xldv20E3nTrailTraceSend attribute (disabled) will
               be sent. "
        ::= { xldv20E3NePPTPEntry 4 }


     xldv20E3nTrailTraceExpect OBJECT-TYPE
        -- info-VALUE:   default : 15 * 0x00
        -- info-VALUE:   15 times [ 0x00 .. 0x7F ]
        -- info-ROU:     GET db SET tm 
        -- info-IMPL:    V2.0->          
        -- info-VERCTRL: -
        SYNTAX        OCTET STRING ( SIZE (0..16) )
        ACCESS        read-write
        STATUS        mandatory
        DESCRIPTION
             " The expected pattern.
	     It will be compared with the value of the
               E3nTrailTraceReceive attribute provided that the attribute
               E3nTrailTraceTIMDetection is enabled. "
        ::= { xldv20E3NePPTPEntry 5 }

     xldv20E3nTrailTraceTIMDetectionActivate OBJECT-TYPE
        -- info-VALUE:   enabled, disabled (default)
        -- info-ROU:     GET db SET tm
        -- info-IMPL:    V2.0->          
        -- info-VERCTRL: -
        SYNTAX        Xldv20OperState
        ACCESS        read-write
        STATUS        mandatory
        DESCRIPTION
             " Enables / disables (default) signal comparison of the signals
               E3nTrailTraceExpect and E3nTrailTraceReceive. "
        ::= { xldv20E3NePPTPEntry 6 }

     xldv20E3nTrailTraceReceive OBJECT-TYPE
        -- info-VALUE:   15 times <= 0x7F
        -- info-ROU:     GET tm
        -- info-IMPL:    V2.0->          
        -- info-VERCTRL: -
        SYNTAX        OCTET STRING ( SIZE (0..16) )
        ACCESS        read-only
        STATUS        mandatory
        DESCRIPTION
             " The received trail trace value from the LE. "
        ::= { xldv20E3NePPTPEntry 7 }

     xldv20E3nEmptyCellType OBJECT-TYPE
        -- info-VALUE:   idle (default), unassigned
        -- info-ROU:     GET db SET tm
        -- info-IMPL:    V2.0->          
        -- info-VERCTRL: -
        SYNTAX        Xldv20EmptyCellType
        ACCESS        read-write
        STATUS        mandatory
        DESCRIPTION
             " Type of empty cells. "
        ::= { xldv20E3NePPTPEntry 8 }

     xldv20E3nPayloadType OBJECT-TYPE
        -- info-VALUE:   unequipped(1), nonSpecific(2),
        -- info-VALUE:   atm(3) (default) 
        -- info-ROU:     GET tm 
        -- info-IMPL:    V2.0->          
        -- info-VERCTRL: -
        SYNTAX        Xldv20E3nPayloadType
        ACCESS        read-only
        STATUS        mandatory
        DESCRIPTION
             " The received payload type. "
        ::= { xldv20E3NePPTPEntry 9 }

        xldv20E3nBandwidthUsage OBJECT-TYPE
        -- info-VALUE:   0..100, default 0
        -- info-ROU:     GET db
        -- info-IMPL:    V2.0->
        -- info-VERCTRL: -
        SYNTAX        INTEGER (0..100)
        ACCESS        read-only
        STATUS        mandatory
        DESCRIPTION
             " Used bandwidth in percent. "
        ::= { xldv20E3NePPTPEntry 10 }

     -- --------------------------------------------------------------
     --                 TLM STM1 near-end PPTP Table
     -- --------------------------------------------------------------
     --
     -- This managed entity represents the extension for the PPTP at
     -- the STM1 near-end interface. It includes the additional
     -- attributes to configure the STM1 link.
     --

     xldv20Stm1NePPTPTable OBJECT-TYPE
        -- info-IMPL:    V2.0->          
        SYNTAX        SEQUENCE OF Xldv20Stm1NePPTPEntry
        ACCESS        not-accessible
        STATUS        mandatory
        DESCRIPTION
             " The physical path termination point table for the STM1 IF. "
        --DEFAULT test-function-async     fsnS1nEntryTest
        --DEFAULT next-function-async     fsnS1nEntryNext
        --DEFAULT set-function-async      fsnS1nEntrySet
        --DEFAULT get-function-async      fsnS1nEntryGet
        ::= { xldv20Tlm 9 }

     xldv20Stm1NePPTPEntry OBJECT-TYPE
        -- info-IMPL:    V2.0->          
        SYNTAX        Xldv20Stm1NePPTPEntry
        ACCESS        not-accessible
        STATUS        mandatory
        DESCRIPTION
             " An entry describing a termination point in the PPTP table.
               Notifications : see xldv20IfEntry. "
        INDEX         { xldv20IfIndex }
        ::= { xldv20Stm1NePPTPTable 1 }

     Xldv20Stm1NePPTPEntry ::=
        SEQUENCE { xldv20S1nLineType                 Xldv20LineType,
                   xldv20S1nPathTraceSend            OCTET STRING,
                   xldv20S1nPathTraceSendDefault     Xldv20OperState,
                   xldv20S1nPathTraceExpect          OCTET STRING,
                   xldv20S1nPathTraceTIMDetectionActivate  Xldv20OperState,
                   xldv20S1nPathTraceReceive         OCTET STRING,
                   xldv20S1nHpEberThreshold          Xldv20S1nS3nEberThreshold,
                   xldv20S1nMsEberThreshold          Xldv20S1nS3nEberThreshold,
                   xldv20S1nRsEberThreshold          Xldv20S1nS3nEberThreshold,
                   xldv20S1nSDThreshold              Xldv20S1nS3nSDThreshold,
                   xldv20S1nRDIAISOnEber             Xldv20OperState,
                   xldv20S1nSignalLabelReceive       Integer32,
                   xldv20S1nEmptyCellType            Xldv20EmptyCellType,
                   xldv20S1nBandwidthUsage           INTEGER }

     xldv20S1nLineType OBJECT-TYPE
        -- info-VALUE:   mediumSingleMode,
        -- info-VALUE:   longSingleMode, coax
        -- info-ROU:     GET db
        -- info-IMPL:    V2.0->          
        SYNTAX        Xldv20LineType
        ACCESS        read-only
        STATUS        mandatory
        DESCRIPTION
             " The physical medium of the line used for transmission. "
        ::= { xldv20Stm1NePPTPEntry 1 }

     xldv20S1nPathTraceSend OBJECT-TYPE
        -- info-VALUE:   1'st byte: any value (CRC incl. Sync-Bit)
        -- info-VALUE:   1'st byte: inserted value will be ignored by DSLAM and
        -- info-VALUE:   generated itself by DSLAM.                      
        -- info-VALUE:   2'nd-16'th byte: value <= 0x7F
        -- info-ROU:     GET db  SET tm 
        -- info-IMPL:    V2.0->          
        -- info-VERCTRL: -
        SYNTAX        OCTET STRING ( SIZE (0..16) )
        ACCESS        read-write
        STATUS        mandatory
        DESCRIPTION
             " Pattern to be sent to the LE (CRC + 15 bytes) used for the path
               trace send functionality. "
        ::= { xldv20Stm1NePPTPEntry 2 }

     xldv20S1nPathTraceSendDefault OBJECT-TYPE
        -- info-VALUE:   enabled(1), disabled(2)
        -- info-VALUE:   default: enabled
        -- info-ROU:     GET db  SET tm 
        -- info-IMPL:    V2.0->          
        -- info-VERCTRL: -
        SYNTAX        Xldv20OperState
        ACCESS        read-write
        STATUS        mandatory
        DESCRIPTION
             " To configure the path trace send functionality.
               A default path trace value (enabled) or the pattern
               defined in the xldv20S1nPathTraceSend attribute (disabled) will
               be sent. "
        ::= { xldv20Stm1NePPTPEntry 3 }

     xldv20S1nPathTraceExpect OBJECT-TYPE
        -- info-VALUE:   1'st byte: any value (CRC incl. Sync-Bit)
        -- info-VALUE:   1'st byte: inserted value will be ignored by DSLAM and
        -- info-VALUE:   generated itself by DSLAM.                        
        -- info-VALUE:   2'nd-16'th byte: value <= 0x7F
        -- info-ROU:     GET db  SET tm
        -- info-IMPL:    V2.0->          
        -- info-VERCTRL: -
        SYNTAX        OCTET STRING ( SIZE (0..16) )
        ACCESS        read-write
        STATUS        mandatory
        DESCRIPTION
             " The expected result of a path trace operation.
	       This signal will be compared with the
               S1nPathTraceReceive, when the Attribute
               S1nPathTraceTIMDetectionActivate is enabled. If the comparison 
               detects unequality an alarm notification (TIM) is sent. "
        ::= { xldv20Stm1NePPTPEntry 4 }

     xldv20S1nPathTraceTIMDetectionActivate OBJECT-TYPE
        -- info-VALUE:   enabled(1), disabled(2) (default)
        -- info-ROU:     GET db  SET tm
        -- info-IMPL:    V2.0->          
        -- info-VERCTRL: -
        SYNTAX        Xldv20OperState
        ACCESS        read-write
        STATUS        mandatory
        DESCRIPTION
             " Enables / disables (default) the comparison of xldv20S1nPathTraceExpect
	     and xldv20S1nPathTraceReceive attribute. "
        ::= { xldv20Stm1NePPTPEntry 5 }

     xldv20S1nPathTraceReceive OBJECT-TYPE
        -- info-VALUE:   1'st byte: CRC (incl. Sync-Bit)
        -- info-VALUE:   2'nd-16'th byte: value <= 0x7F
        -- info-ROU:     GET tm
        -- info-IMPL:    V2.0->          
        -- info-VERCTRL: -
        SYNTAX        OCTET STRING ( SIZE (0..16) )
        ACCESS        read-only
        STATUS        mandatory
        DESCRIPTION
             " Received path trace value from the LE. "
        ::= { xldv20Stm1NePPTPEntry 6 }

     xldv20S1nHpEberThreshold OBJECT-TYPE
        -- info-VALUE:   exp10E3(1), exp10E4(2), exp10E5(3), noSupervision(255)
        -- info-VALUE:   default: exp10E3
        -- info-ROU:     GET db  SET tm 
        -- info-IMPL:    V2.0->          
        -- info-VERCTRL: -
        SYNTAX        Xldv20S1nS3nEberThreshold
        ACCESS        read-write
        STATUS        mandatory
        DESCRIPTION
             " The threshold for the higher-order path excessive bit error check. "
        ::= { xldv20Stm1NePPTPEntry 7 }

     xldv20S1nMsEberThreshold OBJECT-TYPE
        -- info-VALUE:   exp10E3(1), exp10E4(2), exp10E5(3), noSupervision(255)
        -- info-VALUE:   default: exp10E3
        -- info-ROU:     GET db  SET tm 
        -- info-IMPL:    V2.0->          
        -- info-VERCTRL: -
        SYNTAX        Xldv20S1nS3nEberThreshold
        ACCESS        read-write
        STATUS        mandatory
        DESCRIPTION
             " The threshold for the multiplexer section excessive bit error check. "
        ::= { xldv20Stm1NePPTPEntry 8 }

     xldv20S1nRsEberThreshold OBJECT-TYPE
        -- info-VALUE:   exp10E3(1), exp10E4(2), exp10E5(3), noSupervision(255)
        -- info-VALUE:   default: exp10E3
        -- info-ROU:     GET db  SET tm 
        -- info-IMPL:    V2.0->          
        -- info-VERCTRL: -
        SYNTAX        Xldv20S1nS3nEberThreshold
        ACCESS        read-write
        STATUS        mandatory
        DESCRIPTION
             " The threshold for the repeater section excessive bit error check. "
        ::= { xldv20Stm1NePPTPEntry 9 }

     xldv20S1nSDThreshold OBJECT-TYPE
        -- info-VALUE:   exp10E5(3), exp10E6(4), exp10E7(5), exp10E8(6), exp10E9(7),
        -- info-VALUE:   noSupervision(255)
        -- info-VALUE:   default: exp10E5
        -- info-ROU:     GET db  SET tm 
        -- info-IMPL:    V2.0->          
        -- info-VERCTRL: -
        SYNTAX        Xldv20S1nS3nSDThreshold
        ACCESS        read-write
        STATUS        mandatory
        DESCRIPTION
             " The threshold for the signal degration check. "
        ::= { xldv20Stm1NePPTPEntry 10 }

     xldv20S1nRDIAISOnEber OBJECT-TYPE
        -- info-VALUE:   enabled(1) (default), disabled(2)
        -- info-ROU:     GET db  SET tm 
        -- info-IMPL:    V2.0->          
        -- info-VERCTRL: -
        SYNTAX        Xldv20OperState
        ACCESS        read-write
        STATUS        mandatory
        DESCRIPTION
             " Enables (default) / disables the RDI-and VP-AIS generation
               on defect excessive bit ratio. "
        ::= { xldv20Stm1NePPTPEntry 11 }

     xldv20S1nSignalLabelReceive OBJECT-TYPE
        -- info-VALUE:   -2147483648..2147483647
        -- info-ROU:     GET tm 
        -- info-IMPL:    V2.0->          
        -- info-VERCTRL: -
        SYNTAX        Integer32
        ACCESS        read-only
        STATUS        mandatory
        DESCRIPTION
              " Received signal label from the LE. "
        ::= { xldv20Stm1NePPTPEntry 12 }

     xldv20S1nEmptyCellType OBJECT-TYPE
        -- info-VALUE:   idle (default), unassigned
        -- info-ROU:     GET db  SET tm 
        -- info-IMPL:    V2.0->          
        -- info-VERCTRL: -
        SYNTAX        Xldv20EmptyCellType
        ACCESS        read-write
        STATUS        mandatory
        DESCRIPTION
             " The type of empty cells. "
        ::= { xldv20Stm1NePPTPEntry 13 }

        xldv20S1nBandwidthUsage OBJECT-TYPE
        -- info-VALUE:   0..100, Default 0
        -- info-ROU:     GET db
        -- info-IMPL:    V2.0->
        -- info-VERCTRL: -
        SYNTAX        INTEGER (0..100)
        ACCESS        read-only
        STATUS        mandatory
        DESCRIPTION
             " Used bandwidth in percent. "
        ::= { xldv20Stm1NePPTPEntry 14 }

     -- --------------------------------------------------------------
     --                 TLM STS3c near-end PPTP Table
     -- --------------------------------------------------------------
     --
     -- This managed entity represents the extension for the PPTP at
     -- the STS3 near end interface. It includes the additional
     -- attributes to configure the STS3 link.
     --

     xldv20Sts3NePPTPTable OBJECT-TYPE
        -- info-IMPL:    V2.0->          
        SYNTAX        SEQUENCE OF Xldv20Sts3NePPTPEntry
        ACCESS        not-accessible
        STATUS        mandatory
        DESCRIPTION
             " The physical path termination point table for the STS3c IF. "
        --DEFAULT test-function-async     fsnS3nEntryTest
        --DEFAULT next-function-async     fsnS3nEntryNext
        --DEFAULT set-function-async      fsnS3nEntrySet
        --DEFAULT get-function-async      fsnS3nEntryGet
        ::= { xldv20Tlm 10 }

     xldv20Sts3NePPTPEntry OBJECT-TYPE
        -- info-IMPL:    V2.0->          
        SYNTAX        Xldv20Sts3NePPTPEntry
        ACCESS        not-accessible
        STATUS        mandatory
        DESCRIPTION
             " An entry describing a termination point in the PPTP table.
               Notifications : see xldv20IfEntry. "
        INDEX         { xldv20IfIndex }
        ::= { xldv20Sts3NePPTPTable 1 }

     Xldv20Sts3NePPTPEntry ::=
        SEQUENCE { xldv20S3nLineType                 Xldv20LineType,
                   xldv20S3nPathTraceSend            OCTET STRING ( SIZE (0..16) ),
                   xldv20S3nPathTraceSendDefault     Xldv20OperState,
                   xldv20S3nPathTraceExpect          OCTET STRING ( SIZE (0..16) ),
                   xldv20S3nPathTraceTIMDetectionActivate  Xldv20OperState,
                   xldv20S3nPathTraceReceive         OCTET STRING ( SIZE (0..16) ),
                   xldv20S3nPathTraceSync            Xldv20OperState,
                   xldv20S3nPathTraceSendCRCActivate     Xldv20OperState,
                   xldv20S3nPathTraceReceiveCRCActivate  Xldv20OperState,
                   xldv20S3nHpEberThreshold          Xldv20S1nS3nEberThreshold,
                   xldv20S3nMsEberThreshold          Xldv20S1nS3nEberThreshold,
                   xldv20S3nRsEberThreshold          Xldv20S1nS3nEberThreshold,
                   xldv20S3nSDThreshold              Xldv20S1nS3nSDThreshold,
                   xldv20S3nSignalLabelReceive       Integer32,
                   xldv20S3nEmptyCellType            Xldv20EmptyCellType,
                   xldv20S3nBandwidthUsage           INTEGER }

     xldv20S3nLineType OBJECT-TYPE
        -- info-VALUE:   other(1), shortSingleMode(2),
        -- info-VALUE:   mediumSingleMode(3) (default)
        -- info-VALUE:   longSingleMode(4), coax(5), utp(6)
        -- info-ROU:     GET db 
        -- info-IMPL:    V2.0->          
        -- info-VERCTRL: GET db
        -- info-VERCTRL: -
        SYNTAX        Xldv20LineType
        ACCESS        read-only
        STATUS        mandatory
        DESCRIPTION
             " The physical medium of the line used for transmission. "
        ::= { xldv20Sts3NePPTPEntry 1 }

     xldv20S3nPathTraceSend OBJECT-TYPE
        -- info-VALUE:   16 times <= 0x7F
        -- info-VALUE:   (case CRC enabled / Sync-Bit enabled):
        -- info-VALUE:   * 1'st byte: CRC+Sync-Bit +
        -- info-VALUE:     15 times less or equal 0x7F
        -- info-VALUE:     (default: 16 * 0x00)
        -- info-VALUE:   (case CRC enabled / Sync-Bit disabled):
        -- info-VALUE:   * 1'st byte: CRC-no-Sync-Bit +
        -- info-VALUE:     15 times less or equal 0x7F
        -- info-VALUE:     (default: 16 * 0x00)
        -- info-VALUE:   (case CRC disabled / Sync-Bit enabled):
        -- info-VALUE:   * 16 times less or equal 0x7F
        -- info-VALUE:     (default: 16 * 0x00)
        -- info-VALUE:     == value from set-request + Sync-Bit
        -- info-VALUE:   * The first bit of the first byte is set
        -- info-VALUE:   (case CRC disabled / Sync-Bit disabled):
        -- info-VALUE:   * 16 times less or equal 0x7F
        -- info-VALUE:     (default: 16 * 0x00)
        -- info-VALUE:      == value from set-request / no Sync-Bit
        -- info-VALUE:   * The first bit of the first byte is not set
        -- info-ROU:     GET db  SET tm 
        -- info-IMPL:    V2.0->          
        -- info-VERCTRL: GET db  SET asw
        -- info-VERCTRL: -
        SYNTAX        OCTET STRING ( SIZE (0..16) )
        ACCESS        read-write
        STATUS        mandatory
        DESCRIPTION
             " The input signal used for the path trace send functionality. "
        ::= { xldv20Sts3NePPTPEntry 2 }

     xldv20S3nPathTraceSendDefault OBJECT-TYPE
        -- info-VALUE:   enabled(1) (default), disabled(2)
        -- info-ROU:     GET db  SET tm 
        -- info-IMPL:    V2.0->          
        -- info-VERCTRL: -
        SYNTAX        Xldv20OperState
        ACCESS        read-write
        STATUS        mandatory
        DESCRIPTION
             " Enables/disables the path trace send functionality.
               A default path trace value (enabled) or the pattern
               defined in the xldv20S3nPathTraceSend attribute (disabled) will
               be sent. "
        ::= { xldv20Sts3NePPTPEntry 3 }

     xldv20S3nPathTraceExpect OBJECT-TYPE
        -- info-VALUE:   (case received CRC enabled):  
        -- info-VALUE:   * 1'st byte: any value (will be ignored by the DSLAM and generated itself)
        -- info-VALUE:   (case received CRC disabled): * 16 times less or equal 0x7F.
        -- info-VALUE:   + 15 times less or equal 0x7F (default: 16 * 0x00).
        -- info-ROU:     GET db  SET tm 
        -- info-IMPL:    V2.0->          
        -- info-VERCTRL: -
        SYNTAX        OCTET STRING ( SIZE (0..16) )
        ACCESS        read-write
        STATUS        mandatory
        DESCRIPTION
             " The expected result of a path trace operation.
	     This signal will be compared with the
               S3nPathTraceReceive, when the attribute
               S3nPathTraceTIMDetectionActivate is enabled. If the comparison detects
               unequality an alarm notification (TIM) is sent. When CRC is
               activated, only the first 15 bytes are compared. "
        ::= { xldv20Sts3NePPTPEntry 4 }

     xldv20S3nPathTraceTIMDetectionActivate OBJECT-TYPE
        -- info-VALUE:   enabled(1), disabled(2) (default)
        -- info-ROU:     GET db  SET tm 
        -- info-IMPL:    V2.0->          
        -- info-VERCTRL: -
        SYNTAX        Xldv20OperState
        ACCESS        read-write
        STATUS        mandatory
        DESCRIPTION
             " Enables/disables the comparsion of the signals
               S3nPathTraceExpect and S3nPathTraceReceive.  "
        ::= { xldv20Sts3NePPTPEntry 5 }

     xldv20S3nPathTraceReceive OBJECT-TYPE
        -- info-VALUE:   1'st byte: maybe CRC (incl. sync-bit) + 15 times <= 0x7F
        -- info-ROU:     GET tm 
        -- info-IMPL:    V2.0->          
        -- info-VERCTRL: -
        SYNTAX        OCTET STRING ( SIZE (0..16) )
        ACCESS        read-only
        STATUS        mandatory
        DESCRIPTION
             " Received path trace value from the LE. "
        ::= { xldv20Sts3NePPTPEntry 6 }

     xldv20S3nPathTraceSync OBJECT-TYPE
        -- info-VALUE:   enabled(1), disabled(2) (default: without sync-bit)
        -- info-ROU:     GET db  SET tm 
        -- info-IMPL:    V2.0->          
        -- info-VERCTRL: -
        SYNTAX        Xldv20OperState
        ACCESS        read-write
        STATUS        mandatory
        DESCRIPTION
             " Enables/disables the path trace synchronization 
	     (the sync-bit generation for the path trace send attribute). "
        ::= { xldv20Sts3NePPTPEntry 7 }

     xldv20S3nPathTraceSendCRCActivate OBJECT-TYPE
        -- info-VALUE:   enabled(1), disabled(2) (default == DSLAM uses 1'st
        -- info-VALUE:   Byte of MIB-attribute xldv20S3nPathTraceSend )
        -- info-ROU:     GET db  SET tm 
        -- info-IMPL:    V2.0->          
        -- info-VERCTRL: -
        SYNTAX        Xldv20OperState
        ACCESS        read-write
        STATUS        mandatory
        DESCRIPTION
             " Enables/disbales the CRC generation
	     for the path trace send attribute.
	     First Trace Send byte ignored and used for CRC when CRC is enabled. "
        ::= { xldv20Sts3NePPTPEntry 8 }

     xldv20S3nPathTraceReceiveCRCActivate OBJECT-TYPE
        -- info-VALUE:   enabled(1), disabled(2) (default)
        -- info-ROU:     GET db  SET tm 
        -- info-IMPL:    V2.0->          
        -- info-VERCTRL: -
        SYNTAX        Xldv20OperState
        ACCESS        read-write
        STATUS        mandatory
        DESCRIPTION
             " Enables/disables the CRC generation
               for the path trace reveive attribute. "
        ::= { xldv20Sts3NePPTPEntry 9 }

     xldv20S3nHpEberThreshold OBJECT-TYPE
        -- info-VALUE:   exp10E3(1), exp10E4(2), exp10E5(3), noSupervision(255)
        -- info-VALUE:   default: noSupervision
        -- info-ROU:     GET db  SET tm 
        -- info-IMPL:    V2.0->          
        -- info-VERCTRL: -
        SYNTAX        Xldv20S1nS3nEberThreshold
        ACCESS        read-write
        STATUS        mandatory
        DESCRIPTION
             " Threshold for the higher-order path
               excessive bit error check. "
        ::= { xldv20Sts3NePPTPEntry 10 }

     xldv20S3nMsEberThreshold OBJECT-TYPE
        -- info-VALUE:   exp10E3(1), exp10E4(2), exp10E5(3), noSupervision(255)
        -- info-VALUE:   default: noSupervision
        -- info-ROU:     GET db  SET tm
        -- info-IMPL:    V2.0->          
        -- info-VERCTRL: -
        SYNTAX        Xldv20S1nS3nEberThreshold
        ACCESS        read-write
        STATUS        mandatory
        DESCRIPTION
             " Threshold for the multiplexer
               section excessive bit error check. "
        ::= { xldv20Sts3NePPTPEntry 11 }

     xldv20S3nRsEberThreshold OBJECT-TYPE
        -- info-VALUE:   exp10E3(1), exp10E4(2), exp10E5(3), noSupervision(255)
        -- info-VALUE:   default: noSupervision
        -- info-ROU:     GET db  SET tm 
        -- info-IMPL:    V2.0->          
        -- info-VERCTRL: -
        SYNTAX        Xldv20S1nS3nEberThreshold
        ACCESS        read-write
        STATUS        mandatory
        DESCRIPTION
             " Threshold for the repeater section
               excessive bit error check. "
        ::= { xldv20Sts3NePPTPEntry 12 }

     xldv20S3nSDThreshold OBJECT-TYPE
        -- info-VALUE:   exp10E5(1), exp10E6(2), exp10E7(3),exp10E8(2), exp10E9(3),
        -- info-VALUE:   noSupervision(255)
        -- info-VALUE:   default: exp10E5
        -- info-ROU:     GET db  SET tm 
        -- info-IMPL:    V2.0->          
        -- info-VERCTRL: -
        SYNTAX        Xldv20S1nS3nSDThreshold
        ACCESS        read-write
        STATUS        mandatory
        DESCRIPTION
             " Threshold for the signal degration check.  "
        ::= { xldv20Sts3NePPTPEntry 13 }

     xldv20S3nSignalLabelReceive OBJECT-TYPE
        -- info-VALUE:   0 ... 255
        -- info-ROU:     GET tm
        -- info-IMPL:    V2.0->          
        -- info-VERCTRL: -
        SYNTAX        Integer32
        ACCESS        read-only
        STATUS        mandatory
        DESCRIPTION
              " Received signal label value from the LE. "
        ::= { xldv20Sts3NePPTPEntry 14 }

     xldv20S3nEmptyCellType OBJECT-TYPE
        -- info-VALUE:   idle, unassigned (default)
        -- info-ROU:     GET db  SET tm
        -- info-IMPL:    V2.0->          
        -- info-VERCTRL: -
        SYNTAX        Xldv20EmptyCellType
        ACCESS        read-write
        STATUS        mandatory
        DESCRIPTION
             " Type of empty cells. "
        ::= { xldv20Sts3NePPTPEntry 15 }

        xldv20S3nBandwidthUsage OBJECT-TYPE
        -- info-VALUE:   0..100, Default 0
        -- info-ROU:     GET db
        -- info-IMPL:    V2.0->
        -- info-VERCTRL: -
        SYNTAX        INTEGER (0..100)
        ACCESS        read-only
        STATUS        mandatory
        DESCRIPTION
             " Used bandwidth in percent. "
        ::= { xldv20Sts3NePPTPEntry 16 }

     -- --------------------------------------------------------------
     --                 The DS1 transmission subtree (RFC1406)
     -- --------------------------------------------------------------
     -- The DS1 Near End Group consists of
     -- the DS1 Configuration Table
 
     xldv20Dsx1ConfigTable OBJECT-TYPE
        -- info-IMPL:    V2.0->
        SYNTAX  SEQUENCE OF Xldv20Dsx1ConfigEntry
        ACCESS  not-accessible
        STATUS  mandatory
        DESCRIPTION
        "The DS1 Configuration table. "
        --DEFAULT next-function-async     fsnDsxEntryNext
        --DEFAULT get-function-async      fsnDsxEntryGet
        ::= { xldv20Tlm 11 }
 
     xldv20Dsx1ConfigEntry OBJECT-TYPE
        -- info-IMPL:    V2.0->
        SYNTAX  Xldv20Dsx1ConfigEntry
        ACCESS  not-accessible
        STATUS  mandatory
        DESCRIPTION
        "An entry in the DS1 Configuration table (RFC1406) .
        Index is IfIndex of dsx1nePPTP (e1nIma). "
        INDEX   { xldv20IfIndex }
        ::= { xldv20Dsx1ConfigTable 1 }

     Xldv20Dsx1ConfigEntry ::=
         SEQUENCE {
             xldv20Dsx1LineType            INTEGER,
             xldv20Dsx1LineCoding          INTEGER,
             xldv20Dsx1LoopbackConfig      INTEGER,
             xldv20Dsx1SignalMode          INTEGER,
             xldv20Dsx1TransmitClockSource INTEGER,
             xldv20Dsx1Fdl                 INTEGER
         }
 
        xldv20Dsx1LineType OBJECT-TYPE
        -- info-VALUE:   other(1), dsx1ESF(2),
        -- info-VALUE:   dsx1D4(3), dsx1E1(4)
        -- info-VALUE:   dsx1E1-CRC(5) (default), dsx1E1-MF(6),
        -- info-VALUE:   dsx1E1-CRC-MF(7)
        -- info-ROU:     GET db
        -- info-IMPL:    V2.0->
        -- info-VERCTRL: -
        SYNTAX  INTEGER {
                   other(1),
                   dsx1ESF(2),
                   dsx1D4(3),
                   dsx1E1(4),
                   dsx1E1-CRC(5),
                   dsx1E1-MF(6),
                   dsx1E1-CRC-MF(7)
                }
        ACCESS  read-only
        STATUS  mandatory
        DESCRIPTION
           " This variable indicates  the  variety  of  DS1
           Line  implementing  this  circuit.  The type of
           circuit affects the number of bits  per  second
           that  the circuit can reasonably carry, as well
           as the interpretation of the  usage  and  error
           statistics.  The values, in sequence.
 
                dsx1ESF       Extended SuperFrame DS1.
                dsx1D4        AT&T D4 format DS1.
                dsx1E1        CCITT Recommendation G704
                                (Table 4a).
                dsx1E1-CRC    CCITT Recommendation G704
                                (Table 4b).
                dsxE1-MF      G704 (Table 4a) with TS16
                                multiframing enabled.
                dsx1E1-CRC-MF G704 (Table 4b) with TS16.
                                multiframing enabled. "
        ::= { xldv20Dsx1ConfigEntry 1 }

        xldv20Dsx1LineCoding OBJECT-TYPE
        -- info-VALUE:   dsx1JBZS (1), dsx1B8ZS (2),
        -- info-VALUE:   dsx1HDB3 (3) (default), dsx1ZBTSI (4),
        -- info-VALUE:   dsx1AMI (5), other(6)
        -- info-ROU:     GET db
        -- info-IMPL:    V2.0->
        -- info-VERCTRL: -
        SYNTAX  INTEGER {
                    dsx1JBZS (1),
                    dsx1B8ZS (2),
                    dsx1HDB3 (3),
                    dsx1ZBTSI (4),
                    dsx1AMI (5),
                    other(6)
                }
        ACCESS  read-only
        STATUS  mandatory
        DESCRIPTION
           "This variable describes the  variety  of  Zero
           Code  Suppression  used  on  the link, which in
           turn affects a number of its characteristics.
 
           dsx1JBZS refers the Jammed  Bit  Zero  Suppres-
           sion,  in  which  the  AT&T specification of at
           least one pulse every 8 bit periods is literal-
           ly  implemented  by forcing a pulse in bit 8 of
           each channel.  Thus, only seven bits per  chan-
           nel, or 1.344 Mbps, is available for data.
 
           dsx1B8ZS refers to the use of a specified  pat-
           tern  of  normal  bits  and  bipolar violations
           which are used to replace a sequence  of  eight
           zero bits.
 
           ANSI Clear Channels may use dsx1ZBTSI, or  Zero
           Byte Time Slot Interchange.
 
           E1 links, with or without CRC, use dsx1HDB3  or
           dsx1AMI.
 
 
           dsx1AMI refers to a mode wherein no  zero  code
           suppression  is  present  and the line encoding
           does not solve the problem directly.   In  this
           application, the higher layer must provide data
           which meets or exceeds the  pulse  density  re-
           quirements, such as inverting HDLC data. "
       ::= { xldv20Dsx1ConfigEntry 2 }
       
        xldv20Dsx1LoopbackConfig OBJECT-TYPE
        -- info-VALUE:   dsx1OtherLoop(4)
        -- info-ROU:     GET db
        -- info-IMPL:    V2.0->
        -- info-VERCTRL: -
        SYNTAX  INTEGER {
                    dsx1NoLoop(1),
                    dsx1PayloadLoop(2),
                    dsx1LineLoop(3),
                    dsx1OtherLoop(4)
                }
        ACCESS  read-only
        STATUS  mandatory
        DESCRIPTION
        "This variable represents the  loopback  confi-
           guration of the DS1 interface.  Agents support-
           ing read/write access should return badValue in
           response to a requested loopback state that the
           interface does not support.  The values mean:.
 
 
                dsx1NoLoop
                     Not in the loopback state.  A device  that
                     is not capable of performing a loopback on
                     the interface shall always return this  as
                     it's value.
 
                dsx1PayloadLoop
                     The received signal at this  interface  is
                     looped  through  the device. Typically the
                     received signal is  looped  back  for  re-
                     transmission  after  it has passed through
                     the device's framing function.
 
                dsx1LineLoop
                     The received signal at this interface does
                     not  go  through the device (minimum pene-
                     tration) but is looped back out.
 
                dsx1OtherLoop
                     Loopbacks that are not defined here. "
       ::= { xldv20Dsx1ConfigEntry 3 }
 
        xldv20Dsx1SignalMode OBJECT-TYPE
        -- info-VALUE:   none (1)
        -- info-ROU:     GET db
        -- info-IMPL:    V2.0->
        -- info-VERCTRL: -
        SYNTAX  INTEGER {
                    none (1),
                    robbedBit (2),
                    bitOriented (3),
                    messageOriented (4)
                }
        ACCESS  read-only
        STATUS  mandatory
        DESCRIPTION
                " The signal mode.
		
		'none' indicates that no bits are reserved for
                signaling on this channel.
 
                 'robbedBit' indicates that T1 Robbed Bit  Sig-
                naling is in use.
 
                 'bitOriented' indicates that E1 Channel  Asso-
                ciated Signaling is in use.
 
                 'messageOriented' indicates that Common  Chan-
                nel Signaling is in use either on channel 16 of
                an E1 link or channel 24 of a T1. "
        ::= { xldv20Dsx1ConfigEntry 4 }

        xldv20Dsx1TransmitClockSource OBJECT-TYPE
        -- info-VALUE:   localTiming (2),
        -- info-ROU:     GET db
        -- info-IMPL:    V2.0->
        -- info-VERCTRL: -
        SYNTAX  INTEGER {
                    loopTiming (1),
                    localTiming (2),
                    throughTiming (3)
                }
        ACCESS  read-only
        STATUS  mandatory
        DESCRIPTION
           "The source of Transmit Clock.
 
                 'loopTiming' indicates that the recovered  re-
                ceive clock is used as the transmit clock.
 
                 'localTiming' indicates  that  a  local  clock
                source is used.
 
                 'throughTiming' indicates that  recovered  re-
                ceive  clock  from another interface is used as
                the transmit clock. "
       ::= { xldv20Dsx1ConfigEntry 5 }

        xldv20Dsx1Fdl OBJECT-TYPE
        -- info-VALUE:   dsx1Att-54016(4)
        -- info-ROU:     GET db
        -- info-IMPL:    V2.0->
        -- info-VERCTRL: -
        SYNTAX  INTEGER {
                      other(1),
                      dsx1Ansi-T1-403(2),
                      dsx1Att-54016(4),
                      dsx1Fdl-none(8)
                }
        ACCESS  read-only
        STATUS  mandatory
        DESCRIPTION
           "This bitmap describes the use of  the  facili-
           ties data link, and is the sum of the capabili-
           ties:
 
            'other' indicates that a protocol  other  than
           one following is used.
 
            'dsx1Ansi-T1-403' refers to the  FDL  exchange
                recommended by ANSI.
 
            'dsx1Att-54016' refers to ESF FDL exchanges.
 
            'dsx1Fdl-none' indicates that the device  does
           not use the FDL. "
       ::= { xldv20Dsx1ConfigEntry 6 }

     -- --------------------------------------------------------------
     --              TLM SDSL central control subgroup
     -- --------------------------------------------------------------
     --
     -- This managed entity manages the control commands
     -- for the SDSL central link.
     --
 
     xldv20SdcControl OBJECT IDENTIFIER 
        -- info-IMPL:    V2.0->
        -- info-VERCTRL: -
     ::= { xldv20Tlm 12 }
 
     xldv20SdcCtrlControlReq OBJECT-TYPE
        -- info-VALUE:   activateData
        -- info-ROU:     GET db SET tm
        -- info-IMPL:    V2.0->
        -- info-VERCTRL: -
        SYNTAX        Xldv20ControlReq
        ACCESS        read-write
        STATUS        mandatory
        DESCRIPTION
           " To activate a configured set of data (command: activateData).  "
        --DEFAULT test-function-async     fsnSdcCtrlTest
        --DEFAULT next-function-async     fsnSdcCtrlNext
        --DEFAULT set-function-async      fsnSdcCtrlSet
        --DEFAULT get-function-async      fsnSdcCtrlGet
        ::= { xldv20SdcControl 1 }
 
     xldv20SdcCtrlControlStatus OBJECT-TYPE
        -- info-VALUE:   requestIdle(1), requestBusy(2), requestPassed(3)
        -- info-VALUE:   requestFailed(4)
        -- info-ROU:     GET db
        -- info-IMPL:    V2.0->
        -- info-VERCTRL: -
        SYNTAX        Xldv20ControlStatus
        ACCESS        read-only
        STATUS        mandatory
        DESCRIPTION
             " Indicates the status of a control request. "
        --DEFAULT next-function-async     fsnSdcCtrlNext
        --DEFAULT get-function-async      fsnSdcCtrlGet
        ::= { xldv20SdcControl 2 }
 
     xldv20SdcCtrlIfIndex OBJECT-TYPE
        -- info-VALUE:   0..65535
        -- info-ROU:     GET db SET db
        -- info-IMPL:    V2.0->
        -- info-VERCTRL: -
        SYNTAX        Unsigned16
        ACCESS        read-write
        STATUS        mandatory
        DESCRIPTION
             " Index to identify a sdc PPTP. "
        --DEFAULT test-function-async     fsnSdcCtrlTest
        --DEFAULT next-function-async     fsnSdcCtrlNext
        --DEFAULT set-function-async      fsnSdcCtrlSet
        --DEFAULT get-function-async      fsnSdcCtrlGet
        ::= { xldv20SdcControl 3 }
 
     xldv20SdcCtrlRate OBJECT-TYPE
        -- info-VALUE:  kbps160Cps377     (   5 ),
        -- info-VALUE:  kbps192Cps452     (   6 ),
        -- info-VALUE:  kbps208Cps490     (   7 ),
        -- info-VALUE:  kbps256Cps603     (   8 ),
        -- info-VALUE:  kbps288Cps679     (   9 ),
        -- info-VALUE:  kbps320Cps754     (  10 ),
        -- info-VALUE:  kbps352Cps830     (  11 ),
        -- info-VALUE:  kbps384Cps905     (  12 ),
        -- info-VALUE:  kbps400Cps943     (  13 )
        -- info-VALUE:  kbps768Cps1811    (  24 ),
        -- info-VALUE:  kbps784Cps1849    (  25 )
        -- info-VALUE:  kbps1152Cps2716   (  36 ),
        -- info-VALUE:  kbps1168Cps2754   (  37 )
        -- info-VALUE:  kbps1536Cps3622   (  48 ),
        -- info-VALUE:  kbps1552Cps3660   (  49 )
        -- info-VALUE:  kbps1744Cps4113   (  54 ),
        -- info-VALUE:  kbps2320Cps5471   (  72 )
        -- info-ROU:     GET db SET db
        -- info-IMPL:    V2.0->
        -- info-VERCTRL: -
        SYNTAX        Xldv20SdslDataRate
        ACCESS        read-write
        STATUS        mandatory
        DESCRIPTION
             " Desired SDSL data rate. The supported line rates ranges from 
               160 and 2320 Kbit/sec.
	       The cell rate range is between 377 and 5471 cells/sec.
	       Default is 5 ( 160 kbps/377cps). "
        --DEFAULT test-function-async     fsnSdcCtrlTest
        --DEFAULT next-function-async     fsnSdcCtrlNext
        --DEFAULT set-function-async      fsnSdcCtrlSet
        --DEFAULT get-function-async      fsnSdcCtrlGet
        ::= { xldv20SdcControl 4 }
 
     xldv20SdcCtrlXdslServiceType OBJECT-TYPE
        -- info-VALUE:   diamondLaneFraming  ( 1 ) (default)
        -- info-VALUE:   clearChannelFraming ( 2 )
        -- info-VALUE:   ituFraming          ( 3 )
        -- info-ROU:     GET db SET db
        -- info-IMPL:    V2.0->
        -- info-VERCTRL: -
        SYNTAX        Xldv20SdslServiceType
        ACCESS        read-write
        STATUS        mandatory
        DESCRIPTION
             " The service mode for the SDSL line. "
        --DEFAULT test-function-async     fsnSdcCtrlTest
        --DEFAULT next-function-async     fsnSdcCtrlNext
        --DEFAULT set-function-async      fsnSdcCtrlSet
        --DEFAULT get-function-async      fsnSdcCtrlGet
        ::= { xldv20SdcControl 5 }
 
     xldv20SdcCtrlControlReqResult OBJECT-TYPE
        -- info-VALUE:   noRequest, paramFaulty
        -- info-VALUE:   wrongAdminState
        -- info-VALUE:   resourceProblemUpstream, resourceProblemDownstream
        -- info-VALUE:   vpProblemUpstream, vpProblemDownstream
        -- info-VALUE:   bandwidthUpstreamWarning, bandwidthDownstreamWarning
        -- info-VALUE:   mbsUpstreamWarning, mbsDownstreamWarning.
        -- info-VALUE:   requestBusy,setDataFailed
        -- info-VALUE:   aswTimeout, commandFailed, commandSucceeded,
        -- info-VALUE:   wrongXdslServiceType
        -- info-ROU:     GET db
        -- info-IMPL:    V2.0->
        -- info-VERCTRL: -
        SYNTAX        Xldv20ControlReq
        ACCESS        read-only
        STATUS        mandatory
        DESCRIPTION
              " The result of the last user command. "
        --DEFAULT next-function-async     fsnSdcCtrlNext
        --DEFAULT get-function-async      fsnSdcCtrlGet
        ::= { xldv20SdcControl 6 }
 
      xldv20SdcCtrlControlTimeStamp OBJECT-TYPE
         -- info-VALUE:   0..2Giga
         -- info-ROU:     GET db
         -- info-IMPL:    V2.0->
         -- info-VERCTRL: -
         SYNTAX        TimeTicks
         ACCESS        read-only
         STATUS        mandatory
         DESCRIPTION
            " The time stamp of the last command (end of command). "
        --DEFAULT next-function-async     fsnSdcCtrlNext
        --DEFAULT get-function-async      fsnSdcCtrlGet
        ::= { xldv20SdcControl 7 }

     xldv20SdcCtrlMinMarginUp OBJECT-TYPE
        -- info-VALUE:   -127..128 (default 0)
        -- info-ROU:     GET db SET db
        -- info-IMPL:    V2.0->
        -- info-VERCTRL: -
        SYNTAX        INTEGER (-127..128)
        ACCESS        read-write
        STATUS        mandatory
        DESCRIPTION
             " The desired threshold for upstream margin when an alarm
               should be sent (in units of dB). "
        --DEFAULT test-function-async     fsnSdcCtrlTest
        --DEFAULT next-function-async     fsnSdcCtrlNext
        --DEFAULT set-function-async      fsnSdcCtrlSet
        --DEFAULT get-function-async      fsnSdcCtrlGet
        ::= { xldv20SdcControl 8 }

     -- --------------------------------------------------------------
     --                 TLM SDSL central PPTP Table
     -- --------------------------------------------------------------
 
     -- This managed entity represents the extension for the PPTP at
     -- the SDSL central interface. It includes additional attributes to
     -- configure the SDSL link.
     --
 
     xldv20SdcPPTPTable OBJECT-TYPE
        -- info-IMPL:    V2.0->
        -- info-VERCTRL: -
        SYNTAX        SEQUENCE OF Xldv20SdcPPTPEntry
        ACCESS        not-accessible
        STATUS        mandatory
        DESCRIPTION
             " The physical path termination point table for SDSL C. "
        --DEFAULT test-function-async     fsnSdcEntryTest
        --DEFAULT next-function-async     fsnSdcEntryNext
        --DEFAULT get-function-async      fsnSdcEntryGet
        --DEFAULT set-function-async      fsnSdcEntrySet
        ::= { xldv20Tlm 13 }
 
     xldv20SdcPPTPEntry OBJECT-TYPE
        -- info-IMPL:    V2.0->
        -- info-VERCTRL: -
        SYNTAX        Xldv20SdcPPTPEntry
        ACCESS        not-accessible
        STATUS        mandatory
        DESCRIPTION
             " An entry describing a termination point in the PPTP table.
               Notifications : see xldv20IfEntry. "
        INDEX         { xldv20IfIndex }
        ::= { xldv20SdcPPTPTable 1 }
 
     Xldv20SdcPPTPEntry ::=
        SEQUENCE { xldv20SdcRateCfg            Xldv20SdslDataRate,
                   xldv20SdcXdslServiceTypeCfg Xldv20SdslServiceType,
                   xldv20SdcRate               Xldv20SdslDataRateCurrent,
                   xldv20SdcMarginDn           Xldv20AdslMargin,
                   xldv20SdcMarginUp           Xldv20AdslMargin,
                   xldv20SdcAttenuationDn      Xldv20AdslAttenuation,
                   xldv20SdcAttenuationUp      Xldv20AdslAttenuation,
                   xldv20SdcLinkState          Xldv20LinkState,
                   xldv20SdcAISOnLOS           Xldv20OperState,
                   xldv20SdcAISOnACT           Xldv20OperState ,
                   xldv20SdcGuaranteedBandwidthUsage INTEGER,
                   xldv20SdcInitStatus         Xldv20XdslInitStatus,
                   xldv20SdcMinMarginUpCfg           INTEGER,
	           xldv20SdcTransceiverOutputPower Xldv20AdslOutputPower,
	           xldv20SdcXdslServiceType    Xldv20XdslServiceTypeCurrent
                   }
 
     xldv20SdcRateCfg OBJECT-TYPE
        -- info-VALUE:   for values see Xldv20SdcCtrlRate
        -- info-ROU:     GET db
        -- info-IMPL:    V2.0->
        -- info-VERCTRL: -
        SYNTAX        Xldv20SdslDataRate
        ACCESS        read-only
        STATUS        mandatory
        DESCRIPTION
             " The desired data rate.
	     The data rate ranges from 160 to 2320 Kbit/sec.
	     The cell rate ranges between 377 and 5471 cells/sec.
	     Default is 5 ( 160 kbps/377cps). "
        ::= { xldv20SdcPPTPEntry 1 }
 
     xldv20SdcXdslServiceTypeCfg OBJECT-TYPE
        -- info-VALUE:   diamondLaneFraming  ( 1 ) (default)
        -- info-VALUE:   clearChannelFraming ( 2 )
        -- info-VALUE:   ituFraming          ( 3 )
        -- info-ROU:     GET db
        -- info-IMPL:    V2.0->
        -- info-VERCTRL: -
        SYNTAX        Xldv20SdslServiceType
        ACCESS        read-only
        STATUS        mandatory
        DESCRIPTION
             " The configured service mode for SDSL line. "
        ::= { xldv20SdcPPTPEntry 2 }
 
     xldv20SdcRate OBJECT-TYPE
        -- info-VALUE:   for values see Xldv20SdcCtrlRate
        -- info-VALUE:   rateInvalid(32767)
        -- info-ROU:     GET tm
        -- info-IMPL:    V2.0->
        -- info-VERCTRL: -
        SYNTAX        Xldv20SdslDataRateCurrent
        ACCESS        read-only
        STATUS        mandatory
        DESCRIPTION
             " The current downstream data rate.
	     The data rate ranges from 160 to 2320 Kbit/sec.
	     The cell rate ranges between 377 and 5471 cells/sec.
	     Default is 5 ( 160 kbps/377cps). "
        ::= { xldv20SdcPPTPEntry 3 }
 
     xldv20SdcMarginDn OBJECT-TYPE
        -- info-VALUE:   marginNotApplicable (32766)
        -- info-ROU:     GET tm
        -- info-IMPL:    V2.0->
        -- info-VERCTRL: -
        SYNTAX        Xldv20AdslMargin
        ACCESS        read-only
        STATUS        mandatory
        DESCRIPTION
             " Not applicable. GetRequest returns 
               marginNotApplicable . "
        ::= { xldv20SdcPPTPEntry 4 }
 
     xldv20SdcMarginUp OBJECT-TYPE
        -- info-VALUE:   see xldv20AdcMarginDn
        -- info-ROU:     GET tm
        -- info-IMPL:    V2.0->
        -- info-VERCTRL: -
        SYNTAX        Xldv20AdslMargin
        ACCESS        read-only
        STATUS        mandatory
        DESCRIPTION
             " The current upstream margin in units of dB.
               Default is marginInvalid . "
        ::= { xldv20SdcPPTPEntry 5 }
 
     xldv20SdcAttenuationDn OBJECT-TYPE
        -- info-VALUE:   attenuationNotApplicable (32766)
        -- info-ROU:     GET tm
        -- info-IMPL:    V2.0->
        -- info-VERCTRL: -
        SYNTAX        Xldv20AdslAttenuation
        ACCESS        read-only
        STATUS        mandatory
        DESCRIPTION
             " Not applicable. GetRequest returns 
	       attenuationNotApplicable. "
        ::= { xldv20SdcPPTPEntry 6 }
 
     xldv20SdcAttenuationUp OBJECT-TYPE
        -- info-VALUE:   see xldv20AdcAttenuationDn
        -- info-VALUE:   0..255
        -- info-ROU:     GET tm
        -- info-IMPL:    V2.0->
        -- info-VERCTRL: -
        SYNTAX        Xldv20AdslAttenuation
        ACCESS        read-only
        STATUS        mandatory
        DESCRIPTION
             " The current upstream attenuation in steps of 0,5 dB.
               Default is attenuationInvalid. "
        ::= { xldv20SdcPPTPEntry 7 }
 
     xldv20SdcLinkState OBJECT-TYPE
        -- info-VALUE:   unknown,idle,quiet,train,active,
        -- info-VALUE:   download,remoteDownload
        -- info-ROU:     GET tm
        -- info-IMPL:    V2.0->
        -- info-VERCTRL: -
        SYNTAX        Xldv20LinkState
        ACCESS        read-only
        STATUS        mandatory
        DESCRIPTION
             " The link states of the SDSL Central Office Modem. "
        ::= { xldv20SdcPPTPEntry 8 }
 
     xldv20SdcAISOnLOS  OBJECT-TYPE
        -- info-VALUE:   disabled : No VP-AIS generation (default)
        -- info-VALUE:   enabled  :    VP-AIS generation
        -- info-ROU:     GET db SET tm
        -- info-IMPL:    V2.0->
        -- info-VERCTRL: -
        SYNTAX        Xldv20OperState
        ACCESS        read-write
        STATUS        mandatory
        DESCRIPTION
             " The attribute enables or disables the VP-AIS generation
               after defect LOS. "
        ::= { xldv20SdcPPTPEntry 9 }
 
     xldv20SdcAISOnACT  OBJECT-TYPE
        -- info-VALUE:   disabled : No VP-AIS generation (default)
        -- info-VALUE:   enabled  :    VP-AIS generation
        -- info-ROU:     GET db SET tm
        -- info-IMPL:    V2.0->
        -- info-VERCTRL: -
        SYNTAX        Xldv20OperState
        ACCESS        read-write
        STATUS        mandatory
        DESCRIPTION
             " The attribute enables or disables the VP-AIS generation
               after link activation fault. "
        ::= { xldv20SdcPPTPEntry 10 }
 
        xldv20SdcGuaranteedBandwidthUsage OBJECT-TYPE
        -- info-VALUE:   0..100, default 0
        -- info-ROU:     GET db
        -- info-IMPL:    V2.0->
        -- info-VERCTRL: -
        SYNTAX        INTEGER (0..100)
        ACCESS        read-only
        STATUS        mandatory
        DESCRIPTION
             " The guaranteed bandwidth in percent. "
        ::= { xldv20SdcPPTPEntry 11 }
 
     xldv20SdcInitStatus OBJECT-TYPE
        -- info-VALUE:   ntNotPresent(1),communicationFailed(2)
        -- info-VALUE:   fastRetrainProfileError(3)
        -- info-VALUE:   rateParameterConfigurationError(4)
        -- info-VALUE:   serviceTypeAdrRequestRejected(5)
        -- info-VALUE:   serviceTypeAdcRequestRejected(6)
        -- info-VALUE:   configuredRatesOutOfRange(7) (not in g.992.2 range)
        -- info-VALUE:   configuredMinMaxRelationInvalid(8)
        -- info-VALUE:   channelRatesExceedsSystemLimits(9)
        -- info-VALUE:   adaptationCombinationInvalid(10)
        -- info-VALUE:   configuredDualChannelInvalid(11)
        -- info-VALUE:   marginLessThanMinMargin(12)
        -- info-VALUE:   adrNotCapableOfDualLatency(13)
        -- info-VALUE:   reserved1(14) ,reserved2(15)
        -- info-VALUE:   trainingBlockedBySu(16)
        -- info-VALUE:   trainingBlockedByCi(17)
        -- info-VALUE:   ntNotPresentDetectedOnCi(18)
        -- info-VALUE:   gliteModeNotPossibleInPCM(19)
        -- info-VALUE:   alarmsDetected(20)
        -- info-VALUE:   initStatusUnknown(21)
        -- info-VALUE:   noInitError(255)  (default value)
        -- info-ROU:     GET db
        -- info-IMPL:    V2.0->
        -- info-VERCTRL: -
        SYNTAX        Xldv20XdslInitStatus
        ACCESS        read-only
        STATUS        mandatory
        DESCRIPTION
             " The initialization status field of an SDSL line.
               Describes the initalization error in case of
               an activation problem on an SDSL line . "
        ::= { xldv20SdcPPTPEntry 12 }

     xldv20SdcMinMarginUpCfg OBJECT-TYPE
        -- info-VALUE:   -127..128 (default 0)
        -- info-ROU:     GET db SET db
        -- info-IMPL:    V2.0->
        -- info-VERCTRL: -
        SYNTAX        INTEGER (-127..128)
        ACCESS        read-only
        STATUS        mandatory
        DESCRIPTION
             " The desired threshold for upstream margin when an alarm
               should be sent (in units of dB). "
        ::= { xldv20SdcPPTPEntry 13 }

        xldv20SdcTransceiverOutputPower OBJECT-TYPE
        -- info-VALUE:   dBm-31     (-31),
        -- info-VALUE:   dBm-30     (-30),
        -- info-VALUE:   dBm-29     (-29),
        -- info-VALUE:   dBm-28     (-28),
        -- info-VALUE:   dBm-27     (-27),
        -- info-VALUE:   dBm-26     (-26),
        -- info-VALUE:   dBm-25     (-25),
        -- info-VALUE:   dBm-24     (-24),
        -- info-VALUE:   dBm-23     (-23),
        -- info-VALUE:   dBm-22     (-22),
        -- info-VALUE:   dBm-21     (-21),
        -- info-VALUE:   dBm-20     (-20),
        -- info-VALUE:   dBm-19     (-19),
        -- info-VALUE:   dBm-18     (-18),
        -- info-VALUE:   dBm-17     (-17),
        -- info-VALUE:   dBm-16     (-16),
        -- info-VALUE:   dBm-15     (-15),
        -- info-VALUE:   dBm-14     (-14),
        -- info-VALUE:   dBm-13     (-13),
        -- info-VALUE:   dBm-12     (-12),
        -- info-VALUE:   dBm-11     (-11),
        -- info-VALUE:   dBm-10     (-10),
        -- info-VALUE:   dBm-9      (-9),
        -- info-VALUE:   dBm-8      (-8),
        -- info-VALUE:   dBm-7      (-7),
        -- info-VALUE:   dBm-6      (-6),
        -- info-VALUE:   dBm-5      (-5),
        -- info-VALUE:   dBm-4      (-4),
        -- info-VALUE:   dBm-3      (-3),
        -- info-VALUE:   dBm-2      (-2),
        -- info-VALUE:   dBm-1      (-1),
        -- info-VALUE:   dBm0       (0 ),
        -- info-VALUE:   dBm1       (1 ),
        -- info-VALUE:   dBm2       (2 ),
        -- info-VALUE:   dBm3       (3 ),
        -- info-VALUE:   dBm4       (4 ),
        -- info-VALUE:   dBm5       (5 ),
        -- info-VALUE:   dBm6       (6 ),
        -- info-VALUE:   dBm7       (7 ),
        -- info-VALUE:   dBm8       (8 ),
        -- info-VALUE:   dBm9       (9 ),
        -- info-VALUE:   dBm10      (10),
        -- info-VALUE:   dBm11      (11),
        -- info-VALUE:   dBm12      (12),
        -- info-VALUE:   dBm13      (13),
        -- info-VALUE:   dBm14      (14),
        -- info-VALUE:   dBm15      (15),
        -- info-VALUE:   dBm16      (16),
        -- info-VALUE:   dBm17      (17),
        -- info-VALUE:   dBm18      (18),
        -- info-VALUE:   dBm19      (19),
        -- info-VALUE:   dBm20      (20),
        -- info-VALUE:   dBm21      (21),
        -- info-VALUE:   dBm22      (22),
        -- info-VALUE:   dBm23      (23),
        -- info-VALUE:   dBm24      (24),
        -- info-VALUE:   dBm25      (25),
        -- info-VALUE:   dBm26      (26),
        -- info-VALUE:   dBm27      (27),
        -- info-VALUE:   dBm28      (28),
        -- info-VALUE:   dBm29      (29),
        -- info-VALUE:   dBm30      (30),
        -- info-VALUE:   dBm31      (31),
        -- info-VALUE:   dBm32      (32),
        -- info-VALUE:   outputPowerInvalid (32767)
        -- info-ROU:     GET tm
        -- info-IMPL:    V2.0->
        -- info-VERCTRL: -
        SYNTAX        Xldv20AdslOutputPower
        ACCESS        read-only
        STATUS        mandatory
        DESCRIPTION
             " The SDSL tranceiver output power. Granularity 1.0 dBm.
	     Default value is outputPowerInvalid. "
        ::= { xldv20SdcPPTPEntry 14 }

	xldv20SdcXdslServiceType OBJECT-TYPE
        -- info-VALUE:   gDotDmtMode  (1),
        -- info-VALUE:   ansiT1Dot413 (2),
        -- info-VALUE:   gDotLiteMode (3)
        -- info-VALUE:   serviceTypeUnknown (10)
        -- info-ROU:     GET tm
        -- info-IMPL:    V2.0->
        -- info-VERCTRL: -
        SYNTAX        Xldv20XdslServiceTypeCurrent
        ACCESS        read-only
        STATUS        mandatory
        DESCRIPTION
             " The current service type resulting from the configured service
	     type. It depends on the actual hardware.
	     Configuring gDotHsMode can result either in gDotLiteMode or gDotDmtMode.
	     gDotAll can result in gDotDmtMode, ansiT1dot413 or gDotLiteMode.
	     Default value is serviceTypeUnknown (10). "
        ::= { xldv20SdcPPTPEntry 15 }

     -- --------------------------------------------------------------
     --                 The IMA subtree (IMA-MIB)
     -- --------------------------------------------------------------
     --

     xldv20ImaMibObjects OBJECT IDENTIFIER 
        -- info-IMPL:    V2.0->
        -- info-VERCTRL: -
     ::= { xldv20TlmIma 1 }


     xldv20ImaGroupNumber OBJECT-TYPE
        -- info-VALUE:   currently 1
        -- info-ROU:     GET db
        -- info-IMPL:    V2.0->
        SYNTAX      INTEGER (0..2147483647)
        ACCESS      read-only
        STATUS      mandatory
        DESCRIPTION
            " The number of IMA groups configured on this system. "
        --DEFAULT next-function-async     fsnImnNext
        --DEFAULT get-function-async      fsnImnGet
      ::= { xldv20ImaMibObjects 1 }

         
     -- --------------------------------------------------------------
     --                 The IMA Control subtree (IMA-MIB)
     -- --------------------------------------------------------------
     --
     -- The IMA Control subtree consists of the number of IMA groups and 
     -- all attributes used for user commands on IMA MIB objects.
     --

     xldv20ImaControl OBJECT IDENTIFIER 
        -- info-IMPL:    V2.0->          
        -- info-VERCTRL: -
     ::= { xldv20ImaMibObjects 2 }

     xldv20ImaControlReq OBJECT-TYPE
        -- info-VALUE:   imaSetMinNumTxLinks
        -- info-ROU:     GET db SET tm  
        -- info-IMPL:    V2.0->
        -- info-VERCTRL: -
        SYNTAX        Xldv20ControlReq
        ACCESS        read-write
        STATUS        mandatory
        DESCRIPTION
              " The IMA control request object for IMA MIB objects. "
        --DEFAULT test-function-async     fsnImcTest
        --DEFAULT next-function-async     fsnImcNext
        --DEFAULT set-function-async      fsnImcSet
        --DEFAULT get-function-async      fsnImcGet
      ::= { xldv20ImaControl 1 }

     xldv20ImaControlMinNumLinks OBJECT-TYPE
        -- info-VALUE:   1..8
        -- info-ROU:     GET db  SET db
        -- info-IMPL:    V2.0->          
        -- info-VERCTRL: -
        SYNTAX        INTEGER (1..8)
        ACCESS        read-write
        STATUS        mandatory
        DESCRIPTION
             " The required minimum number of IMA links . "
        --DEFAULT test-function-async     fsnImcTest
        --DEFAULT next-function-async     fsnImcNext
        --DEFAULT set-function-async      fsnImcSet
        --DEFAULT get-function-async      fsnImcGet
        ::= { xldv20ImaControl 2 }

     xldv20ImaControlGroupIndex OBJECT-TYPE
        -- info-VALUE:   1 only!
        -- info-ROU:     GET db  SET db
        -- info-IMPL:    V2.0->          
        -- info-VERCTRL: -
        SYNTAX        INTEGER (1..2147483647)
        ACCESS        read-write
        STATUS        mandatory
        DESCRIPTION
             " The index of the IMA group. "
        --DEFAULT test-function-async     fsnImcTest
        --DEFAULT next-function-async     fsnImcNext
        --DEFAULT set-function-async      fsnImcSet
        --DEFAULT get-function-async      fsnImcGet
        ::= { xldv20ImaControl 3 }

     xldv20ImaControlReqResult OBJECT-TYPE
        -- info-VALUE:   imaSetMinNumTxLinks(command)
        -- info-VALUE:   reject reasons :
        -- info-VALUE:   imaBwError(CAC)
        -- info-VALUE:   imaSetMinNumOk      (9202)
        -- info-VALUE:   imaSetMinNumFailed  (9203)
        -- info-VALUE:   paramFaulty, commExecStarted
        -- info-VALUE:   requestBusy,setDataFailed,
        -- info-VALUE:   aswTimeout,
        -- info-ROU:     GET db
        -- info-IMPL:    V2.0->
        -- info-VERCTRL: -
        SYNTAX        Xldv20ControlReq
        ACCESS        read-only
        STATUS        mandatory
        DESCRIPTION
              " The result of the last user command. "
        --DEFAULT next-function-async     fsnImcNext
        --DEFAULT get-function-async      fsnImcGet
        ::= { xldv20ImaControl 4 }

      xldv20ImaControlTimeStamp OBJECT-TYPE
         -- info-VALUE:   0..2Giga
         -- info-ROU:     GET db
         -- info-IMPL:    V2.0->
         -- info-VERCTRL: -
         SYNTAX        TimeTicks
         ACCESS        read-only
         STATUS        mandatory
         DESCRIPTION
            " The time stamp of the last command (end of command). "
        --DEFAULT next-function-async     fsnImcNext
        --DEFAULT get-function-async      fsnImcGet
        ::= { xldv20ImaControl 5 }

      xldv20ImaControlStatus OBJECT-TYPE
         -- info-VALUE:   requestIdle(1), requestBusy(2), requestPassed(3)
         -- info-VALUE:   requestFailed(4)
         -- info-ROU:     GET db
         -- info-IMPL:    V2.0->
         -- info-VERCTRL: -
         SYNTAX        Xldv20ControlStatus
         ACCESS        read-only
         STATUS        mandatory
         DESCRIPTION
            " The status of the control request. "
        --DEFAULT next-function-async     fsnImcNext
        --DEFAULT get-function-async      fsnImcGet
        ::= { xldv20ImaControl 6 }

     xldv20ImaControlTimer OBJECT-TYPE
        -- info-VALUE:   0..2147483647
        -- info-ROU:     GET db
        -- info-IMPL:    V2.0->
        -- info-VERCTRL: -
        SYNTAX        Unsigned32
        ACCESS        read-only
        STATUS        mandatory
        DESCRIPTION
              " The maximum wait time for the manager when changing
                the minimum number of active links. As the LUIMA
                performs a restart the command cannot be processed 
                immediately ( value commExecStarted in GetResponse
                for xldv20ImaControlReq ). "
        --DEFAULT next-function-async     fsnImcNext
        --DEFAULT get-function-async      fsnImcGet
        ::= { xldv20ImaControl 7 }

     -- --------------------------------------------------------------
     --                 The IMA group subtree (IMA-MIB)
     -- --------------------------------------------------------------
     --
     -- The IMA Group subtree consists of the table of IMA groups.
     -- Each entry in the table of IMA groups contains
     -- information (configuration and status) specific to each group.
     --
     xldv20ImaGroupTable OBJECT-TYPE
        -- info-IMPL:    V2.0->
        SYNTAX        SEQUENCE OF Xldv20ImaGroupEntry
        ACCESS        not-accessible
        STATUS        mandatory
        DESCRIPTION
             " The IMA Group configuration Table.
	      Index is ImaGroupIndex. "
        --DEFAULT test-function-async     fsnImgEntryTest
        --DEFAULT next-function-async     fsnImgEntryNext
        --DEFAULT set-function-async      fsnImgEntrySet
        --DEFAULT get-function-async      fsnImgEntryGet
        ::= { xldv20ImaMibObjects 3 }
 
     xldv20ImaGroupEntry OBJECT-TYPE
        -- info-IMPL:    V2.0->
        SYNTAX      Xldv20ImaGroupEntry
        ACCESS      not-accessible
        STATUS      mandatory
        DESCRIPTION
            " An entry in the IMA Group table. "
        INDEX       { xldv20ImaGroupIndex }
      ::= { xldv20ImaGroupTable 1 }
 
      Xldv20ImaGroupEntry ::= SEQUENCE {
        xldv20ImaGroupIndex               INTEGER (1..2147483647),
        xldv20ImaGroupRowStatus           Xldv20RowStatus,
        xldv20ImaGroupIfIndex             Unsigned16,
        xldv20ImaGroupNeState             Xldv20ImaGroupState,
        xldv20ImaGroupFeState             Xldv20ImaGroupState,
        xldv20ImaGroupFailureStatus       Xldv20ImaGroupFailureStatus,
        xldv20ImaGroupSymmetry            Xldv20ImaGroupSymmetry,
        xldv20ImaGroupMinNumTxLinks       INTEGER (1..8),
        xldv20ImaGroupMinNumRxLinks       INTEGER (1..8),
        xldv20ImaGroupNeTxClkMode         Xldv20ImaGroupTxClkMode,
        xldv20ImaGroupFeTxClkMode         Xldv20ImaGroupTxClkMode,
        xldv20ImaGroupTxTimingRefLink     Unsigned16,
        xldv20ImaGroupRxTimingRefLink     Unsigned16,
        xldv20ImaGroupLastChange          TimeTicks,
        xldv20ImaGroupTxImaId             INTEGER (0..255),
        xldv20ImaGroupRxImaId             INTEGER (0..255),
        xldv20ImaGroupTxFrameLength       Xldv20ImaFrameLength,
        xldv20ImaGroupRxFrameLength       Xldv20ImaFrameLength,
        xldv20ImaGroupDiffDelayMax        MilliSeconds,
        xldv20ImaGroupLeastDelayLink      Unsigned16,
        xldv20ImaGroupDiffDelayMaxObs     MilliSeconds,
        xldv20ImaGroupAlphaValue          INTEGER (1..2),
        xldv20ImaGroupBetaValue           INTEGER (1..5),
        xldv20ImaGroupGammaValue          INTEGER (1..5),
        xldv20ImaGroupRunningSecs         Gauge32,
        xldv20ImaGroupUnavailSecs         Counter32,
        xldv20ImaGroupNeNumFailures       Counter32,
        xldv20ImaGroupFeNumFailures       Counter32,
        xldv20ImaGroupNumTxCfgLinks       Gauge32,
        xldv20ImaGroupNumRxCfgLinks       Gauge32,
        xldv20ImaGroupNumTxActLinks       Gauge32,
        xldv20ImaGroupNumRxActLinks       Gauge32,
        xldv20ImaGroupBandwidthUsage      INTEGER 
        }

      xldv20ImaGroupIndex OBJECT-TYPE
        -- info-VALUE:   currently 1
        -- info-ROU:     GET db
        -- info-IMPL:    V2.0->
        -- info-VERCTRL: -
        SYNTAX      INTEGER (1..2147483647)
        ACCESS      read-only
        STATUS      mandatory
        DESCRIPTION
             " The index of the table identifying an IMA Group. "
        ::= { xldv20ImaGroupEntry 1 }
 
      xldv20ImaGroupRowStatus OBJECT-TYPE
        -- info-VALUE:   created
        -- info-ROU:     GET db
        -- info-IMPL:    V2.0->
        -- info-VERCTRL: 
        SYNTAX      Xldv20RowStatus
        ACCESS      read-only
        STATUS      mandatory
        DESCRIPTION
             " The imaGroupRowStatus object allows create, change, and delete
        operations on imaGroupTable entries.
        In the first version only one IMA group for the LU-IMA will be
        created during start-up. "
        ::= { xldv20ImaGroupEntry 2 }
 
        xldv20ImaGroupIfIndex OBJECT-TYPE
        -- info-VALUE:   
        -- info-ROU:     GET db
        -- info-IMPL:    V2.0->
        -- info-VERCTRL: -
        SYNTAX      Unsigned16
        ACCESS      read-only
        STATUS      mandatory
        DESCRIPTION
             " The IfIndex of the IMA group. "
        ::= { xldv20ImaGroupEntry 3 }
 
        xldv20ImaGroupNeState OBJECT-TYPE
        -- info-VALUE:   notConfigured(1), startUp(2),
        -- info-VALUE:   startUpAck(3),
        -- info-VALUE:   configAbortUnsupported(4),
        -- info-VALUE:   configAbortIncompatibleSymmetry(5),
        -- info-VALUE:   configAbortOther(6),
        -- info-VALUE:   insufficientLinks(7),
        -- info-VALUE:   blocked(8),
        -- info-VALUE:   operational(9),
        -- info-VALUE:   configAbortUnsupportedImaVersion(10)
        -- info-ROU:     GET tm
        -- info-IMPL:    V2.0->
        -- info-VERCTRL: -
        SYNTAX      Xldv20ImaGroupState
        ACCESS      read-only
        STATUS      mandatory
        DESCRIPTION
             " The current operational state of the near-end IMA Group State
        Machine. "
        ::= { xldv20ImaGroupEntry 4 }

        xldv20ImaGroupFeState OBJECT-TYPE
        -- info-VALUE:   notConfigured(1), startUp(2),
        -- info-VALUE:   startUpAck(3),
        -- info-VALUE:   configAbortUnsupported(4),
        -- info-VALUE:   configAbortIncompatibleSymmetry(5),
        -- info-VALUE:   configAbortOther(6),
        -- info-VALUE:   insufficientLinks(7),
        -- info-VALUE:   blocked(8),
        -- info-VALUE:   operational(9),
        -- info-VALUE:   configAbortUnsupportedImaVersion(10)
        -- info-ROU:     GET tm
        -- info-IMPL:    V2.0->
        -- info-VERCTRL: -
        SYNTAX     Xldv20ImaGroupState
        ACCESS      read-only
        STATUS      mandatory
        DESCRIPTION
             " The current operational state of the far-end IMA Group State
        Machine. "
        ::= { xldv20ImaGroupEntry 5 }

        xldv20ImaGroupFailureStatus OBJECT-TYPE
        -- info-VALUE:   noFailure(1),
        -- info-VALUE:   startUpNe(2),
        -- info-VALUE:   startUpFe(3), invalidValueNe(4),
        -- info-VALUE:   invalidValueFe(5), failedAssymetricNe(6),
        -- info-VALUE:   failedAssymetricFe(7),
        -- info-VALUE:   insufficientLinksNe(8),
        -- info-VALUE:   insufficientLinksFe(9),
        -- info-VALUE:   blockedNe(10), blockedFe(11),
        -- info-VALUE:   otherFailure(12),
        -- info-VALUE:   invalidImaVersionNe(13),
        -- info-VALUE:   invalidImaVersionFe(14) }
        -- info-ROU:     GET tm
        -- info-IMPL:    V2.0->
        -- info-VERCTRL: -
        SYNTAX      Xldv20ImaGroupFailureStatus
        ACCESS      read-only
        STATUS      mandatory
        DESCRIPTION
            " The current failure status of the IMA group (the reason why
        the GTSM is in the down state). "
        ::= { xldv20ImaGroupEntry 6 }

        xldv20ImaGroupSymmetry  OBJECT-TYPE
        -- info-VALUE:   symmetricOperation (1) only!
        -- info-ROU:     GET tm
        -- info-IMPL:    V2.0->
        -- info-VERCTRL: -
        SYNTAX      Xldv20ImaGroupSymmetry
        ACCESS      read-only
        STATUS      mandatory
        DESCRIPTION
            " Symmetry of the IMA group. "
        ::= { xldv20ImaGroupEntry 7 }

        xldv20ImaGroupMinNumTxLinks OBJECT-TYPE
        -- info-VALUE:   1..8 (default 1)
        -- info-VALUE:   Note : Tx = Rx !
        -- info-ROU:     GET db
        -- info-IMPL:    V2.0->
        -- info-VERCTRL: -
        SYNTAX      INTEGER (1..8)
        ACCESS      read-only
        STATUS      mandatory
        DESCRIPTION
            " Minimum number of transmit links required to be Active for
        the IMA group to be in the Operational state. "
        ::= { xldv20ImaGroupEntry 8 }

        xldv20ImaGroupMinNumRxLinks OBJECT-TYPE
        -- info-VALUE:   1..8 (Rx = Tx !)
        -- info-ROU:     GET db
        -- info-IMPL:    V2.0->
        -- info-VERCTRL: -
        SYNTAX      INTEGER (1..8)
        ACCESS      read-only
        STATUS      mandatory
        DESCRIPTION
            "  Minimum number of receive links required to be Active for
        the IMA group to be in the Operational state. "
        ::= { xldv20ImaGroupEntry 9 }

        xldv20ImaGroupNeTxClkMode OBJECT-TYPE
        -- info-VALUE:   ctc(1) only!
        -- info-ROU:     GET db
        -- info-IMPL:    V2.0->
        -- info-VERCTRL: -
        SYNTAX      Xldv20ImaGroupTxClkMode
        ACCESS      read-only
        STATUS      mandatory
        DESCRIPTION
             " Transmit clocking mode used by the near-end IMA group. "
        ::= { xldv20ImaGroupEntry 10 }

        xldv20ImaGroupFeTxClkMode OBJECT-TYPE
        -- info-VALUE:   ctc(1) only!
        -- info-ROU:     GET tm
        -- info-IMPL:    V2.0->
        -- info-VERCTRL: -
        SYNTAX      Xldv20ImaGroupTxClkMode
        ACCESS      read-only
        STATUS      mandatory
        DESCRIPTION
             " Transmit clocking mode used by the far-end IMA group. "
        ::= { xldv20ImaGroupEntry 11 }

        xldv20ImaGroupTxTimingRefLink OBJECT-TYPE
        -- info-VALUE:   
        -- info-ROU:     GET tm
        -- info-IMPL:    V2.0->
        -- info-VERCTRL: -
        SYNTAX      Unsigned16
        ACCESS      read-only
        STATUS      mandatory
        DESCRIPTION
            " The ifIndex of the transmit timing reference link to be
        used by the near-end for IMA data cell clock recovery from
        the ATM layer.  "
        ::= { xldv20ImaGroupEntry 12 }

        xldv20ImaGroupRxTimingRefLink OBJECT-TYPE
        -- info-VALUE:   
        -- info-ROU:     GET tm
        -- info-IMPL:    V2.0->
        -- info-VERCTRL: -
        SYNTAX      Unsigned16
        ACCESS      read-only
        STATUS      mandatory
        DESCRIPTION
            " The ifIndex of the transmit timing reference link to be
        used by the near-end for IMA data cell clock recovery toward
        the ATM layer. "
        ::= { xldv20ImaGroupEntry 13 }

        xldv20ImaGroupLastChange OBJECT-TYPE
        -- info-VALUE:   
        -- info-ROU:     GET tm
        -- info-IMPL:    V2.0->
        -- info-VERCTRL: -
        SYNTAX      TimeTicks
        ACCESS      read-only
        STATUS      mandatory
        DESCRIPTION
            " The time stamp the IMA group last changed operational
        state ( value of imaGroupNeState changed). "
        ::= { xldv20ImaGroupEntry 14 }

        xldv20ImaGroupTxImaId OBJECT-TYPE
        -- info-VALUE:   default : 0xAA
        -- info-ROU:     GET db SET tm
        -- info-IMPL:    V2.0->
        -- info-VERCTRL: -
        SYNTAX      INTEGER (0..255)
        ACCESS      read-write
        STATUS      mandatory
        DESCRIPTION
            " The IMA ID currently in use by the near-end IMA function. "
        ::= { xldv20ImaGroupEntry 15 }

        xldv20ImaGroupRxImaId OBJECT-TYPE
        -- info-VALUE:   
        -- info-ROU:     GET tm
        -- info-IMPL:    V2.0->
        -- info-VERCTRL: -
        SYNTAX      INTEGER (0..255)
        ACCESS      read-only
        STATUS      mandatory
        DESCRIPTION
            " The IMA ID currently in use by the far-end IMA function. "
        ::= { xldv20ImaGroupEntry 16 }

        xldv20ImaGroupTxFrameLength OBJECT-TYPE
        -- info-VALUE:   m128 only!
        -- info-ROU:     GET db
        -- info-IMPL:    V2.0->
        -- info-VERCTRL: -
        SYNTAX      Xldv20ImaFrameLength
        ACCESS      read-only
        STATUS      mandatory
        DESCRIPTION
            " The frame length to be used by the IMA group in the transmit
        direction.  "
        ::= { xldv20ImaGroupEntry 17 }

        xldv20ImaGroupRxFrameLength OBJECT-TYPE
        -- info-VALUE:   -
        -- info-ROU:     GET tm
        -- info-IMPL:    V2.0->
        -- info-VERCTRL: -
        SYNTAX      Xldv20ImaFrameLength
        ACCESS      read-only
        STATUS      mandatory
        DESCRIPTION
            " Value of IMA frame length as received from remote IMA function. "
        ::= { xldv20ImaGroupEntry 18 }

        xldv20ImaGroupDiffDelayMax OBJECT-TYPE
        -- info-VALUE:   only : 25 supported!
        -- info-ROU:     GET db
        -- info-IMPL:    V2.0->
        -- info-VERCTRL: -
        SYNTAX      MilliSeconds
        ACCESS      read-only
        STATUS      mandatory
        DESCRIPTION
            " The maximum number of milliseconds of differential delay among
        the links that will be tolerated on this interface. "
        ::= { xldv20ImaGroupEntry 19 }

        xldv20ImaGroupLeastDelayLink OBJECT-TYPE
        -- info-VALUE:   
        -- info-ROU:     GET tm
        -- info-IMPL:    V2.0->
        -- info-VERCTRL: -
        SYNTAX      Unsigned16
        ACCESS      read-only
        STATUS      mandatory
        DESCRIPTION
            " The ifIndex of the link configured in the IMA group which has
        the smallest link propagation delay. This value has meaning only
        if at least one link has been configured in the IMA group. "
        ::= { xldv20ImaGroupEntry 20 }

        xldv20ImaGroupDiffDelayMaxObs OBJECT-TYPE
        -- info-VALUE:   
        -- info-ROU:     GET tm
        -- info-IMPL:    V2.0->
        -- info-VERCTRL: -
        SYNTAX      MilliSeconds 
        ACCESS      read-only
        STATUS      mandatory
        DESCRIPTION
            " The latest maximum differential delay observed (in milliseconds)
        between the links having the least and most link propagation delay,
        among the receive links that are currently configured in the IMA
        group. "
        ::= { xldv20ImaGroupEntry 21 }

        xldv20ImaGroupAlphaValue OBJECT-TYPE
        -- info-VALUE:   2 only!
        -- info-ROU:     GET tm
        -- info-IMPL:    V2.0->
        -- info-VERCTRL: -
        SYNTAX      INTEGER (1..2)
        ACCESS      read-only
        STATUS      mandatory
        DESCRIPTION
            " This indicates the 'alpha' value used to specify the number
        of consecutive invalid ICP cells to be detected before moving
        to the IMA Hunt state from the IMA Sync state. "
        ::= { xldv20ImaGroupEntry 22 }

        xldv20ImaGroupBetaValue OBJECT-TYPE
        -- info-VALUE:   2 only!
        -- info-ROU:     GET tm
        -- info-IMPL:    V2.0->
        -- info-VERCTRL: -
        SYNTAX      INTEGER (1..5)
        ACCESS      read-only
        STATUS      mandatory
        DESCRIPTION
            " This indicates the 'beta' value used to specify the number
        of consecutive errored ICP cells to be detected before moving
        to the IMA Hunt state from the IMA Sync state. "
        ::= { xldv20ImaGroupEntry 23 }

        xldv20ImaGroupGammaValue OBJECT-TYPE
        -- info-VALUE:   1 only!
        -- info-ROU:     GET tm
        -- info-IMPL:    V2.0->
        -- info-VERCTRL: -
        SYNTAX      INTEGER (1..5)
        ACCESS      read-only
        STATUS      mandatory
        DESCRIPTION
            " This indicates the 'gamma' value used to specify the number
        of consecutive valid ICP cells to be detected before moving
        to the IMA Sync state from the IMA PreSync state. "
        ::= { xldv20ImaGroupEntry 24 }

        xldv20ImaGroupRunningSecs  OBJECT-TYPE
        -- info-VALUE:   
        -- info-ROU:     GET tm
        -- info-IMPL:    V2.0->
        -- info-VERCTRL: -
        SYNTAX      Gauge32
        ACCESS      read-only
        STATUS      mandatory
        DESCRIPTION
            " The amount of time (in seconds) since this IMA group has
        been in the operation (up or down). "
        ::= { xldv20ImaGroupEntry 25 }

        xldv20ImaGroupUnavailSecs OBJECT-TYPE
        -- info-VALUE:   
        -- info-ROU:     GET tm
        -- info-IMPL:    V2.0->
        -- info-VERCTRL: -
        SYNTAX      Counter32
        ACCESS      read-only
        STATUS      mandatory
        DESCRIPTION
            " Count of one second intervals where the IMA Group Traffic
        State Machine is Down. "
        ::= { xldv20ImaGroupEntry 26 }

        xldv20ImaGroupNeNumFailures OBJECT-TYPE
        -- info-VALUE:   
        -- info-ROU:     GET tm
        -- info-IMPL:    V2.0->
        -- info-VERCTRL: -
        SYNTAX      Counter32
        ACCESS      read-only
        STATUS      mandatory
        DESCRIPTION
            " The number of times a near-end group failure (Config-Aborted,
        Insufficient-Links) has been reported since power-up or reboot. "
        ::= { xldv20ImaGroupEntry 27 }

        xldv20ImaGroupFeNumFailures OBJECT-TYPE
        -- info-VALUE:   
        -- info-ROU:     GET tm
        -- info-IMPL:    V2.0->
        -- info-VERCTRL: -
        SYNTAX      Counter32
        ACCESS      read-only
        STATUS      mandatory
        DESCRIPTION
            " The number of times a far-end group failure (Config-Aborted,
        Insufficient-Links) has been reported since power-up or reboot. "
        ::= { xldv20ImaGroupEntry 28 }

        xldv20ImaGroupNumTxCfgLinks OBJECT-TYPE
        -- info-VALUE:   
        -- info-ROU:     GET tm
        -- info-IMPL:    V2.0->
        -- info-VERCTRL: -
        SYNTAX      Gauge32
        ACCESS      read-only
        STATUS      mandatory
        DESCRIPTION
            " The number of links that are configured to transmit in this IMA
        group. This attribute overwrites the value of the
        imaGroupNumRxActLinks attribute when the IMA group is configured
        in the Symmetrical Configuration group symmetry mode. "
        ::= { xldv20ImaGroupEntry 29 }

        xldv20ImaGroupNumRxCfgLinks OBJECT-TYPE
        -- info-VALUE:   
        -- info-ROU:     GET tm
        -- info-IMPL:    V2.0->
        -- info-VERCTRL: -
        SYNTAX      Gauge32
        ACCESS      read-only
        STATUS      mandatory
        DESCRIPTION
            " The number of links that are configured to receive in this IMA
        group. This attribute is overwritten by the value of the
        imaGroupNumTxActLinks attribute when the IMA group is configured
        in the Symmetrical Configuration group symmetry mode. "
        ::= { xldv20ImaGroupEntry 30 }

        xldv20ImaGroupNumTxActLinks OBJECT-TYPE
        -- info-VALUE:   
        -- info-ROU:     GET tm
        -- info-IMPL:    V2.0->
        -- info-VERCTRL: -
        SYNTAX      Gauge32
        ACCESS      read-only
        STATUS      mandatory
        DESCRIPTION
            " The number of links which are configured to transmit and are
        currently Active in this IMA group. "
        ::= { xldv20ImaGroupEntry 31 }

        xldv20ImaGroupNumRxActLinks OBJECT-TYPE
        -- info-VALUE:   
        -- info-ROU:     GET tm
        -- info-IMPL:    V2.0->
        -- info-VERCTRL: -
        SYNTAX      Gauge32
        ACCESS      read-only
        STATUS      mandatory
        DESCRIPTION
            " The number of links which are configured to receive and are
        currently Active in this IMA group. "
        ::= { xldv20ImaGroupEntry 32 }

        xldv20ImaGroupBandwidthUsage OBJECT-TYPE
        -- info-VALUE:   0..100, Default 0
        -- info-ROU:     GET db
        -- info-IMPL:    V2.0->
        -- info-VERCTRL: -
        SYNTAX        INTEGER (0..100)
        ACCESS        read-only
        STATUS        mandatory
        DESCRIPTION
                 "  Used bandwidth in percent. "
        ::= { xldv20ImaGroupEntry 33 }

     -- --------------------------------------------------------------
     --                 The IMA group mapping table
     -- --------------------------------------------------------------

     -- The IMA Group Mapping Table subtree consists of a table of mappings
     -- from 'ifIndex' values of IMA groups to their 'imaGroupIndex' values.
     -- This table allows the Unit Management to perform easy look-ups (no
     -- searches and sorts).
     --
     -- Note that the Group Index is different from the ifIndex.
     --

     xldv20ImaGroupMappingTable OBJECT-TYPE
        -- info-IMPL:    V2.0->
        SYNTAX        SEQUENCE OF Xldv20ImaGroupMappingEntry
        ACCESS        not-accessible
        STATUS        mandatory
        DESCRIPTION
            " A table mapping the 'ifIndex' values of 'imaGroupIfIndex'
        to the 'imaGroupIndex' values of the corresponding IMA group.
	Index is ifIndex of IMA group (atmIma).  "
        --DEFAULT next-function-async     fsnImmEntryNext
        --DEFAULT get-function-async      fsnImmEntryGet
        ::= { xldv20ImaMibObjects 4 }
 
     xldv20ImaGroupMappingEntry OBJECT-TYPE
        -- info-IMPL:    V2.0->
        SYNTAX        Xldv20ImaGroupMappingEntry
        ACCESS        not-accessible
        STATUS        mandatory
        DESCRIPTION
            " An entry in the IMA Group Mapping table. "
        INDEX       { xldv20IfIndex }
        ::= { xldv20ImaGroupMappingTable 1 }

     Xldv20ImaGroupMappingEntry ::= SEQUENCE {
      xldv20ImaGroupMappingIndex    Unsigned32 }

     xldv20ImaGroupMappingIndex OBJECT-TYPE
        -- info-VALUE:   currentrly 1 only
        -- info-ROU:     GET db
        -- info-IMPL:    V2.0->
        -- info-VERCTRL: -
        SYNTAX      Unsigned32
        ACCESS      read-only
        STATUS      mandatory
        DESCRIPTION
            " The imaGroupIndex of the IMA Group which implements the
        specified interface. "
      ::= { xldv20ImaGroupMappingEntry 1 }

     -- --------------------------------------------------------------
     --                 The IMA link subtree
     -- --------------------------------------------------------------
     --
     -- The IMA Link subtree consists of a table of IMA links.  Each entry
     -- in the table contains status information about a link which is part
     -- of an IMA group, and also contains a configuration object to select
     -- to which IMA group the link belongs.
     --
 
     xldv20ImaLinkTable OBJECT-TYPE
        -- info-IMPL:    V2.0->
        SYNTAX        SEQUENCE OF Xldv20ImaLinkEntry
        ACCESS        not-accessible
        STATUS        mandatory
        DESCRIPTION
                " The IMA group Link Status and Configuration table. "
        --DEFAULT test-function-async     fsnImlEntryTest
        --DEFAULT next-function-async     fsnImlEntryNext
        --DEFAULT set-function-async      fsnImlEntrySet
        --DEFAULT get-function-async      fsnImlEntryGet
        ::= { xldv20ImaMibObjects 5 }
 
      xldv20ImaLinkEntry OBJECT-TYPE
        SYNTAX        Xldv20ImaLinkEntry
        ACCESS        not-accessible
        STATUS        mandatory
        DESCRIPTION
                " An entry in the IMA Group Link table.
	    Index is IfIndex of dsx1nePPTP (e1nIma). "
        INDEX       { xldv20IfIndex }
        ::= { xldv20ImaLinkTable 1 }

      Xldv20ImaLinkEntry ::= SEQUENCE {
        xldv20ImaLinkRowStatus            Xldv20RowStatus,
        xldv20ImaLinkGroupIndex           Integer32,
        xldv20ImaLinkNeTxState            Xldv20ImaLinkState,
        xldv20ImaLinkNeRxState            Xldv20ImaLinkState,
        xldv20ImaLinkFeTxState            Xldv20ImaLinkState,
        xldv20ImaLinkFeRxState            Xldv20ImaLinkState,
        xldv20ImaLinkNeRxFailureStatus    Xldv20ImaLinkFailureStatus,
        xldv20ImaLinkFeRxFailureStatus    Xldv20ImaLinkFailureStatus,
        xldv20ImaLinkTxLid                INTEGER (0..7),
        xldv20ImaLinkRxLid                INTEGER (0..7),
        xldv20ImaLinkImaViolations        Counter32,
        xldv20ImaLinkOifAnomalies         Counter32,
        xldv20ImaLinkNeSevErroredSecs     Counter32,
        xldv20ImaLinkFeSevErroredSecs     Counter32,
        xldv20ImaLinkNeUnavailSecs        Counter32,
        xldv20ImaLinkFeUnavailSecs        Counter32,
        xldv20ImaLinkNeTxUnusableSecs     Counter32,
        xldv20ImaLinkNeRxUnusableSecs     Counter32,
        xldv20ImaLinkFeTxUnusableSecs     Counter32,
        xldv20ImaLinkFeRxUnusableSecs     Counter32,
        xldv20ImaLinkNeTxNumFailures      Counter32,
        xldv20ImaLinkNeRxNumFailures      Counter32,
        xldv20ImaLinkFeTxNumFailures      Counter32,
        xldv20ImaLinkFeRxNumFailures      Counter32,
        xldv20ImaLinkTxStuffs             Counter32,
        xldv20ImaLinkRxStuffs             Counter32
        }
 
      xldv20ImaLinkRowStatus OBJECT-TYPE
        -- info-VALUE:   created
        -- info-ROU:     GET db
        -- info-IMPL:    V2.0->
        -- info-VERCTRL: 
        SYNTAX      Xldv20RowStatus
        ACCESS      read-only
        STATUS      mandatory
        DESCRIPTION
            " The imaLinkRowStatus object allows create, change, and delete
            operations on imaLinkTable entries.
            In the first version the IMA  links for the LU-IMA will be
            created during start-up. "
      ::= { xldv20ImaLinkEntry 1 }

      xldv20ImaLinkGroupIndex OBJECT-TYPE
        -- info-VALUE:   currently 1 only
        -- info-ROU:     GET db
        -- info-IMPL:    V2.0->
        -- info-VERCTRL: 
        SYNTAX      Integer32
        ACCESS      read-only
        STATUS      mandatory
      DESCRIPTION
        " The value which identifies the IMA group (imaGroupIndex)
        of which this link is a member. "
      ::= { xldv20ImaLinkEntry 2 }
 
      xldv20ImaLinkNeTxState OBJECT-TYPE
        -- info-VALUE:   notInGroup(1), unusableNoGivenReason(2),
        -- info-VALUE:   unusableFault(3), unusableMisconnected(4),
        -- info-VALUE:   unusableInhibited(5), unusableFailed(6),
        -- info-VALUE:   usable(7), active(8) }
        -- info-ROU:     GET tm
        -- info-IMPL:    V2.0->
        -- info-VERCTRL: -
        SYNTAX      Xldv20ImaLinkState
        ACCESS      read-only
        STATUS      mandatory
        DESCRIPTION
            " The current state of the near-end transmit link. "
      ::= { xldv20ImaLinkEntry 3 }
 
      xldv20ImaLinkNeRxState OBJECT-TYPE
        -- info-VALUE:   notInGroup(1), unusableNoGivenReason(2),
        -- info-VALUE:   unusableFault(3), unusableMisconnected(4),
        -- info-VALUE:   unusableInhibited(5), unusableFailed(6),
        -- info-VALUE:   usable(7), active(8) }
        -- info-ROU:     GET tm
        -- info-IMPL:    V2.0->
        -- info-VERCTRL: -
        SYNTAX      Xldv20ImaLinkState
        ACCESS      read-only
        STATUS      mandatory
        DESCRIPTION
            " The current state of the near-end receive link. "
      ::= { xldv20ImaLinkEntry 4 }
 
      xldv20ImaLinkFeTxState OBJECT-TYPE
        -- info-VALUE:   notInGroup(1), unusableNoGivenReason(2),
        -- info-VALUE:   unusableFault(3), unusableMisconnected(4),
        -- info-VALUE:   unusableInhibited(5), unusableFailed(6),
        -- info-VALUE:   usable(7), active(8) }
        -- info-ROU:     GET tm
        -- info-IMPL:    V2.0->
        -- info-VERCTRL: -
        SYNTAX      Xldv20ImaLinkState
        ACCESS      read-only
        STATUS      mandatory
        DESCRIPTION
            " The current state of the far-end transmit link as reported
        via ICP cells. "
      ::= { xldv20ImaLinkEntry 5 }
 
      xldv20ImaLinkFeRxState OBJECT-TYPE
        -- info-VALUE:   notInGroup(1), unusableNoGivenReason(2),
        -- info-VALUE:   unusableFault(3), unusableMisconnected(4),
        -- info-VALUE:   unusableInhibited(5), unusableFailed(6),
        -- info-VALUE:   usable(7), active(8) }
        -- info-ROU:     GET tm
        -- info-IMPL:    V2.0->
        -- info-VERCTRL: -
        SYNTAX      Xldv20ImaLinkState
        ACCESS      read-only
        STATUS      mandatory
        DESCRIPTION
            " The current state of the far-end receive link as reported
        via ICP cells. "
      ::= { xldv20ImaLinkEntry 6 }
 
      xldv20ImaLinkNeRxFailureStatus OBJECT-TYPE
        -- info-VALUE:   noFailure(1), imaLinkFailure(2),
        -- info-VALUE:   lifFailure(3), lodsFailure(4),
        -- info-VALUE:   misConnected(5), blocked(6),
        -- info-VALUE:   fault(7),
        -- info-VALUE:   farEndTxLinkUnusable(8),
        -- info-VALUE:   farEndRxLinkUnusable(9)
        -- info-ROU:     GET tm
        -- info-IMPL:    V2.0->
        -- info-VERCTRL: -
        SYNTAX      Xldv20ImaLinkFailureStatus
        ACCESS      read-only
        STATUS      mandatory
        DESCRIPTION
            " The current link failure status of the near-end receive link as reported
        via ICP cells. "
      ::= { xldv20ImaLinkEntry 7 }
 
      xldv20ImaLinkFeRxFailureStatus OBJECT-TYPE
        -- info-VALUE:   noFailure(1), imaLinkFailure(2),
        -- info-VALUE:   lifFailure(3), lodsFailure(4),
        -- info-VALUE:   misConnected(5), blocked(6),
        -- info-VALUE:   fault(7),
        -- info-VALUE:   farEndTxLinkUnusable(8),
        -- info-VALUE:   farEndRxLinkUnusable(9)
        -- info-ROU:     GET tm
        -- info-IMPL:    V2.0->
        -- info-VERCTRL: -
        SYNTAX      Xldv20ImaLinkFailureStatus
        ACCESS      read-only
        STATUS      mandatory
        DESCRIPTION
            " The current link failure status of the far-end receive link as reported
        via ICP cells. "
      ::= { xldv20ImaLinkEntry 8 }
 
      xldv20ImaLinkTxLid OBJECT-TYPE
        -- info-VALUE:  
        -- info-ROU:     GET tm
        -- info-IMPL:    V2.0->
        -- info-VERCTRL: -
        SYNTAX      INTEGER (0..7)
        ACCESS      read-only
        STATUS      mandatory
        DESCRIPTION
            " The outgoing LID used currently on the link by the local end.
        This value has meaning only if the link belongs to an IMA group. "
      ::= { xldv20ImaLinkEntry 9 }

      xldv20ImaLinkRxLid OBJECT-TYPE
        -- info-VALUE:  
        -- info-ROU:     GET tm
        -- info-IMPL:    V2.0->
        -- info-VERCTRL: -
        SYNTAX      INTEGER (0..7)
        ACCESS      read-only
        STATUS      mandatory
        DESCRIPTION
            " The outgoing LID used currently on the link by the remote end.
        This value has meaning only if the link belongs to an IMA group. "
      ::= { xldv20ImaLinkEntry 10 }

      xldv20ImaLinkImaViolations OBJECT-TYPE
        -- info-VALUE: 
        -- info-ROU:     GET tm
        -- info-IMPL:    V2.0->
        -- info-VERCTRL: -
        SYNTAX      Counter32
        ACCESS      read-only
        STATUS      mandatory
        DESCRIPTION
            " ICP violations: count of errored, invalid or missing ICP cells,
        except during SES-IMA or UAS-IMA conditions. "
      ::= { xldv20ImaLinkEntry 11 }

      xldv20ImaLinkOifAnomalies OBJECT-TYPE
        -- info-VALUE: 
        -- info-ROU:     GET tm
        -- info-IMPL:    V2.0->
        -- info-VERCTRL: -
        SYNTAX      Counter32
        ACCESS      read-only
        STATUS      mandatory
        DESCRIPTION
            " The number of OIF anomalies, except during SES-IMA or UAS-IMA
        conditions, at the near-end.  This is an optional attribute. "
      ::= { xldv20ImaLinkEntry 12 }

      xldv20ImaLinkNeSevErroredSecs OBJECT-TYPE
        -- info-VALUE: 
        -- info-ROU:     GET tm
        -- info-IMPL:    V2.0->
        -- info-VERCTRL: -
        SYNTAX      Counter32
        ACCESS      read-only
        STATUS      mandatory
        DESCRIPTION
            "  Count of one second intervals containing >= 30% of the ICP cells
        counted as IV-IMAs, or one or more link defects (e.g., LOS, OOF/LOF,
        AIS, or LCD), LIF defects, or LODS defects, except during UAS-IMA
        condition. "
      ::= { xldv20ImaLinkEntry 13 }

      xldv20ImaLinkFeSevErroredSecs OBJECT-TYPE
        -- info-VALUE: 
        -- info-ROU:     GET tm
        -- info-IMPL:    V2.0->
        -- info-VERCTRL: -
        SYNTAX      Counter32
        ACCESS      read-only
        STATUS      mandatory
        DESCRIPTION
            " Count of one second intervals containing one or more RDI-IMA
        defects, except during UAS-IMA-FE condition. "
      ::= { xldv20ImaLinkEntry 14 }

      xldv20ImaLinkNeUnavailSecs OBJECT-TYPE
        -- info-VALUE:  
        -- info-VALUE: 
        -- info-ROU:     GET tm
        -- info-IMPL:    V2.0->
        -- info-VERCTRL: -
        SYNTAX      Counter32
        ACCESS      read-only
        STATUS      mandatory
        DESCRIPTION
            " Count of unavailable seconds at near-end: unavailability begins
        at the onset of 10 contiguous SES-IMA and ends at the onset
        of 10 contiguous seconds with no SES-IMA. "
      ::= { xldv20ImaLinkEntry 15 }

      xldv20ImaLinkFeUnavailSecs OBJECT-TYPE
        -- info-VALUE:  
        -- info-VALUE: 
        -- info-ROU:     GET tm
        -- info-IMPL:    V2.0->
        -- info-VERCTRL: -
        SYNTAX      Counter32
        ACCESS      read-only
        STATUS      mandatory
        DESCRIPTION
            " Count of unavailable seconds at near-end: unavailability begins
        at the onset of 10 contiguous SES-IMA-FE and ends at the onset
        of 10 contiguous seconds with no SES-IMA-FE. "
      ::= { xldv20ImaLinkEntry 16 }

      xldv20ImaLinkNeTxUnusableSecs OBJECT-TYPE
        -- info-VALUE:  
        -- info-VALUE: 
        -- info-ROU:     GET tm
        -- info-IMPL:    V2.0->
        -- info-VERCTRL: -
        SYNTAX      Counter32
        ACCESS      read-only
        STATUS      mandatory
        DESCRIPTION
            " Tx Unusable seconds: count of Tx Unusable seconds at the near-end
        Tx LSM. "
      ::= { xldv20ImaLinkEntry 17 }

      xldv20ImaLinkNeRxUnusableSecs OBJECT-TYPE
        -- info-VALUE:  
        -- info-VALUE: 
        -- info-ROU:     GET tm
        -- info-IMPL:    V2.0->
        -- info-VERCTRL: -
        SYNTAX      Counter32
        ACCESS      read-only
        STATUS      mandatory
        DESCRIPTION
            "  Rx Unusable seconds: count of Rx Unusable seconds at the near-end
        Rx LSM. "
      ::= { xldv20ImaLinkEntry 18 }

      xldv20ImaLinkFeTxUnusableSecs OBJECT-TYPE
        -- info-VALUE:  
        -- info-VALUE: 
        -- info-ROU:     GET tm
        -- info-IMPL:    V2.0->
        -- info-VERCTRL: -
        SYNTAX      Counter32
        ACCESS      read-only
        STATUS      mandatory
        DESCRIPTION
            " Tx Unusable seconds: count of Tx Unusable seconds at the far-end
        Tx LSM. "
      ::= { xldv20ImaLinkEntry 19 }

      xldv20ImaLinkFeRxUnusableSecs OBJECT-TYPE
        -- info-VALUE:  
        -- info-VALUE: 
        -- info-ROU:     GET tm
        -- info-IMPL:    V2.0->
        -- info-VERCTRL: -
        SYNTAX      Counter32
        ACCESS      read-only
        STATUS      mandatory
        DESCRIPTION
            " Rx Unusable seconds: count of Rx Unusable seconds at the far-end
        Rx LSM. "
      ::= { xldv20ImaLinkEntry 20 }

      xldv20ImaLinkNeTxNumFailures OBJECT-TYPE
        -- info-VALUE:  
        -- info-VALUE: 
        -- info-ROU:     GET tm
        -- info-IMPL:    V2.0->
        -- info-VERCTRL: -
        SYNTAX      Counter32
        ACCESS      read-only
        STATUS      mandatory
        DESCRIPTION
            " The number of times a near-end transmit failure alarm condition
        has been entered on this link (i.e., some form of implementation
        specific transmit fault). "
      ::= { xldv20ImaLinkEntry 21 }

      xldv20ImaLinkNeRxNumFailures OBJECT-TYPE
        -- info-VALUE:  
        -- info-VALUE: 
        -- info-ROU:     GET tm
        -- info-IMPL:    V2.0->
        -- info-VERCTRL: -
        SYNTAX      Counter32
        ACCESS      read-only
        STATUS      mandatory
        DESCRIPTION
            " The number of times a near-end receive failure alarm condition
        has been entered on this link (i.e., LIF, LODS,
        RFI-IMA, Mis-Connected or some form of implementation specific receive
        fault). "
      ::= { xldv20ImaLinkEntry 22 }

      xldv20ImaLinkFeTxNumFailures OBJECT-TYPE
        -- info-VALUE:  
        -- info-VALUE: 
        -- info-ROU:     GET tm
        -- info-IMPL:    V2.0->
        -- info-VERCTRL: -
        SYNTAX      Counter32
        ACCESS      read-only
        STATUS      mandatory
        DESCRIPTION
            " The number of times a far-end transmit failure alarm condition
        has been entered on this link (i.e., Tx-Unusable-FE).  This is an
        optional attribute. "
      ::= { xldv20ImaLinkEntry 23 }

      xldv20ImaLinkFeRxNumFailures OBJECT-TYPE
        -- info-VALUE:  
        -- info-VALUE: 
        -- info-ROU:     GET tm
        -- info-IMPL:    V2.0->
        -- info-VERCTRL: -
        SYNTAX      Counter32
        ACCESS      read-only
        STATUS      mandatory
        DESCRIPTION
            " The number of times a far-end receive failure alarm condition
        has been entered on this link (i.e., Rx-Unusable-FE).  This is an
        optional attribute. "
      ::= { xldv20ImaLinkEntry 24 }

      xldv20ImaLinkTxStuffs OBJECT-TYPE
        -- info-VALUE:  
        -- info-VALUE: 
        -- info-ROU:     GET tm
        -- info-IMPL:    V2.0->
        -- info-VERCTRL: -
        SYNTAX      Counter32
        ACCESS      read-only
        STATUS      mandatory
        DESCRIPTION
            " Count of stuff events inserted in the transmit direction.
        This is an optional attribute. "
      ::= { xldv20ImaLinkEntry 25 }

      xldv20ImaLinkRxStuffs OBJECT-TYPE
        -- info-VALUE:  
        -- info-VALUE: 
        -- info-ROU:     GET tm
        -- info-IMPL:    V2.0->
        -- info-VERCTRL: -
        SYNTAX      Counter32
        ACCESS      read-only
        STATUS      mandatory
        DESCRIPTION
            " Count of stuff events inserted in the receive direction.
        This is an optional attribute. "
      ::= { xldv20ImaLinkEntry 26 }



     -- --------------------------------------------------------------
     --                 Subtree for T L M  O A M  functions
     --                 Table of Loop location Points (at TCA) 
     -- --------------------------------------------------------------

     xldv20LoopBackPointTable  OBJECT-TYPE
        -- info-IMPL:    V2.0->
        SYNTAX        SEQUENCE OF Xldv20LbpEntry
        ACCESS        not-accessible
        STATUS        mandatory
        DESCRIPTION
             " The loop back point table"
        --DEFAULT test-function-async     fsnLbpEntryTest
        --DEFAULT next-function-async     fsnLbpEntryNext
        --DEFAULT set-function-async      fsnLbpEntrySet
        --DEFAULT get-function-async      fsnLbpEntryGet
        ::= { xldv20TlmOam 1 }
 
     xldv20LbpEntry   OBJECT-TYPE
        -- info-IMPL:    V2.0->
        SYNTAX        Xldv20LbpEntry
        ACCESS        not-accessible
        STATUS        mandatory
        DESCRIPTION
             " An entry in the loop back point table.
               The entry holds parameters of loop back points
               (as the loop location ID for loop back points or
               the loop mode).
               Loopback points are either the TCA at the LU* or SU
               or the IMA group at the LUIMA (within the DSLAM),
               or the TCA of adrPPTP at the NTAD.
               Notifications : see xldv20IfEntry. "
        INDEX         { xldv20IfIndex }
        ::= { xldv20LoopBackPointTable 1 }
 
     Xldv20LbpEntry ::=
        SEQUENCE { xldv20LbpLoopLocId   OCTET STRING,
                   xldv20LbpLoopMode    Xldv20LoopMode
                   }

     xldv20LbpLoopLocId   OBJECT-TYPE
        -- info-VALUE:   default: 16 times FF
        -- info-VALUE:   hexadecimal at TMN-OS
        -- info-ROU:     GET tm  SET tm
        -- info-IMPL:    V2.0->
        -- info-VERCTRL: -
        SYNTAX        OCTET STRING ( SIZE (0..16) )
        ACCESS        read-write
        STATUS        mandatory
        DESCRIPTION
             " A unique number known by the crafts person specifying
              the location where the OAM loopback cell shall be
              looped back.
              Loopback point is either the TCA at the LU* or SU (within the DSLAM)
              or the TCA of adrPPTP at NTAD.
              NOTE : Due to the functionality of ASPEN at SU the loop location ID
              only of port 1 is configurable. The IDs for port2-16 are calculated
              from this value by the ASPEN. TMN will store these values to the
              corresponding  table entries . "
        ::= {xldv20LbpEntry 1 }
 
 
     xldv20LbpLoopMode   OBJECT-TYPE
        -- info-VALUE:   forward(default), loopAndForward
        -- info-ROU:     GET tm  SET tm
        -- info-IMPL:    V2.0->
        -- info-VERCTRL: -
        SYNTAX        Xldv20LoopMode
        ACCESS        read-write
        STATUS        mandatory
        DESCRIPTION
             " This attribute selects for connecting points
             whether the received loopback cell shall be
             forwarded or forwarded and looped back . "
        ::= {xldv20LbpEntry 2 }

     -- --------------------------------------------------------------
     --                 TLM Physical Loop Test subgroup
     -- --------------------------------------------------------------

     xldv20PhyLoopTest OBJECT IDENTIFIER 
        -- info-IMPL:    V2.0->          
        -- info-VERCTRL: -
     ::= { xldv20TlmOam 2 }

     -- This group handles the TMN control request for starting a service
     -- interrupting physical layer loop diagnosis.
     --

     xldv20PltIfIndex OBJECT-TYPE
        -- info-VALUE:   0..65535
        -- info-ROU:     GET db  SET db 
        -- info-IMPL:    V2.0->          
        -- info-VERCTRL: -
        SYNTAX        Unsigned16
        ACCESS        read-write
        STATUS        mandatory
        DESCRIPTION
             " This attribute labels the location of the physical loopback. It
               can be the ifIndex of a PPTP at LI25, LU, SU . "
        --DEFAULT test-function-async     fsnPltTest
        --DEFAULT next-function-async     fsnPltNext
        --DEFAULT set-function-async      fsnPltSet
        --DEFAULT get-function-async      fsnPltGet
        ::= { xldv20PhyLoopTest 1 }

     xldv20PltControlReq OBJECT-TYPE
        -- info-VALUE:   noRequest
        -- info-VALUE:   loopDiagRequest
        -- info-ROU:     GET db  SET tm 
        -- info-IMPL:    V2.0->          
        -- info-VERCTRL: -
        SYNTAX        Xldv20ControlReq
        ACCESS        read-write
        STATUS        mandatory
        DESCRIPTION
             " The received command to start an OAM cell loopback test
               (loopDiagRequest).
               Notifications : 
                 xldv20TrPltTestResult . "
        --DEFAULT test-function-async     fsnPltTest
        --DEFAULT next-function-async     fsnPltNext
        --DEFAULT set-function-async      fsnPltSet
        --DEFAULT get-function-async      fsnPltGet
        ::= { xldv20PhyLoopTest 2 }

     xldv20PltControlStatus OBJECT-TYPE
        -- info-VALUE:   requestIdle(1), requestBusy(2), requestPassed(3)
        -- info-VALUE:   requestFailed(4)
        -- info-ROU:     GET db
        -- info-IMPL:    V2.0->          
        -- info-VERCTRL: -
        SYNTAX        Xldv20ControlStatus
        ACCESS        read-only
        STATUS        mandatory
        DESCRIPTION
             " The status of the control request. "
        --DEFAULT next-function-async     fsnPltNext
        --DEFAULT get-function-async      fsnPltGet
        ::= { xldv20PhyLoopTest 3 }

     xldv20PltControlTimer OBJECT-TYPE
        -- info-VALUE:   0..2147483647
        -- info-ROU:     GET db
        -- info-IMPL:    V2.0->          
        -- info-VERCTRL: -
        SYNTAX        Unsigned32
        ACCESS        read-only
        STATUS        mandatory
        DESCRIPTION
             " This is the maximum duration of a physical loop diagnosis.
               It is required by the SNMP manager to detect the end of a
               physical loop diagnosis in case of the response
               'xldv20TrPltTestResult' was not received in time. "
        --DEFAULT next-function-async     fsnPltNext
        --DEFAULT get-function-async      fsnPltGet
        ::= { xldv20PhyLoopTest 4 }

     xldv20PltControlReqResult OBJECT-TYPE
        -- info-VALUE:   noRequest, commExecStarted, paramFaulty 
        -- info-VALUE:   loopDiagRequest, loopTestBusy ,loopTestReject 
        -- info-VALUE:   requestBusy,setDataFailed, commandFailed
        -- info-VALUE:   aswTimeout, commandFailed, commandSucceeded
        -- info-ROU:     GET db
        -- info-IMPL:    V2.0->          
        -- info-VERCTRL: -
        SYNTAX        Xldv20ControlReq
        ACCESS        read-only
        STATUS        mandatory
        DESCRIPTION
              " The result of the last user command. "
        --DEFAULT next-function-async     fsnPltNext
        --DEFAULT get-function-async      fsnPltGet
        ::= { xldv20PhyLoopTest 5 }

      xldv20PltControlTimeStamp OBJECT-TYPE
         -- info-VALUE:   0..2Giga
         -- info-ROU:     GET db
         -- info-IMPL:    V2.0->
         -- info-VERCTRL: -
         SYNTAX        TimeTicks
         ACCESS        read-only
         STATUS        mandatory
         DESCRIPTION
            " The time stamp of the last command (end of command). "
        --DEFAULT next-function-async     fsnPltNext
        --DEFAULT get-function-async      fsnPltGet
        ::= { xldv20PhyLoopTest 6 }

     -- --------------------------------------------------------------
     --                  TLM ATM Loop Test subgroup
     -- --------------------------------------------------------------

     xldv20AtmLoopTest OBJECT IDENTIFIER 
        -- info-IMPL:    V2.0->          
        -- info-VERCTRL: -
     ::= { xldv20TlmOam 3 }

     -- This subgroup is used to handle the TMN attribute control request
     -- for starting a non service interrupting OAM cell loopback test.
     --

     xldv20AltIfIndex OBJECT-TYPE
        -- info-VALUE:   0..65535
        -- info-ROU:     GET db  SET db
        -- info-IMPL:    V2.0->          
        -- info-VERCTRL: -
        SYNTAX        Unsigned16
        ACCESS        read-write
        STATUS        mandatory
        DESCRIPTION
             " The TLM interface where OAM cells are inserted.
               It can be the 'IfIndex' of a PPTP at a LU or SU. "
        --DEFAULT test-function-async     fsnAltTest
        --DEFAULT next-function-async     fsnAltNext
        --DEFAULT set-function-async      fsnAltSet
        --DEFAULT get-function-async      fsnAltGet
        ::= { xldv20AtmLoopTest 1 }

     xldv20AltVpi OBJECT-TYPE
        -- info-VALUE:   0..4095
        -- info-ROU:     GET db  SET db
        -- info-IMPL:    V2.0->          
        -- info-VERCTRL: -
        SYNTAX        INTEGER (0..4095)
        ACCESS        read-write
        STATUS        mandatory
        DESCRIPTION
             " Identifies the VPI which shall be tested. It is VPINni 
               when test in LE direction or it is VPIUni when test in
               NT direction. "
        --DEFAULT test-function-async     fsnAltTest
        --DEFAULT next-function-async     fsnAltNext
        --DEFAULT set-function-async      fsnAltSet
        --DEFAULT get-function-async      fsnAltGet
        ::= { xldv20AtmLoopTest 2 }

     xldv20AltLoopLocId OBJECT-TYPE
        -- info-VALUE:   Length 16 bytes, default = FF..FF
        -- info-ROU:     GET db  SET db
        -- info-IMPL:    V2.0->          
        -- info-VERCTRL: -
        SYNTAX        OCTET STRING (SIZE (0..16))
        ACCESS        read-write
        STATUS        mandatory
        DESCRIPTION
             " Test cell loopback location. It is an identifier known
               by the crafts person identifying a ATM node in the ATM
               network.  For EndToEnd loop test the default value is valid. "
        --DEFAULT test-function-async     fsnAltTest
        --DEFAULT next-function-async     fsnAltNext
        --DEFAULT set-function-async      fsnAltSet
        --DEFAULT get-function-async      fsnAltGet
        ::= { xldv20AtmLoopTest 3 }

     xldv20AltControlReq OBJECT-TYPE
        -- info-VALUE:   noRequest, loopTestRequest
        -- info-ROU:     GET db  SET tm 
        -- info-IMPL:    V2.0->          
        -- info-VERCTRL: -
        SYNTAX        Xldv20ControlReq
        ACCESS        read-write
        STATUS        mandatory
        DESCRIPTION
             " The received command to start an OAM cell loopback test
	     (loopTestRequest).
             Reject reasons are faulty parameters from the agent
             (response: paramFaulty, commExecStarted, loopTestReject,
             commandFailed)
             or a loop request during a running test (response: loopTestBusy).
             Notifications : xldv20TrAltTestResult . "
        --DEFAULT test-function-async     fsnAltTest
        --DEFAULT next-function-async     fsnAltNext
        --DEFAULT set-function-async      fsnAltSet
        --DEFAULT get-function-async      fsnAltGet
        ::= { xldv20AtmLoopTest 4 }

     xldv20AltControlStatus OBJECT-TYPE
        -- info-VALUE:   requestIdle(1), requestBusy(2), requestPassed(3)
        -- info-VALUE:   requestFailed(4)
        -- info-ROU:     GET db
        -- info-IMPL:    V2.0->          
        -- info-VERCTRL: -
        SYNTAX        Xldv20ControlStatus
        ACCESS        read-only
        STATUS        mandatory
        DESCRIPTION
             " The status of the command handling. "
        --DEFAULT next-function-async     fsnAltNext
        --DEFAULT get-function-async      fsnAltGet
        ::= { xldv20AtmLoopTest 5 }

     xldv20AltControlTimer OBJECT-TYPE
        -- info-VALUE:   0..2147483647
        -- info-ROU:     GET db
        -- info-IMPL:    V2.0->          
        -- info-VERCTRL: -
        SYNTAX        Unsigned32
        ACCESS        read-only
        STATUS        mandatory
        DESCRIPTION
             " The maximum duration of loop- back test. 
	     It is required by the SNMP manager to detect the end
             of loopback test in case of the response'xldv20TrAltTestResult'
             was not received in time. "
        --DEFAULT next-function-async     fsnAltNext
        --DEFAULT get-function-async      fsnAltGet
        ::= { xldv20AtmLoopTest 6 }

     xldv20AltOamLevel OBJECT-TYPE
        -- info-VALUE:   f4 (4) (default), f5 (5)
        -- info-ROU:     GET db  SET db 
        -- info-IMPL:    V2.0->          
        -- info-VERCTRL: -
        SYNTAX        Xldv20OamLevel
        ACCESS        read-write
        STATUS        mandatory
        DESCRIPTION
             " The OAM level for loop test on VP/VC level.
               Valid:    f4 (for VP )  f5 (for VC). "
        --DEFAULT test-function-async     fsnAltTest
        --DEFAULT next-function-async     fsnAltNext
        --DEFAULT set-function-async      fsnAltSet
        --DEFAULT get-function-async      fsnAltGet
        ::= { xldv20AtmLoopTest 7 }

     xldv20AltLoopTestType OBJECT-TYPE
        -- info-VALUE:   segment(1), endToEnd(2) 
        -- info-ROU:     GET db  SET db 
        -- info-IMPL:    V2.0->          
        -- info-VERCTRL: -
        SYNTAX        Xldv20TestType
        ACCESS        read-write
        STATUS        mandatory
        DESCRIPTION
             " The type of loop test .
	      For EndToEnd loop test loop location ID is FF..FF. "
        --DEFAULT test-function-async     fsnAltTest
        --DEFAULT next-function-async     fsnAltNext
        --DEFAULT set-function-async      fsnAltSet
        --DEFAULT get-function-async      fsnAltGet
        ::= { xldv20AtmLoopTest 8 }

     xldv20AltVci OBJECT-TYPE
        -- info-VALUE:   0..65535
        -- info-ROU:     GET db  SET db
        -- info-IMPL:    V2.0->          
        -- info-VERCTRL: -
        SYNTAX        INTEGER (0..65535)
        ACCESS        read-write
        STATUS        mandatory
        DESCRIPTION
             " Insertion point for OAM cells for F5 level " 
        --DEFAULT test-function-async     fsnAltTest
        --DEFAULT next-function-async     fsnAltNext
        --DEFAULT set-function-async      fsnAltSet
        --DEFAULT get-function-async      fsnAltGet
        ::= { xldv20AtmLoopTest 9 }

     xldv20AltControlReqResult OBJECT-TYPE
        -- info-VALUE:   noRequest, loopTestRequest, commExecStarted
        -- info-VAlUE:   paramFaulty,looptestBusy,looptestReject
        -- info-VALUE:   requestBusy,setDataFailed,commandFailed
        -- info-VALUE:   aswTimeout, commandSucceeded
        -- info-ROU:     GET db
        -- info-IMPL:    V2.0->          
        -- info-VERCTRL: -
        SYNTAX        Xldv20ControlReq
        ACCESS        read-only
        STATUS        mandatory
        DESCRIPTION
              " The result of the last user command. "
        --DEFAULT next-function-async     fsnAltNext
        --DEFAULT get-function-async      fsnAltGet
        ::= { xldv20AtmLoopTest 10 }

     xldv20AltFlowDirection OBJECT-TYPE
        -- info-VALUE:   inwards, outwards
        -- info-ROU:     GET db  SET db
        -- info-IMPL:    V2.0->          
        -- info-VERCTRL: -
        SYNTAX        Xldv20FlowDirection
        ACCESS        read-write
        STATUS        mandatory
        DESCRIPTION
             " Labels the flow direction of loop back cells.
             'inwards' meanxing towards cellbus.
             'outwards' meaning towards UTOPIA interface . "
        --DEFAULT test-function-async     fsnAltTest
        --DEFAULT next-function-async     fsnAltNext
        --DEFAULT set-function-async      fsnAltSet
        --DEFAULT get-function-async      fsnAltGet
        ::= { xldv20AtmLoopTest 11 }

      xldv20AltControlTimeStamp OBJECT-TYPE
         -- info-VALUE:   0..2Giga
         -- info-ROU:     GET db
         -- info-IMPL:    V2.0->
         -- info-VERCTRL: -
         SYNTAX        TimeTicks
         ACCESS        read-only
         STATUS        mandatory
         DESCRIPTION
            " The time stamp of the last command (end of command). "
        --DEFAULT next-function-async     fsnAltNext
        --DEFAULT get-function-async      fsnAltGet
        ::= { xldv20AtmLoopTest 12 }

     -- --------------------------------------------------------------
     --                 TLM Multiple ATM Loop Back Technique
     --                 Multiple Loopback Result table
     -- --------------------------------------------------------------

     xldv20MultipleLoopbackResultTable  OBJECT-TYPE
        -- info-IMPL:    V2.0->          
        SYNTAX        SEQUENCE OF Xldv20MlbEntry
        ACCESS        not-accessible
        STATUS        mandatory
        DESCRIPTION
             " The Multiple Loopback Result table.
             Used for the multiple loopback functionality to collect
             the IDs of connecting points which
             looped back to the XLD.
             When an ATM looptest is started the table is empty.
             An entry is created when an OAM cell is received from a
             connecting point. "
        --DEFAULT next-function-async     fsnMlbEntryNext
        --DEFAULT get-function-async      fsnMlbEntryGet
        ::= { xldv20TlmOam 4 }

     xldv20MlbEntry   OBJECT-TYPE
        -- info-IMPL:    V2.0->          
        SYNTAX        Xldv20MlbEntry
        ACCESS        not-accessible
        STATUS        mandatory
        DESCRIPTION
             " An entry in the Multiple Loopback Result Table. "
        INDEX         { xldv20MlbIndex }
        ::= { xldv20MultipleLoopbackResultTable 1 }

     Xldv20MlbEntry ::=
        SEQUENCE { xldv20MlbIndex       Unsigned16,
                   xldv20MlbLoopLocId   OCTET STRING
                 }

     xldv20MlbIndex OBJECT-TYPE
        -- info-VALUE:   0..65535
        -- info-ROU:     GET db
        -- info-IMPL:    V2.0->          
        -- info-VERCTRL: -
        SYNTAX        Unsigned16
        ACCESS        read-only
        STATUS        mandatory
        DESCRIPTION
             " The index of this table.  "
        ::= {xldv20MlbEntry 1 }

     xldv20MlbLoopLocId   OBJECT-TYPE
        -- info-VALUE:   hexadecimal at TMN-OS
        -- info-ROU:     GET db
        -- info-IMPL:    V2.0->          
        -- info-VERCTRL: -
        SYNTAX        OCTET STRING ( SIZE (0..16) ) 
        ACCESS        read-only
        STATUS        mandatory
        DESCRIPTION
             " A unique number known by the crafts person specifying 
              the ID of a connecting point which looped back an OAM cell
              to the originating point (SU or LU) within the XLD. "
        ::= {xldv20MlbEntry 2 }

     -- ==============================================================
     --                  A l a r m i n g   G r o u p
     -- ==============================================================
     
        -- List of values and meaning of the attribute xldv20AlmSpecProblem 
        -- (almSpecProblem Abbreviation Description).
        -- This attribute is sent within alarm traps.
        --
        -- Note : For TLM alarms the value of almSpecProblem is identical with the trapId.
        -- For HWM alarms the value has a different meaning depending on the HW.
        -- The trap variable xldv20TvAlmSpecificProblemText describes
        -- textual the specific problem.
        --

     -- --------------------------------------------------------------
     --                    External Alarms Table 
     -- --------------------------------------------------------------

     xldv20ExternalAlarmsTable OBJECT-TYPE
        -- info-IMPL:    V2.0->          
        SYNTAX        SEQUENCE OF Xldv20ExternalAlarmEntry
        ACCESS        not-accessible
        STATUS        mandatory
        DESCRIPTION
             " The entities of the table are used to control the
               forwarding of external alarms to the TMN-OS and LCT. "
        --DEFAULT test-function-async     fsnExtEntryTest
        --DEFAULT next-function-async     fsnExtEntryNext
        --DEFAULT set-function-async      fsnExtEntrySet
        --DEFAULT get-function-async      fsnExtEntryGet
        ::= { xldv20Alarming 1 }

     xldv20ExternalAlarmEntry OBJECT-TYPE
        -- info-IMPL:    V2.0->          
        SYNTAX        Xldv20ExternalAlarmEntry
        ACCESS        not-accessible
        STATUS        mandatory
        DESCRIPTION
             " Entry of external alarm table.
               Notifications : xldv20TrExternalAlarm. "
        INDEX         { xldv20ExtAlarmIndex }
        ::= { xldv20ExternalAlarmsTable 1 }

     Xldv20ExternalAlarmEntry ::=
          SEQUENCE { xldv20ExtAlarmIndex           INTEGER,
                     xldv20ExtAlarmAdminState      Xldv20AdminState,
                     xldv20ExtAlarmOperState       Xldv20OperState,
                     xldv20ExtAlarmActivityState   Xldv20ExtAlarmActivityState,
                     xldv20ExtAlarmSeverityIndex   Xldv20AlmSevProfileIndex,
                     xldv20ExtAlarmFilteringIndex  Xldv20AlmFiltProfileIndex,
                     xldv20ExtAlarmName            OCTET STRING }

      xldv20ExtAlarmIndex  OBJECT-TYPE
        -- info-VALUE:   1..3
        -- info-ROU:     GET db
        -- info-IMPL:    V2.0->          
        -- info-VERCTRL: -
        SYNTAX        INTEGER (1..3)
        ACCESS        read-only
        STATUS        mandatory
        DESCRIPTION
             " A unique number identifying an entry of the 
               external alarm table. "
        ::= { xldv20ExternalAlarmEntry 1 }

     xldv20ExtAlarmAdminState OBJECT-TYPE
        -- info-VALUE:   unlocked(1), locked(2)
        -- info-ROU:     GET db  SET gf
        -- info-IMPL:    V2.0->          
        -- info-VERCTRL: -
        SYNTAX        Xldv20AdminState
        ACCESS        read-write
        STATUS        mandatory
        DESCRIPTION
             " This attribute is used to activate (unlock) and deactivate
               (lock) the forwarding of the external alarm towards the
               manager.  "
        ::= { xldv20ExternalAlarmEntry 2 }

     xldv20ExtAlarmOperState OBJECT-TYPE
        -- info-VALUE:   enabled(1), disabled(2)
        -- info-ROU:     GET db
        -- info-IMPL:    V2.0->          
        -- info-VERCTRL: -
        SYNTAX        Xldv20OperState
        ACCESS        read-only
        STATUS        mandatory
        DESCRIPTION
             " Indicates whether or not the external alarm is
               capable of performing its normal functions. "
        ::= { xldv20ExternalAlarmEntry 3 }

     xldv20ExtAlarmActivityState OBJECT-TYPE
        -- info-VALUE:   undeterminate(0), on(1), off(2)
        -- info-ROU:     GET db
        -- info-IMPL:    V2.0->          
        -- info-VERCTRL: -
        SYNTAX        Xldv20ExtAlarmActivityState
        ACCESS        read-only
        STATUS        mandatory
        DESCRIPTION
             " The status of the external alarm.
	     Only if the operational state is enabled
               and the alarm state is on, an external alarm is generated
               for this object. "
        ::= { xldv20ExternalAlarmEntry 4 }

     xldv20ExtAlarmSeverityIndex OBJECT-TYPE
        -- info-VALUE:   1..40 (default is 1)
        -- info-ROU:     GET db  SET db
        -- info-IMPL:    V2.0->
        -- info-VERCTRL: -
        SYNTAX        Xldv20AlmSevProfileIndex
        ACCESS        read-write
        STATUS        mandatory
        DESCRIPTION
             " The index of the associated entry in the alarm severity
               profile table. These entries contain the severity
               assigments for the alarms reported by this managed
               entity. "
        ::= { xldv20ExternalAlarmEntry 5 }

     xldv20ExtAlarmFilteringIndex OBJECT-TYPE
        -- info-VALUE:   1..40
        -- info-ROU:     GET db
        -- info-IMPL:    V2.x
        -- info-VERCTRL: -
        SYNTAX        Xldv20AlmFiltProfileIndex
        ACCESS        read-only
        STATUS        mandatory
        DESCRIPTION
             " It is a pointer to the instance of the alarm filtering
               assignment profile managed entity that contains the filtering
               assignments for the alarms reported by this managed entity. "
        ::= { xldv20ExternalAlarmEntry 6 }

        xldv20ExtAlarmName OBJECT-TYPE
        -- info-VALUE:   -
        -- info-ROU:     GET db SET db
        -- info-IMPL:    V2.0->
        -- info-VERCTRL: -
        SYNTAX        OCTET STRING ( SIZE (0..50) )
        ACCESS        read-write
        STATUS        mandatory
        DESCRIPTION
             " Describe the input line and the type of external alarm.
               Default values on startup are :
               index=1 : Fan 1 Fail
               index=2 : Fan 2 Fail
               index=3 : High Temperature. "
        ::= { xldv20ExternalAlarmEntry 7 }

     -- --------------------------------------------------------------
     --               Alarm Severity Profile Table
     -- --------------------------------------------------------------

     xldv20AlarmSeverityProfileTable OBJECT-TYPE
        -- info-IMPL:    V2.0->          
        -- info-VERCTRL: -
        SYNTAX        SEQUENCE OF Xldv20AlarmSeverityProfileEntry
        ACCESS        not-accessible
        STATUS        mandatory
        DESCRIPTION
             " The table of alarm severity profiles.
               Profiles can be created or deleted dynamically.
               Creating or deleting an entry in this table automatically creates
               or deletes the corresponding entries in the
               xldv20AlarmSevTable. "
        --DEFAULT test-function-async     fsnAlmSevProfileEntryTest
        --DEFAULT next-function-async     fsnAlmSevProfileEntryNext
        --DEFAULT set-function-async      fsnAlmSevProfileEntrySet
        --DEFAULT get-function-async      fsnAlmSevProfileEntryGet
        ::= { xldv20Alarming 2 }

     xldv20AlarmSeverityProfileEntry OBJECT-TYPE
        -- info-IMPL:    V2.0->          
        -- info-VERCTRL: -
        SYNTAX        Xldv20AlarmSeverityProfileEntry
        ACCESS        not-accessible
        STATUS        mandatory
        DESCRIPTION
             " A group of severities, one for each alarm type in
               the communications alarm group. "
        INDEX         { xldv20AlmSevProfileIndex }
        ::= { xldv20AlarmSeverityProfileTable 1 }

     Xldv20AlarmSeverityProfileEntry ::=
        SEQUENCE { xldv20AlmSevProfileIndex      Xldv20AlmSevProfileIndex,
                   xldv20AlmSevProfileRowStatus  Xldv20RowStatus }

     xldv20AlmSevProfileIndex OBJECT-TYPE
        -- info-VALUE:   1..40
        -- info-ROU:     GET db
        -- info-VERCTRL: -
        SYNTAX        Xldv20AlmSevProfileIndex
        ACCESS        read-only
        STATUS        mandatory
        DESCRIPTION
             " A number identifying this alarm severity profile. "
        ::= { xldv20AlarmSeverityProfileEntry 1 }

     xldv20AlmSevProfileRowStatus OBJECT-TYPE
        -- info-VALUE:   create(1), delete(2)
        -- info-ROU:     GET db SET db
        -- info-IMPL:    V2.0->          
        -- info-VERCTRL: -
        SYNTAX        Xldv20RowStatus
        ACCESS        read-write
        STATUS        mandatory
        DESCRIPTION
             " Used to create a new row or to delete
               an existing row in the table.
               Default value:
                   xldv20AlmSevProfileIndex = 1..10:  created
                   xldv20AlmSevProfileIndex = 11..40: deleted . "
        ::= { xldv20AlarmSeverityProfileEntry 2 }

     -- --------------------------------------------------------------
     --                    Alarm Severity Table
     -- --------------------------------------------------------------

     xldv20AlarmSeverityTable OBJECT-TYPE
        -- info-IMPL:    V2.0->          
        SYNTAX        SEQUENCE OF Xldv20AlarmSeverityEntry
        ACCESS        not-accessible
        STATUS        mandatory
        DESCRIPTION
             " The alarm severity table associates
               profile index and trap ID pairs with severities to be
               used for alarm traps that have occurred.
               (Note that this table does not apply to cleared alarms). "
        --DEFAULT test-function-async     fsnAlmSevEntryTest
        --DEFAULT next-function-async     fsnAlmSevEntryNext
        --DEFAULT set-function-async      fsnAlmSevEntrySet
        --DEFAULT get-function-async      fsnAlmSevEntryGet
        ::= { xldv20Alarming 3 }

     xldv20AlarmSeverityEntry OBJECT-TYPE
        -- info-IMPL:    V2.0->          
        SYNTAX        Xldv20AlarmSeverityEntry
        ACCESS        not-accessible
        STATUS        mandatory
        DESCRIPTION
             " An entry in this table associates an alarm severity
               profile index/trap ID pair with a severity to be used
               for alarm traps.
               The alarm severity profile index is referenced by the
               'Alarm Severity assignment Profile Pointer' attribute
               in the alarm-reporting managed entity e.g. plug-in unit
               and TLM interface (tcAdaptor, Physical Path Termination
               Point etc.).
               Notifications : none. "
        INDEX         { xldv20AlmSevProfileIndex,
	                xldv20AlmSevTrapId }
        ::= { xldv20AlarmSeverityTable 1 }

     Xldv20AlarmSeverityEntry ::=
        SEQUENCE { xldv20AlmSevTrapId  Xldv20TrapIds,
                   xldv20AlmSeverity   Xldv20AlarmSeverity }

     xldv20AlmSevTrapId OBJECT-TYPE
        -- info-VALUE:   trHpExcBER ( 1 ),
        -- info-VALUE:   trHpUNEQ( 2 ), trLcd( 3 ),
        -- info-VALUE:   trLof( 4 ),trLop( 5 ),
        -- info-VALUE:   trLos( 6 ),trMsAIS( 7 ),
        -- info-VALUE:   trMsExcBER( 8 ),trMsRDI( 9 ),
        -- info-VALUE:   trMsSD( 10 ),trPAIS( 11 ),
        -- info-VALUE:   trPRDI( 12 ),trRsExcBER( 13 ),
        -- info-VALUE:   trSlm( 14 ), trTim( 15 ),
        -- info-VALUE:   trActFault( 16 ),
        -- info-VALUE:   trReplaceableUnitTypeMismatch ( 17 ),
        -- info-VALUE:   trReplaceableUnitFailure      ( 18 ),
        -- info-VALUE:   trReplaceableUnitProblem      ( 19 ),
        -- info-VALUE:   trReplaceableUnitNotInstalled ( 20 ),
        -- info-VALUE:   trReplaceableUnitSwMismatch   ( 21 ),
        -- info-VALUE:   trXmissionErr( 105 ),
        -- info-VALUE:   trReplaceableUnitRemoved( 113 ),
        -- info-VALUE:   trAIS( 114 ),trRDI( 115 ),
        -- info-VALUE:   trPlcpLof( 116 ),trPlcpRDI( 117 ),
        -- info-VALUE:   trReplaceableUnitSwMissing( 122 )
        -- info-VALUE:   trInternalFault( 123 ),
        -- info-VALUE:   trAttributeValueChange( 124 ),
        -- info-VALUE:   trImmMNR( 130 ), trLpr( 131 ),
        -- info-VALUE:   trLol( 132 ),
        -- info-VALUE:   trAtmLayerMultiAlarm( 135 ),
        -- info-VALUE:   trWrongServiceConfigData( 141 ),
        -- info-VALUE:   trLOC( 145 ), 
        -- info-VALUE:   Trap ID's for LUIMA :
        -- info-VALUE:   E1 near-end :
        -- info-VALUE:   trExcBER( 407 ), trLif( 408 ),
        -- info-VALUE:   trLods( 409 ),
        -- info-VALUE:   E1 far-end :
        -- info-VALUE:   trTxUnusableFe( 410 ),
        -- info-VALUE:   trRxUnusableFe( 411 ),
        -- info-VALUE:   trRfiIma( 412 ),
        -- info-VALUE:   trRAI( 413 ),
        -- info-VALUE:   IMA group  :
        -- info-VALUE:   trStartUp( 450 ),trStartUpFe( 451 ),
        -- info-VALUE:   trConfigAbort( 452 ),
        -- info-VALUE:   trConfigAbortFe( 453 ),
        -- info-VALUE:   trInsufficientLinks( 454 ),
        -- info-VALUE:   trInsufficientLinksFe( 455 ),
        -- info-VALUE:   trBlockedFe( 456 ),
        -- info-VALUE:   trGrTimingMismatch( 457 ),
        -- info-ROU:     GET db
        -- info-IMPL:    V2.0->          
        -- info-VERCTRL: -
        SYNTAX        Xldv20TrapIds
        ACCESS        read-only
        STATUS        mandatory
        DESCRIPTION
             " The trap ID of the alarm trap type this entry applies to.
               NOTE : the severity of xldv20TrAtmLayerMultiAlarm 
               is not configurable. "
        ::= { xldv20AlarmSeverityEntry 1 }

     xldv20AlmSeverity OBJECT-TYPE
        -- info-VALUE:   critical(1), major(2)
        -- info-VALUE:   minor(3), warning(4), noAlarming(5)
        -- info-ROU:     GET db SET db
        -- info-IMPL:    V2.0->          
        -- info-VERCTRL: -
        SYNTAX        Xldv20AlarmSeverity
        ACCESS        read-write
        STATUS        mandatory
        DESCRIPTION
             " The severity to be used for this trap type when the
               entry is selected. "
        ::= { xldv20AlarmSeverityEntry 2 }

     -- --------------------------------------------------------------
     --                Alarm Filtering Profile Table
     -- --------------------------------------------------------------

     xldv20AlarmFilteringProfileTable OBJECT-TYPE
        -- info-IMPL:    V2.0->          
        SYNTAX        SEQUENCE OF Xldv20AlarmFilteringProfileEntry
        ACCESS        not-accessible
        STATUS        mandatory
        DESCRIPTION
             " The table of alarm filtering profiles.
             Creating or deleting an entry in this table automatically creates
             or deletes the corresponding entries in the
             xldv20AlarmFilteringTable. "
        --DEFAULT next-function-async     fsnAlmFiltProfileEntryNext
        --DEFAULT get-function-async      fsnAlmFiltProfileEntryGet
        ::= { xldv20Alarming 4 }

     xldv20AlarmFilteringProfileEntry OBJECT-TYPE
        -- info-IMPL:    V2.0->          
        SYNTAX        Xldv20AlarmFilteringProfileEntry
        ACCESS        not-accessible
        STATUS        mandatory
        DESCRIPTION
             " An entry of the alarm filtering profile table. "
        INDEX         { xldv20AlmFiltProfileIndex }
        ::= { xldv20AlarmFilteringProfileTable 1 }

     Xldv20AlarmFilteringProfileEntry ::=
        SEQUENCE { xldv20AlmFiltProfileIndex      Xldv20AlmFiltProfileIndex,
                   xldv20AlmFiltProfileRowStatus  Xldv20RowStatus }

     xldv20AlmFiltProfileIndex OBJECT-TYPE
        -- info-VALUE:   1..40 (default 1)
        -- info-ROU:     GET db
        -- info-IMPL:    V2.0->          
        -- info-VERCTRL: -
        SYNTAX        Xldv20AlmFiltProfileIndex
        ACCESS        read-only 
        STATUS        mandatory
        DESCRIPTION
             " A number identifying this alarm filtering profile. "
        ::= { xldv20AlarmFilteringProfileEntry 1 }

     xldv20AlmFiltProfileRowStatus OBJECT-TYPE
        -- info-VALUE:   create(1), delete(2)
        -- info-ROU:     GET db
        -- info-IMPL:    V2.0->          
        -- info-VERCTRL: -
        SYNTAX        Xldv20RowStatus
        ACCESS        read-only
        STATUS        mandatory
        DESCRIPTION
             " This object is used to create a new row or to delete
               an existing row in the table.
               Default value: xldv20AlmFiltProfileIndex = 1: created
                              xldv20AlmFiltProfileIndex = 2 .. 300: deleted . "
        ::= { xldv20AlarmFilteringProfileEntry 2 }

     -- --------------------------------------------------------------
     --                   Alarm Filtering Table 
     -- --------------------------------------------------------------

     xldv20AlarmFilteringTable OBJECT-TYPE
        -- info-IMPL:    V2.0->          
        SYNTAX        SEQUENCE OF Xldv20AlarmFilteringEntry
        ACCESS        not-accessible
        STATUS        mandatory
        DESCRIPTION
             " The alarm filtering table is used for
               temporairy filtering of alarms. "
        --DEFAULT next-function-async     fsnAlmFiltEntryNext
        --DEFAULT get-function-async      fsnAlmFiltEntryGet
        ::= { xldv20Alarming 5 }

     xldv20AlarmFilteringEntry OBJECT-TYPE
        -- info-IMPL:    V2.0->          
        SYNTAX        Xldv20AlarmFilteringEntry
        ACCESS        not-accessible
        STATUS        mandatory
        DESCRIPTION
             " An entry in this table associates a trap id/ temporal
               filter parameter with a xldv20AlmFiltProfileIndex. "
        INDEX   { xldv20AlmFiltProfileIndex,
                  xldv20AlmFiltTrapId }
        ::= { xldv20AlarmFilteringTable 1 }

     Xldv20AlarmFilteringEntry ::=
        SEQUENCE { xldv20AlmFiltTrapId   Xldv20TrapIds,
                   xldv20AlmTempFilter   INTEGER }

     xldv20AlmFiltTrapId OBJECT-TYPE
        -- info-VALUE:   see xldv20AlmSevTrapId
        -- info-ROU:     GET db
        -- info-IMPL:    V2.0->          
        -- info-VERCTRL: -
        SYNTAX        Xldv20TrapIds
        ACCESS        read-only 
        STATUS        mandatory
        DESCRIPTION
             " The ID of the trap type this entry applies to. "
        ::= { xldv20AlarmFilteringEntry 1 }

     xldv20AlmTempFilter OBJECT-TYPE
        -- info-VALUE:   1..86400
        -- info-ROU:     GET db
        -- info-IMPL:    V2.0->          
        -- info-VERCTRL: -
        SYNTAX        INTEGER (0..86400)
        ACCESS        read-only
        STATUS        mandatory
        DESCRIPTION
             " The temporal filtering period in seconds.
               The value 0 means no filtering. "
        ::= { xldv20AlarmFilteringEntry 2 }

     -- --------------------------------------------------------------
     --                      Alarm List Table
     -- --------------------------------------------------------------

     xldv20AlarmListTable OBJECT-TYPE
        -- info-IMPL:    V2.0->          
        SYNTAX        SEQUENCE OF Xldv20AlarmListEntry
        ACCESS        not-accessible
        STATUS        mandatory
        DESCRIPTION
             " The alarm list table is used to store all reported alarms.  "
        --DEFAULT next-function-async     fsnAlmListEntryNext
        --DEFAULT get-function-async      fsnAlmListEntryGet
        ::= { xldv20Alarming 6 }

     xldv20AlarmListEntry OBJECT-TYPE
        -- info-IMPL:    V2.0->          
        SYNTAX        Xldv20AlarmListEntry
        ACCESS        not-accessible
        STATUS        mandatory
        DESCRIPTION
             " Entry of the alarm list table.
               Notifications : none. "
        INDEX         { xldv20AlmIndex }
        ::= { xldv20AlarmListTable 1 }

     Xldv20AlarmListEntry ::=
        SEQUENCE { xldv20AlmIndex               INTEGER,
                   xldv20AlmNatureOfAlarm       Xldv20TrapIds,
                   xldv20AlmSpecProblem         INTEGER,
                   xldv20AlmSpecProblemText     OCTET STRING,
                   xldv20AlmRepEntityId         Integer32,
                   xldv20AlmRepSource           Xldv20RepSource,
                   xldv20AlmFailedComponent     Integer32,
                   xldv20AlmFailedComponentRepSource  Xldv20RepSource,
                   xldv20AlmSeverityOfFailure   Xldv20AlarmSeverity,
                   xldv20AlmPropRepairAction    Integer32,
                   xldv20AlmTimeAndDate         Integer32 }

     xldv20AlmIndex OBJECT-TYPE
        -- info-VALUE:   1..700
        -- info-ROU:     GET db
        -- info-IMPL:    V2.0->          
        -- info-VERCTRL: -
        SYNTAX        INTEGER (1..700)
        ACCESS        read-only
        STATUS        mandatory
        DESCRIPTION
             " Unique value to identify an entry in the alarm list when the
               entry is read or cleared, when the entry is created. "
        ::= { xldv20AlarmListEntry 1 }

     xldv20AlmNatureOfAlarm OBJECT-TYPE
        -- info-VALUE:   see xldv20AlmSevTrapId
        -- info-ROU:     GET db
        -- info-IMPL:    V2.0->          
        -- info-VERCTRL: -
        SYNTAX        Xldv20TrapIds
        ACCESS        read-only
        STATUS        mandatory
        DESCRIPTION
             " Generic trouble description of an alarm (the trap ID). "
        ::= { xldv20AlarmListEntry 2 }

     xldv20AlmSpecProblem OBJECT-TYPE
        -- info-VALUE:   0..255 
        -- info-ROU:     GET db
        -- info-IMPL:    V2.0->          
        -- info-VERCTRL: -
        SYNTAX        INTEGER (0..255)
        ACCESS        read-only
        STATUS        mandatory
        DESCRIPTION
             " Description of further information about an alarm. "
        ::= { xldv20AlarmListEntry 3 }

     xldv20AlmSpecProblemText OBJECT-TYPE
        -- info-VALUE:   0..50 
        -- info-ROU:     GET db
        -- info-IMPL:    V2.0->          
        -- info-VERCTRL: -
        SYNTAX        OCTET STRING ( SIZE (0..50) )
        ACCESS        read-only
        STATUS        mandatory
        DESCRIPTION
             " Description of further information about an alarm in text form. "
        ::= { xldv20AlarmListEntry 4 }

     xldv20AlmRepEntityId OBJECT-TYPE
        -- info-VALUE:   -
        -- info-ROU:     GET db
        -- info-IMPL:    V2.0->          
        -- info-VERCTRL: -
        SYNTAX        Integer32
        ACCESS        read-only
        STATUS        mandatory
        DESCRIPTION
             " The managed entity that reported the alarm. In case of a HWM /
               TLM / COH / GFH object it is the HW unit index / interface
               index / vpcTP or vccTp index /  External Alarm index. "
        ::= { xldv20AlarmListEntry 5 }

     xldv20AlmRepSource OBJECT-TYPE
        -- info-VALUE:   hwm, tlm, vplNni, vplUni
        -- info-VALUE:   extAlarm, vccTp, vpcTp
        -- info-VALUE:   line, vclTp, vplTp
        -- info-VALUE:   vclNni, vclUni
        -- info-ROU:     GET db
        -- info-IMPL:    V2.0->          
        -- info-VERCTRL: -
        SYNTAX        Xldv20RepSource
        ACCESS        read-only
        STATUS        mandatory
        DESCRIPTION
             " Source reporting the alarm. "
        ::= { xldv20AlarmListEntry 6 }

     xldv20AlmFailedComponent OBJECT-TYPE
        -- info-VALUE:   -
        -- info-ROU:     GET db
        -- info-IMPL:    V2.0->          
        -- info-VERCTRL: -
        SYNTAX        Integer32
        ACCESS        read-only
        STATUS        mandatory
        DESCRIPTION
             " The managed entity which is defective. "
        ::= { xldv20AlarmListEntry 7 }

     xldv20AlmFailedComponentRepSource OBJECT-TYPE
        -- info-VALUE:   hwm, tlm, vplNni, vplUni
        -- info-VALUE:   extAlarm, vccTp, vpcTp
        -- info-VALUE:   line, vclTp, vplTp
        -- info-VALUE:   vclNni, vclUni
        -- info-ROU:     GET db
        -- info-IMPL:    V2.0->          
        -- info-VERCTRL: -
        SYNTAX        Xldv20RepSource
        ACCESS        read-only
        STATUS        mandatory
        DESCRIPTION
             " The SW application isolating the failed component. "
        ::= { xldv20AlarmListEntry 8 }

     xldv20AlmSeverityOfFailure OBJECT-TYPE
        -- info-VALUE:   critical(1), major(2)
        -- info-VALUE:   minor(3), warning(4), noAlarming(5)
        -- info-ROU:     GET db
        -- info-IMPL:    V2.0->          
        -- info-VERCTRL: -
        SYNTAX        Xldv20AlarmSeverity 
        ACCESS        read-only
        STATUS        mandatory
        DESCRIPTION
             " The severity of an alarm. "
        ::= { xldv20AlarmListEntry 9 }

     xldv20AlmPropRepairAction OBJECT-TYPE
        -- info-VALUE:   -
        -- info-ROU:     GET db
        -- info-IMPL:    V2.0->          
        -- info-VERCTRL: -
        SYNTAX        Integer32
        ACCESS        read-only
        STATUS        mandatory
        DESCRIPTION
             " Suggestion of solutions to fix the problem. "
        ::= { xldv20AlarmListEntry 10 }

     xldv20AlmTimeAndDate OBJECT-TYPE
        -- info-VALUE:   -
        -- info-ROU:     GET db
        -- info-IMPL:    V2.0->          
        -- info-VERCTRL: -
        SYNTAX        Integer32
        ACCESS        read-only
        STATUS        mandatory
        DESCRIPTION
             " Entry time of the report into the log. "
        ::= { xldv20AlarmListEntry 11 }


     -- --------------------------------------------------------------
     --                     Alarm Control group 
     -- --------------------------------------------------------------

     xldv20AlmControl OBJECT IDENTIFIER 
        -- info-IMPL:    V2.0->          
        -- info-VERCTRL: -
     ::= { xldv20Alarming 7 }

     -- This managed entity manages the update of the alarm list
     -- (xldv20AlarmListTable) and the alarming filtering table.
     -- The craft person has to update the alarm list when he/she has changed
     -- alarm severities.
     -- The craft person has to update the alarm filtering table when he/she has
     -- changed temporal filter in the alarm filtering table.
     --
     -- The TMN-OS can request the DSLAM to send Atm layer multi alarm traps.
     --

     xldv20AlmControlReq OBJECT-TYPE
        -- info-VALUE:   updateAlmList
        -- info-VALUE:   updateFiltList
        -- info-VALUE:   commandFailed
        -- info-VALUE:   startSendingAlarms
        -- info-ROU:     GET db SET gf
        -- info-IMPL:    V2.0->          
        -- info-VERCTRL: -
        SYNTAX        Xldv20ControlReq
        ACCESS        read-write
        STATUS        mandatory
        DESCRIPTION
             " Marks the received command to update the alarm list
               (updateAlmList) or the alarming filtering table
               (updateFiltList) or the request of Atm layer multi 
               alarm traps (startSendingAlarms). "
        --DEFAULT test-function-async     fsnAlmTest
        --DEFAULT next-function-async     fsnAlmNext
        --DEFAULT set-function-async      fsnAlmSet
        --DEFAULT get-function-async      fsnAlmGet
        ::= { xldv20AlmControl 1 }

     xldv20AlmControlStatus OBJECT-TYPE
        -- info-VALUE:   requestIdle(1), requestBusy(2), requestPassed(3)
        -- info-VALUE:   requestFailed(4)
        -- info-ROU:     GET db
        -- info-IMPL:    V2.0->          
        -- info-VERCTRL: -
        SYNTAX        Xldv20ControlStatus
        ACCESS        read-only
        STATUS        mandatory
        DESCRIPTION
             " The status of the control request. The value requestIdle
               will be set after startup/recovery or after a running
               test was aborted by the SNMP manager. "
        --DEFAULT next-function-async     fsnAlmNext
        --DEFAULT get-function-async      fsnAlmGet
        ::= { xldv20AlmControl 2 }

     xldv20AlmControlReqResult OBJECT-TYPE
        -- info-VALUE:   updateAlmList (command)
        -- info-VALUE:   updateFiltList(command)
        -- info-VALUE:   commandFailed
        -- info-VALUE:   startSendingAlarms(command)
        -- info-VALUE:   requestBusy,setDataFailed
        -- info-VALUE:   aswTimeout
        -- info-ROU:     GET db
        -- info-IMPL:    V2.0->          
        -- info-VERCTRL: -
        SYNTAX        Xldv20ControlReq
        ACCESS        read-only
        STATUS        mandatory
        DESCRIPTION
              " The result of the last user command. "
        --DEFAULT next-function-async     fsnAlmNext
        --DEFAULT get-function-async      fsnAlmGet
        ::= { xldv20AlmControl 3 }

      xldv20AlmControlTimeStamp OBJECT-TYPE
         -- info-VALUE:   0..2Giga
         -- info-ROU:     GET db
         -- info-IMPL:    V2.0->
         -- info-VERCTRL: -
         SYNTAX        TimeTicks
         ACCESS        read-only
         STATUS        mandatory
         DESCRIPTION
            " The time stamp of the last command (end of command). "
        --DEFAULT next-function-async     fsnAlmNext
        --DEFAULT get-function-async      fsnAlmGet
        ::= { xldv20AlmControl 4 }

     -- --------------------------------------------------------------
     --                         Reset group 
     -- --------------------------------------------------------------

     xldv20Reset OBJECT IDENTIFIER 
        -- info-IMPL:    V2.0->          
        -- info-VERCTRL: -
     ::= { xldv20Alarming 8 }


   -- Performs the reset of one plugInUnit or of all applicable plug in units.
   -- Not all kinds of reset can be performed on every unit.

     xldv20RstControlReq OBJECT-TYPE
        -- info-VALUE:   warm,cold,reload,dbReload
        -- info-VALUE:   noRequest,
        -- info-ROU:     GET db SET gf
        -- info-IMPL:    V2.0->          
        -- info-VERCTRL: -
        SYNTAX        Xldv20ControlReq
        ACCESS        read-write
        STATUS        mandatory
        DESCRIPTION
             " Request to perform a reset.
               Notifications : 
               xldv20TrReplaceableUnitReset at beginning of reset PIU.
               xldv20TrReplaceableUnitResetEnd at end of reset PIU.
               xldv20TrRstResult for reset of CI in case of a failure occured
               after the reset has been accepted. "
        --DEFAULT test-function-async     fsnRstTest
        --DEFAULT next-function-async     fsnRstNext
        --DEFAULT set-function-async      fsnRstSet
        --DEFAULT get-function-async      fsnRstGet
        ::= { xldv20Reset 1 }

     xldv20RstControlStatus OBJECT-TYPE
        -- info-VALUE:   requestIdle(1), requestBusy(2), requestPassed(3)
        -- info-VALUE:   requestFailed(4)
        -- info-ROU:     GET db
        -- info-IMPL:    V2.0->          
        -- info-VERCTRL: -
        SYNTAX        Xldv20ControlStatus
        ACCESS        read-only
        STATUS        mandatory
        DESCRIPTION
             " The actual status of the reset procedure. "
        --DEFAULT next-function-async     fsnRstNext
        --DEFAULT get-function-async      fsnRstGet
        ::= { xldv20Reset 2 }

     xldv20RstLevel OBJECT-TYPE
        -- info-VALUE:   plugInUnit,system
        -- info-ROU:     GET db SET db
        -- info-IMPL:    V2.0->          
        -- info-VERCTRL: -
        SYNTAX        Xldv20ResetLevel
        ACCESS        read-write
        STATUS        mandatory
        DESCRIPTION
             " The reset level.
	     With this attribute the TMN-OS can deside to make a reset for one
               unit or the whole system. "
        --DEFAULT test-function-async     fsnRstTest
        --DEFAULT next-function-async     fsnRstNext
        --DEFAULT set-function-async      fsnRstSet
        --DEFAULT get-function-async      fsnRstGet
        ::= { xldv20Reset 3 }

     xldv20RstHwUnitIndex OBJECT-TYPE
        -- info-VALUE:   0..65535
        -- info-ROU:     GET db SET db
        -- info-IMPL:    V2.0->          
        -- info-VERCTRL: -
        SYNTAX        Unsigned16
        ACCESS        read-write
        STATUS        mandatory
        DESCRIPTION
             " The (HwUnitIndex) of the plugin unit which should get the
               reset. "
        --DEFAULT test-function-async     fsnRstTest
        --DEFAULT next-function-async     fsnRstNext
        --DEFAULT set-function-async      fsnRstSet
        --DEFAULT get-function-async      fsnRstGet
        ::= { xldv20Reset 4 }

     xldv20RstControlTimer OBJECT-TYPE
        -- info-VALUE:   0..2147483647
        -- info-ROU:     GET db
        -- info-IMPL:    V2.0->          
        -- info-VERCTRL: -
        SYNTAX        Unsigned32
        ACCESS        read-only
        STATUS        mandatory
        DESCRIPTION
             " Timer value for the trap response. Only valid if
               xldv20RstControlStatus indicates requestBusy. "
        --DEFAULT next-function-async     fsnRstNext
        --DEFAULT get-function-async      fsnRstGet
        ::= { xldv20Reset 5 }

     xldv20RstControlReqResult OBJECT-TYPE
        -- info-VALUE:   noRequest, reload, cold, dbReload
        -- info-VALUE:   warm, commExecStarted,
        -- info-VALUE:   rjUpgRunning,rjRstRunning,rjPiuNotAvail
        -- info-VALUE:   rjResetNotSupported,paramFaulty
        -- info-VALUE:   requestBusy,setDataFailed
        -- info-VALUE:   aswTimeout, commandFailed, commandSucceeded,
        -- info-VALUE:   rstRequestFailed
        -- info-ROU:     GET db
        -- info-IMPL:    V2.0->          
        -- info-VERCTRL: -
        SYNTAX        Xldv20ControlReq
        ACCESS        read-only
        STATUS        mandatory
        DESCRIPTION
              " The result of the last user command. "
        --DEFAULT next-function-async     fsnRstNext
        --DEFAULT get-function-async      fsnRstGet
        ::= { xldv20Reset 6 }

      xldv20RstControlTimeStamp OBJECT-TYPE
         -- info-VALUE:   0..2Giga
         -- info-ROU:     GET db
         -- info-IMPL:    V2.0->
         -- info-VERCTRL: -
         SYNTAX        TimeTicks
         ACCESS        read-only
         STATUS        mandatory
         DESCRIPTION
            " The time stamp of the last command (end of command). "
        --DEFAULT next-function-async     fsnRstNext
        --DEFAULT get-function-async      fsnRstGet
        ::= { xldv20Reset 7 }

     -- ==============================================================
     --       S o f t w a r e   M a i n t e n a n c e   G r o u p
     -- ==============================================================

     -- --------------------------------------------------------------
     --                    Log Handler subgroup
     -- --------------------------------------------------------------

     xldv20SwmLogHandler OBJECT IDENTIFIER 
        -- info-IMPL:    V2.0->          
        -- info-VERCTRL: -
     ::= { xldv20Swm 1 }

     xldv20DbuControlReq OBJECT-TYPE
        -- info-VALUE:   noRequest, 
        -- info-VALUE:   dbuReadRequest(command)
        -- info-ROU:     GET db SET ut
        -- info-IMPL:    V2.0->          
        -- info-VERCTRL: -
        SYNTAX        Xldv20ControlReq
        ACCESS        read-write
        STATUS        mandatory
        DESCRIPTION
             " This attribute serves to launch a read request on either the
               Software Errorlog, the Software Tracelog or the Hardware
               Maintenancelog on the CI .
               From XLDV2.0 error logs and trace logs of PIUs of type 
               SU,IL and LU are provided.
               Notifications : 
                  xldv20TrSweLogRead.
                  xldv20TrHwmLogRead.
                  xldv20TrTraceLogRead . "
        --DEFAULT test-function-async     fsnDbuTest
        --DEFAULT next-function-async     fsnDbuNext
        --DEFAULT set-function-async      fsnDbuSet
        --DEFAULT get-function-async      fsnDbuGet
        ::= { xldv20SwmLogHandler 1 }

     xldv20DbuControlStatus OBJECT-TYPE
        -- info-VALUE:   requestIdle(1), requestBusy(2), requestPassed(3)
        -- info-VALUE:   requestFailed(4)
        -- info-ROU:     GET db
        -- info-IMPL:    V2.0->          
        -- info-VERCTRL: -
        SYNTAX        Xldv20ControlStatus
        ACCESS        read-only
        STATUS        mandatory
        DESCRIPTION
             " The status of the current read request. "
        --DEFAULT next-function-async     fsnDbuNext
        --DEFAULT get-function-async      fsnDbuGet
        ::= { xldv20SwmLogHandler 2 }

     xldv20DbuResultFilePath OBJECT-TYPE
        -- info-VALUE:   -
        -- info-ROU:     GET db SET db
        -- info-IMPL:    V2.0->          
        -- info-VERCTRL: -
        SYNTAX        OCTET STRING ( SIZE (0..150) )
        ACCESS        read-write
        STATUS        mandatory
        DESCRIPTION
             " The path (including the file name)
               where the file resulting from the read request should be
               stored. If this attribute does not contain a valid path
               the results will be printed on screen. "
        --DEFAULT test-function-async     fsnDbuTest
        --DEFAULT next-function-async     fsnDbuNext
        --DEFAULT set-function-async      fsnDbuSet
        --DEFAULT get-function-async      fsnDbuGet
        ::= { xldv20SwmLogHandler 3 }

     xldv20DbuLogType OBJECT-TYPE
        -- info-VALUE:   sweLog, swTraceLog, hwmLog
        -- info-ROU:     GET db SET db
        -- info-IMPL:    V2.0->          
        -- info-VERCTRL: -
        SYNTAX        Xldv20LogType
        ACCESS        read-write
        STATUS        mandatory
        DESCRIPTION
             " The log to be read by the read request. "
        --DEFAULT test-function-async     fsnDbuTest
        --DEFAULT next-function-async     fsnDbuNext
        --DEFAULT set-function-async      fsnDbuSet
        --DEFAULT get-function-async      fsnDbuGet
        ::= { xldv20SwmLogHandler 4 }

     xldv20DbuNumEntries OBJECT-TYPE
        -- info-VALUE:   0..65536
        -- info-ROU:     GET db SET db
        -- info-IMPL:    V2.0->          
        -- info-VERCTRL: -
        SYNTAX        INTEGER (0..65536)
        ACCESS        read-write
        STATUS        mandatory
        DESCRIPTION
             " The number of log entries to be read.
               If it is 0 or if the passed number exceeds the
               number of entries mandatoryly in the log, the entire log
               will be read. "
        --DEFAULT test-function-async     fsnDbuTest
        --DEFAULT next-function-async     fsnDbuNext
        --DEFAULT set-function-async      fsnDbuSet
        --DEFAULT get-function-async      fsnDbuGet
        ::= { xldv20SwmLogHandler 5 }

     xldv20DbuControlTimer OBJECT-TYPE
        -- info-VALUE:   0..2147483647
        -- info-ROU:     GET db
        -- info-IMPL:    V2.0->          
        -- info-VERCTRL: -
        SYNTAX        Unsigned32
        ACCESS        read-only
        STATUS        mandatory
        DESCRIPTION
             " The timer value for trap response. "
        --DEFAULT next-function-async     fsnDbuNext
        --DEFAULT get-function-async      fsnDbuGet
        ::= { xldv20SwmLogHandler 6 }

     xldv20DbuControlReqResult OBJECT-TYPE
        -- info-VALUE:   noRequest, commExecStarted
        -- info-VALUE:   paramFaulty, dbuReadRequest
        -- info-VALUE:   dbuReadComplete,dbuReadFailed
        -- info-VALUE:   dbuFileCreationFailed,dbuFileTransmissionFailed
        -- info-VALUE:   commandFailed, commandSucceeded
        -- info-ROU:     GET db
        -- info-IMPL:    V2.0->          
        -- info-VERCTRL: -
        SYNTAX        Xldv20ControlReq
        ACCESS        read-only
        STATUS        mandatory
        DESCRIPTION
              " The result of the last user command. "
        --DEFAULT next-function-async     fsnDbuNext
        --DEFAULT get-function-async      fsnDbuGet
        ::= { xldv20SwmLogHandler 7 }

     xldv20DbuHwUnitIndex OBJECT-TYPE
        -- info-VALUE:   0..65535
        -- info-ROU:     GET db SET db
        -- info-IMPL:    V2.0->          
        -- info-VERCTRL: -
        SYNTAX        Unsigned16
        ACCESS        read-write
        STATUS        mandatory
        DESCRIPTION
             " The HwUnitIndex of the plug-in unit which log should be read. "
        --DEFAULT test-function-async     fsnDbuTest
        --DEFAULT next-function-async     fsnDbuNext
        --DEFAULT set-function-async      fsnDbuSet
        --DEFAULT get-function-async      fsnDbuGet
        ::= { xldv20SwmLogHandler 8 }

      xldv20DbuControlTimeStamp OBJECT-TYPE
         -- info-VALUE:   0..2Giga
         -- info-ROU:     GET db
         -- info-IMPL:    V2.0->
         -- info-VERCTRL: -
         SYNTAX        TimeTicks
         ACCESS        read-only
         STATUS        mandatory
         DESCRIPTION
            " The time stamp of the last command (end of command). "
        --DEFAULT next-function-async     fsnDbuNext
        --DEFAULT get-function-async      fsnDbuGet
        ::= { xldv20SwmLogHandler 9 }

     -- --------------------------------------------------------------
     --                   Upgrade control subgroup
     -- --------------------------------------------------------------

     -- This managed entity represents the control group for SW upgrade user commands.
     -- The following user commands are implemented :
     -- sucUpgrStartRequest:    
     --    start upgrade for the CI  in the background.
     --        as for background loadable PIUs
     --    start upgrade of  background loadable PIUs :
     --       xldv20SucAllOfType specifies upgrade of a single PIU or all PIUs of same type,
     --       in case of all PIUs of a type sahll be loaded they are loaded with the default
     --       SW version;
     --       xldv20SucSwVersion specifies a particular or the default SW version (\0);
     --    start upgrade of foreground loadable PIUs : parameter as for background loadable
     --    PIUs. 
     --       The PIUs will have to in state locked before starting the upgrade. 
     --       The PIUs run with the new load after unlock.
     -- sucActivateLoad:
     --    Activate a background loaded SW applicable as well for the CI  as for PIUs. 
     --    Single activation (xldv20SucAllOfType=sucUpgrSingle, xldv20SucUnit
     --    (same format as xldv20EqhAccPiuTypes), xldv20SucHwUnitIndex of PIU)
     --    and also the activation of all background loaded SW
     --    (xldv20SucAllOfType=sucUpgrAll) for all PIUs that wait for activation is possible. 
     -- sucReadSAPSContentFile : 
     --    The SAPS (Sytem Application Software) content file describes an assignment of
     --    available SW loads to loadable PIUs inclusively the CI .
     --    If there is a new SAPs content file at the FTP
     --    server f.ex. because of bug fix release the crafts person has to request the
     --    reading of the SAPS content file so that the information is available in the DSLAM.
     --    The SAPS content file is automatically read after reload or after activation
     --    of a CI  load.
     -- sucGetSwVersions:
     --    Read the available SW version and two predecessor versions of a PIU before starting
     --    upgrade of PIUs.
     --    The information is available via 
     --       xldv20SucDefaultSwVerson,
     --       xldv20SucPredecessorSwVersion,
     --       xldv20SucPrePredecessorSwVersion. 


     xldv20SwmUpgradeControl OBJECT IDENTIFIER 
        -- info-IMPL:    V2.0->          
        -- info-VERCTRL: -
     ::= { xldv20Swm 2 }

     xldv20SucUnit OBJECT-TYPE
        -- info-VALUE:   same format as xldv20EqhAccPiuTypes
        -- info-ROU:     GET db SET db
        -- info-IMPL:    V2.0->          
        -- info-VERCTRL: -
        SYNTAX        OCTET STRING ( SIZE (0..20) )
        ACCESS        read-write
        STATUS        mandatory
        DESCRIPTION
             " The plug-in unit type to be upgraded. "
        --DEFAULT test-function-async     fsnSucTest
        --DEFAULT next-function-async     fsnSucNext
        --DEFAULT set-function-async      fsnSucSet
        --DEFAULT get-function-async      fsnSucGet
        ::= { xldv20SwmUpgradeControl 1 }

     xldv20SucAllOfType OBJECT-TYPE
        -- info-VALUE:   sucUpgrAll, sucUpgrSingle
        -- info-ROU:     GET db SET db
        -- info-IMPL:    V2.0->          
        -- info-VERCTRL: -
        SYNTAX        Xldv20SucAllOfType
        ACCESS        read-write
        STATUS        mandatory
        DESCRIPTION
             " Indicates that the loading for the dedicated
               unit type may be started n-times ( sucUpgrAll ) regarding
               to the number of boards of the same type within the DSLAM
               or for a single unit (sucUpgrSingle ). "
        --DEFAULT test-function-async     fsnSucTest
        --DEFAULT next-function-async     fsnSucNext
        --DEFAULT set-function-async      fsnSucSet
        --DEFAULT get-function-async      fsnSucGet
        ::= { xldv20SwmUpgradeControl 2 }

     xldv20SucVersionNo OBJECT-TYPE
        -- info-VALUE:   -
        -- info-ROU:     GET db SET db
        -- info-IMPL:    V2.0->          
        -- info-VERCTRL: -
        SYNTAX        OCTET STRING ( SIZE (0..10) )
        ACCESS        read-write
        STATUS        mandatory
        DESCRIPTION
             " String containing the APS version coded into the load for
               the different board types (destination version).
               Default value is \0. Then the default SW version should
               be loaded. "
        --DEFAULT test-function-async     fsnSucTest
        --DEFAULT next-function-async     fsnSucNext
        --DEFAULT set-function-async      fsnSucSet
        --DEFAULT get-function-async      fsnSucGet
        ::= { xldv20SwmUpgradeControl 3 }

     xldv20SucHwUnitIndex OBJECT-TYPE
        -- info-VALUE:   0..65535
        -- info-ROU:     GET db SET db
        -- info-IMPL:    V2.0->          
        -- info-VERCTRL: -
        SYNTAX        Unsigned16
        ACCESS        read-write
        STATUS        mandatory
        DESCRIPTION
             " The hardware unit index of the plug-in unit 
	     to be loaded in case of an single upgrade. "
        --DEFAULT test-function-async     fsnSucTest
        --DEFAULT next-function-async     fsnSucNext
        --DEFAULT set-function-async      fsnSucSet
        --DEFAULT get-function-async      fsnSucGet
        ::= { xldv20SwmUpgradeControl 4 }

     xldv20SucPathName OBJECT-TYPE
        -- info-VALUE:   -
        -- info-ROU:     GET db SET db
        -- info-IMPL:    V2.0->          
        -- info-VERCTRL: -
        SYNTAX        OCTET STRING ( SIZE (0..121) )
        ACCESS        read-write
        STATUS        mandatory
        DESCRIPTION
             " The pathname of SAPS content file. "
        --DEFAULT test-function-async     fsnSucTest
        --DEFAULT next-function-async     fsnSucNext
        --DEFAULT set-function-async      fsnSucSet
        --DEFAULT get-function-async      fsnSucGet
        ::= { xldv20SwmUpgradeControl 5 }

     xldv20SucFileName OBJECT-TYPE
        -- info-VALUE:   -
        -- info-ROU:     GET db SET db
        -- info-IMPL:    V2.0->          
        -- info-VERCTRL: -
        SYNTAX        OCTET STRING ( SIZE (0..33) )
        ACCESS        read-write
        STATUS        mandatory
        DESCRIPTION
             " The filename of SAPS content file. "
        --DEFAULT test-function-async     fsnSucTest
        --DEFAULT next-function-async     fsnSucNext
        --DEFAULT set-function-async      fsnSucSet
        --DEFAULT get-function-async      fsnSucGet
        ::= { xldv20SwmUpgradeControl 6 }

     xldv20SucControlReq OBJECT-TYPE
        -- info-VALUE:   sucUpgrStartRequest
        -- info-VALUE:   sucActivateLoad, sucReadSAPSContentFile
        -- info-VALUE:   sucGetSwVersions
        -- info-VALUE:   sucUpgrEndRequest
        -- info-ROU:     GET db SET up
        -- info-IMPL:    V2.0->          
        -- info-VERCTRL: -
        SYNTAX        Xldv20ControlReq
        ACCESS        read-write
        STATUS        mandatory
        DESCRIPTION
             " SW upgrade command requests from TMN.
               Notifications :
                 xldv20TrCmuReadyForReset.
                 xldv20TrUnitReadyForReset.
                 xldv20TrActivateLoadResult.
                 xldv20TrPuUpgradeResult.
                 xldv20TrFTPError.       
                 xldv20TrUpgradeCanceled.
                 xldv20TrSwVersionsSet.
                 xldv20TrReadSAPSContentFileReady.
                 xldv20TrUpgradeEndRequestResult.
                 xldv20TrUnitUpgradeNotRequested. "
        --DEFAULT test-function-async     fsnSucTest
        --DEFAULT next-function-async     fsnSucNext
        --DEFAULT set-function-async      fsnSucSet
        --DEFAULT get-function-async      fsnSucGet
        ::= { xldv20SwmUpgradeControl 7 }

     xldv20SucControlStatus OBJECT-TYPE
        -- info-VALUE:   requestIdle(1), requestBusy(2), requestPassed(3)
        -- info-VALUE:   requestFailed(4)
        -- info-ROU:     GET db
        -- info-IMPL:    V2.0->          
        -- info-VERCTRL: -
        SYNTAX        Xldv20ControlStatus
        ACCESS        read-only
        STATUS        mandatory
        DESCRIPTION
             " The status of the current request. "
        --DEFAULT next-function-async     fsnSucNext
        --DEFAULT get-function-async      fsnSucGet
        ::= { xldv20SwmUpgradeControl 8 }

     xldv20SucControlTimer OBJECT-TYPE
        -- info-VALUE:   0..2147483647
        -- info-ROU:     GET db
        -- info-IMPL:    V2.0->          
        -- info-VERCTRL: -
        SYNTAX        Unsigned32
        ACCESS        read-only
        STATUS        mandatory
        DESCRIPTION
             " Wait time in seconds after complete upgrade for a
               unit type. "
        --DEFAULT next-function-async     fsnSucNext
        --DEFAULT get-function-async      fsnSucGet
        ::= { xldv20SwmUpgradeControl 9 }

     xldv20SucNumberOfTraps OBJECT-TYPE
        -- info-VALUE:   -2147483648..2147483647
        -- info-ROU:     GET db
        -- info-IMPL:    V2.0->          
        -- info-VERCTRL: -
        SYNTAX        Integer32
        ACCESS        read-only
        STATUS        mandatory
        DESCRIPTION
             " Number of traps which have to be expected. "
        --DEFAULT next-function-async     fsnSucNext
        --DEFAULT get-function-async      fsnSucGet
        ::= { xldv20SwmUpgradeControl 10 }

     xldv20SucDefaultSwVersion OBJECT-TYPE
        -- info-VALUE:   Default value: \0
        -- info-ROU:     GET db
        -- info-IMPL:    V2.0->          
        -- info-VERCTRL: -
        SYNTAX        DisplayString (SIZE (0..10))
        ACCESS        read-only
        STATUS        mandatory
        DESCRIPTION
             " The default SW version.
	     Result of the command GetSwVersions. "
        --DEFAULT next-function-async     fsnSucNext
        --DEFAULT get-function-async      fsnSucGet
        ::= { xldv20SwmUpgradeControl 11 }

     xldv20SucPredecessorSwVersion OBJECT-TYPE
        -- info-VALUE:   Default value: \0
        -- info-ROU:     GET db
        -- info-IMPL:    V2.0->          
        -- info-VERCTRL: -
        SYNTAX        DisplayString (SIZE (0..10))
        ACCESS        read-only
        STATUS        mandatory
        DESCRIPTION
             " The predecessor Sw version.
	     Result of the command GetSwVersions. "
        --DEFAULT next-function-async     fsnSucNext
        --DEFAULT get-function-async      fsnSucGet
        ::= { xldv20SwmUpgradeControl 12 }

     xldv20SucPrePredecessorSwVersion OBJECT-TYPE
        -- info-VALUE:   Default value: \0
        -- info-ROU:     GET db
        -- info-IMPL:    V2.0->          
        -- info-VERCTRL: -
        SYNTAX        DisplayString (SIZE (0..10))
        ACCESS        read-only
        STATUS        mandatory
        DESCRIPTION
             " The pre predecessor Sw version.
	     Result of the command GetSwVersions. "
        --DEFAULT next-function-async     fsnSucNext
        --DEFAULT get-function-async      fsnSucGet
        ::= { xldv20SwmUpgradeControl 13 }
 
     xldv20SucControlReqResult OBJECT-TYPE
        -- info-VALUE:   noRequest, commExecStarted sucUpgrStartRequest,
        -- info-VALUE:   sucActivateLoad, sucReadSAPSContentFile,
        -- info-VALUE:   sucGetSwVersions, sucUpgrMissParameter
        -- info-VALUE:   sucGetSwVersionsFailed
        -- info-VALUE:   sucOk ,sucNotOk
        -- info-VALUE:   sucDbAccessFailed ,sucPiuUnlocked
        -- info-VALUE:   sucTransmissionError ,sucWrongSwVersion
        -- info-VALUE:   sucUnitTypeMismatch
        -- info-VALUE:   sucFtpTransError ,sucFtpCrcError
        -- info-VALUE:   sucSwHwMismatch ,sucUpgrWrongAvState
        -- info-VALUE:   sucFepromCopyFault ,sucUpdateDescFileFailed
        -- info-VALUE:   sucFtpServerNoteAvailable ,sucFtpSendError
        -- info-VALUE:   sucDbBackupFault ,sucUpgradeComplete
        -- info-VALUE:   sucUpgradeNotComplete
        -- info-VALUE:   sucUpgrTaskCreationFault
        -- info-VALUE:   sucUpgrDbAccessFault
        -- info-VALUE:   sucAlreadyLoaded
        -- info-VALUE:   commandSucceeded, commandFailed
        -- info-ROU:     GET db
        -- info-IMPL:    V2.0->          
        -- info-VERCTRL: -
        SYNTAX        Xldv20ControlReq
        ACCESS        read-only
        STATUS        mandatory
        DESCRIPTION
              " The result of the last user command. "
        --DEFAULT next-function-async     fsnSucNext
        --DEFAULT get-function-async      fsnSucGet
        ::= { xldv20SwmUpgradeControl 14 }
 
      xldv20SucControlTimeStamp OBJECT-TYPE
         -- info-VALUE:   0..2Giga
         -- info-ROU:     GET db
         -- info-IMPL:    V2.0->
         -- info-VERCTRL: -
         SYNTAX        TimeTicks
         ACCESS        read-only
         STATUS        mandatory
         DESCRIPTION
            " The time stamp of the last command (end of command). "
        --DEFAULT next-function-async     fsnSucNext
        --DEFAULT get-function-async      fsnSucGet
        ::= { xldv20SwmUpgradeControl 15 }

     -- --------------------------------------------------------------
     --                      SW Upgrade Task Table
     -- --------------------------------------------------------------
       
     xldv20SwUpgradeTaskTable OBJECT-TYPE 
        -- info-IMPL:    V2.0->
        SYNTAX        SEQUENCE OF Xldv20SutTaskTableEntry
        ACCESS        not-accessible
        STATUS        mandatory
        DESCRIPTION
             " Table of the current active or failed tasks of SW upgrade.
               Entries for successfull loading tasks are removed
               from the table.
               This table is used to display the upgrade status for
               single plugin units at the TMN. " 
        --DEFAULT next-function-async     fsnSutEntryNext
        --DEFAULT get-function-async      fsnSutEntryGet
        ::= { xldv20Swm 3 } 
 
     xldv20SutTaskTableEntry OBJECT-TYPE
        -- info-IMPL:    V2.0->
        SYNTAX        Xldv20SutTaskTableEntry 
        ACCESS        not-accessible
        STATUS        mandatory
        DESCRIPTION
             " Entry of the SW upgrade task table.
               Notifications : none. "
        INDEX         { xldv20SutIndex }
        ::= { xldv20SwUpgradeTaskTable 1 }
 
     Xldv20SutTaskTableEntry ::=
        SEQUENCE { xldv20SutIndex               Unsigned16,
                   xldv20SutPiuType             OCTET STRING,
                   xldv20SutHwUnitIndex         Unsigned16,
                   xldv20SutSwVersion           OCTET STRING,
                   xldv20SutRequester           Xldv20Requester,
                   xldv20SutUpgradeState        Xldv20ControlReq,
                   xldv20SutUpgradeResult       Xldv20ControlReq,
		   xldv20SutTimeStamp           TimeTicks
                   }

     xldv20SutIndex OBJECT-TYPE
        -- info-VALUE:   -
        -- info-ROU:     GET db
        -- info-IMPL:    V2.0->
        -- info-VERCTRL: -
        SYNTAX        Unsigned16
        ACCESS        read-only
        STATUS        mandatory
        DESCRIPTION
             " Unique value to identify an entry of this table. "
        ::= { xldv20SutTaskTableEntry 1 }
 
     xldv20SutPiuType OBJECT-TYPE
        -- info-VALUE:   -
        -- info-ROU:     GET db
        -- info-IMPL:    V1.3N->
        -- info-VERCTRL: -
        SYNTAX        OCTET STRING ( SIZE (0..20) )
        ACCESS        read-only
        STATUS        mandatory
        DESCRIPTION
         " Indicates the plug-in unit type to be upgraded. "
        ::= { xldv20SutTaskTableEntry 2 }
 
     xldv20SutHwUnitIndex OBJECT-TYPE
        -- info-VALUE:   -
        -- info-ROU:     GET db
        -- info-IMPL:    V2.0->
        -- info-VERCTRL: -
        SYNTAX        Unsigned16
        ACCESS        read-only
        STATUS        mandatory
        DESCRIPTION
         " The HwUnitIndex of PIU to be loaded.
           From this value the TMN calculates the location shelf/slot
           of the plug-in unit and displays it at the GUI. "
        ::= { xldv20SutTaskTableEntry 3 }
 
    xldv20SutSwVersion OBJECT-TYPE
       -- info-VALUE:   -
       -- info-ROU:     GET db
       -- info-IMPL:    V2.0->
       -- info-VERCTRL: -
       SYNTAX        OCTET STRING ( SIZE (0..10) )
       ACCESS        read-only
       STATUS        mandatory
       DESCRIPTION
         " String containing the APS version which is loaded
           into the plug-in unit . "
        ::= { xldv20SutTaskTableEntry 4 }
 
     xldv20SutRequester OBJECT-TYPE
        -- info-VALUE:   tmn, hwm
        -- info-ROU:     GET db
        -- info-IMPL:    V2.0->
        -- info-VERCTRL: -
        SYNTAX        Xldv20Requester
        ACCESS        read-only
        STATUS        mandatory
        DESCRIPTION
             " Identifies the requesting unit of
               the current upgrade task. "
        ::= { xldv20SutTaskTableEntry 5 }
 
     xldv20SutUpgradeState OBJECT-TYPE
        -- info-VALUE:   sutInitialized, sutToDo
        -- info-VALUE:   sutStarted, sutCrashed, sutFtpDone
        -- info-VALUE:   sutDone, sutReadyForReset
        -- info-VALUE:   sutObsolete
        -- info-ROU:     GET db
        -- info-IMPL:    V2.0->
        -- info-VERCTRL: -
        SYNTAX        Xldv20ControlReq
        ACCESS        read-only
        STATUS        mandatory
        DESCRIPTION
             " Identifies the current processing state of
               the upgrade task. "
        ::= { xldv20SutTaskTableEntry 6 }
 
    xldv20SutUpgradeResult OBJECT-TYPE
        -- info-VALUE:   commExecStarted sucUpgrStartRequest,
        -- info-VALUE:   sucActivateLoad, sucReadSAPSContentFile,
        -- info-VALUE:   sucGetSwVersions, sucUpgrMissParameter,
        -- info-VALUE:   sucGetSwVersionsFailed
        -- info-VALUE:   sucOk ,sucNotOk
        -- info-VALUE:   sucDbAccessFailed ,sucPiuUnlocked
        -- info-VALUE:   sucTransmissionError ,sucWrongSwVersion
        -- info-VALUE:   sucUnitTypeMismatch
        -- info-VALUE:   sucFtpTransError ,sucFtpCrcError
        -- info-VALUE:   sucSwHwMismatch ,sucUpgrWrongAvState
        -- info-VALUE:   sucFepromCopyFault ,sucUpdateDescFileFailed
        -- info-VALUE:   sucFtpServerNoteAvailable ,sucFtpSendError
        -- info-VALUE:   sucDbBackupFault ,sucUpgradeComplete
        -- info-VALUE:   sucUpgradeNotComplete
        -- info-VALUE:   sucUpgrTaskCreationFault
        -- info-VALUE:   sucUpgrDbAccessFault
        -- info-ROU:     GET db
        -- info-IMPL:    V2.0->
        -- info-VERCTRL: -
        SYNTAX        Xldv20ControlReq
        ACCESS        read-only
        STATUS        mandatory
        DESCRIPTION
          " This read-only attribute informs about the result of
            the performes upgrade (in case of failed upgrade
            the error reason). "
        ::= { xldv20SutTaskTableEntry 7 }
 
  xldv20SutTimeStamp OBJECT-TYPE
     -- info-VALUE:   0..2Giga
     -- info-ROU:     GET db
     -- info-IMPL:    V2.0->
     -- info-VERCTRL: -
     SYNTAX        TimeTicks
     ACCESS        read-only
     STATUS        mandatory
     DESCRIPTION
        " The time stamp of the task. It is updated anytime the
        upgrade task state changes. "
        ::= { xldv20SutTaskTableEntry 8 }
 
 -- --------------------------------------------------------------
 --               Secure Telnet control subgroup
 -- --------------------------------------------------------------
 
 -- This managed entity represents the control group for Secure Telnet.
 -- The secure telnet session will be enabled / disabled via a SET
 -- request to the attribute xldv20StcTelnetAccess.
 
 
     xldv20StcSecureTelnetControl OBJECT IDENTIFIER 
        -- info-IMPL:    V2.x->          
     ::= { xldv20Swm 4 }
 
     xldv20StcTelnetAccess OBJECT-TYPE
        -- info-VALUE:   read(1), trace(2),
        -- info-VALUE:   write(3), noAccess(4)
        -- info-ROU:     GET db  SET st
        -- info-IMPL:    V2.x->          
        -- info-VERCTRL: SET blocked
        SYNTAX        Xldv20TelnetAccess
        ACCESS        read-write
        STATUS        mandatory
        DESCRIPTION
             " Feature not supported. The access mode of a telnet session.
             The setting of values read, trace, write will enable 
             a secure telnet session with the corresponding access right.
             The setting of value noAccess will disable a telnet session. "
        --DEFAULT test-function-async     fsnStcTest
        --DEFAULT next-function-async     fsnStcNext
        --DEFAULT set-function-async      fsnStcSet
        --DEFAULT get-function-async      fsnStcGet
        ::= { xldv20StcSecureTelnetControl 1 }

     -- ==============================================================
     --       D a t a B a s e   M a n a g e m e n t   G r o u p
     -- ==============================================================

     -- --------------------------------------------------------------
     --             DataBase Management control subgroup
     -- --------------------------------------------------------------

     xldv20DbmControl OBJECT IDENTIFIER 
        -- info-IMPL:    V2.0->          
     ::= { xldv20Dbm 1 }

     -- This managed entity manages the control request for storage
     -- of the database.

     xldv20DbmControlReq OBJECT-TYPE
        -- info-VALUE:   backupDb
        -- info-ROU:     GET db SET dm
        -- info-IMPL:    V2.0->          
        -- info-VERCTRL: -
        SYNTAX        Xldv20ControlReq
        ACCESS        read-write
        STATUS        mandatory
        DESCRIPTION
             " The command to store the database
               (backupDb) into the FEPROM of the DSLAM.
               The return value commExecStarted indicates the beginning
               of DB storage.
               Notifications : xldv20TrDbBackup indicates the end and 
               the result of the database storage. "
        --DEFAULT set-function-async      fsnDbmSet
        --DEFAULT next-function-async     fsnDbmNext
        --DEFAULT test-function-async     fsnDbmTest
        --DEFAULT get-function-async      fsnDbmGet
        ::= { xldv20DbmControl 1 }

     xldv20DbmControlStatus OBJECT-TYPE
        -- info-VALUE:   requestIdle(1), requestBusy(2), requestPassed(3)
        -- info-VALUE:   requestFailed(4)
        -- info-ROU:     GET db
        -- info-IMPL:    V2.0->          
        -- info-VERCTRL: -
        SYNTAX        Xldv20ControlStatus
        ACCESS        read-only
        STATUS        mandatory
        DESCRIPTION
             " The status of the control request. "
        --DEFAULT next-function-async     fsnDbmNext
        --DEFAULT get-function-async      fsnDbmGet
        ::= { xldv20DbmControl 2 }

     xldv20DbmControlTimer OBJECT-TYPE
        -- info-VALUE:   0..2147483647
        -- info-ROU:     GET db
        -- info-IMPL:    V2.0->          
        -- info-VERCTRL: -
        SYNTAX        Unsigned32
        ACCESS        read-only
        STATUS        mandatory
        DESCRIPTION
              " The maximum wait time for the manager when a DB storage
                request cannot be executed immediately (value commExecStarted
                in the result attribute xldv20DbmControlReqResult).
                The manager reads this value from the DSLAM.
                The end of request indicates the trap xldv20TrDbBackup. "
        --DEFAULT next-function-async     fsnDbmNext
        --DEFAULT get-function-async      fsnDbmGet
        ::= { xldv20DbmControl 3 }

     xldv20DbmBackupPeriod OBJECT-TYPE
        -- info-VALUE:   12..48 (unit = hour)
        -- info-VALUE:   default = 24
        -- info-ROU:     GET db SET dm
        -- info-IMPL:    V2.0->          
        -- info-VERCTRL: -
        SYNTAX        INTEGER (12..48)
            ACCESS        read-write
            STATUS        mandatory
            DESCRIPTION
                  " Interval between two backup operations in hours. "
            --DEFAULT test-function-async     fsnDbmTest
            --DEFAULT next-function-async     fsnDbmNext
            --DEFAULT set-function-async      fsnDbmSet
            --DEFAULT get-function-async      fsnDbmGet
            ::= { xldv20DbmControl 4 }

     xldv20DbmBackupStartTime OBJECT-TYPE
        -- info-VALUE:   0..86400
        -- info-ROU:     GET db SET db
        -- info-IMPL:    V2.0->          
        -- info-VERCTRL: -
            SYNTAX        INTEGER (0..86400)
            ACCESS        read-write
            STATUS        mandatory
            DESCRIPTION
                  " Start time of next DB backup in seconds. "
            --DEFAULT test-function-async     fsnDbmTest
            --DEFAULT next-function-async     fsnDbmNext
            --DEFAULT set-function-async      fsnDbmSet
            --DEFAULT get-function-async      fsnDbmGet
            ::= { xldv20DbmControl 5 }

     xldv20DbmControlReqResultLocal OBJECT-TYPE
        -- info-VALUE:   see xldv20DbmControlReq
        -- info-ROU:     GET db
        -- info-IMPL:    V2.0->          
        -- info-VERCTRL: -
        SYNTAX        Xldv20ControlReq
        ACCESS        read-only
        STATUS        mandatory
        DESCRIPTION
              " The result of the local backup request. "
        --DEFAULT next-function-async     fsnDbmNext
        --DEFAULT get-function-async      fsnDbmGet
        ::= { xldv20DbmControl 6 }

     xldv20DbmControlReqResultRemote OBJECT-TYPE
        -- info-VALUE:   noRequest, commExecStarted
        -- info-VALUE:   backupDb
        -- info-VALUE:   flashAccessFailed, dbReadFailed 
        -- info-VALUE:   localBackupOk, remoteBackupOk,
        -- info-VALUE:   localBackupFailed, remoteBackupFailed,
        -- info-VALUE:   flashAccessFailed, dbReadFailed 
        -- info-VALUE:   requestBusy,setDataFailed
        -- info-VALUE:   aswTimeout, commandFailed, commandSucceeded
        -- info-ROU:     GET db
        -- info-IMPL:    V2.0->          
        -- info-VERCTRL: -
        SYNTAX        Xldv20ControlReq
        ACCESS        read-only
        STATUS        mandatory
        DESCRIPTION
              " The result of the last remote backup request. "
        --DEFAULT next-function-async     fsnDbmNext
        --DEFAULT get-function-async      fsnDbmGet
        ::= { xldv20DbmControl 7 }

     xldv20DbmPathAndFileName OBJECT-TYPE
        -- info-VALUE:   -
        -- info-ROU:     GET db SET db
        -- info-IMPL:    V2.0->          
        -- info-VERCTRL: -
        SYNTAX        OCTET STRING ( SIZE (0..150) )
        ACCESS        read-write
        STATUS        mandatory
        DESCRIPTION
             " The path and filename (relative to the FTP root) 
	     of the DB backup file needed for the remote backup feature. "
        --DEFAULT test-function-async     fsnDbmTest
        --DEFAULT next-function-async     fsnDbmNext
        --DEFAULT set-function-async      fsnDbmSet
        --DEFAULT get-function-async      fsnDbmGet
        ::= { xldv20DbmControl 8 }

      xldv20DbmControlTimeStamp OBJECT-TYPE
         -- info-VALUE:   0..2Giga
         -- info-ROU:     GET db
         -- info-IMPL:    V2.0->
         -- info-VERCTRL: -
         SYNTAX        TimeTicks
         ACCESS        read-only
         STATUS        mandatory
         DESCRIPTION
            " The time stamp of the last command (end of command). "
        --DEFAULT next-function-async     fsnDbmNext
        --DEFAULT get-function-async      fsnDbmGet
        ::= { xldv20DbmControl 9 }

         -- ==============================================================
         --                       Trap ID group
         -- ==============================================================
 
         -- --------------------------------------------------------------
         --                   Trap variables subgroup
         -- --------------------------------------------------------------
 
         xldv20TrapVars OBJECT IDENTIFIER 
            -- info-IMPL:    V2.0->          
	 ::= { xldv20Traps 1 }

         xldv20TvStartupResult OBJECT-TYPE
            -- info-VALUE:   suFinished(1)..suFailed(2)
            -- info-VALUE:   suStandaloneStartupFinished(3)
            -- info-IMPL:    V2.0->          
            SYNTAX        Xldv20StartupResult
            ACCESS        not-accessible
            STATUS        mandatory
            DESCRIPTION
                 " Indicates the result at end of startup. "
            ::= { xldv20TrapVars 1 }
 
         xldv20TvStartupType OBJECT-TYPE
            -- info-VALUE:   warm(6300), cold(6301),
            -- info-VALUE:   reload(6302), cmuUpgrade(6303),
            -- info-VALUE:   powerUp(6304)
            -- info-IMPL:    V2.0->          
            SYNTAX        Xldv20StartupType
            ACCESS        not-accessible
            STATUS        mandatory
            DESCRIPTION
                 " Indicates the kind of performed restart. "
            ::= { xldv20TrapVars 2 }
 
         xldv20TvSnmLctSession OBJECT-TYPE
            -- info-VALUE:   connected(1),disconnected(2)
            -- info-VALUE:   sessionCancelled(3),sessionTimeout(4)
            -- info-VALUE:   onuCutSession(5) 
            -- info-IMPL:    V2.0->          
            SYNTAX        Xldv20SnmLctSession
            ACCESS        not-accessible
            STATUS        mandatory
            DESCRIPTION
                 " Indicates the state of a LCT session . "
            ::= { xldv20TrapVars 3 }
 
         xldv20TvRepEntity OBJECT-TYPE
            -- info-VALUE:   0..65535
            -- info-IMPL:    V2.0->          
            SYNTAX        Unsigned16
            ACCESS        not-accessible
            STATUS        mandatory
            DESCRIPTION
                 " The hardware unit index (HWM) or interface index (TLM)
                   or index of COH reporting entities. "
            ::= { xldv20TrapVars 4 }
 
         xldv20TvRepSource OBJECT-TYPE
            -- info-VALUE:   hwm, tlm, vplNni, vplUni
            -- info-VALUE:   extAlarm, vccTp, vpcTp
            -- info-VALUE:   line, vclTp, vplTp
            -- info-VALUE:   vclNni, vclUni
            -- info-VALUE:   vplCC, vclCC
            -- info-IMPL:    V2.0->          
            SYNTAX        Xldv20RepSource
            ACCESS        not-accessible
            STATUS        mandatory
            DESCRIPTION
                  " Indicates the source of a reporting entity. "
            ::= { xldv20TrapVars 5 }
 
         xldv20TvTimeAndDate OBJECT-TYPE
            -- info-VALUE:   -2147483648..2147483647
            -- info-IMPL:    V2.0->          
            SYNTAX        Integer32
            ACCESS        not-accessible
            STATUS        mandatory
            DESCRIPTION
                 " The time stamp in seconds. "
            ::= { xldv20TrapVars 6 }
 
         xldv20TvActCcReloadResult OBJECT-TYPE
            -- info-VALUE:   ok(1),notOk(2),lineIndexFaulty(3)
            -- info-IMPL:    V2.0->          
            SYNTAX        INTEGER {
                             ok(1),
                             notOk(2),
                             lineIndexFaulty(3)
                          }
            ACCESS        not-accessible
            STATUS        mandatory
            DESCRIPTION
                 " The result of the cross connection reload. "
            ::= { xldv20TrapVars 7 }
 
         xldv20TvActCcStatus OBJECT-TYPE
        -- info-VALUE:   -2147483648..2147483647
        -- info-IMPL:    V2.0->          
            SYNTAX        Integer32
            ACCESS        not-accessible
            STATUS        mandatory
            DESCRIPTION
                 " The index (xldv20ActVpiNni) of faulty cross connect
                   in the table xldv20AtmCrossConnectTable. "
            ::= { xldv20TrapVars 8 }

         xldv20TvAlmNatureOfAlarm OBJECT-TYPE
            -- info-VALUE:   see xldv20AlmSevTrapId
            -- info-IMPL:    V2.0->          
            SYNTAX        Xldv20TrapIds
            ACCESS        not-accessible
            STATUS        mandatory
            DESCRIPTION
                 " The nature of an alarm. Corresponds to
		 xldv20AlarmSevTrapID. "
            ::= { xldv20TrapVars 9 }
 
         xldv20TvAlmSpecProblem OBJECT-TYPE
            -- info-VALUE:   -2147483648..2147483647
            -- info-IMPL:    V2.0->          
            SYNTAX        Integer32
            ACCESS        not-accessible
            STATUS        mandatory
            DESCRIPTION
                 " The specific problem reported by alarming. "
            ::= { xldv20TrapVars 10 }
 
         xldv20TvAlmFailedComponent OBJECT-TYPE
            -- info-VALUE:   -2147483648..2147483647
            -- info-IMPL:    V2.0->          
            SYNTAX        Integer32
            ACCESS        not-accessible
            STATUS        mandatory
            DESCRIPTION
                 " Describes the failed component. "
            ::= { xldv20TrapVars 11 }
 
         xldv20TvAlmSeverityOfFailure OBJECT-TYPE
            -- info-VALUE:   -2147483648..2147483647
            -- info-IMPL:    V2.0->          
            SYNTAX        Xldv20AlarmSeverity
            ACCESS        not-accessible
            STATUS        mandatory
            DESCRIPTION
                 " The severity of the repoprted failure. "
            ::= { xldv20TrapVars 12 }
 
         xldv20TvAlmStatus OBJECT-TYPE
            -- info-VALUE:   present(0)..cleared(1)
            -- info-IMPL:    V2.0->          
            SYNTAX        INTEGER {
                             present(0),
                             cleared(1)
                          }
            ACCESS        not-accessible
            STATUS        mandatory
            DESCRIPTION
                 " Flag indicating whether alarm appears or is cleared. "
            ::= { xldv20TrapVars 13 }

         xldv20TvAlmPropRepairAction OBJECT-TYPE
            -- info-VALUE:   -2147483648..2147483647
            -- info-IMPL:    V2.0->          
            SYNTAX        Integer32
            ACCESS        not-accessible
            STATUS        mandatory
            DESCRIPTION
                 " Indicates proposed repair actions reported by the agent
                   for the problem identified by the alarm. "
            ::= { xldv20TrapVars 14 }
 
         xldv20TvAlmFailedComponentRepSource OBJECT-TYPE
            -- info-VALUE:   hwm, tlm, vplNni, vplUni
            -- info-VALUE:   extAlarm, vccTp, vpcTp
            -- info-VALUE:   line, vclTp, vplTp
            -- info-VALUE:   vclNni, vclUni
            -- info-IMPL:    V2.0->          
            SYNTAX        Xldv20RepSource
            ACCESS        not-accessible
            STATUS        mandatory
            DESCRIPTION
                  " Indicates the source of the reporting entity. "
            ::= { xldv20TrapVars 15 }
 
         xldv20TvStcOldAdminStatus OBJECT-TYPE
            -- info-VALUE:   unlocked(1)..locked(2)
            -- info-IMPL:    V2.0->          
            SYNTAX        Xldv20AdminState
            ACCESS        not-accessible
            STATUS        mandatory
            DESCRIPTION
                 " The old administrative status of the
                   entity changing its state. "
            ::= { xldv20TrapVars 16 }
 
         xldv20TvStcNewAdminStatus OBJECT-TYPE
            -- info-VALUE:   unlocked(1)..locked(2)
            -- info-IMPL:    V2.0->          
            SYNTAX        Xldv20AdminState
            ACCESS        not-accessible
            STATUS        mandatory
            DESCRIPTION
                 " The new administrative status of the
                   entity changing its state. "
            ::= { xldv20TrapVars 17 }
 
         xldv20TvStcOldOperStatus OBJECT-TYPE
            -- info-VALUE:   enabled(1)..disabled(2)
            -- info-IMPL:    V2.0->          
            SYNTAX        Xldv20OperState
            ACCESS        not-accessible
            STATUS        mandatory
            DESCRIPTION
                 " The old operational state of the reporting entity. "
            ::= { xldv20TrapVars 18 }
 
         xldv20TvStcNewOperStatus OBJECT-TYPE
            -- info-VALUE:   enabled(1)..disabled(2)
            -- info-IMPL:    V2.0->          
            SYNTAX        Xldv20OperState
            ACCESS        not-accessible
            STATUS        mandatory
            DESCRIPTION
                 " The new operational state of the reporting entity. "
            ::= { xldv20TrapVars 19 }
 
         xldv20TvTsrControlStatus OBJECT-TYPE
            -- info-VALUE:   requestIdle(1)..requestBusy(2),
            -- info-VALUE:   requestPassed(3)..requestFailed(4)
            -- info-IMPL:    V2.0->          
            SYNTAX        Xldv20ControlStatus
            ACCESS        not-accessible
            STATUS        mandatory
            DESCRIPTION
                 " The control status of the test result. "
            ::= { xldv20TrapVars 20 }
 
         xldv20TvRstResult OBJECT-TYPE
            -- info-VALUE:   requestFailed(4)
            -- info-IMPL:    V2.0->          
            SYNTAX        Xldv20RstResult
            ACCESS        not-accessible
            STATUS        mandatory
            DESCRIPTION
                 " This value indicates the result of a reset request. "
            ::= { xldv20TrapVars 21 }
 
         xldv20TvRstHwUnitIndex OBJECT-TYPE
            -- info-VALUE:   0..65535
            -- info-IMPL:    V2.0->          
            SYNTAX        Unsigned16
            ACCESS        not-accessible
            STATUS        mandatory
            DESCRIPTION
                 " This value indicates the hardware unit of a reset request. "
            ::= { xldv20TrapVars 22 }
 
         xldv20TvHweResetType OBJECT-TYPE
            -- info-VALUE:   cold, warm, reload
            -- info-IMPL:    V2.0->          
            SYNTAX        Xldv20StartupType
            ACCESS        not-accessible
            STATUS        mandatory
            DESCRIPTION
                 " The reset type of a hardware event. "
            ::= { xldv20TrapVars 23 }
 
         xldv20TvAdcControlStatus OBJECT-TYPE
            -- info-VALUE:   -2147483648..2147483647
            -- info-IMPL:    V2.0->          
            SYNTAX        Integer32
            ACCESS        not-accessible
            STATUS        mandatory
            DESCRIPTION
                 " The result of the changeRate request. "
            ::= { xldv20TrapVars 24 }
 
         xldv20TvSucResult OBJECT-TYPE
            -- info-VALUE:   sucOk ,sucNotOk
            -- info-VALUE:   sucDbAccessFailed ,sucPiuUnlocked
            -- info-VALUE:   sucTransmissionError,sucWrongSwVersion
            -- info-VALUE:   sucUnitTypeMismatch,sucFtpTransError
            -- info-VALUE:   sucFtpCrcError,sucSwHwMismatch
            -- info-VALUE:   sucUpgrWrongAvState,sucFepromCopyFault
            -- info-VALUE:   sucUpdateDescFileFailed,sucFtpServerNoteAvailable
            -- info-VALUE:   sucFtpSendError,sucDbBackupFault
            -- info-VALUE:   sucUpgradeComplete,sucUpgradeNotComplete
            -- info-IMPL:    V2.0->          
            SYNTAX        Xldv20ControlReq
            ACCESS        not-accessible
            STATUS        mandatory
            DESCRIPTION
                 " Result of software upgrade. "
            ::= { xldv20TrapVars 25 }
 
         xldv20TvSucUnit OBJECT-TYPE
            -- info-VALUE:   string: plug in unit
            -- info-IMPL:    V2.0->          
            SYNTAX        DisplayString (SIZE (0..20))
            ACCESS        not-accessible
            STATUS        mandatory
            DESCRIPTION
                 " corresponds to the attribute xldSwmUpgradeControl. "
            ::= { xldv20TrapVars 26 }
 
         xldv20TvSucHwUnitIndex OBJECT-TYPE
            -- info-VALUE:   0..65535
            -- info-IMPL:    V2.0->          
            SYNTAX        Unsigned16
            ACCESS        not-accessible
            STATUS        mandatory
            DESCRIPTION
                 " This attribute corresponds to the one in the group
                   xldSwmUpgradeControl. "
            ::= { xldv20TrapVars 27 }
 
         xldv20TvSucVersionNo OBJECT-TYPE
            -- info-VALUE:   string: version number
            -- info-IMPL:    V2.0->          
            SYNTAX        DisplayString (SIZE (0..10))
            ACCESS        not-accessible
            STATUS        mandatory
            DESCRIPTION
                 " This attribute corresponds to the one in the group
                   xldSwmUpgradeControl.
                   Default value: \0 "
            ::= { xldv20TrapVars 28 }
 
         xldv20TvSucPathName OBJECT-TYPE
            -- info-VALUE:   string: path name of load
            -- info-IMPL:    V2.0->          
            SYNTAX        DisplayString (SIZE (0..150))
            ACCESS        not-accessible
            STATUS        mandatory
            DESCRIPTION
                 " This attribute corresponds to the one in the group
                   xldSwmUpgradeControl. "
            ::= { xldv20TrapVars 29 }
 
         xldv20TvSucFileName OBJECT-TYPE
            -- info-VALUE:   string: file name of load
            -- info-IMPL:    V2.0->          
            SYNTAX        DisplayString (SIZE (0..50))
            ACCESS        not-accessible
            STATUS        mandatory
            DESCRIPTION
                 " This attribute corresponds to the one in the group
                   xldSwmUpgradeControl. "
            ::= { xldv20TrapVars 30 }
 
         xldv20TvDbuSweLogReadResult OBJECT-TYPE
            -- info-VALUE:   dbuReadComplete(7081),
            -- info-VALUE:   dbuReadFailed(7082),
            -- info-VALUE:   dbuFileCreationFailed(7083),
            -- info-VALUE:   dbuFileTransmissionFailed(7084)
            -- info-IMPL:    V2.0->          
            SYNTAX        Xldv20DbuReadStatus
            ACCESS        not-accessible
            STATUS        mandatory
            DESCRIPTION
                 " The value indicates the read result of the software
                   error log. "
            ::= { xldv20TrapVars 31 }
 
         xldv20TvDbuHwmLogReadResult OBJECT-TYPE
            -- info-VALUE:   dbuReadComplete(7081),
            -- info-VALUE:   dbuReadFailed(7082),
            -- info-VALUE:   dbuFileCreationFailed(7083),
            -- info-VALUE:   dbuFileTransmissionFailed(7084)
            -- info-IMPL:    V2.0->          
            SYNTAX        Xldv20DbuReadStatus
            ACCESS        not-accessible
            STATUS        mandatory
            DESCRIPTION
                 " The value indicates the read result of the hardware
                   maintenance log. "
            ::= { xldv20TrapVars 32 }
 
         xldv20TvDbuSwTraceLogReadResult OBJECT-TYPE
            -- info-VALUE:   dbuReadComplete(1),dbuReadFailed(2)
            -- info-VALUE:   dbuFileCreationFailed(3)
            -- info-VALUE:   dbuFileTransmissionFailed(4)
            -- info-IMPL:    V2.0->          
            SYNTAX        Xldv20DbuReadStatus
            ACCESS        not-accessible
            STATUS        mandatory
            DESCRIPTION
                 " The value indicates the read result of the software
                   trace log. "
            ::= { xldv20TrapVars 33 }

         xldv20TvHwUnitType OBJECT-TYPE
            -- info-VALUE:   equipment(1),equipmentHolder(2)
            -- info-VALUE:   plugInUnit(3)
            -- info-IMPL:    V2.0->          
            SYNTAX        Xldv20HwUnitType
            ACCESS        not-accessible
            STATUS        mandatory
            DESCRIPTION
                 " The type of the created or deleted Hwm object. "
            ::= { xldv20TrapVars 34 }
 

         xldv20TvHwContainingUnitIndex OBJECT-TYPE
            -- info-VALUE:   0..65535
            -- info-IMPL:    V2.0->          
            SYNTAX        Unsigned16
            ACCESS        not-accessible
            STATUS        mandatory
            DESCRIPTION
                 " HwUnitIndex of the created or deleted Hwm object. "
            ::= { xldv20TrapVars 35 }

         xldv20TvHwContainedUnitAddr OBJECT-TYPE
            -- info-VALUE:   1..512
            -- info-IMPL:    V2.0->          
            SYNTAX        INTEGER(1..512)
            ACCESS        not-accessible
            STATUS        mandatory
            DESCRIPTION
                 " A number of the contained Unit "
            ::= { xldv20TrapVars 36 }

         xldv20TvHwuControlResult OBJECT-TYPE
            -- info-VALUE:   hwuParamFaulty, hwuCommandFailed,
            -- info-VALUE:   hwuObjExists, hwuEquTypeNotAvail,
            -- info-VALUE:   hwuEqhTypeNotAvail, hwuPiuTypeNotAvail,
            -- info-VALUE:   hwuPiuTypeNotAccepted
            -- info-VALUE:   hwuContainingUnitNotAvail
            -- info-VALUE:   hwuObjNotAvail, hwuObjNotEmpty,
            -- info-VALUE:   hwuObjNotLocked, hwuObjNotValid
            -- info-VALUE:   hwuCreateHwUnitComplete
            -- info-VALUE:   hwuCcExisting, hwuUpgradeRunning
            -- info-IMPL:    V2.0->          
            SYNTAX        Xldv20ControlReq
            ACCESS        not-accessible
            STATUS        mandatory
            DESCRIPTION
                 " The result of the request xldv20HwuControlReq. "
            ::= { xldv20TrapVars 37 }

         xldv20TvRiRemInvResult OBJECT-TYPE
            -- info-VALUE:   riRemoteInventoryComplete(1)
            -- info-VALUE:   riFileCreationFailed(2)
            -- info-VALUE:   riFileTransmissionFailed(3)
            -- info-IMPL:    V2.0->          
            SYNTAX        Xldv20RiResultType 
            ACCESS        not-accessible
            STATUS        mandatory
            DESCRIPTION
                 " The result of the  Remote Inventory Data reading. "
            ::= { xldv20TrapVars 38 }

         xldv20TvVersionNrCmuLoad OBJECT-TYPE
            -- info-VALUE:   string: Version number of current CI  load.
            -- info-IMPL:    V2.0->          
            SYNTAX        DisplayString (SIZE (0..20))
            ACCESS        not-accessible
            STATUS        mandatory
            DESCRIPTION
                 " The version number of the current CI  load. "
            ::= { xldv20TrapVars 39 }

         xldv20TvBackupResult OBJECT-TYPE
            -- info-VALUE:   dbmLocalBackupOk (9100)
            -- info-VALUE:   dbmRemoteBackupOk(9101)
            -- info-VALUE:   dbmLocalBackupFailed (9102)
            -- info-VALUE:   dbmRemoteBackupFailed (9103)
            -- info-VALUE:   dbmFlashAccessFailed (9104)
            -- info-VALUE:   dbmDbReadFailed (9105)
            -- info-VALUE:   dbmLocalBackupFileFaulty (9106)
            -- info-VALUE:   dbmRemoteBackupFileFaulty(9107)
            -- info-VALUE:   dbmRestoreFailed (9108)
            -- info-VALUE:   dbmRestoreOk (9109)
            -- info-IMPL:    V2.0->          
            SYNTAX        Xldv20ControlReq
            ACCESS        not-accessible
            STATUS        mandatory
            DESCRIPTION
                 " The result of the request xldv20DbmControlReq. "
            ::= { xldv20TrapVars 40 }

         xldv20TvVpiNni      OBJECT-TYPE
            -- info-VALUE:   -2147483648..2147483647
            -- info-IMPL:    V2.0->          
            SYNTAX        Integer32
            ACCESS        not-accessible
            STATUS        mandatory
            DESCRIPTION
                 " The VpiNni value of the cross connect. "
            ::= { xldv20TrapVars 41 }

         xldv20TvVpiNniIndex OBJECT-TYPE
            -- info-VALUE:   0..65535
            -- info-IMPL:    V2.0->          
            SYNTAX        Unsigned16
            ACCESS        not-accessible
            STATUS        mandatory
            DESCRIPTION
                 " The index of the cross connect in the ATM 
                   cross connect table. "
            ::= { xldv20TrapVars 42 }

         xldv20TvVplTerminationPointA OBJECT-TYPE
            -- info-VALUE:   -2147483648..2147483647
            -- info-IMPL:    V2.0->          
            SYNTAX        Integer32
            ACCESS        not-accessible
            STATUS        mandatory
            DESCRIPTION
                 " For a point-to-point cross connect this attribute identifies
                   the instance of the VPL termination point that represents
                   the VPL at the LE side. "
            ::= { xldv20TrapVars 43 }

         xldv20TvVplTerminationPointZ OBJECT-TYPE
            -- info-VALUE:   -2147483648..2147483647
            -- info-IMPL:    V2.0->          
            SYNTAX        Integer32
            ACCESS        not-accessible
            STATUS        mandatory
            DESCRIPTION
                 " For a point-to-point cross connect this attribute identifies
                   the instance of the VPL termination point that represents
                   the VPL at the NT side. "
            ::= { xldv20TrapVars 44 }

         xldv20TvSnmMibVersion OBJECT-TYPE
            -- info-VALUE:   string: MIB version.
            -- info-IMPL:    V2.0->          
            SYNTAX        DisplayString (SIZE (0..30))
            ACCESS        not-accessible
            STATUS        mandatory
            DESCRIPTION
                 " The version number of the current MIB . "
            ::= { xldv20TrapVars 47 }

         xldv20TvSnmAgentVersion OBJECT-TYPE
            -- info-VALUE:   string: SNMP agent version.
            -- info-IMPL:    V2.0->          
            SYNTAX        DisplayString (SIZE (0..30))
            ACCESS        not-accessible
            STATUS        mandatory
            DESCRIPTION
                 " The version number of the current Agent SW . "
            ::= { xldv20TrapVars 48 }

         xldv20TvVciNni  OBJECT-TYPE
            -- info-VALUE:   -2147483648..2147483647
            -- info-IMPL:    V2.0->          
            SYNTAX        Integer32
            ACCESS        not-accessible
            STATUS        mandatory
            DESCRIPTION
                 " VciNni "
            ::= { xldv20TrapVars 49 }

         xldv20TvVciNniIndex  OBJECT-TYPE
            -- info-VALUE:   0..65535
            -- info-IMPL:    V2.0->          
            SYNTAX        Unsigned16
            ACCESS        not-accessible
            STATUS        mandatory
            DESCRIPTION
                 " Index of a VciNni "
            ::= { xldv20TrapVars 50 }

         xldv20TvVclTerminationPointA  OBJECT-TYPE
            -- info-VALUE:   -2147483648..2147483647
            -- info-IMPL:    V2.0->          
            SYNTAX        Integer32
            ACCESS        not-accessible
            STATUS        mandatory
            DESCRIPTION
                 " Index of a Vcl termination point at NNI side. "
            ::= { xldv20TrapVars 51 }

         xldv20TvVclTerminationPointZ  OBJECT-TYPE
            -- info-VALUE:   -2147483648..2147483647
            -- info-IMPL:    V2.0->          
            SYNTAX        Integer32
            ACCESS        not-accessible
            STATUS        mandatory
            DESCRIPTION
                 " Index of a Vcl termination point at UNI side. "
            ::= { xldv20TrapVars 52 }

         xldv20TvVpcTpIndex OBJECT-TYPE
            -- info-VALUE:   0..65535
            -- info-IMPL:    V2.0->          
            SYNTAX        Unsigned16
            ACCESS        not-accessible
            STATUS        mandatory
            DESCRIPTION
                 " Index of a VpcTp "
            ::= { xldv20TrapVars 53 }

         xldv20TvVpcNniIndex OBJECT-TYPE
            -- info-VALUE:   0..65535
            -- info-IMPL:    V2.0->          
            SYNTAX        Unsigned16
            ACCESS        not-accessible
            STATUS        mandatory
            DESCRIPTION
                 " Index of a VpcTp at NNI side . "
            ::= { xldv20TrapVars 54 }

         xldv20TvVpcUniIndex OBJECT-TYPE
            -- info-VALUE:   0..65535
            -- info-IMPL:    V2.0->          
            SYNTAX        Unsigned16
            ACCESS        not-accessible
            STATUS        mandatory
            DESCRIPTION
                 " Index of a VpcTp at UNI side . "
            ::= { xldv20TrapVars 55 }

         xldv20TvEthVccTpIndex OBJECT-TYPE
            -- info-VALUE:   0..65535
            -- info-IMPL:    V2.0->          
            SYNTAX        Unsigned16
            ACCESS        not-accessible
            STATUS        mandatory
            DESCRIPTION
                 " Index of a VccTp . "
            ::= { xldv20TrapVars 56 }
 

         xldv20TvVpiValue OBJECT-TYPE
            -- info-VALUE:   -2147483648..2147483647
            -- info-IMPL:    V2.0->          
            SYNTAX        Integer32 
            ACCESS        not-accessible
            STATUS        mandatory
            DESCRIPTION
                 " VPI value "
            ::= { xldv20TrapVars 57 }

         xldv20TvVciValue OBJECT-TYPE
            -- info-VALUE:   0..65535
            -- info-IMPL:    V2.0->          
            SYNTAX        Unsigned16
            ACCESS        not-accessible
            STATUS        mandatory
            DESCRIPTION
                 " VCI value "
            ::= { xldv20TrapVars 58 }

         xldv20TvVplTpIndex OBJECT-TYPE
            -- info-VALUE:   -2147483648..2147483647
            -- info-IMPL:    V2.0->          
            SYNTAX        Integer32 
            ACCESS        not-accessible
            STATUS        mandatory
            DESCRIPTION
                 " Index of a VplTp. " 
            ::= { xldv20TrapVars 59 }
 
         xldv20TvVplIfIndex OBJECT-TYPE
            -- info-VALUE:   -2147483648..2147483647
            -- info-IMPL:    V2.0->          
            SYNTAX        Integer32
            ACCESS        not-accessible
            STATUS        mandatory
            DESCRIPTION
                 " IfIndex of PPTP associated to a VplTp. "
            ::= { xldv20TrapVars 60 }

         xldv20TvAlmFailedComponentString OBJECT-TYPE
            -- info-VALUE:   default value 0
            -- info-IMPL:    V2.0->          
            SYNTAX        OCTET STRING ( SIZE (1..100) ) 
            ACCESS        not-accessible
            STATUS        mandatory
            DESCRIPTION
                  " Up 50 times indeces of VpcTp's or VccTp's. "
            ::= { xldv20TrapVars 61 }

         xldv20TvTelnetSession OBJECT-TYPE
            -- info-VALUE:   default stopped
            -- info-IMPL:    V2.0->          
            SYNTAX        Xldv20TvTelnetSessionStatus
            ACCESS        not-accessible
            STATUS        mandatory
            DESCRIPTION
                  " Signalizes the status of a telnet session. "
            ::= { xldv20TrapVars 62 }

        xldv20TvEthIfIndex OBJECT-TYPE
           -- info-VALUE:   -2147483648..2147483647
           -- info-IMPL:    V2.0->          
           SYNTAX        Integer32
           ACCESS        not-accessible
           STATUS        mandatory
           DESCRIPTION
                 " Index of configured Eth Entry. "
           ::= { xldv20TrapVars 63 }

        xldv20TvCACProblemType OBJECT-TYPE
           -- info-VALUE:  cacBwOverflowUp (2551)
           -- info-VALUE:  cacBwOverflowDown (2552)
           -- info-VALUE:  cacLineBlockedByTlm (2553)
           -- info-VALUE:  cacTrafficTypeConflict(2554)
           -- info-VALUE:  cacTrafficDirectionConflict (2555)
           -- info-VALUE:  cacMbsOverflowUp (2556)
           -- info-VALUE:  cacMbsOverflowDown (2557)
           -- info-VALUE:  cacBwWarningUp (2558)
           -- info-VALUE:  cacBwWarningDown (2559)
           -- info-VALUE:  cacMbsWarningUp (2560)
           -- info-VALUE:  cacMbsWarningDown (2561)
           -- info-VALUE:  cacMbsScrError (2562)
           -- info-VALUE:  cacInternalError (2563)                            
           -- info-IMPL:   V2.0->          
           SYNTAX        Xldv20ControlReq
           ACCESS        not-accessible
           STATUS        mandatory
           DESCRIPTION
                 " problem type when CAC problem . "
           ::= { xldv20TrapVars 64 }

        xldv20TvCACBandwidthUsageUp OBJECT-TYPE
           -- info-VALUE:   0..100
           -- info-IMPL:    V2.0->          
           SYNTAX        INTEGER (0..100 )
           ACCESS        not-accessible
           STATUS        mandatory
           DESCRIPTION
                 "used bandwidth in percent of guaranteed bandwidth (without UBR traffic). "
           ::= { xldv20TrapVars 65 }

        xldv20TvEthVpcTpIndex OBJECT-TYPE
           -- info-VALUE:   0..65535
           -- info-IMPL:    V2.0->          
           SYNTAX        Unsigned16
           ACCESS        not-accessible
           STATUS        mandatory
           DESCRIPTION
                 " Index of VpcTp at Ethernet port. "
           ::= { xldv20TrapVars 66 }

        xldv20TvEthEntryIndex OBJECT-TYPE
           -- info-VALUE:   0..65535
           -- info-IMPL:    V2.0->          
           SYNTAX        Unsigned16
           ACCESS        not-accessible
           STATUS        mandatory
           DESCRIPTION
                 "used within TrVplCcDeletion. "
           ::= { xldv20TrapVars 68 }

         xldv20TvRepEntityExt OBJECT-TYPE
            -- info-VALUE:   0..65535
            -- info-IMPL:    V2.0->          
            SYNTAX        Unsigned16
            ACCESS        not-accessible
            STATUS        mandatory
            DESCRIPTION
                 " The hardware unit index (HWM) or interface index (TLM)
                   or index of COH reporting ext. entities. "
            ::= { xldv20TrapVars 69 }

         xldv20TvTelnetSessionUser OBJECT-TYPE
            -- info-VALUE:   string: Telnet User Name.
            -- info-IMPL:    V2.0->          
            SYNTAX        DisplayString (SIZE (0..20))
            ACCESS        not-accessible
            STATUS        mandatory
            DESCRIPTION
                 " The Telnet user name currently logged. "
            ::= { xldv20TrapVars 70 }
                
         xldv20TvIndexSegment OBJECT-TYPE
            -- info-VALUE:   0..65535
            -- info-IMPL:    V2.0->          
            SYNTAX        Unsigned16
            ACCESS        not-accessible
            STATUS        mandatory
            DESCRIPTION
                 " Index of entry in Xldv20ContinuityCheckVpTable
                 or Xldv20ContinuityCheckVcTable for 
                 continuity check on segment level. "
            ::= { xldv20TrapVars 71 }

         xldv20TvIndexEndToEnd OBJECT-TYPE
            -- info-VALUE:   0..65535
            -- info-IMPL:    V2.0->          
            SYNTAX        Unsigned16
            ACCESS        not-accessible
            STATUS        mandatory
            DESCRIPTION
                 " Index of entry in Xldv20ContinuityCheckVpTable
                 or Xldv20ContinuityCheckVcTable for endToEnd continuity check. "
            ::= { xldv20TrapVars 72 }

         xldv20TvRestoreResult OBJECT-TYPE
            -- info-VALUE:   dbmLocalBackupOk(9100)
            -- info-VALUE:   dbmRemoteBackupOk(9101)
            -- info-VALUE:   dbmLocalBackupFailed(9102)
            -- info-VALUE:   dbmRemoteBackupFailed(9103)
            -- info-VALUE:   dbmFlashAccessFailed(9104)
            -- info-VALUE:   dbmDbReadFailed(9105)
            -- info-VALUE:   dbmLocalBackupFileFaulty(9106)
            -- info-VALUE:   dbmRemoteBackupFileFaulty(9107)
            -- info-VALUE:   dbmRestoreFailed(9108)
            -- info-VALUE:   dbmRestoreOk(9109)
            -- info-IMPL:    V2.0->          
            SYNTAX        Xldv20ControlReq
            ACCESS        not-accessible
            STATUS        mandatory
            DESCRIPTION
                 " The result of the DB restoration after reload. "
            ::= { xldv20TrapVars 75 }

        xldv20TvCACBandwidthUsageDown OBJECT-TYPE
           -- info-VALUE:   0..100
           -- info-IMPL:    V2.0->          
           SYNTAX        INTEGER (0..100)
           ACCESS        not-accessible
           STATUS        mandatory
           DESCRIPTION
                 "used bandwidth downstream in percent of guaranteed bandwidth. "
           ::= { xldv20TrapVars 76 }

         xldv20TvCallpObjectType OBJECT-TYPE
            -- info-VALUE:   vplTp, vpcTp, vccTp
            -- info-IMPL:    V2.0->          
            SYNTAX        Xldv20RepSource
            ACCESS        not-accessible
            STATUS        mandatory
            DESCRIPTION
                 " Specifies the type of COH Object . "
            ::= { xldv20TrapVars 77 }

         xldv20TvVpcTpIfIndex OBJECT-TYPE
            -- info-VALUE:   -
            -- info-IMPL:    V2.0->          
            SYNTAX        INTEGER (1..9192)
            ACCESS        not-accessible
            STATUS        mandatory
            DESCRIPTION
                 " new for V2.0"
            ::= { xldv20TrapVars 79 }

         xldv20TvAlmSpecProblemText OBJECT-TYPE
            -- info-VALUE:   -
            -- info-IMPL:    V2.0->          
            SYNTAX        OCTET STRING ( SIZE (0..50) )
            ACCESS        not-accessible
            STATUS        mandatory
            DESCRIPTION
                 " Textual description of specific problem reported by alarming. "
            ::= { xldv20TrapVars 80 }

         xldv20TvImaSetNumResult OBJECT-TYPE
            -- info-VALUE:   imaSetMinNumOk,imaSetMinNumFailed
            -- info-IMPL:    V2.0->          
            SYNTAX        Xldv20ControlReq
            ACCESS        not-accessible
            STATUS        mandatory
            DESCRIPTION
                 " Result of command imaSetMinNumTxLinks . "
            ::= { xldv20TrapVars 81 }

         xldv20TvStcOldAvailStatus OBJECT-TYPE
            -- info-SYNTAX:  Xldv20AvailStatus
            -- info-VALUE:   available(1), failed(2), degraded(3), offline(4)
            -- info-VALUE:   notInstalled(5), dependency(7)
            -- info-IMPL:    V2.0->          
            SYNTAX        Xldv20AvailStatus
            ACCESS        not-accessible
            STATUS        mandatory
            DESCRIPTION
                 " The old availability state of the reporting entity. "
            ::= { xldv20TrapVars 82 }
 
         xldv20TvStcNewAvailStatus OBJECT-TYPE
            -- info-VALUE:   available(1), failed(2), degraded(3), offline(4)
            -- info-VALUE:   notInstalled(5), dependency(7)
            -- info-IMPL:    V2.0->          
            SYNTAX        Xldv20AvailStatus
            ACCESS        not-accessible
            STATUS        mandatory
            DESCRIPTION
                 " The new availability state of the reporting entity. "
            ::= { xldv20TrapVars 83 }

         -- --------------------------------------------------------------
         --                    Trap types group
         -- --------------------------------------------------------------
 
         xldv20TrapTypes OBJECT IDENTIFIER 
            -- info-IMPL:    V2.0->          
	 ::= { xldv20Traps 2 }

         -- Alarm Trap 
         xldv20TrHpExcBER TRAP-TYPE
            -- info-TRAPTYPE:  alarm
            -- info-FAILEDSRC: tlm
            -- info-FAILEDOBJ: S1n(= STM-1 NePPTP),S3n
            -- info-IMPL:    V2.0->          
            ENTERPRISE xldv20Traps
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Excessive bit error rate at high order path. "
            ::= 1

         -- Alarm Trap
         xldv20TrHpUNEQ TRAP-TYPE
            -- info-TRAPTYPE:  alarm
            -- info-FAILEDSRC: tlm
            -- info-FAILEDOBJ: S1n(= STM-1 NePPTP),S3n,E3n
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Unequipped at higher order path. "
            ::= 2

         -- Alarm Trap 
         xldv20TrLcd TRAP-TYPE
            -- info-TRAPTYPE:  alarm
            -- info-FAILEDSRC: tlm
            -- info-FAILEDOBJ: Tca
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Loss of cell delineation. "
            ::= 3

         -- Alarm Trap 
         xldv20TrLof TRAP-TYPE
            -- info-TRAPTYPE:  alarm
            -- info-FAILEDOBJ: S1n(= STM-1 NePPTP),S3n,E3n,D3n
            -- info-FAILEDOBJ: Pon,Adc(= Adc-PPTP),Adr,Vdc,Vdr,
            -- info-FAILEDOBJ: e1nIma
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Los of frame. "
            ::= 4

         -- Alarm Trap 
         xldv20TrLop TRAP-TYPE
            -- info-TRAPTYPE:  alarm
            -- info-FAILEDSRC: tlm 
            -- info-FAILEDOBJ: S1n(= STM-1 NePPTP),S3n
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Loss of pointer. "
            ::= 5

         -- Alarm Trap 
         xldv20TrLos TRAP-TYPE
            -- info-TRAPTYPE:  alarm
            -- info-FAILEDSRC: tlm
            -- info-FAILEDOBJ: S1n(= STM-1 NePPTP),S3n,E3n,D3n
            -- info-FAILEDOBJ: Pon,Adc(= Adc-PPTP),Adr,Vdc,Vdr
            -- info-FAILEDOBJ: Ibm(= Ibm-PPTP),Eth, e1nIma  
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Loss of signal. "
            ::= 6

         -- Alarm Trap 
         xldv20TrMsAIS TRAP-TYPE
            -- info-TRAPTYPE:  alarm
            -- info-FAILEDSRC: tlm
            -- info-FAILEDOBJ: S1n(= STM-1 NePPTP),S3n
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Alarm indication signal at multiplexer section. "
            ::= 7

         -- Alarm Trap
         xldv20TrMsExcBER TRAP-TYPE
            -- info-TRAPTYPE:  alarm
            -- info-FAILEDSRC: tlm
            -- info-FAILEDOBJ: S1n(= STM-1 NePPTP),S3n
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Excessive bit error rate at multiplexer section. "
            ::= 8

         -- Alarm Trap
         xldv20TrMsRDI TRAP-TYPE
            -- info-TRAPTYPE:  alarm
            -- info-FAILEDSRC: tlm
            -- info-FAILEDOBJ: S1f(= STM-1 FePPTP),S3f
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Remote defect indication at multiplexer section. "
            ::= 9

         -- Alarm Trap 
         xldv20TrMsSD TRAP-TYPE
            -- info-TRAPTYPE:  alarm
            -- info-FAILEDSRC: tlm
            -- info-FAILEDOBJ: S1n(= STM-1 NePPTP),S3n
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Signal degrade at multiplexer section. "
            ::= 10

         -- Alarm Trap 
         xldv20TrPAIS TRAP-TYPE
            -- info-TRAPTYPE:  alarm
            -- info-FAILEDSRC: tlm
            -- info-FAILEDOBJ: S1n(= STM-1 NePPTP),S3n
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Alarm indication signal at path. "
            ::= 11

         -- Alarm Trap 
         xldv20TrPRDI TRAP-TYPE
            -- info-TRAPTYPE:  alarm
            -- info-FAILEDSRC: tlm
            -- info-FAILEDOBJ: S1f(= STM-1 FePPTP),S3f
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Remote defect indication at path. "
            ::= 12

         -- Alarm Trap 
         xldv20TrRsExcBER TRAP-TYPE
            -- info-TRAPTYPE:  alarm
            -- info-FAILEDSRC: tlm
            -- info-FAILEDOBJ: S1n(= STM-1 NePPTP),S3n
            -- info-IMPL:    V2.0->
            ENTERPRISE xldv20Traps
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Excessive bit error rate at repeater section. "
            ::= 13

         -- Alarm Trap
         xldv20TrSlm TRAP-TYPE
            -- info-TRAPTYPE:  alarm
            -- info-FAILEDSRC: tlm
            -- info-FAILEDOBJ: S1n(= STM-1 NePPTP),S3n,E3n
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Signal label mismatch. "
            ::= 14

         -- Alarm Trap 
         xldv20TrTim TRAP-TYPE
            -- info-TRAPTYPE:  alarm
            -- info-FAILEDSRC: tlm
            -- info-FAILEDOBJ: S1n(= STM-1 NePPTP),S3n,E3n
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Trace identification mismatch. "
            ::= 15

         -- Alarm Trap
         xldv20TrActFault TRAP-TYPE
            -- info-TRAPTYPE:  alarm
            -- info-FAILEDSRC: tlm
            -- info-FAILEDOBJ: Adc(= Adc-PPTP)
            -- info-IMPL:    V2.0->          
            ENTERPRISE  xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                  " The ADSL C PPTP reports a link activation fault. "
            ::= 16

         -- Alarm Trap 
         xldv20TrReplaceableUnitTypeMismatch TRAP-TYPE
            -- info-TRAPTYPE:  alarm
            -- info-FAILEDSRC: hwm
            -- info-FAILEDOBJ: LU155,LUDSX3,CI,SUAD,SUSDSL
            -- info-FAILEDOBJ: LIETH,LI25,NTAD,
            -- info-FAILEDOBJ: LUIMA
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                  " Trap to indicate that a wrong unit is plugged. "
            ::= 17

         -- Alarm Trap
         xldv20TrReplaceableUnitFailure TRAP-TYPE
            -- info-TRAPTYPE:  alarm
            -- info-FAILEDSRC: hwm
            -- info-FAILEDOBJ: LU155,LUDSX3,LUPON,CI ,SUAD,SUSDSL
            -- info-FAILEDOBJ: LIETH,LI25,NTAD,NTVD,LUIMA
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                  " Indicates a unit Out Of Service. "
            ::= 18

         -- Alarm Trap 
         xldv20TrReplaceableUnitProblem TRAP-TYPE
            -- info-TRAPTYPE:  alarm
            -- info-FAILEDSRC: hwm
            -- info-FAILEDOBJ: LU155,LUDSX3,LUPON,CI,SUAD,SUSDSL
            -- info-FAILEDOBJ: LIETH,LI25,NTAD,LUIMA
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                  " Indicates a unit partly Out Of Service. "
            ::= 19

         -- Alarm Trap
         xldv20TrReplaceableUnitNotInstalled TRAP-TYPE
            -- info-TRAPTYPE:  alarm
            -- info-FAILEDSRC: hwm
            -- info-FAILEDOBJ: LU155,LUDSX3,LUPON,SUAD,SUSDSL
            -- info-FAILEDOBJ: LIETH,LI25,NTAD, LUIMA
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                  " Indicates that the unit is not plugged. "
            ::= 20

         -- Alarm Trap 
         xldv20TrReplaceableUnitSwMismatch TRAP-TYPE
            -- info-TRAPTYPE:  alarm
            -- info-FAILEDSRC: hwm
            -- info-FAILEDOBJ: CI,SUAD,SUSDSL
            -- info-FAILEDOBJ: LIETH,LI25,NTAD
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                  " The SW version in the inventory data mismatches with the
                    configured version in the equipment holder. "
            ::= 21

         -- Event Trap 
         xldv20TrReplaceableUnitReset TRAP-TYPE
            -- info-TRAPTYPE:  event
            -- info-IMPL:    V2.0->          
            ENTERPRISE xldv20Traps 
            VARIABLES { xldv20TvTimeAndDate,
                        xldv20TvRepEntity,
                        xldv20TvRepSource,
                        xldv20TvHweResetType }
            DESCRIPTION
                 " A replaceable unit is performing a reset. "
            ::= 22

         -- Event Trap
         xldv20TrReplaceableUnitResetEnd TRAP-TYPE
            -- info-TRAPTYPE: event
            -- info-IMPL:    V2.0->          
            ENTERPRISE xldv20Traps 
            VARIABLES { xldv20TvTimeAndDate,
                        xldv20TvRepEntity,
                        xldv20TvRepSource }
            DESCRIPTION
                 " A replaceable unit finished a reset. "
            ::= 23

         -- Event Trap 
         xldv20TrStartupEnd TRAP-TYPE
            -- info-TRAPTYPE: event
            -- info-IMPL:    V2.0->          
            ENTERPRISE xldv20Traps 
            VARIABLES { xldv20TvTimeAndDate,
                        xldv20TvStartupResult,
                        xldv20TvStartupType,
                        xldv20TvSnmMibVersion,
                        xldv20TvSnmAgentVersion,
                        xldv20TvVersionNrCmuLoad }
            DESCRIPTION
                 " End of startup. "
            ::= 24

         -- Event Trap 
         xldv20TrLctSession TRAP-TYPE
            -- info-TRAPTYPE: event
            -- info-IMPL:    V2.0->          
            ENTERPRISE xldv20Traps 
            VARIABLES { xldv20TvTimeAndDate,
                        xldv20TvSnmLctSession }
            DESCRIPTION
                 " Event concerning a LCT session . "
            ::= 25

         -- Event Trap 
         xldv20TrSnmAgentRunning TRAP-TYPE
            -- info-TRAPTYPE: event
            -- info-IMPL:    V2.0->          
            ENTERPRISE xldv20Traps 
            VARIABLES { xldv20TvTimeAndDate,
                        xldv20TvSnmMibVersion,
                        xldv20TvSnmAgentVersion }
            DESCRIPTION
                 " SNMP agent is active now. "
            ::= 26

         -- Event Trap
         xldv20TrRstResult TRAP-TYPE
            -- info-TRAPTYPE: event
            -- info-IMPL:    V2.0->          
            ENTERPRISE xldv20Traps 
            VARIABLES { xldv20TvTimeAndDate,
                        xldv20TvRstResult,
                        xldv20TvRepSource,
                        xldv20TvRstHwUnitIndex }
            DESCRIPTION
                 " Result of reset. "
            ::= 27

         -- Event Trap 
         xldv20TrPltTestResult TRAP-TYPE
            -- info-TRAPTYPE: event
            -- info-IMPL:    V2.0->          
            ENTERPRISE xldv20Traps 
            VARIABLES { xldv20TvTimeAndDate,
                        xldv20TvTsrControlStatus }
            DESCRIPTION
                 " Result of loop test. "
            ::= 28

         -- Event Trap 
         xldv20TrStateChangeAdmin TRAP-TYPE
            -- info-TRAPTYPE: event
            -- info-IMPL:    V2.0->          
            ENTERPRISE xldv20Traps 
            VARIABLES { xldv20TvTimeAndDate,
                        xldv20TvRepEntity,
                        xldv20TvRepSource,
                        xldv20TvStcOldAdminStatus,
                        xldv20TvStcNewAdminStatus }
            DESCRIPTION
                 " The administrative state of the reporting entity
                   has changed. "
            ::= 29

         -- Event Trap
         xldv20TrStateChangeOper TRAP-TYPE
            -- info-TRAPTYPE: event
            -- info-IMPL:    V2.0->          
            ENTERPRISE xldv20Traps 
            VARIABLES { xldv20TvTimeAndDate,
                        xldv20TvRepEntity,
                        xldv20TvRepSource,
                        xldv20TvStcOldOperStatus,
                        xldv20TvStcNewOperStatus }
            DESCRIPTION
                 " The operational state of the reporting entity
                   has changed. "
            ::= 30

         -- Event Trap 
         xldv20TrChangeRate TRAP-TYPE
            -- info-TRAPTYPE: event
            -- info-IMPL:    V2.0->          
            ENTERPRISE xldv20Traps 
            VARIABLES { xldv20TvTimeAndDate,
                        xldv20TvAdcControlStatus,
                        xldv20TvRepEntity,
                        xldv20TvRepSource }
            DESCRIPTION
                 " This trap indicates the end of change rate request. "
            ::= 31

         -- Event Trap
         xldv20TrCmuReadyForReset TRAP-TYPE
            -- info-TRAPTYPE: event
            -- info-IMPL:    V2.0->          
            ENTERPRISE xldv20Traps 
            VARIABLES { xldv20TvTimeAndDate }
            DESCRIPTION
                " Indicates upgrade end. Unit is ready for reset. "
            ::= 32

         -- Event Trap
         xldv20TrAltTestResult TRAP-TYPE
            -- info-TRAPTYPE: event
            -- info-IMPL:     V2.0->
            ENTERPRISE xldv20Traps 
            VARIABLES { xldv20TvTimeAndDate,
                        xldv20TvTsrControlStatus }
            DESCRIPTION
                 " Result of ATM loop test. "
            ::= 33

         -- Event Trap 
         xldv20TrActivateLoadResult TRAP-TYPE
            -- info-TRAPTYPE: event
            -- info-IMPL:    V2.0->          
            ENTERPRISE xldv20Traps 
            VARIABLES { xldv20TvTimeAndDate,
                        xldv20TvSucResult,
                        xldv20TvSucUnit,
                        xldv20TvSucHwUnitIndex }
            DESCRIPTION
                  " This trap indicates that a replaceable unit is performing
                    a reset. "
            ::= 34

         -- Event Trap 
         xldv20TrPuUpgradeSucc TRAP-TYPE
            -- info-TRAPTYPE: event
            -- info-IMPL:    V2.0->          
            ENTERPRISE xldv20Traps 
            VARIABLES { xldv20TvTimeAndDate,
                        xldv20TvSucUnit,
                        xldv20TvSucHwUnitIndex,
                        xldv20TvSucVersionNo }
            DESCRIPTION
                 " Upgrade ended successfully. "
            ::= 35

         -- Event Trap 
         xldv20TrUpgradeCancelled TRAP-TYPE
            -- info-TRAPTYPE: event
            -- info-IMPL:    V2.0->          
            ENTERPRISE xldv20Traps 
            VARIABLES { xldv20TvTimeAndDate,
                        xldv20TvSucUnit,
                        xldv20TvSucHwUnitIndex,
                        xldv20TvSucVersionNo,
                        xldv20TvSucResult }
            DESCRIPTION
                 " The upgrade request has been cancelled. "
            ::= 36

         -- Event Trap 
         xldv20TrFtpError TRAP-TYPE
            -- info-TRAPTYPE: event
            -- info-IMPL:    V2.0->          
            ENTERPRISE xldv20Traps 
            VARIABLES { xldv20TvTimeAndDate,
                        xldv20TvSucUnit,
                        xldv20TvSucPathName,
                        xldv20TvSucFileName ,
                        xldv20TvSucResult }
            DESCRIPTION
                  " Sw upgrade reports a problem with FTP. "
            ::= 38

         -- Event Trap 
         xldv20TrSweLogRead TRAP-TYPE
            -- info-TRAPTYPE: event
            -- info-IMPL:    V2.0->          
            ENTERPRISE xldv20Traps 
            VARIABLES { xldv20TvTimeAndDate,
                        xldv20TvDbuSweLogReadResult }
            DESCRIPTION
                 " End of SWE log reading. "
            ::= 40

         -- Event Trap 
         xldv20TrHwmLogRead TRAP-TYPE
            -- info-TRAPTYPE: event
            -- info-IMPL:    V2.0->          
            ENTERPRISE xldv20Traps 
            VARIABLES { xldv20TvTimeAndDate,
                        xldv20TvDbuHwmLogReadResult }
            DESCRIPTION
                 " End of HWM log reading. "
            ::= 41

         -- Event Trap 
         xldv20TrTraceLogRead TRAP-TYPE
            -- info-TRAPTYPE: event
            -- info-IMPL:    V2.0->          
            ENTERPRISE xldv20Traps 
            VARIABLES { xldv20TvTimeAndDate,
                        xldv20TvDbuSwTraceLogReadResult }
            DESCRIPTION
                 " End of trace log reading. "
            ::= 42

                 
         -- This trap delivers the resulting indeces of a VPC creation.
         -- The trap variables are xldv20TvTimeAndDate, the xldv20TvVpiNni value of
         -- the CC, the index xldv20TvVpiNniIndex belonging to the CC of the
         -- AtmCrossConnect Table and the indeces xldv20TvVplTerminationPointA and
         -- xldv20TvVplTerminationPointZ of the VPLs of the VPL table.

         -- Event Trap 
            xldv20TrVplCcCreation TRAP-TYPE
               -- info-TRAPTYPE: event
               -- info-IMPL:    V2.0->          
               ENTERPRISE xldv20Traps 
               VARIABLES { xldv20TvTimeAndDate,
                           xldv20TvVpiNni,
                           xldv20TvVpiNniIndex,
                           xldv20TvVplTerminationPointA,
                           xldv20TvVplTerminationPointZ,
                           xldv20TvEthVpcTpIndex,   
                           xldv20TvEthVccTpIndex,
                           xldv20TvVplTpIndex
                           }
               DESCRIPTION
                     " The resulting indeces of a VPC creation command.  "
               ::= 45

         -- This trap delivers the indeces of a CC, which was deleted.
         -- The trap variables are xldv20TvTimeAndDate, the xldv20TvVpiNni value of
         -- the deleted CC, the index xldv20TvVpiNniIndex belonging to the deleted
         -- CC of the AtmCrossConnect Table and the indeces xldv20TvVplTerminationPointA
         -- and xldv20TvVplTerminationPointZ of the deleted VPLs of the VPL table.

         -- Event Trap 
         xldv20TrVplCcDeletion TRAP-TYPE
            -- info-TRAPTYPE: event
            -- info-IMPL:    V2.0->          
            ENTERPRISE xldv20Traps 
            VARIABLES { xldv20TvTimeAndDate,
                        xldv20TvVpiNni,
                        xldv20TvVpiNniIndex,
                        xldv20TvVplTerminationPointA,
                        xldv20TvVplTerminationPointZ,
                        xldv20TvEthVpcTpIndex,   
                        xldv20TvEthVccTpIndex,
                        xldv20TvVplTpIndex
                        }   
            DESCRIPTION
                  " The resulting indeces of a VPC deletion command. "
            ::= 46

         -- Event Trap 
         xldv20TrObjCreate TRAP-TYPE
            -- info-TRAPTYPE: event
            -- info-IMPL:    V2.0->          
            ENTERPRISE xldv20Traps 
            VARIABLES { xldv20TvTimeAndDate,
                        xldv20TvRepSource,
                        xldv20TvRepEntity,
                        xldv20TvHwUnitType,
                        xldv20TvHwContainingUnitIndex,
                        xldv20TvHwContainedUnitAddr }
            DESCRIPTION
                 " Create object event.
                   The varBinds xldv20TvHwUnitType and xldv20TvHwContainingUnitIndex
                   only occure when xldv20TvRepSource = hwm. "
            ::= 100
 
         -- Event Trap 
        xldv20TrObjDelete TRAP-TYPE
            -- info-TRAPTYPE: event
            -- info-IMPL:    V2.0->          
            ENTERPRISE xldv20Traps 
            VARIABLES { xldv20TvTimeAndDate,
                        xldv20TvRepSource,
                        xldv20TvRepEntity,
                        xldv20TvHwUnitType,
                        xldv20TvHwContainingUnitIndex,
                        xldv20TvHwContainedUnitAddr  }
            DESCRIPTION
                 " Delete object event.
                   The varBinds xldv20TvHwUnitType and xldv20TvHwContainingUnitIndex
                   only occure when xldv20TvRepSource = hwm. "
            ::= 101

         -- Alarm Trap 
         xldv20TrXmissionErr TRAP-TYPE
            -- info-TRAPTYPE:  alarm
            -- info-FAILEDSRC: tlm
            -- info-FAILEDOBJ: Eth
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Transmission Error from LIETH:S. "
            ::= 105

         -- Alarm Trap 
         xldv20TrExternalAlarm TRAP-TYPE
            -- info-TRAPTYPE:  alarm
            -- info-FAILEDSRC: hwm
            -- info-FAILEDOBJ: CI 
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " External alarm. "
            ::= 110

         -- Event Trap 
         -- This trap replaces the xldv20TrSuAd16ReadyForReset trap.
         xldv20TrUnitReadyForReset TRAP-TYPE
            -- info-TRAPTYPE: event
            -- info-IMPL:    V2.0->          
            ENTERPRISE xldv20Traps 
            VARIABLES { xldv20TvTimeAndDate,
                        xldv20TvSucUnit,
                        xldv20TvSucHwUnitIndex,
                        xldv20TvSucVersionNo }
            DESCRIPTION
                 " Indicates upgrade end. Unit is ready for reset. "
            ::= 111

         -- Event Trap 
         xldv20TrHwuControl TRAP-TYPE
            -- info-TRAPTYPE: event
            -- info-IMPL:    V2.0->          
            ENTERPRISE xldv20Traps 
            VARIABLES { xldv20TvTimeAndDate,
                        xldv20TvRepSource,
                        xldv20TvHwuControlResult }
            DESCRIPTION
                 " End of xldv20HwuControlReq. "
            ::= 112

         -- Alarm Trap 
         xldv20TrReplaceableUnitRemoved TRAP-TYPE
            -- info-TRAPTYPE:  alarm
            -- info-FAILEDSRC: hwm
            -- info-FAILEDOBJ: LU155,LUDSX3,CI,SUAD
            -- info-FAILEDOBJ: LIETH,LI25,NTAD
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Replaceable unit removed. "
            ::= 113

         -- Alarm Trap 
         xldv20TrAIS TRAP-TYPE
            -- info-TRAPTYPE:  alarm
            -- info-FAILEDSRC: tlm
            -- info-FAILEDOBJ: E3n,D3n,e1nIma  
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Alarm indication signal at E3/DS3. "
            ::= 114

         -- Alarm Trap 
         xldv20TrRDI TRAP-TYPE
            -- info-TRAPTYPE:  alarm
            -- info-FAILEDSRC: tlm
            -- info-FAILEDOBJ: D3f,E3f, e1fIma  
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Remote defect indication at E3/DS3/dsx1f. "
            ::= 115

         -- Alarm Trap 
         xldv20TrPlcpLof TRAP-TYPE
            -- info-TRAPTYPE:  alarm
            -- info-FAILEDSRC: tlm
            -- info-FAILEDOBJ: D3n
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Loss of Plcp frame at E3/DS3. "
            ::= 116

         -- Alarm Trap 
         xldv20TrPlcpRDI TRAP-TYPE
            -- info-TRAPTYPE:  alarm
            -- info-FAILEDSRC: tlm
            -- info-FAILEDOBJ: D3f
            -- info-FAILEDOBJ: [callp] NePPTP, FePPTP,
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Plcp Remote defect indication at E3/DS3. "
            ::= 117

         -- Event Trap 
         xldv20TrRemInvReady TRAP-TYPE
            -- info-TRAPTYPE: event
            -- info-IMPL:    V2.0->          
            ENTERPRISE xldv20Traps 
            VARIABLES { xldv20TvTimeAndDate,
                        xldv20TvRiRemInvResult }
            DESCRIPTION
                 " Remote inventory ready. "
            ::= 118

         -- Event Trap 
         xldv20TrDbBackup TRAP-TYPE
            -- info-TRAPTYPE: event
            -- info-IMPL:    V2.0->          
            ENTERPRISE xldv20Traps 
            VARIABLES { xldv20TvTimeAndDate,
                        xldv20TvBackupResult }
            DESCRIPTION
                 " Result of Storage of DB. "
            ::= 119

         -- Event Trap 
         xldv20TrSwVersionSet TRAP-TYPE
            -- info-TRAPTYPE: event
            -- info-IMPL:    V2.0->          
            ENTERPRISE xldv20Traps 
            VARIABLES { xldv20TvTimeAndDate,
                        xldv20TvRepSource,
                        xldv20TvRepEntity }
            DESCRIPTION
                 " Equipment holder data updated. "
            ::= 120

         -- Event Trap 
         xldv20TrReadSAPSContentFileReady TRAP-TYPE
            -- info-TRAPTYPE: event
            -- info-IMPL:    V2.0->          
            ENTERPRISE xldv20Traps 
            VARIABLES { xldv20TvTimeAndDate,
                        xldv20TvSucResult }
            DESCRIPTION
                 " End of SAPS content file reading. "
            ::= 121

         -- Alarm Trap 
         xldv20TrReplaceableUnitSwMissing TRAP-TYPE
            -- info-TRAPTYPE:  alarm
            -- info-FAILEDSRC: hwm
            -- info-FAILEDOBJ: SUAD, SUSDSL
            -- info-FAILEDOBJ: LIETH,LI25,NTAD,
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " No SW load found in content file corresponding to mnemo code and
                   FW item number in equipHolder entry. "
            ::= 122

         -- Alarm Trap 
         xldv20TrInternalFault TRAP-TYPE
            -- info-TRAPTYPE:  alarm
            -- info-FAILEDSRC: tlm/hwm
            -- info-FAILEDOBJ: S1n(= STM-1 NePPTP),S1f,S3n,E3n,D3n,S3f,
            -- info-FAILEDOBJ: D3f,E3f,Pon,Adc(= Adc-PPTP),Adr,Vdc,Vdr,
            -- info-FAILEDOBJ: Ibm(= Ibm-PPTP),Eth,Tca,
            -- info-FAILEDOBJ: all HW units
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Internal SW/HW fault. "
            ::= 123

         -- Event Trap 
         xldv20TrVclCcCreation TRAP-TYPE
            -- info-TRAPTYPE: event
            -- info-IMPL:    V2.0->          
            ENTERPRISE xldv20Traps 
            VARIABLES { xldv20TvTimeAndDate,
                        xldv20TvVpiNni,
                        xldv20TvVciNni,
                        xldv20TvVciNniIndex,
                        xldv20TvVclTerminationPointA,
                        xldv20TvVclTerminationPointZ,
                        xldv20TvEthVpcTpIndex,  
                        xldv20TvEthVccTpIndex,
                        xldv20TvVplTpIndex
                        }
            DESCRIPTION
                  " The resulting indeces of a VC CC creation command. "
            ::= 127

         -- Event Trap 
         xldv20TrVclCcDeletion TRAP-TYPE
            -- info-TRAPTYPE: event
            -- info-IMPL:    V2.0->          
            ENTERPRISE xldv20Traps 
            VARIABLES { xldv20TvTimeAndDate,
                        xldv20TvVpiNni,
                        xldv20TvVciNni,
                        xldv20TvVciNniIndex,
                        xldv20TvVclTerminationPointA,
                        xldv20TvVclTerminationPointZ,
                        xldv20TvEthVpcTpIndex,
                        xldv20TvEthVccTpIndex,
                        xldv20TvEthEntryIndex,
                        xldv20TvVplTpIndex
                        }
            DESCRIPTION
                  " The resulting indeces of a VCL CC deletion command. "
            ::= 128

         -- Alarm Trap 
         xldv20TrImmMNR TRAP-TYPE
            -- info-TRAPTYPE:  alarm
            -- info-FAILEDSRC: tlm
            -- info-FAILEDOBJ: Adc(= Adc-PPTP)
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Immediate Margin Not Reached Fault "
            ::= 130

         -- Alarm Trap 
         xldv20TrLpr TRAP-TYPE
            -- info-TRAPTYPE:  alarm
            -- info-FAILEDSRC: tlm
            -- info-FAILEDOBJ: Adr
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Loss of Power (dying gasp) "
            ::= 131
 
         -- Alarm Trap 
         xldv20TrLol TRAP-TYPE
            -- info-TRAPTYPE:  alarm
            -- info-FAILEDSRC: tlm
            -- info-FAILEDOBJ: Adc(= Adc-PPTP)
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Loss of Link (ADC Los without preceding ADR Lpr) "
            ::= 132

         -- This trap indicates mass alarms AIS/RDI/LOC at
         -- VpcTp and VccTp objects. 
         -- These alarms are not logged at TMN-OS. 
         -- Via the xldv20AlmControlReq=startSendingAlarm the DSLAM is requested
         -- to send these alarms.

         -- Alarm Trap 
         xldv20TrAtmLayerMultiAlarm TRAP-TYPE
            -- info-TRAPTYPE:  alarm
            -- info-FAILEDSRC: cp
            -- info-FAILEDOBJ: VpcTp, VccTp,VclTp,VplTp
            -- info-IMPL:    V2.0->          
            ENTERPRISE xldv20Traps 
            VARIABLES { xldv20TvTimeAndDate,
                        xldv20TvAlmNatureOfAlarm,
                        xldv20TvAlmFailedComponentRepSource,
                        xldv20TvAlmSpecProblem,
                        xldv20TvAlmSeverityOfFailure,
                        xldv20TvAlmStatus,
                        xldv20TvAlmPropRepairAction,
                        xldv20TvAlmFailedComponentString
                        }
            DESCRIPTION
                 " Atm Layer Multi Alarm "
            ::= 135

         -- Event Trap 
         xldv20TrTelnetSession TRAP-TYPE
            -- info-TRAPTYPE: event
            -- info-IMPL:    V2.0->          
            ENTERPRISE xldv20Traps 
            VARIABLES { xldv20TvTimeAndDate,
                        xldv20TvTelnetSession,
                        xldv20TvTelnetSessionUser }
            DESCRIPTION
                  " Signalizes an established / stopped telnet session. "
            ::= 136


         -- Event Trap 
         xldv20TrVplCACProblem TRAP-TYPE
            -- info-TRAPTYPE: event
            -- info-IMPL:    V2.0->          
            ENTERPRISE xldv20Traps 
            VARIABLES { xldv20TvTimeAndDate,
                        xldv20TvVpiValue,
                        xldv20TvVplIfIndex,
                        xldv20TvCACProblemType,
                        xldv20TvCACBandwidthUsageUp,
                        xldv20TvCACBandwidthUsageDown
                        }
            DESCRIPTION
                  " Indicates a warning for a resource problem
                    by creating a VplCC.  "
            ::= 137

         -- Event Trap 
         xldv20TrVclCACProblem TRAP-TYPE
            -- info-TRAPTYPE: event
            -- info-IMPL:    V2.0->          
            ENTERPRISE xldv20Traps 
            VARIABLES { xldv20TvTimeAndDate, 
                        xldv20TvVpiValue, 
                        xldv20TvVplIfIndex,
                        xldv20TvVplTpIndex,
                        xldv20TvVciValue, 
                        xldv20TvCACProblemType,
                        xldv20TvCACBandwidthUsageUp,
                        xldv20TvCACBandwidthUsageDown
                        }
            DESCRIPTION
                  " Indicates a warning for a resource problem
                    while creating a VclCC. "
            ::= 139

         -- Alarm Trap 
         xldv20TrWrongServiceConfigData TRAP-TYPE
            -- info-TRAPTYPE:  alarm
            -- info-FAILEDSRC: tlm
            -- info-FAILEDOBJ: Adc(= Adc-PPTP)
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Config Adc Rates out of Range for UDSL. "
            ::= 141

         -- Event Trap 
         xldv20TrReplaceableUnitPlugged TRAP-TYPE
            -- info-TRAPTYPE: event
            -- info-IMPL:    V2.0->          
            ENTERPRISE xldv20Traps 
            VARIABLES { xldv20TvTimeAndDate,
                        xldv20TvRepEntity,
                        xldv20TvRepSource }
            DESCRIPTION
                 " Notification: A PIU has been plugged. "
            ::= 142

         -- Event Trap 
         xldv20TrReplaceableUnitUnplugged TRAP-TYPE
            -- info-TRAPTYPE: event
            -- info-IMPL:    V2.0->          
            ENTERPRISE xldv20Traps 
            VARIABLES { xldv20TvTimeAndDate,
                        xldv20TvRepEntity,
                        xldv20TvRepSource }
            DESCRIPTION
                 " Notification: A PIU has been unplugged. "
            ::= 143

         -- Event Trap 
         xldv20TrStateChangeOperExt TRAP-TYPE
            -- info-TRAPTYPE: event
            -- info-IMPL:    V2.0->          
            ENTERPRISE xldv20Traps 
            VARIABLES { xldv20TvTimeAndDate,
                        xldv20TvRepEntityExt,
                        xldv20TvRepSource,
                        xldv20TvStcOldOperStatus,
                        xldv20TvStcNewOperStatus }
            DESCRIPTION
                 " The operational state of the reporting external entity
                   has changed. "
            ::= 144

         -- Alarm Trap 
         xldv20TrLOC TRAP-TYPE
            -- info-TRAPTYPE:  alarm
            -- info-FAILEDSRC: cp   
            -- info-FAILEDOBJ: VclTp, VplTp
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Loss of continuity. "
            ::= 145


         xldv20TrDbRestore TRAP-TYPE
            -- info-TRAPTYPE:  event
            -- info-IMPL:    V2.0->          
            ENTERPRISE xldv20Traps 
            VARIABLES { xldv20TvTimeAndDate,
                        xldv20TvRestoreResult}
            DESCRIPTION
                 " DB restoration result. "
            ::= 150

         xldv20TrUpgradeEndRequestResult TRAP-TYPE
            -- info-TRAPTYPE:  event
            -- info-IMPL:    V2.0->          
            ENTERPRISE xldv20Traps 
            VARIABLES { xldv20TvTimeAndDate,
                        xldv20TvSucResult}
            DESCRIPTION
                 " Result of sucUpgrEndRequest command. "
            ::= 151
            
         xldv20TrUnitUpgradeNotRequested TRAP-TYPE
            -- info-TRAPTYPE:  event
            -- info-IMPL:    V2.0->          
            ENTERPRISE xldv20Traps 
            VARIABLES { xldv20TvTimeAndDate,
                        xldv20TvSucUnit,
                        xldv20TvSucHwUnitIndex,
                        xldv20TvSucVersionNo }
            DESCRIPTION
                 " Result of sucUpgrEndRequest command. "
            ::= 152

         ------------------------------------------------------------------
         --        XLDV 2.0    T R A P S
         ------------------------------------------------------------------

         -- Event Trap (Introduced for XLDV2.0)        
         xldv20TrVpcTpCreation TRAP-TYPE
            -- info-TRAPTYPE: event
            -- info-IMPL:    V2.0->          
            ENTERPRISE xldv20Traps 
            VARIABLES { xldv20TvTimeAndDate,
                        xldv20TvVpiValue,
                        xldv20TvVpcTpIndex }
            DESCRIPTION
                 " VpcTp created "
            ::= 400 

         -- Event Trap (Introduced for XLDV2.0)        
         xldv20TrVpcTpDeletion TRAP-TYPE
            -- info-TRAPTYPE: event
            -- info-IMPL:    V2.0->          
            ENTERPRISE xldv20Traps 
            VARIABLES { xldv20TvTimeAndDate,
                        xldv20TvVpiValue,
                        xldv20TvVpcTpIndex }
            DESCRIPTION
                 " VpcTp deleted "
            ::= 401

         -- Event Trap (Introduced for XLDV2.0)
         xldv20TrVpcTpCACProblem TRAP-TYPE
            -- info-TRAPTYPE: event
            -- info-IMPL:    V2.0->          
            ENTERPRISE xldv20Traps 
            VARIABLES { xldv20TvTimeAndDate,
                        xldv20TvVpiValue,
                        xldv20TvVpcTpIfIndex,
                        xldv20TvCACProblemType,
                        xldv20TvCACBandwidthUsageUp,
                        xldv20TvCACBandwidthUsageDown
                        }
            DESCRIPTION
                  " Indicates a warning for a resource problem
                    while creating a VpcTP "
            ::= 402

         -- Event Trap 
         xldv20TrContinuityCheckVpEntryCreated TRAP-TYPE
            -- info-TRAPTYPE:  event
            -- info-IMPL:    V2.0->          
            ENTERPRISE xldv20Traps 
            VARIABLES { xldv20TvTimeAndDate,
                        xldv20TvCallpObjectType,
                        xldv20TvIndexSegment,
                        xldv20TvIndexEndToEnd }
            DESCRIPTION
                 " Xldv20ContinuityCheckVpEntry created . "
            ::= 403

         -- Event Trap 
         xldv20TrContinuityCheckVpEntryDeleted TRAP-TYPE
            -- info-TRAPTYPE:  event
            -- info-IMPL:    V2.0->          
            ENTERPRISE xldv20Traps 
            VARIABLES { xldv20TvTimeAndDate,
                        xldv20TvCallpObjectType,
                        xldv20TvIndexSegment,
                        xldv20TvIndexEndToEnd}
            DESCRIPTION
                 " Xldv20ContinuityCheckVpEntry deleted . "
            ::= 404

         -- Event Trap 
         xldv20TrContinuityCheckVcEntryCreated TRAP-TYPE
            -- info-TRAPTYPE:  event
            -- info-IMPL:    V2.0->          
            ENTERPRISE xldv20Traps 
            VARIABLES { xldv20TvTimeAndDate,
                        xldv20TvCallpObjectType,
                        xldv20TvIndexSegment,
                        xldv20TvIndexEndToEnd }
            DESCRIPTION
                 " Xldv20ContinuityCheckVcEntry created . "
            ::= 405

         xldv20TrContinuityCheckVcEntryDeleted TRAP-TYPE
            -- info-TRAPTYPE:  event
            -- info-IMPL:    V2.0->          
            ENTERPRISE xldv20Traps 
            VARIABLES { xldv20TvTimeAndDate,
                        xldv20TvCallpObjectType,
                        xldv20TvIndexSegment,
                        xldv20TvIndexEndToEnd }
            DESCRIPTION
                 " Xldv20ContinuityCheckVcEntry deleted . "
            ::= 406

         -- -------------------------------------------------------------
         --        XLDV 2.0    LUIMA relevant alarm T R A P S
         -- -------------------------------------------------------------

         -- Alarms at dsx1 near-end interface

         -- Alarm Trap 
         xldv20TrExcBER TRAP-TYPE
            -- info-TRAPTYPE:  alarm
            -- info-FAILEDSRC: tm   
            -- info-FAILEDOBJ: e1nIma   
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Excessive Bit Error Ratio at near-end dsx1 PPTP. "
            ::= 407

         -- Alarm Trap 
         xldv20TrLif TRAP-TYPE
            -- info-TRAPTYPE:  alarm
            -- info-FAILEDSRC: tm   
            -- info-FAILEDOBJ: e1nIma   
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Loss of IMA frame at near-end dsx1 PPTP. "
            ::= 408

         -- Alarm Trap 
         xldv20TrLods TRAP-TYPE
            -- info-TRAPTYPE:  alarm
            -- info-FAILEDSRC: tm   
            -- info-FAILEDOBJ: e1nIma   
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Link out of Delay Sychronisation at near-end dsx1 PPTP. "
            ::= 409

         -- Alarms at dsx1 near-end interface

         -- Alarm Trap 
         xldv20TrTxUnusableFe TRAP-TYPE
            -- info-TRAPTYPE:  alarm
            -- info-FAILEDSRC: tm   
            -- info-FAILEDOBJ: e1fIma    
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Tx is unusable at far-end dsx1 PPTP. "
            ::= 410

         -- Alarm Trap 
         xldv20TrRxUnusableFe TRAP-TYPE
            -- info-TRAPTYPE:  alarm
            -- info-FAILEDSRC: tm   
            -- info-FAILEDOBJ: e1fIma  
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Rx is unusable at far-end dsx1 PPTP. "
            ::= 411

         -- Alarm Trap 
         xldv20TrRfiIma TRAP-TYPE
            -- info-TRAPTYPE:  alarm
            -- info-FAILEDSRC: tm   
            -- info-FAILEDOBJ: e1fIma    
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Remote failure indication defect at far-end dsx1 PPTP. "
            ::= 412

         -- Alarm Trap 
         xldv20TrRAI TRAP-TYPE
            -- info-TRAPTYPE:  alarm
            -- info-FAILEDSRC: tm   
            -- info-FAILEDOBJ: d1fIma
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Far-end ds1 IMA PPTP reports remote alarm indication. "
            ::= 413


         -- Alarms at atmIma interface

         xldv20TrStartUpFe TRAP-TYPE
            -- info-TRAPTYPE:  alarm
            -- info-FAILEDSRC: tm   
            -- info-FAILEDOBJ: atmIma
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " IMA group isn't able to finish startup at far-end. " 
            ::= 450
            
         xldv20TrConfigAbort TRAP-TYPE
            -- info-TRAPTYPE:  alarm
            -- info-FAILEDSRC: tm   
            -- info-FAILEDOBJ: atmIma
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Far-end tries to use unacceptable
                 configuration parameter. "
            ::= 451

         xldv20TrConfigAbortFe TRAP-TYPE
            -- info-TRAPTYPE:  alarm
            -- info-FAILEDSRC: tm   
            -- info-FAILEDOBJ: atmIma
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Far-end reports unacceptable
                 configuration parameters. "
            ::= 452

         xldv20TrInsufficientLinks TRAP-TYPE
            -- info-TRAPTYPE:  alarm
            -- info-FAILEDSRC: tm   
            -- info-FAILEDOBJ: atmIma
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " IMA group reports less than minimum number of links are active
		 (detected on far-end). "
            ::= 453
            
         xldv20TrInsufficientLinksFe TRAP-TYPE
            -- info-TRAPTYPE:  alarm
            -- info-FAILEDSRC: tm   
            -- info-FAILEDOBJ: atmIma
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Less than minimum number of links are active for IMA group
                   (detected on far-end). "
            ::= 454

         xldv20TrBlockedFe TRAP-TYPE
            -- info-TRAPTYPE:  alarm
            -- info-FAILEDSRC: tm   
            -- info-FAILEDOBJ: atmIma
            -- info-IMPL:    V2.0->          
            ENTERPRISE xldv20Traps 
            VARIABLES { xldv20TvTimeAndDate,
                        xldv20TvRepEntity,
                        xldv20TvRepSource,
                        xldv20TvAlmSpecProblem,
                        xldv20TvAlmNatureOfAlarm,
                        xldv20TvAlmFailedComponent,
                        xldv20TvAlmFailedComponentRepSource,
                        xldv20TvAlmSeverityOfFailure,
                        xldv20TvAlmStatus,
                        xldv20TvAlmPropRepairAction,
                        xldv20TvAlmSpecProblemText }
            DESCRIPTION
                 " Far-end reports that it is blocked.  "
            ::= 455

         -- Event Trap
         xldv20TrImaMinNumOfLinks TRAP-TYPE
            -- info-TRAPTYPE:  event
            -- info-IMPL:      V2.0->          
            ENTERPRISE xldv20Traps 
            VARIABLES { xldv20TvTimeAndDate,
                        xldv20TvImaSetNumResult
                        }
            DESCRIPTION
                 " Result of imaSetMinNumTxLinks command . "
            ::= 456

         -- Event Trap
         xldv20TrStateChangeAvail TRAP-TYPE
            -- info-TRAPTYPE: event
            -- info-IMPL:    V2.0->          
            ENTERPRISE xldv20Traps 
            VARIABLES { xldv20TvTimeAndDate,
                        xldv20TvRepEntity,
                        xldv20TvRepSource,
                        xldv20TvStcOldAvailStatus,
                        xldv20TvStcNewAvailStatus }
            DESCRIPTION
                 " The availablity state of the reporting entity
                   has changed. "
            ::= 457

END
