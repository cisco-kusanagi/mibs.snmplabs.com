NSCDXCDA-MIB DEFINITIONS ::= BEGIN

-- Title:	NSC DX CDA MIB version 1.2 in concise format
-- Date:	25 January 1995
-- By:		John Lyman <john.lyman@nsco.network.com>

IMPORTS
	OBJECT-TYPE, Counter  
	    FROM RFC1155-SMI
	DisplayString
	    FROM RFC1213-MIB
        nscDx
            FROM NSC-MIB
	TRAP-TYPE
	    FROM RFC-1215;

--
-- CDA
--

nscDxCda OBJECT IDENTIFIER ::= { nscDx 3 }

nscDxCdaTraceInfoTable OBJECT-TYPE
	SYNTAX	SEQUENCE OF NscDxCdaTraceInfoEntry
	ACCESS	not-accessible
	STATUS	mandatory
	DESCRIPTION
		"List of trace information entries."
	::= { nscDxCda 1 }

nscDxCdaTraceInfoEntry OBJECT-TYPE
	SYNTAX	NscDxCdaTraceInfoEntry
	ACCESS	not-accessible
	STATUS	mandatory
	DESCRIPTION
		"Trace information entry."
	INDEX	{ nscDxCdaTraceInfoEntKeyId }
	::= { nscDxCdaTraceInfoTable 1 }

NscDxCdaTraceInfoEntry ::= SEQUENCE {
	nscDxCdaTraceInfoEntKeyId
		INTEGER,
	nscDxCdaTraceInfoEntTraceSeverity
		INTEGER,
	nscDxCdaTraceInfoEntTraceFacilityMask
		INTEGER,
	nscDxCdaTraceInfoEntTrapSeverity
		INTEGER,
	nscDxCdaTraceInfoEntTrapFacilityMask
		INTEGER,
	nscDxCdaTraceInfoEntFacility
		INTEGER,
	nscDxCdaTraceInfoEntSeverity
		INTEGER,
	nscDxCdaTraceInfoEntMsgnum
		INTEGER,
	nscDxCdaTraceInfoEntTimestamp
		Counter,
	nscDxCdaTraceInfoEntMsg
		DisplayString
}

nscDxCdaTraceInfoEntKeyId OBJECT-TYPE
	SYNTAX	INTEGER (0..'F'h)
	ACCESS	read-only
	STATUS	mandatory
	DESCRIPTION
		"Processor Key ID (KID). This is a unique
		value for each interface."
	::= { nscDxCdaTraceInfoEntry 1 }

nscDxCdaTraceInfoEntTraceSeverity OBJECT-TYPE
	SYNTAX	INTEGER (0..15)
	ACCESS	read-write
	STATUS	mandatory
	DESCRIPTION
		"Trace buffer severity level.  Higher numbers indicate that
		the message is more important than lower numbers."
	::= { nscDxCdaTraceInfoEntry 2 }

nscDxCdaTraceInfoEntTraceFacilityMask OBJECT-TYPE
	SYNTAX	INTEGER
	ACCESS	read-write
	STATUS	mandatory
	DESCRIPTION
		"Bit mask of trace facilities enabled.  Facilities available:
			Executive    (0x00000001),
			Console      (0x00000002),
			Packets      (0x00000004),
			Bridge       (0x00000008),
			LocalIP      (0x00000010),
			Dlcx	     (0x00000020),
			Xport        (0x00020000),
			Session      (0x00040000),
			Device       (0x00080000),
			Bus&tag      (0x00100000),
			Escon        (0x00200000),
			Greenline    (0x00400000),
			Ho15         (0x00800000),
			Isr          (0x01000000),
			All	     (0xffffffff),
			None         (0x0)"
	::= { nscDxCdaTraceInfoEntry 3 }

nscDxCdaTraceInfoEntTrapSeverity OBJECT-TYPE
	SYNTAX	INTEGER (0..15)
	ACCESS	read-write
	STATUS	mandatory
	DESCRIPTION
		"Trap severity level.  Higher numbers indicate that
		the message is more important than lower numbers."
	::= { nscDxCdaTraceInfoEntry 4 }

nscDxCdaTraceInfoEntTrapFacilityMask OBJECT-TYPE
	SYNTAX	INTEGER
	ACCESS	read-write
	STATUS	mandatory
	DESCRIPTION
		"Bit mask of trap facilities enabled.  Facilities available:
			Executive    (0x00000001),
			Console      (0x00000002),
			Packets      (0x00000004),
			Bridge       (0x00000008),
			LocalIP      (0x00000010),
			Dlcx	     (0x00000020),
			Xport        (0x00020000),
			Session      (0x00040000),
			Device       (0x00080000),
			Bus&tag      (0x00100000),
			Escon        (0x00200000),
			Greenline    (0x00400000),
			Ho15         (0x00800000),
			Isr          (0x01000000),
			All	     (0xffffffff),
			None         (0x0)"
	::= { nscDxCdaTraceInfoEntry 5 }

nscDxCdaTraceInfoEntFacility OBJECT-TYPE
	SYNTAX	INTEGER {
		    executive (0),
		    console (1),
		    packets (2),
		    bridge (3),
		    localip (4),
		    dlcx (5),
		    xport (17),
		    session (18),
		    device (19),
		    bus-tag (20),
		    escon (21),
		    greenline (22),
		    ho15 (23),
		    isr (24)
		}
	ACCESS	read-only
	STATUS	mandatory
	DESCRIPTION
		"Facility (activity in progress) of last trace/trap."
	::= { nscDxCdaTraceInfoEntry 6 }

nscDxCdaTraceInfoEntSeverity OBJECT-TYPE
	SYNTAX	INTEGER (0..15)
	ACCESS	read-only
	STATUS	mandatory
	DESCRIPTION
		"Severity of last trace/trap.  Higher numbers indicate that
		the message is more important than lower numbers."
	::= { nscDxCdaTraceInfoEntry 7 }

nscDxCdaTraceInfoEntMsgnum OBJECT-TYPE
	SYNTAX	INTEGER
	ACCESS	read-only
	STATUS	mandatory
	DESCRIPTION
		"Message number representing the last trace/trap."
	::= { nscDxCdaTraceInfoEntry 8 }

nscDxCdaTraceInfoEntTimestamp OBJECT-TYPE
	SYNTAX	Counter
	ACCESS	read-only
	STATUS	mandatory
	DESCRIPTION
		"Timestamp of last trace/trap.  This value is an unsigned 32 bit
		integer which wraps when it reaches it highest value.  The speed
		that the count changes is board dependent, but it is usually the
		processor clock speed."
	::= { nscDxCdaTraceInfoEntry 9 }

nscDxCdaTraceInfoEntMsg OBJECT-TYPE
	SYNTAX	DisplayString (SIZE (0..255))
	ACCESS	read-only
	STATUS	mandatory
	DESCRIPTION
		"Ascii string of last trace/trap."
	::= { nscDxCdaTraceInfoEntry 10 }



nscDxCdaTraceTable OBJECT-TYPE
	SYNTAX	SEQUENCE OF NscDxCdaTraceEntry
	ACCESS	not-accessible
	STATUS	mandatory
	DESCRIPTION
		"List of trace entries."
	::= { nscDxCda 2 }

nscDxCdaTraceEntry OBJECT-TYPE
	SYNTAX	NscDxCdaTraceEntry
	ACCESS	not-accessible
	STATUS	mandatory
	DESCRIPTION
		"Trace entry."
	INDEX	{ nscDxCdaTraceEntKeyId, nscDxCdaTraceEntNum }
	::= { nscDxCdaTraceTable 1 }

NscDxCdaTraceEntry ::= SEQUENCE {
	nscDxCdaTraceEntKeyId
		INTEGER,
	nscDxCdaTraceEntNum
		INTEGER,
	nscDxCdaTraceEntFacility
		INTEGER,
	nscDxCdaTraceEntSeverity
		INTEGER,
	nscDxCdaTraceEntMsgnum
		INTEGER,
	nscDxCdaTraceEntTimestamp
		Counter,
	nscDxCdaTraceEntMsg
		DisplayString
}

nscDxCdaTraceEntKeyId OBJECT-TYPE
	SYNTAX	INTEGER (0..'F'h)
	ACCESS	read-only
	STATUS	mandatory
	DESCRIPTION
		"Processor Key ID (KID). This is a unique
		value for each interface."
	::= { nscDxCdaTraceEntry 1 }

nscDxCdaTraceEntNum OBJECT-TYPE
	SYNTAX	INTEGER
	ACCESS	read-only
	STATUS	mandatory
	DESCRIPTION
		"Trace entry number."
	::= { nscDxCdaTraceEntry 2 }

nscDxCdaTraceEntFacility OBJECT-TYPE
	SYNTAX	INTEGER {
		    executive (0),
		    console (1),
		    packets (2),
		    bridge (3),
		    localip (4),
		    dlcx (5),
		    xport (17),
		    session (18),
		    device (19),
		    bus-tag (20),
		    escon (21),
		    greenline (22),
		    ho15 (23),
		    isr (24)
		}
	ACCESS	read-only
	STATUS	mandatory
	DESCRIPTION
		"Facility of this trace message."
	::= { nscDxCdaTraceEntry 3 }

nscDxCdaTraceEntSeverity OBJECT-TYPE
	SYNTAX	INTEGER (0..15)
	ACCESS	read-only
	STATUS	mandatory
	DESCRIPTION
		"Severity of this trace message.  Higher numbers indicate that
		the message is more important than lower numbers."
	::= { nscDxCdaTraceEntry 4 }

nscDxCdaTraceEntMsgnum OBJECT-TYPE
	SYNTAX	INTEGER
	ACCESS	read-only
	STATUS	mandatory
	DESCRIPTION
		"Message number representing this trace message."
	::= { nscDxCdaTraceEntry 5 }

nscDxCdaTraceEntTimestamp OBJECT-TYPE
	SYNTAX	Counter
	ACCESS	read-only
	STATUS	mandatory
	DESCRIPTION
		"Timestamp of last trace/trap.  This value is an unsigned 32 bit
		integer which wraps when it reaches it highest value.  The speed
		that the count changes is board dependent, but it is usually the
		processor clock speed."
	::= { nscDxCdaTraceEntry 6 }

nscDxCdaTraceEntMsg OBJECT-TYPE
	SYNTAX	DisplayString (SIZE (0..255))
	ACCESS	read-only
	STATUS	mandatory
	DESCRIPTION
		"Ascii string of this trace message."
	::= { nscDxCdaTraceEntry 7 }


nscDxCdaProfilesTable OBJECT-TYPE
	SYNTAX	SEQUENCE OF NscDxCdaProfilesEntry
	ACCESS	not-accessible
	STATUS	mandatory
	DESCRIPTION
		"List of profile entries."
	::= { nscDxCda 3 }

nscDxCdaProfilesEntry OBJECT-TYPE
	SYNTAX	NscDxCdaProfilesEntry
	ACCESS	not-accessible
	STATUS	mandatory
	DESCRIPTION
		"Profile entry."
	INDEX	{ nscDxCdaProfilesEntKeyId }
	::= { nscDxCdaProfilesTable 1 }

NscDxCdaProfilesEntry ::= SEQUENCE {
	nscDxCdaProfilesEntKeyId
		INTEGER,
	nscDxCdaProfilesEntDateWritten
		INTEGER,
	nscDxCdaProfilesEntTimeWritten
		INTEGER,
	nscDxCdaProfilesEntName
		DisplayString,
	nscDxCdaProfilesEntSaveProfiles
		INTEGER,
	nscDxCdaProfilesEntProcessorSpecific
		OBJECT IDENTIFIER
}

nscDxCdaProfilesEntKeyId OBJECT-TYPE
	SYNTAX	INTEGER (0..'F'h)
	ACCESS	read-only
	STATUS	mandatory
	DESCRIPTION
		"Processor Key ID (KID). This is a unique
		value for each interface."
	::= { nscDxCdaProfilesEntry 1 }

nscDxCdaProfilesEntDateWritten OBJECT-TYPE
	SYNTAX	INTEGER
	ACCESS	read-only
	STATUS	mandatory
	DESCRIPTION
		"The date that the profiles were last saved.  The date is
		stored with the high order (first) byte zero, the second byte
		is the month, the third byte is the day and the low order
		(fourth) byte is the year.  Each byte is stored as two, four
		bit decimal digits (BCD).  For example the value 0x11
		represents 11 in decimal."
	::= { nscDxCdaProfilesEntry 2 }

nscDxCdaProfilesEntTimeWritten OBJECT-TYPE
	SYNTAX	INTEGER
	ACCESS	read-only
	STATUS	mandatory
	DESCRIPTION
		"The time that the profiles were last saved.  The time is
		stored with the high order (first) byte zero, the second byte
		is the hour, the third byte is the minute and the low order
		(fourth) byte is the second.  Each byte is stored as two, four
		bit decimal digits (BCD).  For example the value 0x53
		represents 53 in decimal."
	::= { nscDxCdaProfilesEntry 3 }

nscDxCdaProfilesEntName OBJECT-TYPE
	SYNTAX	DisplayString (SIZE (0..255))
	ACCESS	read-write
	STATUS	mandatory
	DESCRIPTION
		"Console name displayed in console prompt."
	::= { nscDxCdaProfilesEntry 4 }

nscDxCdaProfilesEntSaveProfiles OBJECT-TYPE
	SYNTAX	INTEGER {
		    modified(1),
		    up-to-date(2)
		}
	ACCESS	read-write
	STATUS	mandatory
	DESCRIPTION
		"Toggle switch to save profiles in eeprom."
	::= { nscDxCdaProfilesEntry 5 }

nscDxCdaProfilesEntProcessorSpecific OBJECT-TYPE
	SYNTAX	OBJECT IDENTIFIER
	ACCESS	read-only
	STATUS	mandatory
	DESCRIPTION
		"A reference to MIB definitions specific to the
		particular processor being used to realize the interface.
		If this information is not present, its value should
		be set to the OBJECT IDENTIFIER { 0 0 }, which is
		a syntatically valid object identifier, and any
		conformant implementation of ASN.1 and BER must be
		able to generate and recognize this value."
	::= { nscDxCdaProfilesEntry 6 }

nscDxTrace TRAP-TYPE
	ENTERPRISE  nscDx 
	VARIABLES {
		nscDxCdaTraceInfoEntKeyId,
		nscDxCdaTraceInfoEntFacility,
		nscDxCdaTraceInfoEntSeverity,
		nscDxCdaTraceInfoEntMsgnum,
		nscDxCdaTraceInfoEntTimestamp,
		nscDxCdaTraceInfoEntMsg
		}
	DESCRIPTION
		"The nscDxTrace event is generated when a trace message is
		generated with (1) severity greater or equal to the trap
		severity and (2) facility included in the trap faclility."
	::= 1

END
