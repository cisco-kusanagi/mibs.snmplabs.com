CPQDCEO-MIB DEFINITIONS ::= BEGIN

IMPORTS
    compaq        FROM CPQHOST-MIB
--    enterprises   FROM RFC1155-SMI
--    IpAddress     FROM RFC1155-SMI
    TimeTicks     FROM RFC1155-SMI
    Gauge         FROM RFC1155-SMI
    Counter       FROM RFC1155-SMI
    DisplayString FROM RFC1213-MIB
    ifIndex       FROM RFC1213-MIB
    ifDescr       FROM RFC1213-MIB
    sysName       FROM RFC1213-MIB
    sysDescr      FROM RFC1213-MIB
    sysContact    FROM RFC1213-MIB
    sysLocation   FROM RFC1213-MIB  
    OBJECT-TYPE   FROM RFC-1212
    TRAP-TYPE     FROM RFC-1215;

-- compaq                  OBJECT IDENTIFIER       ::= { enterprises 232 }
cpqDceo                 OBJECT IDENTIFIER       ::= { compaq 173 }

environmentalDevice     OBJECT IDENTIFIER       ::= { cpqDceo 1 }

dceoTrapInfo            OBJECT IDENTIFIER       ::= { environmentalDevice 1 }  

--
-- dceoTrapInfo                OBJECT IDENTIFIER       ::= { environmentalDevice 1 }
-- trap information group
--

trapDescription OBJECT-TYPE
	SYNTAX DisplayString (SIZE (0..255))
	ACCESS read-only
	STATUS mandatory
	DESCRIPTION
		"A string identifying the event for that last trap that was sent."
	::= { dceoTrapInfo 1 }

trapDeviceDetails OBJECT-TYPE
	SYNTAX DisplayString (SIZE (0..255))
	ACCESS read-only
	STATUS mandatory
	DESCRIPTION
		"A string details information about the device, including rack name, 
		 basestation unique ID, PAN ID, sensor location, sensor temperature, etc...."
	::= { dceoTrapInfo 2 }

trapDeviceMgmtUrl OBJECT-TYPE
	SYNTAX DisplayString (SIZE (0..255))
	ACCESS read-only
	STATUS mandatory
	DESCRIPTION
	    "A string contains the URL for the management software."
	::= { dceoTrapInfo 3 }

--
-- Dceo Trap Definition
--
trapDceoHighPriority TRAP-TYPE
	ENTERPRISE cpqDceo
	VARIABLES  { sysName, 
	             trapDescription, 
	             trapDeviceDetails, 
	             trapDeviceMgmtUrl }
	DESCRIPTION
        "A high priority alert has occurred. Action: Check the Trap Details for more information."
    --#TYPE      "High Priority Alert"
    --#SEVERITY  Critical
    --#CATEGORY  "Cpqdceo"
        ::= 1

trapDceoMediumPriority TRAP-TYPE
	ENTERPRISE cpqDceo
	VARIABLES  { sysName,
	             trapDescription, 
	             trapDeviceDetails, 
	             trapDeviceMgmtUrl }
	DESCRIPTION
        "A medium priority alert has occurred. Action: Check the Trap Details for more information."
    --#TYPE      "Medium Priority Alert"
    --#SEVERITY  Major
    --#CATEGORY  "Cpqdceo"
	::= 2

trapDceoLowPriority TRAP-TYPE
	ENTERPRISE cpqDceo
	VARIABLES  { sysName, 
	             trapDescription, 
	             trapDeviceDetails, 
	             trapDeviceMgmtUrl }
	DESCRIPTION
        "A low priority alert has occurred. Action: Check the Trap Details for more information."
    --#TYPE      "Low Priority Alert"
    --#SEVERITY  Minor
    --#CATEGORY  "Cpqdceo"
	::= 3

END
