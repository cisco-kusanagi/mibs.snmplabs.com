-- 
-- Copyright 1999 by Fore Systems, Inc. 
-- Converted to SMIv2 rfc 2578,2579,2580 - STD 58
--
-- Copyright 1996 by Fore Systems, Inc.

Fore-TCM-MIB DEFINITIONS ::= BEGIN

IMPORTS
	Counter32, Gauge32, IpAddress,
	TimeTicks, Integer32,
	OBJECT-TYPE,
	NOTIFICATION-TYPE,
	MODULE-IDENTITY				FROM SNMPv2-SMI
	DateAndTime,
	TimeInterval,
	DisplayString, PhysAddress		FROM SNMPv2-TC
	EntryStatus,
	hardware,
	atmSwitch				FROM Fore-Common-MIB
	trapLogIndex				FROM Fore-TrapLog-MIB;

-----------
--
--  The Timing Control Module (TCM) is composed of two subsystems:
--  (1) the External Synchronization Interface (ESI), which provides
--  the timing control functionality, and (2) Extended Control Processor,
--  which performs housekeepping functions for the ESI and environmental
--  monitoring and alarming for the switch enclosure, and provides a
--  single point of IP connectivity for the switch enclosure.
--
--  The TCM MIB is likewise divided along these lines:  an ECP section
--  followed by an ESI section.
--  
-----------

-----------
--  ECP Definitions
-----------

ecpStationModule MODULE-IDENTITY
          LAST-UPDATED         "9911050000Z"
          ORGANIZATION         "FORE"
          CONTACT-INFO         
               "      Postal:   FORE Systems Inc.
                                 1000 FORE Drive
                                 Warrendale, PA 15086-7502
                       Tel:      +1 724 742 6900
                       Email:    nm_mibs@fore.com
                       Web:      http://www.fore.com"
          DESCRIPTION
	      "The Timing Control Module (TCM)."
    ::= { hardware 7 }

ecpHardware		OBJECT IDENTIFIER ::= { ecpStationModule 1 }
ecpSoftware		OBJECT IDENTIFIER ::= { ecpStationModule 2 }
ecpSwMainGroup		OBJECT IDENTIFIER ::= { ecpSoftware 1 }
ecpIpGroup		OBJECT IDENTIFIER ::= { ecpSoftware 2 }

ecpEnvironment		OBJECT IDENTIFIER ::= { ecpHardware 3 }
ecpAlarmGroup		OBJECT IDENTIFIER ::= { ecpEnvironment 1 }
--  ecpPowerGroup	OBJECT IDENTIFIER ::= { ecpEnvironment 2 }
--  ecpFansGroup	OBJECT IDENTIFIER ::= { ecpEnvironment 3 }
--  ecpTempGroup	OBJECT IDENTIFIER ::= { ecpEnvironment 4 }
--  ecpCpuGroup		OBJECT IDENTIFIER ::= { ecpEnvironment 5 }
--  ecpMgmtGroup	OBJECT IDENTIFIER ::= { ecpEnvironment 6 }
--  ecpFabricGroup	OBJECT IDENTIFIER ::= { ecpEnvironment 7 }

ecpSnmp			OBJECT IDENTIFIER ::= { ecpSoftware 3 }
ecpTrapConfGroup	OBJECT IDENTIFIER ::= { ecpSnmp 1 }
--  ecpSnmpConfGroup	OBJECT IDENTIFIER ::= { ecpSnmp 2 }

-----------
--  ESI Definitions
-----------

esiCard			OBJECT IDENTIFIER ::= { hardware 8 }
esiHardware		OBJECT IDENTIFIER ::= { esiCard 1 }
esiSoftware		OBJECT IDENTIFIER ::= { esiCard 2 }

--
--  ESI Reference Sources
--

EsiReferenceSource ::= INTEGER {
			fab1Pri(1),
			fab1Sec(2),
			fab2Pri(3),
			fab2Sec(4),
			fab3Pri(5),
			fab3Sec(6),
			fab4Pri(7),
			fab4Sec(8),
			bits1(9),
			bits2(10)
			-- freerun(11)
			}

------------

------------
--  ECP Hardware Definitions
------------

ecpBoardTable   OBJECT-TYPE
	SYNTAX	SEQUENCE OF EcpBoardEntry
	MAX-ACCESS	not-accessible
	STATUS	current
	DESCRIPTION
		"This table contains Extended Control Processor (ECP)
		board information."
	::= { ecpHardware 1 }

ecpBoardEntry   OBJECT-TYPE
	SYNTAX	EcpBoardEntry
	MAX-ACCESS	not-accessible
	STATUS	current
	DESCRIPTION
		"This entry contains Extended Control Processor (ECP)
		board information"
	INDEX	{ ecpBoardIndex }
	::= { ecpBoardTable 1 }

EcpBoardEntry  ::= SEQUENCE {
		ecpBoardIndex			INTEGER,
		ecpBoardVersion			Integer32,
		ecpBoardSerialNumber		Integer32,
		ecpBoardOtherEcpPresent		INTEGER,
		ecpBoardEsiPresent		INTEGER
	}

ecpBoardIndex   OBJECT-TYPE
	SYNTAX	INTEGER {
			slotX(1),
			slotY(2)
		}
	MAX-ACCESS	read-only
	STATUS	current
	DESCRIPTION
		"This is the Extended Control Processor board index
		within the management station."
	::= { ecpBoardEntry 1 }

ecpBoardVersion OBJECT-TYPE
	SYNTAX	Integer32
	MAX-ACCESS	read-only
	STATUS	current
	DESCRIPTION
		"This is the version number of this Extended Control
		Processor (ECP) board."
	::= { ecpBoardEntry 2 }

ecpBoardSerialNumber OBJECT-TYPE
	SYNTAX	Integer32
	MAX-ACCESS	read-only
	STATUS	current
	DESCRIPTION
		"This is the serial number of this Extended Control
		Processor (ECP) board."
	::= { ecpBoardEntry 3 }

ecpBoardOtherEcpPresent  OBJECT-TYPE
	SYNTAX	INTEGER {
			ecpPresent(1),
			ecpAbsent(2)
		}
	MAX-ACCESS	read-only
	STATUS	current
	DESCRIPTION
		"This is the other ECP board present indicator for this
		Extended Control Processor (ECP) board."
	::= { ecpBoardEntry 4 }

ecpBoardEsiPresent  OBJECT-TYPE
	SYNTAX	INTEGER {
			esiPresent(1),
			esiAbsent(2)
		}
	MAX-ACCESS	read-only
	STATUS	current
	DESCRIPTION
		"This is the External Synchronization Interface (ESI) present
		indicator for this Extended Control Processor (ECP) board."
	::= { ecpBoardEntry 5 }

------------
--  ECP Serial Interface Definitions
------------

ecpSerialIfTable  OBJECT-TYPE
	SYNTAX	SEQUENCE OF EcpSerialIfEntry
	MAX-ACCESS	not-accessible
	STATUS	current
	DESCRIPTION
		"This table contains the serial port interface information
		for the Extended Control Processor (ECP) board."
	::= { ecpHardware 2 }

ecpSerialIfEntry  OBJECT-TYPE
	SYNTAX	EcpSerialIfEntry
	MAX-ACCESS	not-accessible
	STATUS	current
	DESCRIPTION
		"This entry contains the serial port interface information
		for the Extended Control Processor (ECP) board."
	INDEX	{ ecpBoardIndex, ecpSerialIfPortIndex }
	::= { ecpSerialIfTable 1 }

EcpSerialIfEntry ::= SEQUENCE {
		ecpSerialIfPortIndex		Integer32,
		ecpSerialIfPortType		INTEGER,
		ecpSerialIfPortSpeed		Integer32,
		ecpSerialIfFlowType		INTEGER,
		ecpSerialIfPortBits		Integer32,
		ecpSerialIfPortStopBits		INTEGER,
		ecpSerialIfPortParity		INTEGER
	}

ecpSerialIfPortIndex  OBJECT-TYPE
	SYNTAX	Integer32
	MAX-ACCESS	read-only
	STATUS	current
	DESCRIPTION
		"This is the serial port interface index for this port on
		the Extended Control Processor (ECP) board."
	::= { ecpSerialIfEntry 1 }

ecpSerialIfPortType  OBJECT-TYPE
	SYNTAX	INTEGER {
		other(1),
		rs232(2),
		rs422(3),
		rs423(4),
		v35(5),
		x21(6)
	}
	MAX-ACCESS	read-only
	STATUS	current
	DESCRIPTION
		"This is the serial port interface type for this port on
		the Extended Control Processor (ECP) board."
	::= { ecpSerialIfEntry 2 }

ecpSerialIfPortSpeed  OBJECT-TYPE
	SYNTAX	Integer32
	MAX-ACCESS	read-only
	STATUS	current
	DESCRIPTION
		"This is the serial port interface speed for this port on
		the Extended Control Processor (ECP) board."
	::= { ecpSerialIfEntry 3 }

ecpSerialIfFlowType  OBJECT-TYPE
	SYNTAX	INTEGER {
		none(1),
		ctsRts(2),
		dsrDtr(3)
	}
	MAX-ACCESS	read-only
	STATUS	current
	DESCRIPTION
		"This is the serial port interface flow control for this
		port on the Extended Control Processor (ECP) board."
	::= { ecpSerialIfEntry 4 }

ecpSerialIfPortBits  OBJECT-TYPE
	SYNTAX	Integer32
	MAX-ACCESS	read-only
	STATUS	current
	DESCRIPTION
		"This is the serial port interface character size for this
		port on the Extended Control Processor (ECP) board."
	::= { ecpSerialIfEntry 5 }

ecpSerialIfPortStopBits  OBJECT-TYPE
	SYNTAX	INTEGER {
		one(1),
		two(2),
		oneAndHalf(3),
		dynamic(4)
	}
	MAX-ACCESS	read-only
	STATUS	current
	DESCRIPTION
		"This is the serial port interface stop bit count for this
		port on the Extended Control Processor (ECP) board."
	::= { ecpSerialIfEntry 6 }

ecpSerialIfPortParity  OBJECT-TYPE
	SYNTAX	INTEGER {
		none(1),
		odd(2),
		even(3),
		mark(4),
		space(5)
	}
	MAX-ACCESS	read-only
	STATUS	current
	DESCRIPTION
		"This is the serial port interface character parity for this
		port on the Extended Control Processor (ECP) board."
	::= { ecpSerialIfEntry 7 }

-----------
--  ECP Environmental Variables
-----------

------------------------------------------------------------------------
-- The ECP Alarm Group

ecpAlarmTable OBJECT-TYPE
	SYNTAX	SEQUENCE OF EcpAlarmEntry
	MAX-ACCESS	not-accessible
	STATUS	current
	DESCRIPTION
		"A table of switch alarm definitions and configuration."
	::= { ecpAlarmGroup 1 }

ecpAlarmEntry OBJECT-TYPE
	SYNTAX	EcpAlarmEntry
	MAX-ACCESS	not-accessible
	STATUS	current
	DESCRIPTION
		"A table entry containing switch alarm definitions."
	INDEX	{ ecpBoardIndex, ecpAlarmType }
	::= { ecpAlarmTable 1 }

EcpAlarmEntry ::=
	SEQUENCE {
		ecpAlarmType		INTEGER,
		ecpAlarmStatus		INTEGER,
		ecpAlarmMinorCategory	INTEGER,
		ecpAlarmMajorCategory	INTEGER,
		ecpAlarmReset		Integer32
	}

ecpAlarmType OBJECT-TYPE
	SYNTAX INTEGER {
			powerSupplyInputFailed(1),
			powerSupplyOutputFailed(2),
			fanBankFailed(3),
			tempSensorOverTemp(4),
			linkFailed(5),
			spansFailed(6),
			powerSupplyOverCurrent(7),
			powerSupply5VoltFailed(8),
                        faultyOrMissingStandbyTcm(9),
                        esiLossOfSyncSrc(10)
		}
	MAX-ACCESS 	read-only
	STATUS 	current
	DESCRIPTION
		"The type of the alarm."
	::= { ecpAlarmEntry 1 }

ecpAlarmStatus OBJECT-TYPE
	SYNTAX	INTEGER {
			active(1),
			inactive(2)
		}
	MAX-ACCESS 	read-only
	STATUS	current
	DESCRIPTION
		"The status of this alarm entry. An alarm becomes
		active if the underlying condition is detected.
		For power supplies, the input failed alarm condition
		is asserted if the input voltage is not within
		the nominal range for the supply. This does not 
		necessarily mean that an ouput failure will result.
		A power supply output failure condition is asserted
		if any power supply is failing or if it is physically
		removed. Power supply output alarms are only applicable
		to switches with multiple power supplies. Fan bank
		and temperature sensor failures are applicable only
		to switches with the appropriate sensing capabilities.
		Link and spans failures are applicable to all switches."
	::= { ecpAlarmEntry 2 }

ecpAlarmMinorCategory OBJECT-TYPE
	SYNTAX	INTEGER {
			enabled(1),
			disabled(2)
		}
	MAX-ACCESS 	read-write
	STATUS	current
	DESCRIPTION
		"This object indicates whether a minor alarm is triggered
		when this event occurs."
	::= { ecpAlarmEntry 3 }

ecpAlarmMajorCategory OBJECT-TYPE
	SYNTAX	INTEGER {
			enabled(1),
			disabled(2)
		}
	MAX-ACCESS 	read-write
	STATUS	current
	DESCRIPTION
		"This object indicates whether a major alarm is triggered
		when this event occurs."
	::= { ecpAlarmEntry 4 }

ecpAlarmReset OBJECT-TYPE
	SYNTAX Integer32
	MAX-ACCESS read-write
	STATUS current
	DESCRIPTION
		"The manager may set this to the value zero to cancel
		 a current alarm. This is useful for silencing alarms
		 triggered via edge detection. If this variable is
	 	 readable, then the alarm is resettable."
	::= { ecpAlarmEntry 5 }

------------------------------------------------------------------------

ecpAlarmMajorRelayState OBJECT-TYPE
	SYNTAX	INTEGER {
			on(1),
			off(2)
		}
	MAX-ACCESS	read-only
	STATUS	current
	DESCRIPTION
		"This object indicates the current state of the major alarm 
		relay. If one or more of the alarms (ecpAlarmType) that are 
		defined major (ecpAlarmMajorCategory) are currently active 
		(ecpAlarmStatus), this object will be on(1)."
	::= { ecpAlarmGroup 2 }


ecpAlarmMinorRelayState OBJECT-TYPE
	SYNTAX	INTEGER {
			on(1),
			off(2)
		}
	MAX-ACCESS	read-only
	STATUS	current
	DESCRIPTION
		"This object indicates the current state of the minor alarm 
		relay. Ifone or mote of the alarms (ecpAlarmType) that are 
		defined minor (ecpAlarmMinorCategory) are currently active 
		(ecpAlarmStatus), this object will be on(1)."
	::= { ecpAlarmGroup 3 }

------------------------------------------------------------------------

ecpAlarmRelayTable  OBJECT-TYPE
	SYNTAX	SEQUENCE OF EcpAlarmRelayEntry
	MAX-ACCESS	not-accessible
	STATUS	current
	DESCRIPTION
		"This table contains the alarm relay definitions for the 
		Extended Control Processor (ECP) board."
	::= { ecpAlarmGroup 4 }

ecpAlarmRelayEntry  OBJECT-TYPE
	SYNTAX	EcpAlarmRelayEntry
	MAX-ACCESS	not-accessible
	STATUS	current
	DESCRIPTION
		"This entry contains the alarm relay definitions for the 
		Extended Control Processor (ECP) board."
	INDEX	{ ecpBoardIndex, ecpAlarmRelayIndex }
	::= { ecpAlarmRelayTable 1 }

EcpAlarmRelayEntry ::=
	SEQUENCE {
		ecpAlarmRelayIndex	Integer32,
		ecpAlarmRelayFunction	INTEGER,
		ecpAlarmRelayState	INTEGER
	}

ecpAlarmRelayIndex  OBJECT-TYPE
	SYNTAX	Integer32
	MAX-ACCESS	read-only
	STATUS	current
	DESCRIPTION
		"This is the index of the alarm relay on the Extended
		Control Processor (ECP).  The Raven ECP has 5 addressable
		alarm relays (1-5)."
	::= { ecpAlarmRelayEntry 1 }

ecpAlarmRelayFunction  OBJECT-TYPE
	SYNTAX	INTEGER {
			ecpUnusedRelay(1),
			ecpMajorAlarmRelay(2),
			ecpMinorAlarmRelay(3)
		}
	MAX-ACCESS	read-write
	STATUS	current
	DESCRIPTION
		"This is the alarm function associated with an alarm
		relay on the Extended Control Processor (ECP).  An
		alarm relay may either be unused, assigned to the major
		alarm, or assigned to the minor alarm."
	::= { ecpAlarmRelayEntry 2 }

ecpAlarmRelayState  OBJECT-TYPE
	SYNTAX	INTEGER {
			on(1),
			off(2)
		}
	MAX-ACCESS	read-only
	STATUS	current
	DESCRIPTION
		"This is the current state of the alarm relay on the
		Extended Control Processor (ECP).  The state 'on'
		means that the alarm relay is activated; the state 'off'
		means that it is deactivated."
	::= { ecpAlarmRelayEntry 3 }

------------
--  ECP Software Definitions
------------

ecpSwMainTable  OBJECT-TYPE
	SYNTAX	SEQUENCE OF EcpSwMainEntry
	MAX-ACCESS	not-accessible
	STATUS	current
	DESCRIPTION
		"The table contains the Extended Control Processor
		(ECP) information maintained by the control software."
	::= { ecpSwMainGroup 1 }

ecpSwMainEntry  OBJECT-TYPE
	SYNTAX	EcpSwMainEntry
	MAX-ACCESS	not-accessible
	STATUS	current
	DESCRIPTION
		"This entry contains the Extended Control Processor
		(ECP) information maintained by the control software."
	INDEX	{ ecpBoardIndex }
	::= { ecpSwMainTable 1 }

EcpSwMainEntry  ::= SEQUENCE {
		ecpName				DisplayString,
		ecpHardwareVersion		Integer32,
		ecpSoftwareVersion		Integer32,
		ecpSoftwareVersionText		DisplayString,
		ecpType				INTEGER,
		ecpOperatingStatus		INTEGER,
		ecpProtocolType			INTEGER,
		ecpTimeZone			DisplayString,
		ecpGMTime			DateAndTime,
		ecpUptime			TimeTicks,
		ecpModeChangeTime		DateAndTime,
		ecpOtherEcpStatus		INTEGER,
		ecpExternalInput1		INTEGER,
		ecpExternalInput2		INTEGER,
		ecpExternalInput3		INTEGER,
		ecpExternalInput4		INTEGER,
		ecpExternalInput5		INTEGER
	}

ecpName  OBJECT-TYPE
	SYNTAX	DisplayString
	MAX-ACCESS	read-write
	STATUS	current
	DESCRIPTION
		"This is the system name of this Extended Control
		Processor (ECP) platform."
	::= { ecpSwMainEntry 1 }

ecpHardwareVersion  OBJECT-TYPE
	SYNTAX	Integer32
	MAX-ACCESS	read-only
	STATUS	current
	DESCRIPTION
		"This is the hardware version of the Extended Control
		Processor (ECP) platform."
	::= { ecpSwMainEntry 2 }

ecpSoftwareVersion  OBJECT-TYPE
	SYNTAX	Integer32
	MAX-ACCESS	read-only
	STATUS	current
	DESCRIPTION
		"This is the software version of the Extended Control
		Processor (ECP) control software.  The version is encoded
		into 6 hex characters.  Version 1.2.3 would be 0x010203."
	::= { ecpSwMainEntry 3 }

ecpSoftwareVersionText  OBJECT-TYPE
	SYNTAX	DisplayString
	MAX-ACCESS	read-only
	STATUS	current
	DESCRIPTION
		"This is the software version text of the Extended
		Control Processor (ECP) control software.  This object
		contains information regarding the software configuration
		that was used to build this software."
	::= { ecpSwMainEntry 4 }

ecpType  OBJECT-TYPE
	SYNTAX	INTEGER {
			unrecognized(1),
			cec-plus(2),
			cec-plus-t(3)
		}
	MAX-ACCESS	read-only
	STATUS	current
	DESCRIPTION
		"This is the type of the Extended Control Processor
		(ECP) board."
	::= { ecpSwMainEntry 5 }

ecpOperatingStatus  OBJECT-TYPE
	SYNTAX	INTEGER {
			ecpUnknown(1),
			ecpStandby(2),
			ecpActive(3),
			ecpOffline(4)
		}
	MAX-ACCESS	read-only
	STATUS	current
	DESCRIPTION
		"This is the software status of this Extended
		Control Processor (ECP)."
	::= { ecpSwMainEntry 6 }

ecpProtocolType  OBJECT-TYPE
	SYNTAX	INTEGER {
                        tftp(1),
                        ftp(2)
                }
	MAX-ACCESS	read-write
	STATUS	current
	DESCRIPTION
		"The transfer protocol that is used when upgrading the 	
		software, saving/restoring the CDB, etc. on this
		Extended Control Processor (ECP) board." 
	::= { ecpSwMainEntry 7 }

ecpTimeZone  OBJECT-TYPE
	SYNTAX	DisplayString (SIZE (0..255))
	MAX-ACCESS	read-write
	STATUS	current
	DESCRIPTION
		"The TimeZone configured for this Extended Control
		Processor (ECP).  This variable follows the POSIX standard
		1003.1-1988 for the format of the TZ environment variable.
		In particular, it is general enough to specify the rules
		for converting from Standard to Daylight Savings time
		for most timezones of the world.

		By default, the ECP has the rules built in for the following
		timezones:
			EST5EDT
			CST6CDT
			MST7MDT
			PST8PDT
			AKST9AKDT.

		Locales outside of these timezones will need to
		supply the appropriate rule for switching between
		Daylight and Standard time. "
		::= { ecpSwMainEntry 8 }

ecpGMTime  OBJECT-TYPE
	SYNTAX	DateAndTime
	MAX-ACCESS	read-write
	STATUS	current
	DESCRIPTION
		"The Extended Control Processor's (ECP's) notion of
		Greenwich Mean Time.  Linked to hrSystemDate.  Offset
		part of time spec, if supplied, is considered an error."
		::= { ecpSwMainEntry 9 }

ecpUptime       OBJECT-TYPE
	SYNTAX	TimeTicks
	MAX-ACCESS	read-only
	STATUS	current
	DESCRIPTION
		"This is the amount of time that the Extended Control
		Processor (ECP) control software has been running, in
		hundredths of a second."
	::= { ecpSwMainEntry 10 }

ecpModeChangeTime  OBJECT-TYPE
	SYNTAX	DateAndTime
	MAX-ACCESS	read-only
	STATUS	current
	DESCRIPTION
		"This is the time that the Extended Control Processor (ECP)
		control software has switched to the current operating mode."
	::= { ecpSwMainEntry 11 }

ecpOtherEcpStatus  OBJECT-TYPE
	SYNTAX	INTEGER {
			ecpNormal(1),
			ecpUnknown(2)
		}
	MAX-ACCESS	read-only
	STATUS	current
	DESCRIPTION
		"This is the software status of the other Extended
		Control Processor (ECP) from the viewpoint of this ECP."
	::= { ecpSwMainEntry 12 }

ecpExternalInput1  OBJECT-TYPE
	SYNTAX	INTEGER {
		ecpInputOn(1),
		ecpInputOff(2)
	}
	MAX-ACCESS	read-only
	STATUS	current
	DESCRIPTION
		"This is the state of External Input #1 from the viewpoint
		of the Extended Control Processor (ECP)."
	::= { ecpSwMainEntry 13 }

ecpExternalInput2  OBJECT-TYPE
	SYNTAX	INTEGER {
		ecpInputOn(1),
		ecpInputOff(2)
	}
	MAX-ACCESS	read-only
	STATUS	current
	DESCRIPTION
		"This is the state of External Input #2 from the viewpoint
		of the Extended Control Processor (ECP)."
	::= { ecpSwMainEntry 14 }

ecpExternalInput3  OBJECT-TYPE
	SYNTAX	INTEGER {
		ecpInputOn(1),
		ecpInputOff(2)
	}
	MAX-ACCESS	read-only
	STATUS	current
	DESCRIPTION
		"This is the state of External Input #3 from the viewpoint
		of the Extended Control Processor (ECP)."
	::= { ecpSwMainEntry 15 }

ecpExternalInput4  OBJECT-TYPE
	SYNTAX	INTEGER {
		ecpInputOn(1),
		ecpInputOff(2)
	}
	MAX-ACCESS	read-only
	STATUS	current
	DESCRIPTION
		"This is the state of External Input #4 from the viewpoint
		of the Extended Control Processor (ECP)."
	::= { ecpSwMainEntry 16 }

ecpExternalInput5  OBJECT-TYPE
	SYNTAX	INTEGER {
		ecpInputOn(1),
		ecpInputOff(2)
	}
	MAX-ACCESS	read-only
	STATUS	current
	DESCRIPTION
		"This is the state of External Input #5 from the viewpoint
		of the Extended Control Processor (ECP)."
	::= { ecpSwMainEntry 17 }

------------
--  ECP Network Interface Definitions
------------

ecpNetIfTable  OBJECT-TYPE
	SYNTAX	SEQUENCE OF EcpNetIfEntry
	MAX-ACCESS	not-accessible
	STATUS	current
	DESCRIPTION
		"This table contains the network interface information
		for the Extended Control Processor (ECP) board."
	::= { ecpIpGroup 1 }

ecpNetIfEntry  OBJECT-TYPE
	SYNTAX	EcpNetIfEntry
	MAX-ACCESS	not-accessible
	STATUS	current
	DESCRIPTION
		"This entry contains the network interface information
		for the Extended Control Processor (ECP) board."
	INDEX	{ ecpBoardIndex, ecpNetIfIndex }
	::= { ecpNetIfTable 1 }

EcpNetIfEntry ::= SEQUENCE {
		ecpNetIfIndex			Integer32,
		ecpNetIfDescr			DisplayString,
		ecpNetIfPhysAddress		PhysAddress,
		ecpNetIfAdminStatus		INTEGER,
		ecpNetIfOperStatus		INTEGER,
		ecpNetIfLastChange		TimeTicks,
		ecpNetIfIpAddr			IpAddress,
		ecpNetIfIpMask			IpAddress,
		ecpNetIfIpBcastAddr		Integer32
	}

ecpNetIfIndex  OBJECT-TYPE
	SYNTAX	Integer32
	MAX-ACCESS	read-only
	STATUS	current
	DESCRIPTION
		"A unique value for each interface.  Its value
		ranges between 1 and the value of ifNumber.  The
		value for each interface must remain constant at
		least from one re-initialization of the entity's
		network management system to the next re-
		initialization."
	::= { ecpNetIfEntry 1 }

ecpNetIfDescr  OBJECT-TYPE
	SYNTAX	DisplayString
	MAX-ACCESS	read-only
	STATUS	current
	DESCRIPTION
		"A textual string containing information about the
		interface.  This string should include the name of
		the manufacturer, the product name and the version
		of the hardware interface."
	::= { ecpNetIfEntry 2 }

ecpNetIfPhysAddress  OBJECT-TYPE
	SYNTAX	PhysAddress
	MAX-ACCESS	read-only
	STATUS	current
	DESCRIPTION
		"The interface's address at the protocol layer
		immediately `below' the network layer in the
		protocol stack.  For interfaces which do not have
		such an address (e.g., a serial line), this object
		should contain an octet string of zero length."
	::= { ecpNetIfEntry 3 }

ecpNetIfAdminStatus  OBJECT-TYPE
	SYNTAX	INTEGER {
			up(1),
			down(2)
		}
	MAX-ACCESS	read-write
	STATUS	current
	DESCRIPTION
		"The desired state of the interface."
	::= { ecpNetIfEntry 4 }

ecpNetIfOperStatus  OBJECT-TYPE
	SYNTAX	INTEGER {
			up(1),
			down(2)
		}
	MAX-ACCESS	read-only
	STATUS	current
	DESCRIPTION
		"The current operational state of the interface."
	::= { ecpNetIfEntry 5 }

ecpNetIfLastChange  OBJECT-TYPE
	SYNTAX	TimeTicks
	MAX-ACCESS	read-only
	STATUS	current
	DESCRIPTION
		"The value of sysUpTime at the time the interface
		entered its current operational state.  If the
		current state was entered prior to the last re-
		initialization of the local network management
		subsystem, then this object contains a zero
		value."
	::= { ecpNetIfEntry 6 }

ecpNetIfIpAddr  OBJECT-TYPE
	SYNTAX	IpAddress
	MAX-ACCESS	read-write
	STATUS	current
	DESCRIPTION
		"The IP address associated with this network interface."
	::= { ecpNetIfEntry 7 }

ecpNetIfIpMask  OBJECT-TYPE
	SYNTAX	IpAddress
	MAX-ACCESS	read-write
	STATUS	current
	DESCRIPTION
		"The subnet mask associated with the IP address of
		this entry.  The value of the mask is an IP
		address with all the network bits set to 1 and all
		the hosts bits set to 0."
	::= { ecpNetIfEntry 8 }

ecpNetIfIpBcastAddr  OBJECT-TYPE
	SYNTAX	Integer32
	MAX-ACCESS	read-write
	STATUS	current
	DESCRIPTION
		"The value of the least-significant bit in the IP
		broadcast address used for sending datagrams on
		the (logical) interface associated with the IP
		address of this entry.  For example, when the
		Internet standard all-ones broadcast address is
		used, the value will be 1.  This value applies to
		both the subnet and network broadcasts addresses
		used by the entity on this (logical) interface."
	::= { ecpNetIfEntry 9 }


ecpNetIfStatsTable  OBJECT-TYPE
	SYNTAX  SEQUENCE OF EcpNetIfStatsEntry
	MAX-ACCESS	not-accessible
	STATUS	current
	DESCRIPTION
		"This table contains the network interface statistics
		for the Extended Control Processor (ECP) board."
	::= { ecpIpGroup 2 }

ecpNetIfStatsEntry  OBJECT-TYPE
	SYNTAX	EcpNetIfStatsEntry
	MAX-ACCESS	not-accessible
	STATUS	current
	DESCRIPTION
		"This entry contains the network interface statistics
		for the Extended Control Processor (ECP) board."
	INDEX	{ ecpBoardIndex, ecpNetIfIndex }
	::= { ecpNetIfStatsTable 1 }

EcpNetIfStatsEntry ::= SEQUENCE {
		ecpNetIfInOctets		Counter32,
		ecpNetIfInUcastPkts		Counter32,
		ecpNetIfInNUcastPkts		Counter32,
		ecpNetIfInDiscards		Counter32,
		ecpNetIfInErrors		Counter32,
		ecpNetIfInUnknownProtos		Counter32,
		ecpNetIfOutOctets		Counter32,
		ecpNetIfOutUcastPkts		Counter32,
		ecpNetIfOutNUcastPkts		Counter32,
		ecpNetIfOutDiscards		Counter32,
		ecpNetIfOutErrors		Counter32,
		ecpNetIfOutQLen			Gauge32
	}

ecpNetIfInOctets  OBJECT-TYPE
	SYNTAX	Counter32
	MAX-ACCESS	read-only
	STATUS	current
	DESCRIPTION
		"The total number of octets received on the
		interface, including framing characters."
	::= { ecpNetIfStatsEntry 1 }

ecpNetIfInUcastPkts  OBJECT-TYPE
	SYNTAX	Counter32
	MAX-ACCESS	read-only
	STATUS	current
	DESCRIPTION
		"The number of subnetwork-unicast packets
		delivered to a higher-layer protocol."
	::= { ecpNetIfStatsEntry 2 }

ecpNetIfInNUcastPkts  OBJECT-TYPE
	SYNTAX	Counter32
	MAX-ACCESS	read-only
	STATUS	current
	DESCRIPTION
		"The number of non-unicast (i.e., subnetwork-
		broadcast or subnetwork-multicast) packets
		delivered to a higher-layer protocol."
	::= { ecpNetIfStatsEntry 3 }

ecpNetIfInDiscards  OBJECT-TYPE
	SYNTAX	Counter32
	MAX-ACCESS	read-only
	STATUS	current
	DESCRIPTION
		"The number of inbound packets which were chosen
		to be discarded even though no errors had been
		detected to prevent their being deliverable to a
		higher-layer protocol.  One possible reason for
		discarding such a packet could be to free up
		buffer space."
	::= { ecpNetIfStatsEntry 4 }

ecpNetIfInErrors  OBJECT-TYPE
	SYNTAX	Counter32
	MAX-ACCESS	read-only
	STATUS	current
	DESCRIPTION
		"The number of inbound packets that contained
		errors preventing them from being deliverable to a
		higher-layer protocol."
	::= { ecpNetIfStatsEntry 5 }

ecpNetIfInUnknownProtos  OBJECT-TYPE
	SYNTAX	Counter32
	MAX-ACCESS	read-only
	STATUS	current
	DESCRIPTION
		"The number of packets received via the interface
		which were discarded because of an unknown or
		unsupported protocol."
	::= { ecpNetIfStatsEntry 6 }

ecpNetIfOutOctets  OBJECT-TYPE
	SYNTAX	Counter32
	MAX-ACCESS	read-only
	STATUS	current
	DESCRIPTION
		"The total number of octets transmitted out of the
		interface, including framing characters."
	::= { ecpNetIfStatsEntry 7 }

ecpNetIfOutUcastPkts  OBJECT-TYPE
	SYNTAX	Counter32
	MAX-ACCESS	read-only
	STATUS	current
	DESCRIPTION
		"The total number of packets that higher-level
		protocols requested be transmitted to a
		subnetwork-unicast address, including those that
		were discarded or not sent."
	::= { ecpNetIfStatsEntry 8 }

ecpNetIfOutNUcastPkts  OBJECT-TYPE
	SYNTAX	Counter32
	MAX-ACCESS	read-only
	STATUS	current
	DESCRIPTION
		"The total number of packets that higher-level
		protocols requested be transmitted to a non-
		unicast (i.e., a subnetwork-broadcast or
		subnetwork-multicast) address, including those
		that were discarded or not sent."
	::= { ecpNetIfStatsEntry 9 }

ecpNetIfOutDiscards  OBJECT-TYPE
	SYNTAX	Counter32
	MAX-ACCESS	read-only
	STATUS	current
	DESCRIPTION
		"The number of outbound packets which were chosen
		to be discarded even though no errors had been
		detected to prevent their being transmitted.  One
		possible reason for discarding such a packet could
		be to free up buffer space."
	::= { ecpNetIfStatsEntry 10 }

ecpNetIfOutErrors  OBJECT-TYPE
	SYNTAX	Counter32
	MAX-ACCESS	read-only
	STATUS	current
	DESCRIPTION
		"The number of outbound packets that could not be
		transmitted because of errors."
	::= { ecpNetIfStatsEntry 11 }

ecpNetIfOutQLen  OBJECT-TYPE
	SYNTAX	Gauge32
	MAX-ACCESS	read-only
	STATUS	current
	DESCRIPTION
		"The length of the output packet queue (in
		packets)."
	::= { ecpNetIfStatsEntry 12 }


------------
--  ECP IP Statistics Definitions
------------

ecpIpStatsTable  OBJECT-TYPE
	SYNTAX  SEQUENCE OF EcpIpStatsEntry
	MAX-ACCESS	not-accessible
	STATUS	current
	DESCRIPTION
		"This table contains the Internet protocol statistics
		for the Extended Control Processor (ECP) board."
	::= { ecpIpGroup 3 }

ecpIpStatsEntry  OBJECT-TYPE
	SYNTAX	EcpIpStatsEntry
	MAX-ACCESS	not-accessible
	STATUS	current
	DESCRIPTION
		"This entry contains the Internet protocol statistics
		for the Extended Control Processor (ECP) board."
	INDEX	{ ecpBoardIndex }
	::= { ecpIpStatsTable 1 }

EcpIpStatsEntry ::= SEQUENCE {
		ecpIpInReceives			Counter32,
		ecpIpInHdrErrors		Counter32,
		ecpIpInAddrErrors		Counter32,
		ecpIpForwDatagrams		Counter32,
		ecpIpInUnknownProtos		Counter32,
		ecpIpInDiscards			Counter32,
		ecpIpInDelivers			Counter32,
		ecpIpOutRequests		Counter32,
		ecpIpOutDiscards		Counter32,
		ecpIpOutNoRoutes		Counter32,
		ecpIpReasmReqds			Counter32,
		ecpIpReasmOKs			Counter32,
		ecpIpReasmFails			Counter32,
		ecpIpFragOKs			Counter32,
		ecpIpFragFails			Counter32,
		ecpIpFragCreates		Counter32
	}

ecpIpInReceives  OBJECT-TYPE
	SYNTAX	Counter32
	MAX-ACCESS	read-only
	STATUS	current
	DESCRIPTION
		"The total number of input datagrams received from
		interfaces, including those received in error."
	::= { ecpIpStatsEntry 1 }

ecpIpInHdrErrors  OBJECT-TYPE
	SYNTAX	Counter32
	MAX-ACCESS	read-only
	STATUS	current
	DESCRIPTION
		"The number of input datagrams discarded due to
		errors in their IP headers, including bad
		checksums, version number mismatch, other format
		errors, time-to-live exceeded, errors discovered
		in processing their IP options, etc."
	::= { ecpIpStatsEntry 2 }

ecpIpInAddrErrors  OBJECT-TYPE
	SYNTAX	Counter32
	MAX-ACCESS	read-only
	STATUS	current
	DESCRIPTION
		"The number of input datagrams discarded because
		the IP address in their IP header's destination
		field was not a valid address to be received at
		this entity.  This count includes invalid
		addresses (e.g., 0.0.0.0) and addresses of
		unsupported Classes (e.g., Class E).  For entities
		which are not IP Gateways and therefore do not
		forward datagrams, this counter includes datagrams
		discarded because the destination address was not
		a local address."
	::= { ecpIpStatsEntry 3 }

ecpIpForwDatagrams  OBJECT-TYPE
	SYNTAX	Counter32
	MAX-ACCESS	read-only
	STATUS	current
	DESCRIPTION
		"The number of input datagrams for which this
		entity was not their final IP destination, as a
		result of which an attempt was made to find a
		route to forward them to that final destination.
		In entities which do not act as IP Gateways, this
		counter will include only those packets which were
		Source-Routed via this entity, and the Source-
		Route option processing was successful."
	::= { ecpIpStatsEntry 4 }

ecpIpInUnknownProtos  OBJECT-TYPE
	SYNTAX	Counter32
	MAX-ACCESS	read-only
	STATUS	current
	DESCRIPTION
		"The number of locally-addressed datagrams
		received successfully but discarded because of an
		unknown or unsupported protocol."
	::= { ecpIpStatsEntry 5 }

ecpIpInDiscards  OBJECT-TYPE
	SYNTAX	Counter32
	MAX-ACCESS	read-only
	STATUS	current
	DESCRIPTION
		"The number of input IP datagrams for which no
		problems were encountered to prevent their
		continued processing, but which were discarded
		(e.g., for lack of buffer space).  Note that this
		counter does not include any datagrams discarded
		while awaiting re-assembly."
	::= { ecpIpStatsEntry 6 }

ecpIpInDelivers  OBJECT-TYPE
	SYNTAX	Counter32
	MAX-ACCESS	read-only
	STATUS	current
	DESCRIPTION
		"The total number of input datagrams successfully
		delivered to IP user-protocols (including ICMP)."
	::= { ecpIpStatsEntry 7 }

ecpIpOutRequests  OBJECT-TYPE
	SYNTAX	Counter32
	MAX-ACCESS	read-only
	STATUS	current
	DESCRIPTION
		"The total number of IP datagrams which local IP
		user-protocols (including ICMP) supplied to IP in
		requests for transmission.  Note that this counter
		does not include any datagrams counted in
		ipForwDatagrams."
	::= { ecpIpStatsEntry 8 }

ecpIpOutDiscards  OBJECT-TYPE
	SYNTAX	Counter32
	MAX-ACCESS	read-only
	STATUS	current
	DESCRIPTION
		"The number of output IP datagrams for which no
		problem was encountered to prevent their
		transmission to their destination, but which were
		discarded (e.g., for lack of buffer space).  Note
		that this counter would include datagrams counted
		in ipForwDatagrams if any such packets met this
		(discretionary) discard criterion."
	::= { ecpIpStatsEntry 9 }

ecpIpOutNoRoutes  OBJECT-TYPE
	SYNTAX	Counter32
	MAX-ACCESS	read-only
	STATUS	current
	DESCRIPTION
		"The number of IP datagrams discarded because no
		route could be found to transmit them to their
		destination.  Note that this counter includes any
		packets counted in ipForwDatagrams which meet this
		`no-route' criterion.  Note that this includes any
		datagarms which a host cannot route because all of
		its default gateways are down."
	::= { ecpIpStatsEntry 10 }

ecpIpReasmReqds  OBJECT-TYPE
	SYNTAX	Counter32
	MAX-ACCESS	read-only
	STATUS	current
	DESCRIPTION
		"The number of IP fragments received which needed
		to be reassembled at this entity."
	::= { ecpIpStatsEntry 11 }

ecpIpReasmOKs  OBJECT-TYPE
	SYNTAX	Counter32
	MAX-ACCESS	read-only
	STATUS	current
	DESCRIPTION
		"The number of IP datagrams successfully re-
		assembled."
	::= { ecpIpStatsEntry 12 }

ecpIpReasmFails  OBJECT-TYPE
	SYNTAX	Counter32
	MAX-ACCESS	read-only
	STATUS	current
	DESCRIPTION
		"The number of failures detected by the IP re-
		assembly algorithm (for whatever reason: timed
		out, errors, etc).  Note that this is not
		necessarily a count of discarded IP fragments
		since some algorithms (notably the algorithm in
		RFC 815) can lose track of the number of fragments
		by combining them as they are received."
	::= { ecpIpStatsEntry 13 }

ecpIpFragOKs  OBJECT-TYPE
	SYNTAX	Counter32
	MAX-ACCESS	read-only
	STATUS	current
	DESCRIPTION
		"The number of IP datagrams that have been
		successfully fragmented at this entity."
	::= { ecpIpStatsEntry 14 }

ecpIpFragFails  OBJECT-TYPE
	SYNTAX	Counter32
	MAX-ACCESS	read-only
	STATUS	current
	DESCRIPTION
		"The number of IP datagrams that have been
		discarded because they needed to be fragmented at
		this entity but could not be, e.g., because their
		Don't Fragment flag was set."
	::= { ecpIpStatsEntry 15 }

ecpIpFragCreates  OBJECT-TYPE
	SYNTAX	Counter32
	MAX-ACCESS	read-only
	STATUS	current
	DESCRIPTION
		"The number of IP datagram fragments that have
		been generated as a result of fragmentation at
		this entity."
	::= { ecpIpStatsEntry 16 }

------------
--  ECP IP Routing Definitions
------------


ecpIpRouteTable  OBJECT-TYPE
	SYNTAX	SEQUENCE OF EcpIpRouteEntry
	MAX-ACCESS	not-accessible
	STATUS	current
	DESCRIPTION
		"This table contains the Internet Protocol routing entries
		for the Extended Control Processor (ECP) board."
	::= { ecpIpGroup 4 }

ecpIpRouteEntry  OBJECT-TYPE
	SYNTAX	EcpIpRouteEntry
	MAX-ACCESS	not-accessible
	STATUS	current
	DESCRIPTION
		"This entry contains the Internet Protocol routing data
		for the Extended Control Processor (ECP) board."
	INDEX	{ ecpBoardIndex, ecpIpRouteDest }
	::= { ecpIpRouteTable 1 }

EcpIpRouteEntry ::= SEQUENCE {
		ecpIpRouteDest			IpAddress,
		ecpIpRouteIfIndex		Integer32,
		ecpIpRouteNextHop		IpAddress,
		ecpIpRouteMetric1		Integer32,
		ecpIpRouteType			INTEGER,
		ecpIpRouteMask			IpAddress
	}

ecpIpRouteDest  OBJECT-TYPE
	SYNTAX	IpAddress
	MAX-ACCESS	read-only
	STATUS	current
	DESCRIPTION
		"The destination IP address of this route.  An
		entry with a value of 0.0.0.0 is considered a
		default route.  Multiple routes to a single
		destination can appear in the table, but access to
		such multiple entries is dependent on the table-
		access mechanisms defined by the network
		management protocol in use."
	::= { ecpIpRouteEntry 1 }

ecpIpRouteIfIndex  OBJECT-TYPE
	SYNTAX	Integer32
	MAX-ACCESS	read-write
	STATUS	current
	DESCRIPTION
		"The index value which uniquely identifies the
		local interface through which the next hop of this
		route should be reached.  The interface identified
		by a particular value of this index is the same
		interface as identified by the same value of
		ifIndex."
	::= { ecpIpRouteEntry 2 }

ecpIpRouteNextHop  OBJECT-TYPE
	SYNTAX	IpAddress
	MAX-ACCESS	read-write
	STATUS	current
	DESCRIPTION
		"The IP address of the next hop of this route.
		(In the case of a route bound to an interface
		which is realized via a broadcast media, the value
		of this field is the agent's IP address on that
		interface.)"
	::= { ecpIpRouteEntry 3 }

ecpIpRouteMetric1  OBJECT-TYPE
	SYNTAX	Integer32
	MAX-ACCESS	read-write
	STATUS	current
	DESCRIPTION
		"The primary routing metric for this route.  The
		semantics of this metric are determined by the
		routing-protocol specified in the route's
		ipRouteProto value.  If this metric is not used,
		its value should be set to -1."
	::= { ecpIpRouteEntry 4 }

ecpIpRouteType  OBJECT-TYPE
	SYNTAX	INTEGER {
		other(1),	-- none of the following
		invalid(2),	-- an invalidated route
		direct(3),	-- route to directly
				-- connected (sub-)network
		indirect(4)	-- route to a non-local
				-- host/network/sub-network
	}
	MAX-ACCESS	read-write
	STATUS	current
	DESCRIPTION
		"The type of route.  Note that the values
		direct(3) and indirect(4) refer to the notion of
		direct and indirect routing in the IP
		architecture.

		Setting this object to the value invalid(2) has
		the effect of invalidating the corresponding entry
		in the ipRouteTable object.  That is, it
		effectively dissasociates the destination
		identified with said entry from the route
		identified with said entry.  It is an
		implementation-specific matter as to whether the
		agent removes an invalidated entry from the table.
		Accordingly, management stations must be prepared
		to receive tabular information from agents that
		corresponds to entries not currently in use.
		Proper interpretation of such entries requires
		examination of the relevant ipRouteType object."
	::= { ecpIpRouteEntry 5 }

ecpIpRouteMask  OBJECT-TYPE
	SYNTAX	IpAddress
	MAX-ACCESS	read-write
	STATUS	current
	DESCRIPTION
		"Indicate the mask to be logical-ANDed with the
		destination address before being compared to the
		value in the ipRouteDest field.  For those systems
		that do not support arbitrary subnet masks, an
		agent constructs the value of the ipRouteMask by
		determining whether the value of the correspondent
		ipRouteDest field belong to a class-A, B, or C
		network, and then using one of:

			mask           network
			255.0.0.0      class-A
			255.255.0.0    class-B
			255.255.255.0  class-C
		If the value of the ipRouteDest is 0.0.0.0 (a
		default route), then the mask value is also
		0.0.0.0.  It should be noted that all IP routing
		subsystems implicitly use this mechanism."
	::= { ecpIpRouteEntry 6 }

------------
--  ECP ICMP Statistics Definitions
------------

ecpIcmpStatsTable  OBJECT-TYPE
	SYNTAX	SEQUENCE OF EcpIcmpStatsEntry
	MAX-ACCESS	not-accessible
	STATUS	current
	DESCRIPTION
		"This table contains the Internet Control Message Protocol
		statistics for the Extended Control Processor (ECP)
		board."
	::= { ecpIpGroup 5 }

ecpIcmpStatsEntry  OBJECT-TYPE
	SYNTAX	EcpIcmpStatsEntry
	MAX-ACCESS	not-accessible
	STATUS	current
	DESCRIPTION
		"This entry contains the Internet Control Message Protocol
		statistics for the Extended Control Processor (ECP)
		board."
	INDEX	{ ecpBoardIndex }
	::= { ecpIcmpStatsTable 1 }

EcpIcmpStatsEntry ::= SEQUENCE {
		ecpIcmpInMsgs			Counter32,
		ecpIcmpInErrors			Counter32,
		ecpIcmpInDestUnreach		Counter32,
		ecpIcmpInTimeExcds		Counter32,
		ecpIcmpInParmProbs		Counter32,
		ecpIcmpInSrcQuenchs		Counter32,
		ecpIcmpInRedirects		Counter32,
		ecpIcmpInEchos			Counter32,
		ecpIcmpInEchoReps		Counter32,
		ecpIcmpInTimestamps		Counter32,
		ecpIcmpInTimestampReps		Counter32,
		ecpIcmpInaddrMasks		Counter32,
		ecpIcmpInAddrMaskReps		Counter32,
		ecpIcmpOutMsgs			Counter32,
		ecpIcmpOutErrors		Counter32,
		ecpIcmpOutDestUnreachs		Counter32,
		ecpIcmpOutTimeExcds		Counter32,
		ecpIcmpOutParmProbs		Counter32,
		ecpIcmpOutSrcQuenchs		Counter32,
		ecpIcmpOutRedirects		Counter32,
		ecpIcmpOutEchos			Counter32,
		ecpIcmpOutEchoReps		Counter32,
		ecpIcmpOutTimestamps		Counter32,
		ecpIcmpOutTimestampReps		Counter32,
		ecpIcmpOutAddrMasks		Counter32,
		ecpIcmpOutAddrMaskReps		Counter32
	}

ecpIcmpInMsgs  OBJECT-TYPE
	SYNTAX	Counter32
	MAX-ACCESS	read-only
	STATUS	current
	DESCRIPTION
		"The total number of ICMP messages which the
		entity received.  Note that this counter includes
		all those counted by icmpInErrors."
	::= { ecpIcmpStatsEntry 1 }

ecpIcmpInErrors  OBJECT-TYPE
	SYNTAX	Counter32
	MAX-ACCESS	read-only
	STATUS	current
	DESCRIPTION
		"The number of ICMP messages which the entity
		received but determined as having ICMP-specific
		errors (bad ICMP checksums, bad length, etc.)."
	::= { ecpIcmpStatsEntry 2 }

ecpIcmpInDestUnreach  OBJECT-TYPE
	SYNTAX	Counter32
	MAX-ACCESS	read-only
	STATUS	current
	DESCRIPTION
		"The number of ICMP Destination Unreachable
		messages received."
	::= { ecpIcmpStatsEntry 3 }

ecpIcmpInTimeExcds  OBJECT-TYPE
	SYNTAX	Counter32
	MAX-ACCESS	read-only
	STATUS	current
	DESCRIPTION
		"The number of ICMP Time Exceeded messages
		received."
	::= { ecpIcmpStatsEntry 4 }

ecpIcmpInParmProbs  OBJECT-TYPE
	SYNTAX	Counter32
	MAX-ACCESS	read-only
	STATUS	current
	DESCRIPTION
		"The number of ICMP Parameter Problem messages
		received."
	::= { ecpIcmpStatsEntry 5 }

ecpIcmpInSrcQuenchs  OBJECT-TYPE
	SYNTAX	Counter32
	MAX-ACCESS	read-only
	STATUS	current
	DESCRIPTION
		"The number of ICMP Source Quench messages
		received."
	::= { ecpIcmpStatsEntry 6 }

ecpIcmpInRedirects  OBJECT-TYPE
	SYNTAX	Counter32
	MAX-ACCESS	read-only
	STATUS	current
	DESCRIPTION
		"The number of ICMP Redirect messages received."
	::= { ecpIcmpStatsEntry 7 }

ecpIcmpInEchos  OBJECT-TYPE
	SYNTAX	Counter32
	MAX-ACCESS	read-only
	STATUS	current
	DESCRIPTION
		"The number of ICMP Echo (request) messages
		received."
	::= { ecpIcmpStatsEntry 8 }

ecpIcmpInEchoReps  OBJECT-TYPE
	SYNTAX	Counter32
	MAX-ACCESS	read-only
	STATUS	current
	DESCRIPTION
		"The number of ICMP Echo Reply messages received."
	::= { ecpIcmpStatsEntry 9 }

ecpIcmpInTimestamps  OBJECT-TYPE
	SYNTAX	Counter32
	MAX-ACCESS	read-only
	STATUS	current
	DESCRIPTION
		"The number of ICMP Timestamp (request) messages
		received."
	::= { ecpIcmpStatsEntry 10 }

ecpIcmpInTimestampReps  OBJECT-TYPE
	SYNTAX	Counter32
	MAX-ACCESS	read-only
	STATUS	current
	DESCRIPTION
		"The number of ICMP Timestamp Reply messages
		received."
	::= { ecpIcmpStatsEntry 11 }

ecpIcmpInaddrMasks  OBJECT-TYPE
	SYNTAX	Counter32
	MAX-ACCESS	read-only
	STATUS	current
	DESCRIPTION
		"The number of ICMP Address Mask Request messages
		received."
	::= { ecpIcmpStatsEntry 12 }

ecpIcmpInAddrMaskReps  OBJECT-TYPE
	SYNTAX	Counter32
	MAX-ACCESS	read-only
	STATUS	current
	DESCRIPTION
		"The number of ICMP Address Mask Reply messages
		received."
	::= { ecpIcmpStatsEntry 13 }

ecpIcmpOutMsgs  OBJECT-TYPE
	SYNTAX	Counter32
	MAX-ACCESS	read-only
	STATUS	current
	DESCRIPTION
		"The total number of ICMP messages which this
		entity attempted to send.  Note that this counter
		includes all those counted by icmpOutErrors."
	::= { ecpIcmpStatsEntry 14 }

ecpIcmpOutErrors  OBJECT-TYPE
	SYNTAX	Counter32
	MAX-ACCESS	read-only
	STATUS	current
	DESCRIPTION
		"The number of ICMP messages which this entity did
		not send due to problems discovered within ICMP
		such as a lack of buffers.  This value should not
		include errors discovered outside the ICMP layer
		such as the inability of IP to route the resultant
		datagram.  In some implementations there may be no
		types of error which contribute to this counter's
		value."
	::= { ecpIcmpStatsEntry 15 }

ecpIcmpOutDestUnreachs  OBJECT-TYPE
	SYNTAX	Counter32
	MAX-ACCESS	read-only
	STATUS	current
	DESCRIPTION
		"The number of ICMP Destination Unreachable
		messages sent."
	::= { ecpIcmpStatsEntry 16 }

ecpIcmpOutTimeExcds  OBJECT-TYPE
	SYNTAX	Counter32
	MAX-ACCESS	read-only
	STATUS	current
	DESCRIPTION
		"The number of ICMP Time Exceeded messages sent."
	::= { ecpIcmpStatsEntry 17 }

ecpIcmpOutParmProbs  OBJECT-TYPE
	SYNTAX	Counter32
	MAX-ACCESS	read-only
	STATUS	current
	DESCRIPTION
		"The number of ICMP Parameter Problem messages
		sent."
	::= { ecpIcmpStatsEntry 18 }

ecpIcmpOutSrcQuenchs  OBJECT-TYPE
	SYNTAX	Counter32
	MAX-ACCESS	read-only
	STATUS	current
	DESCRIPTION
		"The number of ICMP Source Quench messages sent."
	::= { ecpIcmpStatsEntry 19 }

ecpIcmpOutRedirects  OBJECT-TYPE
	SYNTAX	Counter32
	MAX-ACCESS	read-only
	STATUS	current
	DESCRIPTION
		"The number of ICMP Redirect messages sent.  For a
		host, this object will always be zero, since hosts
		do not send redirects."
	::= { ecpIcmpStatsEntry 20 }

ecpIcmpOutEchos  OBJECT-TYPE
	SYNTAX	Counter32
	MAX-ACCESS	read-only
	STATUS	current
	DESCRIPTION
		"The number of ICMP Echo (request) messages sent."
	::= { ecpIcmpStatsEntry 21 }

ecpIcmpOutEchoReps  OBJECT-TYPE
	SYNTAX	Counter32
	MAX-ACCESS	read-only
	STATUS	current
	DESCRIPTION
		"The number of ICMP Echo Reply messages sent."
	::= { ecpIcmpStatsEntry 22 }

ecpIcmpOutTimestamps  OBJECT-TYPE
	SYNTAX	Counter32
	MAX-ACCESS	read-only
	STATUS	current
	DESCRIPTION
		"The number of ICMP Timestamp (request) messages
		sent."
	::= { ecpIcmpStatsEntry 23 }

ecpIcmpOutTimestampReps  OBJECT-TYPE
	SYNTAX	Counter32
	MAX-ACCESS	read-only
	STATUS	current
	DESCRIPTION
		"The number of ICMP Timestamp Reply messages
		sent."
	::= { ecpIcmpStatsEntry 24 }

ecpIcmpOutAddrMasks  OBJECT-TYPE
	SYNTAX	Counter32
	MAX-ACCESS	read-only
	STATUS	current
	DESCRIPTION
		"The number of ICMP Address Mask Request messages
		sent."
	::= { ecpIcmpStatsEntry 25 }

ecpIcmpOutAddrMaskReps  OBJECT-TYPE
	SYNTAX	Counter32
	MAX-ACCESS	read-only
	STATUS	current
	DESCRIPTION
		"The number of ICMP Address Mask Reply messages
		sent."
	::= { ecpIcmpStatsEntry 26 }

------------
--  ECP TCP Statistics Definitions
------------


ecpTcpStatsTable  OBJECT-TYPE
	SYNTAX  SEQUENCE OF EcpTcpStatsEntry
	MAX-ACCESS	not-accessible
	STATUS	current
	DESCRIPTION
		"This table contains the Transmission Control Protocol
		statistics for the Extended Control Processor (ECP)
		board."
	::= { ecpIpGroup 6 }

ecpTcpStatsEntry  OBJECT-TYPE
	SYNTAX	EcpTcpStatsEntry
	MAX-ACCESS	not-accessible
	STATUS	current
	DESCRIPTION
		"This entry contains the Transmission Control Protocol
		statistics for the Extended Control Processor (ECP)
		board."
	INDEX	{ ecpBoardIndex }
	::= { ecpTcpStatsTable 1 }

EcpTcpStatsEntry ::= SEQUENCE {
		ecpTcpActiveOpens		Counter32,
		ecpTcpPassiveOpens		Counter32,
		ecpTcpAttemptFails		Counter32,
		ecpTcpEstabResets		Counter32,
		ecpTcpCurrEstab			Counter32,
		ecpTcpInSegs			Counter32,
		ecpTcpOutSegs			Counter32,
		ecpTcpRetransSegs		Counter32
	}

ecpTcpActiveOpens  OBJECT-TYPE
	SYNTAX	Counter32
	MAX-ACCESS	read-only
	STATUS	current
	DESCRIPTION
		"The number of times TCP connections have made a
		direct transition to the SYN-SENT state from the
		CLOSED state."
	::= { ecpTcpStatsEntry 1 }

ecpTcpPassiveOpens  OBJECT-TYPE
	SYNTAX	Counter32
	MAX-ACCESS	read-only
	STATUS	current
	DESCRIPTION
		"The number of times TCP connections have made a
		direct transition to the SYN-RCVD state from the
		LISTEN state."
	::= { ecpTcpStatsEntry 2 }

ecpTcpAttemptFails  OBJECT-TYPE
	SYNTAX	Counter32
	MAX-ACCESS	read-only
	STATUS	current
	DESCRIPTION
		"The number of times TCP connections have made a
		direct transition to the CLOSED state from either
		the SYN-SENT state or the SYN-RCVD state, plus the
		number of times TCP connections have made a direct
		transition to the LISTEN state from the SYN-RCVD
		state."
	::= { ecpTcpStatsEntry 3 }

ecpTcpEstabResets  OBJECT-TYPE
	SYNTAX	Counter32
	MAX-ACCESS	read-only
	STATUS	current
	DESCRIPTION
		"The number of times TCP connections have made a
		direct transition to the CLOSED state from either
		the ESTABLISHED state or the CLOSE-WAIT state."
	::= { ecpTcpStatsEntry 4 }

ecpTcpCurrEstab  OBJECT-TYPE
	SYNTAX	Counter32
	MAX-ACCESS	read-only
	STATUS	current
	DESCRIPTION
		"The number of TCP connections for which the
		current state is either ESTABLISHED or CLOSE-
		WAIT."
	::= { ecpTcpStatsEntry 5 }

ecpTcpInSegs  OBJECT-TYPE
	SYNTAX	Counter32
	MAX-ACCESS	read-only
	STATUS	current
	DESCRIPTION
		"The total number of segments received, including
		those received in error.  This count includes
		segments received on currently established
		connections."
	::= { ecpTcpStatsEntry 6 }

ecpTcpOutSegs  OBJECT-TYPE
	SYNTAX	Counter32
	MAX-ACCESS	read-only
	STATUS	current
	DESCRIPTION
		"The total number of segments sent, including
		those on current connections but excluding those
		containing only retransmitted octets."
	::= { ecpTcpStatsEntry 7 }

ecpTcpRetransSegs  OBJECT-TYPE
	SYNTAX	Counter32
	MAX-ACCESS	read-only
	STATUS	current
	DESCRIPTION
		"The total number of segments retransmitted - that
		is, the number of TCP segments transmitted
		containing one or more previously transmitted
		octets."
	::= { ecpTcpStatsEntry 8 }


------------
--  ECP UDP Statistics Definitions
------------


ecpUdpStatsTable  OBJECT-TYPE
	SYNTAX  SEQUENCE OF EcpUdpStatsEntry
	MAX-ACCESS	not-accessible
	STATUS	current
	DESCRIPTION
		"This table contains the User Datagram Protocol statistics
		for the Extended Control Processor (ECP) board."
	::= { ecpIpGroup 7 }

ecpUdpStatsEntry  OBJECT-TYPE
	SYNTAX	EcpUdpStatsEntry
	MAX-ACCESS	not-accessible
	STATUS	current
	DESCRIPTION
		"This entry contains the User Datagram Protocol statistics
		for the Extended Control Processor (ECP) board."
	INDEX	{ ecpBoardIndex }
	::= { ecpUdpStatsTable 1 }

EcpUdpStatsEntry ::= SEQUENCE {
		ecpUdpInDatagrams		Counter32,
		ecpUdpNoPorts			Counter32,
		ecpUdpInErrors			Counter32,
		ecpUdpOutDatagrams		Counter32
	}

ecpUdpInDatagrams  OBJECT-TYPE
	SYNTAX	Counter32
	MAX-ACCESS	read-only
	STATUS	current
	DESCRIPTION
		"The total number of UDP datagrams delivered to
		UDP users."
	::= { ecpUdpStatsEntry 1 }

ecpUdpNoPorts  OBJECT-TYPE
	SYNTAX	Counter32
	MAX-ACCESS	read-only
	STATUS	current
	DESCRIPTION
		"The total number of received UDP datagrams for
		which there was no application at the destination
		port."
	::= { ecpUdpStatsEntry 2 }

ecpUdpInErrors  OBJECT-TYPE
	SYNTAX	Counter32
	MAX-ACCESS	read-only
	STATUS	current
	DESCRIPTION
		"The number of received UDP datagrams that could
		not be delivered for reasons other than the lack
		of an application at the destination port."
	::= { ecpUdpStatsEntry 3 }

ecpUdpOutDatagrams  OBJECT-TYPE
	SYNTAX	Counter32
	MAX-ACCESS	read-only
	STATUS	current
	DESCRIPTION
            "The total number of UDP datagrams sent from this
            entity."
	::= { ecpUdpStatsEntry 4 }

ecpIpConfigTable  OBJECT-TYPE
      SYNTAX  SEQUENCE OF EcpIpConfigEntry
      MAX-ACCESS  not-accessible
      STATUS  current
      DESCRIPTION
              "IP Configuration table for the TCMs"
      ::= { ecpIpGroup 8 }

ecpIpConfigEntry  OBJECT-TYPE
      SYNTAX  EcpIpConfigEntry
      MAX-ACCESS  not-accessible
      STATUS  current
      DESCRIPTION
              "IP Configuration table entry for the TCMs"
      INDEX   { ecpBoardIndex }
      ::= { ecpIpConfigTable 1 }

EcpIpConfigEntry ::= SEQUENCE {
              ecpIpForwarding         INTEGER
      }

ecpIpForwarding OBJECT-TYPE
    SYNTAX  INTEGER {
                forwarding(1),    -- acting as a gateway
                not-forwarding(2) -- NOT acting as a gateway
            }
    MAX-ACCESS  read-write
    STATUS  current
    DESCRIPTION
            "The indication of whether this entity is acting
            as an IP gateway in respect to the forwarding of
            datagrams received by, but not addressed to, this
            entity.  IP gateways forward datagrams.  IP hosts
            do not (except those source-routed via the host).

            Note that for some managed nodes, this object may
            take on only a subset of the values possible.
            Accordingly, it is appropriate for an agent to
            return a `badValue' response if a management
            station attempts to change this object to an
            inappropriate value."
    ::= { ecpIpConfigEntry 1 }

------------------------------------------------------------------------
-- The Traps Configuration Group

ecpTrapNumberOfDest OBJECT-TYPE
	SYNTAX	Integer32
	MAX-ACCESS	read-only
	STATUS	current
	DESCRIPTION
		"The current number of configured trap destinations. 
		All traps are sent to all destinations."
	::= { ecpTrapConfGroup 1 }

ecpTrapDestTable OBJECT-TYPE
	SYNTAX	SEQUENCE OF EcpTrapDestEntry
	MAX-ACCESS	not-accessible
	STATUS	current
	DESCRIPTION
		"A table of destinations to which the agent sends traps."
	::= { ecpTrapConfGroup 2 }

ecpTrapDestEntry OBJECT-TYPE
	SYNTAX	EcpTrapDestEntry
	MAX-ACCESS	not-accessible
	STATUS	current
	DESCRIPTION
		"A table entry containing address of a management station, 
		to which the agent sends traps."
	INDEX	{ ecpBoardIndex, ecpTrapDest }
	::= { ecpTrapDestTable 1 }

EcpTrapDestEntry ::=
	SEQUENCE {
		ecpTrapDest		IpAddress,
		ecpTrapDestStatus	EntryStatus
	}

ecpTrapDest OBJECT-TYPE
	SYNTAX	IpAddress
	MAX-ACCESS	read-only
	STATUS	current
	DESCRIPTION
		"Address to which the agent sends traps. Usually a network
		management station sets this address to itself."
	::= { ecpTrapDestEntry 1 }

ecpTrapDestStatus OBJECT-TYPE
	SYNTAX	EntryStatus
	MAX-ACCESS	read-write
	STATUS	current
	DESCRIPTION
		"The status of this trap destination entry."
	::= { ecpTrapDestEntry 2 }

------------
--  ESI hardware definitions
------------

esiCardHwTable  OBJECT-TYPE
	SYNTAX	SEQUENCE OF EsiCardHwEntry
	MAX-ACCESS	not-accessible
	STATUS	current
	DESCRIPTION
     		"This table contains the hardware information for the
		External Synchronization Interface (ESI) cards."
	::= { esiHardware 1 }

esiCardHwEntry	OBJECT-TYPE
	SYNTAX	EsiCardHwEntry
   	MAX-ACCESS	not-accessible
	STATUS	current
	DESCRIPTION
		"This table entry contains the hardware information for
		a single External Synchronization Interface (ESI) card."
	INDEX	{ esiCardIndex }
	::= { esiCardHwTable 1 }

EsiCardHwEntry ::= SEQUENCE {
		esiCardIndex		INTEGER,
		esiHwCardType		INTEGER,
		esiHwCardVersion	Integer32,
		esiHwPllStatus   	INTEGER
	}

esiCardIndex    OBJECT-TYPE
	SYNTAX	INTEGER {
			slotX(1),
			slotY(2)
		}
   	MAX-ACCESS	read-only
	STATUS	current
	DESCRIPTION
		"This is the index for this External Synchronization
		Interface (ESI) card."
	::=  { esiCardHwEntry 1 }

esiHwCardType   OBJECT-TYPE
	SYNTAX	INTEGER {
			esiDs1TypeA(1),
			esiDs1TypeB(2),
			esiE1TypeA(3),
			esiE1TypeB(4)
		}
   	MAX-ACCESS	read-only
	STATUS	current
	DESCRIPTION
		"This is the card type for this External Synchronization
		Interface (ESI) card."
	::= { esiCardHwEntry 2 }

esiHwCardVersion  OBJECT-TYPE
	SYNTAX	Integer32
   	MAX-ACCESS	read-only
	STATUS	current
	DESCRIPTION
		"This is the card version for this External Synchronization
		Interface (ESI) card."
	::= { esiCardHwEntry 3 }

esiHwPllStatus  OBJECT-TYPE
	SYNTAX	INTEGER {
			pllFreeRun(1),
			pllLocked(2),
			pllAcquire(3),
			pllHoldover(4),
			pllRefQualFail(5)
		}
   	MAX-ACCESS	read-only
	STATUS	current
	DESCRIPTION
		"This is the card phase-locked loop (PLL) status for this
		External Synchronization Interface (ESI) card."
	::= { esiCardHwEntry 4 }


------------
--  ESI software definitions
------------

esiCardSwTable  OBJECT-TYPE
	SYNTAX	SEQUENCE OF EsiCardSwEntry
	MAX-ACCESS	not-accessible
	STATUS	current
	DESCRIPTION
     		"This table contains the software information for the
		External Synchronization Interface (ESI) cards."
	::= { esiSoftware 1 }

esiCardSwEntry  OBJECT-TYPE
	SYNTAX	EsiCardSwEntry
   	MAX-ACCESS	not-accessible
	STATUS	current
	DESCRIPTION
		"This table entry contains the software information for
		a single External Synchronization Interface (ESI) card."
	INDEX	{ esiCardIndex }
	::= { esiCardSwTable 1 }

EsiCardSwEntry ::= SEQUENCE {
		esiOperationStatus      INTEGER,
		esiCurrentTimingRef	INTEGER,
		esiRequestedTimingRef	INTEGER,
		esiPrimaryRefSource     EsiReferenceSource,
		esiSecondaryRefSource   EsiReferenceSource,
		esiCurrentFaultBits     Integer32,
		esiBitsFramingFormat	INTEGER,
		esiBitsCodingFormat	INTEGER,
		esiBitsOutputLevel	INTEGER,
		esiRevertiveSwitching	INTEGER,
		esiRevertiveDelay	TimeInterval,
		esiSwitchingDelay	TimeInterval
	}

esiOperationStatus  OBJECT-TYPE
	SYNTAX	INTEGER {
			enabled(1),
			disabled(2)
		}
	MAX-ACCESS	read-only
	STATUS	current
	DESCRIPTION
		"This is the operation status of the clock output for
		this External Synchronization Interface (ESI) card."
	::= { esiCardSwEntry 1 }

esiCurrentTimingRef  OBJECT-TYPE
	SYNTAX 	INTEGER	{
			refFreeRun(1),
			refIsPrimary(2),
			refIsSecondary(3),
			refIsBits1(5),
			refIsBits2(6)
		}
	MAX-ACCESS	read-only
	STATUS	current
	DESCRIPTION
		"This is the current timing reference in use for this
		External Synchronization Interface (ESI) card."
	::= { esiCardSwEntry 2 }

esiRequestedTimingRef  OBJECT-TYPE
	SYNTAX 	INTEGER	{
			requestFreeRun(1),
			requestPrimary(2),	
			requestSecondary(3),
			requestAutomatic(4),
			requestBits(5)
		}
	MAX-ACCESS	read-write
	STATUS	current
	DESCRIPTION
		"This is the timing reference requested to be used for
		this External Synchronization Interface (ESI) card."
	::= { esiCardSwEntry 3 }

esiPrimaryRefSource  OBJECT-TYPE
	SYNTAX  EsiReferenceSource
	MAX-ACCESS  read-write
	STATUS  current
	DESCRIPTION
		"This is the primary timing reference source for this
		External Synchronization Interface (ESI) card."
	::= { esiCardSwEntry 4 }

esiSecondaryRefSource  OBJECT-TYPE
	SYNTAX	EsiReferenceSource
	MAX-ACCESS	read-write
	STATUS  current
	DESCRIPTION
		"This is the secondary timing reference source for this
		External Synchronization Interface (ESI) card."
	::= { esiCardSwEntry 5 }

esiCurrentFaultBits  OBJECT-TYPE
	SYNTAX	Integer32
	MAX-ACCESS  read-only
	STATUS  current
	DESCRIPTION
		"This is the current state of the fault bits presented by
		this External Synchronization Interface (ESI) card."
	::= { esiCardSwEntry 6 }

esiBitsFramingFormat  OBJECT-TYPE
	SYNTAX  INTEGER {
			d4(1),		-- DS1 interface
			esf(2),		-- DS1 interface
			mfas(3),        -- E1  interface
			mfascrc4(4),    -- E1  interface
                        fas(5),         -- E1  interface
                        fascrc4(6)      -- E1  interface
		}
	MAX-ACCESS  read-write
	STATUS	current
	DESCRIPTION
		"This is the framing format of the BITS interface for
		this External Synchronization Interface (ESI) card."
	::= { esiCardSwEntry 7 }

esiBitsCodingFormat  OBJECT-TYPE
	SYNTAX	INTEGER {
			ami(1),		-- DS1 interface
			b8zs(2),	-- DS1 interface
			hdb3(3)		-- E1  interface
		}
	MAX-ACCESS  read-write
	STATUS  current
	DESCRIPTION
		"This is the coding format of the BITS interface for
		this External Synchronization Interface (ESI) card."
	::= { esiCardSwEntry 8 }

esiBitsOutputLevel  OBJECT-TYPE
	SYNTAX	INTEGER {
			esiDs1Level0-6(1),
			esiDs1Level1-2(2),
			esiDs1Level1-8(3),
			esiDs1Level2-4(4),
			esiDs1Level3-0(5)
		}
	MAX-ACCESS	read-write
	STATUS	current
	DESCRIPTION
		"This is the output level (dB) of the DS1 BITS interface
		for this External Synchronization Interface (ESI) card."
	::= { esiCardSwEntry 9 }

esiRevertiveSwitching  OBJECT-TYPE
	SYNTAX	INTEGER {
			enabled(1),
			disabled(2)
		}
	MAX-ACCESS	read-write
	STATUS	current
	DESCRIPTION
		"This is the status of the revertive switching for timing
		sources on this External Synchronization Interface (ESI)
		card."
	::= { esiCardSwEntry 10 }

esiRevertiveDelay  OBJECT-TYPE
	SYNTAX	TimeInterval
	MAX-ACCESS	read-write
	STATUS	current
	DESCRIPTION
		"This is the amount of time after the restoration of the
		primary timing reference before the External Synchronization
		Interface (ESI) card will be instructed to return to the
		primary timing reference.  This value is truncated to whole
		seconds."
	::= { esiCardSwEntry 11 }

esiSwitchingDelay  OBJECT-TYPE
	SYNTAX	TimeInterval
	MAX-ACCESS	read-write
	STATUS	current
	DESCRIPTION
		"This is the amount of time after the failure of a timing
		reference before the External Synchronization Interface
		(ESI) card will be instructed to switch to the next available
		timing reference.  This value is truncated to whole seconds."
	::= { esiCardSwEntry 12 }


------------
--  ESI Reference Source definitions
------------

esiReferenceTable  OBJECT-TYPE
	SYNTAX	SEQUENCE OF EsiReferenceEntry
	MAX-ACCESS	not-accessible
	STATUS	current
	DESCRIPTION
     		"This table contains the timing reference source
		information for the External Synchronization Interface
		(ESI) card."
	::= { esiSoftware 2 }

esiReferenceEntry  OBJECT-TYPE
	SYNTAX	EsiReferenceEntry
   	MAX-ACCESS	not-accessible
	STATUS	current
	DESCRIPTION
		"This table entry contains the timing reference source
		information for a single External Synchronization
		Interface (ESI) card."
	INDEX	{ esiCardIndex, esiRefSource }
	::= { esiReferenceTable 1 }

EsiReferenceEntry ::= SEQUENCE {
		esiRefSource		EsiReferenceSource,
		esiRefSourceText	DisplayString,
		esiRefSourceStatus	INTEGER,
		esiRefSourceAdminStatus	INTEGER,
		esiRefSourceQualStatus	INTEGER
	}

esiRefSource  OBJECT-TYPE
	SYNTAX	EsiReferenceSource
	MAX-ACCESS	read-only
	STATUS  current
	DESCRIPTION
		"This is the timing reference source index for the
		External Synchronization Interface (ESI) card."
	::= { esiReferenceEntry 1 }

esiRefSourceText  OBJECT-TYPE
	SYNTAX	DisplayString
	MAX-ACCESS  read-only
	STATUS  current
	DESCRIPTION
		"This is a textual description of the timing reference
		source that is provided to the External Synchronization
		Interface (ESI) card."
	::= { esiReferenceEntry 2 }

esiRefSourceStatus  OBJECT-TYPE
	SYNTAX	INTEGER {
			available(1),
			unavailable(2)
		}
	MAX-ACCESS	read-only
	STATUS	current
	DESCRIPTION
		"This is the status of the timing reference source
		that is provided to the External Synchornization
		Interface (ESI) card."
	::= { esiReferenceEntry 3 }

esiRefSourceAdminStatus  OBJECT-TYPE
	SYNTAX	INTEGER {
			up(1),
			down(2)
		}
	MAX-ACCESS	read-write
	STATUS	current
	DESCRIPTION
		"This is the admin status of the timing reference source
		that is provided to the External Synchornization
		Interface (ESI) card."
	::= { esiReferenceEntry 4 }

esiRefSourceQualStatus  OBJECT-TYPE
	SYNTAX	INTEGER {
			ok(1),
			fail(2)
		}
	MAX-ACCESS	read-write
	STATUS	current
	DESCRIPTION
		"This is the RefQual status of the timing reference source
		that is provided to the External Synchornization
		Interface (ESI) card."
	::= { esiReferenceEntry 5 }

------------
--  ECP Trap Definitions
------------

ecpOperatingModeChange NOTIFICATION-TYPE
	OBJECTS { ecpBoardIndex, ecpOperatingStatus, trapLogIndex }
	STATUS      current
	DESCRIPTION
                "This trap indicates that the Extended Control
		Processor (ECP) has change operating state."
        ::= { atmSwitch 0 1050 }

----------
--  ESI Trap Definitions
----------

esiTimingSourceChange  NOTIFICATION-TYPE
	OBJECTS { esiCardIndex, esiCurrentTimingRef, esiRefSource,
		    trapLogIndex }
	STATUS      current
	DESCRIPTION
		"This trap is generated whenever the External Synchronization
		Interface (ESI) timing source (esiCurrentTimingRef) is changed
		either manually or by the system due to failure detection."
	::= { atmSwitch 0 1051 }

esiTimingSourceFailed  NOTIFICATION-TYPE
	OBJECTS { esiCardIndex, esiCurrentTimingRef, esiRefSource,
		    trapLogIndex }
	STATUS      current
	DESCRIPTION
		"This trap is generated whenever the External Synchronization
		Interface (ESI) timing source (esiCurrentTimingRef) fails."
	::= { atmSwitch 0 1052 }

ecpStandbyFailed  NOTIFICATION-TYPE
        OBJECTS { ecpBoardIndex, trapLogIndex }
        STATUS      current
        DESCRIPTION
                "This trap is generated whenever the Standby Timing Control
                Module (TCM) appears to haved failed.  This is determined by
                lack of response from it."
        ::= { atmSwitch 0 1076 }

END
