ERI-DNX-STS1-MIB DEFINITIONS ::= BEGIN

IMPORTS
	MODULE-IDENTITY, OBJECT-IDENTITY, OBJECT-TYPE, Integer32,
	Counter32, NOTIFICATION-TYPE
		FROM SNMPv2-SMI
    DisplayString, TEXTUAL-CONVENTION
        FROM SNMPv2-TC
    eriMibs
        FROM ERI-ROOT-SMI
    devices, PortStatus, DecisionType, FunctionSwitch, 
    LinkPortAddress, LinkCmdStatus, trapSequence
        FROM ERI-DNX-SMC-MIB;

eriDNXSts1MIB MODULE-IDENTITY 
      LAST-UPDATED    "200204080000Z"
      ORGANIZATION    "Eastern Research, Inc."
      CONTACT-INFO
                      "Customer Service
                Postal: Eastern Research, Inc.
                        225 Executive Drive
                        Moorestown, NJ 08057
                Phone:  +1-800-337-4374
                Email:  support@erinc.com"
      DESCRIPTION
              "The ERI Enterprise MIB Module for the DNX STS1 Device."

  	::= { eriMibs 4 }

-- *************************************************************************
-- The enterprise OID will be { iso(1) org(3) dod(6) internet(1) private(4)
--                              enterprises(1) virent(644) eri(2) dnx (4) 
--                              devices(2), dnxSTS1(3) }

-- *************************************************************************
-- The STS-1 card is currently controlled via the Config or Diag groups.
-- The Configuration branch is used to perform all STS-1 Mapper and Link 
-- provisioning functions while the Diagnostic branch is used to run tests 
-- and view associated Statistics. 
-- *************************************************************************

dnxSTS1    OBJECT IDENTIFIER 	::= { devices 3 }
sts1Config OBJECT IDENTIFIER 	::= { dnxSTS1 1 }
sts1Diag   OBJECT IDENTIFIER 	::= { dnxSTS1 2 }   

-- *************************************************************************
-- The following textual conventions are used in this MIB
-- *************************************************************************

VtGroupType ::= TEXTUAL-CONVENTION
		STATUS  current
        DESCRIPTION
           "Indicates the type of Virtual Tributaries (VT) grouping option used 
           on the links. 
            VT 1.5 is used to group T1 links into 7 groups of 4 for the 28 links.
            VT 2.0 is used to group E1 links into 7 groups of 3 for the 21 links.
            Using the VT 2.0, links divisible by 4 are skipped over and not used."
        SYNTAX INTEGER {
                vt2-0-e1(0),
                vt1-5-ds1(1)
                }
		
-- *************************************************************************
-- This table is the STS-1 Mapper LIU configuration table

sts1MapperConfigTable OBJECT-TYPE
        SYNTAX SEQUENCE OF STS1MapperConfigEntry
        MAX-ACCESS not-accessible
        STATUS current
        DESCRIPTION
            "This is the STS-1 Mapper LIU Configuration table which consists
            of an entry for each of the STS-1 cards.  The total number of
            entries depends on the number of STS-1 cards in the nest."
        ::= { sts1Config 1 }

sts1MapperConfigEntry OBJECT-TYPE
        SYNTAX STS1MapperConfigEntry
        MAX-ACCESS not-accessible
        STATUS current
        DESCRIPTION
            "The conceptual row of the STS-1 Mapper LIU Configuration table. 
            A row in this table cannot be added or deleted, only modified."
        INDEX { sts1MapperAddr }
        ::= { sts1MapperConfigTable 1 }

STS1MapperConfigEntry ::=
        SEQUENCE {
                sts1MapperAddr        LinkPortAddress,   -- RO
                sts1MapperResource    Integer32,         -- RO
                sts1VtGroup1          VtGroupType,       -- RO
                sts1VtGroup2          VtGroupType,       -- RO
                sts1VtGroup3          VtGroupType,       -- RO
                sts1VtGroup4          VtGroupType,       -- RO
                sts1VtGroup5          VtGroupType,       -- RO
                sts1VtGroup6          VtGroupType,       -- RO
                sts1VtGroup7          VtGroupType,       -- RO
                sts1VtMapping         INTEGER,           -- RO
                sts1Timing            INTEGER,
                sts1ShortCable        FunctionSwitch,
                sts1MaprCmdStatus     LinkCmdStatus
                }

sts1MapperAddr OBJECT-TYPE
        SYNTAX LinkPortAddress
        MAX-ACCESS read-only
        STATUS current
        DESCRIPTION
            "This number uniquely identifies a STS-1 slot/mapper."
        ::= { sts1MapperConfigEntry 1 }

sts1MapperResource OBJECT-TYPE
        SYNTAX Integer32
        MAX-ACCESS read-only
        STATUS current
        DESCRIPTION
           "Uniquely identifies an STS1 Device in the system.
            This number is provided as key to allow the manager to 
            map this entry to a corresponding Resource Table entry."
        ::= { sts1MapperConfigEntry 2 }
        
sts1VtGroup1 OBJECT-TYPE
        SYNTAX VtGroupType 
        MAX-ACCESS read-only
        STATUS current
        DESCRIPTION
           "Indicates the type of grouping option used to on links 1 through 4. 
            Using the VT 2.0, link 4 is not used."
        ::= { sts1MapperConfigEntry 3 }

sts1VtGroup2 OBJECT-TYPE
        SYNTAX VtGroupType 
        MAX-ACCESS read-only
        STATUS current
        DESCRIPTION
           "Indicates the type of grouping option used to on links 5 through 8. 
            Using the VT 2.0, link 8 is not used."
        ::= { sts1MapperConfigEntry 4 }

sts1VtGroup3 OBJECT-TYPE
        SYNTAX VtGroupType 
        MAX-ACCESS read-only
        STATUS current
        DESCRIPTION
           "Indicates the type of grouping option used to on links 9 through 12. 
            Using the VT 2.0, link 12 is not used."
        ::= { sts1MapperConfigEntry 5 }

sts1VtGroup4 OBJECT-TYPE
        SYNTAX VtGroupType 
        MAX-ACCESS read-only
        STATUS current
        DESCRIPTION
           "Indicates the type of grouping option used to on links 13 through 16. 
            Using the VT 2.0, link 16 is not used."
        ::= { sts1MapperConfigEntry 6 }

sts1VtGroup5 OBJECT-TYPE
        SYNTAX VtGroupType 
        MAX-ACCESS read-only
        STATUS current
        DESCRIPTION
           "Indicates the type of grouping option used to on links 17 through 20. 
            Using the VT 2.0, link 20 is not used."
        ::= { sts1MapperConfigEntry 7 }

sts1VtGroup6 OBJECT-TYPE
        SYNTAX VtGroupType 
        MAX-ACCESS read-only
        STATUS current
        DESCRIPTION
           "Indicates the type of grouping option used to on links 21 through 24. 
            Using the VT 2.0, link 24 is not used."
        ::= { sts1MapperConfigEntry 8 }

sts1VtGroup7 OBJECT-TYPE
        SYNTAX VtGroupType 
        MAX-ACCESS read-only
        STATUS current
        DESCRIPTION
           "Indicates the type of grouping option used to on links 25 through 28. 
            Using the VT 2.0, link 28 is not used."
        ::= { sts1MapperConfigEntry 9 }

sts1VtMapping OBJECT-TYPE
        SYNTAX INTEGER {
                standardVT (0),
                sequencialFrm (1)
                }
        MAX-ACCESS read-only
        STATUS current
        DESCRIPTION
           "Indicates the Mapper Standard currently in use."
        ::= { sts1MapperConfigEntry 10 }

sts1Timing OBJECT-TYPE
        SYNTAX INTEGER  {
                internal (0),
                ec1-Line (1)                
                }
        MAX-ACCESS read-write
        STATUS current
        DESCRIPTION
           "Indicates whether the STS-1 device uses an internal or external
           clock source."
        ::= { sts1MapperConfigEntry 11 }

sts1ShortCable OBJECT-TYPE
        SYNTAX FunctionSwitch
        MAX-ACCESS read-write
        STATUS current
        DESCRIPTION
           "Indicates the line build out of the STS-1 transmitter.  'enable' when 
           attached to a cable less than 50 feet long."
        ::= { sts1MapperConfigEntry 12 }

sts1MaprCmdStatus OBJECT-TYPE
        SYNTAX LinkCmdStatus
        MAX-ACCESS read-write
        STATUS current
        DESCRIPTION
           "The command status for this link configuration row/record.
           The value used in a SET will be replaced by a response
           value in the GET RESPONSE indicating success or failure.
           		
            Default Response State used in GET RESPONSE Command
                ready-for-command (0)
                    initial default status for a row           
                    
            STS1 Link Commands used in SET Command (1..199)            
                update-link-config(1),
                    Change existing Link Configuration
               		
            Response States used in GET RESPONSE Command (200..399)
                update-successful (201)
                    Link data has been successfully changed
                                		
            STS1 Mapper Config Error Codes used in GET RESPONSE Command (400..699)
                err-general-link-config-error (400)
                    Unknown link configuration error occurred                
                err-invalid-link-status (401)
                    Unrecognized link status setting
                err-invalid-link-framing (402)         
                    Line framing type not valid for link type
                err-invalid-link-command (403)
                    Unrecognized link command-action
                err-invalid-link-op-mode (407)
                    Configured M13 Op mode not valid for port; verify other
                    link parameters match desired new mode                
                err-invalid-link-rem-loop (408)         
                    Remote Loop type not valid for sts1 frame type
                err-invalid-link-ais (409)
                    Unrecognized sts1 AIS selection
                err-data-locked-by-another-user (450)
                    Another administrative user is making changes to this
                    part of the system via a terminal session. Check Event
                    Log for user name
                err-snmp-parse-failed (500)
                    Agent could not parse variable
                err-invalid-snmp-type (501)
                    Variable ASN type does not match Agent defined type 
                err-invalid-snmp-var-size (502)
                    Variable size is too big"                 		
       ::= { sts1MapperConfigEntry 13}


-- *************************************************************************
-- This table is the STS T1/E1 Link configuration table

sts1T1E1LinkConfigTable OBJECT-TYPE
        SYNTAX SEQUENCE OF STS1T1E1LinkConfigEntry
        MAX-ACCESS not-accessible
        STATUS current
        DESCRIPTION
            "This is the STS T1/E1 Link Configuration table which consists
            of an entry for each of the card's 28 links.  The total number of
            entries depends on the number of STS1 cards in the nest."
        ::= { sts1Config 2 }

sts1T1E1LinkConfigEntry OBJECT-TYPE
        SYNTAX STS1T1E1LinkConfigEntry
        MAX-ACCESS not-accessible
        STATUS current
        DESCRIPTION
            "The conceptual row of the STS T1/E1 Link Configuration table. 
            A row in this table cannot be added or deleted, only modified."
        INDEX { sts1T1E1CfgLinkAddr }
        ::= { sts1T1E1LinkConfigTable 1 }

STS1T1E1LinkConfigEntry ::=
        SEQUENCE {
                sts1T1E1CfgLinkAddr     LinkPortAddress,  -- RO
                sts1T1E1CfgResource     Integer32,        -- RO
                sts1T1E1CfgLinkName     DisplayString,
                sts1T1E1Status          PortStatus,
                sts1T1E1Clear           INTEGER,                
                sts1T1E1Framing         INTEGER,
                sts1T1E1NetLoop         INTEGER,
                sts1T1E1YelAlrm         INTEGER,
                sts1T1E1RecoverTime     INTEGER,
                sts1T1E1EsfFormat       INTEGER,
                sts1T1E1IdleCode        INTEGER,
                sts1T1E1CfgCmdStatus    LinkCmdStatus,
                sts1T1E1Gr303Facility   DecisionType      -- obsolete
                }

sts1T1E1CfgLinkAddr OBJECT-TYPE
        SYNTAX LinkPortAddress
        MAX-ACCESS read-only
        STATUS current
        DESCRIPTION
            "This number uniquely identifies a STS T1/E1 link resource. 
            This number will be used throughout the system to identify 
            a unique resource."
        ::= { sts1T1E1LinkConfigEntry 1 }

sts1T1E1CfgResource OBJECT-TYPE
        SYNTAX Integer32
        MAX-ACCESS read-only
        STATUS current
        DESCRIPTION
                "Uniquely identifies an STS T1/E1 Channel in the system.
                 This number is provided as key to allow the manager to 
                 map this entry to a corresponding Resource Table entry."
        ::= { sts1T1E1LinkConfigEntry 2 }

sts1T1E1CfgLinkName OBJECT-TYPE
        SYNTAX DisplayString (SIZE(0..20))
        MAX-ACCESS read-write
        STATUS current
        DESCRIPTION
        	"This is the user friendly text name to identify the link."
        ::= { sts1T1E1LinkConfigEntry 3 }

sts1T1E1Status OBJECT-TYPE
        SYNTAX PortStatus
        MAX-ACCESS read-write
        STATUS current
        DESCRIPTION
           "Dictates the current status of the link, in-service or 
           out-of-service."
        ::= { sts1T1E1LinkConfigEntry 4 }

sts1T1E1Clear OBJECT-TYPE
        SYNTAX INTEGER {
        	disabled (0),
        	framed   (1),
        	unframed (2)
        	}
        MAX-ACCESS read-write
        STATUS current
        DESCRIPTION
           "Determines if the port supports T1 or E1 unframed."
        ::= { sts1T1E1LinkConfigEntry 5 }

sts1T1E1Framing OBJECT-TYPE
        SYNTAX INTEGER {
--        	e1 (0),
--        	e1Crc (1),
--        	e1Cas (2),
--        	e1CasCrc (3),
--        	e1Unframed (4),
        	t1Esf (5),
        	t1D4 (6),
        	t1Unframed (7)
        	}
        MAX-ACCESS read-write
        STATUS current
        DESCRIPTION
           "Determines the type of framing used on the line.  
           Choose between T1 SuperFrame 'D4', Extended SuperFrame (ESF),
           or T1 Unframed.  Currently E1 is not supported. When value of 
           sts1T1E1Clear is set to unframed (2), the only valid framing 
           options are: e1Unframed(4) or t1Unframed(7)."
        ::= { sts1T1E1LinkConfigEntry 6 }

sts1T1E1NetLoop OBJECT-TYPE
        SYNTAX FunctionSwitch
        MAX-ACCESS read-write
        STATUS current
        DESCRIPTION
           "Determines whether or not the module should respond to loop 
           diagnostic commands received from the network supplier. Select 
           'enable' unless the commands are to be passed to another STS1 
           device."
        ::= { sts1T1E1LinkConfigEntry 7 }

sts1T1E1YelAlrm OBJECT-TYPE
        SYNTAX DecisionType
        MAX-ACCESS read-write
        STATUS current
        DESCRIPTION
           "Causes the module to discard data and send a yellow alarm if it
           is in a red alarm condition after a 3 second period. 'Yes' must
           be chosen if the network supplier is a common carrier, such as a 
           telephone company."
        ::= { sts1T1E1LinkConfigEntry 8 }

sts1T1E1RecoverTime OBJECT-TYPE
        SYNTAX INTEGER {
        	timeout-3-secs (3),
        	timeout-10-secs(10),
        	timeout-15-secs(15)
        	}
        MAX-ACCESS read-write
        STATUS current
        DESCRIPTION
           "This is the red alarm timeout value.  Determines the amount 
           of seconds the port will wait to stop sending the yellow alarm 
           when coming out of a red alarm condition."
        ::= { sts1T1E1LinkConfigEntry 9 }

sts1T1E1EsfFormat OBJECT-TYPE
        SYNTAX INTEGER {
        	att-54016 (0),
        	ansi-t1-403 (1)
        	}
        MAX-ACCESS read-write
        STATUS current
        DESCRIPTION
           "Determines the type of ESF network commands the  T-1 link 
           will respond to. It has no meaning for D4 networks. With ESF 
           networks, this information must be obtained from the network 
           supplier."
        ::= { sts1T1E1LinkConfigEntry 10 }

sts1T1E1IdleCode OBJECT-TYPE
        SYNTAX INTEGER {
        	busy (0),
        	idle (1)
        	}
        MAX-ACCESS read-write
        STATUS current
        DESCRIPTION
           "Determines the whether the code that will be transmitted over 
           the unused links will be 'idle' or 'busy' (all 1's)."
        ::= { sts1T1E1LinkConfigEntry 11 }

sts1T1E1CfgCmdStatus OBJECT-TYPE
        SYNTAX LinkCmdStatus 
        MAX-ACCESS read-write
        STATUS current
        DESCRIPTION
           "The command status for this link configuration row/record.
           The value used in a SET will be replaced by a response
           value in the GET RESPONSE indicating success or failure.
           		
            Default Response State used in GET RESPONSE Command
                ready-for-command (0)
                    initial default status for a row           
                    
            STS1-T1 Link Commands used in SET Command (1..199)            
                update(1)
                    Change existing Link Configuration
                inServiceAll (7)
                    Change Link Status to in-service for all 8 links.
                copyToAll (9)
                    Copy T1 Link configuration to all other links 
                    within the same device
                outOfServiceAll (12)
                    Change Link Status to out-of-service for all 8 links.
               		
            Response States used in GET RESPONSE Command (100..199)
                update-successful (101)
                    Link data has been successfully changed
                insvc-successful (107)
                    All Links have been successfully placed In Service
                copy-successful (109)
                    T1 Link data has been successfully copied to other links
                oos-successful (112)
                    All Links have been successfully placed Out of Service
                                		
            STS1-T1 Link Config Error Codes used in GET RESPONSE Command (400..699)
                err-general-link-config-error (400)
                    Unknown link configuration error occurred                
                err-invalid-link-status (401)
                    Unrecognized link status setting
                err-invalid-link-framing (402)         
                    Line framing type not valid for link type
                err-invalid-link-command (403)
                    Unrecognized link command-action
                err-invalid-esf-format (405)
                    ESF type not applicable to link type
                err-invalid-link-density (406)
                    Unrecognized T1 link density setting 
                err-invalid-network-loop (410)
                    Unrecognized network loop setting
                err-invalid-yellow-alrm (411)
                    Unrecognized yellow alarm setting
                err-invalid-red-timeout (412)
                    Unrecognized red alarm timeout
                err-invalid-idle-code (413)
                    Unrecognized idle code
                err-device-in-standby (414)
                    Can't change config for designated Standby device
                err-data-locked-by-another-user (450)
                    Another administrative user is making changes to this
                    part of the system via a terminal session. Check Event
                    Log for user name           		
                err-snmp-parse-failed (500)
                    Agent could not parse variable
                err-invalid-snmp-type (501)
                    Variable ASN type does not match Agent defined type 
                err-invalid-snmp-var-size (502)
                    Variable size is too big"                 		
        ::= { sts1T1E1LinkConfigEntry 12 }

sts1T1E1Gr303Facility OBJECT-TYPE
        SYNTAX DecisionType
        MAX-ACCESS read-only
        STATUS obsolete
        DESCRIPTION
           "Enables link to be configured as a Gr303 Facility"
        ::= { sts1T1E1LinkConfigEntry 13 }

-- *************************************************************************
-- This table is the STS-1 Mapper Status Display table

sts1MapperStatusTable OBJECT-TYPE
        SYNTAX SEQUENCE OF STS1MapperStatusEntry
        MAX-ACCESS not-accessible
        STATUS current
        DESCRIPTION
            "This is the STS-1 Mapper Status table which consists of a single
            entry for each card's Mapper Display.  The total number of
            entries depends on the number of STS1 cards in the node."
        ::= { sts1Diag 1 }

sts1MapperStatusEntry OBJECT-TYPE
        SYNTAX STS1MapperStatusEntry
        MAX-ACCESS not-accessible
        STATUS current
        DESCRIPTION
            "The conceptual row of the Mapper table. 
            A row in this table cannot be added or deleted, only modified."
        INDEX { sts1MapperStatusAddr }
        ::= { sts1MapperStatusTable 1 }

STS1MapperStatusEntry ::=
        SEQUENCE {
                sts1MapperStatusAddr            LinkPortAddress,  -- RO
                sts1MapperStatusResource        Integer32,        -- RO
                sts1MapperStatusState           INTEGER,
                sts1MapperStatusLOSErrs         Counter32,
                sts1MapperStatusOOFErrs         Counter32,
                sts1MapperStatusLOFErrs      	Counter32,
                sts1MapperStatusLOPtrErrs       Counter32,
                sts1MapperStatusAISErrs         Counter32,
                sts1MapperStatusMultiFErrs      Counter32,
                sts1MapperStatusRxTraceErrs    	Counter32,
                sts1MapperStatusTotErrSecs      Counter32,
                sts1MapperStatusCmdStatus       INTEGER        -- RW              
              	}

sts1MapperStatusAddr OBJECT-TYPE
        SYNTAX LinkPortAddress
        MAX-ACCESS read-only
        STATUS current
        DESCRIPTION
            "This number uniquely identifies a STS1 Mapper resource. 
            This number will be used throughout the system to identify 
            a unique resource."
        ::= { sts1MapperStatusEntry 1 }

sts1MapperStatusResource OBJECT-TYPE 
        SYNTAX Integer32
        MAX-ACCESS read-only
        STATUS current
        DESCRIPTION
            "This number uniquely identifies a STS1 Mapper resource. 
            This number is provided as key to allow the manager to map this
            entry to a corresponding Resource Table Entry."
        ::= { sts1MapperStatusEntry 2 }

sts1MapperStatusState OBJECT-TYPE
        SYNTAX INTEGER {
                ok  (0),
                lof (32),             -- bit 5
                lop (256),            -- bit 8 
                oof (512),            -- bit 9
                ais (1024),           -- bit 10
                los (8192),           -- bit 13  
                lomf (131072),        -- bit 17
                errors(2147483647)    -- all
                }
        MAX-ACCESS read-only
        STATUS current
        DESCRIPTION
           "Determines the current line condition status of the Mapper.
                ok  (0),
                lof (32),             -- bit 5
                lop (256),            -- bit 8 
                oof (512),            -- bit 9
                ais (1024),           -- bit 10
                los (8192),           -- bit 13  
                lomf (131072),        -- bit 17
                errors (2147483647)   -- all
            "
       ::= { sts1MapperStatusEntry 3 }

sts1MapperStatusLOSErrs OBJECT-TYPE
        SYNTAX Counter32
        MAX-ACCESS read-only
        STATUS current
        DESCRIPTION
            "This is the number of seconds a Loss of Signal was declared."
        ::= { sts1MapperStatusEntry 4 } 
     
sts1MapperStatusOOFErrs OBJECT-TYPE
        SYNTAX Counter32
        MAX-ACCESS read-only
        STATUS current
        DESCRIPTION
            "This is the number of seconds an Out Of Frame alignement error was declared."
        ::= { sts1MapperStatusEntry 5 } 
        
sts1MapperStatusLOFErrs OBJECT-TYPE
        SYNTAX Counter32
        MAX-ACCESS read-only
        STATUS current
        DESCRIPTION
            "This is the number of seconds a Loss of Frame was declared."
        ::= { sts1MapperStatusEntry 6 } 

sts1MapperStatusLOPtrErrs OBJECT-TYPE
        SYNTAX Counter32
        MAX-ACCESS read-only
        STATUS current
        DESCRIPTION
            "This is the number of seconds a Loss of Pointer was declared."
        ::= { sts1MapperStatusEntry 7 } 
        
sts1MapperStatusAISErrs OBJECT-TYPE
        SYNTAX Counter32
        MAX-ACCESS read-only
        STATUS current
        DESCRIPTION
            "This is the number of seconds an Alarm Indication Signal was declared."
        ::= { sts1MapperStatusEntry 8 } 

sts1MapperStatusMultiFErrs OBJECT-TYPE   
        SYNTAX Counter32
        MAX-ACCESS read-only
        STATUS current
        DESCRIPTION
            "This is the number of seconds a Near End Loss of Multi-Frame Signal was declared."
        ::= { sts1MapperStatusEntry 9 } 

sts1MapperStatusRxTraceErrs OBJECT-TYPE
        SYNTAX Counter32
        MAX-ACCESS read-only
        STATUS current
        DESCRIPTION
            "This is the number of seconds an error has been detected in the receive path trace."
        ::= { sts1MapperStatusEntry 10 } 

sts1MapperStatusTotErrSecs OBJECT-TYPE
        SYNTAX Counter32
        MAX-ACCESS read-only
        STATUS current
        DESCRIPTION
            "This is the total number of Errored Seconds."
        ::= { sts1MapperStatusEntry 11 } 

sts1MapperStatusCmdStatus OBJECT-TYPE
        SYNTAX INTEGER {
    -- Initial default status for a row
            ready-for-command (0),
    -- Action States used in SET Command (1..99)
            update (1),
            clearErrors (14),
                                
    -- Response States used in GET RESPONSE Command (100..199)
            update-successful (101),
            clear-successful (114),
                                
    -- Mapper Error Codes used in GET RESPONSE Command (200..799)
            err-general-test-error (200),
            err-field-cannot-be-set (206),
            err-snmp-parse-failed(500),
            err-invalid-snmp-type(501),
            err-invalid-snmp-var-size(502) 
            }
        MAX-ACCESS read-write
        STATUS current
        DESCRIPTION
            "This is the command status for the Mapper Row.
           The value used in a SET will be replaced by a response
           value in the GET RESPONSE indicating success or failure.

            Default Response State used in GET RESPONSE Command
                ready-for-command (0)
                    initial default status for a row           
                    
            Action Commands used in SET Command (1..99)            
                update (1)
                    Can be used optionally when activating loops and berts
                    in order to get status code back in response
                clearErrors (14)
                    Resets all error counters to zero
                                
            Response States used in GET RESPONSE Command (100..199)
                update-successful (101)
                    Test action has been successfully performed
                clear-successful (114)
                    Error counts have been successfully cleared
                                
            The Error Codes used in GET RESPONSE Command (200..799)
                err-general-test-error (200)
                    Unknown Test request error occurred.
                err-field-cannot-be-set (206)
                    Read-only field was included in SET request
                err-snmp-parse-failed (500)
                    Agent could not parse variable
                err-invalid-snmp-type (501)
                    Variable ASN type does not match Agent defined type 
                err-invalid-snmp-var-size (502)
                    Variable size is too big" 
        ::= { sts1MapperStatusEntry 12 } 
        
-- *************************************************************************
-- This table is the STS1 LIU Diagnostic Status table

sts1LIUTable OBJECT-TYPE
        SYNTAX SEQUENCE OF STS1LIUEntry
        MAX-ACCESS not-accessible
        STATUS current
        DESCRIPTION
            "This is the STS1 LIU Diagnostic Status table which consists
            of an entry for each STS1 card's Line Interface Unit Display.  The 
            number of entries depends on the number of STS1 cards in the node."
        ::= { sts1Diag 2 }

sts1LIUEntry OBJECT-TYPE
        SYNTAX STS1LIUEntry
        MAX-ACCESS not-accessible
        STATUS current
        DESCRIPTION
            "The conceptual row of the Mapper table. 
            A row in this table cannot be added or deleted, only modified."
        INDEX { sts1LIUAddr }
        ::= { sts1LIUTable 1 }

STS1LIUEntry ::=
        SEQUENCE {
                sts1LIUAddr                LinkPortAddress,  
                sts1LIUResource            Integer32,          
                sts1LIUBertState           INTEGER,          -- RW
                sts1LIUBertErrSecs         Counter32,
                sts1LIUBertDuration        Counter32,
                sts1LIULoopType            INTEGER,          -- RW
                sts1LIUDigitalErrs         Counter32,
                sts1LIUAnalogErrs          Counter32,
                sts1LIUExcessZeros         Counter32,
                sts1LIUCodingViolationErrs Counter32,
                sts1LIUPRBSErrs            Counter32,
              	sts1LIUCmdStatus           INTEGER           -- RW              
                }

sts1LIUAddr OBJECT-TYPE
        SYNTAX LinkPortAddress
        MAX-ACCESS read-only
        STATUS current
        DESCRIPTION
            "This number uniquely identifies a STS1 Mapper resource address. 
            This number will be used throughout the system to identify 
            a unique resource."
        ::= { sts1LIUEntry 1 }

sts1LIUResource OBJECT-TYPE 
        SYNTAX Integer32
        MAX-ACCESS read-only
        STATUS current
        DESCRIPTION
            "This number uniquely identifies a STS1 Mapper resource. 
            This number is provided as a key to allow the manager to map this
            entry to a corresponding Resource Table Entry."
        ::= { sts1LIUEntry 2 }

sts1LIUBertState OBJECT-TYPE
        SYNTAX INTEGER{
        	off (45),
        	liu-bert  (44)
        	}	
        MAX-ACCESS read-write
        STATUS current
        DESCRIPTION
            "This is the LIU Bert State indicated by on/off."
        ::= { sts1LIUEntry 3 } 
     
sts1LIUBertErrSecs OBJECT-TYPE
        SYNTAX Counter32
        MAX-ACCESS read-only
        STATUS current
        DESCRIPTION
            "This is the number of LIU Bert Errored seconds."
        ::= { sts1LIUEntry 4 } 
        
sts1LIUBertDuration OBJECT-TYPE
        SYNTAX Counter32
        MAX-ACCESS read-only
        STATUS current
        DESCRIPTION
            "This is the number of seconds for the LIU Bert Duration."
        ::= { sts1LIUEntry 5 } 

sts1LIULoopType OBJECT-TYPE
        SYNTAX INTEGER {
        	off 	(0),
        	mapper  (1),
        	liu		(39)
        	}
        MAX-ACCESS read-write
        STATUS current
        DESCRIPTION
            "Indicates the loopback status of the Mapper/LIU for this STS1 device.
              off        (0) - indicates loopback is disabled
        	  mapper     (1) - indicates Mapper local data is looped back to itself
        	  liu        (39)- indicates Line Interface Unit local data is looped back
        	                   to itself."
        ::= { sts1LIUEntry 6 } 
        
sts1LIUDigitalErrs OBJECT-TYPE
        SYNTAX Counter32
        MAX-ACCESS read-only
        STATUS current
        DESCRIPTION
            "This is the number of seconds recorded for the LIU Digital Errors."
        ::= { sts1LIUEntry 7 } 

sts1LIUAnalogErrs OBJECT-TYPE   
        SYNTAX Counter32
        MAX-ACCESS read-only
        STATUS current
        DESCRIPTION
            "This is the number of seconds recorded for the LIU Analog Errors."
        ::= { sts1LIUEntry 8 } 

sts1LIUExcessZeros OBJECT-TYPE
        SYNTAX Counter32
        MAX-ACCESS read-only
        STATUS current
        DESCRIPTION
            "This is the number of seconds LIU Excess zero errors were detected."
        ::= { sts1LIUEntry 9 } 

sts1LIUCodingViolationErrs OBJECT-TYPE
        SYNTAX Counter32
        MAX-ACCESS read-only
        STATUS current
        DESCRIPTION
            "This is the total number of Errored Seconds for the LIU Coding Violation."
        ::= { sts1LIUEntry 10 } 

sts1LIUPRBSErrs OBJECT-TYPE
        SYNTAX Counter32
        MAX-ACCESS read-only
        STATUS current
        DESCRIPTION
            "This is the total number of Errored Seconds for the LIU PRBS check."
        ::= { sts1LIUEntry 11 } 

sts1LIUCmdStatus OBJECT-TYPE
        SYNTAX INTEGER {
    -- Initial default status for a row
            ready-for-command (0),
    -- Action States used in SET Command (1..99)
            update (1),
            clearErrors (14),
                                
    -- Response States used in GET RESPONSE Command (100..199)
            update-successful (101),
            clear-successful  (114),                               

    -- LIU Error Codes used in GET RESPONSE Command (200..799)
            err-general-test-error (200),
            err-invalid-loop-type (202),
            err-invalid-bert-type (203),
            err-test-in-progress (205),
            err-field-cannot-be-set (206),
            err-snmp-parse-failed(500),
            err-invalid-snmp-type(501),
            err-invalid-snmp-var-size(502) 
            }
        MAX-ACCESS read-write
        STATUS current
        DESCRIPTION
            "This is the command status for the LIU Mapper Row.
           The value used in a SET will be replaced by a response
           value in the GET RESPONSE indicating success or failure.

            Default Response State used in GET RESPONSE Command
                ready-for-command (0)
                    initial default status for a row           
                    
            LIU Action Commands used in SET Command (1..99)            
                update (1)
                    Can be used optionally when activating loops and berts
                    in order to get status code back in response
                clearErrors (14)
                    Resets all error counters and bert test time to zero
                                
            Response States used in GET RESPONSE Command (100..199)
                update-successful (101)
                    Test action has been successfully performed
                clear-successful (114)
                    Error counts have been successfully cleared
                                
            LIU Test Error Codes used in GET RESPONSE Command (200..799)
                err-general-test-error (200)
                    Unknown Test request error occurred.
                err-invalid-loop-type (202)
                    Unrecognized loop selection
                err-invalid-bert-type (203)
                    Unrecognized bert selection
                err-test-in-progress (205)
                    Requested action cannot be performed during bert
                err-field-cannot-be-set (206)
                    Read-only field was included in SET request
                err-snmp-parse-failed (500)
                    Agent could not parse variable
                err-invalid-snmp-type (501)
                    Variable ASN type does not match Agent defined type 
                err-invalid-snmp-var-size (502)
                    Variable size is too big" 
        ::= { sts1LIUEntry 12 } 

-- *************************************************************************

dnxSTS1Enterprise OBJECT-IDENTITY
      STATUS current
      DESCRIPTION "ERI DNX STS1 Enterprise for Alarms/Events"
    ::= { dnxSTS1 0 }

sts1MapperConfigTrap NOTIFICATION-TYPE
        OBJECTS {
            trapSequence,
            sts1MapperAddr,
            sts1MaprCmdStatus
            }
        STATUS current
        DESCRIPTION
              	"This trap is used to notify a NMS that a user has updated 
              	the Link configuration for a given STS1 Mapper entry."
        ::= { dnxSTS1Enterprise 1 }

sts1T1E1ConfigTrap NOTIFICATION-TYPE
        OBJECTS {
            trapSequence,
            sts1T1E1CfgLinkAddr,
            sts1T1E1CfgCmdStatus
            }
        STATUS current
        DESCRIPTION
              	"This trap is used to notify a NMS that a user has updated 
              	the Link configuration for a given STS-1 T1 channel entry."
        ::= { dnxSTS1Enterprise 2 } 
                       
END

-- *************************************************************************
--
--  MIB:    ERI-DNX-HDS3-MIB
--
--  Purpose:
--          This will be the MIB for the DNX HDS-3 Interface 
--          Module. This will provide for Configuration and Diagnostics
--          on any HDS3 card in the nest.
--
--  Contact: Eastern Research Inc. 1-800-337-4374  Email: support@erinc.com
--
-- *************************************************************************
