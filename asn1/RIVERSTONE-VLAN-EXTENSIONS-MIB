-- #condInclude "rs.inc"

RIVERSTONE-VLAN-EXTENSIONS-MIB DEFINITIONS ::= BEGIN

IMPORTS
    MODULE-IDENTITY, OBJECT-TYPE, OBJECT-IDENTITY, Counter32, Counter64
	FROM SNMPv2-SMI
    TEXTUAL-CONVENTION, TimeStamp, TruthValue              
        FROM SNMPv2-TC
    MODULE-COMPLIANCE, OBJECT-GROUP                        
        FROM SNMPv2-CONF
    SnmpAdminString
        FROM SNMP-FRAMEWORK-MIB
    dot1dBasePort
        FROM BRIDGE-MIB
    dot1qVlanIndex
        FROM Q-BRIDGE-MIB
    riverstoneMibs                      
        FROM RIVERSTONE-SMI-MIB;

rsVlanExtensionsMIB MODULE-IDENTITY
   LAST-UPDATED "200412060000Z"  -- December 6, 2004
   ORGANIZATION "Riverstone Networks, Inc"
   CONTACT-INFO "Riverstone Networks
                 Customer Service

                 Postal:
                 Riverstone Networks, Inc
                 5200 Great America Parkway
                 Santa Clara CA 95054 USA

                 PHONE:+1 408.878.6500
                 EMAIL: nms-eng@riverstonenet.com
                 WEB: http://www.riverstonenet.com"

   DESCRIPTION
       "This module complements VLAN information in qBridgeMIB from RFC2674."

   REVISION     "200412060000Z"
   DESCRIPTION
       "Added:
	rsPortCustomerVlanStatsTable 
		per-port, per-customer, per-vlan statistics
	rsPortHCCustomerVlanStatsTable 
		High-Capacity version of rsPortCustomerVlanStatsTable
	rsCustomerVlanStatsTable 
		per-customer, per-vlan cumulative statistics
	rsCustomerHCVlanStatsTable 
		High-Capacity version of rsCustomerVlanStatsTable
	"

    REVISION     "200208060000Z"
    DESCRIPTION
        "Initial version of Riverstone VLAN extensions."

   ::= { riverstoneMibs 65 }

--
-- Textual conventions
--

rsVlanObjects        OBJECT IDENTIFIER ::= { rsVlanExtensionsMIB 1 }
rsVlanConformance    OBJECT IDENTIFIER ::= { rsVlanExtensionsMIB 2 }

-- MIB contains groups
rsVlanStats OBJECT IDENTIFIER ::= { rsVlanObjects 10 }


-- Conformance information
-- Compliance statements
rsVlanCompliances OBJECT IDENTIFIER ::= { rsVlanConformance 1 }
rsVlanGroups      OBJECT IDENTIFIER ::= { rsVlanConformance 2 }

rsPortVlanStatsTable OBJECT-TYPE
    SYNTAX      SEQUENCE OF RsPortVlanStatsEntry
    MAX-ACCESS  not-accessible
    STATUS      current
    DESCRIPTION
	"A table that has statistics not defined in 
	dot1qPortVlanStatisticsTable."
    ::= { rsVlanStats 1 }

rsPortVlanStatsEntry OBJECT-TYPE
    SYNTAX      RsPortVlanStatsEntry
    MAX-ACCESS  not-accessible
    STATUS      current
    DESCRIPTION
	"More traffic statistics for a VLAN on a physical interface."
    INDEX { dot1dBasePort, dot1qVlanIndex }
    ::= { rsPortVlanStatsTable 1 }

RsPortVlanStatsEntry ::= SEQUENCE {
     rsPortVlanInOctets              Counter32,
     rsPortVlanOutOctets             Counter32,
     rsPortVlanInOverflowOctets      Counter32,
     rsPortVlanOutOverflowOctets     Counter32
}

rsPortVlanInOctets OBJECT-TYPE
    SYNTAX      Counter32
    MAX-ACCESS  read-only
    STATUS      current
    DESCRIPTION
	"The number of octets of the frames received by this port 
	from its segment that were classified as belonging to this
	VLAN. Note that a frame received on this port is
	counted by this object if and only if it is for a
	protocol being processed by the local forwarding process
	for this VLAN. This object includes received bridge
	management frames classified as belonging to this VLAN
	(e.g. GMRP, but not GVRP or STP)."
    ::= { rsPortVlanStatsEntry 101 }

rsPortVlanOutOctets OBJECT-TYPE
    SYNTAX      Counter32
    MAX-ACCESS  read-only
    STATUS      current
    DESCRIPTION
	"The number of octets of the valid frames transmitted 
	by this port from its segment from the local forwarding 
	process for this VLAN. This includes bridge management 
	frames originated by this device which are classified 
	as belonging to this VLAN (e.g. GMRP, but not GVRP or 
	STP)."
    ::= { rsPortVlanStatsEntry 102 }

rsPortVlanInOverflowOctets OBJECT-TYPE
    SYNTAX      Counter32
    MAX-ACCESS  read-only
    STATUS      current
    DESCRIPTION
	"The number of times the associated rsPortVlanInOctets
	counter has overflowed."
    ::= { rsPortVlanStatsEntry 103 }

rsPortVlanOutOverflowOctets OBJECT-TYPE
    SYNTAX      Counter32
    MAX-ACCESS  read-only
    STATUS      current
    DESCRIPTION
	"The number of times the associated rsPortVlanOutOctets
	counter has overflowed."
    ::= { rsPortVlanStatsEntry 104 }

rsPortVlanHCStatsTable OBJECT-TYPE
    SYNTAX      SEQUENCE OF RsPortVlanHCStatsEntry
    MAX-ACCESS  not-accessible
    STATUS      current
    DESCRIPTION
	"A table that has statistics not defined in 
	dot1qPortVlanHCStatisticsTable."
    ::= { rsVlanStats 2 }

rsPortVlanHCStatsEntry OBJECT-TYPE
    SYNTAX      RsPortVlanHCStatsEntry
    MAX-ACCESS  not-accessible
    STATUS      current
    DESCRIPTION
	"More traffic statistics for a VLAN on a physical interface."
    INDEX { dot1dBasePort, dot1qVlanIndex }
    ::= { rsPortVlanHCStatsTable 1 }

RsPortVlanHCStatsEntry ::= SEQUENCE {
     rsPortVlanHCInOctets            Counter64,
     rsPortVlanHCOutOctets           Counter64
}

rsPortVlanHCInOctets OBJECT-TYPE
    SYNTAX      Counter64
    MAX-ACCESS  read-only
    STATUS      current
    DESCRIPTION
	"The number of octets of the frames received by this port 
	from its segment that were classified as belonging to this
	VLAN. Note that a frame received on this port is
	counted by this object if and only if it is for a
	protocol being processed by the local forwarding process
	for this VLAN. This object includes received bridge
	management frames classified as belonging to this VLAN
	(e.g. GMRP, but not GVRP or STP)."
    ::= { rsPortVlanHCStatsEntry 101 }

rsPortVlanHCOutOctets OBJECT-TYPE
    SYNTAX      Counter64
    MAX-ACCESS  read-only
    STATUS      current
    DESCRIPTION
	"The number of octets of the valid frames transmitted 
	by this port from its segment from the local forwarding 
	process for this VLAN. This includes bridge management 
	frames originated by this device which are classified 
	as belonging to this VLAN (e.g. GMRP, but not GVRP or 
	STP)."
    ::= { rsPortVlanHCStatsEntry 102 }

-- end of rsPortVlanTable

rsPortCustomerVlanStatsTable OBJECT-TYPE
    SYNTAX      SEQUENCE OF RsPortCustomerVlanStatsEntry
    MAX-ACCESS  not-accessible
    STATUS      current
    DESCRIPTION
	"A table that has statistics not defined in 
	dot1qPortVlanStatsTable. This table provides statistics
	per-port, per-customer, per-vlan. Transparent VLAN
	is shown as dot1qVlanIndex of 0x7000 (28672).
	"
    ::= { rsVlanStats 3 }

rsPortCustomerVlanStatsEntry OBJECT-TYPE
    SYNTAX      RsPortCustomerVlanStatsEntry
    MAX-ACCESS  not-accessible
    STATUS      current
    DESCRIPTION
	"More traffic statistics for a VLAN on a physical interface
	 per customer."
    INDEX { dot1dBasePort, rsPortCustomerIndex, dot1qVlanIndex }
    ::= { rsPortCustomerVlanStatsTable 1 }

RsPortCustomerVlanStatsEntry ::= SEQUENCE {
	 rsPortCustomerIndex	INTEGER,
-- these stats are similar to what is available in dot1qPortVlanStatsTable
     rsPortCustomerVlanInFrames Counter32,
     rsPortCustomerVlanOutFrames Counter32,
     rsPortCustomerVlanInDiscards Counter32,
     rsPortCustomerVlanInOverflowFrames Counter32,
     rsPortCustomerVlanOutOverflowFrames Counter32,
     rsPortCustomerVlanInOverflowDiscards Counter32,
     rsPortCustomerVlanInOctets              Counter32,
     rsPortCustomerVlanOutOctets             Counter32,
     rsPortCustomerVlanInOverflowOctets      Counter32,
     rsPortCustomerVlanOutOverflowOctets     Counter32
}

rsPortCustomerIndex OBJECT-TYPE
    SYNTAX  INTEGER (0..2147483647)
    MAX-ACCESS  not-accessible
    STATUS  current
    DESCRIPTION
    	"Customer Index under which this vlan falls"
        ::= { rsPortCustomerVlanStatsEntry 1 }

rsPortCustomerVlanInFrames OBJECT-TYPE
    SYNTAX      Counter32
    MAX-ACCESS  read-only
    STATUS      current
    DESCRIPTION
        "The number of valid frames received by this port from
        its segment which were classified as belonging to this
        VLAN.  Note that a frame received on this port is
        counted by this object if and only if it is for a
        protocol being processed by the local forwarding process
        for this VLAN.  This object includes received bridge
        management frames classified as belonging to this VLAN
        (e.g. GMRP, but not GVRP or STP)."
    REFERENCE
        "IEEE 802.1Q/D11 Section 12.6.1.1.3(a)"
    ::= { rsPortCustomerVlanStatsEntry 2 }

rsPortCustomerVlanOutFrames OBJECT-TYPE
    SYNTAX      Counter32
    MAX-ACCESS  read-only
    STATUS      current
    DESCRIPTION
        "The number of valid frames transmitted by this port to
        its segment from the local forwarding process for this
        VLAN.  This includes bridge management frames originated
        by this device which are classified as belonging to this
        VLAN (e.g. GMRP, but not GVRP or STP)."
    REFERENCE
        "IEEE 802.1Q/D11 Section 12.6.1.1.3(d)"
    ::= { rsPortCustomerVlanStatsEntry 3 }


rsPortCustomerVlanInDiscards OBJECT-TYPE
    SYNTAX      Counter32
    MAX-ACCESS  read-only
    STATUS      current
    DESCRIPTION
        "The number of valid frames received by this port from
        its segment which were classified as belonging to this
        VLAN which were discarded due to VLAN related reasons.
        Specifically, the IEEE 802.1Q counters for Discard
        Inbound and Discard on Ingress Filtering."
    REFERENCE
        "IEEE 802.1Q/D11 Section 12.6.1.1.3"
    ::= { rsPortCustomerVlanStatsEntry 4 }

rsPortCustomerVlanInOverflowFrames OBJECT-TYPE
    SYNTAX      Counter32
    MAX-ACCESS  read-only
    STATUS      current
    DESCRIPTION
        "The number of times the associated
        rsPortCustomerVlanPortInFrames counter has overflowed."
    REFERENCE
        "ISO/IEC 15802-3 Section 14.6.1.1.3"
    ::= { rsPortCustomerVlanStatsEntry 5 }

rsPortCustomerVlanOutOverflowFrames OBJECT-TYPE
    SYNTAX      Counter32
    MAX-ACCESS  read-only
    STATUS      current
    DESCRIPTION
        "The number of times the associated
        rsPortCustomerVlanPortOutFrames counter has overflowed."
    REFERENCE
        "ISO/IEC 15802-3 Section 14.6.1.1.3"
    ::= { rsPortCustomerVlanStatsEntry 6 }

rsPortCustomerVlanInOverflowDiscards OBJECT-TYPE
    SYNTAX      Counter32
    MAX-ACCESS  read-only
    STATUS      current
    DESCRIPTION
        "The number of times the associated
        rsPortCustomerVlanPortInDiscards counter has overflowed."
    REFERENCE
        "ISO/IEC 15802-3 Section 14.6.1.1.3"
    ::= { rsPortCustomerVlanStatsEntry 7 }

rsPortCustomerVlanInOctets OBJECT-TYPE
    SYNTAX      Counter32
    MAX-ACCESS  read-only
    STATUS      current
    DESCRIPTION
	"The number of octets of the frames received by this port 
	from its segment that were classified as belonging to this
	VLAN. Note that a frame received on this port is
	counted by this object if and only if it is for a
	protocol being processed by the local forwarding process
	for this VLAN. This object includes received bridge
	management frames classified as belonging to this VLAN
	(e.g. GMRP, but not GVRP or STP)."
    ::= { rsPortCustomerVlanStatsEntry 8 }

rsPortCustomerVlanOutOctets OBJECT-TYPE
    SYNTAX      Counter32
    MAX-ACCESS  read-only
    STATUS      current
    DESCRIPTION
	"The number of octets of the valid frames transmitted 
	by this port from its segment from the local forwarding 
	process for this VLAN. This includes bridge management 
	frames originated by this device which are classified 
	as belonging to this VLAN (e.g. GMRP, but not GVRP or 
	STP)."
    ::= { rsPortCustomerVlanStatsEntry 9}

rsPortCustomerVlanInOverflowOctets OBJECT-TYPE
    SYNTAX      Counter32
    MAX-ACCESS  read-only
    STATUS      current
    DESCRIPTION
	"The number of times the associated rsPortCustomerVlanInOctets
	counter has overflowed."
    ::= { rsPortCustomerVlanStatsEntry 10 }

rsPortCustomerVlanOutOverflowOctets OBJECT-TYPE
    SYNTAX      Counter32
    MAX-ACCESS  read-only
    STATUS      current
    DESCRIPTION
	"The number of times the associated rsPortCustomerVlanOutOctets
	counter has overflowed."
    ::= { rsPortCustomerVlanStatsEntry 11 }


rsPortCustomerVlanHCStatsTable OBJECT-TYPE
    SYNTAX      SEQUENCE OF RsPortCustomerVlanHCStatsEntry
    MAX-ACCESS  not-accessible
    STATUS      current
    DESCRIPTION
	"A table that has statistics not defined in 
	dot1qPortVlanHCStatsTable. This table provides statistics
	per-port, per-customer, per-vlan. Transparent VLAN
	is shown as dot1qVlanIndex of 0x7000 (28672).
	"
    ::= { rsVlanStats 4 }

rsPortCustomerVlanHCStatsEntry OBJECT-TYPE
    SYNTAX      RsPortCustomerVlanHCStatsEntry
    MAX-ACCESS  not-accessible
    STATUS      current
    DESCRIPTION
	"More traffic statistics for a VLAN on a physical interface
	 per-customer."
    INDEX { dot1dBasePort, rsPortCustomerIndex, dot1qVlanIndex }
    ::= { rsPortCustomerVlanHCStatsTable 1 }

RsPortCustomerVlanHCStatsEntry ::= SEQUENCE {
  -- These stats are similar to what is available in rsPortVlanHCStatsTable
     rsPortCustomerVlanHCInFrames             Counter64,
     rsPortCustomerVlanHCOutFrames            Counter64,
     rsPortCustomerVlanHCInDiscards           Counter64,
     rsPortCustomerVlanHCInOctets              Counter64,
     rsPortCustomerVlanHCOutOctets             Counter64
}


rsPortCustomerVlanHCInFrames OBJECT-TYPE
    SYNTAX      Counter64
    MAX-ACCESS  read-only
    STATUS      current
    DESCRIPTION
        "The number of valid frames received by this port from
        its segment which were classified as belonging to this
        VLAN.  Note that a frame received on this port is
        counted by this object if and only if it is for a
        protocol being processed by the local forwarding process
        for this VLAN.  This object includes received bridge
        management frames classified as belonging to this VLAN
        (e.g. GMRP, but not GVRP or STP)."
    REFERENCE
        "IEEE 802.1Q/D11 Section 12.6.1.1.3(a)"
    ::= { rsPortCustomerVlanHCStatsEntry 1 }


rsPortCustomerVlanHCOutFrames OBJECT-TYPE
    SYNTAX      Counter64
    MAX-ACCESS  read-only
    STATUS      current
    DESCRIPTION
        "The number of valid frames transmitted by this port to
        its segment from the local forwarding process for this
        VLAN.  This includes bridge management frames originated
        by this device which are classified as belonging to this
        VLAN (e.g. GMRP, but not GVRP or STP)."
    REFERENCE
        "IEEE 802.1Q/D11 Section 12.6.1.1.3(d)"
    ::= { rsPortCustomerVlanHCStatsEntry 2 }

rsPortCustomerVlanHCInDiscards OBJECT-TYPE
    SYNTAX      Counter64
    MAX-ACCESS  read-only
    STATUS      current
    DESCRIPTION
        "The number of valid frames received by this port from
        its segment which were classified as belonging to this
        VLAN which were discarded due to VLAN related reasons.
        Specifically, the IEEE 802.1Q counters for Discard
        Inbound and Discard on Ingress Filtering."
    REFERENCE
        "IEEE 802.1Q/D11 Section 12.6.1.1.3"
    ::= { rsPortCustomerVlanHCStatsEntry 3 }

rsPortCustomerVlanHCInOctets OBJECT-TYPE
    SYNTAX      Counter64
    MAX-ACCESS  read-only
    STATUS      current
    DESCRIPTION
	"The number of octets of the frames received by this port 
	from its segment that were classified as belonging to this
	VLAN. Note that a frame received on this port is
	counted by this object if and only if it is for a
	protocol being processed by the local forwarding process
	for this VLAN. This object includes received bridge
	management frames classified as belonging to this VLAN
	(e.g. GMRP, but not GVRP or STP)."
    ::= { rsPortCustomerVlanHCStatsEntry 4 }

rsPortCustomerVlanHCOutOctets OBJECT-TYPE
    SYNTAX      Counter64
    MAX-ACCESS  read-only
    STATUS      current
    DESCRIPTION
	"The number of octets of the valid frames transmitted 
	by this port from its segment from the local forwarding 
	process for this VLAN. This includes bridge management 
	frames originated by this device which are classified 
	as belonging to this VLAN (e.g. GMRP, but not GVRP or 
	STP)."
    ::= { rsPortCustomerVlanHCStatsEntry 5 }

-- end of rsPortCustomer...

rsCustomerVlanStatsTable OBJECT-TYPE
    SYNTAX      SEQUENCE OF RsCustomerVlanStatsEntry
    MAX-ACCESS  not-accessible
    STATUS      current
    DESCRIPTION
	"A table that has statistics not defined in 
	dot1qPortVlanStatsTable. This table provides cumulative statistics
	per-customer, per-vlan from all the physical-ports. Transparent VLAN
	is shown as dot1qVlanIndex of 0x7000 (28672).
	"
    ::= { rsVlanStats 5 }

rsCustomerVlanStatsEntry OBJECT-TYPE
    SYNTAX      RsCustomerVlanStatsEntry
    MAX-ACCESS  not-accessible
    STATUS      current
    DESCRIPTION
	"Cumulative traffic statistics for a VLAN from physical interfaces
	 per-customer."
    INDEX { rsPortCustomerIndex, dot1qVlanIndex }
    ::= { rsCustomerVlanStatsTable 1 }

RsCustomerVlanStatsEntry ::= SEQUENCE {
-- these stats are similar to what is available in dot1qPortVlanStatsTable
     rsCustomerVlanInFrames Counter32,
     rsCustomerVlanOutFrames Counter32,
     rsCustomerVlanInDiscards Counter32,
     rsCustomerVlanInOverflowFrames Counter32,
     rsCustomerVlanOutOverflowFrames Counter32,
     rsCustomerVlanInOverflowDiscards Counter32,
     rsCustomerVlanInOctets              Counter32,
     rsCustomerVlanOutOctets             Counter32,
     rsCustomerVlanInOverflowOctets      Counter32,
     rsCustomerVlanOutOverflowOctets     Counter32
}

rsCustomerVlanInFrames OBJECT-TYPE
    SYNTAX      Counter32
    MAX-ACCESS  read-only
    STATUS      current
    DESCRIPTION
        "The number of valid frames received by the ports from
        its segment which were classified as belonging to this
        VLAN.  Note that a frame received on the ports is
        counted by this object if and only if it is for a
        protocol being processed by the local forwarding process
        for this VLAN.  This object includes received bridge
        management frames classified as belonging to this VLAN
        (e.g. GMRP, but not GVRP or STP)."
    REFERENCE
        "IEEE 802.1Q/D11 Section 12.6.1.1.3(a)"
    ::= { rsCustomerVlanStatsEntry 1 }

rsCustomerVlanOutFrames OBJECT-TYPE
    SYNTAX      Counter32
    MAX-ACCESS  read-only
    STATUS      current
    DESCRIPTION
        "The number of valid frames transmitted by the ports to
        its segment from the local forwarding process for this
        VLAN.  This includes bridge management frames originated
        by this device which are classified as belonging to this
        VLAN (e.g. GMRP, but not GVRP or STP)."
    REFERENCE
        "IEEE 802.1Q/D11 Section 12.6.1.1.3(d)"
    ::= { rsCustomerVlanStatsEntry 2 }


rsCustomerVlanInDiscards OBJECT-TYPE
    SYNTAX      Counter32
    MAX-ACCESS  read-only
    STATUS      current
    DESCRIPTION
        "The number of valid frames received by the ports from
        its segment which were classified as belonging to this
        VLAN which were discarded due to VLAN related reasons.
        Specifically, the IEEE 802.1Q counters for Discard
        Inbound and Discard on Ingress Filtering."
    REFERENCE
        "IEEE 802.1Q/D11 Section 12.6.1.1.3"
    ::= { rsCustomerVlanStatsEntry 3 }

rsCustomerVlanInOverflowFrames OBJECT-TYPE
    SYNTAX      Counter32
    MAX-ACCESS  read-only
    STATUS      current
    DESCRIPTION
        "The number of times the associated
        rsCustomerVlanPortInFrames counter has overflowed."
    REFERENCE
        "ISO/IEC 15802-3 Section 14.6.1.1.3"
    ::= { rsCustomerVlanStatsEntry 4 }

rsCustomerVlanOutOverflowFrames OBJECT-TYPE
    SYNTAX      Counter32
    MAX-ACCESS  read-only
    STATUS      current
    DESCRIPTION
        "The number of times the associated
        rsCustomerVlanPortOutFrames counter has overflowed."
    REFERENCE
        "ISO/IEC 15802-3 Section 14.6.1.1.3"
    ::= { rsCustomerVlanStatsEntry 5 }

rsCustomerVlanInOverflowDiscards OBJECT-TYPE
    SYNTAX      Counter32
    MAX-ACCESS  read-only
    STATUS      current
    DESCRIPTION
        "The number of times the associated
        rsCustomerVlanPortInDiscards counter has overflowed."
    REFERENCE
        "ISO/IEC 15802-3 Section 14.6.1.1.3"
    ::= { rsCustomerVlanStatsEntry 6 }

rsCustomerVlanInOctets OBJECT-TYPE
    SYNTAX      Counter32
    MAX-ACCESS  read-only
    STATUS      current
    DESCRIPTION
	"The number of octets of the frames received by the ports 
	from its segment that were classified as belonging to this
	VLAN. Note that a frame received on the ports is
	counted by this object if and only if it is for a
	protocol being processed by the local forwarding process
	for this VLAN. This object includes received bridge
	management frames classified as belonging to this VLAN
	(e.g. GMRP, but not GVRP or STP)."
    ::= { rsCustomerVlanStatsEntry 7 }

rsCustomerVlanOutOctets OBJECT-TYPE
    SYNTAX      Counter32
    MAX-ACCESS  read-only
    STATUS      current
    DESCRIPTION
	"The number of octets of the valid frames transmitted 
	by the ports from its segment from the local forwarding 
	process for this VLAN. This includes bridge management 
	frames originated by this device which are classified 
	as belonging to this VLAN (e.g. GMRP, but not GVRP or 
	STP)."
    ::= { rsCustomerVlanStatsEntry 8}

rsCustomerVlanInOverflowOctets OBJECT-TYPE
    SYNTAX      Counter32
    MAX-ACCESS  read-only
    STATUS      current
    DESCRIPTION
	"The number of times the associated rsCustomerVlanInOctets
	counter has overflowed."
    ::= { rsCustomerVlanStatsEntry 9 }

rsCustomerVlanOutOverflowOctets OBJECT-TYPE
    SYNTAX      Counter32
    MAX-ACCESS  read-only
    STATUS      current
    DESCRIPTION
	"The number of times the associated rsCustomerVlanOutOctets
	counter has overflowed."
    ::= { rsCustomerVlanStatsEntry 10 }


rsCustomerVlanHCStatsTable OBJECT-TYPE
    SYNTAX      SEQUENCE OF RsCustomerVlanHCStatsEntry
    MAX-ACCESS  not-accessible
    STATUS      current
    DESCRIPTION
	"A table that has statistics not defined in 
	dot1qPortVlanHCStatsTable. This table provides cumulative statistics
	per-customer, per-vlan from all the physical-ports. Transparent VLAN
	is shown as dot1qVlanIndex of 0x7000 (28672).
	"
    ::= { rsVlanStats 6 }

rsCustomerVlanHCStatsEntry OBJECT-TYPE
    SYNTAX      RsCustomerVlanHCStatsEntry
    MAX-ACCESS  not-accessible
    STATUS      current
    DESCRIPTION
	"Cumulative traffic statistics for a VLAN from physical interfaces
	 per-customer."
    INDEX { rsPortCustomerIndex, dot1qVlanIndex }
    ::= { rsCustomerVlanHCStatsTable 1 }

RsCustomerVlanHCStatsEntry ::= SEQUENCE {
-- These stats are similar to what is available in rsPortVlanHCStatsTable
     rsCustomerVlanHCInFrames             Counter64,
     rsCustomerVlanHCOutFrames            Counter64,
     rsCustomerVlanHCInDiscards           Counter64,
     rsCustomerVlanHCInOctets              Counter64,
     rsCustomerVlanHCOutOctets             Counter64
}


rsCustomerVlanHCInFrames OBJECT-TYPE
    SYNTAX      Counter64
    MAX-ACCESS  read-only
    STATUS      current
    DESCRIPTION
        "The number of valid frames received by the ports from
        its segment which were classified as belonging to this
        VLAN.  Note that a frame received on the ports is
        counted by this object if and only if it is for a
        protocol being processed by the local forwarding process
        for this VLAN.  This object includes received bridge
        management frames classified as belonging to this VLAN
        (e.g. GMRP, but not GVRP or STP)."
    REFERENCE
        "IEEE 802.1Q/D11 Section 12.6.1.1.3(a)"
    ::= { rsCustomerVlanHCStatsEntry 1 }


rsCustomerVlanHCOutFrames OBJECT-TYPE
    SYNTAX      Counter64
    MAX-ACCESS  read-only
    STATUS      current
    DESCRIPTION
        "The number of valid frames transmitted by the ports to
        its segment from the local forwarding process for this
        VLAN.  This includes bridge management frames originated
        by this device which are classified as belonging to this
        VLAN (e.g. GMRP, but not GVRP or STP)."
    REFERENCE
        "IEEE 802.1Q/D11 Section 12.6.1.1.3(d)"
    ::= { rsCustomerVlanHCStatsEntry 2 }

rsCustomerVlanHCInDiscards OBJECT-TYPE
    SYNTAX      Counter64
    MAX-ACCESS  read-only
    STATUS      current
    DESCRIPTION
        "The number of valid frames received by the ports from
        its segment which were classified as belonging to this
        VLAN which were discarded due to VLAN related reasons.
        Specifically, the IEEE 802.1Q counters for Discard
        Inbound and Discard on Ingress Filtering."
    REFERENCE
        "IEEE 802.1Q/D11 Section 12.6.1.1.3"
    ::= { rsCustomerVlanHCStatsEntry 3 }

rsCustomerVlanHCInOctets OBJECT-TYPE
    SYNTAX      Counter64
    MAX-ACCESS  read-only
    STATUS      current
    DESCRIPTION
	"The number of octets of the frames received by the ports 
	from its segment that were classified as belonging to this
	VLAN. Note that a frame received on the ports is
	counted by this object if and only if it is for a
	protocol being processed by the local forwarding process
	for this VLAN. This object includes received bridge
	management frames classified as belonging to this VLAN
	(e.g. GMRP, but not GVRP or STP)."
    ::= { rsCustomerVlanHCStatsEntry 4 }

rsCustomerVlanHCOutOctets OBJECT-TYPE
    SYNTAX      Counter64
    MAX-ACCESS  read-only
    STATUS      current
    DESCRIPTION
	"The number of octets of the valid frames transmitted 
	by the ports from its segment from the local forwarding 
	process for this VLAN. This includes bridge management 
	frames originated by this device which are classified 
	as belonging to this VLAN (e.g. GMRP, but not GVRP or 
	STP)."
    ::= { rsCustomerVlanHCStatsEntry 5 }

 -- Compliance statements
rsVlanCompliance MODULE-COMPLIANCE
    STATUS  current
    DESCRIPTION
            "The compliance statement for RIVERSTONE-VLAN-EXTENSIONS-MIB."
    MODULE  -- this module
        MANDATORY-GROUPS {
            rsPortVlanStatsGroup
        }

        GROUP      rsPortVlanStatsOverflowGroup 
        DESCRIPTION
            "This group is optional. It is most relevant for high
	    capacity interfaces where the SNMP agent supports only
	    SNMPv1."

        GROUP       rsPortVlanHCStatsGroup
        DESCRIPTION
            "This group is optional. It is most relevant for high
	    capacity interfaces."

        GROUP      rsPortCustomerVlanStatsGroup 
        DESCRIPTION
            "This group is optional. It provides statistics
	    per-port, per-customer, per-vlan for SNMPv1."

        GROUP      rsPortCustomerVlanStatsOverflowGroup 
        DESCRIPTION
            "This group is optional. It provides overflow statistics
	    per-port, per-customer, per-vlan for SNMPv1."

        GROUP       rsPortCustomerVlanHCStatsGroup
        DESCRIPTION
            "This group is optional. High-capacity version of 
	rsPortCustomerVlanStatsGroup."

        GROUP      rsCustomerVlanStatsGroup 
        DESCRIPTION
            "This group is optional. It provides cumulative
 	statistics per-port, per-customer, per-vlan for SNMPv1."

        GROUP      rsCustomerVlanStatsOverflowGroup 
        DESCRIPTION
            "This group is optional. It provides cumulative overflow
	statistics per-customer, per-vlan for SNMPv1."

        GROUP       rsCustomerVlanHCStatsGroup
        DESCRIPTION
            "This group is optional. High-capacity version of 
	rsCustomerVlanStatsGroup."

    ::= { rsVlanCompliances 1 }

 -- MIB groupings

rsPortVlanStatsGroup OBJECT-GROUP
    OBJECTS {
	rsPortVlanInOctets,
	rsPortVlanOutOctets
    }
    STATUS  current
    DESCRIPTION
        "A collection of additional objects providing per-port 
	packet statistics for all VLANs currently configured on 
	this device."
    ::= { rsVlanGroups 1 }

rsPortVlanStatsOverflowGroup OBJECT-GROUP
    OBJECTS {
	rsPortVlanInOverflowOctets,
	rsPortVlanOutOverflowOctets
    }
    STATUS  current
    DESCRIPTION
        "A collection of additional objects providing overflow 
	counters for per-port packet statistics for all VLANs currently
	configured on this device for high capacity interfaces, 
	defined as those that have the value of the corresponding 
	instance of ifSpeed greater than 20,000,000 bits/second."
    ::= { rsVlanGroups 2 }

rsPortVlanHCStatsGroup OBJECT-GROUP
    OBJECTS {
	rsPortVlanHCInOctets,
	rsPortVlanHCOutOctets
    }
    STATUS  current
    DESCRIPTION
        "A collection of additional objects providing per-port packet
        statistics for all VLANs currently configured on this
        device for high capacity interfaces, defined as those
        that have the value of the corresponding instance of
        ifSpeed greater than 20,000,000 bits/second."
    ::= { rsVlanGroups 3 }

rsPortCustomerVlanStatsGroup OBJECT-GROUP
    OBJECTS {
	rsPortCustomerVlanInOctets,
	rsPortCustomerVlanOutOctets
    }
    STATUS  current
    DESCRIPTION
        "A collection of additional objects providing per-port 
	statistics for all VLANs currently configured on 
	this device."
    ::= { rsVlanGroups 4 }

rsPortCustomerVlanStatsOverflowGroup OBJECT-GROUP
    OBJECTS {
	rsPortCustomerVlanInOverflowOctets,
	rsPortCustomerVlanOutOverflowOctets
    }
    STATUS  current
    DESCRIPTION
        "A collection of additional objects providing overflow 
	counters for per-port statistics for all VLANs currently
	configured on this device for high capacity interfaces, 
	defined as those that have the value of the corresponding 
	cumulative instance of ifSpeed greater than 20,000,000 bits/second."
    ::= { rsVlanGroups 5 }

rsPortCustomerVlanHCStatsGroup OBJECT-GROUP
    OBJECTS {
	rsPortCustomerVlanHCInOctets,
	rsPortCustomerVlanHCOutOctets
    }
    STATUS  current
    DESCRIPTION
        "A collection of additional objects providing per-port,
	 			per-customer statistics for all VLANs currently configured on this
        device for high capacity interfaces, defined as those
        that have the value of the corresponding instance of
        ifSpeed greater than 20,000,000 bits/second."
    ::= { rsVlanGroups 6 }

rsCustomerVlanStatsGroup OBJECT-GROUP
    OBJECTS {
	rsCustomerVlanInOctets,
	rsCustomerVlanOutOctets
    }
    STATUS  current
    DESCRIPTION
        "A collection of additional objects providing cumulative
	(all physical ports) statistics for all VLANs currently
	 configured on this device."
    ::= { rsVlanGroups 7 }

rsCustomerVlanStatsOverflowGroup OBJECT-GROUP
    OBJECTS {
	rsCustomerVlanInOverflowOctets,
	rsCustomerVlanOutOverflowOctets
    }
    STATUS  current
    DESCRIPTION
        "A collection of additional objects providing overflow 
	counters for cumulative statistics for all VLANs currently
	configured on this device for high capacity interfaces, 
	defined as those that have the value of the corresponding 
	instance of ifSpeed greater than 20,000,000 bits/second."
    ::= { rsVlanGroups 8 }

rsCustomerVlanHCStatsGroup OBJECT-GROUP
    OBJECTS {
	rsCustomerVlanHCInOctets,
	rsCustomerVlanHCOutOctets
    }
    STATUS  current
    DESCRIPTION
        "A collection of additional objects providing cumulative
        statistics for all VLANs currently configured on this
        device for high capacity interfaces, defined as those
        that have the value of the corresponding instance of
        ifSpeed greater than 20,000,000 bits/second."
    ::= { rsVlanGroups 9 }

END
