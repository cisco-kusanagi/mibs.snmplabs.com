--**************************************************************************
--                                                                          
--    Copyright 2002 Broadcom Corporation                                   
--    All Rights Reserved                                                   
--    No portions of this material may be reproduced in any form without the
--    written permission of:                                                
--             Broadcom Corporation                                         
--             16251 Laguna Canyon Road                                     
--             Irvine, California  92618                                    
--    All information contained in this document is Broadcom Corporation    
--    company private, proprietary, and trade secret.                       
--                                                                          
--                                                                          
--                                                                          
--**************************************************************************
--    Filename: brcm-cabledata-factory.mib
--    Author:   Kevin O'Neal
--    Creation Date: 19-june-2002
--
--**************************************************************************
--    Description:
--
--		factory MIB for cablemodem factory
--		
--**************************************************************************
--    Revision History:
--
--**************************************************************************

BRCM-CABLEDATA-FACTORY-MIB DEFINITIONS ::= BEGIN

IMPORTS
    MODULE-IDENTITY,
    OBJECT-TYPE,
    Unsigned32,
    Integer32,
    IpAddress
        FROM SNMPv2-SMI
    TruthValue,
    DisplayString,
    MacAddress
        FROM SNMPv2-TC
    cableDataPrivateMIBObjects
        FROM BRCM-CABLEDATA-PRIVATE-MIB;
                
cableDataFactory MODULE-IDENTITY
    LAST-UPDATED "200206190000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadcom cabledata factory MIB"
    REVISION      "200206040000Z"
    DESCRIPTION
            "Initial version of this MIB module."
    ::= { cableDataPrivateMIBObjects 2 }

cableDataFactoryBase OBJECT IDENTIFIER ::= { cableDataFactory 1 }

cdFactCommitSettings OBJECT-TYPE
    SYNTAX      TruthValue
    MAX-ACCESS  read-write
    STATUS      current
    DESCRIPTION
       "Setting this object to true(1) causes any factory settings which
        have been provisioned to be committed to permanent storage on the
        device.  Reading this object always returns false(2)."
    ::= { cableDataFactoryBase 1 }

-- 32 bit scratch pad (NEW NV REQUIRED)
cdFactScratchPad OBJECT-TYPE 
    SYNTAX      Unsigned32
    MAX-ACCESS  read-write
    STATUS	    current
    DESCRIPTION
       "This object provides a 32 bit scratch pad which may be used for any
        purpose desired.  Data written to this scratch pad will be permanently
        stored on the device."
    ::= { cableDataFactoryBase 2 }

cdFactSerialNumberTable  OBJECT-TYPE
    SYNTAX      SEQUENCE OF CdFactSerialNumberEntry
    MAX-ACCESS  not-accessible
    STATUS      current
    DESCRIPTION
        "A list of serial numbers for this device.  A table is necessary for
         this purpose to accomodate possibly multiple serial numbers for a
         given device - internal vs. published serial numbers, integrated
         devices with multiple components, etc."
    ::= { cableDataFactoryBase 3 }
    
cdFactSerialNumberEntry OBJECT-TYPE
    SYNTAX      CdFactSerialNumberEntry
    MAX-ACCESS  not-accessible
    STATUS      current
    DESCRIPTION
        "An entry defining a single serial number for this device."
    INDEX   { cdSerialNumIndex }
    ::= { cdFactSerialNumberTable 1 }
    
CdFactSerialNumberEntry ::= 
    SEQUENCE    {
                cdSerialNumIndex         Integer32,
                cdSerialNumber           OCTET STRING,
                cdSerialNumDescr         DisplayString
    }
    
cdSerialNumIndex OBJECT-TYPE
    SYNTAX      Integer32
    MAX-ACCESS  not-accessible
    STATUS      current
    DESCRIPTION
        "Identifies the instance of this serial number."
    ::= { cdFactSerialNumberEntry 1 }
    
cdSerialNumber  OBJECT-TYPE
    SYNTAX      OCTET STRING
    MAX-ACCESS  read-write
    STATUS      current
    DESCRIPTION
        "The value of this serial number."
    ::= { cdFactSerialNumberEntry 2 }
    
cdSerialNumDescr  OBJECT-TYPE
    SYNTAX      DisplayString
    MAX-ACCESS  read-only
    STATUS      current
    DESCRIPTION
        "A textual description of what this serial number is used for."
    ::= { cdFactSerialNumberEntry 3 }    
    
cdFactMacAddressTable  OBJECT-TYPE
    SYNTAX      SEQUENCE OF CdFactMacAddressEntry
    MAX-ACCESS  not-accessible
    STATUS      current
    DESCRIPTION
        "A table of MAC addresses used by this device.  MAC addresses in this
         table may be internal to the device or external, meaning they are
         assigned by the device to an externally attached peripheral."
    ::= { cableDataFactoryBase 4 }
    
cdFactMacAddressEntry OBJECT-TYPE
    SYNTAX      CdFactMacAddressEntry
    MAX-ACCESS  not-accessible
    STATUS      current
    DESCRIPTION
        "An entry defining a single MAC address for this device."
    INDEX   { cdMacAddrIndex }
    ::= { cdFactMacAddressTable 1 }
    
CdFactMacAddressEntry ::= 
    SEQUENCE    {
                cdMacAddrIndex         Integer32,
                cdMacAddress           MacAddress,
                cdMacAddrType          INTEGER,
                cdMacAddrDescr         DisplayString
    }
    
cdMacAddrIndex OBJECT-TYPE
    SYNTAX      Integer32
    MAX-ACCESS  not-accessible
    STATUS      current
    DESCRIPTION
        "Identifies the instance of this MAC address."
    ::= { cdFactMacAddressEntry 1 }
    
cdMacAddress  OBJECT-TYPE
    SYNTAX      MacAddress
    MAX-ACCESS  read-write
    STATUS      current
    DESCRIPTION
        "The value of this serial number."
    ::= { cdFactMacAddressEntry 2 }
    
cdMacAddrType OBJECT-TYPE
    SYNTAX      INTEGER {
                internal(1),
                external(2)
    }
    MAX-ACCESS  read-only
    STATUS      current
    DESCRIPTION
        "Specifies the use of this MAC address.  A value of internal(1) 
         indicates that this MAC address is used internally by this device.  A
         value of external(2) indicates that this device maintains this MAC
         address, but rather than using it internally, it is assigned to an
         attached peripheral."
    ::= { cdFactMacAddressEntry 3 }
    
cdMacAddrDescr  OBJECT-TYPE
    SYNTAX      DisplayString
    MAX-ACCESS  read-only
    STATUS      current
    DESCRIPTION
        "A textual description of what this MAC address is used for."
    ::= { cdFactMacAddressEntry 4 }
    
cdFactIpSettingsTable  OBJECT-TYPE
    SYNTAX      SEQUENCE OF CdFactIpSettingsEntry
    MAX-ACCESS  not-accessible
    STATUS      current
    DESCRIPTION
        "A table of settings used when provisioning the IP stack(s) on this
         device."
    ::= { cableDataFactoryBase 5 }
    
cdFactIpSettingsEntry OBJECT-TYPE
    SYNTAX      CdFactIpSettingsEntry
    MAX-ACCESS  not-accessible
    STATUS      current
    DESCRIPTION
        "An entry defining the characteristics of a single IP stack on this
         device.  This table is indexed by the cdMacAddrIndex value which
         corresponds to the MAC address associated with this IP stack instance."
    INDEX   { cdMacAddrIndex }
    ::= { cdFactIpSettingsTable 1 }
    
CdFactIpSettingsEntry ::= 
    SEQUENCE    {
                cdIpDescr              DisplayString,
                cdIpProvMethod         INTEGER,
                cdIpStaticAddress      IpAddress,
                cdIpStaticSubnet       IpAddress,
                cdIpStaticGateway      IpAddress
    }
    
cdIpDescr OBJECT-TYPE
    SYNTAX      DisplayString
    MAX-ACCESS  read-only
    STATUS      current
    DESCRIPTION
        "A textual description of this IP stack."
    ::= { cdFactIpSettingsEntry 1 }
    
cdIpProvMethod OBJECT-TYPE
    SYNTAX      INTEGER {
                static(0),
                dynamic(1)
    }
    MAX-ACCESS  read-write
    STATUS      current
    DESCRIPTION
        "Indicates whether this IP stack will provision itself using the static
         configuration from this table, or will be dynamically provisioned via
         DHCP or some other protocol."
    ::= { cdFactIpSettingsEntry 2 }
    
cdIpStaticAddress  OBJECT-TYPE
    SYNTAX      IpAddress
    MAX-ACCESS  read-write
    STATUS      current
    DESCRIPTION
        "Specifies the IP address that will be assigned to this IP
         stack if cmIpProvMethod is set to static(0)."
    ::= { cdFactIpSettingsEntry 3 }
    
cdIpStaticSubnet  OBJECT-TYPE
    SYNTAX      IpAddress
    MAX-ACCESS  read-write
    STATUS      current
    DESCRIPTION
        "Specifies the subnet that will be assigned to this IP
         stack if cmIpProvMethod is set to static(0)."
    ::= { cdFactIpSettingsEntry 4 }
    
cdIpStaticGateway  OBJECT-TYPE
    SYNTAX      IpAddress
    MAX-ACCESS  read-write
    STATUS      current
    DESCRIPTION
        "Specifies the default gateway that will be assigned to this IP
         stack if cmIpProvMethod is set to static(0)."
    ::= { cdFactIpSettingsEntry 5 }
    

-- This node is provided for vendor extensions to the cableDataFactory MIB.
-- Each vendor may request any objects under a node which is located at
-- cableDataFactoryVendor.vendorEnterpriseNumber.  For example, Broadcom's
-- node would be cableDataFactoryVendor.4413
cableDataFactoryVendor OBJECT IDENTIFIER ::= { cableDataFactory 99 }
    
END
