FC-PORT-MIB DEFINITIONS ::= BEGIN

-- Title:       FastComm Communications Adapter MIB in concise format
-- Version      5.0.1
-- Date:        September 15, 1999

-- Copyright 1993,1994,1995,1996,1997, 1998 FastComm Communications, Inc. 
-- All Rights Reserved.  Reproduction of this document is authorized 
-- on condition that the foregoing copyright notice is included.
-- This FastComm SNMP Management Information Base Specification
-- (Specification) embodies FastComm's confidential and proprietary
-- intellectual property.  FastComm retains all title and ownership 
-- in the Specification, including any revisions.  
--
-- It is FastComm's intent to encourage the widespread use of this
-- Specification in connection with the management of FastComm
-- products. FastComm grants vendors, end-users, and other interested 
-- parties a non-exclusive license to use this Specification in 
-- connection with the management of FastComm products.
--
-- This Specification is supplied "AS IS," and FastComm makes no
-- warranty, either express or implied, as to the use, operation, 
-- condition, or performance of the Specification.


IMPORTS
	fsPortProtocol
		FROM FC-FASTC-MIB
	fsPortInterface
		FROM FC-FASTC-MIB
	IpAddress
		FROM RFC1155-SMI
	OBJECT-TYPE
		FROM RFC-1212
	DisplayString
		FROM RFC1213-MIB;

fsPortDefinition			OBJECT IDENTIFIER ::= { fsPortProtocol 1 }
fsFrameRelay                  OBJECT IDENTIFIER ::= { fsPortProtocol 2 }
fsAsyncEncapsulation         	OBJECT IDENTIFIER ::= { fsPortProtocol 3 }
fsBitSyncEncapsulation      	OBJECT IDENTIFIER ::= { fsPortProtocol 4 }
fsSLIP                      	OBJECT IDENTIFIER ::= { fsPortProtocol 7 }
--fsSdlcEmulation             OBJECT IDENTIFIER ::= { fsPortProtocol 8 }
fsAsyncBurosEmulation       	OBJECT IDENTIFIER ::= { fsPortProtocol 9 }
fsSyncBurosEmulation        	OBJECT IDENTIFIER ::= { fsPortProtocol 10 }
fsSdlcRoute                 	OBJECT IDENTIFIER ::= { fsPortProtocol 11 }
fsByteSyncEncapsulation     	OBJECT IDENTIFIER ::= { fsPortProtocol 12 }
fsTelnetTerminal            	OBJECT IDENTIFIER ::= { fsPortProtocol 13 }
--fsAnnexG                    OBJECT IDENTIFIER ::= { fsPortProtocol 14 }
--fsX25                       OBJECT IDENTIFIER ::= { fsPortProtocol 15 }
fsALC                       	OBJECT IDENTIFIER ::= { fsPortProtocol 16 }
fsSDLC2                     	OBJECT IDENTIFIER ::= { fsPortProtocol 20 }
fsX25NEW                    	OBJECT IDENTIFIER ::= { fsPortProtocol 21 }
fsXPAD                      	OBJECT IDENTIFIER ::= { fsPortProtocol 22 }
fsPPPNew				OBJECT IDENTIFIER ::= { fsPortProtocol 23 }
fsPPPMLink				OBJECT IDENTIFIER ::= { fsPortProtocol 24 }
fsEtherNet                    OBJECT IDENTIFIER ::= { fsPortProtocol 25 }
fsTokenRing                   OBJECT IDENTIFIER ::= { fsPortProtocol 26 }

fsInterfaceDefinition         OBJECT IDENTIFIER ::= { fsPortInterface 1 }
fsInterfaceE1                 OBJECT IDENTIFIER ::= { fsPortInterface 2 }
fsInterfaceT1                 OBJECT IDENTIFIER ::= { fsPortInterface 3 }
fsInterfaceVoice              OBJECT IDENTIFIER ::= { fsPortInterface 4 }
fsInterfaceSerial             OBJECT IDENTIFIER ::= { fsPortInterface 5 }
fsInterfaceSDSL               OBJECT IDENTIFIER ::= { fsPortInterface 6 }
fsInterfaceDT1E1              OBJECT IDENTIFIER ::= { fsPortInterface 7 }

-- ***************************************************************************
-- frad port definition parameters

fsPortDefTable OBJECT-TYPE
	SYNTAX  SEQUENCE OF FsPortDefEntry
	ACCESS  not-accessible
	STATUS  mandatory
	DESCRIPTION  ""
	::= { fsPortDefinition 1 }

	FsPortDefEntry ::= SEQUENCE {
		fsPortDefLogPortNo	INTEGER,
		fsPortDefPhyBoardNo	INTEGER,
		fsPortDefPhyPortNo	INTEGER,
		fsPortDefProtocol		INTEGER,
		fsPortDefStatus		INTEGER
		}

	fsPortDefEntry OBJECT-TYPE
		SYNTAX  FsPortDefEntry
		ACCESS  not-accessible
		STATUS  mandatory
		DESCRIPTION  ""
		INDEX { fsPortDefLogPortNo }
		::= { fsPortDefTable 1 }

	fsPortDefLogPortNo OBJECT-TYPE
		SYNTAX  INTEGER {
			portN		(1),
			port1       (2),
			port2       (3),
			port3       (4),
			port4       (5),
			portE		(6),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-write
		STATUS  mandatory
		DESCRIPTION  ""
		::= { fsPortDefEntry 1 }

	fsPortDefPhyBoardNo OBJECT-TYPE
		SYNTAX  INTEGER {
			master     (0),
			board1     (1),
			board2     (2),
			board3     (3),
			board4     (4),
			board5     (5),
			board6     (6),
			board7     (7),
			board8     (8),
			board9     (9),
			board10    (10),
			board11    (11),
			board12    (12),
			board13    (13),
			board14    (14),
			undefined  (100)
			}
		ACCESS  read-write
		STATUS  mandatory
		DESCRIPTION  ""
		::= { fsPortDefEntry 2 }

	fsPortDefPhyPortNo OBJECT-TYPE
		SYNTAX  INTEGER {
			portS  	(0),
			portN  	(1),
			port1     	(2),
			port2      	(3),
			port3      	(4),
			port4		(5),
			portE 	(6),
			undefined	(100)
			}
		ACCESS  read-write
		STATUS  mandatory
		DESCRIPTION  ""
		::= { fsPortDefEntry 3 }

	fsPortDefProtocol OBJECT-TYPE
	      SYNTAX  INTEGER {
			undefined	            (0),
--			unused                  (1),
			frameRelay              (2),
			asyncEncapsu      	(3),
			bitSyncEncapsu    	(4),
			slip                    (5),
--			asyncPPP                (6),
--			syncPPP                 (7),
--			sdlcEmulation           (9),
			asyncBurEmulation 	(11),
			syncBurEmulation  	(12),           
			sdlcRouting             (16),
--			annexG                  (17),
			byteSyncEncapsu   	(20),
			etherNet		      (21),
--			x25                     (22),
			telnetTerminal          (24),
			alc			      (25),
                        token                   (26),
--			modemPPP		      (29),
			sdlc2                   (32),
			x25New                  (33),
                	xPad                    (34),
                  pPPNew                  (39),
			mLP				(42)            
			}
		ACCESS  read-write
		STATUS  mandatory
		DESCRIPTION  ""
		::= { fsPortDefEntry 4 }

	fsPortDefStatus OBJECT-TYPE
		SYNTAX  INTEGER {
			view     (1),
			modify   (2)
			}
		ACCESS  read-write
		STATUS  mandatory
		DESCRIPTION  ""
		::= { fsPortDefEntry 5 }

fsPortDialupConfigTable OBJECT-TYPE
	SYNTAX  SEQUENCE OF FsPortDialupConfigEntry
	ACCESS  not-accessible
	STATUS  mandatory
	DESCRIPTION  ""
	::= { fsPortDefinition 2 }

	FsPortDialupConfigEntry ::= SEQUENCE {
		fsPortDialupLogPortNo		INTEGER,
		fsPortDialupDialMode		INTEGER,
		fsPortDialupPrimaryPhe		DisplayString,
		fsPortDialupSecondPhe   	DisplayString,
		fsPortDialupRedialTimer		INTEGER,
		fsPortDialupNumRedial		INTEGER,
		fsPortDialupDialPortPri		INTEGER,
		fsPortDialupTollSaver		INTEGER,
		fsPortDialupTollSaverTimeout  INTEGER,
            fsPortDialupMaxNumSucCalls    INTEGER,
		fsPortDialupLocalTel		INTEGER,
		fsPortDialISDNDataRate        INTEGER,
		fsPortDialStatus		      INTEGER
		}

	fsPortDialupConfigEntry OBJECT-TYPE
		SYNTAX  FsPortDefEntry
		ACCESS  not-accessible
		STATUS  mandatory
		DESCRIPTION  ""
		INDEX { fsPortDialupLogPortNo }
		::= { fsPortDialupConfigTable 1 }

	fsPortDialupLogPortNo OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-write
		STATUS  mandatory
		DESCRIPTION  ""
		::= { fsPortDialupConfigEntry 1 }

	fsPortDialupDialMode OBJECT-TYPE
		SYNTAX  INTEGER {
			dIALOUT    (1),
			aNSWER     (2),
			iNVALID    (100)
			}
		ACCESS  read-write
		STATUS  mandatory
		DESCRIPTION  ""
		::= { fsPortDialupConfigEntry 2 }

	fsPortDialupPrimaryPhe OBJECT-TYPE
		SYNTAX  DisplayString (SIZE (16))
		ACCESS  read-write
		STATUS  mandatory
		DESCRIPTION  ""
		::= { fsPortDialupConfigEntry 3 }

	fsPortDialupSecondPhe OBJECT-TYPE
		SYNTAX  DisplayString (SIZE (16))
		ACCESS  read-write
		STATUS  mandatory
		DESCRIPTION  ""
		::= { fsPortDialupConfigEntry 4 }

	fsPortDialupRedialTimer OBJECT-TYPE
		SYNTAX  INTEGER (0..180)
		ACCESS  read-write
		STATUS  mandatory
		DESCRIPTION  ""
		::= { fsPortDialupConfigEntry 5 }

	fsPortDialupNumRedial OBJECT-TYPE
		SYNTAX  INTEGER (0..99)
		ACCESS  read-write
		STATUS  mandatory
		DESCRIPTION  ""
		::= { fsPortDialupConfigEntry 6 }

	fsPortDialupDialPortPri OBJECT-TYPE
		SYNTAX  INTEGER {
			lOW        (1),
			mEDIUM     (2),
			hIGH       (3)
			}
		ACCESS  read-write
		STATUS  mandatory
		DESCRIPTION  ""
		::= { fsPortDialupConfigEntry 7 }

	fsPortDialupTollSaver OBJECT-TYPE
		SYNTAX  INTEGER {
			eNABLED     (1),
                  dISABLED    (2)
			}
		ACCESS  read-write
		STATUS  mandatory
		DESCRIPTION  ""
		::= { fsPortDialupConfigEntry 8 }

	fsPortDialupTollSaverTimeout OBJECT-TYPE
		SYNTAX  INTEGER (0..600)
		ACCESS  read-write
		STATUS  mandatory
		DESCRIPTION  ""
		::= { fsPortDialupConfigEntry 9 }

	fsPortDialupMaxNumSucCalls OBJECT-TYPE
		SYNTAX  INTEGER (1..25)
		ACCESS  read-write
		STATUS  mandatory
		DESCRIPTION  ""
		::= { fsPortDialupConfigEntry 10 }

	fsPortDialupLocalTel OBJECT-TYPE
		SYNTAX  INTEGER {
			local-Tel-1     (1),
			local-Tel-2     (2),
 			invalid         (3)
			}
		ACCESS  read-write
		STATUS  mandatory
		DESCRIPTION  ""
		::= { fsPortDialupConfigEntry 11 }

	fsPortDialISDNDataRate OBJECT-TYPE
		SYNTAX  INTEGER {
			rate-56K     (1),
			rate-64K     (2),
			invalid      (3)
			}
		ACCESS  read-write
		STATUS  mandatory
		DESCRIPTION  ""
		::= { fsPortDialupConfigEntry 12 }

	fsPortDialStatus OBJECT-TYPE
		SYNTAX  INTEGER {
			view     (1),
			modify   (2)
			}
		ACCESS  read-write
		STATUS  mandatory
		DESCRIPTION  ""
		::= { fsPortDialupConfigEntry 13 }


-- ***************************************************************************
-- Frame Relay parameters

fsFrameRelayDefTable OBJECT-TYPE
	SYNTAX  SEQUENCE OF FsFrameRelayDefEntry
	ACCESS  not-accessible
	STATUS  mandatory
	DESCRIPTION  ""
	::= { fsFrameRelay 1 }

	FsFrameRelayDefEntry ::= SEQUENCE {
		fsFrameRelayPortNo		INTEGER,
		fsFrameRelaySpeed			INTEGER,
		fsFrameRelayProtocol          INTEGER,
		fsFrameRelayN1			INTEGER,
		fsFrameRelayN2			INTEGER,
		fsFrameRelayN3			INTEGER,
		fsFrameRelayT1			INTEGER,
		fsFrameRelayT2			INTEGER,
		fsFrameRelayPriEnable		INTEGER,
		fsFrameRelayPriHiToMed		INTEGER,
		fsFrameRelayPriMedToLow		INTEGER,
		fsFrameRelayStatus		INTEGER
		}

	fsFrameRelayDefEntry OBJECT-TYPE
		SYNTAX  FsFrameRelayDefEntry
		ACCESS  not-accessible
		STATUS  mandatory
		DESCRIPTION  ""
		INDEX { fsFrameRelayPortNo }
		::= { fsFrameRelayDefTable 1 }

	fsFrameRelayPortNo OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION  ""
		::= { fsFrameRelayDefEntry 1 }

	fsFrameRelaySpeed OBJECT-TYPE
		SYNTAX  INTEGER {
			external	(0),
			baud002400  (1),
			baud004800  (2),
			baud009600  (3),
			baud019200  (4),
			baud038400  (5),
			baud048000  (6),
			baud056000  (7),
			baud064000  (8),
			baud096000  (9),
			baud128000  (10),
			baud192000  (11),
			baud256000  (12),
			baud384000  (13),
			baud512000  (14),
			baud768000  (15),
			baud102400  (16),
			baud204800  (17)
			}
		ACCESS  read-write
		STATUS  mandatory
		DESCRIPTION  
			"The sync speed the FRAD will provide/accept clock to/from the
			network"
		::= { fsFrameRelayDefEntry 2 }

	fsFrameRelayProtocol OBJECT-TYPE
		SYNTAX  INTEGER {
			lmiNet          (0),
			lmiUser         (1),
			annexdNet       (2),
			annexdUser      (3),
			annexaNet       (4),
			annexaUser      (5),
			adaptMgmtUser   (6),
			adaptMgmtNet    (7),
			none            (8)
			}
		ACCESS  read-write
		STATUS  mandatory
		DESCRIPTION  
			"Select the type of Frame Relay management protocol to use 
			on the port."
		::= { fsFrameRelayDefEntry 3 }

	fsFrameRelayN1 OBJECT-TYPE
		SYNTAX  INTEGER (1..255)
		ACCESS  read-write
		STATUS  mandatory
		DESCRIPTION  
			"The STATUS_ENQUIRY message typically is a request for 
			the Sequence Number Exchange Only (report type= 00000001).  
			Every N1 polling intervals the user device requests a Full 
			Status Message (report type= 00000000)."
		::= { fsFrameRelayDefEntry 4 }

	fsFrameRelayN2 OBJECT-TYPE
		SYNTAX  INTEGER (1..10)
		ACCESS  read-write
		STATUS  mandatory
		DESCRIPTION  
			"Value N2 is the number of error events that must be 
			detected in the last N3 events in order for the link to be 
			considered down."
		::= { fsFrameRelayDefEntry 5 }

	fsFrameRelayN3 OBJECT-TYPE
		SYNTAX  INTEGER (1..10)
		ACCESS  read-write
		STATUS  mandatory
		DESCRIPTION  
			"Value N3 is the number of events in which N2 errors must 
			be detected for the link to be considered down.  It is 
			also the number of events that must occur with no N2 
			errors in order for the link to be considered back up."
		::= { fsFrameRelayDefEntry 6 }

	fsFrameRelayT1 OBJECT-TYPE
		SYNTAX  INTEGER (5..30)
		ACCESS  read-write
		STATUS  mandatory
		DESCRIPTION  
			"T1 is the length of the time spent waiting for a STATUS 
			message after sending STATUS_ENQUIRY (user devices)."
		::= { fsFrameRelayDefEntry 7 }

	fsFrameRelayT2 OBJECT-TYPE
		SYNTAX  INTEGER (5..30)
		ACCESS  read-write
		STATUS  mandatory
		DESCRIPTION
			"T2 is the time the network will spend waiting for a 
			STATUS_ENQUIRY from user devices."
		::= { fsFrameRelayDefEntry 8 }

	fsFrameRelayPriEnable OBJECT-TYPE
		SYNTAX  INTEGER {
			enable  (1),
			disable (2)
			}
		ACCESS  read-write
		STATUS  mandatory
		DESCRIPTION  
			"Enable priority queuing for the port."
		::= { fsFrameRelayDefEntry 9 }

	fsFrameRelayPriHiToMed OBJECT-TYPE
		SYNTAX  INTEGER {
			by1to1   (0),
			by2to1   (1),
			by4to1   (2),
			by8to1   (3),
			by16to1  (4),
			by32to1  (5),
            	by64to1  (6)
			}
		ACCESS  read-write
		STATUS  mandatory
		DESCRIPTION  
			"This is the ratio of number of bytes sent for 
			High priority data to Medium priority data."
		::= { fsFrameRelayDefEntry 10 }

	fsFrameRelayPriMedToLow OBJECT-TYPE
		SYNTAX  INTEGER {
			by1to1   (0),
			by2to1   (1),
			by4to1   (2),
			by8to1   (3),
			by16to1  (4),
			by32to1  (5),
            	by64to1  (6)
			}
		ACCESS  read-write
		STATUS  mandatory
		DESCRIPTION  
			"This is the ratio of number of bytes sent for 
			Medium priority data to Low priority data."
		::= { fsFrameRelayDefEntry 11 }

	fsFrameRelayStatus OBJECT-TYPE
		SYNTAX  INTEGER {
			view   (1),
			modify (2)
			}
		ACCESS  read-write
		STATUS  mandatory
		DESCRIPTION  ""
		::= { fsFrameRelayDefEntry 12 }

fsFrameRelayPriDlciTable OBJECT-TYPE
	SYNTAX  SEQUENCE OF FsFrameRelayPriDlciEntry
	ACCESS  not-accessible
	STATUS  mandatory
	DESCRIPTION  ""
	::= { fsFrameRelay 2 }

	FsFrameRelayPriDlciEntry ::= SEQUENCE {
		fsFRPriPortNo		INTEGER,
		fsFRPriIndex          	INTEGER,
		fsFRPriDlciNum          INTEGER,
		fsFRPriDlciCIR          INTEGER,
		fsFRPriDlciBc           INTEGER,
		fsFRPriDlciBe           INTEGER,
		fsFRPriStatus         	INTEGER
		}

	fsFrameRelayPriDlciEntry OBJECT-TYPE
		SYNTAX  FsFrameRelayPriDlciEntry
		ACCESS  not-accessible
		STATUS  mandatory
		DESCRIPTION  ""
		INDEX { fsFRPriPortNo, fsFRPriIndex }
		::= { fsFrameRelayPriDlciTable 1 }

	fsFRPriPortNo OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-write
		STATUS  mandatory
		DESCRIPTION  ""
		::= { fsFrameRelayPriDlciEntry 1 }

	fsFRPriIndex OBJECT-TYPE
		SYNTAX  INTEGER
		ACCESS  read-write
		STATUS  mandatory
		DESCRIPTION  ""
		::= { fsFrameRelayPriDlciEntry 2 }

	fsFRPriDlciNum OBJECT-TYPE
		SYNTAX  INTEGER
		ACCESS  read-write
		STATUS  mandatory
		DESCRIPTION  
			"This is the DLCI to use for the data."
		::= { fsFrameRelayPriDlciEntry 3 }

	fsFRPriDlciCIR OBJECT-TYPE
		SYNTAX  INTEGER
		ACCESS  read-write
		STATUS  mandatory
		DESCRIPTION  
			"This is the CIR for the DLCI."
		::= { fsFrameRelayPriDlciEntry 4 }

	fsFRPriDlciBc OBJECT-TYPE
		SYNTAX  INTEGER
		ACCESS  read-write
		STATUS  mandatory
		DESCRIPTION  
			"This is the committed burst rate for the PVC. "
		::= { fsFrameRelayPriDlciEntry 5 }

	fsFRPriDlciBe OBJECT-TYPE
		SYNTAX  INTEGER
		ACCESS  read-write
		STATUS  mandatory
		DESCRIPTION  
			"This is the excess burst rate to use for the PVC."
		::= { fsFrameRelayPriDlciEntry 6 }

	fsFRPriStatus OBJECT-TYPE
		SYNTAX  INTEGER {
			view   (1),
			add    (2),
			delete (3),
                  modify (4)
			}
		ACCESS  read-write
		STATUS  mandatory
		DESCRIPTION  ""
		::= { fsFrameRelayPriDlciEntry 7 }


-- ***************************************************************************
-- Async Encapsulation parameters

fsAsyncEncapDefTable OBJECT-TYPE
	SYNTAX  SEQUENCE OF FsAsyncEncapDefEntry
	ACCESS  not-accessible
	STATUS  mandatory
	DESCRIPTION  ""
	::= { fsAsyncEncapsulation 1 }

	FsAsyncEncapDefEntry ::= SEQUENCE {
		fsAsyncEncapPortNo		INTEGER,
		fsAsyncEncapSpeed			INTEGER,
		fsAsyncEncapDataBits          INTEGER,
		fsAsyncEncapParity		INTEGER,
		fsAsyncEncapStopBits		INTEGER,
		fsAsyncEncapPri			INTEGER,
		fsAsyncEncapDestinationPort   INTEGER,
		fsAsyncEncapBreakLength		INTEGER,
		fsAsyncEncapGptName		DisplayString,
		fsAsyncEncapStatus		INTEGER
		}

	fsAsyncEncapDefEntry OBJECT-TYPE
		SYNTAX  FsAsyncEncapDefEntry
		ACCESS  not-accessible
		STATUS  mandatory
		DESCRIPTION  ""
		INDEX { fsAsyncEncapPortNo }
		::= { fsAsyncEncapDefTable 1 }

	fsAsyncEncapPortNo OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION  ""
		::= { fsAsyncEncapDefEntry 1 }

	fsAsyncEncapSpeed OBJECT-TYPE
		SYNTAX  INTEGER {
			baud001200  (1),
			baud002400  (2),
			baud004800  (3),
			baud009600  (4),
			baud019200  (5),
			baud038400  (6),
			baud048000  (7),
			baud057600  (8),
			baud115200  (9)
			}
		ACCESS  read-write
		STATUS  mandatory
		DESCRIPTION
			"The async speed of the user's equipment"  
		::= { fsAsyncEncapDefEntry 2 }

	fsAsyncEncapDataBits OBJECT-TYPE
		SYNTAX  INTEGER {
			sevenBits   (7),
			eightBits   (8)
			}
		ACCESS  read-write
		STATUS  mandatory
		DESCRIPTION  
			"The number of bits in the data bytes."
		::= { fsAsyncEncapDefEntry 3 }

	fsAsyncEncapParity OBJECT-TYPE
		SYNTAX  INTEGER {
			oddParity   (0),
			evenParity  (1),
			markParity  (2),
			spaceParity (3),
			noParity    (4)
			}
		ACCESS  read-write
		STATUS  mandatory
		DESCRIPTION
			"The type of parity used for the data."
		::= { fsAsyncEncapDefEntry 4 }

	fsAsyncEncapStopBits OBJECT-TYPE
		SYNTAX  INTEGER {
			oneBit  (1),
			twoBits (2)
			}
		ACCESS  read-write
		STATUS  mandatory
		DESCRIPTION
			"The number of stop bits to use for the data."
		::= { fsAsyncEncapDefEntry 5 }

	fsAsyncEncapPri OBJECT-TYPE
		SYNTAX  INTEGER {
			immediate   (0),
			high        (1),
			medium	(2),
			low		(3)
			}
		ACCESS  read-write
		STATUS  mandatory
		DESCRIPTION
			"The priority setting for the data (immediate, 
			high, medium, low)."
		::= { fsAsyncEncapDefEntry 6 }

	fsAsyncEncapDestinationPort OBJECT-TYPE
		SYNTAX  INTEGER {
			portNet-port16  (1),
			port1           (2),
			port2           (3),
			port3           (4),
			port4           (5),
			port5           (6),
			port6           (7),
			port7           (8),
			port8           (9),
			port9           (10),
			port10          (11),
			port11          (12),
			port12          (13),
			port13          (14),
			port14          (15),
			port15          (16)
			}
		ACCESS  read-write
		STATUS  mandatory
		DESCRIPTION
			"The destination port of the remote FRAD."
		::= { fsAsyncEncapDefEntry 7 }

	fsAsyncEncapBreakLength OBJECT-TYPE
		SYNTAX  INTEGER {
			length-200ms    (1),
			length-400ms    (2),
			length-600ms    (3),
			length-800ms    (4),
			length-1000ms   (5)
			}
		ACCESS  read-write
		STATUS  mandatory
		DESCRIPTION  
			"Set the length of a break character."
		::= { fsAsyncEncapDefEntry 8 }

	fsAsyncEncapGptName OBJECT-TYPE
		SYNTAX  DisplayString (SIZE (11))
		ACCESS  read-write
		STATUS  mandatory
		DESCRIPTION ""
		::= { fsAsyncEncapDefEntry 9 }

	fsAsyncEncapStatus OBJECT-TYPE
		SYNTAX  INTEGER {
			view   (1),
			modify (2)
			}
		ACCESS  read-write
		STATUS  mandatory
		DESCRIPTION  ""
		::= { fsAsyncEncapDefEntry 10 }


-- ***************************************************************************
-- BitSync Encapsulation parameters

fsBitSyncEncapDefTable OBJECT-TYPE
	SYNTAX  SEQUENCE OF FsBitSyncEncapDefEntry
	ACCESS  not-accessible
	STATUS  mandatory
	DESCRIPTION  ""
	::= { fsBitSyncEncapsulation 1 }

	FsBitSyncEncapDefEntry ::= SEQUENCE {
		fsBitSyncEncapPortNo		INTEGER,
		fsBitSyncEncapSpeed		INTEGER,
		fsBitSyncEncapFormat          INTEGER,
		fsBitSyncEncapSwitchedDcd	INTEGER,
		fsBitSyncEncapIdleMark   	INTEGER,
		fsBitSyncEncapPri			INTEGER,
		fsBitSyncEncapGptName		DisplayString,
		fsBitSyncEncapStatus		INTEGER
		}

	fsBitSyncEncapDefEntry OBJECT-TYPE
		SYNTAX  FsBitSyncEncapDefEntry
		ACCESS  not-accessible
		STATUS  mandatory
		DESCRIPTION  ""
		INDEX { fsBitSyncEncapPortNo }
		::= { fsBitSyncEncapDefTable 1 }

	fsBitSyncEncapPortNo OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION  ""
		::= { fsBitSyncEncapDefEntry 1 }

	fsBitSyncEncapSpeed OBJECT-TYPE
		SYNTAX  INTEGER {
			external    (0),
			baud002400  (1),
			baud004800  (2),
			baud009600  (3),
			baud019200  (4),
			baud038400  (5),
			baud048000  (6),
			baud056000  (7),
			baud064000  (8),
			baud096000  (9),
			baud128000  (10),
			baud192000  (11),
			baud256000  (12),
			baud384000  (13),
			baud512000  (14),
			baud768000  (15),
			baud1024000 (16)
			}
		ACCESS  read-write
		STATUS  mandatory
		DESCRIPTION
			"The sync speed the FRAD will provide/accept 
			clock to/from the user's equipment"
		::= { fsBitSyncEncapDefEntry 2 }

	fsBitSyncEncapFormat OBJECT-TYPE
		SYNTAX  INTEGER {
			nrz     (1),
			nrzi    (2)
			}
		ACCESS  read-write
		STATUS  mandatory
		DESCRIPTION
			"The format of the HDLC frame (NRZ, NRZI)."
		::= { fsBitSyncEncapDefEntry 3 }

	fsBitSyncEncapSwitchedDcd OBJECT-TYPE
		SYNTAX  INTEGER {
			switched    (1),
			forced      (2)
			}
		ACCESS  read-write
		STATUS  mandatory
		DESCRIPTION
			"Switched DCD is usually used for AS400 users in order 
			to simulate the functionality of a multipoint network."
		::= { fsBitSyncEncapDefEntry 4 }

	fsBitSyncEncapIdleMark OBJECT-TYPE
		SYNTAX  INTEGER {
			mark    (1),
			flag    (2)
			}
		ACCESS  read-write
		STATUS  mandatory
		DESCRIPTION
			"SDLC device use different filler characters in 
			between actual data packets. Select either 'mark' 
			or flag (7E)."
		::= { fsBitSyncEncapDefEntry 5 }

	fsBitSyncEncapPri OBJECT-TYPE
		SYNTAX  INTEGER {
			immediate   (0),
			high        (1),
			medium	(2),
			low		(3)
			}
		ACCESS  read-write
		STATUS  mandatory
		DESCRIPTION
			"Priority setting for the data (immediate, high, 
			medium, low)."
		::= { fsBitSyncEncapDefEntry 6 }

	fsBitSyncEncapGptName OBJECT-TYPE
		SYNTAX  DisplayString (SIZE (11))
		ACCESS  read-write
		STATUS  mandatory
		DESCRIPTION ""
		::= { fsBitSyncEncapDefEntry 7 }

	fsBitSyncEncapStatus OBJECT-TYPE
		SYNTAX  INTEGER {
			view   (1),
			modify (2)
			}
		ACCESS  read-write
		STATUS  mandatory
		DESCRIPTION  ""
		::= { fsBitSyncEncapDefEntry 8 }


-- ***************************************************************************
-- SLIP parameters

fsSlipDefTable OBJECT-TYPE
	SYNTAX  SEQUENCE OF FsSlipDefEntry
	ACCESS  not-accessible
	STATUS  mandatory
	DESCRIPTION  ""
	::= { fsSLIP 1 }

	FsSlipDefEntry ::= SEQUENCE {
		fsSlipPortNo		INTEGER,
		fsSlipSpeed			INTEGER,
		fsSlipStatus		INTEGER
		}

	fsSlipDefEntry OBJECT-TYPE
		SYNTAX  FsSlipDefEntry
		ACCESS  not-accessible
		STATUS  mandatory
		DESCRIPTION  ""
		INDEX { fsSlipPortNo }
		::= { fsSlipDefTable 1 }

	fsSlipPortNo OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION  ""
		::= { fsSlipDefEntry 1 }

	fsSlipSpeed OBJECT-TYPE
		SYNTAX  INTEGER {
			baud001200  (1),
			baud002400  (2),
			baud004800  (3),
			baud009600  (4),
			baud019200  (5),
			baud038400  (6),
			baud048000  (7),
			baud057600  (8),
			baud115200  (9)
			}
		ACCESS  read-write
		STATUS  mandatory
		DESCRIPTION ""
		::= { fsSlipDefEntry 2 }

	fsSlipStatus OBJECT-TYPE
		SYNTAX  INTEGER {
			view   (1),
			modify (2)
			}
		ACCESS  read-write
		STATUS  mandatory
		DESCRIPTION  ""
		::= { fsSlipDefEntry 3 }


-- ***************************************************************************
-- SDLC Emulation parameters

--fsSdlcEmulateDefTable OBJECT-TYPE
--	SYNTAX  SEQUENCE OF FsSdlcEmulateDefEntry
--	ACCESS  not-accessible
--	STATUS  mandatory
--	DESCRIPTION  ""
--	::= { fsSdlcEmulation 1 }

--	FsSdlcEmulateDefEntry ::= SEQUENCE {
--		fsSdlcEmulatePortNo		INTEGER,
--		fsSdlcEmulateSpeed		INTEGER,
--		fsSdlcEmulateType			INTEGER,
--		fsSdlcEmulateFormat		INTEGER,
--		fsSdlcEmulateRetryCount		INTEGER,
--		fsSdlcEmulateRetryTimer		INTEGER,
--		fsSdlcEmulatePollTimer		INTEGER,
--		fsSdlcEmulateSwitchedDcd	INTEGER,
--		fsSdlcEmulateIdleMark		INTEGER,
--		fsSdlcEmulateFcActiveLevel	INTEGER,
--		fsSdlcEmulateFcClearLevel	INTEGER,
--		fsSdlcEmulateStatus		INTEGER
--		}

--	fsSdlcEmulateDefEntry OBJECT-TYPE
--		SYNTAX  FsSdlcEmulateDefEntry
--		ACCESS  not-accessible
--		STATUS  mandatory
--		DESCRIPTION  ""
--		INDEX { fsSdlcEmulatePortNo }
--		::= { fsSdlcEmulateDefTable 1 }

--	fsSdlcEmulatePortNo OBJECT-TYPE
--		SYNTAX  INTEGER {
--			port1		(1),
--			port2       (2),
--			port3       (3),
--			port4       (4),
--			port5       (5),
--			port6		(6),
--			port7       (7),
--			port8       (8),
--			port9       (9),
--			portA      	(10),
--			portB		(11),
--			portC      	(12),
--			portD      	(13),
--			portE      	(14),
--			portF      	(15),
--			portG		(16),
--			portH      	(17),
--			portI      	(18),
--			portJ      	(19)
--			}
--		ACCESS  read-only
--		STATUS  mandatory
--		DESCRIPTION  ""
--		::= { fsSdlcEmulateDefEntry 1 }

--	fsSdlcEmulateSpeed OBJECT-TYPE
--		SYNTAX  INTEGER {
--			external    (0),
--			baud002400  (1),
--			baud004800  (2),
--			baud009600  (3),
--			baud019200  (4),
--			baud038400  (5),
--			baud048000  (6),
--			baud056000  (7),
--			baud064000  (8),
--			baud096000  (9),
--			baud128000  (10),
--			baud192000  (11),
--			baud256000  (12),
--			baud384000  (13),
--			baud512000  (14),
--			baud768000  (15),
--			baud1024000 (16)
--			}
--		ACCESS  read-write
--		STATUS  mandatory
--		DESCRIPTION 
--			"The sync speed the FRAD will provide/accept clock to/from the
--			user's equipment"
--		::= { fsSdlcEmulateDefEntry 2 }

--	fsSdlcEmulateType OBJECT-TYPE
--		SYNTAX  INTEGER {
--			hostEnd     (1),
--			terminalEnd (2)
--			}
--		ACCESS  read-write
--		STATUS  mandatory
--		DESCRIPTION 
--			"Select the type of device the FRAD will be connected to: 
--			i.e if the FRAD is connected to an AS400 host, 
--			then select Host end."
--		::= { fsSdlcEmulateDefEntry 3 }

--	fsSdlcEmulateFormat OBJECT-TYPE
--		SYNTAX  INTEGER {
--			nrz     (1),
--			nrzi    (2)
--			}
--		ACCESS  read-write
--		STATUS  mandatory
--		DESCRIPTION 
--			"The Data Format for the SDLC Emulation setting 
--			allows you to set the Data Format.  There are two 
--			data formats:  Non-Return-to-Zero (NRZ) and 
--			Non-Return-to-Zero Inverted (NRZI).  Check your 
--			equipment specifications to determine which you are using."
--		::= { fsSdlcEmulateDefEntry 4 }

--	fsSdlcEmulateRetryCount OBJECT-TYPE
--		SYNTAX  INTEGER (1..255)
--		ACCESS  read-write
--		STATUS  mandatory
--		DESCRIPTION 
--			"Retry Count for the SDLC Emulation setting allows 
--			you to set the counter that is used by SDLC to effect 
--			error recovery.  This counter is factory set to a 
--			universally accepted value.  If you change it, be sure it 
--			is consistent with your host and terminals."
--		::= { fsSdlcEmulateDefEntry 5 }

--	fsSdlcEmulateRetryTimer OBJECT-TYPE
--		SYNTAX  INTEGER (1..255)
--		ACCESS  read-write
--		STATUS  mandatory
--		DESCRIPTION 
--			"Retry Timer for the SDLC Emulation setting allows you to 
--			set the timer that is used by SDLC to effect error recovery.  
--			This timer is factory set to a universally accepted value.  
--			If you change it, be sure it is consistent with your host 
--			and terminals."
--		::= { fsSdlcEmulateDefEntry 6 }

--	fsSdlcEmulatePollTimer OBJECT-TYPE
--		SYNTAX  INTEGER (0..255)
--		ACCESS  read-write
--		STATUS  mandatory
--		DESCRIPTION 
--			"Poll Timer for the SDLC Emulation setting allows you to 
--			set the delay time between polls sent out by a Terminal FRAD 
--			to the SDLC equipment.  The default for this parameter is 
--			zero, or polling as fast as possible.  If you are uncertain 
--			as to what entry to make, two tenths of a second is suggested.  
--			If the FRAD is configured as a Host FRAD, this option should 
--			be ignored since the Host FRAD does not issue polls."
--		::= { fsSdlcEmulateDefEntry 7 }

--	fsSdlcEmulateSwitchedDcd OBJECT-TYPE
--		SYNTAX  INTEGER {
--			switched    (1),
--			forced      (2)
--			}
--		ACCESS  read-write
--		STATUS  mandatory
--		DESCRIPTION 
--			"DCD for the SDLC Emulation setting allows you to 
--			determine when DCD will be active. It is only effective 
--			on ports configured as DCE. If DCD is set to Switched, 
--			DCD will only be active during data transmission from 
--			the FRAD.  If set to Forced, DCD will remain active at 
--			all times.  The default for this parameter is Forced."
--		::= { fsSdlcEmulateDefEntry 8 }

--	fsSdlcEmulateIdleMark OBJECT-TYPE
--		SYNTAX  INTEGER {
--			mark    (1),
--			flag    (2)
--			}
--		ACCESS  read-write
--		STATUS  mandatory
--		DESCRIPTION 
--			"The Idle Character for the SDLC Protocol Emulation 
--			setting allows you to select transmission of Mark 
--			characters between frames, except after frames whose 
--			Poll/Final (P/F) bit is clear (off).  Normally, an HDLC 
--			protocol transmits HDLC Flag (0x7e with no zero insertion) 
--			characters between frames.  If Idle Character is set to Flag, 
--			the FRAD will continue to issue HDLC Flag characters in 
--			the idle state. If Idle Character is set to Mark, the FRAD 
--			will send solid Mark characters (all binary ones) in the 
--			idle state.  The exception is that any frame which does 
--			not have the P/F flag of the command byte set (bit 0x10 
--			of the second byte of the frame) will be followed by HDLC 
--			Flag characters.  (This exception was explicitly designed 
--			for compatibility with IBM AS400s.  However, it does reflect 
--			the actual state of an HDLC line over half-duplex modems.)  
--			The default for this parameter is Flag."
--		::= { fsSdlcEmulateDefEntry 9 }

--	fsSdlcEmulateFcActiveLevel OBJECT-TYPE
--		SYNTAX  INTEGER (0..100)
--		ACCESS  read-write
--		STATUS  mandatory
--		DESCRIPTION 
--			"Flow Control Active Level for SDLC Emulation allows 
--			you to set flow control buffer levels for traffic coming 
--			into the FRAD from the network.  This value represents the 
--			buffer level (percent occupied) at which flow control will 
--			be set. It can be configured for each SDLC Emulation port"
--		::= { fsSdlcEmulateDefEntry 10 }

--	fsSdlcEmulateFcClearLevel OBJECT-TYPE
--		SYNTAX  INTEGER (0..100)
--		ACCESS  read-write
--		STATUS  mandatory
--		DESCRIPTION 
--			"Flow Control Clear Level for SDLC Emulation allows you to 
--			set flow control buffer levels for traffic coming into the 
--			FRAD from the network.  This value represents the buffer 
--			level at which flow control will be cleared.  It must be 
--			less than the Flow Control Active Level.  The clear level 
--			can be configured for each SDLC Emulation port."
--		::= { fsSdlcEmulateDefEntry 11 }

--	fsSdlcEmulateStatus OBJECT-TYPE
--		SYNTAX  INTEGER {
--			view   (1),
--			modify  (2)
--			}
--		ACCESS  read-write
--		STATUS  mandatory
--		DESCRIPTION  ""
--		::= { fsSdlcEmulateDefEntry 12 }

--fsSdlcEmulateConTable OBJECT-TYPE
--	SYNTAX  SEQUENCE OF FsSdlcEmulateConEntry
--	ACCESS  not-accessible
--	STATUS  mandatory
--	DESCRIPTION  ""
--	::= { fsSdlcEmulation 2 }

--	FsSdlcEmulateConEntry ::= SEQUENCE {
--		fsSdlcEmulateConPortNo			INTEGER,
--		fsSdlcEmulateConIndex          	INTEGER,
--		fsSdlcEmulateConLocalLogicalId      INTEGER,
--		fsSdlcEmulateConLocalCUaddr         DisplayString,
--		fsSdlcEmulateConRemoteIPaddr        IpAddress,
--		fsSdlcEmulateConRemoteLogicalId     INTEGER,
--		fsSdlcEmulateConStatus         	INTEGER
--		}

--	fsSdlcEmulateConEntry OBJECT-TYPE
--		SYNTAX  FsSdlcEmulateConEntry
--		ACCESS  not-accessible
--		STATUS  mandatory
--		DESCRIPTION  ""
--		INDEX { fsSdlcEmulateConPortNo, fsSdlcEmulateConIndex }
--		::= { fsSdlcEmulateConTable 1 }

--	fsSdlcEmulateConPortNo OBJECT-TYPE
--		SYNTAX  INTEGER {
--			port1		(1),
--			port2       (2),
--			port3       (3),
--			port4       (4),
--			port5       (5),
--			port6		(6),
--			port7       (7),
--			port8       (8),
--			port9       (9),
--			portA      	(10),
--			portB		(11),
--			portC      	(12),
--			portD      	(13),
--			portE      	(14),
--			portF      	(15),
--			portG		(16),
--			portH      	(17),
--			portI      	(18),
--			portJ      	(19)
--			}
--		ACCESS  read-write
--		STATUS  mandatory
--		DESCRIPTION  ""
--		::= { fsSdlcEmulateConEntry 1 }

--	fsSdlcEmulateConIndex OBJECT-TYPE
--		SYNTAX  INTEGER
--		ACCESS  read-only
--		STATUS  mandatory
--		DESCRIPTION  ""
--		::= { fsSdlcEmulateConEntry 2 }

--	fsSdlcEmulateConLocalLogicalId OBJECT-TYPE
--		SYNTAX  INTEGER (1..99)
--		ACCESS  read-write
--		STATUS  mandatory
--		DESCRIPTION  
--			"The FRAD transfers data between logical units.  
--			The FRAD maps real controllers onto artificial 
--			logical units.  This is done so that the FRAD 
--			can, for example, map a control unit at a site 
--			with an address of C1 onto a controller that is 
--			known to the host as D2. The Local Logical ID is the 
--			unique identifying number in the FRAD that is mapped 
--			through the Controller table to a real controller.  
--			The Logical ID can be any number from 01 to 99.  
--			The real controller ID is entered as the Local 
--			Controller Address"
--		::= { fsSdlcEmulateConEntry 3 }

--	fsSdlcEmulateConLocalCUaddr OBJECT-TYPE
--		SYNTAX  DisplayString (SIZE (0..4))
--		ACCESS  read-write
--		STATUS  mandatory
--		DESCRIPTION  
--			"The Local Controller Address can be one of 
--			two things.  It is the address of the controller 
--			connected to the FRAD port if the port is configured 
--			as Terminal.  It is the address of a controller for 
--			which the FRAD will answer if the FRAD port is connected 
--			to the host and configured as Host.  This address 
--			consists of two hexadecimal digits."
--		::= { fsSdlcEmulateConEntry 4 }

--	fsSdlcEmulateConRemoteIPaddr OBJECT-TYPE
--		SYNTAX  IpAddress
--		ACCESS  read-write
--		STATUS  mandatory
--		DESCRIPTION  
--			"This option is available only if you selected 
--			'Terminal' for the Polling Emulation Type.  
--			The Remote IP Address is the IP address of the 
--			FRAD (Host) which will receive messages from this 
--			FRAD port.  Every FRAD has an IP address which is 
--			assigned by the Network Administrator."
--		::= { fsSdlcEmulateConEntry 5 }

--	fsSdlcEmulateConRemoteLogicalId OBJECT-TYPE
--		SYNTAX  INTEGER (1..99)
--		ACCESS  read-write
--		STATUS  mandatory
--		DESCRIPTION  
--			"This option is available only if you selected 
--			'Terminal' for the Polling Emulation Type.  The 
--			Remote Logical ID Number is the unique logical number 
--			representing the controller in the remote FRAD (Host) 
--			which will receive messages from this FRAD port.  
--			The Logical ID can be any number from 01 to 99."
--		::= { fsSdlcEmulateConEntry 6 }

--	fsSdlcEmulateConStatus OBJECT-TYPE
--		SYNTAX  INTEGER {
--			view   (1),
--			add     (2),
--			delete  (3)
--			}
--		ACCESS  read-write
--		STATUS  mandatory
--		DESCRIPTION  ""
--		::= { fsSdlcEmulateConEntry 7 }


-- ***************************************************************************
-- AsyncBuros Emulation parameters

fsAsyncBurosEmulateDefTable OBJECT-TYPE
	SYNTAX  SEQUENCE OF FsAsyncBurosEmulateDefEntry
	ACCESS  not-accessible
	STATUS  mandatory
	DESCRIPTION  ""
	::= { fsAsyncBurosEmulation 1 }

	FsAsyncBurosEmulateDefEntry ::= SEQUENCE {
		fsAsyncBurosEmulatePortNo		INTEGER,
		fsAsyncBurosEmulateSpeed		INTEGER,
		fsAsyncBurosEmulateType			INTEGER,
		fsAsyncBurosEmulateResTimeout		INTEGER,
		fsAsyncBurosEmulateCtsDelay	      INTEGER,
		fsAsyncBurosEmulateStatus		INTEGER
		}

	fsAsyncBurosEmulateDefEntry OBJECT-TYPE
		SYNTAX  FsAsyncBurosEmulateDefEntry
		ACCESS  not-accessible
		STATUS  mandatory
		DESCRIPTION  ""
		INDEX { fsAsyncBurosEmulatePortNo }
		::= { fsAsyncBurosEmulateDefTable 1 }

	fsAsyncBurosEmulatePortNo OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION  ""
		::= { fsAsyncBurosEmulateDefEntry 1 }

	fsAsyncBurosEmulateSpeed OBJECT-TYPE
		SYNTAX  INTEGER {
			baud001200  (1),
			baud002400  (2),
			baud004800  (3),
			baud009600  (4),
			baud019200  (5),
			baud038400  (6),
			baud048000  (7),
			baud057600  (8),
			baud115200  (9)
			}
		ACCESS  read-write
		STATUS  mandatory
		DESCRIPTION 
			"The sync speed the FRAD will provide/accept clock to/from the
			user's equipment"
		::= { fsAsyncBurosEmulateDefEntry 2 }

	fsAsyncBurosEmulateType OBJECT-TYPE
		SYNTAX  INTEGER {
			hostEnd     (1),
			terminalEnd (2)
			}
		ACCESS  read-write
		STATUS  mandatory
		DESCRIPTION 
			"The Asynchronous Burroughs parameters allows 
			you to set the Polling Emulation Type.  The FRAD port 
			must be configured as either Host or Terminal, 
			depending on which device is connected to the port. 
			If the FRAD port you are configuring is connected to a Host, 
			type '1'.  If it is connected to a Terminal, type '2'."
		::= { fsAsyncBurosEmulateDefEntry 3 }

	fsAsyncBurosEmulateResTimeout OBJECT-TYPE
		SYNTAX  INTEGER (1..255)
		ACCESS  read-write
		STATUS  mandatory
		DESCRIPTION 
			"Asynchronous Burroughs parameters allows you to set 
			the Terminal Timer.  The default is three seconds.  
			This timer needs to be set only if you selected Terminal 
			as the Polling Emulation Type."
		::= { fsAsyncBurosEmulateDefEntry 4 }

	fsAsyncBurosEmulateCtsDelay OBJECT-TYPE
		SYNTAX  INTEGER (0..255)
		ACCESS  read-write
		STATUS  mandatory
		DESCRIPTION ""
		::= { fsAsyncBurosEmulateDefEntry 5 }

	fsAsyncBurosEmulateStatus OBJECT-TYPE
		SYNTAX  INTEGER {
			view   (1),
			modify (2)
			}
		ACCESS  read-write
		STATUS  mandatory
		DESCRIPTION  ""
		::= { fsAsyncBurosEmulateDefEntry 6 }

fsAsyncBurosTable OBJECT-TYPE
	SYNTAX  SEQUENCE OF FsAsyncBurosEntry
	ACCESS  not-accessible
	STATUS  mandatory
	DESCRIPTION  ""
	::= { fsAsyncBurosEmulation 2 }

	FsAsyncBurosEntry ::= SEQUENCE {
		fsAsyncBurosPortNo			INTEGER,
		fsAsyncBurosIndex          		INTEGER,
		fsAsyncBurosLocalLogicalId    	INTEGER,
		fsAsyncBurosLocalDeviceAddr   	DisplayString,
		fsAsyncBurosLocalGroupAddr    	DisplayString,
		fsAsyncBurosRemoteIPaddr        	IpAddress,
		fsAsyncBurosRemoteLogicalId     	INTEGER,
		fsAsyncBurosStatus         		INTEGER
		}

	fsAsyncBurosEntry OBJECT-TYPE
		SYNTAX  FsAsyncBurosEntry
		ACCESS  not-accessible
		STATUS  mandatory
		DESCRIPTION  ""
		INDEX { fsAsyncBurosPortNo, fsAsyncBurosIndex }
		::= { fsAsyncBurosTable 1 }

	fsAsyncBurosPortNo OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-write
		STATUS  mandatory
		DESCRIPTION  ""
		::= { fsAsyncBurosEntry 1 }

	fsAsyncBurosIndex OBJECT-TYPE
		SYNTAX  INTEGER
		ACCESS  read-only
		STATUS  mandatory
		DESCRIPTION  ""
		::= { fsAsyncBurosEntry 2 }

	fsAsyncBurosLocalLogicalId OBJECT-TYPE
		SYNTAX  INTEGER (1..99)
		ACCESS  read-write
		STATUS  mandatory
		DESCRIPTION  
			"The FRAD transfers data between logical units.  
			This means that the FRAD doesn't deal with real 
			controllers but maps real controllers to artificial 
			logical units.  This is done so that the FRAD can, 
			for example, map a real control unit that has address 
			C1 onto a controller that is known to the host as D2.  
			In this way point-to-point terminals at one end of 
			the network can be made to appear as a multi-dropped 
			line to the host.  The Local Logical ID number is the 
			unique identifying number in the FRAD that is then 
			mapped through this table to a real controller."
		::= { fsAsyncBurosEntry 3 }

	fsAsyncBurosLocalDeviceAddr OBJECT-TYPE
		SYNTAX  DisplayString (SIZE (0..4))
		ACCESS  read-write
		STATUS  mandatory
		DESCRIPTION  
			"This is the address of either a physical 
			controller to be polled if the FRAD port is configured 
			for terminal or a controller for which the FRAD 
			will answer if the FRAD port is configured for Host."
		::= { fsAsyncBurosEntry 4 }

	fsAsyncBurosLocalGroupAddr OBJECT-TYPE
		SYNTAX  DisplayString (SIZE (0..4))
		ACCESS  read-write
		STATUS  mandatory
		DESCRIPTION  
			"Controllers (terminals) in Burroughs Poll/Select 
			can be referred to by a group address.  When a group 
			address is used in a poll, any terminal in that group 
			is permitted to respond."
		::= { fsAsyncBurosEntry 5 }

	fsAsyncBurosRemoteIPaddr OBJECT-TYPE
		SYNTAX  IpAddress
		ACCESS  read-write
		STATUS  mandatory
		DESCRIPTION  
			"This is the IP address of the device that will 
			receive messages sent from this FRAD port.  
			Every FRAD has an IP address. "
		::= { fsAsyncBurosEntry 6 }

	fsAsyncBurosRemoteLogicalId OBJECT-TYPE
		SYNTAX  INTEGER (1..99)
		ACCESS  read-write
		STATUS  mandatory
		DESCRIPTION  
			"- This is the logical ID of the remote device 
			which will receive messages sent from this FRAD port. "
		::= { fsAsyncBurosEntry 7 }

	fsAsyncBurosStatus OBJECT-TYPE
		SYNTAX  INTEGER {
			view   (1),
			add    (2),
			delete (3),
                  modify (4)
			}
		ACCESS  read-write
		STATUS  mandatory
		DESCRIPTION  ""
		::= { fsAsyncBurosEntry 8 }


-- ***************************************************************************
-- SyncBuros Emulation parameters

fsSyncBurosEmulateDefTable OBJECT-TYPE
	SYNTAX  SEQUENCE OF FsSyncBurosEmulateDefEntry
	ACCESS  not-accessible
	STATUS  mandatory
	DESCRIPTION  ""
	::= { fsSyncBurosEmulation 1 }

	FsSyncBurosEmulateDefEntry ::= SEQUENCE {
		fsSyncBurosEmulatePortNo		INTEGER,
		fsSyncBurosEmulateSpeed			INTEGER,
		fsSyncBurosEmulateType			INTEGER,
		fsSyncBurosEmulateResTimeout		INTEGER,
		fsSyncBurosEmulateCtsDelay		INTEGER,
		fsSyncBurosEmulateStatus		INTEGER
		}

	fsSyncBurosEmulateDefEntry OBJECT-TYPE
		SYNTAX  FsSyncBurosEmulateDefEntry
		ACCESS  not-accessible
		STATUS  mandatory
		DESCRIPTION  ""
		INDEX { fsSyncBurosEmulatePortNo }
		::= { fsSyncBurosEmulateDefTable 1 }

	fsSyncBurosEmulatePortNo OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION  ""
		::= { fsSyncBurosEmulateDefEntry 1 }

	fsSyncBurosEmulateSpeed OBJECT-TYPE
		SYNTAX  INTEGER {
			external    (0),
			baud002400  (1),
			baud004800  (2),
			baud009600  (3),
			baud019200  (4),
			baud038400  (5),
			baud048000  (6),
			baud056000  (7),
			baud064000  (8),
			baud096000  (9),
			baud128000  (10),
			baud192000  (11),
			baud256000  (12),
			baud384000  (13),
			baud512000  (14),
			baud768000  (15),
			baud1024000 (16)
			}
		ACCESS  read-write
		STATUS  mandatory
		DESCRIPTION 
			"The sync speed the FRAD will provide/accept clock to/from the
			user's equipment"
		::= { fsSyncBurosEmulateDefEntry 2 }

	fsSyncBurosEmulateType OBJECT-TYPE
		SYNTAX  INTEGER {
			hostEnd     (1),
			terminalEnd (2)
			}
		ACCESS  read-write
		STATUS  mandatory
		DESCRIPTION 
			"If the FRAD port you are configuring is connected 
			to a Host, type '1'.  If it is connected to a Terminal, 
			type '2'."
		::= { fsSyncBurosEmulateDefEntry 3 }

	fsSyncBurosEmulateResTimeout OBJECT-TYPE
		SYNTAX  INTEGER (1..255)
		ACCESS  read-write
		STATUS  mandatory
		DESCRIPTION ""
		::= { fsSyncBurosEmulateDefEntry 4 }

	fsSyncBurosEmulateCtsDelay OBJECT-TYPE
		SYNTAX  INTEGER (0..255)
		ACCESS  read-write
		STATUS  mandatory
		DESCRIPTION ""
		::= { fsSyncBurosEmulateDefEntry 5 }

	fsSyncBurosEmulateStatus OBJECT-TYPE
		SYNTAX  INTEGER {
			view   (1),
			modify (2)
			}
		ACCESS  read-write
		STATUS  mandatory
		DESCRIPTION  ""
		::= { fsSyncBurosEmulateDefEntry 6 }

fsSyncBurosTable OBJECT-TYPE
	SYNTAX  SEQUENCE OF FsSyncBurosEntry
	ACCESS  not-accessible
	STATUS  mandatory
	DESCRIPTION  ""
	::= { fsSyncBurosEmulation 2 }

	FsSyncBurosEntry ::= SEQUENCE {
		fsSyncBurosPortNo				INTEGER,
		fsSyncBurosIndex          		INTEGER,
		fsSyncBurosLocalLogicalId    		INTEGER,
		fsSyncBurosLocalDeviceAddr   		DisplayString,
		fsSyncBurosLocalGroupAddr    		DisplayString,
		fsSyncBurosRemoteIPaddr        	IpAddress,
		fsSyncBurosRemoteLogicalId     	INTEGER,
		fsSyncBurosStatus         		INTEGER
		}

	fsSyncBurosEntry OBJECT-TYPE
		SYNTAX  FsSyncBurosEntry
		ACCESS  not-accessible
		STATUS  mandatory
		DESCRIPTION  ""
		INDEX { fsSyncBurosPortNo, fsSyncBurosIndex }
		::= { fsSyncBurosTable 1 }

	fsSyncBurosPortNo OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-write
		STATUS  mandatory
		DESCRIPTION  ""
		::= { fsSyncBurosEntry 1 }

	fsSyncBurosIndex OBJECT-TYPE
		SYNTAX  INTEGER
		ACCESS  read-only
		STATUS  mandatory
		DESCRIPTION  ""
		::= { fsSyncBurosEntry 2 }

	fsSyncBurosLocalLogicalId OBJECT-TYPE
		SYNTAX  INTEGER (1..99)
		ACCESS  read-write
		STATUS  mandatory
		DESCRIPTION  
			"The FRAD transfers data between logical units.  
			This means that the FRAD doesn't deal with real 
			controllers but maps real controllers to artificial 
			logical units.  This is done so that the FRAD can, 
			for example, map a real control unit at a site 
			that may have an address of C1 onto a controller 
			that is known to the host as D2.  In this way 
			point-to-point terminals at one end of the network 
			can be made to appear as a multi-dropped line to the 
			host.  The Local Logical ID number is the unique 
			identifying number in the FRAD that is then mapped 
			through this table to a real controller." 
		::= { fsSyncBurosEntry 3 }

	fsSyncBurosLocalDeviceAddr OBJECT-TYPE
		SYNTAX  DisplayString (SIZE (0..4))
		ACCESS  read-write
		STATUS  mandatory
		DESCRIPTION
			"This is the address of either a physical 
			controller to be polled if the FRAD port is 
			configured for terminal or a controller for 
			which the FRAD will answer if the FRAD port is 
			configured for Host.  "
		::= { fsSyncBurosEntry 4 }

	fsSyncBurosLocalGroupAddr OBJECT-TYPE
		SYNTAX  DisplayString (SIZE (0..4))
		ACCESS  read-write
		STATUS  mandatory
		DESCRIPTION  
			"If you have selected 'Host' for the Polling 
			Emulation Type, the Local Logical ID option 
			will reappear.  You can either add more addresses 
			or press <ESC> to exit.  If you exit, you will 
			see a list of the addresses which have been entered 
			and be given the option to add, modify or delete.  "
		::= { fsSyncBurosEntry 5 }

	fsSyncBurosRemoteIPaddr OBJECT-TYPE
		SYNTAX  IpAddress
		ACCESS  read-write
		STATUS  mandatory
		DESCRIPTION  
			"This is the IP address of the device that will 
			receive messages sent from this FRAD port.  
			Every FRAD has an IP address.  "
		::= { fsSyncBurosEntry 6 }

	fsSyncBurosRemoteLogicalId OBJECT-TYPE
		SYNTAX  INTEGER (1..99)
		ACCESS  read-write
		STATUS  mandatory
		DESCRIPTION  
			"- This is the logical ID of the remote device 
			which will receive messages sent from this FRAD port."
		::= { fsSyncBurosEntry 7 }

	fsSyncBurosStatus OBJECT-TYPE
		SYNTAX  INTEGER {
			view   (1),
			add    (2),
			delete (3),
                  modify (4)
			}
		ACCESS  read-write
		STATUS  mandatory
		DESCRIPTION  ""
		::= { fsSyncBurosEntry 8 }


-- ***************************************************************************
-- SDLC Route parameters

fsSdlcRouteDefTable OBJECT-TYPE
	SYNTAX  SEQUENCE OF FsSdlcRouteDefEntry
	ACCESS  not-accessible
	STATUS  mandatory
	DESCRIPTION  ""
	::= { fsSdlcRoute 1 }

	FsSdlcRouteDefEntry ::= SEQUENCE {
		fsSdlcRoutePortNo			INTEGER,
		fsSdlcRouteSpeed			INTEGER,
		fsSdlcRouteFormat			INTEGER,
		fsSdlcRouteSwitchedDcd		INTEGER,
		fsSdlcRouteIdleMark		INTEGER,
		fsSdlcRouteStatus			INTEGER
		}

	fsSdlcRouteDefEntry OBJECT-TYPE
		SYNTAX  FsSdlcRouteDefEntry
		ACCESS  not-accessible
		STATUS  mandatory
		DESCRIPTION  ""
		INDEX { fsSdlcRoutePortNo }
		::= { fsSdlcRouteDefTable 1 }

	fsSdlcRoutePortNo OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION  ""
		::= { fsSdlcRouteDefEntry 1 }

	fsSdlcRouteSpeed OBJECT-TYPE
		SYNTAX  INTEGER {
			external    (0),
			baud002400  (1),
			baud004800  (2),
			baud009600  (3),
			baud019200  (4),
			baud038400  (5),
			baud048000  (6),
			baud056000  (7),
			baud064000  (8),
			baud096000  (9),
			baud128000  (10),
			baud192000  (11),
			baud256000  (12),
			baud384000  (13),
			baud512000  (14),
			baud768000  (15),
			baud1024000 (16)
			}
		ACCESS  read-write
		STATUS  mandatory
		DESCRIPTION 
			"The sync speed the FRAD will provide/accept clock to/from the
			user's equipment"
		::= { fsSdlcRouteDefEntry 2 }

	fsSdlcRouteFormat OBJECT-TYPE
		SYNTAX  INTEGER {
			nrz     (1),
			nrzi    (2)
			}
		ACCESS  read-write
		STATUS  mandatory
		DESCRIPTION 
			"The SDLC Routing parameters allows you to set the 
			Data Format.  There are two data formats:  
			Non-Return-to-Zero (NRZ) and Non-Return-to-Zero 
			Inverted (NRZI).  Check your equipment specifications 
			to determine which you are using"
		::= { fsSdlcRouteDefEntry 3 }

	fsSdlcRouteSwitchedDcd OBJECT-TYPE
		SYNTAX  INTEGER {
			switched    (1),
			forced      (2)
			}
		ACCESS  read-write
		STATUS  mandatory
		DESCRIPTION 
			"The SDLC Routing Parameters menu allows you to 
			determine when DCD will be active.  It is only 
			effective on ports set up as DCE interfaces.  
			If DCD is set to Switched, DCD will only be active 
			during data transmission from the FRAD.  If set to 
			Forced, DCD will remain active at all times.  
			The default for this parameter is Forced.  
			(Prior to implementation of this option, a DCE port 
			would raise DCD and keep it active at all times.)"
		::= { fsSdlcRouteDefEntry 4 }

	fsSdlcRouteIdleMark OBJECT-TYPE
		SYNTAX  INTEGER {
			mark    (1),
			flag    (2)
			}
		ACCESS  read-write
		STATUS  mandatory
		DESCRIPTION 
			"Idle Character on the SDLC Routing Parameters menu 
			allows you to select transmission of Mark characters 
			between frames, except after frames whose Poll/Final 
			(P/F) bit is clear (off).  Normally, an HDLC protocol 
			transmits HDLC Flag (0x7e with no zero insertion) 
			characters between frames.  If Idle Character is set to 
			Flag, the FRAD will continue to issue HDLC Flag 
			characters in the idle state. If Idle Character is set 
			to Mark, the FRAD will send solid Mark characters 
			(all binary ones) in the idle state.  The exception is 
			that any frame which does not have the P/F flag of the 
			command byte set (bit 0x10 of the second byte of the frame) 
			will be followed by HDLC Flag characters.  (This exception 
			was explicitly designed for compatibility with IBM AS400s.  
			However, it does reflect the actual state of an HDLC line 
			over half-duplex modems.) The default for this parameter 
			is Flag."
		::= { fsSdlcRouteDefEntry 5 }

	fsSdlcRouteStatus OBJECT-TYPE
		SYNTAX  INTEGER {
			view   (1),
			modify (2)
			}
		ACCESS  read-write
		STATUS  mandatory
		DESCRIPTION  ""
		::= { fsSdlcRouteDefEntry 6 }

fsSdlcRouteConTable OBJECT-TYPE
	SYNTAX  SEQUENCE OF FsSdlcRouteConEntry
	ACCESS  not-accessible
	STATUS  mandatory
	DESCRIPTION  ""
	::= { fsSdlcRoute 2 }

	FsSdlcRouteConEntry ::= SEQUENCE {
		fsSdlcRouteConPortNo		INTEGER,
		fsSdlcRouteConIndex          	INTEGER,
		fsSdlcRouteConAddr   		DisplayString,
            fsSdlcRouteGptName            DisplayString,
		fsSdlcRouteConPri    		INTEGER,
		fsSdlcRouteConStatus         	INTEGER
		}

	fsSdlcRouteConEntry OBJECT-TYPE
		SYNTAX  FsSdlcRouteConEntry
		ACCESS  not-accessible
		STATUS  mandatory
		DESCRIPTION  ""
		INDEX { fsSdlcRouteConPortNo, fsSdlcRouteConIndex }
		::= { fsSdlcRouteConTable 1 }

	fsSdlcRouteConPortNo OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-write
		STATUS  mandatory
		DESCRIPTION  ""
		::= { fsSdlcRouteConEntry 1 }

	fsSdlcRouteConIndex OBJECT-TYPE
		SYNTAX  INTEGER
		ACCESS  read-only
		STATUS  mandatory
		DESCRIPTION  ""
		::= { fsSdlcRouteConEntry 2 }

	fsSdlcRouteConAddr OBJECT-TYPE
		SYNTAX  DisplayString (SIZE (0..2))
		ACCESS  read-write
		STATUS  mandatory
		DESCRIPTION  
			"Type the SDLC controller address."
		::= { fsSdlcRouteConEntry 3 }

	fsSdlcRouteGptName OBJECT-TYPE
		SYNTAX  DisplayString (SIZE (1..12))
		ACCESS  read-write
		STATUS  mandatory
		DESCRIPTION  ""
		::= { fsSdlcRouteConEntry 4 }

	fsSdlcRouteConPri OBJECT-TYPE
		SYNTAX  INTEGER {
			immediate   (0),
			high        (1),
			medium	(2),
			low		(3)
			}
		ACCESS  read-write
		STATUS  mandatory
		DESCRIPTION  
			"Enter the priority level of the data."
		::= { fsSdlcRouteConEntry 5 }

	fsSdlcRouteConStatus OBJECT-TYPE
		SYNTAX  INTEGER {
			view   (1),
			add    (2),
			delete (3),
                  modify (4)
			}
		ACCESS  read-write
		STATUS  mandatory
		DESCRIPTION  ""
		::= { fsSdlcRouteConEntry 6 }


-- ***************************************************************************
-- ByteSync Encapsulation parameters

fsByteSyncEncapDefTable OBJECT-TYPE
	SYNTAX  SEQUENCE OF FsByteSyncEncapDefEntry
	ACCESS  not-accessible
	STATUS  mandatory
	DESCRIPTION  ""
	::= { fsByteSyncEncapsulation 1 }

	FsByteSyncEncapDefEntry ::= SEQUENCE {
		fsByteSyncEncapPortNo			INTEGER,
		fsByteSyncEncapSpeed			INTEGER,
		fsByteSyncEncapPri			INTEGER,
		fsByteSyncEncapDestinationPort	INTEGER,
		fsByteSyncEncapCode			INTEGER,
		fsByteSyncEncapGptName			DisplayString,
		fsByteSyncEncapStatus			INTEGER
		}

	fsByteSyncEncapDefEntry OBJECT-TYPE
		SYNTAX  FsByteSyncEncapDefEntry
		ACCESS  not-accessible
		STATUS  mandatory
		DESCRIPTION  ""
		INDEX { fsByteSyncEncapPortNo }
		::= { fsByteSyncEncapDefTable 1 }

	fsByteSyncEncapPortNo OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION  ""
		::= { fsByteSyncEncapDefEntry 1 }

	fsByteSyncEncapSpeed OBJECT-TYPE
		SYNTAX  INTEGER {
			external    (0),
			baud002400  (1),
			baud004800  (2),
			baud009600  (3),
			baud019200  (4),
			baud038400  (5),
			baud048000  (6),
			baud056000  (7),
			baud064000  (8),
			baud096000  (9),
			baud128000  (10),
			baud192000  (11),
			baud256000  (12),
			baud384000  (13),
			baud512000  (14),
			baud768000  (15),
			baud1024000 (16)
			}
		ACCESS  read-write
		STATUS  mandatory
		DESCRIPTION 
			"The sync speed the FRAD will provide/accept clock to/from the
			user's equipment"
		::= { fsByteSyncEncapDefEntry 2 }

	fsByteSyncEncapPri OBJECT-TYPE
		SYNTAX  INTEGER {
			immediate   (0),
			high        (1),
			medium	(2),
			low		(3)
			}
		ACCESS  read-write
		STATUS  mandatory
		DESCRIPTION 
			"Select the data's priority level."
		::= { fsByteSyncEncapDefEntry 3 }

	fsByteSyncEncapDestinationPort OBJECT-TYPE
		SYNTAX  INTEGER {
			portNet-port16  (1),
			port1           (2),
			port2           (3),
			port3           (4),
			port4           (5),
			port5           (6),
			port6           (7),
			port7           (8),
			port8           (9),
			port9           (10),
			port10          (11),
			port11          (12),
			port12          (13),
			port13          (14),
			port14          (15),
			port15          (16)
			}
		ACCESS  read-write
		STATUS  mandatory
		DESCRIPTION 
			"Select the destination port of the remote FRAD."
		::= { fsByteSyncEncapDefEntry 4 }

	fsByteSyncEncapCode OBJECT-TYPE
		SYNTAX  INTEGER {
			ascii   (1),
			ebcdic  (2)
			}
		ACCESS  read-write
		STATUS  mandatory
		DESCRIPTION 
			"Select the code set to use."
		::= { fsByteSyncEncapDefEntry 5 }

	fsByteSyncEncapGptName OBJECT-TYPE
		SYNTAX  DisplayString (SIZE (11))
		ACCESS  read-write
		STATUS  mandatory
		DESCRIPTION ""
		::= { fsByteSyncEncapDefEntry 6 }

	fsByteSyncEncapStatus OBJECT-TYPE
		SYNTAX  INTEGER {
			view   (1),
			modify (2)
			}
		ACCESS  read-write
		STATUS  mandatory
		DESCRIPTION  ""
		::= { fsByteSyncEncapDefEntry 7 }


-- ***************************************************************************
-- Telnet Terminal parameters

fsTelnetTermDefTable OBJECT-TYPE
	SYNTAX  SEQUENCE OF FsTelnetTermDefEntry
	ACCESS  not-accessible
	STATUS  mandatory
	DESCRIPTION  ""
	::= { fsTelnetTerminal 1 }

	FsTelnetTermDefEntry ::= SEQUENCE {
		fsTelnetTermPortNo		INTEGER,
		fsTelnetTermSpeed			INTEGER,
		fsTelnetTermDataBits          INTEGER,
		fsTelnetTermParity		INTEGER,
		fsTelnetTermStopBits		INTEGER,
		fsTelnetTermFlowControl		INTEGER,
		fsTelnetTermFCType		INTEGER,
		fsTelnetTermConnectionType	INTEGER,
		fsTelnetTermAnswerMode		INTEGER,
		fsTelnetTermDataMode		INTEGER,
		fsTelnetTermNullMode		INTEGER,
		fsTelnetTermQuietMode         INTEGER,
		fsTelnetTermLocalEcho		INTEGER,
		fsTelnetTermRemoteEcho		INTEGER,
		fsTelnetTermForceDTR		INTEGER,
		fsTelnetTermForceDCD		INTEGER,
		fsTelnetTermForceDSR		INTEGER,
		fsTelnetTermLocalTCP		INTEGER,
		fsTelnetTermRemoteTCP		INTEGER,
		fsTelnetTermRemoteIP		IpAddress,
            fsTelnetTermXpadLogPort       INTEGER,
		fsTelnetTermStatus		INTEGER
		}

	fsTelnetTermDefEntry OBJECT-TYPE
		SYNTAX  FsTelnetTermDefEntry
		ACCESS  not-accessible
		STATUS  mandatory
		DESCRIPTION  ""
		INDEX { fsTelnetTermPortNo }
		::= { fsTelnetTermDefTable 1 }

	fsTelnetTermPortNo OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION  ""
		::= { fsTelnetTermDefEntry 1 }

	fsTelnetTermSpeed OBJECT-TYPE
		SYNTAX  INTEGER {
			baud001200  (1),
			baud002400  (2),
			baud004800  (3),
			baud009600  (4),
			baud019200  (5),
			baud038400  (6),
			baud048000  (7),
			baud057600  (8),
			baud115200  (9)
			}
		ACCESS  read-write
		STATUS  mandatory
		DESCRIPTION  
			"The async speed of the user's equipment"
		::= { fsTelnetTermDefEntry 2 }

	fsTelnetTermDataBits OBJECT-TYPE
		SYNTAX  INTEGER {
			sevenBits   (7),
			eightBits   (8)
			}
		ACCESS  read-write
		STATUS  mandatory
		DESCRIPTION  
			"Select the number of data bits."
		::= { fsTelnetTermDefEntry 3 }

	fsTelnetTermParity OBJECT-TYPE
		SYNTAX  INTEGER {
			oddParity   (1),
			evenParity  (2),
			markParity  (3),
			spaceParity (4),
			noParity    (5)
			}
		ACCESS  read-write
		STATUS  mandatory
		DESCRIPTION  
			"Select the parity to be used."
		::= { fsTelnetTermDefEntry 4 }

	fsTelnetTermStopBits OBJECT-TYPE
		SYNTAX  INTEGER {
			oneBit  (1),
			twoBits (2)
			}
		ACCESS  read-write
		STATUS  mandatory
		DESCRIPTION  
			"Select the number of stop bits."
		::= { fsTelnetTermDefEntry 5 }

	fsTelnetTermFlowControl OBJECT-TYPE
		SYNTAX  INTEGER {
			off     (1),
			txOnly  (2),
			rxOnly  (3),
			on      (4)
			}
		ACCESS  read-write
		STATUS  mandatory
		DESCRIPTION  
			"Flow control can be enabled for transmit 
			only, receive only or both directions for either 
			of the two Flow Control Types."
		::= { fsTelnetTermDefEntry 6 }

	fsTelnetTermFCType OBJECT-TYPE
		SYNTAX  INTEGER {
			rtsCts  (1),
			xonXoff (2)
			}
		ACCESS  read-write
		STATUS  mandatory
		DESCRIPTION  
			"Select the type of flow control. Both RTS/CTS 
			hardware flow control and XON/XOFF software flow 
			control are supported."
		::= { fsTelnetTermDefEntry 7 }

	fsTelnetTermConnectionType OBJECT-TYPE
		SYNTAX  INTEGER {
			manual  (1),
			dtrDial (2)
			}
		ACCESS  read-write
		STATUS  mandatory
		DESCRIPTION  
			"This parameter determines how the Telnet Client 
			terminal will initiate a connection with the Telnet 
			Server.  You can select Manual connection or DTR Dial. 
			In the manual mode, you manually enter an IP Address 
			to connect to a Telnet Server by using the Telnet 
			Terminal Commands Menu (see Section 5.16.19) on the 
			local terminal.  This menu can also be used to PING a 
			remote Server.  Pressing <CTRL> 'X' will end the 
			Telnet session.  It can also be terminated from the 
			remote end. In the DTR dial mode, Telnet Terminal will 			
			initiate a Telnet connection to a remote Telnet Server 
			immediately after the port's DTR is enabled.  The remote 
			TCP port and remote IP address configured in the Telnet 
			Terminal Parameters menu will be used to make the connection.  			
			The connection is closed when DTR is off.  Note that DTR 
			can be forced on as described above."
		::= { fsTelnetTermDefEntry 8 }

	fsTelnetTermAnswerMode OBJECT-TYPE
		SYNTAX  INTEGER {
			off     (1),
			on      (2)
			}
		ACCESS  read-write
		STATUS  mandatory
		DESCRIPTION  
			"This parameter allows you to set the port to 
			act as a Telnet Server by turning on the Answer Mode.  
			The port will then respond to Telnet Clients attempting 
			to make a connection.  If the Answer Mode is off, the 
			port will not answer Telnet calls."
		::= { fsTelnetTermDefEntry 9 }

	fsTelnetTermDataMode OBJECT-TYPE
		SYNTAX  INTEGER {
			normal  (1),
			binary  (2)
			}
		ACCESS  read-write
		STATUS  mandatory
		DESCRIPTION  
			"This parameter allows you to set the Data Mode.  
			There are two modes:  normal and binary.  The Normal data 
			mode uses 'Control X' as an escape character.  It allows 
			parameter handshaking after connection.  The binary data 
			mode is in accordance with RFC 856.  When in Binary Data 
			mode, the only available method for dropping a connection 
			is to drop the DTR control signal on either end of the 
			connection.  (Note that dropping DTR drops the connection 
			in Normal mode as well.)  The default for this parameter 
			is Normal."
		::= { fsTelnetTermDefEntry 10 }

	fsTelnetTermNullMode OBJECT-TYPE
		SYNTAX  INTEGER {
			normal   (1),
			disable  (2)
			}
		ACCESS  read-write
		STATUS  mandatory
		DESCRIPTION  ""
		::= { fsTelnetTermDefEntry 11 }

	fsTelnetTermQuietMode OBJECT-TYPE
		SYNTAX  INTEGER {
			on      (1),
			off     (2)
			}
		ACCESS  read-write
		STATUS  mandatory
		DESCRIPTION  
			"When the Telnet Module Connection Type is configured 
			as 'Manual' and there is no active Telnet session 
			on a given port, the Telnet Command menu will be 
			displayed on the associated terminal.  Quiet Mode allows 
			you to disable this display.  This capability is useful 
			if a host machine or computer connected to the Telnet 
			port does not tolerate the menu characters being 
			received from the Telnet port.  The default for this 
			option is Off."
		::= { fsTelnetTermDefEntry 12 }

	fsTelnetTermLocalEcho OBJECT-TYPE
		SYNTAX  INTEGER {
			auto    (1),
			enable  (2),
			disable (3)
			}
		ACCESS  read-write
		STATUS  mandatory
		DESCRIPTION  
			"Local Echo is a straight forward mechanism for 
			displaying data which can be configured in the 
			FRAD by an On, Off or Auto selection. The Local 
			Echo option has three possible settings.  If it is 
			enabled, the FRAD will always echo characters 
			received from the terminal back to the terminal.  
			If Local Echo is disabled, the FRAD will not echo 
			received characters back to the terminal.  
			When Local Echo is set to Auto, the FRAD will echo 
			characters back to the local terminal only if the 
			remote echo option has not been successfully negotiated 
			between the local and remote Telnet modules (the FRAD 
			is performing the Store and Forward option)."
		::= { fsTelnetTermDefEntry 13 }

	fsTelnetTermRemoteEcho OBJECT-TYPE
		SYNTAX  INTEGER {
			auto    (1),
			enable  (2),
			disable (3)
			}
		ACCESS  read-write
		STATUS  mandatory
		DESCRIPTION  
			"There are three settings for this option- 
			Enabled: The FRAD will not attempt to negotiate 
			the Telnet echo option and will refuse to implement 
			it even if the remote Telnet module requests it to 
			do so.  The FRAD will always store data from the local 
			terminal until a <CR> is received or the buffer is 
			filled, then forwards it to the host. Disabled:  
			The FRAD will attempt to negotiate the Telnet echo 
			option and will implement it if requested by the remote 
			Telnet module.  The FRAD will forward all received data 
			immediately to the host even if the remote Telnet 
			module refused the negotiation. Auto:  The FRAD will 
			attempt to negotiate the Telnet echo option and will 
			implement it if requested.  If the negotiation fails, 
			the FRAD will store and forward data.  If the negotiation 
			succeeds, the FRAD will forward all data received from 
			the local terminal immediately."
		::= { fsTelnetTermDefEntry 14 }

	fsTelnetTermForceDTR OBJECT-TYPE
		SYNTAX  INTEGER {
			no      (1),
			yes     (2)
			}
		ACCESS  read-write
		STATUS  mandatory
		DESCRIPTION  
			"This option allows you to force DTR to be On.  Forcing 
			a DTR signal is useful if the terminal equipment 
			connected to the FRAD port fails to supply DTR.  			
			This will also prevent a Telnet session from being 
			disconnected if DTR is dropped."
		::= { fsTelnetTermDefEntry 15 }

	fsTelnetTermForceDCD OBJECT-TYPE
		SYNTAX  INTEGER {
			no      (1),
			yes     (2)
			}
		ACCESS  read-write
		STATUS  mandatory
		DESCRIPTION  
			"This option allows you to force DCD to be On.  
			The Telnet module raises and lowers this control 
			signal to indicate the connection status of its 
			Telnet session. Forcing the signal On is useful 
			if the varying DCD signal has a negative effect 			
			on the operation of the attached terminal."
		::= { fsTelnetTermDefEntry 16 }

	fsTelnetTermForceDSR OBJECT-TYPE
		SYNTAX  INTEGER {
			no      (1),
			yes     (2)
			}
		ACCESS  read-write
		STATUS  mandatory
		DESCRIPTION  
			"This option allows you to force DSR to be On.  
			The Telnet module raises and lowers this control 
			signal to indicate the connection status of its 
			Telnet session.  Forcing the signal On is useful 
			if the varying DSR signal has a negative effect on 
			the operation of the attached terminal. "
		::= { fsTelnetTermDefEntry 17 }

	fsTelnetTermLocalTCP OBJECT-TYPE
		SYNTAX  INTEGER
		ACCESS  read-write
		STATUS  mandatory
		DESCRIPTION  
			"This option allows you to enter the Local TCP Port."
		::= { fsTelnetTermDefEntry 18 }

	fsTelnetTermRemoteTCP OBJECT-TYPE
		SYNTAX  INTEGER
		ACCESS  read-write
		STATUS  mandatory
		DESCRIPTION  
			"This option allows you to enter the Remote TCP Port 
			number.  If you are using the DTR Dial or Continuous 
			Connection Types, the number entered here will be used 
			to establish a Telnet session.  If you are using the 
			Manual Connection Type, you do not need to enter 
			this number."
		::= { fsTelnetTermDefEntry 19 }

	fsTelnetTermRemoteIP OBJECT-TYPE
		SYNTAX  IpAddress
		ACCESS  read-write
		STATUS  mandatory
		DESCRIPTION  
			"Enter the IP address of the remote device."
		::= { fsTelnetTermDefEntry 20 }

	fsTelnetTermXpadLogPort OBJECT-TYPE
		SYNTAX  INTEGER
		ACCESS  read-write
		STATUS  mandatory
		DESCRIPTION "" 
		::= { fsTelnetTermDefEntry 21 }

	fsTelnetTermStatus OBJECT-TYPE
		SYNTAX  INTEGER {
			view   (1),
			modify (2)
			}
		ACCESS  read-write
		STATUS  mandatory
		DESCRIPTION  ""
		::= { fsTelnetTermDefEntry 22 }


-- ***************************************************************************
-- Annex-G parameters

--fsAnnexGDefTable OBJECT-TYPE
--	SYNTAX  SEQUENCE OF FsAnnexGDefEntry
--	ACCESS  not-accessible
--	STATUS  mandatory
--	DESCRIPTION  ""
--	::= { fsAnnexG 1 }

--	FsAnnexGDefEntry ::= SEQUENCE {
--		fsAnnexGPortNo		INTEGER,
--		fsAnnexGSpeed		INTEGER,
--		fsAnnexGRetryCount      INTEGER,
--		fsAnnexGRetryTimer	INTEGER,
--		fsAnnexGHdlcAddress	INTEGER,
--		fsAnnexGMaxLcn		INTEGER,
--		fsAnnexGStatus		INTEGER
--		}

--	fsAnnexGDefEntry OBJECT-TYPE
--		SYNTAX  FsAnnexGDefEntry
--		ACCESS  not-accessible
--		STATUS  mandatory
--		DESCRIPTION  ""
--		INDEX { fsAnnexGPortNo }
--		::= { fsAnnexGDefTable 1 }

--	fsAnnexGPortNo OBJECT-TYPE
--		SYNTAX  INTEGER {
--			port1		(1),
--			port2       (2),
--			port3       (3),
--			port4       (4),
--			port5       (5),
--			port6		(6),
--			port7       (7),
--			port8       (8),
--			port9       (9),
--			portA      	(10),
--			portB		(11),
--			portC      	(12),
--			portD      	(13),
--			portE      	(14),
--			portF      	(15),
--			portG		(16),
--			portH      	(17),
--			portI      	(18),
--			portJ      	(19)
--			}
--		ACCESS  read-only
--		STATUS  mandatory
--		DESCRIPTION  ""
--		::= { fsAnnexGDefEntry 1 }

--	fsAnnexGSpeed OBJECT-TYPE
--		SYNTAX  INTEGER {
--			external    (0),
--			baud002400  (1),
--			baud004800  (2),
--			baud009600  (3),
--			baud019200  (4),
--			baud038400  (5),
--			baud048000  (6),
--			baud056000  (7),
--			baud064000  (8),
--			baud096000  (9),
--			baud128000  (10),
--			baud192000  (11),
--			baud256000  (12),
--			baud384000  (13),
--			baud512000  (14),
--			baud768000  (15),
--			baud1024000 (16)
--			}
--		ACCESS  read-write
--		STATUS  mandatory
--		DESCRIPTION 
--			"The sync speed the FRAD will provide/accept clock to/from the
--			ser's equipment"
--		::= { fsAnnexGDefEntry 2 }

--	fsAnnexGRetryCount OBJECT-TYPE
--		SYNTAX  INTEGER (1..255)
--		ACCESS  read-write
--		STATUS  mandatory
--		DESCRIPTION  
--			"Set the Retry Count.  This parameter defines the 
--			number of times the Level II X.25 protocol (LAP-B) 
--			will attempt to transmit something when errors occur."
--		::= { fsAnnexGDefEntry 3 }

--	fsAnnexGRetryTimer OBJECT-TYPE
--		SYNTAX  INTEGER (1..255)
--		ACCESS  read-write
--		STATUS  mandatory
--		DESCRIPTION  
--			"Set the Retry Timer.  This is the receive timeout, 
--			in seconds, used by the Level II X.25 protocol."
--		::= { fsAnnexGDefEntry 4 }

--	fsAnnexGHdlcAddress OBJECT-TYPE
--		SYNTAX  INTEGER {
--			dte	(1),
--			dce	(2)
--			}		
--		ACCESS  read-write
--		STATUS  mandatory
--		DESCRIPTION  
--			"Set the HDLC Address.  This specifies which side 
--			of the Level II protocol the port will support:  
--			HDLC DCE Address (commands use address 3), or HDLC 
--			DTE Address (commands use address 1).  The equipment 
--			that is connected to the Annex G port on the FRAD 
--			(DCE or DTE) will be configured for the other side 
--			(DTE or DCE)."
--		::= { fsAnnexGDefEntry 5 }

--	fsAnnexGMaxLcn OBJECT-TYPE
--		SYNTAX  INTEGER (1..255)
--		ACCESS  read-write
--		STATUS  mandatory
--		DESCRIPTION  
--			"Set a maximum Logical Channel Number (LCN).  
--			When the FRAD receives an incoming Call Request 
--			from an Annex G port, it must assign an LCN to that 
--			call for use on the Frame Relay link.  You can set a 
--			maximum for this number.  The default for this 
--			parameter is 128"
--		::= { fsAnnexGDefEntry 6 }

--	fsAnnexGStatus OBJECT-TYPE
--		SYNTAX  INTEGER {
--			view   (1),
--			modify  (2)
--			}
--		ACCESS  read-write
--		STATUS  mandatory
--		DESCRIPTION  ""
--		::= { fsAnnexGDefEntry 7 }

--fsAnnexGPvcTable OBJECT-TYPE
--	SYNTAX  SEQUENCE OF FsAnnexGPvcEntry
--	ACCESS  not-accessible
--	STATUS  mandatory
--	DESCRIPTION  ""
--	::= { fsAnnexG 2 }

--	FsAnnexGPvcEntry ::= SEQUENCE {
--		fsAnnexGPvcPortNo			INTEGER,
--		fsAnnexGPvcIndex          	INTEGER,
--		fsAnnexGPvcLcnIn      		INTEGER,
--		fsAnnexGPvcLcnOut         	INTEGER,
--		fsAnnexGPvcFrPort        	INTEGER,
--		fsAnnexGPvcDlci     		INTEGER,
--		fsAnnexGPvcPri     		INTEGER,
--		fsAnnexGPvcStatus         	INTEGER
--		}

--	fsAnnexGPvcEntry OBJECT-TYPE
--		SYNTAX  FsAnnexGPvcEntry
--		ACCESS  not-accessible
--		STATUS  mandatory
--		DESCRIPTION  ""
--		INDEX { fsAnnexGPvcPortNo, fsAnnexGPvcIndex }
--		::= { fsAnnexGPvcTable 1 }

--	fsAnnexGPvcPortNo OBJECT-TYPE
--		SYNTAX  INTEGER {
--			port1		(1),
--			port2       (2),
--			port3       (3),
--			port4       (4),
--			port5       (5),
--			port6		(6),
--			port7       (7),
--			port8       (8),
--			port9       (9),
--			portA      	(10),
--			portB		(11),
--			portC      	(12),
--			portD      	(13),
--			portE      	(14),
--			portF      	(15),
--			portG		(16),
--			portH      	(17),
--			portI      	(18),
--			portJ      	(19)
--			}
--		ACCESS  read-write
--		STATUS  mandatory
--		DESCRIPTION  ""
--		::= { fsAnnexGPvcEntry 1 }

--	fsAnnexGPvcIndex OBJECT-TYPE
--		SYNTAX  INTEGER
--		ACCESS  read-only
--		STATUS  mandatory
--		DESCRIPTION  ""
--		::= { fsAnnexGPvcEntry 2 }

--	fsAnnexGPvcLcnIn OBJECT-TYPE
--		SYNTAX  INTEGER (1..255)
--		ACCESS  read-write
--		STATUS  mandatory
--		DESCRIPTION  
--			"The Local Logical Channel Number (LCN) 
--			is the PVC address on the physical X.25 line.  
--			Legal values are from 1 to 255 but no greater 
--			than the maximum LCN."
--		::= { fsAnnexGPvcEntry 3 }

--	fsAnnexGPvcLcnOut OBJECT-TYPE
--		SYNTAX  INTEGER (1..255)
--		ACCESS  read-write
--		STATUS  mandatory
--		DESCRIPTION  
--			"The Remote LCN is the PVC number in the Annex G 
--			encapsulated X.25 data stream. "
--		::= { fsAnnexGPvcEntry 4 }

--	fsAnnexGPvcFrPort OBJECT-TYPE
--		SYNTAX  INTEGER {
--			portNet (1),
--			port1   (2),
--			port2   (3),
--			port3   (4),
--			port4   (5)
--			}
--		ACCESS  read-write
--		STATUS  mandatory
--		DESCRIPTION  
--			"The Frame Relay Port is the physical port 
--			number to be used for Frame Relay by this PVC."
--		::= { fsAnnexGPvcEntry 5 }

--	fsAnnexGPvcDlci OBJECT-TYPE
--		SYNTAX  INTEGER (16..1007)
--		ACCESS  read-write
--		STATUS  mandatory
--		DESCRIPTION  
--			"The DLCI is the Frame Relay DLCI to be used by the PVC."
--		::= { fsAnnexGPvcEntry 6 }

--	fsAnnexGPvcPri OBJECT-TYPE
--		SYNTAX  INTEGER {
--			immediate   (0),
--			high        (1),
--			medium	(2),
--			low		(3)
--			}
--		ACCESS  read-write
--		STATUS  mandatory
--		DESCRIPTION  
--			"Set the priority for the PVC."
--		::= { fsAnnexGPvcEntry 7 }

--	fsAnnexGPvcStatus OBJECT-TYPE
--		SYNTAX  INTEGER {
--			view   (1),
--			add     (2),
--			delete  (3)
--			}
--		ACCESS  read-write
--		STATUS  mandatory
--		DESCRIPTION  ""
--		::= { fsAnnexGPvcEntry 8 }

--fsAnnexGX121Table OBJECT-TYPE
--	SYNTAX  SEQUENCE OF FsAnnexGX121Entry
--	ACCESS  not-accessible
--	STATUS  mandatory
--	DESCRIPTION  ""
--	::= { fsAnnexG 3 }

--	FsAnnexGX121Entry ::= SEQUENCE {
--		fsAnnexGX121PortNo		INTEGER,
--		fsAnnexGX121Index          	INTEGER,
--		fsAnnexGX121Address      	DisplayString,
--		fsAnnexGX121Status         	INTEGER
--		}

--	fsAnnexGX121Entry OBJECT-TYPE
--		SYNTAX  FsAnnexGX121Entry
--		ACCESS  not-accessible
--		STATUS  mandatory
--		DESCRIPTION  ""
--		INDEX { fsAnnexGX121PortNo, fsAnnexGX121Index }
--		::= { fsAnnexGX121Table 1 }

--	fsAnnexGX121PortNo OBJECT-TYPE
--		SYNTAX  INTEGER {
--			port1		(1),
--			port2       (2),
--			port3       (3),
--			port4       (4),
--			port5       (5),
--			port6		(6),
--			port7       (7),
--			port8       (8),
--			port9       (9),
--			portA      	(10),
--			portB		(11),
--			portC      	(12),
--			portD      	(13),
--			portE      	(14),
--			portF      	(15),
--			portG		(16),
--			portH      	(17),
--			portI      	(18),
--			portJ      	(19)
--			}
--		ACCESS  read-write
--		STATUS  mandatory
--		DESCRIPTION  ""
--		::= { fsAnnexGX121Entry 1 }

--	fsAnnexGX121Index OBJECT-TYPE
--		SYNTAX  INTEGER
--		ACCESS  read-only
--		STATUS  mandatory
--		DESCRIPTION  ""
--		::= { fsAnnexGX121Entry 2 }

--	fsAnnexGX121Address OBJECT-TYPE
--		SYNTAX  DisplayString (SIZE (1..8))
--		ACCESS  read-write
--		STATUS  mandatory
--		DESCRIPTION  
--			"The Annex G port requires the creation of a table 
--			listing all X.121 addresses that are accessible 
--			over the physical X.25 link.  This table is 				
--			used for routing X.25 data coming into the FRAD 
--			over Frame Relay. A maximum of 30 X.121 addresses 
--			and 30 PVCs can be configured on an Annex G port.  
--			X.121 addresses can be up to 15 digits in length 				
--			and are displayed left-zero filled. Two wildcards 
--			can be used in the addresses entry; a '?'and an '*' 
--			The '?' represents any single digit. There can be 
--			up to 15 '?' in an address.  The '*' represents any 
--			series of numbers and can be placed before or after 
--			a number in an address.  An address can consist of 
--			a single '*' which would match any X.121 address."
--		::= { fsAnnexGX121Entry 3 }

--	fsAnnexGX121Status OBJECT-TYPE
--		SYNTAX  INTEGER {
--			view   (1),
--			add     (2),
--			delete  (3)
--			}
--		ACCESS  read-write
--		STATUS  mandatory
--		DESCRIPTION  ""
--		::= { fsAnnexGX121Entry 4 }


-- ***************************************************************************
-- X25 parameters

--fsX25DefTable OBJECT-TYPE
--	SYNTAX  SEQUENCE OF FsX25DefEntry
--	ACCESS  not-accessible
--	STATUS  mandatory
--	DESCRIPTION  ""
--	::= { fsX25 1 }

--	FsX25DefEntry ::= SEQUENCE {
--		fsX25PortNo				INTEGER,
--		fsX25Speed				INTEGER,
--		fsX25Level2Address      	INTEGER,
--		fsX25FrameRetranTimer		INTEGER,
--		fsX25FrameAckTimer		INTEGER,
--		fsX25LinkDownTimer		INTEGER,
--		fsX25RetranRetry      		INTEGER,
--		fsX25FrameWindow			INTEGER,
--		fsX25PacketWindow			INTEGER,
--		fsX25PacketSize			INTEGER,
--		fsX25RestartTimer      		INTEGER,
--		fsX25CallReqTimer			INTEGER,
--		fsX25ResetReqTimer		INTEGER,
--		fsX25ClearReqTimer		INTEGER,
--		fsX25LogicalGroupNumber 	INTEGER,
--		fsX25MaximumPVC			INTEGER,
--		fsX25MinimumSVC			INTEGER,
--		fsX25MaximumSVC			INTEGER,
--		fsX25Status				INTEGER
--		}

--	fsX25DefEntry OBJECT-TYPE
--		SYNTAX  FsX25DefEntry
--		ACCESS  not-accessible
--		STATUS  mandatory
--		DESCRIPTION  ""
--		INDEX { fsX25PortNo }
--		::= { fsX25DefTable 1 }

--	fsX25PortNo OBJECT-TYPE
--		SYNTAX  INTEGER {
--			port1		(1),
--			port2       (2),
--			port3       (3),
--			port4       (4),
--			port5       (5),
--			port6		(6),
--			port7       (7),
--			port8       (8),
--			port9       (9),
--			portA      	(10),
--			portB		(11),
--			portC      	(12),
--			portD      	(13),
--			portE      	(14),
--			portF      	(15),
--			portG		(16),
--			portH      	(17),
--			portI      	(18),
--			portJ      	(19)
--			}
--		ACCESS  read-only
--		STATUS  mandatory
--		DESCRIPTION  ""
--		::= { fsX25DefEntry 1 }

--	fsX25Speed OBJECT-TYPE
--		SYNTAX  INTEGER {
--			external    (0),
--			baud002400  (1),
--			baud004800  (2),
--			baud009600  (3),
--			baud019200  (4),
--			baud038400  (5),
--			baud048000  (6),
--			baud056000  (7),
--			baud064000  (8),
--			baud096000  (9),
--			baud128000  (10),
--			baud192000  (11),
--			baud256000  (12),
--			baud384000  (13),
--			baud512000  (14),
--			baud768000  (15),
--			baud1024000 (16)
--			}
--		ACCESS  read-write
--		STATUS  mandatory
--		DESCRIPTION 
--			"The sync speed the FRAD will provide/accept clock to/from the
--		 	network"
--		::= { fsX25DefEntry 2 }

--	fsX25Level2Address OBJECT-TYPE
--		SYNTAX  INTEGER {
--			dte     (1),
--			dce     (2)
--			}
--		ACCESS  read-write
--		STATUS  mandatory
--		DESCRIPTION  
--			"Set the HDLC Address.  This specifies which side of 
--			the Level II protocol the port will support:  HDLC DCE 
--			Address (commands use address 3), or HDLC DTE Address 
--			(commands use address 1).  The equipment that is connected 
--			to the Annex G port on the FRAD (DCE or DTE) will be 
--			configured for the other side (DTE or DCE)."
--		::= { fsX25DefEntry 3 }

--	fsX25FrameRetranTimer OBJECT-TYPE
--		SYNTAX  INTEGER (1..100)
--		ACCESS  read-write
--		STATUS  mandatory
--		DESCRIPTION  
--			"Set the Retry Timer.  This is the receive timeout, 
--			in seconds, used by the Level II X.25 protocol."
--		::= { fsX25DefEntry 4 }

--	fsX25FrameAckTimer OBJECT-TYPE
--		SYNTAX  INTEGER (1..100)
--		ACCESS  read-write
--		STATUS  mandatory
--		DESCRIPTION  ""
--		::= { fsX25DefEntry 5 }

--	fsX25LinkDownTimer OBJECT-TYPE
--		SYNTAX  INTEGER (1..100)
--		ACCESS  read-write
--		STATUS  mandatory
--		DESCRIPTION  ""
--		::= { fsX25DefEntry 6 }

--	fsX25RetranRetry OBJECT-TYPE
--		SYNTAX  INTEGER (1..100)
--		ACCESS  read-write
--		STATUS  mandatory
--		DESCRIPTION  ""
--		::= { fsX25DefEntry 7 }

--	fsX25FrameWindow OBJECT-TYPE
--		SYNTAX  INTEGER (1..7)
--		ACCESS  read-write
--		STATUS  mandatory
--		DESCRIPTION  ""
--		::= { fsX25DefEntry 8 }

--	fsX25PacketWindow OBJECT-TYPE
--		SYNTAX  INTEGER (1..7)
--		ACCESS  read-write
--		STATUS  mandatory
--		DESCRIPTION  ""
--		::= { fsX25DefEntry 9 }

--	fsX25PacketSize OBJECT-TYPE
--		SYNTAX  INTEGER {
--			unknown     (0),
--			size16      (1),
--			size32      (2),
--			size64      (3),
--			size128     (4),
--			size256     (5),
--			size512     (6),
--			size1024    (7)                
--			}
--		ACCESS  read-write
--		STATUS  mandatory
--		DESCRIPTION  ""
--		::= { fsX25DefEntry 10 }

--	fsX25RestartTimer OBJECT-TYPE
--		SYNTAX  INTEGER (1..100)
--		ACCESS  read-write
--		STATUS  mandatory
--		DESCRIPTION  ""
--		::= { fsX25DefEntry 11 }

--	fsX25CallReqTimer OBJECT-TYPE
--		SYNTAX  INTEGER (1..100)
--		ACCESS  read-write
--		STATUS  mandatory
--		DESCRIPTION  ""
--		::= { fsX25DefEntry 12 }

--	fsX25ResetReqTimer OBJECT-TYPE
--		SYNTAX  INTEGER (1..100)
--		ACCESS  read-write
--		STATUS  mandatory
--		DESCRIPTION  ""
--		::= { fsX25DefEntry 13 }

--	fsX25ClearReqTimer OBJECT-TYPE
--		SYNTAX  INTEGER (1..100)
--		ACCESS  read-write
--		STATUS  mandatory
--		DESCRIPTION  ""
--		::= { fsX25DefEntry 14 }

--	fsX25LogicalGroupNumber OBJECT-TYPE
--		SYNTAX  INTEGER (0..15)
--		ACCESS  read-write
--		STATUS  mandatory
--		DESCRIPTION  ""
--		::= { fsX25DefEntry 15 }

--	fsX25MaximumPVC OBJECT-TYPE
--		SYNTAX  INTEGER (1..255)
--		ACCESS  read-write
--		STATUS  mandatory
--		DESCRIPTION  ""
--		::= { fsX25DefEntry 16 }

--	fsX25MinimumSVC OBJECT-TYPE
--		SYNTAX  INTEGER (1..255)
--		ACCESS  read-write
--		STATUS  mandatory
--		DESCRIPTION  ""
--		::= { fsX25DefEntry 17 }

--	fsX25MaximumSVC OBJECT-TYPE
--		SYNTAX  INTEGER (1..255)
--		ACCESS  read-write
--		STATUS  mandatory
--		DESCRIPTION  ""
--		::= { fsX25DefEntry 18 }

--	fsX25Status OBJECT-TYPE
--		SYNTAX  INTEGER {
--			view   (1),
--			modify  (2)
--			}
--		ACCESS  read-write
--		STATUS  mandatory
--		DESCRIPTION  ""
--		::= { fsX25DefEntry 19 }

--fsX25CircuitTable OBJECT-TYPE
--	SYNTAX  SEQUENCE OF FsX25CircuitEntry
--	ACCESS  not-accessible
--	STATUS  mandatory
--	DESCRIPTION  ""
--	::= { fsX25 2 }

--	FsX25CircuitEntry ::= SEQUENCE {
--		fsX25CircuitPortNo			INTEGER,
--		fsX25CircuitIndex          		INTEGER,
--		fsX25CircuitDlci      			INTEGER,
--		fsX25CircuitType         		INTEGER,
--		fsX25CircuitConnectMode        	INTEGER,
--		fsX25CircuitPVCLcn      		INTEGER,
--		fsX25CircuitSVCAddress     		DisplayString,
--		fsX25CircuitLocalAddress     		DisplayString,
--		fsX25CircuitStatus         		INTEGER
--		}

--	fsX25CircuitEntry OBJECT-TYPE
--		SYNTAX  FsX25CircuitEntry
--		ACCESS  not-accessible
--		STATUS  mandatory
--		DESCRIPTION  ""
--		INDEX { fsX25CircuitPortNo, fsX25CircuitIndex }
--		::= { fsX25CircuitTable 1 }

--	fsX25CircuitPortNo OBJECT-TYPE
--		SYNTAX  INTEGER {
--			port1		(1),
--			port2       (2),
--			port3       (3),
--			port4       (4),
--			port5       (5),
--			port6		(6),
--			port7       (7),
--			port8       (8),
--			port9       (9),
--			portA      	(10),
--			portB		(11),
--			portC      	(12),
--			portD      	(13),
--			portE      	(14),
--			portF      	(15),
--			portG		(16),
--			portH      	(17),
--			portI      	(18),
--			portJ      	(19)
--			}
--		ACCESS  read-write
--		STATUS  mandatory
--		DESCRIPTION  ""
--		::= { fsX25CircuitEntry 1 }

--	fsX25CircuitIndex OBJECT-TYPE
--		SYNTAX  INTEGER
--		ACCESS  read-only
--		STATUS  mandatory
--		DESCRIPTION  ""
--		::= { fsX25CircuitEntry 2 }

--	fsX25CircuitDlci OBJECT-TYPE
--		SYNTAX  INTEGER (16..1007)
--		ACCESS  read-write
--		STATUS  mandatory
--		DESCRIPTION  ""
--		::= { fsX25CircuitEntry 3 }

--	fsX25CircuitType OBJECT-TYPE
--		SYNTAX  INTEGER {
--			svc     (1),
--			pvc     (2)
--			}
--		ACCESS  read-write
--		STATUS  mandatory
--		DESCRIPTION  ""
--		::= { fsX25CircuitEntry 4 }

--	fsX25CircuitConnectMode OBJECT-TYPE
--		SYNTAX  INTEGER {
--			data    (1),
--			uto    (2)
--			}
--		ACCESS  read-write
--		STATUS  mandatory
--		DESCRIPTION  ""
--		::= { fsX25CircuitEntry 5 }

--	fsX25CircuitPVCLcn OBJECT-TYPE
--		SYNTAX  INTEGER (1..255)
--		ACCESS  read-write
--		STATUS  mandatory
--		DESCRIPTION  ""
--		::= { fsX25CircuitEntry 6 }

--	fsX25CircuitSVCAddress OBJECT-TYPE
--		SYNTAX  DisplayString (SIZE (1..16))
--		ACCESS  read-write
--		STATUS  mandatory
--		DESCRIPTION  ""
--		::= { fsX25CircuitEntry 7 }

--	fsX25CircuitLocalAddress OBJECT-TYPE
--		SYNTAX  DisplayString (SIZE (1..16))
--		ACCESS  read-write
--		STATUS  mandatory
--		DESCRIPTION  ""
--		::= { fsX25CircuitEntry 8 }

--	fsX25CircuitStatus OBJECT-TYPE
--		SYNTAX  INTEGER {
--			view   (1),
--			add     (2),
--			delete  (3)
--			}
--		ACCESS  read-write
--		STATUS  mandatory
--		DESCRIPTION  ""
--		::= { fsX25CircuitEntry 9 }


-- ***************************************************************************
-- Alc parameters

fsALCDefTable OBJECT-TYPE
	SYNTAX  SEQUENCE OF FsALCDefEntry
	ACCESS  not-accessible
	STATUS  mandatory
	DESCRIPTION  ""
	::= { fsALC 1 }

	FsALCDefEntry ::= SEQUENCE {
		fsALCPortNo			INTEGER,
		fsALCSpeed			INTEGER,
		fsALCPollTime		INTEGER,
		fsALCTimeOut		INTEGER,
		fsALCControllerIA		DisplayString,
		fsALCControllerIPAddr	IpAddress,
		fsALCRemoteHostIPAddr	IpAddress,
		fsALCESDIPAddr		IpAddress,
		fsALCStatus			INTEGER
		}

	fsALCDefEntry OBJECT-TYPE
		SYNTAX  FsALCDefEntry
		ACCESS  not-accessible
		STATUS  mandatory
		DESCRIPTION  ""
		INDEX { fsALCPortNo }
		::= { fsALCDefTable 1 }

	fsALCPortNo OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION  ""
		::= { fsALCDefEntry 1 }

	fsALCSpeed OBJECT-TYPE
		SYNTAX  INTEGER {
			baud001200  (1),
			baud002400  (2),
			baud004800  (3),
			baud009600  (4),
			baud019200  (5),
			baud038400  (6),
			baud048000  (7),
			baud057600  (8),
			baud115200  (9)
			}
		ACCESS  read-write
		STATUS  mandatory
		DESCRIPTION ""
		::= { fsALCDefEntry 2 }

	fsALCPollTime OBJECT-TYPE
		SYNTAX  INTEGER (0..5000)
		ACCESS  read-write
		STATUS  mandatory
		DESCRIPTION ""
		::= { fsALCDefEntry 3 }

	fsALCTimeOut OBJECT-TYPE
		SYNTAX  INTEGER (0..5000)
		ACCESS  read-write
		STATUS  mandatory
		DESCRIPTION ""
		::= { fsALCDefEntry 4 }

	fsALCControllerIA OBJECT-TYPE
		SYNTAX  DisplayString (SIZE (0..8))
		ACCESS  read-write
		STATUS  mandatory
		DESCRIPTION ""
		::= { fsALCDefEntry 5 }

	fsALCControllerIPAddr OBJECT-TYPE
		SYNTAX  IpAddress
		ACCESS  read-write
		STATUS  mandatory
		DESCRIPTION ""
		::= { fsALCDefEntry 6 }

	fsALCRemoteHostIPAddr OBJECT-TYPE
		SYNTAX  IpAddress
		ACCESS  read-write
		STATUS  mandatory
		DESCRIPTION ""
		::= { fsALCDefEntry 7 }

	fsALCESDIPAddr OBJECT-TYPE
		SYNTAX  IpAddress
		ACCESS  read-write
		STATUS  mandatory
		DESCRIPTION ""
		::= { fsALCDefEntry 8 }

	fsALCStatus OBJECT-TYPE
		SYNTAX  INTEGER {
			view   (1),
			modify (2)
			}
		ACCESS  read-write
		STATUS  mandatory
		DESCRIPTION  ""
		::= { fsALCDefEntry 9 }


-- ***************************************************************************
-- SDLC2 parameters

fsSDLC2DefTable OBJECT-TYPE
	SYNTAX  SEQUENCE OF FsSDLC2DefEntry
	ACCESS  not-accessible
	STATUS  mandatory
	DESCRIPTION  ""
	::= { fsSDLC2 1 }

	FsSDLC2DefEntry ::= SEQUENCE {
		fsSDLC2PortNo		INTEGER,
		fsSDLC2Speed		INTEGER,
            fsSDLC2PollType         INTEGER,
            fsSDLC2DataFmt		INTEGER,
            fsSDLC2IdleMark		INTEGER,
            fsSDLC2DCD              INTEGER,
		fsSDLC2UserBuffHigh	INTEGER,
		fsSDLC2UserBuffLow	INTEGER,
		fsSDLC2Status		INTEGER
		}

	fsSDLC2DefEntry OBJECT-TYPE
		SYNTAX  FsSDLC2DefEntry
		ACCESS  not-accessible
		STATUS  mandatory
		DESCRIPTION  ""
		INDEX { fsSDLC2PortNo }
		::= { fsSDLC2DefTable 1 }

	fsSDLC2PortNo OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION  ""
		::= { fsSDLC2DefEntry 1 }

	fsSDLC2Speed OBJECT-TYPE
		SYNTAX  INTEGER {
			external    (1),
	    		baud002400  (2),
	    		baud004800  (3),
	    		baud009600  (4),
	    		baud019200  (5),
	    		baud038400  (6),
	    		baud048000  (7),
	    		baud056000  (8),
	    		baud064000  (9),
	    		baud096000  (10),
	    		baud128000  (11),
	    		baud192000  (12),
	    		baud256000  (13),
	    		baud384000  (14),
	    		baud512000  (15),
	    		baud768000  (16),
	    		baud1024000 (17)
	    		}
		ACCESS  read-write
		STATUS  mandatory
		DESCRIPTION 
			"The sync speed the FRAD will provide/accept clock to/from the
			user's equipment"
		::= { fsSDLC2DefEntry 2 }

	fsSDLC2PollType OBJECT-TYPE
		SYNTAX  INTEGER {
			term-end    (1),
                  host-end    (2)
	      	}
		ACCESS  read-write
		STATUS  mandatory
		DESCRIPTION ""
		::= { fsSDLC2DefEntry 3 }

	fsSDLC2DataFmt OBJECT-TYPE
		SYNTAX  INTEGER {
			nrz   (1),
			nrzi  (2)
	      	}
		ACCESS  read-write
		STATUS  mandatory
		DESCRIPTION 
	   		"Data Format for the port."
		::= { fsSDLC2DefEntry 4 }

	fsSDLC2IdleMark OBJECT-TYPE
		SYNTAX  INTEGER {
			mark  (1),
			flag  (2)
	      	}
		ACCESS  read-write
		STATUS  mandatory
		DESCRIPTION 
	   		"Idle/Mark for the port."
		::= { fsSDLC2DefEntry 5 }

	fsSDLC2DCD OBJECT-TYPE
		SYNTAX  INTEGER {
			switched  (1),
			forced    (2)
	      	}
		ACCESS  read-write
		STATUS  mandatory
		DESCRIPTION ""
		::= { fsSDLC2DefEntry 6 }

	fsSDLC2UserBuffHigh OBJECT-TYPE
		SYNTAX  INTEGER (16..31)
		ACCESS  read-write
		STATUS  mandatory
		DESCRIPTION 
			"High-water mark for user buffers."
		::= { fsSDLC2DefEntry 7 }

	fsSDLC2UserBuffLow OBJECT-TYPE
		SYNTAX  INTEGER (10..15)
		ACCESS  read-write
		STATUS  mandatory
		DESCRIPTION 
			"High-water mark for user buffers."
		::= { fsSDLC2DefEntry 8 }

	fsSDLC2Status OBJECT-TYPE
		SYNTAX  INTEGER {
			view   (1),
			modify (2)
			}
		ACCESS  read-write
		STATUS  mandatory
		DESCRIPTION  ""
		::= { fsSDLC2DefEntry 9 }

fsSDLC2StnTable OBJECT-TYPE
	SYNTAX  SEQUENCE OF FsSDLC2StnEntry
	ACCESS  not-accessible
	STATUS  mandatory
	DESCRIPTION  ""
	::= { fsSDLC2 2 }

	FsSDLC2StnEntry ::= SEQUENCE {
		fsSDLC2StnPortNo			INTEGER,
		fsSDLC2StnIndex          	INTEGER,
		fsSDLC2StnAddr			DisplayString,
            fsSDLC2DuplexMode             INTEGER,
		fsSDLC2StnRWindow			INTEGER,
		fsSDLC2StnXWindow			INTEGER,
            fsSDLC2InactTimer             INTEGER,
            fsSDLC2AckTimer               INTEGER,
            fsSDLC2MaxRetries             INTEGER,
		fsSDLC2StnStatus         	INTEGER
		}

	fsSDLC2StnEntry OBJECT-TYPE
		SYNTAX  FsSDLC2StnEntry
		ACCESS  not-accessible
		STATUS  mandatory
		DESCRIPTION  ""
		INDEX { fsSDLC2StnPortNo, fsSDLC2StnIndex }
		::= { fsSDLC2StnTable 1 }

	fsSDLC2StnPortNo OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-write
		STATUS  mandatory
		DESCRIPTION  ""
		::= { fsSDLC2StnEntry 1 }

	fsSDLC2StnIndex OBJECT-TYPE
		SYNTAX  INTEGER
		ACCESS  read-only
		STATUS  mandatory
		DESCRIPTION  ""
		::= { fsSDLC2StnEntry 2 }

	fsSDLC2StnAddr OBJECT-TYPE
    		SYNTAX  DisplayString (SIZE(2))
    		ACCESS  read-write
    		STATUS  mandatory
    		DESCRIPTION
	   		"This value is the poll address of the
	    		secondary link station for this SDLC link.  It
	    		uniquely identifies the SDLC link station
	    		within a single SDLC port."
    		::= { fsSDLC2StnEntry  3 }

	fsSDLC2DuplexMode OBJECT-TYPE
    		SYNTAX  INTEGER {
		 	twa	(1),
		 	tws	(2)
	       	}
    		ACCESS  read-write
    		STATUS  mandatory
    		DESCRIPTION
	   		"This object controls the transmit-receive
	    		capabilities for this SDLC link station."
    		::= { fsSDLC2StnEntry  4 }

	fsSDLC2StnRWindow OBJECT-TYPE
    		SYNTAX  INTEGER (1..7)
    		ACCESS  read-write
    		STATUS  mandatory
    		DESCRIPTION
	   		"This object controls the maximum number of
	    		unacknowledged I-frames which an SDLC link
	    		station may receive.  This should range from 1
	    		to 7."
    		::= { fsSDLC2StnEntry  5 }

	fsSDLC2StnXWindow OBJECT-TYPE
    		SYNTAX  INTEGER (1..7)
    		ACCESS  read-write
    		STATUS  mandatory
    		DESCRIPTION
	   		"This object controls the maximum number of
	    		consecutive unacknowledged I-frames which an
	    		SDLC link station shall send without an
	    		acknowledgement.  This shall range from 1 to 7."
    		::= { fsSDLC2StnEntry  6 }

	fsSDLC2InactTimer OBJECT-TYPE
    		SYNTAX  INTEGER (1..60)
    		ACCESS  read-write
    		STATUS  mandatory
    		DESCRIPTION ""
    		::= { fsSDLC2StnEntry  7 }

	fsSDLC2AckTimer OBJECT-TYPE
    		SYNTAX  INTEGER (1..60)
    		ACCESS  read-write
    		STATUS  mandatory
    		DESCRIPTION ""
    		::= { fsSDLC2StnEntry  8 }

	fsSDLC2MaxRetries OBJECT-TYPE
    		SYNTAX  INTEGER (0..60)
    		ACCESS  read-write
    		STATUS  mandatory
    		DESCRIPTION ""
    		::= { fsSDLC2StnEntry  9 }

	fsSDLC2StnStatus OBJECT-TYPE
		SYNTAX  INTEGER {
			view   (1),
			add    (2),
			delete (3),
                  modify (4)
			}
		ACCESS  read-write
		STATUS  mandatory
		DESCRIPTION  ""
		::= { fsSDLC2StnEntry 10 }

-- ********************************************************************
-- X.25 New Parameters

fsX25NEWL1DefTable OBJECT-TYPE
	SYNTAX  SEQUENCE OF FsX25NEWL1DefEntry
	ACCESS  not-accessible
	STATUS  mandatory
	DESCRIPTION  ""
	::= { fsX25NEW 1 }

	FsX25NEWL1DefEntry ::= SEQUENCE {
		fsX25NEWL1PortNo		INTEGER,
		fsX25NEWL1Speed		INTEGER,
            fsX25NEWL1GptName       DisplayString,
		fsX25NEWL1Status		INTEGER
		}

	fsX25NEWL1DefEntry OBJECT-TYPE
		SYNTAX  FsX25NEWL1DefEntry
		ACCESS  not-accessible
		STATUS  mandatory
		DESCRIPTION  ""
		INDEX { fsX25NEWL1PortNo }
		::= { fsX25NEWL1DefTable 1 }

	fsX25NEWL1PortNo OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION  ""
		::= { fsX25NEWL1DefEntry 1 }

	fsX25NEWL1Speed OBJECT-TYPE
		SYNTAX  INTEGER {
			external    (0),
			baud002400  (1),
			baud004800  (2),
			baud009600  (3),
			baud019200  (4),
			baud038400  (5),
			baud048000  (6),
			baud056000  (7),
			baud064000  (8),
			baud096000  (9),
			baud128000  (10),
			baud192000  (11),
			baud256000  (12),
			baud384000  (13),
			baud512000  (14),
			baud768000  (15),
			baud1024000 (16)
			}
		ACCESS  read-write
		STATUS  mandatory
		DESCRIPTION 
			"The sync speed the FRAD will provide/accept clock to/from the
			user's equipment"
		::= { fsX25NEWL1DefEntry 2 }

	fsX25NEWL1GptName OBJECT-TYPE
		SYNTAX  DisplayString (SIZE (11))
		ACCESS  read-write
		STATUS  mandatory
		DESCRIPTION ""
		::= { fsX25NEWL1DefEntry 3 }

	fsX25NEWL1Status OBJECT-TYPE
		SYNTAX  INTEGER {
			view    (1),
			modify  (2)
			}
		ACCESS  read-write
		STATUS  mandatory
		DESCRIPTION  ""
		::= { fsX25NEWL1DefEntry 4 }

fsX25NEWL2DefTable OBJECT-TYPE
	SYNTAX  SEQUENCE OF FsX25NEWL2DefEntry
	ACCESS  not-accessible
	STATUS  mandatory
	DESCRIPTION  ""
	::= { fsX25NEW 2 }

	FsX25NEWL2DefEntry ::= SEQUENCE {
		fsX25NEWL2PortNo			INTEGER,
		fsX25NEWL2Mode			INTEGER,
            fsX25NEWL2LinkActivator		INTEGER,
            fsX25NEWL2T1AckTimer		INTEGER,
            fsX25NEWL2T2ResTimer		INTEGER,
            fsX25NEWL2T3DisconnectTimer	INTEGER,
            fsX25NEWL2N2RetryCount   	INTEGER,
		fsX25NEWL2Sequence		INTEGER,
            fsX25NEWL2RxKWindowSize		INTEGER,
		fsX25NEWL2TxKWindowSize		INTEGER,
		fsX25NEWL2Status			INTEGER
		}

	fsX25NEWL2DefEntry OBJECT-TYPE
		SYNTAX  FsX25NEWL2DefEntry
		ACCESS  not-accessible
		STATUS  mandatory
		DESCRIPTION  ""
		INDEX { fsX25NEWL2PortNo }
		::= { fsX25NEWL2DefTable 1 }

	fsX25NEWL2PortNo OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION  ""
		::= { fsX25NEWL2DefEntry 1 }

	fsX25NEWL2Mode OBJECT-TYPE
		SYNTAX  INTEGER {
                  dte (1),
                  dce (2)
                	}
		ACCESS  read-write
		STATUS  mandatory
		DESCRIPTION 
			"The LAPB Mode."
		::= { fsX25NEWL2DefEntry 2 }

	fsX25NEWL2LinkActivator OBJECT-TYPE
		SYNTAX  INTEGER {
                  dte (1),
                  dce (2)
                	}
		ACCESS  read-write
		STATUS  mandatory
		DESCRIPTION 
                	"This identifies which node, DTE or DCE, will activate the
                 	link."
		::= { fsX25NEWL2DefEntry 3 }

	fsX25NEWL2T1AckTimer OBJECT-TYPE
		SYNTAX  INTEGER (1..10)
		ACCESS  read-write
		STATUS  mandatory
		DESCRIPTION 
                	"The T1 timer for this interface. It specifies the
                 	maximum time to wait for acknowledgment of a PDU.
                	This timer is in seconds.          
                	The default value is 3."
		::= { fsX25NEWL2DefEntry 4 }

	fsX25NEWL2T2ResTimer OBJECT-TYPE
		SYNTAX  INTEGER (1..20)
		ACCESS  read-write
		STATUS  mandatory
		DESCRIPTION 
                	"The default T2 timer for this interface. This
                	specifies the maximum time to wait before sending an 
                	acknowledgment for a sequenced PDU. A value of zero 
                	means there will be no delay in acknowledgement 
                	generation.
                	This value is entered in seconds.               
                	The default value is 1."
		::= { fsX25NEWL2DefEntry 5 }

	fsX25NEWL2T3DisconnectTimer OBJECT-TYPE
		SYNTAX  INTEGER (10..180)
		ACCESS  read-write
		STATUS  mandatory
		DESCRIPTION 
                	"The T3 timer for this interface. This specifies the
                	time to wait before considering the link disconnected. 
                	A value of zero indicates the link will be considered 
                	disconnected upon completion of the frame exchange to 
                	disconnect the link.
                	This value is expressed in seconds.             
                	The default value is 60."
		::= { fsX25NEWL2DefEntry 6 }

	fsX25NEWL2N2RetryCount OBJECT-TYPE
		SYNTAX  INTEGER (1..30)
		ACCESS  read-write
		STATUS  mandatory
		DESCRIPTION 
                	"The default N2 retry counter for this interface. This
                	specifies the number of times a PDU will be resent
                	after the T1 timer expires without an acknowledgement
                	for the PDU.
                	The default value is 20.
                	The valid values range from 0 to 65535."
		::= { fsX25NEWL2DefEntry 7 }

	fsX25NEWL2Sequence OBJECT-TYPE
		SYNTAX  INTEGER {
                  module-8   (1),
                  module-128 (2)
                	}
		ACCESS  read-write
		STATUS  mandatory
		DESCRIPTION 
			"LAPB Sequencing."
		::= { fsX25NEWL2DefEntry 8 }

	fsX25NEWL2RxKWindowSize OBJECT-TYPE
		SYNTAX  INTEGER (1..127)
		ACCESS  read-write
		STATUS  mandatory
		DESCRIPTION 
                	"The default receive window size for this Interface.
                	This is the maximum number of unacknowledged sequenced
                	PDUs that may be outstanding from this DTE at any one
                	time.                      
                	The default value is 7.
                	The valid values range from 1 to 127."
		::= { fsX25NEWL2DefEntry 9 }

	fsX25NEWL2TxKWindowSize OBJECT-TYPE
		SYNTAX  INTEGER (1..127)
		ACCESS  read-write
		STATUS  mandatory
		DESCRIPTION 
                	"The default transmit window size for this Interface.
                	PDUs that may be outstanding from this DTE at any one
                	time.        
                	The default value is 7.
                	The valid values range from 1 to 127."
		::= { fsX25NEWL2DefEntry 10 }

	fsX25NEWL2Status OBJECT-TYPE
		SYNTAX  INTEGER {
			view   (1),
			modify (2)
			}
		ACCESS  read-write
		STATUS  mandatory
		DESCRIPTION  ""
		::= { fsX25NEWL2DefEntry 11 }

fsX25NEWL3DefTable OBJECT-TYPE
	SYNTAX  SEQUENCE OF FsX25NEWL3DefEntry
	ACCESS  not-accessible
	STATUS  mandatory
	DESCRIPTION  ""
	::= { fsX25NEW 3 }

	FsX25NEWL3DefEntry ::= SEQUENCE {
		fsX25NEWL3PortNo				INTEGER,
		fsX25NEWL3Mode				INTEGER,
		fsX25NEWL3TxPacketSize			INTEGER,
		fsX25NEWL3RxPacketSize			INTEGER,
		fsX25NEWL3Sequencing			INTEGER,
		fsX25NEWL3TxWindowSize			INTEGER,
		fsX25NEWL3RxWindowSize			INTEGER,
		fsX25NEWL3RestartTimer			INTEGER,
		fsX25NEWL3CallTimer			INTEGER,
		fsX25NEWL3ResetTimer			INTEGER,
		fsX25NEWL3ClearTimer			INTEGER,
		fsX25NEWL3InputCallFacOpt		INTEGER,
		fsX25NEWL3OutputCallFacOpt		INTEGER,
		fsX25NEWL3HPVC				INTEGER,
		fsX25NEWL3LSVC				INTEGER,
		fsX25NEWL3HSVC				INTEGER,
		fsX25NEWL3MaxActiveVC			INTEGER,
		fsX25NEWL3Status				INTEGER
		}

	fsX25NEWL3DefEntry OBJECT-TYPE
		SYNTAX  FsX25NEWL3DefEntry
		ACCESS  not-accessible
		STATUS  mandatory
		DESCRIPTION  ""
		INDEX { fsX25NEWL3PortNo }
		::= { fsX25NEWL3DefTable 1 }

	fsX25NEWL3PortNo OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION  ""
		::= { fsX25NEWL3DefEntry 1 }

	fsX25NEWL3Mode OBJECT-TYPE
		SYNTAX  INTEGER {
                  dte (1),
                  dce (2)
                	}
		ACCESS  read-write
		STATUS  mandatory
		DESCRIPTION 
                	"Identifies DCE/DTE mode in which the interface
                	operates."
		::= { fsX25NEWL3DefEntry 2 }

	fsX25NEWL3TxPacketSize OBJECT-TYPE
		SYNTAX  INTEGER (128..4096)
		ACCESS  read-write
		STATUS  mandatory
		DESCRIPTION 
                	"The transmit packet size in octets for a circuit. If
                	this parameter is changed and if there are any active
                	VCs, the port will be reinitialized (PVCs will be 
                	reset and SVCs will be cleared).                                 
                	The default value is 128."
		::= { fsX25NEWL3DefEntry 3 }

	fsX25NEWL3RxPacketSize OBJECT-TYPE
		SYNTAX  INTEGER (128..4096)
		ACCESS  read-write
		STATUS  mandatory
		DESCRIPTION 
                	"The receive packet size in octets for a circuit. If
                	this parameter is changed and if there are any active
                	VCs, the port will be reinitialized (PVCs will be 
                	reset and SVCs will be cleared).                                
                	The default value is 128."
		::= { fsX25NEWL3DefEntry 4 }

	fsX25NEWL3Sequencing OBJECT-TYPE
		SYNTAX  INTEGER {
                  module-8   (1),
                  module-128 (2)
                	}
		ACCESS  read-write
		STATUS  mandatory
		DESCRIPTION 
                	"The modulus of the packet sequence number space.                 
                	The default value is 'modulo8'."
		::= { fsX25NEWL3DefEntry 5 }

	fsX25NEWL3TxWindowSize OBJECT-TYPE
		SYNTAX  INTEGER (1..127)
		ACCESS  read-write
		STATUS  mandatory
		DESCRIPTION 
                	"The receive packet size in octets for a circuit. If
                	this parameter is changed and if there are any active
                	VCs, the port will be reinitialized (PVCs will be 
                	reset and SVCs will be cleared).                
                	The default value is 7.
                	The valid values range from 1 to 127."
		::= { fsX25NEWL3DefEntry 6 }

	fsX25NEWL3RxWindowSize OBJECT-TYPE
		SYNTAX  INTEGER (1..127)
		ACCESS  read-write
		STATUS  mandatory
		DESCRIPTION 
                	"The receive window size for a circuit. If this
                	parameter is changed and if there are any active VCs,
                	the particular port will be reinitialized (PVCs will be 
                	reset and SVCs will be cleared).              
                	The default value is 7.
                	The valid values range from 1 to 127."
		::= { fsX25NEWL3DefEntry 7 }

	fsX25NEWL3RestartTimer OBJECT-TYPE
		SYNTAX  INTEGER (10..600)
		ACCESS  read-write
		STATUS  mandatory
		DESCRIPTION 
                	"The T20 restart timer in seconds.               
                	The default value is 180.
                	The valid values range from 10 to 600."
		::= { fsX25NEWL3DefEntry 8 }

	fsX25NEWL3CallTimer OBJECT-TYPE
		SYNTAX  INTEGER (10..600)
		ACCESS  read-write
		STATUS  mandatory
		DESCRIPTION 
                	"The T21 Call timer in seconds.                
                	The default value is 200.
                	The valid values range from 10 to 600."
		::= { fsX25NEWL3DefEntry 9 }

	fsX25NEWL3ResetTimer OBJECT-TYPE
		SYNTAX  INTEGER (10..600)
		ACCESS  read-write
		STATUS  mandatory
		DESCRIPTION 
                	"The T22 Reset timer in seconds.                
                	The default value is 180.
                	The valid values range from 10 to 600."
		::= { fsX25NEWL3DefEntry 10 }

	fsX25NEWL3ClearTimer OBJECT-TYPE
		SYNTAX  INTEGER (10..600)
		ACCESS  read-write
		STATUS  mandatory
		DESCRIPTION 
                	"The T23 Clear timer in seconds.             
                	The default value is 180.
                	The valid values range from 10 to 600."
		::= { fsX25NEWL3DefEntry 11 }

	fsX25NEWL3InputCallFacOpt OBJECT-TYPE
		SYNTAX  INTEGER { 
                  pass-facilities-through	(1),
                  remove-facilities 	(2),
                  clear-call 			(3)
                 	}     
		ACCESS  read-write
		STATUS  mandatory
		DESCRIPTION 
                 	" This field controls the manner in which this port 
                   will respond when presented with any input Call 
                   Packet containing faciliities that are not actively
                   supported by the system.
                   Regardless of the value of this object, the
                   system will always clear calls containing
                   Flow Control Parameter Negotiation facilities
                   and will handle Reverse Charging facilities as
                   configured by the operator.
                   The value of this object will have no effect on 
                   system-generated call processing; any facility
                   present in calls received by multiprotocol switching
                   applications will always be ignored.
                   If this object is set to 'pass-facilities-through',
                   which is the default, unsupported facilities
                   will be passed unchanged through the system.
                   If this object is set to 'remove-facilities',
                   unsupported facilities will be stripped from
                   the packet before it is passed on through the 
                   system.
                   If this object is set to 'clear-call', calls
                   using unsupported facilities will be cleared
                   by the system  with the Invalid Facility Clear
                   Cause and Diagnostic Code combination."
		::= { fsX25NEWL3DefEntry 12 }

	fsX25NEWL3OutputCallFacOpt OBJECT-TYPE
		SYNTAX  INTEGER { 
                  pass-facilities-through (1),
                  remove-facilities 	(2),
                  clear-call 			(3)
                 	}     
		ACCESS  read-write
		STATUS  mandatory
		DESCRIPTION 
                 	" This field controls the manner in which this port 
                   will respond when presented with any output Call 
                   Packet containing faciliities that are not 
                   actively supported by the system.
                   Regardless of the value of this object, the
                   system will always clear calls containing
                   Flow Control Parameter Negotiation facilities
                   and will handle Reverse Charging facilities as
                   configured by the operator.
                   The value of this object will have no effect on 
                   system-generated call processing; any facility
                   present in calls received by multiprotocol switching
                   applications will always be ignored.
                   If this object is set to 'pass-facilities-through',
                   which is the default, unsupported facilities
                   will be passed unchanged through the system.
                   If this object is set to 'remove-facilities',
                   unsupported facilities will be stripped from
                   the packet before it is passed on through the 
                   system.
                   If this object is set to 'clear-call', calls
                   using unsupported facilities will be cleared
                   by the system  with the Invalid Facility Clear
                   Cause and Diagnostic Code combination."
		::= { fsX25NEWL3DefEntry 13 }

	fsX25NEWL3HPVC OBJECT-TYPE
		SYNTAX  INTEGER (0..4095)
		ACCESS  read-write
		STATUS  mandatory
		DESCRIPTION 
                	"Lowest Incoming channel.               
                	The default value is 0.
                	The valid values range from 0 to 4095."
		::= { fsX25NEWL3DefEntry 14 }

	fsX25NEWL3LSVC OBJECT-TYPE
		SYNTAX  INTEGER (0..4095)
		ACCESS  read-write
		STATUS  mandatory
		DESCRIPTION 
                	"Highest Incoming channel. A value of zero indicates no
                	channels in this range.                
                	The default value is 0.
                	The valid values range from 0 to 4095."
		::= { fsX25NEWL3DefEntry 15 }

	fsX25NEWL3HSVC OBJECT-TYPE
		SYNTAX  INTEGER (1..4095)
		ACCESS  read-write
		STATUS  mandatory
		DESCRIPTION 
                	"Lowest Two-way channel.              
                	The default value is 1.
                	The valid values range from 1 to 4095."
		::= { fsX25NEWL3DefEntry 16 }

	fsX25NEWL3MaxActiveVC OBJECT-TYPE
		SYNTAX  INTEGER (0..100)
		ACCESS  read-write
		STATUS  mandatory
		DESCRIPTION 
                	"Maximum Active VCs at a time.                
                	The default value is 20.
                	The valid values range from 0 to 100."
		::= { fsX25NEWL3DefEntry 17 }

	fsX25NEWL3Status OBJECT-TYPE
		SYNTAX  INTEGER {
			view    (1),
			modify  (2)
			}
		ACCESS  read-write
		STATUS  mandatory
		DESCRIPTION  ""
		::= { fsX25NEWL3DefEntry 18 }


-- ***************************************************************************
-- XPAD parameters

fsXPADDefTable OBJECT-TYPE
	SYNTAX  SEQUENCE OF FsXPADDefEntry
	ACCESS  not-accessible
	STATUS  mandatory
	DESCRIPTION  ""
	::= { fsXPAD 1 }

	FsXPADDefEntry ::= SEQUENCE {
		fsXPADPortNo			INTEGER,
		fsXPADX3Speed			INTEGER,
		fsXPADDataBits			INTEGER,
		fsXPADStopBits			INTEGER,
                fsXPADFlowControl               INTEGER,
                fsXPADFlowConType               INTEGER,
		fsXPADSubAddr			DisplayString,
		fsXPADAllowMnemonics		INTEGER,
		fsXPADIdleVCTmr			INTEGER,
            fsXPADX3ProfileSelect		INTEGER,
            fsXPADTelLogPort              INTEGER,
		fsXPADStatus			INTEGER
		}

	fsXPADDefEntry OBJECT-TYPE
		SYNTAX  FsXPADDefEntry
		ACCESS  not-accessible
		STATUS  mandatory
		DESCRIPTION  ""
		INDEX { fsXPADPortNo }
		::= { fsXPADDefTable 1 }

	fsXPADPortNo OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION  ""
		::= { fsXPADDefEntry 1 }

	fsXPADX3Speed OBJECT-TYPE
		SYNTAX  INTEGER {
			baud001200  (1),
			baud002400  (2),
			baud004800  (3),
			baud009600  (4),
			baud019200  (5),
			baud038400  (6),
			baud048000  (7),
			baud057600  (8),
			baud115200  (9)
	    		}
		ACCESS  read-write
		STATUS  mandatory
		DESCRIPTION 
                	"This object specifies the baudrate at which the PAD
                 	operates the link between the PAD and the TTY. Note that
                 	this object may only be read."
		::= { fsXPADDefEntry 2 }

	fsXPADDataBits OBJECT-TYPE
		SYNTAX  INTEGER {
                	seven-bits (7),
                  eight-bits (8)
                  }  
		ACCESS  read-write
		STATUS  mandatory
		DESCRIPTION ""
		::= { fsXPADDefEntry 3 }

	fsXPADStopBits OBJECT-TYPE
		SYNTAX  INTEGER {
               	one-bit  (1),
                  two-bits (2)
                  }
		ACCESS  read-write
		STATUS  mandatory
		DESCRIPTION ""
		::= { fsXPADDefEntry 4 }

	fsXPADFlowControl OBJECT-TYPE
		SYNTAX  INTEGER {
               	    off        (1),
                    tX-Only    (2),
                    rX-Only    (3),
                    on         (4)
                }
		ACCESS  read-write
		STATUS  mandatory
		DESCRIPTION ""
		::= { fsXPADDefEntry 5 }

	fsXPADFlowConType OBJECT-TYPE
		SYNTAX  INTEGER {
               	    rTS-CTS    (1),
                    xON-XOFF   (2)
                }
		ACCESS  read-write
		STATUS  mandatory
		DESCRIPTION ""
		::= { fsXPADDefEntry 6 }

	fsXPADSubAddr OBJECT-TYPE
		SYNTAX  DisplayString (SIZE (15))
		ACCESS  read-write
		STATUS  mandatory
		DESCRIPTION 
			"Sub Address ." 
		::= { fsXPADDefEntry 7 }

	fsXPADAllowMnemonics OBJECT-TYPE
		SYNTAX  INTEGER {
              	not-allowed  (1),
                  allowed     (2)
                  }
		ACCESS  read-write
		STATUS  mandatory
		DESCRIPTION 
                	"This boolean object specifies whether or not the use of
                 	Mnemonics is permissible at the PAD port."
		::= { fsXPADDefEntry 8 }

	fsXPADIdleVCTmr OBJECT-TYPE
		SYNTAX  INTEGER (0..600)
		ACCESS  read-write
		STATUS  mandatory
		DESCRIPTION 
               "This object specifies the maximum duration in minutes for which 
                an SVC on the PAD port may be allowed to remain idle. A value
                of zero indicates the VC may be allowed to remain idle forever.
                This timer is in seconds.              
                The default value is 180."
        	DEFVAL  { 180 }
		::= { fsXPADDefEntry 9 }

	fsXPADX3ProfileSelect OBJECT-TYPE
		SYNTAX  INTEGER {
                	simple          (1),
                  transparent     (2),
                  user-Configured (3)
                  }  
		ACCESS  read-write
		STATUS  mandatory
		DESCRIPTION 
                	"This is an index into the padX3ProfileTable the entries
                 	within which are to be the default X.3 paramaters for the
                 	PAD port."
		::= { fsXPADDefEntry 10 }

	fsXPADTelLogPort OBJECT-TYPE
		SYNTAX  INTEGER {
                  n-a       (0),
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION  ""
		::= { fsXPADDefEntry 11 }

	fsXPADStatus OBJECT-TYPE
		SYNTAX  INTEGER {
			view    (1),
			modify  (2)
			}
		ACCESS  read-write
		STATUS  mandatory
		DESCRIPTION  ""
		::= { fsXPADDefEntry 12 }

fsXPADProfile1DefTable OBJECT-TYPE
	SYNTAX  SEQUENCE OF FsXPADProfile1Entry
	ACCESS  not-accessible
	STATUS  mandatory
	DESCRIPTION  ""
	::= { fsXPAD 2 }

	FsXPADProfile1Entry ::= SEQUENCE {
		fsXPADPro1PortNo			INTEGER,
		fsXPADX3RecallChar		INTEGER,
            fsXPADX3EchoEnable		INTEGER,
            fsXPADX3DataFwdChar		INTEGER,
            fsXPADX3IdleTmr			INTEGER,
		fsXPADX3ANCDevCtrl		INTEGER,
		fsXPADX3PSSCtrl			INTEGER,
		fsXPADX3ActOnBreak		INTEGER,
		fsXPADX3DiscardOutput		INTEGER,
		fsXPADX3CRPadding			INTEGER,
		fsXPADX3LineFolding		INTEGER,
		fsXPADPro1Status			INTEGER
		}

	fsXPADProfile1Entry OBJECT-TYPE
		SYNTAX  FsXPADProfile1Entry
		ACCESS  not-accessible
		STATUS  mandatory
		DESCRIPTION  ""
		INDEX { fsXPADPro1PortNo }
		::= { fsXPADProfile1DefTable 1 }

	fsXPADPro1PortNo OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION  ""
		::= { fsXPADProfile1Entry 1 }

	fsXPADX3RecallChar OBJECT-TYPE
		SYNTAX  INTEGER (0..126)
		ACCESS  read-write
		STATUS  mandatory
		DESCRIPTION 
               	"This object specifies the value of the PAD Recall character
                	which allows the TTY to initiate an escape from the 'data
                	transfer' state or the 'connection in progress' state to 
                	send 'PAD Command signals'. This object may take one of
                	the following values:            
                   - 0             Not possible
                   - 1             Character DLE
                   - 32 to 126     The graphic character corresponding
                                   to the value. "
		::= { fsXPADProfile1Entry 2 }

	fsXPADX3EchoEnable OBJECT-TYPE
		SYNTAX  INTEGER {
               	no  (1),
                  yes (2)
                  }
		ACCESS  read-write
		STATUS  mandatory
		DESCRIPTION 
                	"This object specifies whether the character received from
                 	the TTY is transmitted back (apart from being interpreted
                 	by the PAD)."
		::= { fsXPADProfile1Entry 3 }

	fsXPADX3DataFwdChar OBJECT-TYPE
		SYNTAX  INTEGER {
             	no                     (0),
                  all-AlphaNumeric-Chars (1),
                  cr                     (2),
                  all-Unprintable-Chars  (126),
                  all-Chars              (127)  
                  }
		ACCESS  read-write
		STATUS  mandatory
		DESCRIPTION 
             	"This object defines the sets of character(s) received from
              	the TTY that are to recognised by the PAD as an indication
              	to complete the assembly and forward a 'complete packet
              	sequence' as defined in <>."
		::= { fsXPADProfile1Entry 4 }

	fsXPADX3IdleTmr OBJECT-TYPE
		SYNTAX  INTEGER (0..255)
		ACCESS  read-write
		STATUS  mandatory
		DESCRIPTION 
                	"This object defines the duration of an interval between 
                 	successive characters received from the TTY, which, when
                 	exceeded, will cause the PAD to terminate the assembly of
                 	a packet and forward the same.
                 	This timer is in 20th of a second.               
                 	The default value is 0."
        	DEFVAL  { 0 }
		::= { fsXPADProfile1Entry 5 }

	fsXPADX3ANCDevCtrl OBJECT-TYPE
		SYNTAX  INTEGER {
              	  no     (1),
                  dxfer  (2),
                  always (3)
                  }
		ACCESS  read-write
		STATUS  mandatory
		DESCRIPTION 
                	"This object allows for flow control between the PAD and the
                 	TTY. If this is set to 'dxfer', flow control is enabled
                 	only in the 'data transfer' state. The other permissible
                 	values are self-explanatory."
		::= { fsXPADProfile1Entry 6 }

	fsXPADX3PSSCtrl OBJECT-TYPE
		SYNTAX  INTEGER {
              	no                      (0),
                  ss-Other-than-PADPrompt (1),
                  all-SS                  (5)
                  } 
		ACCESS  read-write
		STATUS  mandatory
		DESCRIPTION 
                	"This object specifies whether or not and in what format
                 	PAD Service signals are transmitted."
		::= { fsXPADProfile1Entry 7 }

	fsXPADX3ActOnBreak OBJECT-TYPE
		SYNTAX  INTEGER {
             	no      (1),
                  rst     (2),
                  esc     (3)
                  }
		ACCESS  read-write
		STATUS  mandatory
		DESCRIPTION 
                	"This object determines the action to be initiated by the
                 	PAD upon receipt of a break signal from the TTY."
		::= { fsXPADProfile1Entry 8 }

	fsXPADX3DiscardOutput OBJECT-TYPE
		SYNTAX  INTEGER {
              	no  (1),
                  yes (2)
                  }
		ACCESS  read-write
		STATUS  mandatory
		DESCRIPTION 
                	"This object provides for the PAD to discard the content of
                 	user sequences in packets upon request rather than 
                 	disassembling and transmitting these to the TTY."
		::= { fsXPADProfile1Entry 9 }

	fsXPADX3CRPadding OBJECT-TYPE
		SYNTAX  INTEGER (0..255)
		ACCESS  read-write
		STATUS  mandatory
		DESCRIPTION 
                	"This object provides for the automatic insertion by the PAD
                 	of padding characters in the character stream transmitted
                 	to the TTY after the occurence of a 'carriage return`."
        	DEFVAL  { 0 }
		::= { fsXPADProfile1Entry 10 }

	fsXPADX3LineFolding OBJECT-TYPE
		SYNTAX  INTEGER (0..255)
		ACCESS  read-write
		STATUS  mandatory
		DESCRIPTION 
               	"This object provides for the automatic insertion by the PAD
                	of appropriate format effectors in the character stream
                	transmitted to the TTY. In other words, this object
                	specifies the maxmimum number of graphic characters that
                	may be present in a line."
        	DEFVAL  { 0 }
		::= { fsXPADProfile1Entry 11 }

	fsXPADPro1Status OBJECT-TYPE
		SYNTAX  INTEGER {
			view    (1),
			modify  (2)
			}
		ACCESS  read-write
		STATUS  mandatory
		DESCRIPTION  ""
		::= { fsXPADProfile1Entry 12 }

fsXPADProfile2DefTable OBJECT-TYPE
	SYNTAX  SEQUENCE OF FsXPADProfile2Entry
	ACCESS  not-accessible
	STATUS  mandatory
	DESCRIPTION  ""
	::= { fsXPAD 3 }

	FsXPADProfile2Entry ::= SEQUENCE {
		fsXPADPro2PortNo			INTEGER,
		fsXPADX3FlowCtrl			INTEGER,
		fsXPADX3LFAfterCR			INTEGER,
		fsXPADX3LFPadding			INTEGER,
		fsXPADX3Editing 			INTEGER,
		fsXPADX3CharDelChar		INTEGER,
		fsXPADX3LineDelChar		INTEGER,
		fsXPADX3LineDisplayChar		INTEGER,
		fsXPADX3EditingPSS		INTEGER,
		fsXPADX3EchoMask			INTEGER,
		fsXPADX3Parity			INTEGER,
		fsXPADX3PageWait			INTEGER,
		fsXPADPro2Status			INTEGER
		}

	fsXPADProfile2Entry OBJECT-TYPE
		SYNTAX  FsXPADProfile2Entry
		ACCESS  not-accessible
		STATUS  mandatory
		DESCRIPTION  ""
		INDEX { fsXPADPro2PortNo }
		::= { fsXPADProfile2DefTable 1 }

	fsXPADPro2PortNo OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION  ""
		::= { fsXPADProfile2Entry 1 }

	fsXPADX3FlowCtrl OBJECT-TYPE
		SYNTAX  INTEGER {
               	no  (1),
                  yes (2)
                  }
		ACCESS  read-write
		STATUS  mandatory
		DESCRIPTION 
                	"This object determines whether or not flow control is
                 	enabled between the TTY and the PAD."
		::= { fsXPADProfile2Entry 2 }

	fsXPADX3LFAfterCR OBJECT-TYPE
		SYNTAX  INTEGER (0..7)
		ACCESS  read-write
		STATUS  mandatory
		DESCRIPTION 
                	"This object provides for the automatic insertion by the PAD
                 	of a linefeed (LF) character in the character stream to or
                 	from the TTY after the occurence of each carriage return
                 	(CR) character. This is applicable only in the 'data
                 	transfer' state."
		::= { fsXPADProfile2Entry 3 }

	fsXPADX3LFPadding OBJECT-TYPE
		SYNTAX  INTEGER (0..255)
		ACCESS  read-write
		STATUS  mandatory
		DESCRIPTION 
               	"This object provides for the automatic insertion by the PAD
                	of padding character(s) in the character stream transmitted
                	to the TTY after the occurence of an LF character. This is 
                	applicable only in the 'data transfer' state."
        	DEFVAL  { 0 }
		::= { fsXPADProfile2Entry 4 }

	fsXPADX3Editing OBJECT-TYPE
		SYNTAX  INTEGER {
               	no  (1),
                  yes (2)
                  }
		ACCESS  read-write
		STATUS  mandatory
		DESCRIPTION 
                	"This object specifies whether or not the character delete,
                 	line delete and the line display editing capabilities are
                 	enabled in the 'data transfer' state."
		::= { fsXPADProfile2Entry 5 }

	fsXPADX3CharDelChar OBJECT-TYPE
		SYNTAX  INTEGER (0..127)
		ACCESS  read-write
		STATUS  mandatory
		DESCRIPTION ""
		::= { fsXPADProfile2Entry 6 }

	fsXPADX3LineDelChar OBJECT-TYPE
		SYNTAX  INTEGER (0..127)
		ACCESS  read-write
		STATUS  mandatory
		DESCRIPTION ""
		::= { fsXPADProfile2Entry 7 }

	fsXPADX3LineDisplayChar OBJECT-TYPE
		SYNTAX  INTEGER (0..127)
		ACCESS  read-write
		STATUS  mandatory
		DESCRIPTION ""
		::= { fsXPADProfile2Entry 8 }

	fsXPADX3EditingPSS OBJECT-TYPE
		SYNTAX  INTEGER (0..126)
		ACCESS  read-write
		STATUS  mandatory
		DESCRIPTION ""
		::= { fsXPADProfile2Entry 9 }

	fsXPADX3EchoMask OBJECT-TYPE
		SYNTAX  INTEGER {
              	no-Echo-Mask                            (0),
                  no-Echo-of-CR                           (1),
                  no-Echo-of-LF                           (2),
                  no-Echo-of-VT-HT-FF                     (4),
                  no-Echo-of-BEL-BS                       (8),
                  no-Echo-of-ESC-ENQ                      (16),
                  no-Echo-of-ACK-NAK-STX-SOH-EOT-ETB-ETX  (32),
                  no-Echo-of-CharDel-LineDel-LineDispChar (64),
                  no-Echo-of-NonGraphicChars              (128)
                  }
		ACCESS  read-write
		STATUS  mandatory
		DESCRIPTION ""
		::= { fsXPADProfile2Entry 10 }

	fsXPADX3Parity OBJECT-TYPE
		SYNTAX  INTEGER {
              	noParityChecking-or-Generation  (0), 
                  parityChecking-and-Generation   (3)
                  }
		ACCESS  read-write
		STATUS  mandatory
		DESCRIPTION ""
		::= { fsXPADProfile2Entry 11 }

	fsXPADX3PageWait OBJECT-TYPE
		SYNTAX  INTEGER (0..255)
		ACCESS  read-write
		STATUS  mandatory
		DESCRIPTION ""
		::= { fsXPADProfile2Entry 12 }

	fsXPADPro2Status OBJECT-TYPE
		SYNTAX  INTEGER {
			view    (1),
			modify  (2)
			}
		ACCESS  read-write
		STATUS  mandatory
		DESCRIPTION  ""
		::= { fsXPADProfile2Entry 13 }


-- ***************************************************************************
-- New PPP parameters

fsPPPNewDefTable OBJECT-TYPE
	SYNTAX  SEQUENCE OF FsPPPNewDefEntry
	ACCESS  not-accessible
	STATUS  mandatory
	DESCRIPTION  ""
	::= { fsPPPNew 1 }

	FsPPPNewDefEntry ::= SEQUENCE {
		fsPPPNewPortNo			INTEGER,
		fsPPPNewType			INTEGER,
		fsPPPNewSpeed			INTEGER,
		fsPPPNewLQM			      INTEGER,
		fsPPPNewLQMPert			INTEGER,
            fsPPPNewLQMTimer              INTEGER,
		fsPPPNewIPXNetNumber        	DisplayString,
		fsPPPNewNodeNumber 		DisplayString,
            fsPPPNewSapMode               INTEGER,
		fsPPPNewLCPMRU			INTEGER,
            fsPPPNewAddrNegoSel           INTEGER,
            fsPPPNewAddrNego              IpAddress,
            fsPPPNewLocalUserName         DisplayString,
            fsPPPNewLocalPasswd           DisplayString,
            fsPPPNewAuthProtocol          INTEGER,
		fsPPPNewStatus			INTEGER
		}

	fsPPPNewDefEntry OBJECT-TYPE
		SYNTAX  FsPPPNewDefEntry
		ACCESS  not-accessible
		STATUS  mandatory
		DESCRIPTION  ""
		INDEX { fsPPPNewPortNo }
		::= { fsPPPNewDefTable 1 }

	fsPPPNewPortNo OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION  ""
		::= { fsPPPNewDefEntry 1 }

	fsPPPNewType OBJECT-TYPE
		SYNTAX  INTEGER {
			sYNC   (40),
			aSYNC  (41)
			}
		ACCESS  read-write
		STATUS  mandatory
		DESCRIPTION ""
		::= { fsPPPNewDefEntry 2 }

	fsPPPNewSpeed OBJECT-TYPE
		SYNTAX  INTEGER {
			baud001200  (1),
	    		baud002400  (2),
	    		baud004800  (3),
	    		baud009600  (4),
	    		baud019200  (5),
	    		baud038400  (6),
	    		baud048000  (7),
	    		baud056000  (8),
	    		baud064000  (9),
	    		baud096000  (10),
	    		baud128000  (11),
	    		baud192000  (12),
	    		baud256000  (13),
	    		baud384000  (14),
	    		baud512000  (15),
	    		baud768000  (16),
	    		baud1024000 (17),
			baud057600  (18),
	            baud115200  (19)
			}
		ACCESS  read-write
		STATUS  mandatory
		DESCRIPTION ""
		::= { fsPPPNewDefEntry 3 }

	fsPPPNewLQM OBJECT-TYPE
		SYNTAX  INTEGER {
			on   (1),
			off  (2)
			}
		ACCESS  read-write
		STATUS  mandatory
		DESCRIPTION ""
		::= { fsPPPNewDefEntry 4 }

	fsPPPNewLQMPert OBJECT-TYPE
		SYNTAX  INTEGER 
		ACCESS  read-write
		STATUS  mandatory
		DESCRIPTION ""
		::= { fsPPPNewDefEntry 5 }

	fsPPPNewLQMTimer OBJECT-TYPE
		SYNTAX  INTEGER (10..300)
		ACCESS  read-write
		STATUS  mandatory
		DESCRIPTION ""
		::= { fsPPPNewDefEntry 6 }

	fsPPPNewIPXNetNumber OBJECT-TYPE
		SYNTAX  DisplayString (SIZE (0..8))
		ACCESS  read-write
		STATUS  mandatory
		DESCRIPTION ""
		::= { fsPPPNewDefEntry 7 }

	fsPPPNewNodeNumber OBJECT-TYPE
		SYNTAX  DisplayString (SIZE (0..12))
		ACCESS  read-write
		STATUS  mandatory
		DESCRIPTION ""
		::= { fsPPPNewDefEntry 8 }

	fsPPPNewSapMode OBJECT-TYPE
        	SYNTAX  INTEGER {
			on	      (0),
			send	      (1),
			listen      (2),
			off		(3)
	      	} 
		ACCESS  read-write
		STATUS  mandatory
		DESCRIPTION  ""
		::= { fsPPPNewDefEntry 9 }

	fsPPPNewLCPMRU OBJECT-TYPE
		SYNTAX  INTEGER 
		ACCESS  read-write
		STATUS  mandatory
		DESCRIPTION ""
		::= { fsPPPNewDefEntry 10 }

	fsPPPNewAddrNegoSel OBJECT-TYPE
		SYNTAX  INTEGER {
		dynamically       (1),
                  negotiate         (2),
			do-Not-Negotiate  (3)
			}
		ACCESS  read-write
		STATUS  mandatory
		DESCRIPTION  ""
		::= { fsPPPNewDefEntry 11 }

	fsPPPNewAddrNego OBJECT-TYPE
		SYNTAX  IpAddress
		ACCESS  read-write
		STATUS  mandatory
		DESCRIPTION  ""
		::= { fsPPPNewDefEntry 12 }

	fsPPPNewLocalUserName OBJECT-TYPE
		SYNTAX  DisplayString 
		ACCESS  read-write
		STATUS  mandatory
		DESCRIPTION ""
		::= { fsPPPNewDefEntry 13 }

	fsPPPNewLocalPasswd OBJECT-TYPE
		SYNTAX  DisplayString 
		ACCESS  read-write
		STATUS  mandatory
		DESCRIPTION ""
		::= { fsPPPNewDefEntry 14 }

	fsPPPNewAuthProtocol OBJECT-TYPE
		SYNTAX  INTEGER {
			cHAP       (1),
			pAP        (2),
                  cHAP-PAP   (3),
                  pAP-CHAP   (4),
                  nONE       (5)
			}
		ACCESS  read-write
		STATUS  mandatory
		DESCRIPTION  ""
		::= { fsPPPNewDefEntry 15 }

	fsPPPNewStatus OBJECT-TYPE
		SYNTAX  INTEGER {
			view   (1),
			modify (2)
			}
		ACCESS  read-write
		STATUS  mandatory
		DESCRIPTION  ""
		::= { fsPPPNewDefEntry 16 }

fsPPPNewRemoteUserTable OBJECT-TYPE
	SYNTAX  SEQUENCE OF FsPPPNewRemoteUserEntry
	ACCESS  not-accessible
	STATUS  mandatory
	DESCRIPTION  ""
	::= { fsPPPNew 2 }

	FsPPPNewRemoteUserEntry ::= SEQUENCE {
		fsPPPRemotePortNo		INTEGER,
		fsPPPRemoteIndex        INTEGER,
            fsPPPRemoteName         DisplayString,
		fsPPPRemotePasswd       DisplayString,
		fsPPPRemoteStatus       INTEGER
		}

	fsPPPNewRemoteUserEntry OBJECT-TYPE
		SYNTAX  FsPPPNewRemoteUserEntry
		ACCESS  not-accessible
		STATUS  mandatory
		DESCRIPTION  ""
		INDEX { fsPPPRemotePortNo, fsPPPRemoteIndex }
		::= { fsPPPNewRemoteUserTable 1 }

	fsPPPRemotePortNo OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-write
		STATUS  mandatory
		DESCRIPTION  ""
		::= { fsPPPNewRemoteUserEntry 1 }

	fsPPPRemoteIndex OBJECT-TYPE
		SYNTAX  INTEGER
		ACCESS  read-write
		STATUS  mandatory
		DESCRIPTION  ""
		::= { fsPPPNewRemoteUserEntry 2 }

	fsPPPRemoteName OBJECT-TYPE
		SYNTAX  DisplayString
		ACCESS  read-write
		STATUS  mandatory
		DESCRIPTION  ""
		::= { fsPPPNewRemoteUserEntry 3 }

	fsPPPRemotePasswd OBJECT-TYPE
		SYNTAX  DisplayString
		ACCESS  read-write
		STATUS  mandatory
		DESCRIPTION ""  
		::= { fsPPPNewRemoteUserEntry 4 }

	fsPPPRemoteStatus OBJECT-TYPE
		SYNTAX  INTEGER {
			view   (1),
			add    (2),
			delete (3),
                  modify (4)
			}
		ACCESS  read-write
		STATUS  mandatory
		DESCRIPTION  ""
		::= { fsPPPNewRemoteUserEntry 5 }


-- ***************************************************************************
-- MultiLink PPP parameters

fsPPPMLinkDefTable OBJECT-TYPE
	SYNTAX  SEQUENCE OF FsPPPMLinkDefEntry
	ACCESS  not-accessible
	STATUS  mandatory
	DESCRIPTION  ""
	::= { fsPPPMLink 1 }

	FsPPPMLinkDefEntry ::= SEQUENCE {
		fsPPPMLinkPortNo			INTEGER,
		fsPPPMLinkIPXNetNumber        DisplayString,
		fsPPPMLinkNodeNumber 		DisplayString,
            fsPPPMLinkSapMode             INTEGER,
		fsPPPMLinkMRRU			INTEGER,
            fsPPPMLinkMPHeader            INTEGER,
            fsPPPMLinkAddrNegoSel         INTEGER,
            fsPPPMLinkAddrNego            IpAddress,
            fsPPPMLinkLocalUserName         DisplayString,
            fsPPPMLinkLocalPasswd           DisplayString,
            fsPPPMLinkAuthProtocol          INTEGER,
		fsPPPMLinkStatus			INTEGER
		}

	fsPPPMLinkDefEntry OBJECT-TYPE
		SYNTAX  FsPPPMLinkDefEntry
		ACCESS  not-accessible
		STATUS  mandatory
		DESCRIPTION  ""
		INDEX { fsPPPMLinkPortNo }
		::= { fsPPPMLinkDefTable 1 }

	fsPPPMLinkPortNo OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION  ""
		::= { fsPPPMLinkDefEntry 1 }

	fsPPPMLinkIPXNetNumber OBJECT-TYPE
		SYNTAX  DisplayString (SIZE (0..8))
		ACCESS  read-write
		STATUS  mandatory
		DESCRIPTION ""
		::= { fsPPPMLinkDefEntry 2 }

	fsPPPMLinkNodeNumber OBJECT-TYPE
		SYNTAX  DisplayString (SIZE (0..12))
		ACCESS  read-write
		STATUS  mandatory
		DESCRIPTION ""
		::= { fsPPPMLinkDefEntry 3 }

	fsPPPMLinkSapMode OBJECT-TYPE
        	SYNTAX  INTEGER {
			on	      (0),
			send	      (1),
			listen      (2),
			off		(3)
	      	} 
		ACCESS  read-write
		STATUS  mandatory
		DESCRIPTION  ""
		::= { fsPPPMLinkDefEntry 4 }

	fsPPPMLinkMRRU OBJECT-TYPE
		SYNTAX  INTEGER 
		ACCESS  read-write
		STATUS  mandatory
		DESCRIPTION ""
		::= { fsPPPMLinkDefEntry 5 }

	fsPPPMLinkMPHeader OBJECT-TYPE
        	SYNTAX  INTEGER {
			must	      (1),
			not-must	(2)
	      	} 
		ACCESS  read-write
		STATUS  mandatory
		DESCRIPTION  ""
		::= { fsPPPMLinkDefEntry 6 }
			
	fsPPPMLinkAddrNegoSel OBJECT-TYPE
		SYNTAX  INTEGER {
			dynamically       (1),
                        negotiate         (2),
			do-Not-Negotiate  (3)
			}
		ACCESS  read-write
		STATUS  mandatory
		DESCRIPTION  ""
		::= { fsPPPMLinkDefEntry 7 }

	fsPPPMLinkAddrNego OBJECT-TYPE
		SYNTAX  IpAddress
		ACCESS  read-write
		STATUS  mandatory
		DESCRIPTION  ""
		::= { fsPPPMLinkDefEntry 8 }

	fsPPPMLinkLocalUserName OBJECT-TYPE
		SYNTAX  DisplayString 
		ACCESS  read-write
		STATUS  mandatory
		DESCRIPTION ""
		::= { fsPPPMLinkDefEntry 9 }

	fsPPPMLinkLocalPasswd OBJECT-TYPE
		SYNTAX  DisplayString 
		ACCESS  read-write
		STATUS  mandatory
		DESCRIPTION ""
		::= { fsPPPMLinkDefEntry 10 }

	fsPPPMLinkAuthProtocol OBJECT-TYPE
		SYNTAX  INTEGER {
			cHAP       (1),
			pAP        (2),
                  cHAP-PAP   (3),
                  pAP-CHAP   (4),
                  nONE       (5)
			}
		ACCESS  read-write
		STATUS  mandatory
		DESCRIPTION  ""
		::= { fsPPPMLinkDefEntry 11 }

	fsPPPMLinkStatus OBJECT-TYPE
		SYNTAX  INTEGER {
			view   (1),
			modify (2)
			}
		ACCESS  read-write
		STATUS  mandatory
		DESCRIPTION  ""
		::= { fsPPPMLinkDefEntry 12 }

fsPPPMLinkMemberTable OBJECT-TYPE
	SYNTAX  SEQUENCE OF FsPPPMLinkMemberEntry
	ACCESS  not-accessible
	STATUS  mandatory
	DESCRIPTION  ""
	::= { fsPPPMLink 2 }

	FsPPPMLinkMemberEntry ::= SEQUENCE {
		fsPPPMemberPortNo		INTEGER,
		fsPPPMemberIndex        INTEGER,
            fsPPPMemberPort         INTEGER,
		fsPPPMemberStatus       INTEGER
		}

	fsPPPMLinkMemberEntry OBJECT-TYPE
		SYNTAX  FsPPPMLinkMemberEntry
		ACCESS  not-accessible
		STATUS  mandatory
		DESCRIPTION  ""
		INDEX { fsPPPMemberPortNo, fsPPPMemberIndex }
		::= { fsPPPMLinkMemberTable 1 }

	fsPPPMemberPortNo OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-write
		STATUS  mandatory
		DESCRIPTION  ""
		::= { fsPPPMLinkMemberEntry 1 }

	fsPPPMemberIndex OBJECT-TYPE
		SYNTAX  INTEGER
		ACCESS  read-write
		STATUS  mandatory
		DESCRIPTION  ""
		::= { fsPPPMLinkMemberEntry 2 }

	fsPPPMemberPort OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-write
		STATUS  mandatory
		DESCRIPTION  ""
		::= { fsPPPMLinkMemberEntry 3 }

	fsPPPMemberStatus OBJECT-TYPE
		SYNTAX  INTEGER {
			view   (1),
			add    (2),
			delete (3),
                  modify (4)
			}
		ACCESS  read-write
		STATUS  mandatory
		DESCRIPTION  ""
		::= { fsPPPMLinkMemberEntry 4 }

fsPPPMLinkRemoteUserTable OBJECT-TYPE
	SYNTAX  SEQUENCE OF FsPPPMLinkRemoteUserEntry
	ACCESS  not-accessible
	STATUS  mandatory
	DESCRIPTION  ""
	::= { fsPPPMLink 3 }

	FsPPPMLinkRemoteUserEntry ::= SEQUENCE {
		fsPPPMLRemotePortNo       INTEGER,
		fsPPPMLRemoteIndex        INTEGER,
            fsPPPMLRemoteName         DisplayString,
		fsPPPMLRemotePasswd       DisplayString,
		fsPPPMLRemoteStatus       INTEGER
		}

	fsPPPMLinkRemoteUserEntry OBJECT-TYPE
		SYNTAX  FsPPPMLinkRemoteUserEntry
		ACCESS  not-accessible
		STATUS  mandatory
		DESCRIPTION  ""
		INDEX { fsPPPMLRemotePortNo, fsPPPMLRemoteIndex }
		::= { fsPPPMLinkRemoteUserTable 1 }

	fsPPPMLRemotePortNo OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-write
		STATUS  mandatory
		DESCRIPTION  ""
		::= { fsPPPMLinkRemoteUserEntry 1 }

	fsPPPMLRemoteIndex OBJECT-TYPE
		SYNTAX  INTEGER
		ACCESS  read-write
		STATUS  mandatory
		DESCRIPTION  ""
		::= { fsPPPMLinkRemoteUserEntry 2 }

	fsPPPMLRemoteName OBJECT-TYPE
		SYNTAX  DisplayString
		ACCESS  read-write
		STATUS  mandatory
		DESCRIPTION  ""
		::= { fsPPPMLinkRemoteUserEntry 3 }

	fsPPPMLRemotePasswd OBJECT-TYPE
		SYNTAX  DisplayString
		ACCESS  read-write
		STATUS  mandatory
		DESCRIPTION ""  
		::= { fsPPPMLinkRemoteUserEntry 4 }

	fsPPPMLRemoteStatus OBJECT-TYPE
		SYNTAX  INTEGER {
			view   (1),
			add    (2),
			delete (3),
                  modify (4)
			}
		ACCESS  read-write
		STATUS  mandatory
		DESCRIPTION  ""
		::= { fsPPPMLinkRemoteUserEntry 5 }

-- ***************************************************************************
-- EtherNet parameters

fsPortEtherDefinition OBJECT IDENTIFIER ::= { fsEtherNet 1 }

fsPortEtherIPXEncaps OBJECT-TYPE
	SYNTAX  INTEGER {
		iEEE802-3     (1),
		iEEE802-2     (2),
		iEEE802-2SNAP (3),
		ether         (4)
		}
	ACCESS  read-write
	STATUS  mandatory
	DESCRIPTION  ""
	::= { fsPortEtherDefinition 1 }

fsPortEtherNetNumber OBJECT-TYPE
	SYNTAX  DisplayString (SIZE (0..8))
	ACCESS  read-write
	STATUS  mandatory
	DESCRIPTION  ""
	::= { fsPortEtherDefinition 2 }

fsPortEtherSmartARP OBJECT-TYPE
        SYNTAX  INTEGER {
		enabled	(1),
		disabled	(2)
	      } 
        ACCESS  read-write
        STATUS  mandatory
        DESCRIPTION  ""
        ::= { fsPortEtherDefinition 3 }

fsPortEtherSapMode OBJECT-TYPE
        SYNTAX  INTEGER {
		on	      (0),
		send	      (1),
		listen      (2),
		off		(3)
	      } 
        ACCESS  read-write
        STATUS  mandatory
        DESCRIPTION  ""
        ::= { fsPortEtherDefinition 4 }


-- ***************************************************************************
-- TokenRing parameters

fsPortTokenDefinition	OBJECT IDENTIFIER ::= { fsTokenRing 1 }

fsPortTokenSpeed OBJECT-TYPE
        SYNTAX  INTEGER {
		mpbs-4       (1),
		mpbs-16	 (2),
		unknown	 (3)
	      } 
        ACCESS  read-write
        STATUS  mandatory
        DESCRIPTION  ""
        ::= { fsPortTokenDefinition 1 }

fsPortTokenEarlyRelease OBJECT-TYPE
        SYNTAX  INTEGER {
		enabled	(1),
		disabled	(2)
	      } 
        ACCESS  read-write
        STATUS  mandatory
        DESCRIPTION  ""
        ::= { fsPortTokenDefinition 2 }

fsPortTokenIPXNetNum OBJECT-TYPE
	  SYNTAX  DisplayString (SIZE (0..8))
	  ACCESS  read-write
        STATUS  mandatory
        DESCRIPTION  ""
        ::= { fsPortTokenDefinition 3 }

fsPortTokenIPXEncapsu OBJECT-TYPE
        SYNTAX  INTEGER {
		iEEE802-2Encap		(1),
		iEEE802-2-SNAPEncap	(2),
		invalid			(3)
	      }
	  ACCESS  read-write
        STATUS  mandatory
        DESCRIPTION  ""
        ::= { fsPortTokenDefinition 4 }

fsPortTokenSmartARP OBJECT-TYPE
        SYNTAX  INTEGER {
		enabled	(1),
		disabled	(2)
	      } 
        ACCESS  read-write
        STATUS  mandatory
        DESCRIPTION  ""
        ::= { fsPortTokenDefinition 5 }

fsPortTokenSapMode OBJECT-TYPE
        SYNTAX  INTEGER {
		on	      (0),
		send	      (1),
		listen      (2),
		off		(3)
	      } 
        ACCESS  read-write
        STATUS  mandatory
        DESCRIPTION  ""
        ::= { fsPortTokenDefinition 6 }

-- ***************************************************************************
-- Port Interface parameters

fsInterDefTable OBJECT-TYPE
	SYNTAX  SEQUENCE OF FsInterDefEntry
	ACCESS  not-accessible
	STATUS  mandatory
	DESCRIPTION  ""
	::= { fsInterfaceDefinition 1 }

	FsInterDefEntry ::= SEQUENCE {
		fsInterfacePortNo			INTEGER,
		fsInterfaceType			INTEGER,
            fsInterfaceDesc               DisplayString
		}

	fsInterDefEntry OBJECT-TYPE
		SYNTAX  FsInterDefEntry
		ACCESS  not-accessible
		STATUS  mandatory
		DESCRIPTION  ""
		INDEX { fsInterfacePortNo }
		::= { fsInterDefTable 1 }

	fsInterfacePortNo OBJECT-TYPE
		SYNTAX  INTEGER {
                  sup-Voice   (1),
			portN		(2),
			port1       (3),
			port2       (4),
			port3       (5),
			port4       (6)
			}
		ACCESS  read-only
		STATUS  mandatory
		DESCRIPTION  ""
		::= { fsInterDefEntry 1 }

	fsInterfaceType OBJECT-TYPE
		SYNTAX  INTEGER {
                  sUP         (1),
			e1   		(2),
			t1   		(3),
                  vOICE		(4),
                  sERIAL      (5),
                  cSU-DSU     (6),
                  dT1E1        (7),
                  uNDEFINED   (200)
			}
		ACCESS  read-write
		STATUS  mandatory
		DESCRIPTION ""
		::= { fsInterDefEntry 2 }

	fsInterfaceDesc OBJECT-TYPE
		SYNTAX  DisplayString
		ACCESS  read-write
		STATUS  mandatory
		DESCRIPTION ""
		::= { fsInterDefEntry 3 }

-- ***************************************************************************
-- E1 port parameters

fsPortE1DefTable OBJECT-TYPE
	SYNTAX  SEQUENCE OF FsPortE1DefEntry
	ACCESS  not-accessible
	STATUS  mandatory
	DESCRIPTION  ""
	::= { fsInterfaceE1 1 }

	FsPortE1DefEntry ::= SEQUENCE {
		fsPortE1PortNo			INTEGER,
		fsPortE1DsuFrameFormat		INTEGER,
		fsPortE1DsuCRC          	INTEGER,
            fsPortE1LineBuildout          INTEGER,
		fsPortE1DsuClock			INTEGER,
            fsPortE1DsuTimeSlots		DisplayString,
            fsPortE1DsuDataType		INTEGER,
		fsPortE1DsuDisFrame		INTEGER,
		fsPortE1DsuAISTrans		INTEGER,
            fsPortE1DsuLineLoop           INTEGER,
            fsPortE1ChannelMode           INTEGER,
            fsPortE1Channel64KRate        DisplayString,
            fsPortE1Channel56KRate        DisplayString,
            fsPortE1Channel48KRate        DisplayString,
		fsPortE1ConfigStatus		INTEGER
		}

	fsPortE1DefEntry OBJECT-TYPE
		SYNTAX  FsPortE1DefEntry
		ACCESS  not-accessible
		STATUS  mandatory
		DESCRIPTION  ""
		INDEX { fsPortE1PortNo }
		::= { fsPortE1DefTable 1 }

	fsPortE1PortNo OBJECT-TYPE
		SYNTAX  INTEGER {
                  vOICE       (1),
			portN		(2),
			port1       (3),
			port2       (4),
			port3       (5),
			port4       (6)
			}
		ACCESS  read-only
		STATUS  mandatory
		DESCRIPTION  ""
		::= { fsPortE1DefEntry 1 }

	fsPortE1DsuFrameFormat OBJECT-TYPE
		SYNTAX  INTEGER {
			framed      (1),
			unframed    (2),
                  na          (222)
	      	} 
		ACCESS  read-write
		STATUS  mandatory
		DESCRIPTION  ""
		::= { fsPortE1DefEntry 2 }

	fsPortE1DsuCRC OBJECT-TYPE
		SYNTAX  INTEGER {
			enable      (1),
			disable     (2),
                  na          (222)
	      	} 
		ACCESS  read-write
		STATUS  mandatory
		DESCRIPTION  ""
		::= { fsPortE1DefEntry 3 }

	fsPortE1LineBuildout OBJECT-TYPE
		SYNTAX  INTEGER {
			ft0-110		(1),
			ft110-220         (2),
			ft220-330         (3),
     			ft330-440         (4),
    			ft440-550         (5),
			ft550-660         (6),
	  		g703-75           (7),
			g703-120          (8),
            	na                (222)
	      	} 
		ACCESS  read-write
		STATUS  mandatory
		DESCRIPTION  ""
		::= { fsPortE1DefEntry 4 }

	fsPortE1DsuClock OBJECT-TYPE
		SYNTAX  INTEGER {
			line        (1),
			internal    (2),
                  na          (222)
	      	} 
		ACCESS  read-write
		STATUS  mandatory
		DESCRIPTION  ""
		::= { fsPortE1DefEntry 5 }

	fsPortE1DsuTimeSlots OBJECT-TYPE
		SYNTAX  DisplayString (SIZE (24))
		ACCESS  read-write
		STATUS  mandatory
		DESCRIPTION  ""
		::= { fsPortE1DefEntry 6 }

	fsPortE1DsuDataType OBJECT-TYPE
		SYNTAX  INTEGER {
			normal      (1),
			invert      (2),
                  na          (222)
	      	} 
		ACCESS  read-write
		STATUS  mandatory
		DESCRIPTION  ""
		::= { fsPortE1DefEntry 7 }

	fsPortE1DsuDisFrame OBJECT-TYPE
		SYNTAX  INTEGER {
			enable      (1),
			disable     (2),
                  na          (222)
	      	} 
		ACCESS  read-write
		STATUS  mandatory
		DESCRIPTION  ""
		::= { fsPortE1DefEntry 8 }

	fsPortE1DsuAISTrans OBJECT-TYPE
		SYNTAX  INTEGER {
			enable      (1),
			disable     (2),
                  na          (222)
	      	} 
		ACCESS  read-write
		STATUS  mandatory
		DESCRIPTION  ""
		::= { fsPortE1DefEntry 9 }

	fsPortE1DsuLineLoop OBJECT-TYPE
		SYNTAX  INTEGER {
			activateLoopBack  (1),
			removeLoopBack    (2),
                  na                (222)
	      	} 
		ACCESS  read-write
		STATUS  mandatory
		DESCRIPTION  ""
		::= { fsPortE1DefEntry 10 }

	fsPortE1ChannelMode OBJECT-TYPE
		SYNTAX  INTEGER {
			channelized       (1),
                  unchannelized	(2),
			na                (222)
			}
		ACCESS  read-write
		STATUS  mandatory
		DESCRIPTION  ""
		::= { fsPortE1DefEntry 11 }

	fsPortE1Channel64KRate OBJECT-TYPE
		SYNTAX  DisplayString (SIZE (24))
		ACCESS  read-write
		STATUS  mandatory
		DESCRIPTION  ""
		::= { fsPortE1DefEntry 12 }

	fsPortE1Channel56KRate OBJECT-TYPE
		SYNTAX  DisplayString (SIZE (24))
		ACCESS  read-write
		STATUS  mandatory
		DESCRIPTION  ""
		::= { fsPortE1DefEntry 13 }

	fsPortE1Channel48KRate OBJECT-TYPE
		SYNTAX  DisplayString (SIZE (24))
		ACCESS  read-write
		STATUS  mandatory
		DESCRIPTION  ""
		::= { fsPortE1DefEntry 14 }

	fsPortE1ConfigStatus OBJECT-TYPE
		SYNTAX  INTEGER {
			view   (1),
			modify (2)
			}
		ACCESS  read-write
		STATUS  mandatory
		DESCRIPTION  ""
		::= { fsPortE1DefEntry 15 }

-- ***************************************************************************
-- T1 port parameters

fsPortT1DefTable OBJECT-TYPE
	SYNTAX  SEQUENCE OF FsPortT1DefEntry
	ACCESS  not-accessible
	STATUS  mandatory
	DESCRIPTION  ""
	::= { fsInterfaceT1 1 }

	FsPortT1DefEntry ::= SEQUENCE {
		fsPortT1PortNo				INTEGER,
		fsPortT1DsuFrameFormat			INTEGER,
		fsPortT1DsuLineCode          		INTEGER,
		fsPortT1DsuBitStuffing			INTEGER,
            fsPortT1DsuLineBuildOut			INTEGER,
		fsPortT1DsuGSTACKLineBuildOut		INTEGER,
		fsPortT1DsuClock				INTEGER,
		fsPortT1DsuLineLoopBack			INTEGER,
            fsPortT1DsuLocAnalog                INTEGER,
            fsPortT1DsuLocDigital               INTEGER,
            fsPortT1DsuRemAnalog                INTEGER,
            fsPortT1DsuRemDigital               INTEGER,
		fsPortT1DsuTimeSlotDataRate		INTEGER,
            fsPortT1DsuTimeSlots			DisplayString,
		fsPortT1DsuTimeSlotDataType		INTEGER,
		fsPortT1DsuYellowAlarm			INTEGER,
            fsPortT1ChannelMode                 INTEGER,
            fsPortT1Channel64KRate              DisplayString,
            fsPortT1Channel56KRate              DisplayString,
            fsPortT1Channel48KRate              DisplayString,
		fsPortT1ConfigStatus			INTEGER
		}

	fsPortT1DefEntry OBJECT-TYPE
		SYNTAX  FsPortT1DefEntry
		ACCESS  not-accessible
		STATUS  mandatory
		DESCRIPTION  ""
		INDEX { fsPortT1PortNo }
		::= { fsPortT1DefTable 1 }

	fsPortT1PortNo OBJECT-TYPE
		SYNTAX  INTEGER {
                  vOICE       (1),
			portN		(2),
			port1       (3),
			port2       (4),
			port3       (5),
			port4       (6)
			}
		ACCESS  read-only
		STATUS  mandatory
		DESCRIPTION  ""
		::= { fsPortT1DefEntry 1 }

	fsPortT1DsuFrameFormat OBJECT-TYPE
		SYNTAX  INTEGER {
			d4          (1),
			eSF         (2),
			unframed    (3),
                  na          (222)
	      	} 
		ACCESS  read-write
		STATUS  mandatory
		DESCRIPTION  ""
		::= { fsPortT1DefEntry 2 }

	fsPortT1DsuLineCode OBJECT-TYPE
		SYNTAX  INTEGER {
			aMI         (1),
			b8ZS        (2),
                  na          (222)
	      	} 
		ACCESS  read-write
		STATUS  mandatory
		DESCRIPTION  ""
		::= { fsPortT1DefEntry 3 }

	fsPortT1DsuBitStuffing OBJECT-TYPE
		SYNTAX  INTEGER {
			enable      (1),
			disable     (2),
                  na          (222)
	      	} 
		ACCESS  read-write
		STATUS  mandatory
		DESCRIPTION  ""
		::= { fsPortT1DefEntry 4 }

	fsPortT1DsuLineBuildOut OBJECT-TYPE
		SYNTAX  INTEGER {
			db-0              (1),
                  db-Seven-and-half            (2),
 			db-15             (3),
                  db-TwentyTwo-and-half           (4),
			ft-133		(5),
			ft-266            (6),
			ft-399            (7),
     			ft-533            (8),
    			ft-655            (9),
            	na                (222)
	      	} 
		ACCESS  read-write
		STATUS  mandatory
		DESCRIPTION  ""
		::= { fsPortT1DefEntry 5 }

	fsPortT1DsuGSTACKLineBuildOut OBJECT-TYPE
		SYNTAX  INTEGER {
			ft0-110		(1),
			ft110-220         (2),
			ft220-330         (3),
     			ft330-440         (4),
    			ft440-550         (5),
			ft550-660         (6),
	  		ft-greater-600            (7),
			square            (8),
            	na                (222)
	      	} 
		ACCESS  read-write
		STATUS  mandatory
		DESCRIPTION  ""
		::= { fsPortT1DefEntry 6 }

	fsPortT1DsuClock OBJECT-TYPE
		SYNTAX  INTEGER {
			line        (1),
			internal    (2),
                  na          (222)
	      	} 
		ACCESS  read-write
		STATUS  mandatory
		DESCRIPTION  ""
		::= { fsPortT1DefEntry 7 }

	fsPortT1DsuLineLoopBack OBJECT-TYPE
		SYNTAX  INTEGER {
			enable      (1),
			disable     (2),
                  na          (222)
	      	} 
		ACCESS  read-write
		STATUS  mandatory
		DESCRIPTION  ""
		::= { fsPortT1DefEntry 8 }

	fsPortT1DsuLocAnalog OBJECT-TYPE
		SYNTAX  INTEGER {
			up        	(1),
			down       	(2),
            	na          (222)
	      	} 
		ACCESS  read-write
		STATUS  mandatory
		DESCRIPTION  ""
		::= { fsPortT1DefEntry 9 }

	fsPortT1DsuLocDigital OBJECT-TYPE
		SYNTAX  INTEGER {
			up        	(1),
			down       	(2),
            	na          (222)
	      	} 
		ACCESS  read-write
		STATUS  mandatory
		DESCRIPTION  ""
		::= { fsPortT1DefEntry 10 }

	fsPortT1DsuRemAnalog OBJECT-TYPE
		SYNTAX  INTEGER {
			up        	(1),
			down       	(2),
            	na          (222)
	      	} 
		ACCESS  read-write
		STATUS  mandatory
		DESCRIPTION  ""
		::= { fsPortT1DefEntry 11 }

	fsPortT1DsuRemDigital OBJECT-TYPE
		SYNTAX  INTEGER {
			up        	(1),
			down       	(2),
            	na          (222)
	      	} 
		ACCESS  read-write
		STATUS  mandatory
		DESCRIPTION  ""
		::= { fsPortT1DefEntry 12 }

	fsPortT1DsuTimeSlotDataRate OBJECT-TYPE
		SYNTAX  INTEGER {
			k48         (1),
			k56         (2),
			k64         (3),
                  na          (222)
	      	} 
		ACCESS  read-write
		STATUS  mandatory
		DESCRIPTION  ""
		::= { fsPortT1DefEntry 13 }

	fsPortT1DsuTimeSlots OBJECT-TYPE
		SYNTAX  DisplayString (SIZE (24))
		ACCESS  read-write
		STATUS  mandatory
		DESCRIPTION  ""
		::= { fsPortT1DefEntry 14 }

	fsPortT1DsuTimeSlotDataType OBJECT-TYPE
		SYNTAX  INTEGER {
			normal      (1),
			invert      (2),
                  na          (222)
	      	} 
		ACCESS  read-write
		STATUS  mandatory
		DESCRIPTION  ""
		::= { fsPortT1DefEntry 15 }

	fsPortT1DsuYellowAlarm OBJECT-TYPE
		SYNTAX  INTEGER {
			enable      (1),
			disable     (2),
                  na          (222)
	      	} 
		ACCESS  read-write
		STATUS  mandatory
		DESCRIPTION  ""
		::= { fsPortT1DefEntry 16 }

	fsPortT1ChannelMode OBJECT-TYPE
		SYNTAX  INTEGER {
			channelized       (1),
                  unchannelized	(2),
			na                (222)
			}
		ACCESS  read-write
		STATUS  mandatory
		DESCRIPTION  ""
		::= { fsPortT1DefEntry 17 }

	fsPortT1Channel64KRate OBJECT-TYPE
		SYNTAX  DisplayString (SIZE (24))
		ACCESS  read-write
		STATUS  mandatory
		DESCRIPTION  ""
		::= { fsPortT1DefEntry 18 }

	fsPortT1Channel56KRate OBJECT-TYPE
		SYNTAX  DisplayString (SIZE (24))
		ACCESS  read-write
		STATUS  mandatory
		DESCRIPTION  ""
		::= { fsPortT1DefEntry 19 }

	fsPortT1Channel48KRate OBJECT-TYPE
		SYNTAX  DisplayString (SIZE (24))
		ACCESS  read-write
		STATUS  mandatory
		DESCRIPTION  ""
		::= { fsPortT1DefEntry 20 }

	fsPortT1ConfigStatus OBJECT-TYPE
		SYNTAX  INTEGER {
			view   (1),
			modify (2)
			}
		ACCESS  read-write
		STATUS  mandatory
		DESCRIPTION  ""
		::= { fsPortT1DefEntry 21 }

-- ***************************************************************************
-- Voice port parameters

fsPortVoiceE1LineBuildOut OBJECT-TYPE
	SYNTAX  INTEGER {
		ft0-110		(1),
		ft110-220         (2),
		ft220-330         (3),
     		ft330-440         (4),
    		ft440-550         (5),
		ft550-660         (6),
	  	g703-75           (7),
		g703-120          (8),
            na                (222)
	      } 
	ACCESS  read-write
	STATUS  mandatory
	DESCRIPTION  ""
	::= { fsInterfaceVoice 1 }

fsPortVoiceE1Clock OBJECT-TYPE
	SYNTAX  INTEGER {
		line        (1),
		internal    (2),
            na          (222)
	      } 
	ACCESS  read-write
	STATUS  mandatory
	DESCRIPTION  ""
	::= { fsInterfaceVoice 2 }

fsPortVoiceE1SeizeABCD OBJECT-TYPE
	SYNTAX  DisplayString
	ACCESS  read-write
	STATUS  mandatory
	DESCRIPTION  ""
	::= { fsInterfaceVoice 3 }

fsPortVoiceE1IdleABCD OBJECT-TYPE
	SYNTAX  DisplayString
	ACCESS  read-write
	STATUS  mandatory
	DESCRIPTION  ""
	::= { fsInterfaceVoice 4 }

fsPortVoiceT1FrameFormat OBJECT-TYPE
	SYNTAX  INTEGER {
		d4          (1),
		eSF         (2),
		unframed    (3),
            na          (222)
	  	} 
	ACCESS  read-write
	STATUS  mandatory
	DESCRIPTION  ""
	::= { fsInterfaceVoice 5 }

fsPortVoiceT1LineCode OBJECT-TYPE
	SYNTAX  INTEGER {
		aMI         (1),
		b8ZS        (2),
            na          (222)
	      } 
	ACCESS  read-write
	STATUS  mandatory
	DESCRIPTION  ""
	::= { fsInterfaceVoice 6 }

fsPortVoiceT1LineBuildOut OBJECT-TYPE
	SYNTAX  INTEGER {
		ft0-110		(1),
		ft110-220         (2),
		ft220-330         (3),
     		ft330-440         (4),
    		ft440-550         (5),
		ft550-660         (6),
	  	ft-greater-600            (7),
		square            (8),
            na                (222)
	      } 
	ACCESS  read-write
	STATUS  mandatory
	DESCRIPTION  ""
	::= { fsInterfaceVoice 7 }

fsPortVoiceT1Clock OBJECT-TYPE
	SYNTAX  INTEGER {
		line        (1),
		internal    (2),
            na          (222)
	      } 
	ACCESS  read-write
	STATUS  mandatory
	DESCRIPTION  ""
	::= { fsInterfaceVoice 8 }

fsPortVoiceT1SeizeABCD OBJECT-TYPE
	SYNTAX  DisplayString
	ACCESS  read-write
	STATUS  mandatory
	DESCRIPTION  ""
	::= { fsInterfaceVoice 9 }

fsPortVoiceT1IdleABCD OBJECT-TYPE
	SYNTAX  DisplayString
	ACCESS  read-write
	STATUS  mandatory
	DESCRIPTION  ""
	::= { fsInterfaceVoice 10 }

fsPortVoiceTeleSignal OBJECT-TYPE
	SYNTAX  INTEGER {
		switch-CAS		(1),
		switch-CCS	      (2),
            trans-CAS         (3),
            trans-CCS         (4),
            na                (222)
	      } 
	ACCESS  read-write
	STATUS  mandatory
	DESCRIPTION  ""
	::= { fsInterfaceVoice 11 }

fsPortVoiceEMType OBJECT-TYPE
	SYNTAX  INTEGER {
		type-1	(1),
		type-2	(2),
            type-5      (3),
            na          (222)
	      } 
	ACCESS  read-write
	STATUS  mandatory
	DESCRIPTION  ""
	::= { fsInterfaceVoice 12 }

fsPortVoiceEMWire OBJECT-TYPE
	SYNTAX  INTEGER {
		invalid	(1),
		two-wire	(2),
            four-wire   (3),
            na          (222)
	      } 
 	ACCESS  read-write
	STATUS  mandatory
	DESCRIPTION  ""
	::= { fsInterfaceVoice 13 }

-- ***************************************************************************
-- Serial port parameters

fsPortSerialDefTable OBJECT-TYPE
	SYNTAX  SEQUENCE OF FsPortSerialDefEntry
	ACCESS  not-accessible
	STATUS  mandatory
	DESCRIPTION  ""
	::= { fsInterfaceSerial 1 }

	FsPortSerialDefEntry ::= SEQUENCE {
		fsPortSerialPortNo		INTEGER,
		fsPortSerialDteDceMode		INTEGER,
		fsPortSerialConfigStatus	INTEGER
		}

	fsPortSerialDefEntry OBJECT-TYPE
		SYNTAX  FsPortSerialDefEntry
		ACCESS  not-accessible
		STATUS  mandatory
		DESCRIPTION  ""
		INDEX { fsPortSerialPortNo }
		::= { fsPortSerialDefTable 1 }

	fsPortSerialPortNo OBJECT-TYPE
		SYNTAX  INTEGER {
                  vOICE       (1),
			portN		(2),
			port1       (3),
			port2       (4),
			port3       (5),
			port4       (6)
			}
		ACCESS  read-only
		STATUS  mandatory
		DESCRIPTION  ""
		::= { fsPortSerialDefEntry 1 }

	fsPortSerialDteDceMode OBJECT-TYPE
		SYNTAX  INTEGER {
			dTE      (1),
			dCE      (2),
                  na       (222)
	      	} 
		ACCESS  read-write
		STATUS  mandatory
		DESCRIPTION  ""
		::= { fsPortSerialDefEntry 2 }

	fsPortSerialConfigStatus OBJECT-TYPE
		SYNTAX  INTEGER {
			view   (1),
			modify (2)
			}
		ACCESS  read-write
		STATUS  mandatory
		DESCRIPTION  ""
		::= { fsPortSerialDefEntry 3 }

-- ***************************************************************************
-- SDSL port parameters

fsPortSDSLTerminalType OBJECT-TYPE
	SYNTAX  INTEGER {
		central     (1),
		remote      (2),
            undefined   (3),
            na          (222)
	      } 
	ACCESS  read-write
	STATUS  mandatory
	DESCRIPTION  ""
	::= { fsInterfaceSDSL 1 }

fsPortSDSLDataRate OBJECT-TYPE
	SYNTAX  INTEGER {
		r144kbps   (1),
		r192kbps   (2),
		r256kbps   (3),
		r384kbps   (4),
		r512kbps   (5),
		r768kbps   (6),
		r784kbps   (7),
		r1168kbps  (8),
		r1536kbps  (9),
		r2048kbps  (10),
		r2320kbps  (11),
            undefined  (12),
            na         (222)
	      } 
	ACCESS  read-write
	STATUS  mandatory
	DESCRIPTION  ""
	::= { fsInterfaceSDSL 2 }

fsPortSDSLAnalogAGC OBJECT-TYPE
	SYNTAX  INTEGER {
		no-AGC      (1),
		level-2     (2),
            level-4     (3),
            level-6     (4),
            undefined   (5),
            na          (222)
	      } 
	ACCESS  read-write
	STATUS  mandatory
	DESCRIPTION  ""
	::= { fsInterfaceSDSL 3 }

fsPortSDSLSeqSource OBJECT-TYPE
	SYNTAX  INTEGER {
		external    (1),
		internal    (2),
            undefined   (3),
            na          (222)
	      } 
	ACCESS  read-write
	STATUS  mandatory
	DESCRIPTION  ""
	::= { fsInterfaceSDSL 4 }

fsPortSDSLTranScrambler OBJECT-TYPE
	SYNTAX  INTEGER {
		disable     (1),
		enable      (2),
            undefined   (3),
            na          (222)
	      } 
	ACCESS  read-write
	STATUS  mandatory
	DESCRIPTION  ""
	::= { fsInterfaceSDSL 5 }

fsPortSDSLRecDeScrambler OBJECT-TYPE
	SYNTAX  INTEGER {
		disable     (1),
		enable      (2),
            undefined   (3),
            na          (222)
	      } 
	ACCESS  read-write
	STATUS  mandatory
	DESCRIPTION  ""
	::= { fsInterfaceSDSL 6 }

fsPortSDSLEchoCanceller OBJECT-TYPE
	SYNTAX  INTEGER {
		off         (1),
		on         	(2),
            undefined   (3),
            na          (222)
	      } 
	ACCESS  read-write
	STATUS  mandatory
	DESCRIPTION  ""
	::= { fsInterfaceSDSL 7 }

fsPortSDSLRemoteBitpump OBJECT-TYPE
	SYNTAX  INTEGER {
		conexent         (1),
            non-Conexent     (2),
            undefined        (3),
            na      	     (222)
	      } 
	ACCESS  read-write
	STATUS  mandatory
	DESCRIPTION  ""
	::= { fsInterfaceSDSL 8 }

fsPortSDSLTestModes OBJECT-TYPE
	SYNTAX  INTEGER {
		external-Analog-Loopback	(1),
		digital-Near-End-Loopback     (2),
		digital-Far-End-Loopback      (3),    
		tx-Isolated-plus-3-Level-Pulse     (4),
		tx-Isolated-plus-1-Level-Pulse     (5),
		tx-Isolated-1-Level-Pulse     (6),
		tx-Isolated-3-Level-Pulse     (7),
		tx-4-Level-Scrambled-Data     (8),
		tx-2-Level-Scrambled-Data     (9),
		set-Nominal-VCXO-Frequency    (10),
		set-Minimum-VCXO-Frequency    (11),
		set-Maximum-VCXO-Frequency    (12),
		internal-Analog-Loopback      (13),
		isolated-Analog-Loopback      (14),
		echo-Return-Loss-Enhancement  (15),
		analog-AGC-Test               (16),
		tx-Alternating-plus-3-3-Symbols    (17),
		tx-Alternating-plus-1-1-Symbols    (18),
		exit-Test-Mode                (19),
            disabled                      (20),
            undefined                     (22),
            na      	                  (222)
	      } 
	ACCESS  read-write
	STATUS  mandatory
	DESCRIPTION  ""
	::= { fsInterfaceSDSL 9 }

-- ***************************************************************************
-- DT1E1 port parameters

fsPortDT1E1ConfigTable OBJECT-TYPE
	SYNTAX  SEQUENCE OF FsPortDT1E1ConfigEntry
	ACCESS  not-accessible
	STATUS  mandatory
	DESCRIPTION  ""
	::= { fsInterfaceDT1E1 1 }

	FsPortDT1E1ConfigEntry ::= SEQUENCE {
	    fsPortDT1E1ConfigPortNo		INTEGER,
            fsPortDT1E1ConfigPort1LineBuildout  INTEGER,
            fsPortDT1E1ConfigPort2LineBuildout  INTEGER,
            fsPortDT1E1ConfigPort1Clock		INTEGER,
            fsPortDT1E1ConfigPort2Clock		INTEGER,
            fsPortDT1E1ConfigPort1TimeSlot      DisplayString,
            fsPortDT1E1ConfigPort2TimeSlot      DisplayString,
            fsPortDT1E1ConfigPortType		INTEGER,
            fsPortDT1E1ConfigChannelMode        INTEGER,
            fsPortDT1E1ConfigChannel64KRate     DisplayString,
            fsPortDT1E1ConfigChannel56KRate     DisplayString,
            fsPortDT1E1ConfigChannel48KRate     DisplayString,
            fsPortDT1E1ConfigTimingRef		INTEGER,
            fsPortDT1E1ConfigTDMClockRate	INTEGER,
	    fsPortDT1E1ConfigStatus		INTEGER,
	    fsPortDT1E1ConfigPort1IdleABCDBits	DisplayString,
	    fsPortDT1E1ConfigPort2IdleABCDBits	DisplayString,
	    fsPortDT1E1ConfigPort1SeizeABCDBits	DisplayString,
	    fsPortDT1E1ConfigPort2SeizeABCDBits	DisplayString
		}

	fsPortDT1E1ConfigEntry OBJECT-TYPE
		SYNTAX  FsPortDT1E1ConfigEntry
		ACCESS  not-accessible
		STATUS  mandatory
		DESCRIPTION  ""
		INDEX { fsPortDT1E1ConfigPortNo }
		::= { fsPortDT1E1ConfigTable 1 }

	fsPortDT1E1ConfigPortNo OBJECT-TYPE
		SYNTAX  INTEGER {
                  vOICE       (1),
			portN		(2),
			port1       (3),
			port2       (4),
			port3       (5),
			port4       (6)
			}
		ACCESS  read-only
		STATUS  mandatory
		DESCRIPTION  ""
		::= { fsPortDT1E1ConfigEntry 1 }

	fsPortDT1E1ConfigPort1LineBuildout OBJECT-TYPE
		SYNTAX  INTEGER {
			lH-0dot0-Db		(1),
			lH-7dot5-Db         (2),
			lH-15dot0-Db        (3),
     			lH-22dot5-Db        (4),
    			lH-0-110ft        (5),
			lH-110-220ft      (6),
	  		lH-220-330ft      (7),
                  lH-330-440ft      (8),
                  lH-440-550ft      (9),
                  lH-550-660ft      (10),
			g703-120          (11),
                  g703-75           (12),
            	na                (222)
	      	} 
		ACCESS  read-write
		STATUS  mandatory
		DESCRIPTION  ""
		::= { fsPortDT1E1ConfigEntry 2 }

	fsPortDT1E1ConfigPort2LineBuildout OBJECT-TYPE
		SYNTAX  INTEGER {
			lH-0dot0-Db		(1),
			lH-7dot5-Db         (2),
			lH-15dot0-Db        (3),
     			lH-22dot5-Db        (4),
    			lH-0-110ft        (5),
			lH-110-220ft      (6),
	  		lH-220-330ft      (7),
                  lH-330-440ft      (8),
                  lH-440-550ft      (9),
                  lH-550-660ft      (10),
			g703-120          (11),
                  g703-75           (12),
            	na                (222)
	      	} 
		ACCESS  read-write
		STATUS  mandatory
		DESCRIPTION  ""
		::= { fsPortDT1E1ConfigEntry 3 }

	fsPortDT1E1ConfigPort1Clock OBJECT-TYPE
		SYNTAX  INTEGER {
			line        (1),
			internal    (2),
                  na          (222)
	      	} 
		ACCESS  read-write
		STATUS  mandatory
		DESCRIPTION  ""
		::= { fsPortDT1E1ConfigEntry 4 }

	fsPortDT1E1ConfigPort2Clock OBJECT-TYPE
		SYNTAX  INTEGER {
			line        (1),
			internal    (2),
                  na          (222)
	      	} 
		ACCESS  read-write
		STATUS  mandatory
		DESCRIPTION  ""
		::= { fsPortDT1E1ConfigEntry 5 }

	fsPortDT1E1ConfigPort1TimeSlot OBJECT-TYPE
		SYNTAX  DisplayString (SIZE (24))
		ACCESS  read-write
		STATUS  mandatory
		DESCRIPTION  ""
		::= { fsPortDT1E1ConfigEntry 6 }

	fsPortDT1E1ConfigPort2TimeSlot OBJECT-TYPE
		SYNTAX  DisplayString (SIZE (24))
		ACCESS  read-write
		STATUS  mandatory
		DESCRIPTION  ""
		::= { fsPortDT1E1ConfigEntry 7 }

	fsPortDT1E1ConfigPortType OBJECT-TYPE
		SYNTAX  INTEGER {
			e1        (1),
			t1        (2),
                  na        (222)
	      	} 
		ACCESS  read-write
		STATUS  mandatory
		DESCRIPTION  ""
		::= { fsPortDT1E1ConfigEntry 8 }

	fsPortDT1E1ConfigChannelMode OBJECT-TYPE
		SYNTAX  INTEGER {
			channelized       (1),
                  unchannelized	(2),
			na                (222)
			}
		ACCESS  read-write
		STATUS  mandatory
		DESCRIPTION  ""
		::= { fsPortDT1E1ConfigEntry 9 }

	fsPortDT1E1ConfigChannel64KRate OBJECT-TYPE
		SYNTAX  DisplayString (SIZE (24))
		ACCESS  read-write
		STATUS  mandatory
		DESCRIPTION  ""
		::= { fsPortDT1E1ConfigEntry 10 }

	fsPortDT1E1ConfigChannel56KRate OBJECT-TYPE
		SYNTAX  DisplayString (SIZE (24))
		ACCESS  read-write
		STATUS  mandatory
		DESCRIPTION  ""
		::= { fsPortDT1E1ConfigEntry 11 }

	fsPortDT1E1ConfigChannel48KRate OBJECT-TYPE
		SYNTAX  DisplayString (SIZE (24))
		ACCESS  read-write
		STATUS  mandatory
		DESCRIPTION  ""
		::= { fsPortDT1E1ConfigEntry 12 }

	fsPortDT1E1ConfigTimingRef OBJECT-TYPE
		SYNTAX  INTEGER {
			port1        (1),
			port2        (2),
                  smm          (3),
                  na           (222)
	      	} 
		ACCESS  read-write
		STATUS  mandatory
		DESCRIPTION  ""
		::= { fsPortDT1E1ConfigEntry 13 }

	fsPortDT1E1ConfigTDMClockRate OBJECT-TYPE
		SYNTAX  INTEGER {
			mHZ4        (1),
			mHZ2        (2),
                  na          (222)
	      	} 
		ACCESS  read-write
		STATUS  mandatory
		DESCRIPTION  ""
		::= { fsPortDT1E1ConfigEntry 14 }

	fsPortDT1E1ConfigStatus OBJECT-TYPE
		SYNTAX  INTEGER {
			view   (1),
			modify (2)
			}
		ACCESS  read-write
		STATUS  mandatory
		DESCRIPTION  ""
		::= { fsPortDT1E1ConfigEntry 15 }

	fsPortDT1E1ConfigPort1IdleABCDBits OBJECT-TYPE
	        SYNTAX  DisplayString 
		ACCESS  read-write
		STATUS  mandatory
		DESCRIPTION  ""
		::= { fsPortDT1E1ConfigEntry 16 }

	fsPortDT1E1ConfigPort2IdleABCDBits OBJECT-TYPE
	        SYNTAX  DisplayString 
		ACCESS  read-write
		STATUS  mandatory
		DESCRIPTION  ""
		::= { fsPortDT1E1ConfigEntry 17 }

	fsPortDT1E1ConfigPort1SeizeABCDBits OBJECT-TYPE
	        SYNTAX  DisplayString 
		ACCESS  read-write
		STATUS  mandatory
		DESCRIPTION  ""
		::= { fsPortDT1E1ConfigEntry 18 }

	fsPortDT1E1ConfigPort2SeizeABCDBits OBJECT-TYPE
	        SYNTAX  DisplayString 
		ACCESS  read-write
		STATUS  mandatory
		DESCRIPTION  ""
		::= { fsPortDT1E1ConfigEntry 19 }

fsPortDT1E1CrossConnTable OBJECT-TYPE
	SYNTAX  SEQUENCE OF FsPortDT1E1CrossConnEntry
	ACCESS  not-accessible
	STATUS  mandatory
	DESCRIPTION  ""
	::= { fsInterfaceDT1E1 2 }

	FsPortDT1E1CrossConnEntry ::= SEQUENCE {
		fsPortDT1E1CrossConnPortNo		INTEGER,
            fsPortDT1E1CrossConnSys-Port1       DisplayString,
            fsPortDT1E1CrossConnSys-Port2       DisplayString,
            fsPortDT1E1CrossConnPort1-Sys       DisplayString,
            fsPortDT1E1CrossConnPort1-Port2     DisplayString,
            fsPortDT1E1CrossConnPort2-Sys       DisplayString,
            fsPortDT1E1CrossConnPort2-Port1     DisplayString,
		fsPortDT1E1CrossConnStatus		INTEGER
		}

	fsPortDT1E1CrossConnEntry OBJECT-TYPE
		SYNTAX  FsPortDT1E1CrossConnEntry
		ACCESS  not-accessible
		STATUS  mandatory
		DESCRIPTION  ""
		INDEX { fsPortDT1E1CrossConnPortNo }
		::= { fsPortDT1E1CrossConnTable 1 }

	fsPortDT1E1CrossConnPortNo OBJECT-TYPE
		SYNTAX  INTEGER {
                  vOICE       (1),
			portN		(2),
			port1       (3),
			port2       (4),
			port3       (5),
			port4       (6)
			}
		ACCESS  read-only
		STATUS  mandatory
		DESCRIPTION  ""
		::= { fsPortDT1E1CrossConnEntry 1 }

	fsPortDT1E1CrossConnSys-Port1 OBJECT-TYPE
		SYNTAX  DisplayString (SIZE (24))
		ACCESS  read-write
		STATUS  mandatory
		DESCRIPTION  ""
		::= { fsPortDT1E1CrossConnEntry 2 }

	fsPortDT1E1CrossConnSys-Port2 OBJECT-TYPE
		SYNTAX  DisplayString (SIZE (24))
		ACCESS  read-write
		STATUS  mandatory
		DESCRIPTION  ""
		::= { fsPortDT1E1CrossConnEntry 3 }

	fsPortDT1E1CrossConnPort1-Sys OBJECT-TYPE
		SYNTAX  DisplayString (SIZE (24))
		ACCESS  read-write
		STATUS  mandatory
		DESCRIPTION  ""
		::= { fsPortDT1E1CrossConnEntry 4 }

	fsPortDT1E1CrossConnPort1-Port2 OBJECT-TYPE
		SYNTAX  DisplayString (SIZE (24))
		ACCESS  read-write
		STATUS  mandatory
		DESCRIPTION  ""
		::= { fsPortDT1E1CrossConnEntry 5 }

	fsPortDT1E1CrossConnPort2-Sys OBJECT-TYPE
		SYNTAX  DisplayString (SIZE (24))
		ACCESS  read-write
		STATUS  mandatory
		DESCRIPTION  ""
		::= { fsPortDT1E1CrossConnEntry 6 }

	fsPortDT1E1CrossConnPort2-Port1 OBJECT-TYPE
		SYNTAX  DisplayString (SIZE (24))
		ACCESS  read-write
		STATUS  mandatory
		DESCRIPTION  ""
		::= { fsPortDT1E1CrossConnEntry 7 }

	fsPortDT1E1CrossConnStatus OBJECT-TYPE
		SYNTAX  INTEGER {
			view   (1),
			modify (2)
			}
		ACCESS  read-write
		STATUS  mandatory
		DESCRIPTION  ""
		::= { fsPortDT1E1CrossConnEntry 8 }
END
