Wellfleet-TNC-MIB DEFINITIONS ::= BEGIN

-- Created by mdl2asn version 3.1
-- Creation date: Wed Aug 30 16:49:36 EDT 1995


    IMPORTS

      Counter, Gauge
        FROM RFC1155-SMI
      OBJECT-TYPE
        FROM RFC-1212
      DisplayString
        FROM RFC1213-MIB
      wfTelnetGroup
        FROM Wellfleet-COMMON-MIB;


    wfTelnetClient	OBJECT IDENTIFIER ::= { wfTelnetGroup 2 }

    wfTelnetClientDelete OBJECT-TYPE
        SYNTAX	INTEGER {
    		    created(1),
    		    deleted(2)
    		}
        ACCESS	read-write
        STATUS	mandatory
        DESCRIPTION
                "Create or Delete the Object Base Record"
        DEFVAL	{ created }
        ::= { wfTelnetClient 1 }

    wfTelnetClientDisable OBJECT-TYPE
        SYNTAX	INTEGER {
    		    enabled(1),
    		    disabled(2)
    		}
        ACCESS	read-write
        STATUS	mandatory
        DESCRIPTION
                "Enable or Disable Telnet Client"
        DEFVAL	{ enabled }
        ::= { wfTelnetClient 2 }

    wfTelnetClientDebug OBJECT-TYPE
        SYNTAX	INTEGER {
    		    on(1),
    		    off(2)
    		}
        ACCESS	read-write
        STATUS	mandatory
        DESCRIPTION
                "The Initial Value of the Debug Toggle"
        DEFVAL	{ off }
        ::= { wfTelnetClient 3 }

    wfTelnetClientRemotePort OBJECT-TYPE
        SYNTAX	INTEGER
        ACCESS	read-write
        STATUS	mandatory
        DESCRIPTION
                "The Default Remote Telnet Server TCP Port"
        DEFVAL	{ 23 }
        ::= { wfTelnetClient 4 }

    wfTelnetClientPrompt OBJECT-TYPE
        SYNTAX	DisplayString
        ACCESS	read-write
        STATUS	mandatory
        DESCRIPTION
                "The Default Telnet Client Command Prompt"
        ::= { wfTelnetClient 5 }

    wfTelnetClientActiveSessions OBJECT-TYPE
        SYNTAX	Gauge
        ACCESS	read-only
        STATUS	mandatory
        DESCRIPTION
                "The number of active outbound telnet sessions"
        ::= { wfTelnetClient 6 }

    wfTelnetClientTotalSessions OBJECT-TYPE
        SYNTAX	Counter
        ACCESS	read-only
        STATUS	mandatory
        DESCRIPTION
                "Total number of outbound telnet sessions"
        ::= { wfTelnetClient 7 }

    END  -- Wellfleet-TNC-MIB
