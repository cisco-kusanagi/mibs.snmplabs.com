Macromedia-MIB DEFINITIONS ::= BEGIN

        --
        --  MIB Definitions for Macromedia software products.

		-- Cluster Membership Table is supported in NT and Windows 2000 servers, not in UNIX servers.


    IMPORTS
	TRAP-TYPE FROM RFC-1215
        enterprises
                                FROM RFC1155-SMI
        OBJECT-TYPE
                                FROM RFC-1212
        DisplayString
                                FROM RFC1213-MIB;

    allaire				OBJECT IDENTIFIER ::= { enterprises 7138 }
    software            OBJECT IDENTIFIER ::= { allaire  1 }
    coldfusion			OBJECT IDENTIFIER ::= { software 1 } 
	jrun				OBJECT IDENTIFIER ::= { software 2 } 
	jrunServers			OBJECT IDENTIFIER ::= { software 3 } 	
	jrunJDBCs			OBJECT IDENTIFIER ::= { software 4 }
	jrunWebApps			OBJECT IDENTIFIER ::= { software 5 }
	jrunEJBs			OBJECT IDENTIFIER ::= { software 6 }
	probes				OBJECT IDENTIFIER ::= { software 7 }
	haaManagement		OBJECT IDENTIFIER ::= { software 8 }
    serverManagement	OBJECT IDENTIFIER ::= { software 9 }
    clusterManagement	OBJECT IDENTIFIER ::= { software 10 }
    clusterMembership	OBJECT IDENTIFIER ::= { software 11 }
    trapRecord			OBJECT IDENTIFIER ::= { software 12 }


-----------  ColdFusion Information ----------------


    cfOSName OBJECT-TYPE
        SYNTAX DisplayString (SIZE (1..128))
        ACCESS read-only
        STATUS mandatory
        DESCRIPTION
            "The name of the operation system."
        ::= { coldfusion 1 }


    cfOSVersion OBJECT-TYPE
        SYNTAX DisplayString (SIZE (1..128))
        ACCESS read-only
        STATUS mandatory
        DESCRIPTION
            "The version of the operation system."
        ::= { coldfusion 2 }


    cfOSBuildNumber OBJECT-TYPE
        SYNTAX DisplayString (SIZE (1..128))
        ACCESS read-only
        STATUS mandatory
        DESCRIPTION
            "The build number of the operation system."
        ::= { coldfusion 3 }


    cfOSAdditionalInfo OBJECT-TYPE
        SYNTAX DisplayString (SIZE (1..128))
        ACCESS read-only
        STATUS mandatory
        DESCRIPTION
            "Additional information concerning the operation system."
        ::= { coldfusion 4 }

    cfProductName OBJECT-TYPE
        SYNTAX DisplayString (SIZE (1..128))
        ACCESS read-only
        STATUS mandatory
        DESCRIPTION
            "The name of the ColdFusion product."
        ::= { coldfusion 5 }

    cfProductLevel OBJECT-TYPE
        SYNTAX DisplayString (SIZE (1..128))
        ACCESS read-only
        STATUS mandatory
        DESCRIPTION
            "The level of the ColdFusion product."
        ::= { coldfusion 6 }

    cfProductVersion OBJECT-TYPE
        SYNTAX DisplayString (SIZE (1..128))
        ACCESS read-only
        STATUS mandatory
        DESCRIPTION
            "The version of the ColdFusion product."
        ::= { coldfusion 7 }

	cfPerformanceMonitorOn OBJECT-TYPE
        SYNTAX INTEGER {
                        no(0),
                        yes(1)
                        }
		ACCESS read-only
        STATUS mandatory
        DESCRIPTION
            "Indicator specifying whether ColdFusion Enable Performance Monitoring is turned on.  
			 If off, the next 11 runtime parameters will have the value 0."
        ::= { coldfusion 8 }

-----------  ColdFusion Performance Information Begin----------------

    cfPageHits OBJECT-TYPE
        SYNTAX INTEGER
        ACCESS read-only
        STATUS mandatory
        DESCRIPTION
            "The number of ColdFusion page hits per seconds."
        ::= { coldfusion 9 }

    cfRequestsQueued OBJECT-TYPE
        SYNTAX INTEGER
        ACCESS read-only
        STATUS mandatory
        DESCRIPTION
            "The number of ColdFusion requests currently being queued."
        ::= { coldfusion 10 }

    cfDatabaseHits OBJECT-TYPE
        SYNTAX INTEGER
        ACCESS read-only
        STATUS mandatory
        DESCRIPTION
            "The number of database hits by ColdFusion pages per seconds."
        ::= { coldfusion 11 }

    cfRequestsRunning OBJECT-TYPE
        SYNTAX INTEGER
        ACCESS read-only
        STATUS mandatory
        DESCRIPTION
            "The number of requests currently being processed by ColdFusion."
        ::= { coldfusion 12 }

    cfReqestsTimedOut OBJECT-TYPE
        SYNTAX INTEGER
        ACCESS read-only
        STATUS mandatory
        DESCRIPTION
            "The number of ColdFusion requests that have been timed out."
        ::= { coldfusion 13 }

    cfBytesIn OBJECT-TYPE
        SYNTAX INTEGER
        ACCESS read-only
        STATUS mandatory
        DESCRIPTION
            "The total number of bytes that have been read by ColdFusion per second."
        ::= { coldfusion 14 }

    cfBytesOut OBJECT-TYPE
        SYNTAX INTEGER
        ACCESS read-only
        STATUS mandatory
        DESCRIPTION
            "The total number of bytes that have been outputted by ColdFusion per second."
        ::= { coldfusion 15 }

    cfAvgQueueTimes OBJECT-TYPE
        SYNTAX INTEGER
        ACCESS read-only
        STATUS mandatory
        DESCRIPTION
            "The average amount of time spent by a ColdFusion page request 
			in the queue before being processed."
        ::= { coldfusion 16 }

    cfAvgRequestTime OBJECT-TYPE
        SYNTAX INTEGER
        ACCESS read-only
        STATUS mandatory
        DESCRIPTION
            "The average amount of process time spent on a ColdFusion request 
			(queuing time not included)."
        ::= { coldfusion 17 }

    cfAvgDBTime OBJECT-TYPE
        SYNTAX INTEGER
        ACCESS read-only
        STATUS mandatory
        DESCRIPTION
            "The average amount of process time spent by ColdFusion for a database requests."
        ::= { coldfusion 18 }

    cfCachePops OBJECT-TYPE
        SYNTAX INTEGER
        ACCESS read-only
        STATUS mandatory
        DESCRIPTION
            "The number of cache pops performed by ColdFusion per seconds."
        ::= { coldfusion 19 }

-----------  ColdFusion Performance Information End----------------


    cfMaxRequests OBJECT-TYPE
        SYNTAX INTEGER
        ACCESS read-only
        STATUS mandatory
        DESCRIPTION
            "Maximum number of concurrent requests ColdFusion may process."
        ::= { coldfusion 20 }


    cfLimitTime OBJECT-TYPE
        SYNTAX INTEGER {
                        no(0),
                        yes(1)
                        }
		ACCESS read-only
        STATUS mandatory
        DESCRIPTION
            "Indicator specifying whether ColdFusion should limit the time a request may take."
        ::= { coldfusion 21 }

    cfMaxSeconds OBJECT-TYPE
        SYNTAX INTEGER
        ACCESS read-only
        STATUS mandatory
        DESCRIPTION
            "Maximum number of seconds a ColdFusion request may take."
        ::= { coldfusion 22 }

    cfTrustCache OBJECT-TYPE
        SYNTAX INTEGER {
                        no(0),
                        yes(1)
                        }
		ACCESS read-only
        STATUS mandatory
        DESCRIPTION
            "Indicator specifying whether ColdFusion trusts the content of the cache."
        ::= { coldfusion 23 }

    cfTemplateCacheSize OBJECT-TYPE
        SYNTAX INTEGER
        ACCESS read-only
        STATUS mandatory
        DESCRIPTION
            "The size of the ColdFusion template cache."
        ::= { coldfusion 24 }

    cfRunningRDS OBJECT-TYPE
        SYNTAX INTEGER {
                        no(0),
                        yes(1)
                        }
		ACCESS read-only
        STATUS mandatory
        DESCRIPTION
            "Indicator specifying whether ColdFusion is running."
        ::= { coldfusion 25 }

	cfDebuggingOn OBJECT-TYPE
        SYNTAX INTEGER {
                        no(0),
                        yes(1)
                        }
		ACCESS read-only
        STATUS mandatory
        DESCRIPTION
            "Indicator specifying whether one of the debug settings in the ColdFusion Admin
			 Debug Settings page is turned on (Enable Performance Monitoring excluded)."
        ::= { coldfusion 26 }

    cfEnforceStrictAttributeValidation OBJECT-TYPE
        SYNTAX INTEGER {
                        no(0),
                        yes(1)
                        }
		ACCESS read-only
        STATUS mandatory
        DESCRIPTION
            "Indicator specifying whether ColdFusion strictly enforces attribute validation."
        ::= { coldfusion 27 }

    cfRestartThreshold OBJECT-TYPE
        SYNTAX INTEGER
        ACCESS read-only
        STATUS mandatory
        DESCRIPTION
            "The maximum number of unresponsive requests allowed before restarting ColdFusion."
        ::= { coldfusion 28 }

    cfMaxCachedQueries OBJECT-TYPE
        SYNTAX INTEGER
        ACCESS read-only
        STATUS mandatory
        DESCRIPTION
            "The maximum number of cached queries for ColdFusion."
        ::= { coldfusion 29 }

    cfMailServerName OBJECT-TYPE
        SYNTAX DisplayString (SIZE (1..128))
        ACCESS read-only
        STATUS mandatory
        DESCRIPTION
            "The name of the Mail Server used by ColdFusion."
        ::= { coldfusion 30 }

    cfMailServerPortNumber OBJECT-TYPE
        SYNTAX INTEGER
        ACCESS read-only
        STATUS mandatory
        DESCRIPTION
            "The port number of the ColdFusion Mail Server."
        ::= { coldfusion 31 }

    cfMailServerConnectTimeout OBJECT-TYPE
        SYNTAX INTEGER
        ACCESS read-only
        STATUS mandatory
        DESCRIPTION
            "The time ColdFusion should wait for a response from the mail server."
        ::= { coldfusion 32 }

-----------  JRun Information ----------------


    jOSName OBJECT-TYPE
        SYNTAX DisplayString (SIZE (1..128))
        ACCESS read-only
        STATUS mandatory
        DESCRIPTION
            "The name of the operation system."
        ::= { jrun 1 }

    jOSVersion OBJECT-TYPE
        SYNTAX DisplayString (SIZE (1..128))
        ACCESS read-only
        STATUS mandatory
        DESCRIPTION
            "The version number of the operation system."
        ::= { jrun 2 }

    jMachineArchitecture OBJECT-TYPE
        SYNTAX DisplayString (SIZE (1..128))
        ACCESS read-only
        STATUS mandatory
        DESCRIPTION
            "The architecture of the machine."
        ::= { jrun 3 }

    jJDKVendor OBJECT-TYPE
        SYNTAX DisplayString (SIZE (1..128))
        ACCESS read-only
        STATUS mandatory
        DESCRIPTION
            "The company that supplies the Java Development Kit."
        ::= { jrun 4 }

    jJDKVersion OBJECT-TYPE
        SYNTAX DisplayString (SIZE (1..128))
        ACCESS read-only
        STATUS mandatory
        DESCRIPTION
            "The version of the Java Development Kit."
        ::= { jrun 5 }

    jJRunVersion OBJECT-TYPE
        SYNTAX DisplayString (SIZE (1..128))
        ACCESS read-only
        STATUS mandatory
        DESCRIPTION
            "JRun version number."
        ::= { jrun 6 }

    jFreeMomory OBJECT-TYPE
        SYNTAX INTEGER
        ACCESS read-only
        STATUS mandatory
        DESCRIPTION
            "Kilobytes of free memory in the heap."
        ::= { jrun 7 }

    jTotalMomory OBJECT-TYPE
        SYNTAX INTEGER
        ACCESS read-only
        STATUS mandatory
        DESCRIPTION
            "Total kilobytes in the heap."
        ::= { jrun 8 }

    jSessions OBJECT-TYPE
        SYNTAX INTEGER
        ACCESS read-only
        STATUS mandatory
        DESCRIPTION
            "Current number of active sessions."
        ::= { jrun 9 }

    jSessionsInMemory OBJECT-TYPE
        SYNTAX INTEGER
        ACCESS read-only
        STATUS mandatory
        DESCRIPTION
            "Number of sessions in memory."
        ::= { jrun 10 }

    jJcpBytesIn OBJECT-TYPE
        SYNTAX INTEGER
        ACCESS read-only
        STATUS mandatory
        DESCRIPTION
            "The number of bytes read from request by the JRun Service."
        ::= { jrun 11 }

    jJcpBytesOut OBJECT-TYPE
        SYNTAX INTEGER
        ACCESS read-only
        STATUS mandatory
        DESCRIPTION
            "The number of bytes written in response by the JRun Service."
        ::= { jrun 12 }

    jJcpHandledRequests OBJECT-TYPE
        SYNTAX INTEGER
        ACCESS read-only
        STATUS mandatory
        DESCRIPTION
            "Number of requests handled by the JRun Service."
        ::= { jrun 13 }

    jJcpDelayRequests OBJECT-TYPE
        SYNTAX INTEGER
        ACCESS read-only
        STATUS mandatory
        DESCRIPTION
            "Number of requests delayed by the JRun Service due to high concurrency."
        ::= { jrun 14 }

    jJcpDroppedRequests OBJECT-TYPE
        SYNTAX INTEGER
        ACCESS read-only
        STATUS mandatory
        DESCRIPTION
            "Number of requests dropped by the JRun Service."
        ::= { jrun 15 }

    jJcpHandledMs OBJECT-TYPE
        SYNTAX INTEGER
        ACCESS read-only
        STATUS mandatory
        DESCRIPTION
            "Number of milliseconds spent servicing requests by the JRun Service (delay time not included)."
        ::= { jrun 16 }

    jJcpDelayMs OBJECT-TYPE
        SYNTAX INTEGER
        ACCESS read-only
        STATUS mandatory
        DESCRIPTION
            "Number of milliseconds spent in delayed state by the JRun Service."
        ::= { jrun 17 }

    jJcpTotalThreads OBJECT-TYPE
        SYNTAX INTEGER
        ACCESS read-only
        STATUS mandatory
        DESCRIPTION
            "Total workers threads of the JRun Service."
        ::= { jrun 18 }

    jJcpListenThreads OBJECT-TYPE
        SYNTAX INTEGER
        ACCESS read-only
        STATUS mandatory
        DESCRIPTION
            "Threads in the JRun Service waiting for a new connection."
        ::= { jrun 19 }

    jJcpBusyThreads OBJECT-TYPE
        SYNTAX INTEGER
        ACCESS read-only
        STATUS mandatory
        DESCRIPTION
            "Threads in the JRun Service currently running."
        ::= { jrun 20 }

    jJcpDelayThreads OBJECT-TYPE
        SYNTAX INTEGER
        ACCESS read-only
        STATUS mandatory
        DESCRIPTION
            "Threads in the JRun Service waiting to run."
        ::= { jrun 21 }

    jJcpIdleThreads OBJECT-TYPE
        SYNTAX INTEGER
        ACCESS read-only
        STATUS mandatory
        DESCRIPTION
            "Threads in the JRun Service waiting for a new request."
        ::= { jrun 22 }

    jWebBytesIn OBJECT-TYPE
        SYNTAX INTEGER
        ACCESS read-only
        STATUS mandatory
        DESCRIPTION
            "The number of bytes read from request by the JRun Web Server."
        ::= { jrun 23 }

    jWebBytesOut OBJECT-TYPE
        SYNTAX INTEGER
        ACCESS read-only
        STATUS mandatory
        DESCRIPTION
            "The number of bytes written in response by the JRun Web Server."
        ::= { jrun 24 }

    jWebHandledRequests OBJECT-TYPE
        SYNTAX INTEGER
        ACCESS read-only
        STATUS mandatory
        DESCRIPTION
            "Number of requests handled by the JRun Web Server."
        ::= { jrun 25 }

    jWebDelayRequests OBJECT-TYPE
        SYNTAX INTEGER
        ACCESS read-only
        STATUS mandatory
        DESCRIPTION
            "Number of requests delayed by the JRun Web Server due to high concurrency."
        ::= { jrun 26 }

    jWebDroppedRequests OBJECT-TYPE
        SYNTAX INTEGER
        ACCESS read-only
        STATUS mandatory
        DESCRIPTION
            "Number of requests dropped by the JRun Web Server."
        ::= { jrun 27 }

    jWebHandledMs OBJECT-TYPE
        SYNTAX INTEGER
        ACCESS read-only
        STATUS mandatory
        DESCRIPTION
            "Number of milliseconds spent servicing requests by the JRun Web Server (delay time not included)."
        ::= { jrun 28 }

    jWebDelayMs OBJECT-TYPE
        SYNTAX INTEGER
        ACCESS read-only
        STATUS mandatory
        DESCRIPTION
            "Number of milliseconds spent in delayed state by the JRun Web Server."
        ::= { jrun 29 }

    jWebTotalThreads OBJECT-TYPE
        SYNTAX INTEGER
        ACCESS read-only
        STATUS mandatory
        DESCRIPTION
            "Total workers threads of the JRun Web Server."
        ::= { jrun 30 }

    jWebListenThreads OBJECT-TYPE
        SYNTAX INTEGER
        ACCESS read-only
        STATUS mandatory
        DESCRIPTION
            "Threads in the JRun Web Server waiting for a new connection."
        ::= { jrun 31 }

    jWebBusyThreads OBJECT-TYPE
        SYNTAX INTEGER
        ACCESS read-only
        STATUS mandatory
        DESCRIPTION
            "Threads in the JRun Web Server currently running."
        ::= { jrun 32 }

    jWebDelayThreads OBJECT-TYPE
        SYNTAX INTEGER
        ACCESS read-only
        STATUS mandatory
        DESCRIPTION
            "Threads in the JRun Web Server waiting to run."
        ::= { jrun 33 }

    jWebIdleThreads OBJECT-TYPE
        SYNTAX INTEGER
        ACCESS read-only
        STATUS mandatory
        DESCRIPTION
            "Threads in the JRun Web Server waiting for a new request."
        ::= { jrun 34 }

----------------------- JRun Servers -----

    jrunServerTable OBJECT-TYPE
        SYNTAX SEQUENCE OF JRunServerEntry 
        ACCESS not-accessible
        STATUS mandatory
        DESCRIPTION
            "A table containing JRun Servers (e.g. Admin Server, Default Server)."
        ::= { jrunServers 1 }

    jrunServerEntry OBJECT-TYPE
        SYNTAX JRunServerEntry
        ACCESS not-accessible
        STATUS mandatory
        DESCRIPTION
            "Row definition for this table."
        INDEX { jrunServerOrdinal}
        ::= { jrunServerTable 1 }

    JRunServerEntry ::=
        SEQUENCE {	
					jrunServerOrdinal		INTEGER,			
					jrunServerName			DisplayString,
					jrunServerState			INTEGER
				 }

	jrunServerOrdinal OBJECT-TYPE
        SYNTAX INTEGER
        ACCESS read-only
        STATUS mandatory
        DESCRIPTION
            "The ordinal of this JRun server amongst all the JRun Servers.
			The JRun Servers are sorted by their name."
        ::= { jrunServerEntry 1 }

    jrunServerName OBJECT-TYPE
        SYNTAX DisplayString (SIZE (1..255))
        ACCESS read-only
        STATUS mandatory
        DESCRIPTION
             "The name of the JRun Server."
        ::= { jrunServerEntry 2 }


    jrunServerState OBJECT-TYPE
        SYNTAX INTEGER {
                        success(0),
                        failure(1)
                        }
        ACCESS read-only
        STATUS mandatory
        DESCRIPTION
            "The state of the JRun server."
        ::= { jrunServerEntry 3 }


-----------  JRun JDBC Table ----------------


    jrunJDBCTable OBJECT-TYPE
        SYNTAX SEQUENCE OF JRunJDBCEntry 
        ACCESS not-accessible
        STATUS mandatory
        DESCRIPTION
            "A table describing JDBC data sources associated with JRun servers."
        ::= { jrunJDBCs 1 }

    jrunJDBCEntry OBJECT-TYPE
        SYNTAX JRunJDBCEntry
        ACCESS not-accessible
        STATUS mandatory
        DESCRIPTION
            "Row definition for this table."
        INDEX { jdbcOrdinal }
        ::= { jrunJDBCTable 1 }

    JRunJDBCEntry ::=
        SEQUENCE {	
					 jdbcOrdinal			INTEGER,			
					 jdbcJRunServerName		DisplayString,
					 jdbcName				DisplayString,
					 jdbcState				INTEGER
				 }

	jdbcOrdinal OBJECT-TYPE
        SYNTAX INTEGER
        ACCESS read-only
        STATUS mandatory
        DESCRIPTION
            "The ordinal of the JDBC data source in the associated JRun server."
        ::= { jrunJDBCEntry 1 }

	jdbcJRunServerName OBJECT-TYPE
        SYNTAX DisplayString (SIZE (1..255))
        ACCESS read-only
        STATUS mandatory
        DESCRIPTION
            "The name of the JRun Server to which the JDBC definition belongs."
        ::= { jrunJDBCEntry 2 }

    jdbcName OBJECT-TYPE
        SYNTAX DisplayString (SIZE (1..255))
        ACCESS read-only
        STATUS mandatory
        DESCRIPTION
             "The name of the JDBC data source."
        ::= { jrunJDBCEntry 3 }

    jdbcState OBJECT-TYPE
        SYNTAX INTEGER {
                        success(0),
                        failure(1)
                        }
		ACCESS read-only
        STATUS mandatory
        DESCRIPTION
             "The state of the JDBC data source."
        ::= { jrunJDBCEntry 4 }


-----------  JRun Web Application Table ----------------


    jrunWebAppTable OBJECT-TYPE
        SYNTAX SEQUENCE OF JRunWebAppEntry 
        ACCESS not-accessible
        STATUS mandatory
        DESCRIPTION
            "A table describing Web applications associated with JRun servers."
        ::= { jrunWebApps 1 }

    jrunWebAppEntry OBJECT-TYPE
        SYNTAX JRunWebAppEntry
        ACCESS not-accessible
        STATUS mandatory
        DESCRIPTION
            "Row definition for this table."
        INDEX { webAppOrdinal }
        ::= { jrunWebAppTable 1 }

    JRunWebAppEntry ::=
        SEQUENCE {	
					webAppOrdinal			INTEGER,	
					webAppJRunServerName	DisplayString,
					webAppName				DisplayString
				 }

	webAppOrdinal OBJECT-TYPE
        SYNTAX INTEGER
        ACCESS read-only
        STATUS mandatory
        DESCRIPTION
            "The ordinal of the Web Application in the associated JRun server."
        ::= { jrunWebAppEntry 1 }

	webAppJRunServerName OBJECT-TYPE
        SYNTAX DisplayString (SIZE (1..255))
        ACCESS read-only
        STATUS mandatory
        DESCRIPTION
            "The name of this JRun Server to which the web application belong."
        ::= { jrunWebAppEntry 2 }

    webAppName OBJECT-TYPE
        SYNTAX DisplayString (SIZE (1..255))
        ACCESS read-only
        STATUS mandatory
        DESCRIPTION
             "The name of the Web Application."
        ::= { jrunWebAppEntry 3 }


-----------  JRun EJB Table ----------------


    jrunEjbTable OBJECT-TYPE
        SYNTAX SEQUENCE OF JRunEjbEntry 
        ACCESS not-accessible
        STATUS mandatory
        DESCRIPTION
            "A table describing EJB's associated with JRun servers."
        ::= { jrunEJBs 1 }

    jrunEjbEntry OBJECT-TYPE
        SYNTAX JRunEjbEntry
        ACCESS not-accessible
        STATUS mandatory
        DESCRIPTION
            "Row definition for this table."
        INDEX { ejbOrdinal }
        ::= { jrunEjbTable 1 }

    JRunEjbEntry ::=
        SEQUENCE {	
					ejbOrdinal				INTEGER,
					ejbJRunServerName		DisplayString,			
					ejbName					DisplayString
				 }

	ejbOrdinal OBJECT-TYPE
        SYNTAX INTEGER
        ACCESS read-only
        STATUS mandatory
        DESCRIPTION
            "The ordinal of the EJB in the associated JRun server."
        ::= { jrunEjbEntry 1 }

	ejbJRunServerName OBJECT-TYPE
        SYNTAX DisplayString (SIZE (1..255))
        ACCESS read-only
        STATUS mandatory
        DESCRIPTION
            "The name of this JRun Server to which the EJB belongs."
        ::= { jrunEjbEntry 2 }


    ejbName OBJECT-TYPE
        SYNTAX DisplayString (SIZE (1..255))
        ACCESS read-only
        STATUS mandatory
        DESCRIPTION
             "The name of the EJB."
        ::= { jrunEjbEntry 3 }


-----------  Probe Table ----------------


    probeTable OBJECT-TYPE
        SYNTAX SEQUENCE OF ProbeEntry 
        ACCESS not-accessible
        STATUS mandatory
        DESCRIPTION
            "A table containing ColdFusion probes."
        ::= { probes 1 }

    probeEntry OBJECT-TYPE
        SYNTAX ProbeEntry
        ACCESS not-accessible
        STATUS mandatory
        DESCRIPTION
            "Row definition for this table."
        INDEX { probeOrdinalNumber}
        ::= { probeTable 1 }

    ProbeEntry ::=
        SEQUENCE {	
					probeOrdinalNumber		INTEGER,			
					probeName				DisplayString,
					probeState				INTEGER
				}

	probeOrdinalNumber OBJECT-TYPE
        SYNTAX INTEGER
        ACCESS read-only
        STATUS mandatory
        DESCRIPTION
            "The ordinal of this probe amongst the Application probes.  
			The probes are sorted by their name."
        ::= { probeEntry 1 }

    probeName OBJECT-TYPE
        SYNTAX DisplayString (SIZE (1..255))
        ACCESS read-only
        STATUS mandatory
        DESCRIPTION
             "The name of the probe."
        ::= { probeEntry 2 }


    probeState OBJECT-TYPE
        SYNTAX INTEGER {
                        success(0),
                        failure(1),
                        suspended(2)
                       }
        ACCESS read-only
        STATUS mandatory
        DESCRIPTION
            "The state of the probe."
        ::= { probeEntry 3 }


-----------  HAA Web Server Table ----------------


    haaServerTable OBJECT-TYPE
        SYNTAX SEQUENCE OF HAAServerEntry 
        ACCESS not-accessible
        STATUS mandatory
        DESCRIPTION
            "A table containing instance information for web servers in the computer."
        ::= { haaManagement 1 }

    hserverEntry OBJECT-TYPE
        SYNTAX HAAServerEntry
        ACCESS not-accessible
        STATUS mandatory
        DESCRIPTION
            "Row definition for this table."
        INDEX { hServerOrdinalNumber}
        ::= { haaServerTable 1 }

    HAAServerEntry ::=
        SEQUENCE {	
					hServerOrdinalNumber		INTEGER,
					hServerName					DisplayString,
					hServerIP					DisplayString,
					hServerState				INTEGER,
					hServerMode					INTEGER,
					hServerLoad					INTEGER,
					hServerLoadBalanceProduct	INTEGER,
					hServerLoadThreshold		INTEGER,
					hServerLoadType				INTEGER
				}

	hServerOrdinalNumber OBJECT-TYPE
        SYNTAX INTEGER
        ACCESS read-only
        STATUS mandatory
        DESCRIPTION
            "The ordinal of this web server amongst web servers in the computer."
        ::= { hserverEntry 1 }


    hServerName OBJECT-TYPE
        SYNTAX DisplayString (SIZE (1..255))
        ACCESS read-only
        STATUS mandatory
        DESCRIPTION
            "Fully qualified hostname for the Web Server."
        ::= { hserverEntry 2 }

	hServerIP OBJECT-TYPE
        SYNTAX DisplayString (SIZE (1..255))
        ACCESS read-only
        STATUS mandatory
        DESCRIPTION
            "IP address of the Web Server."
        ::= { hserverEntry 3 }

    hServerState OBJECT-TYPE
        SYNTAX INTEGER {
							available(0),
							unavailable(1),
							busy(2),
							restricted(3)
                        }
        ACCESS read-only
        STATUS mandatory
        DESCRIPTION
            "The state of the Web Server."
        ::= { hserverEntry 4 }


    hServerMode OBJECT-TYPE
        SYNTAX INTEGER {
                        passive(0),
                        active(1)
                        }
        ACCESS read-only
        STATUS mandatory
        DESCRIPTION
            "For HAA, server mode being active means that it sends load statistics to the Hardware Load Balancing box."
        ::= { hserverEntry 5 }


    hServerLoad OBJECT-TYPE
        SYNTAX INTEGER (0..100)
        ACCESS read-only
        STATUS mandatory
        DESCRIPTION
            "The load of the server, value is between 0 and 100."
        ::= { hserverEntry 6 }


    hServerLoadBalanceProduct OBJECT-TYPE
        SYNTAX INTEGER { 
						none(0),
                        brightTiger(1),
                        ciscoLocalDirector(2),
						other(3)
                        }        
		ACCESS read-only
        STATUS mandatory
        DESCRIPTION
            "The product used for balancing web traffic."
        ::= { hserverEntry 7 }


    hServerLoadThreshold OBJECT-TYPE
        SYNTAX INTEGER (0..100)
        ACCESS read-only
        STATUS mandatory
        DESCRIPTION
            "A value between 0-100, when the server load reaches this value, HTTP requests will be redirected."
        ::= { hserverEntry 8 }
                               

	hServerLoadType OBJECT-TYPE
        SYNTAX INTEGER {
                        coldFusion(0),
                        jrun(1)
                        }        
		ACCESS read-only
        STATUS mandatory
        DESCRIPTION
            "The type of load used by the server for load balancing calculation."
        ::= { hserverEntry 9 }


-----------  ClusterCATS Web Server Table ----------------


    serverTable OBJECT-TYPE
        SYNTAX SEQUENCE OF ServerEntry 
        ACCESS not-accessible
        STATUS mandatory
        DESCRIPTION
            "A table containing instance information for web servers in the computer."
        ::= { serverManagement 1 }

    serverEntry OBJECT-TYPE
        SYNTAX ServerEntry
        ACCESS not-accessible
        STATUS mandatory
        DESCRIPTION
            "Row definition for this table."
        INDEX { serverOrdinalNumber}
        ::= { serverTable 1 }

    ServerEntry ::=
        SEQUENCE {	
					serverOrdinalNumber			INTEGER,
					serverName					DisplayString,
					serverIP					DisplayString,
					serverState					INTEGER,
					serverMode					INTEGER,
					serverLoad					INTEGER,
					serverLoadBalanceProduct	INTEGER,
					serverLoadThreshold			INTEGER,
					serverLoadType				INTEGER,
					serverCluster				DisplayString,
					serverAdminAgent			DisplayString,
					serverSessionAwareness		INTEGER,
					serverGradualLoadThreshold	INTEGER,
                    serverGradualRedirectState	INTEGER
				}

	serverOrdinalNumber OBJECT-TYPE
        SYNTAX INTEGER
        ACCESS read-only
        STATUS mandatory
        DESCRIPTION
            "The ordinal of this web server amongst web servers in the computer."
        ::= { serverEntry 1 }


    serverName OBJECT-TYPE
        SYNTAX DisplayString (SIZE (1..255))
        ACCESS read-only
        STATUS mandatory
        DESCRIPTION
            "Fully qualified hostname for the Web Server."
        ::= { serverEntry 2 }

	serverIP OBJECT-TYPE
        SYNTAX DisplayString (SIZE (1..255))
        ACCESS read-only
        STATUS mandatory
        DESCRIPTION
            "IP address of the Web Server."
        ::= { serverEntry 3 }

    serverState OBJECT-TYPE
        SYNTAX INTEGER {
							available(0),
							unavailable(1),
							busy(2),
							restricted(3)
                        }
        ACCESS read-only
        STATUS mandatory
        DESCRIPTION
            "The state of the Web Server."
        ::= { serverEntry 4 }

    serverMode OBJECT-TYPE
        SYNTAX INTEGER {
                        passive(0),
                        active(1)
                        }
        ACCESS read-only
        STATUS mandatory
        DESCRIPTION
            "For HAA, server mode being active means that it sends load statistics to the Hardware Load Balancing box.
			 For ClusterCATS, server mode being active means that the server redirects web traffic to balance load"
        ::= { serverEntry 5 }

    serverLoad OBJECT-TYPE
        SYNTAX INTEGER (0..100)
        ACCESS read-only
        STATUS mandatory
        DESCRIPTION
            "The load of the server, value is between 0 and 100."
        ::= { serverEntry 6 }


    serverLoadBalanceProduct OBJECT-TYPE
        SYNTAX INTEGER { 
						none(0),
                        brightTiger(1),
                        ciscoLocalDirector(2),
						other(3)
                        }        
		ACCESS read-only
        STATUS mandatory
        DESCRIPTION
            "The product used for balancing web traffic."
        ::= { serverEntry 7 }


    serverLoadThreshold OBJECT-TYPE
        SYNTAX INTEGER (0..100)
        ACCESS read-only
        STATUS mandatory
        DESCRIPTION
            "A value between 0-100, when the server load reaches this value, HTTP requests will be redirected."
        ::= { serverEntry 8 }
                               

	serverLoadType OBJECT-TYPE
        SYNTAX INTEGER {
                        coldFusion(0),
                        jrun(1)
                        }        
		ACCESS read-only
        STATUS mandatory
        DESCRIPTION
            "The type of load used by the server for load balancing calculation."
        ::= { serverEntry 9 }


	serverCluster OBJECT-TYPE
        SYNTAX DisplayString (SIZE (1..255))
        ACCESS read-only
        STATUS mandatory
        DESCRIPTION
            "The cluster the Web Server belongs to."
        ::= { serverEntry 10 }


	serverAdminAgent OBJECT-TYPE
        SYNTAX DisplayString (SIZE (1..255))
        ACCESS read-only
        STATUS mandatory
        DESCRIPTION
            "The Admin Agent of the cluster the Web Server belongs to."
        ::= { serverEntry 11 }

    serverSessionAwareness OBJECT-TYPE
        SYNTAX INTEGER {
                        off(0),
                        on(1)
                        }        
		ACCESS read-only
        STATUS mandatory
        DESCRIPTION
            "An indicator signifying whether session aware load balancing is turned on."
        ::= { serverEntry 12 }

    serverGradualLoadThreshold OBJECT-TYPE
        SYNTAX INTEGER (0..100)
        ACCESS read-only
        STATUS mandatory
        DESCRIPTION
			"A value between 0-100, when the server load reaches this value, some of the HTTP requests will be redirected."
        ::= { serverEntry 13 }


    serverGradualRedirectState OBJECT-TYPE
        SYNTAX INTEGER {
                        off(0),
                        on(1)
                        }
        ACCESS read-only
        STATUS mandatory
        DESCRIPTION
            "Specifies if gradual redirection is turned on."
        ::= { serverEntry 14 }


-----------  Cluster Table ----------------


    clusterTable OBJECT-TYPE
        SYNTAX SEQUENCE OF ClusterEntry 
        ACCESS not-accessible
        STATUS mandatory
        DESCRIPTION
            "A table describing clusters to which the webservers belong."
        ::= { clusterManagement 1 }

    clusterEntry OBJECT-TYPE
        SYNTAX ClusterEntry
        ACCESS not-accessible
        STATUS mandatory
        DESCRIPTION
            "Row definition for this table."
        INDEX { clusterOrdinalNumber}
        ::= { clusterTable 1 }

    ClusterEntry ::=
        SEQUENCE {	
					clusterOrdinalNumber	INTEGER,			
					clusterName				DisplayString,
					clusterAdminAgent		DisplayString
				}

	clusterOrdinalNumber OBJECT-TYPE
        SYNTAX INTEGER
        ACCESS read-only
        STATUS mandatory
        DESCRIPTION
            "The ordinal of this cluster amongst the clusters encountered in this server."
        ::= { clusterEntry 1 }

    clusterName OBJECT-TYPE
        SYNTAX DisplayString (SIZE (1..255))
        ACCESS read-only
        STATUS mandatory
        DESCRIPTION
             "The name of the cluster."
        ::= { clusterEntry 2 }


    clusterAdminAgent OBJECT-TYPE
        SYNTAX DisplayString (SIZE (1..255))
        ACCESS read-only
        STATUS mandatory
        DESCRIPTION
             "The name of the cluster's Admin Agent."
        ::= { clusterEntry 3 }


-----------  Cluster Membership Table --------------------------------------------------

    clusterMemberTable OBJECT-TYPE
        SYNTAX SEQUENCE OF ClusterMemberEntry 
        ACCESS not-accessible
        STATUS mandatory
        DESCRIPTION
            "A table describing webservers members for clusters found in a computer."
        ::= { clusterMembership 1 }

    clusterMemberEntry OBJECT-TYPE
        SYNTAX ClusterMemberEntry
        ACCESS not-accessible
        STATUS mandatory
        DESCRIPTION
            "Row definition for this table."
        INDEX { mClusterOrdinalNumber, mServerOrdinalNumber }
        ::= { clusterMemberTable 1 }

    ClusterMemberEntry ::=
        SEQUENCE {	
					mClusterOrdinalNumber	INTEGER,
					mServerOrdinalNumber	INTEGER,			
					mServerName				DisplayString
				}

	mClusterOrdinalNumber OBJECT-TYPE
        SYNTAX INTEGER
        ACCESS read-only
        STATUS mandatory
        DESCRIPTION
            "The ordinal of this cluster amongst the clusters encountered in this server."
        ::= { clusterMemberEntry 1 }

	mServerOrdinalNumber OBJECT-TYPE
        SYNTAX INTEGER
        ACCESS read-only
        STATUS mandatory
        DESCRIPTION
            "The ordinal of the member webservers in a cluster."
        ::= { clusterMemberEntry 2 }


    mServerName OBJECT-TYPE
        SYNTAX DisplayString (SIZE (1..255))
        ACCESS read-only
        STATUS mandatory
        DESCRIPTION
             "The name of the member webserver."
        ::= { clusterMemberEntry 3 }



-------  Macromedia trap record contains the information of the latest trap for each trap category -----

    trapProbeName OBJECT-TYPE
        SYNTAX DisplayString (SIZE (1..255))
        ACCESS read-only
        STATUS mandatory
        DESCRIPTION
             "The name of the probe in the latest Probe Failure trap."
        ::= { trapRecord 1 }

    trapProbeFailureTime OBJECT-TYPE
        SYNTAX DisplayString (SIZE (1..255))
        ACCESS read-only
        STATUS mandatory
        DESCRIPTION
             "The time at which the latest Probe Failure trap occurred."
        ::= { trapRecord 2 }


    trapServerName OBJECT-TYPE
        SYNTAX DisplayString (SIZE (1..255))
        ACCESS read-only
        STATUS mandatory
        DESCRIPTION
            "The name of the server in the latest Server Abnormal State trap."
        ::= { trapRecord 3 }

    trapServerState OBJECT-TYPE
        SYNTAX INTEGER {
							available(0),
							unavailable(1),
							busy(2),
							restricted(3)
                        }
        ACCESS read-only
        STATUS mandatory
        DESCRIPTION
            "The state of the Web Server in the latest Server Abnormal State trap."
        ::= { trapRecord 4 }

    trapServerAbnormalStateTime OBJECT-TYPE
        SYNTAX DisplayString (SIZE (1..255))
        ACCESS read-only
        STATUS mandatory
        DESCRIPTION
             "The time at which the latest Server Abnormal State trap occurred."
        ::= { trapRecord 5 }

    trapJRunServerName OBJECT-TYPE
        SYNTAX DisplayString (SIZE (1..255))
        ACCESS read-only
        STATUS mandatory
        DESCRIPTION
             "The name of the JRun Server in the latest JRun Server Abnormal State trap."
        ::= { trapRecord 6 }

    trapJRunServerAbnormalStateTime OBJECT-TYPE
        SYNTAX DisplayString (SIZE (1..255))
        ACCESS read-only
        STATUS mandatory
        DESCRIPTION
             "The time at which the latest JRun Server Abnormal State trap occurred."
        ::= { trapRecord 7 }

	trapJdbcJRunServerName OBJECT-TYPE
        SYNTAX DisplayString (SIZE (1..255))
        ACCESS read-only
        STATUS mandatory
        DESCRIPTION
            "The name of the JRun Server in the latest JRun JDBC Failure trap."
        ::= { trapRecord 8 }

    trapJdbcName OBJECT-TYPE
        SYNTAX DisplayString (SIZE (1..255))
        ACCESS read-only
        STATUS mandatory
        DESCRIPTION
             "The name of the JDBC data source in the latest JRun JDBC Failure trap."
        ::= { trapRecord 9 }

    trapJRunJDBCFailureTime OBJECT-TYPE
        SYNTAX DisplayString (SIZE (1..255))
        ACCESS read-only
        STATUS mandatory
        DESCRIPTION
             "The time at which the latest JRun JDBC Failure trap occurred."
        ::= { trapRecord 10 }


-------  Macromedia TRAPS.  Sender's IP address is automatically included in each trap message -----


	probeFailure TRAP-TYPE
        ENTERPRISE  allaire
		VARIABLES { trapProbeName }
        DESCRIPTION
			 "This trap occurs whenever a probe on the server fails."
			::= 1

	serverAbnormalState TRAP-TYPE
        ENTERPRISE  allaire
		VARIABLES { trapServerName, trapServerState }
        DESCRIPTION
			"This trap occurs whenever a web virtual server is not in the available state."
			::= 2

	jrunServerAbnormalState TRAP-TYPE
        ENTERPRISE  allaire
		VARIABLES { trapJRunServerName}
        DESCRIPTION
			"This trap occurs whenever a JRun server is not in the available state."
			::= 3

	jrunJDBCFailure TRAP-TYPE
        ENTERPRISE  allaire
		VARIABLES { trapJdbcJRunServerName, trapJdbcName}
        DESCRIPTION
			 "This trap occurs whenever connection to a JDBC data source of a JRun Server fails."
			::= 4



     END
