-- $Id: wan.mib,v 29.12.30.1 1999/11/30 22:54:46 cmiller Exp $

--
-- Feb 14, 1997 rm   Initial creation
-- 02 Oct 97:   kn   EOI-12553:  Rename wanInfo to advancedAgent
--


ASCEND-WAN-MIB DEFINITIONS ::= BEGIN

       IMPORTS
                advancedAgent
                        FROM ASCEND-MIB;

	-- Ascend WAN types
	--
	-- Each Ascend WAN type is assigned an object ID.  These ids are
	-- the root of MIB subtrees containing WAN specific information.
	-- These subtrees, when required, are described in separate files.

    wanTypeAny		OBJECT IDENTIFIER ::= { advancedAgent 1 }
    wanTypeT1		OBJECT IDENTIFIER ::= { advancedAgent 2 }
    wanTypeE1		OBJECT IDENTIFIER ::= { advancedAgent 3 }
    wanTypeDpnss	OBJECT IDENTIFIER ::= { advancedAgent 4 }
    wanTypeBri		OBJECT IDENTIFIER ::= { advancedAgent 5 }
    wanTypeS562		OBJECT IDENTIFIER ::= { advancedAgent 6 }
    wanTypeS564		OBJECT IDENTIFIER ::= { advancedAgent 7 }
    wanTypeSdsl		OBJECT IDENTIFIER ::= { advancedAgent 8 }
    wanTypeAdslCap      OBJECT IDENTIFIER ::= { advancedAgent 9 }
    wanTypeAdslDmt      OBJECT IDENTIFIER ::= { advancedAgent 10 }
    wanTypeHdsl2        OBJECT IDENTIFIER ::= { advancedAgent 12 }

END
