PKTC-MTA-MIB DEFINITIONS ::= BEGIN
IMPORTS

	TEXTUAL-CONVENTION FROM SNMPv2-TC
	MODULE-IDENTITY,
	OBJECT-TYPE,
	Integer32,
	Unsigned32,
	Counter32,
	NOTIFICATION-TYPE
FROM SNMPv2-SMI
	
	TruthValue, 
	DisplayString, 
	DateAndTime, 
	RowStatus
FROM SNMPv2-TC

	OBJECT-GROUP,
	MODULE-COMPLIANCE
FROM SNMPv2-CONF

	clabProjPacketCable
FROM CLAB-DEF-MIB

	ifIndex 
FROM IF-MIB

	docsDevSwCurrentVers
FROM DOCS-CABLE-DEVICE-MIB;	-- version 8

pktcMtaMib MODULE-IDENTITY
	LAST-UPDATED		"9912010000Z" -- December 1, 1999
	ORGANIZATION		"IPCablecom OSS Group"
	CONTACT-INFO
			"Roy Spitzer
			Postal: Telogy Networks, Inc.
			20250 Century Blvd.
			Germantown, MD 20855
			U.S.A.
			Phone: +1 301-515-6531
			Fax:	+1 301-515-7954
			E-mail: rspitzer@telogy.com"
	DESCRIPTION
			"This MIB module supplies the basic management objects 
			for the MTA Device."
	::= { clabProjPacketCable 1 }

-- Textual conventions
X509Certificate ::= TEXTUAL-CONVENTION
STATUS current
DESCRIPTION
"An X509 digital certificate encoded as an ASN.1 DER
object."
SYNTAX OCTET STRING (SIZE (0..4096))

--
--  IPCablecom supports embedded MTA only
--  IPCablecom requires SNMPv3
--


pktcMtaMibObjects	OBJECT IDENTIFIER ::= { pktcMtaMib 1 }
pktcMtaDevBase		OBJECT IDENTIFIER ::= { pktcMtaMibObjects 1 }
pktcMtaDevServer	OBJECT IDENTIFIER ::= { pktcMtaMibObjects 2 }
pktcMtaDevSecurity	OBJECT IDENTIFIER ::= { pktcMtaMibObjects 3 }
pktcMtaDevEvent		OBJECT IDENTIFIER ::= { pktcMtaMibObjects 4 }




--
-- The following group describes the base objects in the MTA 
--
pktcMtaDevResetNow OBJECT-TYPE
	SYNTAX		TruthValue
	MAX-ACCESS	read-write
	STATUS		current
	DESCRIPTION
		"Setting this object to true(1) causes the device to reset.
		Reading this object always returns false(2)."
	::= { pktcMtaDevBase 1 }

pktcMtaDevSerialNumber OBJECT-TYPE
	SYNTAX		DisplayString (SIZE (0..128))
	MAX-ACCESS 	read-only
	STATUS		current
	DESCRIPTION
			"The manufacturer's serial number for this MTA."
	::= { pktcMtaDevBase 2 }

pktcMtaDevHardwareVersion OBJECT-TYPE
	SYNTAX		DisplayString (SIZE (0..48))
	MAX-ACCESS	read-only
	STATUS		current
	DESCRIPTION
		"The manufacturer's hardware version for this MTA."
	::= { pktcMtaDevBase 3 }

pktcMtaDevMacAddress OBJECT-TYPE
	SYNTAX		OCTET STRING
	MAX-ACCESS	read-only
	STATUS		current
	DESCRIPTION
		"The telephony MAC address for this device."
	::= { pktcMtaDevBase 4 }	

pktcMtaDevFQDN	OBJECT-TYPE
  SYNTAX		DisplayString
  MAX-ACCESS 		read-write
  STATUS		current
  DESCRIPTION
		"The Fully Qualified Domain Name for this MTA."
	::= { pktcMtaDevBase 5 }	

pktcMtaDevEndPntCount	OBJECT-TYPE
	SYNTAX		INTEGER (1..255)
	MAX-ACCESS 	read-only
	STATUS		current
	DESCRIPTION
		"The physical end points for this MTA."
	::= { pktcMtaDevBase 6 }
	
pktcMtaDevEnabled	OBJECT-TYPE
	SYNTAX		TruthValue
	MAX-ACCESS 	read-write
	STATUS		current
	DESCRIPTION
		"The MTA Admin Status of this device, where True(1) means
		the voice feature is enabled and false(2) indicates that
		it is disabled."
	::= { pktcMtaDevBase 7 }

pktcMtaDevTypeIdentifier	OBJECT-TYPE
	SYNTAX		DisplayString
	MAX-ACCESS 	read-only
	STATUS		current
	DESCRIPTION
		"This is a copy of the device type identifier used in the 
		DHCP option 60 exchanged between the MTA and the DHCP server."
	::= { pktcMtaDevBase 8 }

pktcMtaDevProvisioningState	OBJECT-TYPE
	SYNTAX		INTEGER {
				pass(1),
				inProgress(2),
				fail(3)
			}
	MAX-ACCESS 	read-only
	STATUS		current
	DESCRIPTION
		"This object indicates the completion state of the
		provisioning process. Pass or Fail states occur after processing
		of the config file is completed. InProgress occurs from boot
		time until config file processing is complete. Fail state requires 		
		manual intervention."
	::= { pktcMtaDevBase 9 }

pktcMtaDevHttpAccess	OBJECT-TYPE
	SYNTAX		TruthValue
	MAX-ACCESS	read-only
	STATUS		current
	DESCRIPTION
		"This indicates whether HTTP file access is supported for 
		MTA configuration file transfer."
	::= { pktcMtaDevBase 10 }


--
-- The following group describes the security objects in the MTA 
--
pktcMtaDevManufacturerCertificate OBJECT-TYPE
	SYNTAX		X509Certificate
	MAX-ACCESS	read-only
	STATUS		current
	DESCRIPTION
		"ASN.1 DER encoding of the MTA Manufacturer's X.509 public-key
		certificate, called MTA Manufacturer Certificate. It is issued to
		each MTA manufacturer and is installed into each MTA either in the 		
		factory or with a code download. The provisioning server cannot 			
		update this certificate."
	::= { pktcMtaDevSecurity 1 }


pktcMtaDevCertificate OBJECT-TYPE
	SYNTAX		X509Certificate
	MAX-ACCESS	read-only
	STATUS		current
	DESCRIPTION
		"ASN.1 DER encoding of the MTA's X.509 public-key certificate
		issued by the manufacturer and installed into the embedded-MTA in
		the factory. This certificate, called MTA Device Certificate, 
		contains the MTA's MAC address. It cannot be updated by the 
		provisioning server."
	::= { pktcMtaDevSecurity 2 }


pktcMtaDevSignature OBJECT-TYPE
	SYNTAX		OCTET STRING (SIZE (0..256))
	MAX-ACCESS 	read-only
	STATUS		current
	DESCRIPTION
		"A unique signature created by the MTA for each SNMP Inform 
		or SNMP Trap or SNMP GetResponse message exchanged prior to 
		enabling SNMPv3 security ASN.1 encoded Digital signature in 
		the Cryptographic message syntax (includes nonce)."
	::= { pktcMtaDevSecurity 3 }

pktcMtaDevCorrelationId OBJECT-TYPE
	SYNTAX		Integer32
	MAX-ACCESS 	read-only
	STATUS		current
	DESCRIPTION
		"Random value generated by the MTA for use in registration
		authorization. It is for use only in the MTA initialization 
		messages and for MTA configuration file download."
	::= { pktcMtaDevSecurity 4 }

		
pktcMtaDevSecurityTable OBJECT-TYPE
	SYNTAX		SEQUENCE OF PktcMtaDevSecurityEntry
	MAX-ACCESS 	not-accessible
	STATUS		current
	DESCRIPTION
		"Contains per endpoint security information."
	::= { pktcMtaDevSecurity 5 }


pktcMtaDevSecurityEntry OBJECT-TYPE
	SYNTAX		PktcMtaDevSecurityEntry
	MAX-ACCESS 	not-accessible
	STATUS		current
	DESCRIPTION
		"List of security attributes for a single IPCablecom 
		endpoint interface associated with ifType(104)."
	INDEX { ifIndex }
	::= { pktcMtaDevSecurityTable 1 }


PktcMtaDevSecurityEntry ::= SEQUENCE {
	pktcMtaDevServProviderCertificate 	OCTET STRING,
	pktcMtaDevTelephonyCertificate 		OCTET STRING,
	pktcMtaDevKerberosRealm 		OCTET STRING,
	pktcMtaDevKerbPrincipalName 		DisplayString,
	pktcMtaDevServGracePeriod 		Integer32, 
	pktcMtaDevLocalSystemCertificate 	OCTET STRING,
	pktcMtaDevKeyMgmtTimeout1 		Integer32,
	pktcMtaDevKeyMgmtTimeout2 		Integer32
}


 pktcMtaDevServProviderCertificate OBJECT-TYPE
	SYNTAX		X509Certificate
	MAX-ACCESS 	read-write
	STATUS		current
	DESCRIPTION
		"ASN.1 DER encoding of the Telephony Service Provider's X.509
		public-key certificate, called Service Provider Certificate. It 
		serves as the root of the intra-domain trust hierarchy. Each MTA is
		configured with this certificate so that it can authenticate KDCs
		owned by the same service provider. The provisioning server needs
		the ability to update this certificate in the MTAs via both SNMP and
		configuration files."
	::= { pktcMtaDevSecurityEntry 1 }



pktcMtaDevTelephonyCertificate OBJECT-TYPE
	SYNTAX		X509Certificate
	MAX-ACCESS	read-write
	STATUS		current
	DESCRIPTION
		"ASN.1 DER encoding of the MTA's X.509 public-key certificate
		issued by the Service Provider with either the Service Provider 
		CA or a Local System CA. This certificate, called MTA Telephony
		Certificate, contains the same public key as the MTA Device
		Certificate issued by the manufacturer. It is used to authenticate 
		the identity of the MTA to the TGS (during PKINIT exchanges). The
		provisioning server needs the ability to update this certificate in 
		the MTAs via both SNMP and configuration files."
	::= { pktcMtaDevSecurityEntry 2 }


pktcMtaDevKerberosRealm OBJECT-TYPE
	SYNTAX		OCTET STRING (SIZE (0..1280))
	MAX-ACCESS	read-write
	STATUS		current
	DESCRIPTION
		"Specifies a Kerberos realm (i.e. administrative domain), required
		for IPCablecom key management]."
	::= { pktcMtaDevSecurityEntry 3 }


pktcMtaDevKerbPrincipalName OBJECT-TYPE
	SYNTAX		DisplayString (SIZE(0..40))
	MAX-ACCESS 	read-write
	STATUS		current
	DESCRIPTION
		"Kerberos principal name for the Call Agent. This information 
		is required in order for the MTA to obtain Call Agent Kerberos 
		tickets. This principal name does not include the realm, which 
		is specified as a separate field in this configuration file. A 
		Single Kerberos principal name MAY be shared among several 
		Call Agents."
	::= { pktcMtaDevSecurityEntry 4 }


pktcMtaDevServGracePeriod OBJECT-TYPE
	SYNTAX		Integer32 (15..600)
	MAX-ACCESS 	read-write
	STATUS		current
	DESCRIPTION
		"The MTA MUST obtain a new Kerberos ticket (with a PKINIT
		exchange) this many minutes before the old ticket expires. The
		minimum allowable value is 15 mins. The default is 30 mins."
	DEFVAL { 30 }
	::= { pktcMtaDevSecurityEntry 5 }

pktcMtaDevLocalSystemCertificate OBJECT-TYPE
	SYNTAX 		X509Certificate
	MAX-ACCESS 	read-write
	STATUS		current
	DESCRIPTION		
		"Telephony Service Provider CA may delegate the issuance of 
		certificates to a regional Certification Authority called Local 
		System CA (with the corresponding Local System Certificate). 
		This parameter is the ASN.1 DER encoding of the Local System 
		Certificate. It MUST have a non-empty value when the MTA Telephony 
		certificate is signed by a Local System CA. 
		Otherwise, the value MUST be of length 0."
	::= { pktcMtaDevSecurityEntry 6 }

pktcMtaDevKeyMgmtTimeout1 OBJECT-TYPE
	SYNTAX		Integer32 (15..600)
	UNITS		"seconds"
	MAX-ACCESS 	read-write
	STATUS		current
	DESCRIPTION  
		"This timeout applies only when the MTA initiated key management. It 
		is the period during which the MTA will save a nonce (inside the 
		sequence number field) from the sent out AP Request and wait for the 
		matching AP Reply from the CMS."
	::= { pktcMtaDevSecurityEntry 7 } 


pktcMtaDevKeyMgmtTimeout2 OBJECT-TYPE
	SYNTAX		Integer32 (15..600)
	UNITS		"seconds"
	MAX-ACCESS	read-write
	STATUS	current
	DESCRIPTION
		"This timeout applies only when the CMS initiated key management 
		(with a Wake Up or Rekey message). It is the period during which the 
		MTA will save a nonce (inside the sequence number field) from the 
		sent out AP Request and wait for the matching AP Reply from the 
		CMS."
	::= { pktcMtaDevSecurityEntry 8}


pktcMtaDevTgsTable OBJECT-TYPE
	SYNTAX		SEQUENCE OF PktcMtaDevTgsEntry
	MAX-ACCESS 	not-accessible
	STATUS		current
	DESCRIPTION
		"Contains per endpoint Ticket Granting Server information."
	::= { pktcMtaDevSecurity 8 }


pktcMtaDevTgsEntry OBJECT-TYPE
	SYNTAX		PktcMtaDevTgsEntry
	MAX-ACCESS 	not-accessible
	STATUS		current
	DESCRIPTION
		"List of Tgs attributes for a single IPCablecom 
		endpoint interface associated with ifType(104)."
	INDEX 		{ ifIndex, pktcMtaDevTgsIndex }
	::= { pktcMtaDevTgsTable 1 }

PktcMtaDevTgsEntry ::= SEQUENCE {
	pktcMtaDevTgsIndex 	Integer32,
	pktcMtaDevTgsLocation 	DisplayString,
	pktcMtaDevTgsStatus 	RowStatus
}


pktcMtaDevTgsIndex OBJECT-TYPE
	SYNTAX		Integer32
	MAX-ACCESS 	not-accessible
	STATUS		current
	DESCRIPTION
		"Index into the TGS table for TGS locations.
		IfType specifies the endpoint, TgsIndex specifies a TGS."
	::= { pktcMtaDevTgsEntry 1 }


pktcMtaDevTgsLocation OBJECT-TYPE
	SYNTAX		DisplayString (SIZE (0..255))
	MAX-ACCESS 	read-create
	STATUS		current
	DESCRIPTION
		"Name of the TGS - Ticket Granting Server, which is the Kerberos 
		Server. This parameter is a FQDN or Ipv4 address. There may be 
		multiple entries of this type. The order in which these entries 
		are listed is the priority order in which the MTA will attempt to 
		contact them for this endpoint."
	::= { pktcMtaDevTgsEntry 2 }
			
pktcMtaDevTgsStatus	OBJECT-TYPE
	SYNTAX		RowStatus
	MAX-ACCESS	read-create
	STATUS		current
	DESCRIPTION
		"This object contains the Row Status associated with 
		the pktcMtaDevTgsTable."
	::= { pktcMtaDevTgsEntry 3 }
--
-- The following group describes server access and parameters used for
-- initial provisioning and bootstrapping.
--
pktcMtaDevServerBootState OBJECT-TYPE
	SYNTAX 		INTEGER {
				operational(1),
				disabled(2),
				waitingForDhcpOffer(3),
				waitingForDhcpResponse(4),
				waitingForConfig(5),
				refusedByCmts(6),
				other(7),
				unknown(8)
			}
	MAX-ACCESS 	read-only
	STATUS	current
	DESCRIPTION
		"If operational(1), the device has completed loading and
		processing of configuration parameters and the Access Node has
		completed the Registration exchange.
		If disabled(2) then the device was administratively
		disabled, possibly by being refused network access in the
		configuration file.
		If waitingForDhcpOffer(3) then a DHCP Discover has been
		transmitted and no offer has yet been received.
		If waitingForDhcpResponse(4) then a DHCP Request has been
		transmitted and no response has yet been received.
		If waitingForConfig(5) then a request to the config parameter
		server has been made and no response received.
		If refusedByCmts(6) then the Registration Request/Response
		exchange with the Access Node failed."

	::= { pktcMtaDevServer 1 }

pktcMtaDevServerDhcp OBJECT-TYPE
	SYNTAX		DisplayString
	MAX-ACCESS	read-write
	STATUS		current
	DESCRIPTION
		"The IP address or FQDN of the DHCP server that assigned an IP
		address to this device. Returns 0.0.0.0 if DHCP was not
		used for IP address assignment."
	::= { pktcMtaDevServer 2 }

pktcMtaDevServerDns1 OBJECT-TYPE
	SYNTAX		DisplayString
	MAX-ACCESS	read-write
	STATUS		current
	DESCRIPTION
		"The IP address or FQDN of the primary DNS server that resolved
		an IP address for this device."
	::= { pktcMtaDevServer 3 }

pktcMtaDevServerDns2 OBJECT-TYPE
	SYNTAX		DisplayString
	MAX-ACCESS	read-write
	STATUS		current
	DESCRIPTION
		"The IP address or FQDN of the secondary DNS server that resolved an IP 
		address for this device."
	::= { pktcMtaDevServer 4 }

pktcMtaDevConfigFile OBJECT-TYPE	
	SYNTAX		DisplayString
	MAX-ACCESS	read-write
	STATUS		current
	DESCRIPTION
		"The URL of the TFTP/HTTP file for downloading provisioning
		and configuration parameters to this device. Returns NULL if the
		server address is unknown. Supports both TFTP and HTTP"
	::= { pktcMtaDevServer 5 }

pktcMtaDevSnmpEntity OBJECT-TYPE
	SYNTAX		DisplayString
	MAX-ACCESS	read-write
	STATUS		current
	DESCRIPTION
		"The IP address or FQDN of the SNMP entity for provisioning trap 
		handling that assigned an IP address to this device. Returns 
		0.0.0.0 if DHCP was not used for IP address assignment."
	::= { pktcMtaDevServer 6 }
--
-- Event Reporting
--

pktcMtaDevEvControl OBJECT-TYPE
	SYNTAX 		INTEGER {
				resetLog(1),
				useDefaultReporting(2)
			}
	MAX-ACCESS	read-write
	STATUS		current
	DESCRIPTION
		"Setting this object to resetLog(1) empties the event log.
		All data is deleted. Setting it to useDefaultReporting(2)
		returns all event priorities to their factory-default
		reporting. Reading this object always returns
		useDefaultReporting(2)."
	::= { pktcMtaDevEvent 1 }

pktcMtaDevEvSyslog OBJECT-TYPE
	SYNTAX		DisplayString
	MAX-ACCESS	read-write
	STATUS		current
	DESCRIPTION
		"The IP address or FQDN of the Syslog server. If 0.0.0.0, 
		syslog transmission is inhibited."
	::= { pktcMtaDevEvent 2 }

pktcMtaDevEvThrottleAdminStatus OBJECT-TYPE
	SYNTAX 		INTEGER {
				unconstrained(1),
				maintainBelowThreshold(2),
				stopAtThreshold(3),
				inhibited(4)
			}
	MAX-ACCESS	read-write
	STATUS		current
	DESCRIPTION
		"Controls the transmission of traps and syslog messages
		with respect to the trap pacing threshold.
		unconstrained(1) causes traps and syslog messages to be
		transmitted without regard to the threshold settings.
		maintainBelowThreshold(2) causes trap transmission and
		syslog messages to be suppressed if the number of traps
		would otherwise exceed the threshold.
		stopAtThreshold(3) causes trap transmission to cease
		at the threshold, and not resume until directed to do so.
		inhibited(4) causes all trap transmission and syslog
		messages to be suppressed.

		A single event is always treated as a single event for
		threshold counting. That is, an event causing both a trap
		and a syslog message is still treated as a single event.

		Writing to this object resets the thresholding state.

		At initial startup, this object has a default value of
		unconstrained(1)."
	::= { pktcMtaDevEvent 3 }


pktcMtaDevEvThrottleInhibited OBJECT-TYPE
	SYNTAX		TruthValue
	MAX-ACCESS 	read-only
	STATUS		current
	DESCRIPTION
		"If true(1), trap and syslog transmission is currently
		inhibited due to thresholds and/or the current setting of
		pktcMtaDevEvThrottleAdminStatus. In addition, this is set to
		true(1) if transmission is inhibited due to no
		syslog (pktcMtaDevEvSyslog) or trap (pktcMtaDevNmAccessEntry)
		destinations having been set."
	::= { pktcMtaDevEvent 4 }

pktcMtaDevEvThrottleThreshold OBJECT-TYPE
	SYNTAX		Unsigned32
	MAX-ACCESS	read-write
	STATUS		current
	DESCRIPTION
		"Number of trap/syslog events per pktcMtaDevEvThrottleInterval
		to be transmitted before throttling.

		A single event is always treated as a single event for
		threshold counting. That is, an event causing both a trap
		and a syslog message is still treated as a single event.

		At initial startup, this object returns 0."
	::= { pktcMtaDevEvent 5 }



pktcMtaDevEvThrottleInterval OBJECT-TYPE
	SYNTAX		Integer32 (1..2147483647)
	UNITS	 	"seconds"
	MAX-ACCESS	read-write
	STATUS		current
	DESCRIPTION
		"The interval over which the trap threshold applies.
		At initial startup, this object has a value of 1."
	::= { pktcMtaDevEvent 6 }


--
-- The following table controls the reporting of the various classes of
-- events.
--

pktcMtaDevEvControlTable OBJECT-TYPE
	SYNTAX		SEQUENCE OF PktcMtaDevEvControlEntry
	MAX-ACCESS 	not-accessible
	STATUS		current
	DESCRIPTION
		"This table allows control of the reporting of event classes.
		For each event priority, a combination of logging and
		reporting mechanisms may be chosen. The mapping of event types
		to priorities is vendor-dependent. Vendors may also choose to
		allow the user to control that mapping through proprietary means."
	::= { pktcMtaDevEvent 7 }


pktcMtaDevEvControlEntry OBJECT-TYPE
	SYNTAX		PktcMtaDevEvControlEntry
	MAX-ACCESS 	not-accessible
	STATUS		current
	DESCRIPTION
		"Allows configuration of the reporting mechanisms for a
		particular event priority."
	INDEX 		{ pktcMtaDevEvPriority }
	::= { pktcMtaDevEvControlTable 1 }

PktcMtaDevEvControlEntry ::= SEQUENCE {
	pktcMtaDevEvPriority		INTEGER,
	pktcMtaDevEvReporting	 	BITS
}

pktcMtaDevEvPriority OBJECT-TYPE
	SYNTAX 		INTEGER {
				emergency(1),
				alert(2),
				critical(3),
				error(4),
				warning(5),
				notice(6),
				information(7),
				debug(8)
			}
	MAX-ACCESS 	not-accessible
	STATUS		current
	DESCRIPTION
		"The priority level that is controlled by this
		entry. These are ordered from most (emergency) to least (debug)
		critical. Each event with a CM or Access Node has a particular
		priority level associated with it (as defined by the
		vendor). During normal operation no event more critical than
		notice(6) should be generated. Events between warning and
		emergency should be generated at appropriate levels of
		problems (e.g. emergency when the box is about to
		crash)."
	::= { pktcMtaDevEvControlEntry 1 }

pktcMtaDevEvReporting OBJECT-TYPE
	SYNTAX 		BITS {
				local(0),
				traps(1),
				syslog(2)
			}
	MAX-ACCESS	read-write
	STATUS		current
	DESCRIPTION
		"Defines the action to be taken on occurrence of this
		event class. Implementations may not necessarily support
		all options for all event classes, but at minimum must
		allow traps and syslogging to be disabled. If the
		local(0) bit is set, then log to the internal log, if the
		traps(1) bit is set, then generate a trap, if the
		syslog(2) bit is set, then send a syslog message
		(assuming the syslog address is set)."
	::= { pktcMtaDevEvControlEntry 2 }


pktcMtaDevEventTable OBJECT-TYPE
	SYNTAX		SEQUENCE OF PktcMtaDevEventEntry
	MAX-ACCESS 	not-accessible
	STATUS		current
	DESCRIPTION
		"Contains a log of network and device events that may be
		of interest in fault isolation and troubleshooting."
	::= { pktcMtaDevEvent 8 }

pktcMtaDevEventEntry OBJECT-TYPE
	SYNTAX		PktcMtaDevEventEntry
	MAX-ACCESS 	not-accessible
	STATUS		current
	DESCRIPTION
		"Describes a network or device event that may be of
		interest in fault isolation and troubleshooting. Multiple
		sequential identical events are represented by
		incrementing pktcMtaDevEvCounts and setting
		pktcMtaDevEvLastTime to the current time rather than creating
		multiple rows.

		Entries are created with the first occurrance of an event.
		pktcMtaDevEvControl can be used to clear the table.
		Individual events can not be deleted."
	INDEX 	{ pktcMtaDevEvIndex }
	::= { pktcMtaDevEventTable 1 }

PktcMtaDevEventEntry ::= SEQUENCE {
	pktcMtaDevEvIndex	INTEGER,
	pktcMtaDevEvFirstTime	DateAndTime,
	pktcMtaDevEvLastTime	DateAndTime,
	pktcMtaDevEvCounts	Counter32,
	pktcMtaDevEvLevel	INTEGER,
	pktcMtaDevEvId		Unsigned32,
	pktcMtaDevEvText	DisplayString
}



pktcMtaDevEvIndex OBJECT-TYPE
	SYNTAX		INTEGER (1..2147483647)
	MAX-ACCESS 	not-accessible
	STATUS		current
	DESCRIPTION
		"Provides relative ordering of the objects in the event
		log. This object will always increase except when
		(a) the log is reset via pktcMtaDevEvControl,
		(b) the device reboots and does not implement non-volatile
		storage for this log, or (c) it reaches the value 2^31.
		The next entry for all the above cases is 1."
	::= { pktcMtaDevEventEntry 1 }

pktcMtaDevEvFirstTime OBJECT-TYPE
	SYNTAX		DateAndTime
	MAX-ACCESS 	read-only
	STATUS		current
	DESCRIPTION
		"The time that this entry was created."
	::= { pktcMtaDevEventEntry 2 }

pktcMtaDevEvLastTime OBJECT-TYPE
	SYNTAX		DateAndTime
	MAX-ACCESS 	read-only
	STATUS		current
	DESCRIPTION
		"If multiple events are reported via the same entry, the
		time that the last event for this entry occurred,
		otherwise this should have the same value as
		pktcMtaDevEvFirstTime."
	::= { pktcMtaDevEventEntry 3 }

pktcMtaDevEvCounts OBJECT-TYPE
	SYNTAX		Counter32
	MAX-ACCESS 	read-only
	STATUS		current
	DESCRIPTION
		"The number of consecutive event instances reported by
		this entry. This starts at 1 with the creation of this
		row and increments by 1 for each subsequent duplicate event."
	::= { pktcMtaDevEventEntry 4 }

pktcMtaDevEvLevel OBJECT-TYPE
	SYNTAX 		INTEGER {
				critical(1),
				major(2),
				minor(3),
				warning(4),
				information(5),
				notice(6),
				debug(7)
			}
	MAX-ACCESS 	read-only
	STATUS		current
	DESCRIPTION
		"The priority level of this event as defined by the
		vendor. These are ordered from most serious (critical)
		to least serious (debug)."
	::= { pktcMtaDevEventEntry 5 }
--
-- Vendors will provide their own enumerations for the following.
-- The interpretation of the enumeration is unambiguous for a
-- particular value of the vendor's enterprise number in sysObjectID.
--

pktcMtaDevEvId OBJECT-TYPE
	SYNTAX		Unsigned32
	MAX-ACCESS 	read-only
	STATUS		current
	DESCRIPTION
		"For this product, uniquely identifies the type of event
		that is reported by this entry."
	::= { pktcMtaDevEventEntry 6 }

pktcMtaDevEvText OBJECT-TYPE
	SYNTAX		DisplayString
	MAX-ACCESS 	read-only
	STATUS		current
	DESCRIPTION
		"Provides a human-readable description of the event,
		including all relevant context (interface numbers,
		etc.)."
	::= { pktcMtaDevEventEntry 7 }

--
-- notification group is for future extension.
-- 

pktcMtaNotification 	OBJECT IDENTIFIER ::= { pktcMtaMib 2 }
pktcMtaConformance 	OBJECT IDENTIFIER ::= { pktcMtaMib 3 }
pktcMtaCompliances 	OBJECT IDENTIFIER ::= { pktcMtaConformance 1 }
pktcMtaGroups	 	OBJECT IDENTIFIER ::= { pktcMtaConformance 2 }

--
--	Notification Group
--


pktcMtaProvisioningEnrollment NOTIFICATION-TYPE
	OBJECTS { 
		pktcMtaDevHardwareVersion,
		docsDevSwCurrentVers,
		pktcMtaDevTypeIdentifier,
		pktcMtaDevMacAddress,
		pktcMtaDevCorrelationId,
		pktcMtaDevSignature
	}
	STATUS	current
	DESCRIPTION
		"This inform is issued to initiate the IPCablecom 
		process provisioning."
	REFERENCE
		"Inform as defined in RFC 1902"
	::= { pktcMtaNotification 1 }


pktcMtaProvisioningStatus NOTIFICATION-TYPE
	OBJECTS {
		pktcMtaDevMacAddress,
		pktcMtaDevCorrelationId,
		pktcMtaDevSignature,
		pktcMtaDevProvisioningState
	}
	STATUS	current
	DESCRIPTION
		"This inform is issued to confirm completion of the IPCablecom 
		provisioning process, and indicate the completion state."
	REFERENCE
		"Inform as defined in RFC 1902"
	::= { pktcMtaNotification 2 }


-- compliance statements

pktcMtaBasicCompliance MODULE-COMPLIANCE
	STATUS	current
	DESCRIPTION
		"The compliance statement for devices that implement 
		MTA feature."
	MODULE  --pktcMtaMib

-- unconditionally mandatory groups

	MANDATORY-GROUPS {
			pktcMtaGroup
	}

-- units of conformance

OBJECT pktcMtaDevCorrelationId
	MIN-ACCESS read-only
	DESCRIPTION
		"not-accessible when request is SNMP get
		read-only when used in informs during provisioning."

OBJECT pktcMtaDevCertificate 
	MIN-ACCESS read-only
	DESCRIPTION
		"Read-write when request is through configuration file `
		download, otherwise it's a read-only object."

OBJECT pktcMtaDevTelephonyCertificate
	MIN-ACCESS read-only
	DESCRIPTION
		"Read-write when request is through configuration file 
		download, otherwise it's a read-only object."

OBJECT pktcMtaDevServProviderCertificate 
	MIN-ACCESS read-only
	DESCRIPTION
		"Read-write when request is through configuration file 
		download, otherwise it's a read-only object."

OBJECT pktcMtaDevLocalSystemCertificate 
	MIN-ACCESS read-only
	DESCRIPTION
		"Read-write when request is through configuration file 
		download, otherwise it's a read-only object."

OBJECT pktcMtaDevKerberosRealm 
	MIN-ACCESS read-only
	DESCRIPTION
		"Read-write when request is through configuration file 
		download, otherwise it's a read-only object."

OBJECT pktcMtaDevTgsLocation 
	MIN-ACCESS read-only
	DESCRIPTION
		"Read-write when request is through configuration file 
		download, otherwise it's a read-only object."

OBJECT pktcMtaDevKerbPrincipalName 
	MIN-ACCESS read-only
	DESCRIPTION
		"Read-write when request is through configuration file 
		download, otherwise it's a read-only object."

OBJECT pktcMtaDevServGracePeriod 
	MIN-ACCESS read-only
	DESCRIPTION
		"Read-write when request is through configuration file 
		download, otherwise it's a read-only object."
::= { pktcMtaCompliances 3 }


pktcMtaGroup OBJECT-GROUP
	OBJECTS {
		pktcMtaDevResetNow,
		pktcMtaDevSerialNumber,
		pktcMtaDevHardwareVersion,
		pktcMtaDevMacAddress,
		pktcMtaDevFQDN,
		pktcMtaDevEndPntCount,
		pktcMtaDevEnabled,
		pktcMtaDevTypeIdentifier,
		pktcMtaDevProvisioningState,
		pktcMtaDevCertificate,
		pktcMtaDevSignature,
		pktcMtaDevCorrelationId,
		pktcMtaDevManufacturerCertificate,
		pktcMtaDevTelephonyCertificate,
		pktcMtaDevServProviderCertificate,
		pktcMtaDevLocalSystemCertificate,
		pktcMtaDevKerberosRealm,
		pktcMtaDevTgsLocation,
		pktcMtaDevKerbPrincipalName,
		pktcMtaDevServGracePeriod,
		pktcMtaDevKeyMgmtTimeout1,
		pktcMtaDevKeyMgmtTimeout2,
		pktcMtaDevServerBootState,
		pktcMtaDevServerDhcp,
		pktcMtaDevSnmpEntity,
		pktcMtaDevEvControl,
		pktcMtaDevEvSyslog,
		pktcMtaDevEvThrottleAdminStatus,
		pktcMtaDevEvThrottleInhibited,
		pktcMtaDevEvThrottleThreshold,
		pktcMtaDevEvThrottleInterval,
		pktcMtaDevEvReporting,
		pktcMtaDevEvFirstTime,
		pktcMtaDevEvLastTime,
		pktcMtaDevEvCounts,
		pktcMtaDevEvLevel,
		pktcMtaDevEvId,
		pktcMtaDevEvText
	}
	STATUS	current
	DESCRIPTION
		"Group of objects for IPCablecom MTA MIB."
	::= { pktcMtaGroups 1 } 

END
