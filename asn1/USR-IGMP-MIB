USR-IGMP-MIB DEFINITIONS ::= BEGIN
IMPORTS
    OBJECT-TYPE, MODULE-IDENTITY, OBJECT-IDENTITY, NOTIFICATION-TYPE,
    Counter32, Integer32, IpAddress, Gauge32, TimeTicks
        FROM SNMPv2-SMI
    RowStatus, TruthValue, DisplayString
        FROM SNMPv2-TC
    common, UsrDisplayString
        FROM USR-DEFINITIONS-MIB;
usrIgmp  MODULE-IDENTITY
         LAST-UPDATED "200202071020Z"
         ORGANIZATION "CommWorks Corporation, a 3Com Company"
         CONTACT-INFO "Customer Support"
         DESCRIPTION
                 "The commWorks enterprise defined MIB objects
                   for IGMP"
--       REVISION     "200202071020Z"
--       DESCRIPTION "Converted traps to SNMPv2"
    ::= { common 53 }
usrIgmpInterfaceTable OBJECT-TYPE
    SYNTAX     SEQUENCE OF UsrIgmpInterfaceEntry
    MAX-ACCESS not-accessible
    STATUS     current
    DESCRIPTION
            "The (conceptual) table listing the interfaces on which IGMP
            is enabled."
    ::= { usrIgmp 1 }
usrIgmpInterfaceEntry OBJECT-TYPE
    SYNTAX     UsrIgmpInterfaceEntry
    MAX-ACCESS not-accessible
    STATUS     current
    DESCRIPTION
            "An entry (conceptual row) representing an interface on
            which IGMP is enabled."
    INDEX      { usrIgmpInterfaceIfName }
    ::= { usrIgmpInterfaceTable 1 }
UsrIgmpInterfaceEntry ::= SEQUENCE {
    usrIgmpInterfaceIfName                DisplayString,
    usrIgmpInterfaceQueryInterval         Integer32,
    usrIgmpInterfaceStatus                RowStatus,
    usrIgmpInterfaceVersion               INTEGER,
    usrIgmpInterfaceQuerier               IpAddress,
    usrIgmpInterfaceQueryMaxResponseTime  Integer32,
    usrIgmpInterfaceVersion1QuerierTimer  Integer32,                        
    usrIgmpInterfaceWrongVersionQueries   Counter32,                        
    usrIgmpInterfaceJoins                 Counter32,                        
    usrIgmpInterfaceGroups	          Gauge32,
    usrIgmpInterfaceRobustness            Integer32,
    usrIgmpInterfaceMcastFwdEnabled       TruthValue,
    usrIgmpInterfacePushEnabled           TruthValue,
    usrIgmpInterfaceProxyEnabled          TruthValue,
    usrIgmpInterfaceShortPackets          Counter32,
    usrIgmpInterfaceBadChecksum           Counter32,
    usrIgmpInterfaceQueriesReceived       Counter32,
    usrIgmpInterfaceReportsReceived       Counter32,
    usrIgmpInterfaceReportsForKnownGroups Counter32,
    usrIgmpInterfaceReportsSent           Counter32,
    usrIgmpInterfaceWrongVersionReports   Counter32
}
usrIgmpInterfaceIfName OBJECT-TYPE
    SYNTAX     DisplayString (SIZE (1..32))
    MAX-ACCESS not-accessible
    STATUS     current
    DESCRIPTION
            "The interface name for which IGMP is enabled."
::= { usrIgmpInterfaceEntry 1 }
usrIgmpInterfaceQueryInterval OBJECT-TYPE
    SYNTAX     Integer32 (5..65535)
    UNITS      "seconds"
    MAX-ACCESS read-create
    STATUS     current
    DESCRIPTION
            "The frequency at which IGMP Host-Query packets are
            transmitted on this interface."
    DEFVAL     { 125 }
    --CONFIGURABLE
::= { usrIgmpInterfaceEntry 2 }
usrIgmpInterfaceStatus OBJECT-TYPE
    SYNTAX     RowStatus
    MAX-ACCESS read-create
    STATUS     current
    DESCRIPTION
            "The activation of a row enables IGMP on the interface.  The
            destruction of a row disables IGMP on the interface."
    --CONFIGURABLE
::= { usrIgmpInterfaceEntry 3 }
usrIgmpInterfaceVersion OBJECT-TYPE
    SYNTAX     INTEGER { version1(1), version2(2) }
    MAX-ACCESS read-create
    STATUS     current
    DESCRIPTION
            "The version of IGMP which is running on this interface.
            This object can be used to configure a router capable of
            running either value.  For IGMP to function correctly, all   
            routers on a LAN must be configured to run the same version  
            of IGMP on that LAN."                                        
    DEFVAL     { version2 }
    --CONFIGURABLE
::= { usrIgmpInterfaceEntry 4 }
usrIgmpInterfaceQuerier OBJECT-TYPE
    SYNTAX     IpAddress
    MAX-ACCESS read-only
    STATUS     current
    DESCRIPTION
            "The address of the IGMP Querier on the IP subnet to which
            this interface is attached."
::= { usrIgmpInterfaceEntry 5 }
usrIgmpInterfaceQueryMaxResponseTime OBJECT-TYPE
    SYNTAX     Integer32 (1..10)
    UNITS      "seconds"
    MAX-ACCESS read-create
    STATUS     current
    DESCRIPTION
            "The maximum query response time advertised in IGMPv2
            queries on this interface.  Smaller values allow a router to
            prune groups faster."
    DEFVAL     { 10 }
    --CONFIGURABLE                                                    
::= { usrIgmpInterfaceEntry 6 }
usrIgmpInterfaceVersion1QuerierTimer OBJECT-TYPE                            
    SYNTAX     Integer32                                                 
    MAX-ACCESS read-only                                                 
    STATUS     current                                                   
    DESCRIPTION                                                          
            "The time remaining until the host assumes that there are no 
            IGMPv1 routers present on the interface.  While this is      
            non-zero, the host will reply to all queries with version 1  
            membership reports."                                         
::= { usrIgmpInterfaceEntry 7 }                                         
usrIgmpInterfaceWrongVersionQueries OBJECT-TYPE                             
    SYNTAX     Counter32                                                 
    MAX-ACCESS read-only                                                 
    STATUS     current                                                   
    DESCRIPTION                                                          
            "The number of queries received whose IGMP version does not  
            match usrIgmpInterfaceVersion.   IGMP requires that all routers 
            on a LAN be configured to run the same version of IGMP.      
            Thus, if any queries are received with the wrong version,    
            this indicates a configuration error."                       
::= { usrIgmpInterfaceEntry 8 }                                        
usrIgmpInterfaceJoins OBJECT-TYPE                                           
    SYNTAX     Counter32                                                 
    MAX-ACCESS read-only                                                 
    STATUS     current                                                   
    DESCRIPTION                                                          
            "The number of times a group membership has been added on    
            this interface; that is, the number of times an entry for    
            this interface has been added to the Cache Table.  This      
            object gives an indication of the amount of IGMP activity    
            over time."                                                  
::= { usrIgmpInterfaceEntry 9 }                                        
usrIgmpInterfaceGroups OBJECT-TYPE
    SYNTAX     Gauge32
    MAX-ACCESS read-only
    STATUS     current
    DESCRIPTION
            "The current number of entries for this interface in the
            Cache Table."
    ::= { usrIgmpInterfaceEntry 10 }
usrIgmpInterfaceRobustness OBJECT-TYPE
    SYNTAX     Integer32 (1..5)
    MAX-ACCESS read-create
    STATUS     current
    DESCRIPTION
            "The Robustness Variable allows tuning for the expected
            packet loss on a subnet.  If a subnet is expected to be
            lossy, the Robustness Variable may be increased.  IGMP is
            robust to (Robustness Variable-1) packet losses."
    DEFVAL     { 2 }
    --CONFIGURABLE                                                    
    ::= { usrIgmpInterfaceEntry 11 }
usrIgmpInterfaceMcastFwdEnabled OBJECT-TYPE                                          
    SYNTAX     TruthValue                                                 
    MAX-ACCESS read-create                                                 
    STATUS     current                                                   
    DESCRIPTION
            "If enabled Multicast packets will be forwarded on this
             interface."   
    DEFVAL    { true }
    --CONFIGURABLE                                                        
::= { usrIgmpInterfaceEntry 12 }                                        
usrIgmpInterfacePushEnabled OBJECT-TYPE                                          
    SYNTAX     TruthValue                                                 
    MAX-ACCESS read-create                                                 
    STATUS     current                                                   
    DESCRIPTION 
            "If enabled once a Multicast group is learned on this interface  
             it will not be removed even if a report is not received within
             the membership interval." 
    DEFVAL    { false }
    --CONFIGURABLE                         
::= { usrIgmpInterfaceEntry 13 }                                        
usrIgmpInterfaceProxyEnabled OBJECT-TYPE                                          
    SYNTAX     TruthValue                                                 
    MAX-ACCESS read-create                                                 
    STATUS     current                                                   
    DESCRIPTION 
            "If enabled when a Multicast group is learned on this interface  
             it will also be joined as a proxy on the ethernet interface 
             specified in usrIgmpInterfaceProxyIfName."
    DEFVAL    { false }
    --CONFIGURABLE                         
::= { usrIgmpInterfaceEntry 14 }                                        
usrIgmpInterfaceShortPackets OBJECT-TYPE
    SYNTAX     Counter32
    MAX-ACCESS read-only
    STATUS     current
    DESCRIPTION
            "The number of short IGMP packets received on this interface."
::= { usrIgmpInterfaceEntry 15 }
usrIgmpInterfaceBadChecksum OBJECT-TYPE
    SYNTAX     Counter32
    MAX-ACCESS read-only
    STATUS     current
    DESCRIPTION
            "The number of IGMP packets with bad checksum received on 
             this interface."
::= { usrIgmpInterfaceEntry 16 }
usrIgmpInterfaceQueriesReceived OBJECT-TYPE
    SYNTAX     Counter32
    MAX-ACCESS read-only
    STATUS     current
    DESCRIPTION
            "The number of queries received on this interface."
::= { usrIgmpInterfaceEntry 17 }
usrIgmpInterfaceReportsReceived OBJECT-TYPE
    SYNTAX     Counter32
    MAX-ACCESS read-only
    STATUS     current
    DESCRIPTION
            "The number of reports received on this interface."
::= { usrIgmpInterfaceEntry 18 }
usrIgmpInterfaceReportsForKnownGroups OBJECT-TYPE
    SYNTAX     Counter32
    MAX-ACCESS read-only
    STATUS     current
    DESCRIPTION
            "The number of reports for known groups received on this 
             interface."
::= { usrIgmpInterfaceEntry 19 }
usrIgmpInterfaceReportsSent OBJECT-TYPE
    SYNTAX     Counter32
    MAX-ACCESS read-only
    STATUS     current
    DESCRIPTION
            "The number of reports sent on this interface."
::= { usrIgmpInterfaceEntry 20 }
usrIgmpInterfaceWrongVersionReports OBJECT-TYPE
    SYNTAX     Counter32
    MAX-ACCESS read-only
    STATUS     current
    DESCRIPTION
            "The number of wrong version reports received on this interface."
::= { usrIgmpInterfaceEntry 21 }
--
--  The IGMP Cache Table
--
usrIgmpCacheTable OBJECT-TYPE
    SYNTAX     SEQUENCE OF UsrIgmpCacheEntry
    MAX-ACCESS not-accessible
    STATUS     current
    DESCRIPTION
            "The (conceptual) table listing the IP multicast groups for
            which there are members on a particular interface."
::= { usrIgmp 2 }
usrIgmpCacheEntry OBJECT-TYPE
    SYNTAX     UsrIgmpCacheEntry
    MAX-ACCESS not-accessible
    STATUS     current
    DESCRIPTION
            "An entry (conceptual row) in the usrIgmpCacheTable."
    INDEX      { usrIgmpCacheAddress, usrIgmpCacheIfName }
::= { usrIgmpCacheTable 1 }
UsrIgmpCacheEntry ::= SEQUENCE {
    usrIgmpCacheAddress            IpAddress,
    usrIgmpCacheIfName             DisplayString,
    usrIgmpCacheSelf               Integer32,
    usrIgmpCacheLastReporter       IpAddress,
    usrIgmpCacheUpTime             TimeTicks,
    usrIgmpCacheExpiryTime         TimeTicks,
    usrIgmpCacheStatus             RowStatus,
    usrIgmpCacheVersion1HostTimer  Integer32                                
}
usrIgmpCacheAddress OBJECT-TYPE
    SYNTAX     IpAddress
    MAX-ACCESS not-accessible
    STATUS     current
    DESCRIPTION
            "The IP multicast group address for which this entry
            contains information."
::= { usrIgmpCacheEntry 1 }
usrIgmpCacheIfName OBJECT-TYPE
    SYNTAX     DisplayString (SIZE (1..32))
    MAX-ACCESS not-accessible
    STATUS     current
    DESCRIPTION
            "The interface name for which this entry contains 
            information for an IP multicast group address."
::= { usrIgmpCacheEntry 2 }
usrIgmpCacheSelf OBJECT-TYPE
    SYNTAX     Integer32
    MAX-ACCESS read-create
    STATUS     current
    DESCRIPTION
            "An indication of whether the local system is a member of
            or proxying this group address on this interface."
::= { usrIgmpCacheEntry 3 }
usrIgmpCacheLastReporter OBJECT-TYPE
    SYNTAX     IpAddress
    MAX-ACCESS read-only
    STATUS     current
    DESCRIPTION
            "The IP address of the source of the last membership report
            received for this IP Multicast group address on this
            interface.  If no membership report has been received, this
            object has the value 0.0.0.0."
::= { usrIgmpCacheEntry 4 }
usrIgmpCacheUpTime OBJECT-TYPE
    SYNTAX     TimeTicks
    MAX-ACCESS read-only
    STATUS     current
    DESCRIPTION
            "The time since the system joined this group address, or
            zero if the system is not currently a member."
::= { usrIgmpCacheEntry 5 }
usrIgmpCacheExpiryTime OBJECT-TYPE
    SYNTAX     TimeTicks
    MAX-ACCESS read-only
    STATUS     current
    DESCRIPTION
            "The minimum amount of time remaining before this entry will
            be aged out."
::= { usrIgmpCacheEntry 6 }
usrIgmpCacheStatus OBJECT-TYPE
    SYNTAX     RowStatus
    MAX-ACCESS read-create
    STATUS     current
    DESCRIPTION
            "The status of this entry."
    --CONFIGURABLE                                                        
::= { usrIgmpCacheEntry 7 }
usrIgmpCacheVersion1HostTimer OBJECT-TYPE                                   
    SYNTAX     Integer32
    UNITS      "seconds"
    MAX-ACCESS read-only
    STATUS     current
    DESCRIPTION
            "The time remaining until the local router will assume that
            there are no longer any IGMP version 1 members on the IP     
            subnet attached to this interface.  Upon hearing any IGMPv1
            Membership Report, this value is reset to the group
            membership timer.  While this time remaining is non-zero,
            the local router ignores any IGMPv2 Leave messages for this  
            group that it receives on this interface."                   
::= { usrIgmpCacheEntry 8 }
usrIgmpProxyInterface OBJECT-TYPE
    SYNTAX     UsrDisplayString (SIZE (1..32))
    MAX-ACCESS read-create                                                 
    STATUS     current                                                   
    DESCRIPTION 
            "The name of the interface on which all groups learned 
             on the wan connections will be proxied onto if 
             usrIgmpInterfaceProxyEnabled is enabled."
    --CONFIGURABLE                         
::= { usrIgmp 3 }
usrIgmpHeartbeatGroup OBJECT IDENTIFIER ::= { usrIgmp 4 }
usrIgmpHeartbeatInterface OBJECT-TYPE
    SYNTAX     UsrDisplayString (SIZE (1..32))
    MAX-ACCESS read-write                                                 
    STATUS     current                                                   
    DESCRIPTION 
            "The name of the interface on which to monitor
             multicast traffic for group specified in
             usrIgmpHeartbeatGroupAddr."
    --CONFIGURABLE                         
::= { usrIgmpHeartbeatGroup 1 }
usrIgmpHeartbeatGroupAddr OBJECT-TYPE
    SYNTAX     IpAddress
    MAX-ACCESS read-write
    STATUS     current
    DESCRIPTION
            "The multicast group being monitored."
    --CONFIGURABLE                         
::= { usrIgmpHeartbeatGroup 2 }
usrIgmpHeartbeatTime OBJECT-TYPE                                   
    SYNTAX     Integer32 (0..65535)
    UNITS      "seconds"
    MAX-ACCESS read-write
    STATUS     current
    DESCRIPTION
            "The time interval to monitor multicast traffic."
    DEFVAL     { 60 }
    --CONFIGURABLE                                                    
::= { usrIgmpHeartbeatGroup 3 }
usrIgmpHeartbeatWindow OBJECT-TYPE
    SYNTAX     Integer32 (0..255)
    MAX-ACCESS read-write
    STATUS     current
    DESCRIPTION
            "The number of usrIgmpHeartbeatTime intervals to monitor 
             multicast traffic on."
    DEFVAL     { 5 }
    --CONFIGURABLE                                                    
::= { usrIgmpHeartbeatGroup 4 }
usrIgmpHeartbeatThreshold OBJECT-TYPE
    SYNTAX     Integer32 (0..65535)
    MAX-ACCESS read-write
    STATUS     current
    DESCRIPTION
            "If multicast traffic in not received for this number or 
             more intervals a SNMP trap is issued."
    DEFVAL     { 3 }
    --CONFIGURABLE                                                    
::= { usrIgmpHeartbeatGroup 5 }
usrIgmpHeartbeatStatus OBJECT-TYPE
   SYNTAX      INTEGER {
                enabled(1),
                disabled(2),
                delete(3)
                }
   MAX-ACCESS  read-write
   STATUS      current
   DESCRIPTION
           "This object is used to allow the system to start or
            or stop the IGMP heartbeat feature.  This heartbeat
            feature is used to monitor multicast traffic for a 
            particular multicast group (usrIgmpHeartbeatGroupAddr)
            on a specified interface (usrIgmpHeartbeatInterface).  
            Traffic is monitored on this interface for 
            usrIgmpHeartbeatWindowSize usrIgmpHeartbeatTime intervals.
            During each time interval it is determined if multicast
            traffic was received.  After usrIgmpHeartbeatWindowSize
            time intervals the number of times we did NOT receive 
            traffic is compared against usrIgmpHeartbeatThreshold. If
            the number of intervals we did NOT receive traffic is 
            equal to or higher than usrIgmpHeartbeatThreshold a SNMP 
            trap is issued." 
    --CONFIGURABLE                                                    
::= { usrIgmpHeartbeatGroup 6 }
usrIgmpTraps OBJECT IDENTIFIER ::= { usrIgmp 5 }
usrIgmpTrapsV2 OBJECT-IDENTITY
   STATUS       current
   DESCRIPTION
           " The events for IGMP"
::= { usrIgmpTraps 0 }
usrIgmpHeartbeatTrap NOTIFICATION-TYPE
   OBJECTS { usrIgmpHeartbeatThreshold }
   STATUS       current
   DESCRIPTION
	   "A usrIgmpHeartbeatTrap signifies that the configured 
        number of time intervals have occurred without receiving 
        multicast traffic for the configured group."
    --#TYPE     "Warning"
    --#SUMMARY  "IGMP Heartbeat Threshold %d Reached"
    --#ARGUMENTS { 0 }
    --#SEVERITY MINOR
    --#STATE    OPERATIONAL
    --#PROBABLECAUSE "Network Error"
::= { usrIgmpTrapsV2 1 }
usrIgmpTrafficAffectInactivity OBJECT-TYPE
   SYNTAX      INTEGER {
                enabled(1),
                disabled(2)
                }
   MAX-ACCESS  read-write
   STATUS      current
   DESCRIPTION
           "This object is used to allow the system to treat IGMP traffic 
	    over PPP links as background traffic. If this switch is enabled 
	    then IGMP traffic will be treated as background traffic and idle 
	    timeout functionality will ignore this traffic. If this switch 
	    is disabled the IGMP multicast traffic will be treated as regular
	    traffic and connection will not be dropped." 
    --CONFIGURABLE                                                    
::= { usrIgmp 6 }
END         -- End of USR-IGMP-MIB DEFINITIONS
