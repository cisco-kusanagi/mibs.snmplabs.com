-- extracted from draft-ietf-ips-isns-mib-08.txt
-- at Sun Jan 29 06:14:56 2006

   ISNS-MGMT-MIB DEFINITIONS ::= BEGIN 
   --  
   --  
   IMPORTS 
       MODULE-IDENTITY, 
       OBJECT-TYPE, 
       NOTIFICATION-TYPE, 
       Gauge32, 
       Unsigned32, 
       transmission 
            FROM SNMPv2-SMI 
    
       OBJECT-GROUP, 
       MODULE-COMPLIANCE, 
       MODULE-COMPLIANCE, 
       NOTIFICATION-GROUP 
            FROM SNMPv2-CONF 
    
       TEXTUAL-CONVENTION, 
       TimeStamp, 
       TruthValue, 
       StorageType 
            FROM SNMPv2-TC 
    
   --  From RFC 2021 
       ZeroBasedCounter32 
            FROM RMON2-MIB 
    
   --  From RFC 2856 
       ZeroBasedCounter64 
            FROM HCNUM-TC 
    
   --  From RFC 2863 
       InterfaceIndexOrZero 
            FROM IF-MIB 
    
   --  From RFC 3411 
       SnmpAdminString 
            FROM SNMP-FRAMEWORK-MIB 
    
   --  From RFC 4001 
       InetAddressType, 
       InetAddress, 
       InetPortNumber 
            FROM INET-ADDRESS-MIB 
    
   Gibbons                Expires July 2006                         7 
   Internet Draft              iSNS MIB                   January 2006 

    
   --  From RFC 4044 
       FcNameIdOrZero,  
       FcAddressIdOrZero  
            FROM FC-MGMT-MIB  
    
   --  From RFC 4133 
       PhysicalIndexOrZero 
            FROM ENTITY-MIB 
         ; 
    
   isnsMgmtMIB  MODULE-IDENTITY 
         LAST-UPDATED "200601310000Z" 
         ORGANIZATION "IETF IPS Working Group" 
         CONTACT-INFO " 
           Attn: Kevin Gibbons 
                 McDATA Corporation 
                 4555 Great America Pkwy 
                 Santa Clara, CA 95054-1208 
                 USA 
                 Tel: +1 408 567-5765 
                 Fax: +1 408 567-0063 
                 Email: kevin.gibbons@mcdata.com 
    
                 G.D. Ramkumar 
                 McDATA Corporation 
                 4555 Great America Pkwy 
                 Santa Clara, CA 95054-1208 
                 USA 
                 Tel: +1 408-567-5614 
                 Fax: +1 408 567-0063 
                 Email: gramkumar@stanfordalumni.org 
    
                 Scott Kipp 
                 McDATA Corporation 
                 4 McDATA Pkwy 
                 Broomfield, CO 80021 
                 USA 
                 Tel: +1 720-558-3452 
                 Fax: +1 720-558-8999 
                 Email: scott.kipp@mcdata.com 
                       " 
    
            DESCRIPTION  
                    "This module defines management information  
                     specific to internet Storage Name Service  
                     (iSNS) management. 
        
                     Copyright (C) The Internet Society 2006.   
                     This version of this MIB module is part 
                     of RFC XXXX; see the RFC itself for full  
                     legal notices."  
    
   Gibbons                Expires July 2006                         8 
   Internet Draft              iSNS MIB                   January 2006 

        
            REVISION    "200601310000Z"  
    
            DESCRIPTION   
                     "Initial version of iSNS Management Module. 
                      This MIB published as RFC XXXX."  
        
      -- RFC Ed.: replace XXXX with RFC number assigned to  
      -- this document 
              ::=  { transmission 4371 } 
      --      ::=  { transmission XXXX } 
      -- RFC Ed.: enter the IANA assigned number to this MIB  
      -- for YYYY ??? 
        
      --  
      --  Textual Conventions  
      --  
    
   IsnsDiscoveryDomainSetId ::= TEXTUAL-CONVENTION 
       STATUS         current 
       DESCRIPTION 
   "The unique Discovery Domain Set Identifier associated with a 
    Discovery Domain Set (DDS)." 
       REFERENCE      "RFC 4171, Section 6" 
       SYNTAX         Unsigned32 ( 1 .. 4294967295 ) 
    
   IsnsDdsStatusId ::= TEXTUAL-CONVENTION 
       STATUS         current 
       DESCRIPTION 
   "The bitmap indicating the status of a Discovery Domain 
    Set (DDS) registered in the iSNS. 
                 Bit           Status 
              ---------       --------- 
                  0            enabled 
    
    If bit(0) is set to true then the DDS is Enabled.  Otherwise 
    the DDS is disabled." 
       REFERENCE      "RFC 4171, Section 6" 
       SYNTAX         BITS {  
                         enabled(0) 
                           } 
    
   IsnsDiscoveryDomainId ::= TEXTUAL-CONVENTION 
       STATUS         current 
       DESCRIPTION 
   "The unique Discovery Domain Identifier (DD_ID) associated 
    with each Discovery Domain (DD).  This can be used to 
    uniquely index and reference a DD.  New storage nodes  
    are automatically added to the default DD if 
    isnsSrvrInstDfltDdDdsStatus is set to inDefaultDdAndDds." 
       REFERENCE      "RFC 4171, Section 6" 
       SYNTAX         Unsigned32 ( 1 .. 4294967295 ) 
    
   Gibbons                Expires July 2006                         9 
   Internet Draft              iSNS MIB                   January 2006 

    
   DdFeatureBitmapId ::= TEXTUAL-CONVENTION 
       STATUS         current 
       DESCRIPTION 
   "The bitmap indicating the types of features 
    each Discovery Domain (DD) has. 
                 Bit           Status 
              ---------       --------- 
                  0            Boot List 
     
    Boot List: this feature indicates that the targets 
    in this DD provide boot capabilities for the member 
    initiators.  Setting the bit to true (1) indicates 
    the feature is enabled.  Otherwise it is disabled." 
       REFERENCE      "RFC 4171, Section 6" 
       SYNTAX         BITS {  
                         bootlist(0) 
                           } 
    
   IsnsDdDdsModificationBitmap ::= TEXTUAL-CONVENTION 
       STATUS         current 
       DESCRIPTION 
   "The methods that can be used to modify the Discovery 
    Domain and Discovery Domain Sets in the iSNS Server 
    instance. Although this MIB does not allow modification 
    of DD's and DDS's, SNMP may be used to modify them via 
    another MIB. 
    
        Bit Field            Flag Description 
        ---------   ------------------------------------ 
            0       SNMP protocol is allowed to modify DD's/DDS's 
            1       Control Nodes are allowed 
            2       Target iSCSI Nodes are allowed 
            3       Initiator iSCSI Nodes are allowed 
            4       Target iFCP Ports are allowed 
            5       Initiator iFCP Ports are allowed 
    
    Setting a bit to true (1) indicates the feature is 
    enabled.  Otherwise it is disabled." 
       REFERENCE      "RFC 4171, Section 2.4" 
       SYNTAX         BITS {  
                         snmpEnabled(0), 
                         controlNode(1), 
                         targetIscsiNode(2), 
                         initiatorIscsiNode(3), 
                         targetIfcpNode(4), 
                         initiatorIfcpNode(5) 
                           } 
    
   IsnsEntityIndexId ::= TEXTUAL-CONVENTION 
       STATUS         current 
       DESCRIPTION 
    
   Gibbons                Expires July 2006                        10 
   Internet Draft              iSNS MIB                   January 2006 

   "This textual convention is used as an identifier for 
    the unique integer Entity Index associated with a storage 
    entity that is registered in an iSNS Server.  The index 
    is unique within an iSNS Server instance." 
       REFERENCE      "RFC 4171, Section 6" 
       SYNTAX         Unsigned32 ( 1 .. 4294967295 ) 
    
   IsnsEntityProtocolId ::= TEXTUAL-CONVENTION 
       STATUS         current 
       DESCRIPTION 
   "The type of protocol that is supported by this entity. 
    
              Type Value       Entity Type 
              ----------       ----------- 
                 1             No Protocol 
                 2             iSCSI 
                 3             iFCP 
               All Others      As in the iSNS Specification 
   " 
       REFERENCE      "RFC 4171, Section 6" 
       SYNTAX         INTEGER { noProtocol(1), 
                                iSCSI(2), 
                                iFCP(3) } 
    
   IsnsPortalGroupIndexId ::= TEXTUAL-CONVENTION 
       STATUS         current 
       DESCRIPTION 
   "The identifier for the unique integer Portal Group Index 
    associated with a iSNS registered Portal Group object." 
       REFERENCE      "RFC 4171, Section 6" 
       SYNTAX         Unsigned32 ( 1 .. 4294967295 ) 
    
   IsnsPortalIndexId ::= TEXTUAL-CONVENTION 
       STATUS         current 
       DESCRIPTION 
   "The identifier for the unique integer Portal Index 
    associated with a storage portal." 
       REFERENCE      "RFC 4171, Section 6" 
       SYNTAX         Unsigned32 ( 1 .. 4294967295 ) 
    
   IsnsPortalPortTypeId ::= TEXTUAL-CONVENTION 
       STATUS         current 
       DESCRIPTION 
   "The UDP or TCP port type being used by a Portal for an 
    Entity." 
       REFERENCE      "RFC 4171, Section 6" 
       SYNTAX         INTEGER { udp(1), tcp(2) } 
    
   IsnsPortalGroupTagIdOrZero ::= TEXTUAL-CONVENTION 
       STATUS         current 
       DESCRIPTION 
   "The Portal Group Tag (PGT) TC for iSCSI Portal Group 
    
   Gibbons                Expires July 2006                        11 
   Internet Draft              iSNS MIB                   January 2006 

    objects registered in the iSNS.  The value of zero 
    indicates a NULL value, or no association, between the 
    associated Portal and iSCSI Node." 
       REFERENCE      "RFC 4171, Section 6" 
       SYNTAX         Unsigned32 ( 0 .. 65535 ) 
    
   IsnsPortalSecurityBitmapId ::= TEXTUAL-CONVENTION 
       STATUS         current 
       DESCRIPTION 
   "Indicates security attribute settings for the Portal as 
    registered in the Portal Security Bitmap attribute.  The 
    valid bit must be set in order for this attribute to contain 
    valid information.  The definition of the bitmap is based on 
    the iSNS Specification [iSNS].  The representation of each 
    bit setting (0 or 1) is indicated below. 
    
        Bit Field            Flag Description 
        ---------   ------------------------------------ 
           0        1 = Tunnel Mode Preferred; 0 = No Preference 
           1        1 = Transport Mode Preferred; 0 = No Preference 
           2        1 = PFS Enabled; 0 = PFS Disabled 
           3        1 = Aggressive Mode Enabled; 0 = Disabled 
           4        1 = Main Mode Enabled; 0 = MM Disabled 
           5        1 = IKE/IPSec Enabled; 0 = IKE/IPSec Disabled 
           6        1 = Bitmap VALID; 0 = INVALID 
    
   " 
       REFERENCE      "RFC 4171, Section 6" 
       SYNTAX        BITS {  
                         tunnelModePreferred(0), 
                         transportModePreferred(1), 
                         pfsEnabled(2), 
                         agressiveModeEnabled(3), 
                         mainModeEnabled(4), 
                         ikeIpsecEnabled(5), 
                         bitmapVALID(6) 
                          } 
    
   IsnsNodeIndexId ::= TEXTUAL-CONVENTION 
       STATUS         current 
       DESCRIPTION 
   "The identifier for the unique integer Node Index associated   
    with a storage node.  In order to support objects that have 
    key identifiers whose maximum length is longer than the  
    maximum SNMP supported length, the iSNS server provides  
    secondary non-zero integer index identifiers.  These indexes 
    SHALL be persistent for as long as the server is active. 
    Furthermore, index values for recently deregistered objects 
    SHOULD NOT be reused in the short term." 
       REFERENCE      "RFC 4171, Section 6" 
       SYNTAX         Unsigned32 ( 1 .. 4294967295 ) 
    
    
   Gibbons                Expires July 2006                        12 
   Internet Draft              iSNS MIB                   January 2006 

   IsnsNodeIndexIdOrZero ::= TEXTUAL-CONVENTION 
       STATUS         current 
       DESCRIPTION 
   "The identifier for the unique integer Node Index associated   
    with a storage node, or the value zero.  In order to support 
    objects that have key identifiers whose maximum length is  
    longer than the maximum SNMP supported length, the iSNS  
    server provides secondary non-zero integer index identifiers. 
    These indexes SHALL be persistent for as long as the server 
    is active. Furthermore, index values for recently deregistered 
    objects SHOULD NOT be reused in the short term." 
       REFERENCE      "RFC 4171, Section 6" 
       SYNTAX         Unsigned32 ( 0 .. 4294967295 ) 
    
   IsnsNodeTypeId ::= TEXTUAL-CONVENTION 
       STATUS         current 
       DESCRIPTION 
   "The Node Type bit-map defines the functions of this node.  
    The definitiions of each setting are defined in the iSNS 
    Specification [iSNS]. 
                 Bit          Node Type 
              ---------       --------- 
                 0            Control 
                 1            Initiator 
                 2            Target 
   " 
       REFERENCE      "RFC 4171, Section 6" 
       SYNTAX         BITS {  
                         control(0), 
                         initiator(1), 
                         target(2) 
                           } 
    
   IsnsCosBitmapId ::= TEXTUAL-CONVENTION 
       STATUS         current 
       DESCRIPTION 
   "This bit-map indicates the Fibre Channel Class of Service 
    types that are supported by the registered port. 
    
        Bit Field          Flag Description 
        ---------          ---------------- 
           0             Fibre Channel Class 3 Supported   
           1             Fibre Channel Class 2 Supported 
    
    Setting a bit to true (1) indicates the class of service is 
    supported." 
       REFERENCE      "RFC 4171, Section 6" 
       SYNTAX         BITS {  
                         class3(0), 
                         class2(1) 
                           } 
    
    
   Gibbons                Expires July 2006                        13 
   Internet Draft              iSNS MIB                   January 2006 

   IsnsScnBitmapId ::= TEXTUAL-CONVENTION 
       STATUS         current 
       DESCRIPTION 
   "The State Change Notification (SCN) bitmap for a node as 
    defined in the iSNS Specification [iSNS].  A set bit (1) 
    indicates the type of SCN for the bitmap as follows: 
    
        Bit Field          Flag Description 
        ---------          ---------------- 
           0               INITIATOR AND SELF INFORMATION ONLY 
           1               TARGET AND SELF INFORMATION ONLY  
           2               MANAGEMENT REGISTRATION/SCN 
           3               REGISTERED OBJECT REMOVED 
           4               REGISTERED OBJECT ADDED 
           5               REGISTERED OBJECT UPDATED 
           6               DD/DDS MEMBER REMOVED (MGT REG/SCN 
                             ONLY) 
           7               DD/DDS MEMBER ADDED (MGT REG/SCN 
                             ONLY) 
   " 
       REFERENCE      "RFC 4171, Section 6" 
       SYNTAX         BITS {  
                         initiatorAndSelfOnly(0), 
                         targetAndSelfOnly(1), 
                         managementRegistrationScn(2), 
                         registeredObjectRemoved(3), 
                         registeredObjectAdded(4), 
                         registeredObjectUpdated(5), 
                         ddOrDdsMemberRemoved(6), 
                         ddOrDdsMemberAdded(7) 
                           } 
    
   IsnsSrvrDscvryMthdId ::= TEXTUAL-CONVENTION 
       STATUS         current 
       DESCRIPTION 
   "This bitamp is used to indicate the iSNS Server discovery 
    methods that are supported and enabled on an iSNS Server.  
    The options are DHCP, SLP, multicast group iSNS heartbeat, 
    broadcast group iSNS heartbeat, configured server list, and 
    other.  The iSNS Server may also support additional discovery 
    methods not indicated.  The bitmap also is used to indicate 
    the type of discovery being used by an iSNS Client instance.  
    If being used, the configured server list for a specific iSNS 
    client is specified in isnsClntSrvrCfgTable table.  If used, 
    the multicast group is specified in isnsClntInstDiscMcGrp." 
       SYNTAX         BITS { 
                    dhcp(0), 
                    slp(1), 
                    multicastGroupHb(2), 
                    broadcastHb(3), 
                    cfgdServerList(4), 
                    other(5) 
    
   Gibbons                Expires July 2006                        14 
   Internet Draft              iSNS MIB                   January 2006 

                               } 
    
   -- 
   -- Internet Storage Name Service Management 
   -- 
    
   isnsObj                     OBJECT IDENTIFIER ::= 
                                   { isnsMgmtMIB 1 } 
   isnsConformance             OBJECT IDENTIFIER ::= 
                                   { isnsMgmtMIB 2 } 
    
   -- 
   -- iSNS Server instance managed objects -------------------- 
   -- 
    
   isnsSrvrInfo OBJECT IDENTIFIER ::= { isnsObj 1 } 
    
   isnsSrvrInstTable           OBJECT-TYPE 
       SYNTAX                  SEQUENCE OF IsnsSrvrInstEntry 
       MAX-ACCESS              not-accessible 
       STATUS                  current 
       DESCRIPTION 
   "This table provides a list of the iSNS Server instances 
    that are managed through the same SNMP context." 
       ::= { isnsSrvrInfo 1 } 
    
   isnsSrvrInstEntry           OBJECT-TYPE 
       SYNTAX                  IsnsSrvrInstEntry 
       MAX-ACCESS              not-accessible 
       STATUS                  current 
       DESCRIPTION 
   "This is a row in the iSNS Server instance table.  The number 
    of rows is dependent on the number of iSNS Server instances 
    that are being managed through same SNMP context." 
       INDEX   { isnsSrvrInstIndex } 
       ::= { isnsSrvrInstTable 1 } 
    
   IsnsSrvrInstEntry ::= 
       SEQUENCE {  
          isnsSrvrInstIndex              Unsigned32, 
          isnsSrvrInstName               SnmpAdminString, 
          isnsSrvrInstIsnsVersion        Unsigned32, 
          isnsSrvrInstVendorInfo         SnmpAdminString, 
          isnsSrvrInstPhyIndex           Unsigned32, 
          isnsSrvrInstTcpPort            InetPortNumber, 
          isnsSrvrInstUdpPort            InetPortNumber, 
          isnsSrvrInstDiscontinuityTime  TimeStamp, 
          isnsSrvrInstRole               INTEGER, 
          isnsSrvrInstDiscMthdsEnbld     IsnsSrvrDscvryMthdId, 
          isnsSrvrInstDiscMcGrpType      InetAddressType, 
          isnsSrvrInstDiscMcGrp          InetAddress, 
          isnsSrvrInstCntrlNodeAuth      INTEGER, 
    
   Gibbons                Expires July 2006                        15 
   Internet Draft              iSNS MIB                   January 2006 

          isnsSrvrInstEsiNonRespThrshld  Unsigned32, 
          isnsSrvrInstEnblCntrlNdeMgtScn TruthValue, 
          isnsSrvrInstDfltDdDdsStatus    INTEGER,  
          isnsSrvrInstUpdateDdDdsSpprtd  
   IsnsDdDdsModificationBitmap, 
          isnsSrvrInstUpdateDdDdsEnbld   
   IsnsDdDdsModificationBitmap 
                } 
    
   isnsSrvrInstIndex           OBJECT-TYPE 
       SYNTAX                  Unsigned32 ( 1 .. 4294967295 ) 
       MAX-ACCESS              not-accessible 
       STATUS                  current 
       DESCRIPTION 
   "This managed object uniquely identifies the iSNS Server being 
    managed by the SNMP context, and is the key for this table.  
    This is an instance index for each iSNS Server being managed.  
    The value of this managed object is used elsewhere in the MIB 
    to reference specific iSNS Servers." 
       ::= { isnsSrvrInstEntry 1 } 
    
   isnsSrvrInstName            OBJECT-TYPE 
       SYNTAX                  SnmpAdminString (SIZE (0..255)) 
       MAX-ACCESS              read-only 
       STATUS                  current 
       DESCRIPTION 
   "A non-unique name that can be assigned to the iSNS Server 
    instance.  If not configured, the value is an empty string." 
       ::= { isnsSrvrInstEntry 2 } 
    
   isnsSrvrInstIsnsVersion     OBJECT-TYPE 
       SYNTAX                  Unsigned32 ( 0 .. 65535 ) 
       MAX-ACCESS              read-only 
       STATUS                  current 
       DESCRIPTION  
   "The iSNS version value as contained in messages received 
    from the current primary server.  The header of each iSNSP 
    message contains the iSNS version of the sender.  If 
    unknown the reported value is 0." 
       REFERENCE               "draft-ietf-ips-iSNS-22.txt" 
       DEFVAL                  { 1 } 
       ::= { isnsSrvrInstEntry 3 } 
    
   isnsSrvrInstVendorInfo      OBJECT-TYPE 
       SYNTAX                  SnmpAdminString (SIZE (0..255)) 
       MAX-ACCESS              read-only 
       STATUS                  current 
       DESCRIPTION 
   "If this server instance is utilizing the product of a 
    particular 'vendor', then this managed object contains that 
    vendor's name and version.  Otherwise, it contains the empty 
    string.  The format of the string is as follows: Vendor Name, 
    
   Gibbons                Expires July 2006                        16 
   Internet Draft              iSNS MIB                   January 2006 

    Vendor Version, Vendor Defined Information. 
    
          Field           Description 
        ---------       ---------------- 
       Vendor Name      The name of the vendor (if one exists) 
       Vendor Version   The version of the vendor product 
       Vendor Defined   This follows the second comma in the 
                        string, if one exists, and is vendor 
                        defined 
   " 
       ::= { isnsSrvrInstEntry 4 } 
    
   isnsSrvrInstPhyIndex        OBJECT-TYPE 
       SYNTAX                  Unsigned32 (0..2147483647) 
       MAX-ACCESS              read-only 
       STATUS                  current 
       DESCRIPTION 
   "An index indicating the location of this iSNS Server within 
    a larger entity, if one exists.  If the iSNS Server instance 
    is not part of a larger entity, then the value is 0." 
       REFERENCE               "draft-ietf-ips-iSNS-22.txt" 
       ::= { isnsSrvrInstEntry 5 } 
    
   isnsSrvrInstTcpPort         OBJECT-TYPE 
       SYNTAX                  InetPortNumber 
       MAX-ACCESS              read-only 
       STATUS                  current 
       DESCRIPTION 
   "Indicates the TCP port this iSNS instance is accepting 
    iSNSP messages on, generally the iSNS well known port.  
    The well known TCP port for iSNSP is 3205.  If TCP is 
    not supported by this server instance, then the value 
    is 0." 
       ::= { isnsSrvrInstEntry 6 } 
    
   isnsSrvrInstUdpPort         OBJECT-TYPE 
       SYNTAX                  InetPortNumber 
       MAX-ACCESS              read-only 
       STATUS                  current 
       DESCRIPTION 
   "Indicates the UDP port this iSNS instance is accepting 
    iSNSP messages on, generally the iSNS well known port.  
    The well known UDP port for iSNSP is 3205.  If UDP is 
    not supported by this server instance, then the value 
    is 0." 
       ::= { isnsSrvrInstEntry 7 } 
    
   isnsSrvrInstDiscontinuityTime  OBJECT-TYPE 
        SYNTAX                 TimeStamp 
        MAX-ACCESS             read-only 
        STATUS                 current 
        DESCRIPTION  
    
   Gibbons                Expires July 2006                        17 
   Internet Draft              iSNS MIB                   January 2006 

   "The value of sysUpTime on the most recent occasion that 
    this iSNS server became active or suffered a 
    discontinuity." 
       ::= { isnsSrvrInstEntry 8 } 
    
   isnsSrvrInstRole            OBJECT-TYPE 
        SYNTAX                 INTEGER { notSet(0), 
                                         server(1),  
                                         serverNotPrimary(2) } 
        MAX-ACCESS             read-only 
        STATUS                 current 
        DESCRIPTION  
   "The current operational mode of this iSNS Server instance. 
          Value             Description 
        ---------         ---------------- 
         notSet           The iSNS Server role is not configured. 
         server           The iSNS Server instance is operating 
                          as a primary iSNS Server. 
         serverNotPrimary The iSNS Server instance can be a 
                          primary iSNS Server, but is not 
                          currently acting as a primary." 
       ::= { isnsSrvrInstEntry 9 } 
    
   isnsSrvrInstDiscMthdsEnbld  OBJECT-TYPE 
       SYNTAX                  IsnsSrvrDscvryMthdId 
       MAX-ACCESS              read-only 
       STATUS                  current 
       DESCRIPTION  
   "Indicates the discovery methods currently supported and 
    enabled on this iSNS Server instance.  This bitmap can be 
    used by a client to determine what discovery methods should 
    be used for this iSNS Server.  Additional methods of 
    discovery may also be supported." 
       ::= { isnsSrvrInstEntry 10 } 
    
   isnsSrvrInstDiscMcGrpType   OBJECT-TYPE 
       SYNTAX                  InetAddressType 
       MAX-ACCESS              read-only 
       STATUS                  current 
       DESCRIPTION 
   "The type of Inet address in isnsSrvrInstDiscMcGrp. If not 
    set, then the value is unknown(0)." 
       ::= { isnsSrvrInstEntry 11 } 
    
   isnsSrvrInstDiscMcGrp       OBJECT-TYPE 
       SYNTAX                  InetAddress 
       MAX-ACCESS              read-only 
       STATUS                  current 
       DESCRIPTION 
   "The multicast group that iSNS Heartbeat messages are 
    sent to if multicast based discovery has been enabled 
    for this server instance.  If not configured, then 
    
   Gibbons                Expires July 2006                        18 
   Internet Draft              iSNS MIB                   January 2006 

    the value is an empty string." 
       ::= { isnsSrvrInstEntry 12 } 
    
   isnsSrvrInstEsiNonRespThrshld OBJECT-TYPE 
       SYNTAX                  Unsigned32 ( 0 .. 65535 ) 
       MAX-ACCESS              read-only 
       STATUS                  current 
       DESCRIPTION  
   "ESI Non-Response Threshold - the number of ESI 
    messages that will be sent without receiving a response 
    before an entity is deregistered from the iSNS database.  
    If 0 then Entities will never be deregistered due to 
    non-receipt of ESI messages." 
       REFERENCE "RFC 4171, Section 3.4" 
       DEFVAL                  { 3 } 
       ::= { isnsSrvrInstEntry 13 } 
    
   isnsSrvrInstEnblCntrlNdeMgtScn OBJECT-TYPE 
       SYNTAX                  TruthValue 
       MAX-ACCESS              read-only 
       STATUS                  current 
       DESCRIPTION  
   "Whether enable Management SCN for Control Node - enable the 
    option for a control node to register for and receive 
   Management 
    SCNs sent by this server." 
       REFERENCE "RFC 4171, Section 3.4" 
       DEFVAL                  { true } 
       ::= { isnsSrvrInstEntry 14 } 
    
   isnsSrvrInstCntrlNodeAuth   OBJECT-TYPE 
       SYNTAX                  INTEGER { anyNode(1),  
                                         viewNodes(2), 
                                         noSnmpAccess(3) } 
       MAX-ACCESS              read-only 
       STATUS                  current 
       DESCRIPTION 
   "Control Nodes can be configured to receive management SCNs 
    indicating network updates, including information on 
    modification to DDs and DDSs.  This managed object indicates 
    if SNMP has access to control node information and, if it 
    does, which type of storage nodes can register with the 
    server instance as a control node.  Possible values for this 
    managed object are: 
          Value              Description 
        ---------          ---------------- 
        anyNode      Any storage node MAY register as a control 
                     node 
        viewNodes    Specified nodes MAY register as control 
                     nodes, SNMP view only 
        noSnmpAccess Control node information is not accessible 
                     via SNMP 
    
   Gibbons                Expires July 2006                        19 
   Internet Draft              iSNS MIB                   January 2006 

    If only specified nodes are allowed to register as control 
    nodes, and SNMP is allowed to modify the list of control 
    nodes, then they SHALL be listed in the 
    isnsCntlNodeIscsiTable and isnsCntlNodeFcPortTable. 
    If SNMP is not allowed to view or modify the list of control 
    nodes, then this managed object SHALL be set to 
    noSnmpAccess." 
       REFERENCE "RFC 4171, Section 3.4" 
       ::= { isnsSrvrInstEntry 15 } 
    
   isnsSrvrInstDfltDdDdsStatus OBJECT-TYPE 
       SYNTAX                  INTEGER { inNoDomain(1),  
                                         inDefaultDdAndDds(2) } 
       MAX-ACCESS              read-only 
       STATUS                  current 
       DESCRIPTION 
   "This indicates the Discovery Domain (DD) and Discovery Domain 
    Set (DDS) membership status for a new device when registerd in 
    the iSNS Server instance. Either the new device will not be in 
    a DD/DDS, or will be placed into a default DD and default DDS.  
    The default setting is inNoDomain." 
       REFERENCE "RFC 4171, Section 3.4" 
       DEFVAL                  { inNoDomain } 
       ::= { isnsSrvrInstEntry 16 } 
    
   isnsSrvrInstUpdateDdDdsSpprtd OBJECT-TYPE 
       SYNTAX                  IsnsDdDdsModificationBitmap 
       MAX-ACCESS              read-only 
       STATUS                  current 
       DESCRIPTION  
   "The methods that this iSNS Server instance supports 
    to modify Discovery Domains and Discovery Domain Sets. 
        Bit Field            Flag Description 
        ---------   ------------------------------------ 
            0       SNMP protocol is allowed to modify 
                    DD's/DDS's 
            1       Control Nodes are allowed 
            2       Target iSCSI Nodes are allowed 
            3       Initiator iSCSI Nodes are allowed 
            4       Target iFCP Ports are allowed 
            5       Initiator iFCP Ports are allowed 
    
    If a bit is true (1) then the flag is enabled.  If no 
    method to change a DD is supported, then the bitmap 
    is set to 0.  Two methods generally supported are SNMP 
    and Control Nodes." 
       REFERENCE  "RFC 4171, Section 3.4" 
       ::= { isnsSrvrInstEntry 17 } 
    
   isnsSrvrInstUpdateDdDdsEnbld OBJECT-TYPE 
       SYNTAX                  IsnsDdDdsModificationBitmap 
       MAX-ACCESS              read-only 
    
   Gibbons                Expires July 2006                        20 
   Internet Draft              iSNS MIB                   January 2006 

       STATUS                  current 
       DESCRIPTION  
   "This indicates the methods this server instance allows 
    for modifying Discovery Domains and Discovery Domain Sets. 
        Bit Field            Flag Description 
        ---------   ------------------------------------ 
            0       SNMP protocol is allowed to modify DD's/DDS's 
            1       Control Nodes are allowed 
            2       Target iSCSI Nodes are allowed 
            3       Initiator iSCSI Nodes are allowed 
            4       Target iFCP Ports are allowed 
            5       Initiator iFCP Ports are allowed 
    
    If a bit is true (1) then the mode is enabled.  If no 
    methods to change a DD are enabled, then the bitmap 
    is set to 0." 
       REFERENCE  "RFC 4171, Sec 2.2.2 and 3.4" 
       ::= { isnsSrvrInstEntry 18 } 
    
   -- 
   -- Count of objects currently registered in a server instance 
   -- 
    
   isnsNumObjTable             OBJECT-TYPE 
       SYNTAX                  SEQUENCE OF 
                                 IsnsNumObjEntry 
       MAX-ACCESS              not-accessible 
       STATUS                  current 
       DESCRIPTION      
   "Table providing the number of registered objects of each 
    type in the iSNS Server instance.  This table is optional 
    to implement.  The number of entries is dependent upon the 
    number of iSNS Server instances being managed." 
       ::= { isnsSrvrInfo 2 } 
    
   isnsNumObjEntry             OBJECT-TYPE 
       SYNTAX                  IsnsNumObjEntry 
       MAX-ACCESS              not-accessible 
       STATUS                  current 
       DESCRIPTION      
   "Entry of an iSNS Server instance." 
       AUGMENTS { isnsSrvrInstEntry } 
        ::= { isnsNumObjTable 1 } 
    
   IsnsNumObjEntry ::= SEQUENCE      {  
        isnsNumDds             Unsigned32, 
        isnsNumDd              Unsigned32, 
        isnsNumEntities        Unsigned32, 
        isnsNumPortals         Unsigned32, 
        isnsNumPortalGroups    Unsigned32, 
        isnsNumIscsiNodes      Unsigned32, 
        isnsNumFcPorts         Unsigned32, 
    
   Gibbons                Expires July 2006                        21 
   Internet Draft              iSNS MIB                   January 2006 

        isnsNumFcNodes         Unsigned32 
                                      } 
    
   isnsNumDds                  OBJECT-TYPE 
       SYNTAX                  Unsigned32 ( 0 .. 4294967295 ) 
       MAX-ACCESS              read-only 
       STATUS                  current 
       DESCRIPTION 
   "The current total number of Discovery Domain Sets 
    in this iSNS instance.  This is the number of rows 
    in the isnsSrvrDdsTable." 
       ::= { isnsNumObjEntry 1 } 
    
   isnsNumDd                   OBJECT-TYPE 
       SYNTAX                  Unsigned32 ( 0 .. 4294967295 ) 
       MAX-ACCESS              read-only 
       STATUS                  current 
       DESCRIPTION 
   "The current total number of Discovery Domains  
    in this iSNS instance.  This is the number of rows in the 
    isnsSrvrDdTable." 
       ::= { isnsNumObjEntry 2 } 
    
   isnsNumEntities             OBJECT-TYPE 
       SYNTAX                  Unsigned32 ( 0 .. 4294967295 ) 
       MAX-ACCESS              read-only 
       STATUS                  current 
       DESCRIPTION 
   "The current number of Entities registered in this 
    iSNS Server instance.  This is the number of rows in 
    the isnsRegEntityTable for this instance." 
       ::= { isnsNumObjEntry 3 } 
    
   isnsNumPortals              OBJECT-TYPE 
       SYNTAX                  Unsigned32 ( 0 .. 4294967295 ) 
       MAX-ACCESS              read-only 
       STATUS                  current 
       DESCRIPTION 
   "The current total number of Portals registered in iSNS. 
    This is the number of rows in isnsRegPortalTable." 
       ::= { isnsNumObjEntry 4 } 
    
   isnsNumPortalGroups         OBJECT-TYPE 
       SYNTAX                  Unsigned32 ( 0 .. 4294967295 ) 
       MAX-ACCESS              read-only 
       STATUS                  current 
       DESCRIPTION 
   "The current total number of Portal Groups registered in 
    iSNS.  This is the number of rows in isnsRegPgTable." 
       ::= { isnsNumObjEntry 5 } 
    
   isnsNumIscsiNodes           OBJECT-TYPE 
    
   Gibbons                Expires July 2006                        22 
   Internet Draft              iSNS MIB                   January 2006 

       SYNTAX                  Unsigned32 ( 0 .. 4294967295 ) 
       MAX-ACCESS              read-only 
       STATUS                  current 
       DESCRIPTION 
   "The current total number of iSCSI node entries registered in 
    the iSNS.  This is the number rows in isnsRegIscsiNodeTable." 
       ::= { isnsNumObjEntry 6 } 
    
   isnsNumFcPorts              OBJECT-TYPE 
       SYNTAX                  Unsigned32 ( 0 .. 4294967295 ) 
       MAX-ACCESS              read-only 
       STATUS                  current 
       DESCRIPTION 
   "The current total number of FC Port entries registered in the 
    iSNS.  This is the number of rows in isnsRegFcPortTable." 
       ::= { isnsNumObjEntry 7 } 
    
   isnsNumFcNodes              OBJECT-TYPE 
       SYNTAX                  Unsigned32 ( 0 .. 4294967295 ) 
       MAX-ACCESS              read-only 
       STATUS                  current 
       DESCRIPTION 
   "The current total number of FC node entries registered in the 
    iSNS. This is the number of rows in isnsRegFcNodeTable." 
       ::= { isnsNumObjEntry 8 } 
    
   -- 
   -- Control node information 
   -- 
    
   isnsCntlNodeInfo     OBJECT IDENTIFIER ::= { isnsSrvrInfo 4 } 
    
   -- 
   -- Specific iSCSI Nodes authorized to register as Control Nodes 
   -- 
    
   isnsCntlNodeIscsiTable      OBJECT-TYPE 
       SYNTAX                  SEQUENCE OF 
                                 IsnsCntlNodeIscsiEntry 
       MAX-ACCESS              not-accessible 
       STATUS                  current 
       DESCRIPTION      
   "Specified iSCSI Nodes that can register as control nodes.  
    The number of rows is dependent on the number of possible 
    iSCSI Control Nodes, and if SNMP is enabled to view control 
    node information, as indicated by isnsSrvrInstCntrlNodeAuth. 
    This table is accesible and usable to view the 
    set of control nodes if isnsSrvrInstCntrlNodeAuth is set to 
    the viewNodes or modifyNodes value." 
       ::= { isnsCntlNodeInfo 1 } 
    
   isnsCntlNodeIscsiEntry      OBJECT-TYPE 
    
   Gibbons                Expires July 2006                        23 
   Internet Draft              iSNS MIB                   January 2006 

       SYNTAX                  IsnsCntlNodeIscsiEntry 
       MAX-ACCESS              not-accessible 
       STATUS                  current 
       DESCRIPTION 
   "This is an iSCSI Control Node entry for a specific iSNS 
    server instance." 
        INDEX          { isnsSrvrInstIndex, 
                         isnsCntlNodeIscsiNodeIdx } 
        ::= { isnsCntlNodeIscsiTable 1 } 
    
   IsnsCntlNodeIscsiEntry ::= SEQUENCE {  
        isnsCntlNodeIscsiNodeIdx       IsnsNodeIndexId, 
        isnsCntlNodeIscsiNodeName      SnmpAdminString 
                                       } 
    
   isnsCntlNodeIscsiNodeIdx    OBJECT-TYPE 
       SYNTAX                  IsnsNodeIndexId 
       MAX-ACCESS              not-accessible 
       STATUS                  current 
       DESCRIPTION 
   "The iSCSI Index for the storage node authorized to act 
    as a control node." 
        ::= { isnsCntlNodeIscsiEntry 1 } 
    
   isnsCntlNodeIscsiNodeName   OBJECT-TYPE 
       SYNTAX                  SnmpAdminString (SIZE (0..223)) 
       MAX-ACCESS              read-only 
       STATUS                  current 
       DESCRIPTION      
   "The iSCSI Name of the initiator or target associated with 
    the storage node.  The iSCSI Name can not be longer then 
    223 bytes.  The iSNS Server internal maximum size is 224 
    bytes to provide NULL termination.  This is the iSCSI Node 
    Name for the storage node authorized to act as a control 
    node." 
        ::= { isnsCntlNodeIscsiEntry 2 } 
    
   -- 
   -- Specific FC Ports authorized to register as Control Nodes 
   -- 
    
   isnsCntlNodeFcPortTable     OBJECT-TYPE 
       SYNTAX                  SEQUENCE OF 
                                 IsnsCntlNodeFcPortEntry 
       MAX-ACCESS              not-accessible 
       STATUS                  current 
       DESCRIPTION      
   "Specified FC Ports that can register as control nodes.  The 
    number of rows is dependent on the number of possible FC 
    Port Control Nodes, and if SNMP is enabled to view control 
    node information, as indicated by isnsSrvrInstCntrlNodeAuth. 
    This table is accesible and usable to view and/or modify the 
    
   Gibbons                Expires July 2006                        24 
   Internet Draft              iSNS MIB                   January 2006 

    set of control nodes if isnsSrvrInstCntrlNodeAuth is set to 
    the viewNodes or modifyNodes value." 
       ::= { isnsCntlNodeInfo 2 } 
    
   isnsCntlNodeFcPortEntry     OBJECT-TYPE 
       SYNTAX                  IsnsCntlNodeFcPortEntry 
       MAX-ACCESS              not-accessible 
       STATUS                  current 
       DESCRIPTION      
   "FC Port control node entry." 
        INDEX          { isnsSrvrInstIndex, 
                         isnsCntlNodeFcPortName } 
        ::= { isnsCntlNodeFcPortTable 1 } 
    
   IsnsCntlNodeFcPortEntry ::= SEQUENCE     {  
        isnsCntlNodeFcPortName          FcNameIdOrZero 
                                            } 
    
   isnsCntlNodeFcPortName      OBJECT-TYPE 
       SYNTAX                  FcNameIdOrZero 
       MAX-ACCESS              not-accessible 
       STATUS                  current 
       DESCRIPTION      
   "The FC Port WWN that can be a control node for the specified 
    iSNS Server.  Zero is not a valid value for this managed 
    object.  This managed object, combined with the 
    isnsSrvrInstIndex, is the key for this table." 
        ::= { isnsCntlNodeFcPortEntry 1 } 
    
   -- 
   -- Discovery Domain Set information 
   -- 
    
   isnsDdsInfo     OBJECT IDENTIFIER ::= { isnsSrvrInfo 5 } 
    
   -- 
   -- Discovery Domain Set Registrations -------------------- 
   -- 
    
   isnsDdsTable                OBJECT-TYPE 
       SYNTAX                  SEQUENCE OF IsnsDdsEntry 
       MAX-ACCESS              not-accessible 
       STATUS                  current 
       DESCRIPTION 
   "A table containing configuration information for each 
    Discovery Domain Set (DDS) registered in the iSNS Server 
    instance. The number of rows in the table is dependent 
    on the number of DDSs registered in the specified iSNS 
    server instance." 
       ::= { isnsDdsInfo 1 } 
    
   isnsDdsEntry                OBJECT-TYPE 
    
   Gibbons                Expires July 2006                        25 
   Internet Draft              iSNS MIB                   January 2006 

       SYNTAX                  IsnsDdsEntry 
       MAX-ACCESS              not-accessible 
       STATUS                  current 
       DESCRIPTION 
   "Information on one Discovery Domain Set (DDS) registered 
    in the iSNS Server instance." 
       INDEX   { isnsSrvrInstIndex, isnsDdsId} 
       ::= { isnsDdsTable 1 } 
    
   IsnsDdsEntry ::= 
       SEQUENCE {  
          isnsDdsId             IsnsDiscoveryDomainSetId, 
          isnsDdsSymbolicName   SnmpAdminString, 
          isnsDdsStatus         IsnsDdsStatusId 
                } 
    
   isnsDdsId                   OBJECT-TYPE 
       SYNTAX                  IsnsDiscoveryDomainSetId 
       MAX-ACCESS              not-accessible 
       STATUS                  current 
       DESCRIPTION 
   "The ID that refers to this Discovery Domain Set and 
    index to the table." 
       ::= { isnsDdsEntry 1 } 
    
   isnsDdsSymbolicName         OBJECT-TYPE 
       SYNTAX                  SnmpAdminString (SIZE (0..255)) 
       MAX-ACCESS              read-only 
       STATUS                  current 
       DESCRIPTION 
   "The Discovery Domain Set Symbolic Name field contains 
    a unique variable-length description (up to 255 bytes) 
    that is associated with the DDS.  If a Symbolic Name is 
    not provided, then one will be generated by the iSNS 
    server." 
       REFERENCE "RFC 4171, Section 6" 
       ::= { isnsDdsEntry 2 } 
    
   isnsDdsStatus               OBJECT-TYPE 
       SYNTAX                  IsnsDdsStatusId 
       MAX-ACCESS              read-only 
       STATUS                  current 
       DESCRIPTION 
   "The bitmap indicating the status of a Discovery Domain 
    Set (DDS) registered in the iSNS. 
                 Bit           Status 
              ---------       --------- 
                  0            enabled 
    
    If bit(0) is set to true then the DDS is Enabled.  If set 
    to false then the DDS is disabled." 
       REFERENCE "RFC 4171, Section 6" 
    
   Gibbons                Expires July 2006                        26 
   Internet Draft              iSNS MIB                   January 2006 

       DEFVAL                  { { enabled } } 
       ::= { isnsDdsEntry 3 } 
    
   -- 
   -- Discovery Domain Set Members -------------------- 
   -- 
    
   -- 
   -- DDS Membership Assignment 
   -- 
    
   isnsDdsMemberTable          OBJECT-TYPE 
       SYNTAX                  SEQUENCE OF IsnsDdsMemberEntry 
       MAX-ACCESS              not-accessible 
       STATUS                  current 
       DESCRIPTION 
   "A table containing Discovery Domains (DDs) that have 
    been assigned to specific Discovery Domain Sets (DDSs). 
    The number of rows in the table is dependent on the 
    number of DD to DDS relationships in the iSNS instance." 
       ::= { isnsDdsInfo 2 } 
    
   isnsDdsMemberEntry          OBJECT-TYPE 
       SYNTAX                  IsnsDdsMemberEntry 
       MAX-ACCESS              not-accessible 
       STATUS                  current 
       DESCRIPTION 
   "The mapping of one Discovery Domain (DD) to a Discovery 
    Domain Set (DDS).  This indicates the DD is a member of 
    the DDS." 
       INDEX   { isnsSrvrInstIndex, 
                 isnsDdsId, 
                 isnsDdsMemberDdId } 
       ::= { isnsDdsMemberTable 1 } 
    
   IsnsDdsMemberEntry ::= 
       SEQUENCE {  
          isnsDdsMemberDdId       IsnsDiscoveryDomainId 
                } 
    
   isnsDdsMemberDdId           OBJECT-TYPE 
       SYNTAX                  IsnsDiscoveryDomainId 
       MAX-ACCESS              not-accessible 
       STATUS                  current 
       DESCRIPTION 
   "The ID that identifies the Discovery Domain  
    which is a member of the Discovery Domain Set." 
       ::= { isnsDdsMemberEntry 1 } 
    
   -- 
   -- Discovery Domain information 
   -- 
    
   Gibbons                Expires July 2006                        27 
   Internet Draft              iSNS MIB                   January 2006 

    
   isnsDdInfo     OBJECT IDENTIFIER ::= { isnsSrvrInfo 6 } 
    
   -- 
   -- Discovery Domain Registrations ---------------------------- 
   -- 
    
   isnsDdTable                 OBJECT-TYPE 
       SYNTAX                  SEQUENCE OF IsnsDdEntry 
       MAX-ACCESS              not-accessible 
       STATUS                  current 
       DESCRIPTION 
   "A table containing configuration information for each 
    Discovery Domain (DD) registered in the iSNS.  The number 
    of rows in the table is dependent on the number of DDs 
    registered in the iSNS instance." 
       ::= { isnsDdInfo 1 } 
    
   isnsDdEntry                 OBJECT-TYPE 
       SYNTAX                  IsnsDdEntry 
       MAX-ACCESS              not-accessible 
       STATUS                  current 
       DESCRIPTION 
   "Information on a Discovery Domain (DD) registered in 
    the iSNS Server instance." 
       INDEX   { isnsSrvrInstIndex, isnsDdId} 
       ::= { isnsDdTable 1 } 
    
   IsnsDdEntry::= 
       SEQUENCE {  
          isnsDdId             IsnsDiscoveryDomainId, 
          isnsDdSymbolicName   SnmpAdminString, 
          isnsDdFeatures       DdFeatureBitmapId 
                } 
    
   isnsDdId                    OBJECT-TYPE 
       SYNTAX                  IsnsDiscoveryDomainId 
       MAX-ACCESS              not-accessible 
       STATUS                  current 
       DESCRIPTION 
   "The ID that refers to this Discovery Domain, and the 
    index to the table." 
       REFERENCE "RFC 4171, Section 6" 
       ::= { isnsDdEntry 1 } 
    
   isnsDdSymbolicName          OBJECT-TYPE 
       SYNTAX                  SnmpAdminString (SIZE (0..255)) 
       MAX-ACCESS              read-only 
       STATUS                  current 
       DESCRIPTION 
   "The Discovery Domain Symbolic Name field contains a 
    unique variable-length description (up to 255 bytes)  
    
   Gibbons                Expires July 2006                        28 
   Internet Draft              iSNS MIB                   January 2006 

    that is associated with the DD." 
       REFERENCE "RFC 4171, Section 6" 
       ::= { isnsDdEntry 2 } 
    
   isnsDdFeatures              OBJECT-TYPE 
       SYNTAX                  DdFeatureBitmapId 
       MAX-ACCESS              read-only 
       STATUS                  current 
       DESCRIPTION 
   "The Discovery Domain Features field contains a bitmap 
    indicating the features of this DD.   
        Bit            DD Feature 
       ---------       --------- 
         0             Boot List 
    
    Boot List: this feature indicates that the targets 
    in this DD provide boot capabilities for the member 
    initiators.  By default no DD features are enabled." 
       REFERENCE "RFC 4171, Section 6" 
       ::= { isnsDdEntry 3 } 
    
   -- 
   -- Discovery Domain Members -------------------- 
   --  
    
   -- 
   -- DD iSCSI Node Membership Assignment 
   -- 
    
   isnsDdIscsiMemberTable      OBJECT-TYPE 
       SYNTAX                  SEQUENCE OF IsnsDdIscsiMemberEntry 
       MAX-ACCESS              not-accessible 
       STATUS                  current 
       DESCRIPTION 
   "A table containing iSCSI node indexes that have been 
    assigned to specific DDs in this iSNS Server instance.  The 
    number of rows in the table is dependent on the number of 
    relationships between iSCSI Nodes and DDs registered in the 
    iSNS instance." 
       ::= { isnsDdInfo 2 } 
    
   isnsDdIscsiMemberEntry      OBJECT-TYPE 
       SYNTAX                  IsnsDdIscsiMemberEntry 
       MAX-ACCESS              not-accessible 
       STATUS                  current 
       DESCRIPTION 
   "The mapping of one iSCSI Node to a Discovery Domain to 
    indicate membership in the DD.  The indexes are the iSNS 
    server instance, the DD ID of the Discovery Domain, and 
    the iSCSI Node Index of the iSCSI Node." 
       INDEX   { isnsSrvrInstIndex, 
                 isnsDdId,  
    
   Gibbons                Expires July 2006                        29 
   Internet Draft              iSNS MIB                   January 2006 

                 isnsDdMemberIscsiIdx } 
       ::= { isnsDdIscsiMemberTable 1 } 
    
   IsnsDdIscsiMemberEntry::= 
       SEQUENCE {  
          isnsDdMemberIscsiIdx     IsnsNodeIndexId, 
          isnsDdMemberIscsiName    SnmpAdminString, 
          isnsDdMemberIsRegistered TruthValue 
                } 
    
   isnsDdMemberIscsiIdx        OBJECT-TYPE 
       SYNTAX                  IsnsNodeIndexId 
       MAX-ACCESS              not-accessible 
       STATUS                  current 
       DESCRIPTION 
   "The iSCSI node index for this member node entry.  This 
    index is used to uniquely indicate this table entry, 
    and provides a 1 to 1 mapping to a node name.  The 
    iSCSI node name is too long to be used for an index 
    directly.  The iSCSI node index used for a specific 
    iSCSI node name MUST be indentical in all DDs, and is 
    persistent across server reinitializations when the 
    iSCSI node is a member of a Discovery Domain (DD)." 
       REFERENCE "RFC 4171, Section 6" 
       ::= { isnsDdIscsiMemberEntry 1 } 
    
   isnsDdMemberIscsiName       OBJECT-TYPE 
       SYNTAX                  SnmpAdminString (SIZE (0..223)) 
       MAX-ACCESS              read-only 
       STATUS                  current 
       DESCRIPTION 
   "The iSCSI Name associated with the storage node.  The 
    iSCSI Name can not be longer then 223 bytes.  The iSNS 
    server internal maximum size is 224 bytes to provide 
    NULL termination.  This is the iSCSI Name for the storage 
    node that is a member of the DD.  This value maps 1 to 1 
    to the isnsDdMemberIscsiIdx node index.  The iSCSI Name 
    field is too long to be easily used for an index directly.  
    The node index used for a specific node name is only 
    persistent across iSNS Server reinitializations for nodes 
    that are in a Discovery Domain (DD) or are registered 
    control nodes.  This value is only required during row 
    creation if the storage node is not yet registered in the 
    iSNS Server instance.  If the storage node is not yet 
    registered, then the iSCSI Name MUST be provided with the 
    iSCSI node index during row creation in order to create the 
    1 to 1 mapping." 
       REFERENCE "RFC 4171, Section 6" 
       ::= { isnsDdIscsiMemberEntry 2 } 
    
   isnsDdMemberIsRegistered    OBJECT-TYPE 
       SYNTAX                  TruthValue 
    
   Gibbons                Expires July 2006                        30 
   Internet Draft              iSNS MIB                   January 2006 

       MAX-ACCESS              read-only 
       STATUS                  current 
       DESCRIPTION  
   "This indicates whether this member of the DD is currently 
    registered in the iSNS Server instance.  iSCSI Storage 
    Node members do not need to be currently registered in 
    order for their iSCSI Name and Index to be added to 
    a DD." 
       REFERENCE "RFC 4171, Section 6.11" 
       ::= { isnsDdIscsiMemberEntry 3 } 
    
   -- 
   -- DD Portal Membership Assignment 
   -- 
    
   isnsDdPortalMemberTable     OBJECT-TYPE 
       SYNTAX                  SEQUENCE OF IsnsDdPortalMemberEntry 
       MAX-ACCESS              not-accessible 
       STATUS                  current 
       DESCRIPTION 
   "A table containing currently registered and unregistered 
    portal objects that have been explicitly assigned to specific 
    DDs.  Explicit assignment of a portal to a DD is only done 
    when a specific set of portals are prefered for use within a 
    DD.  Otherwise, for iSCSI, the Portal Group Object should be 
    used for identifying which portals provide access to which 
    storage nodes. The number of rows in the table is dependent 
    on the number of explicit relationships between portals and 
    DDs registered in the iSNS." 
       REFERENCE "RFC 4171, Section 6" 
       ::= { isnsDdInfo 3 } 
    
   isnsDdPortalMemberEntry     OBJECT-TYPE 
       SYNTAX                  IsnsDdPortalMemberEntry 
       MAX-ACCESS              not-accessible 
       STATUS                  current 
       DESCRIPTION 
   "Each entry indicates an explicit addition of a portal to a 
    discovery domain.  The explicit addition of an entity portal 
    to a discovery domain indicates the portal is preferred for 
    access to nodes of the entity for this discovery domain.  
    Registered Portal Group objects are used in iSCSI to indicate 
    mapping of portals to nodes across all discovery domains. 
    Portals that have been explicitly mapped a discovery domain 
    will be returned as part of a query that is scoped to that 
    discovery domain.  If no portal of an entity has been 
    explicitly mapped to a discovery domain, then all portals of 
    the entity that provide access to a storage node are returned 
    as part of a query.  The table indexes are the server 
    instance, the DD ID of the Discovery Domain, and the Portal 
    Index of the portal." 
       INDEX   { isnsSrvrInstIndex, 
    
   Gibbons                Expires July 2006                        31 
   Internet Draft              iSNS MIB                   January 2006 

                 isnsDdId, 
                 isnsDdMemberPortalIdx } 
       ::= { isnsDdPortalMemberTable 1 } 
    
   IsnsDdPortalMemberEntry ::= 
       SEQUENCE {  
          isnsDdMemberPortalIdx        IsnsPortalIndexId, 
          isnsDdMemberPortalAddrType   InetAddressType, 
          isnsDdMemberPortalAddr       InetAddress, 
          isnsDdMemberPortalPortType   IsnsPortalPortTypeId, 
          isnsDdMemberPortalPort       InetPortNumber, 
          isnsDdMemberPortalIsRegistered TruthValue 
                } 
    
   isnsDdMemberPortalIdx       OBJECT-TYPE 
       SYNTAX                  IsnsPortalIndexId 
       MAX-ACCESS              not-accessible 
       STATUS                  current 
       DESCRIPTION 
   "The index for a portal explicitly contained in the discovery 
    domain.  The Portal Index used for a specific portal 
    IP-address and port number pair is only persistent across 
    reboots for portals that have been explicitly added to a 
    Discovery Domain (DD).  If a portal is not explicitly 
    registered in any DD, then the index used for a portal can 
    change after a server reinitialization." 
       REFERENCE "RFC 4171, Section 6" 
       ::= { isnsDdPortalMemberEntry 1 } 
    
   isnsDdMemberPortalAddrType  OBJECT-TYPE 
       SYNTAX                  InetAddressType 
       MAX-ACCESS              read-only 
       STATUS                  current 
       DESCRIPTION 
   "The type of Inet address in isnsDdMemberPortalAddr." 
       ::= { isnsDdPortalMemberEntry 2 } 
    
   isnsDdMemberPortalAddr      OBJECT-TYPE 
       SYNTAX                  InetAddress 
       MAX-ACCESS              read-only 
       STATUS                  current 
       DESCRIPTION 
   "The Inet Address for the portal." 
       REFERENCE "RFC 4171, Section 6" 
       ::= { isnsDdPortalMemberEntry 3 } 
    
   isnsDdMemberPortalPortType  OBJECT-TYPE 
       SYNTAX                  IsnsPortalPortTypeId 
       MAX-ACCESS              read-only 
       STATUS                  current 
       DESCRIPTION 
   "The port type for the portal, either UDP or TCP." 
    
   Gibbons                Expires July 2006                        32 
   Internet Draft              iSNS MIB                   January 2006 

       REFERENCE "RFC 4171, Section 6" 
       ::= { isnsDdPortalMemberEntry 4 } 
    
   isnsDdMemberPortalPort      OBJECT-TYPE 
       SYNTAX                  InetPortNumber 
       MAX-ACCESS              read-only 
       STATUS                  current 
       DESCRIPTION 
   "The port number for the portal.  Whether the portal 
    type is TCP or UDP is indicated by isnsDdPortalPortType." 
       REFERENCE "RFC 4171, Section 6" 
       ::= { isnsDdPortalMemberEntry 5 } 
    
   isnsDdMemberPortalIsRegistered OBJECT-TYPE 
       SYNTAX                  TruthValue 
       MAX-ACCESS              read-only 
       STATUS                  current 
       DESCRIPTION  
   "This indicates whether this member of the DD is currently 
    registered in the iSNS Server instance.  Portals that are 
    DD members do not need to be currently registered in 
    order for them to be added to a DD." 
       REFERENCE "RFC 4171, Section 6.11" 
       ::= { isnsDdPortalMemberEntry 6 } 
    
   -- 
   -- DD FC Port Membership Assignment 
   -- 
    
   isnsDdFcPortMemberTable     OBJECT-TYPE 
       SYNTAX                  SEQUENCE OF IsnsDdFcPortMemberEntry 
       MAX-ACCESS              not-accessible 
       STATUS                  current 
       DESCRIPTION 
   "A table containing FC Port World Wide Names (WWN) that 
    have been assigned to specific DDs.  The number of rows 
    in the table is dependent on the number of relationships 
    between FC Ports and DDs registered in the iSNS." 
       ::= { isnsDdInfo 4 } 
    
   isnsDdFcPortMemberEntry     OBJECT-TYPE 
       SYNTAX                  IsnsDdFcPortMemberEntry 
       MAX-ACCESS              not-accessible 
       STATUS                  current 
       DESCRIPTION 
   "The association of one FC Port with a Discovery Domain. 
    Membership of an FC Port in a Discovery Domain is 
    indicated by creating a row for the appropriate DD ID 
    and FC Port WWN." 
       INDEX   { isnsSrvrInstIndex, 
                 isnsDdId, 
                 isnsDdMemberFcPortName } 
    
   Gibbons                Expires July 2006                        33 
   Internet Draft              iSNS MIB                   January 2006 

       ::= { isnsDdFcPortMemberTable 1 } 
    
   IsnsDdFcPortMemberEntry ::= 
       SEQUENCE {  
          isnsDdMemberFcPortName     FcNameIdOrZero, 
          isnsDdMemberFcIsRegistered TruthValue 
       } 
    
   isnsDdMemberFcPortName      OBJECT-TYPE 
       SYNTAX                  FcNameIdOrZero 
       MAX-ACCESS              not-accessible 
       STATUS                  current 
       DESCRIPTION 
   "The Port WWN the FC Port that is a member of the DD. The 
    value MUST be a valid FC WWN, as per the FC-GS standard.  
    This managed object, combined with the isnsSrvrInstIndex 
    and isnsDdId are the key for this table.  Zero is not a 
    valid value for this managed object." 
       REFERENCE "RFC 4171, Section 6" 
       ::= { isnsDdFcPortMemberEntry 1 } 
    
   isnsDdMemberFcIsRegistered  OBJECT-TYPE 
       SYNTAX                  TruthValue 
       MAX-ACCESS              read-only 
       STATUS                  current 
       DESCRIPTION  
   "This indicates whether this member of the DD is currently 
    registered in the iSNS Server instance." 
       REFERENCE "RFC 4171, Section 6.11" 
       ::= { isnsDdFcPortMemberEntry 2 } 
    
   -- 
   --  Registered Device Information 
   -- 
    
   isnsReg    OBJECT IDENTIFIER ::= { isnsSrvrInfo 7 } 
    
   isnsRegEntityInfo           OBJECT IDENTIFIER 
                                  ::= { isnsReg    1 } 
    
   -- 
   -- iSNS Registered Entities Table 
   -- 
    
   isnsRegEntityTable          OBJECT-TYPE 
       SYNTAX                  SEQUENCE OF IsnsRegEntityEntry 
       MAX-ACCESS              not-accessible 
       STATUS                  current 
       DESCRIPTION 
   "A table containing registered Entity objects in each iSNS 
    server instance.  The number of entries in the table is 
    dependent on the number of Entity objects registered in the 
    
   Gibbons                Expires July 2006                        34 
   Internet Draft              iSNS MIB                   January 2006 

    iSNS Server instances.  All Entity objects are registered in 
    the iSNS using the iSNS protocol." 
       ::= { isnsRegEntityInfo 1 } 
    
   isnsRegEntityEntry          OBJECT-TYPE 
       SYNTAX                  IsnsRegEntityEntry 
       MAX-ACCESS              not-accessible 
       STATUS                  current 
       DESCRIPTION 
   "Information on one registered Entity object in an iSNS 
    server instance." 
       INDEX   { isnsSrvrInstIndex, 
                 isnsRegEntityIdx } 
       ::= { isnsRegEntityTable 1 } 
    
   IsnsRegEntityEntry ::= 
       SEQUENCE {  
          isnsRegEntityIdx            IsnsEntityIndexId, 
          isnsRegEntityEID            SnmpAdminString, 
          isnsRegEntityProtocol       IsnsEntityProtocolId, 
          isnsRegEntityMgtAddrType    InetAddressType, 
          isnsRegEntityMgtAddr        InetAddress, 
          isnsRegEntityTimestamp      TimeStamp, 
          isnsRegEntityVersionMin     Unsigned32, 
          isnsRegEntityVersionMax     Unsigned32, 
          isnsRegEntityRegPeriod      Unsigned32 
               } 
    
   isnsRegEntityIdx            OBJECT-TYPE 
       SYNTAX                  IsnsEntityIndexId 
       MAX-ACCESS              not-accessible 
       STATUS                  current 
       DESCRIPTION 
   "The Entity Index for this entity.  This integer based index 
    is assigned by the iSNS Server when an Entity is initially 
    registered. The Entity Index can be used to represent a 
    registered Entity object in situations where the Entity EID 
    would be too long/unwieldy." 
       REFERENCE "RFC 4171, Section 6" 
       ::= { isnsRegEntityEntry 1 } 
    
   isnsRegEntityEID            OBJECT-TYPE 
       SYNTAX                  SnmpAdminString (SIZE (0..255)) 
       MAX-ACCESS              read-only 
       STATUS                  current 
       DESCRIPTION 
   "The EID is a unique registered Entity object identifier, as 
    specified in the iSNS Specification.  This is the iSNS 
    Entity Identifier for the registered Entity object." 
       REFERENCE "RFC 4171, Section 6" 
       ::= { isnsRegEntityEntry 2 } 
    
    
   Gibbons                Expires July 2006                        35 
   Internet Draft              iSNS MIB                   January 2006 

   isnsRegEntityProtocol       OBJECT-TYPE 
       SYNTAX                  IsnsEntityProtocolId 
       MAX-ACCESS              read-only 
       STATUS                  current 
       DESCRIPTION 
   "The type of protocol that is supported by this entity. 
    Additional values may be assigned by IANA. 
    
              Type Value       Entity Type 
              ----------       ----------- 
                 1             No Protocol 
                 2             iSCSI 
                 3             iFCP 
               All Others      As assigned by IANA 
   " 
       REFERENCE  "RFC 4171, Section 6" 
       ::= { isnsRegEntityEntry 3 } 
    
   isnsRegEntityMgtAddrType    OBJECT-TYPE 
       SYNTAX                  InetAddressType 
       MAX-ACCESS              read-only 
       STATUS                  current 
       DESCRIPTION 
   "The type of Inet address in isnsRegEntityMgtAddr." 
       ::= { isnsRegEntityEntry 4 } 
    
   isnsRegEntityMgtAddr        OBJECT-TYPE 
       SYNTAX                  InetAddress 
       MAX-ACCESS              read-only 
       STATUS                  current 
       DESCRIPTION 
   "The iSNS Management IP Address for the registred Entity 
    object." 
       REFERENCE "RFC 4171, Section 6" 
       ::= { isnsRegEntityEntry 5 } 
    
   isnsRegEntityTimestamp      OBJECT-TYPE 
       SYNTAX                  TimeStamp 
       MAX-ACCESS              read-only 
       STATUS                  current 
       DESCRIPTION 
   "The iSNS Entity Registration Timestamp for the registred 
    Entity object.  This is the most recent date and time that 
    the registered Entity object, and associated registered 
    objects contained in the Entity, were registered or 
    updated." 
       REFERENCE "RFC 4171, Section 6" 
       ::= { isnsRegEntityEntry 6 } 
    
   isnsRegEntityVersionMin     OBJECT-TYPE 
       SYNTAX                  Unsigned32 ( 0 .. 65535 ) 
       MAX-ACCESS              read-only 
    
   Gibbons                Expires July 2006                        36 
   Internet Draft              iSNS MIB                   January 2006 

       STATUS                  current 
       DESCRIPTION 
   "The iSNS Entity Protocol Version Range minimum value.  A 
    value of x'FF' is a wildcard value indicating no minimum to 
    the protocol versions supported by this Entity.  Entity 
    registrations with isnsRegEntityProtocol set to No Protocol 
    always have a minimum version of 0." 
       REFERENCE "RFC 4171, Section 6" 
       ::= { isnsRegEntityEntry 7 } 
    
   isnsRegEntityVersionMax     OBJECT-TYPE 
       SYNTAX                  Unsigned32 ( 0 .. 65535 ) 
       MAX-ACCESS              read-only 
       STATUS                  current 
       DESCRIPTION 
   "The iSNS Entity Protocol Version Range maximum value.  A 
    value of x'FF' is a wildcard value indicating no maximum to 
    the protocol versions supported by this Entity.  Entity 
    registrations with isnsRegEntityProtocol set to No Protocol 
    always have a maximum version of 0." 
       REFERENCE "RFC 4171, Section 6" 
       ::= { isnsRegEntityEntry 8 } 
    
   isnsRegEntityRegPeriod      OBJECT-TYPE 
       SYNTAX                  Unsigned32 ( 0 .. 4294967295 ) 
       MAX-ACCESS              read-only 
       STATUS                  current 
       DESCRIPTION 
   "The iSNS Entity Status Inquiry (ESI) registration period 
    which indicates the maximum time, in seconds, that the 
    registration will be maintained without receipt of an iSNSP 
    message from the entity.  If the Registration Period is set 
    to 0, then the Entity SHALL NOT be deregistered due to no 
    contact with the entity." 
       REFERENCE "RFC 4171, Section 6" 
       ::= { isnsRegEntityEntry 9 } 
    
   -- 
   -- Registered Objects Associated With an Entity Information 
   -- 
    
   isnsRegEntityNumObjTable    OBJECT-TYPE 
       SYNTAX                  SEQUENCE OF  
                                 IsnsRegEntityNumObjEntry 
       MAX-ACCESS              not-accessible 
       STATUS                  current 
       DESCRIPTION 
   "A table containing information on the number of registered 
    objects associated with a registered Entity in the iSNS 
    server instance.  This table is optional to implement.  The 
    number of entries in the table is dependent on the number 
    of registered Entity objects in the iSNS." 
    
   Gibbons                Expires July 2006                        37 
   Internet Draft              iSNS MIB                   January 2006 

       ::= { isnsRegEntityInfo 2 } 
    
   isnsRegEntityNumObjEntry    OBJECT-TYPE 
       SYNTAX                  IsnsRegEntityNumObjEntry 
       MAX-ACCESS              not-accessible 
       STATUS                  current 
       DESCRIPTION 
   "Information on the number of registered objects associated 
    with a registered Entity object in an iSNS Server instance." 
       INDEX   { isnsSrvrInstIndex, 
                 isnsRegEntityIdx } 
       ::= { isnsRegEntityNumObjTable 1 } 
    
   IsnsRegEntityNumObjEntry ::= 
       SEQUENCE {  
          isnsRegEntityInfoNumPortals      Unsigned32, 
          isnsRegEntityInfoNumPortalGroups Unsigned32, 
          isnsRegEntityInfoNumIscsiNodes   Unsigned32, 
          isnsRegEntityInfoNumFcPorts      Unsigned32, 
          isnsRegEntityInfoNumFcNodes      Unsigned32 
               } 
    
   isnsRegEntityInfoNumPortals OBJECT-TYPE 
       SYNTAX                  Unsigned32 ( 0 .. 4294967295 ) 
       MAX-ACCESS              read-only 
       STATUS                  current 
       DESCRIPTION 
   "The number of Portals associated with this Entity." 
       ::= { isnsRegEntityNumObjEntry 1 } 
    
   isnsRegEntityInfoNumPortalGroups OBJECT-TYPE 
       SYNTAX                  Unsigned32 ( 0 .. 4294967295 ) 
       MAX-ACCESS              read-only 
       STATUS                  current 
       DESCRIPTION 
   "The number of Portal Groups associated with this Entity." 
       ::= { isnsRegEntityNumObjEntry 2 } 
    
   isnsRegEntityInfoNumIscsiNodes OBJECT-TYPE 
       SYNTAX                  Unsigned32 ( 0 .. 4294967295 ) 
       MAX-ACCESS              read-only 
       STATUS                  current 
       DESCRIPTION 
   "The number of iSCSI Storage Nodes associated with this 
    Entity." 
       ::= { isnsRegEntityNumObjEntry 3 } 
    
   isnsRegEntityInfoNumFcPorts OBJECT-TYPE 
       SYNTAX                  Unsigned32 ( 0 .. 4294967295 ) 
       MAX-ACCESS              read-only 
       STATUS                  current 
       DESCRIPTION 
    
   Gibbons                Expires July 2006                        38 
   Internet Draft              iSNS MIB                   January 2006 

   "The number of FC Ports associated with this Entity." 
       ::= { isnsRegEntityNumObjEntry 4 } 
    
   isnsRegEntityInfoNumFcNodes OBJECT-TYPE 
       SYNTAX                  Unsigned32 ( 0 .. 4294967295 ) 
       MAX-ACCESS              read-only 
       STATUS                  current 
       DESCRIPTION 
   "The number of FC Nodes associated with this Entity." 
       ::= { isnsRegEntityNumObjEntry 5 } 
    
    
   -- 
   -- iSNS Registered Portal Information 
   -- 
    
   isnsRegPortalInfo           OBJECT IDENTIFIER 
                                  ::= { isnsReg  2 } 
    
   -- 
   -- iSNS Registered Portal Table 
   -- 
    
   isnsRegPortalTable          OBJECT-TYPE 
       SYNTAX                  SEQUENCE OF IsnsRegPortalEntry 
       MAX-ACCESS              not-accessible 
       STATUS                  current 
       DESCRIPTION 
   "A table containing the registered Portals in the iSNS. 
    The number of entries is dependent on the number of 
    Portals registered in the iSNS." 
       ::= { isnsRegPortalInfo 1 } 
    
   isnsRegPortalEntry          OBJECT-TYPE 
       SYNTAX                  IsnsRegPortalEntry 
       MAX-ACCESS              not-accessible 
       STATUS                  current 
       DESCRIPTION 
   "Information on one registered Entity Portal in the iSNS.  
    The Entity Index is part of the table index to quickly 
    find Portals that support a specific Entity." 
       INDEX   { isnsSrvrInstIndex, 
                 isnsRegEntityIdx, 
                 isnsRegPortalPrtlIdx } 
       ::= { isnsRegPortalTable 1 } 
    
   IsnsRegPortalEntry ::= 
       SEQUENCE {  
          isnsRegPortalPrtlIdx        IsnsPortalIndexId, 
          isnsRegPortalAddrType       InetAddressType, 
          isnsRegPortalAddr           InetAddress, 
          isnsRegPortalPortType       IsnsPortalPortTypeId, 
    
   Gibbons                Expires July 2006                        39 
   Internet Draft              iSNS MIB                   January 2006 

          isnsRegPortalPort           InetPortNumber, 
          isnsRegPortalSymName        SnmpAdminString, 
          isnsRegPortalEsiInterval    Unsigned32, 
          isnsRegPortalEsiPortType    IsnsPortalPortTypeId, 
          isnsRegPortalEsiPort        InetPortNumber, 
          isnsRegPortalScnPortType    IsnsPortalPortTypeId, 
          isnsRegPortalScnPort        InetPortNumber, 
          isnsRegPortalSecurityInfo   IsnsPortalSecurityBitmapId 
               } 
    
   isnsRegPortalPrtlIdx        OBJECT-TYPE 
       SYNTAX                  IsnsPortalIndexId 
       MAX-ACCESS              not-accessible 
       STATUS                  current 
       DESCRIPTION 
   "The Portal Index for this node.  The index is created by the 
    iSNS Server for mapping between registered objects.  The 
    Portal Index used for a specific portal IP-address and port 
    number pair is only persistent across reboots for portals 
    that have been explicitly added to a Discovery Domain (DD).  
    If a portal is not explicitly registered in any DD, then the 
    index used for a portal can change after a server 
    reinitialization." 
       REFERENCE "RFC 4171, Section 6" 
       ::= { isnsRegPortalEntry 1 } 
    
   isnsRegPortalAddrType       OBJECT-TYPE 
       SYNTAX                  InetAddressType 
       MAX-ACCESS              read-only 
       STATUS                  current 
       DESCRIPTION 
   "The type of Inet address in isnsRegPortalAddr." 
       ::= { isnsRegPortalEntry 2 } 
    
   isnsRegPortalAddr           OBJECT-TYPE 
       SYNTAX                  InetAddress 
       MAX-ACCESS              read-only 
       STATUS                  current 
       DESCRIPTION 
   "The Inet Address for this Portal as defined in 
    the iSNS Specification [iSNS]." 
       REFERENCE "RFC 4171, Section 6" 
       ::= { isnsRegPortalEntry 3 } 
    
   isnsRegPortalPortType       OBJECT-TYPE 
       SYNTAX                  IsnsPortalPortTypeId 
       MAX-ACCESS              read-only 
       STATUS                  current 
       DESCRIPTION 
   "The port type for this Portal, either UDP or TCP, as 
    defined in the iSNS Specification [iSNS]." 
       REFERENCE "RFC 4171, Section 6" 
    
   Gibbons                Expires July 2006                        40 
   Internet Draft              iSNS MIB                   January 2006 

       ::= { isnsRegPortalEntry 4 } 
    
   isnsRegPortalPort           OBJECT-TYPE 
       SYNTAX                  InetPortNumber 
       MAX-ACCESS              read-only 
       STATUS                  current 
       DESCRIPTION 
   "The port number for this Portal as defined in the 
    iSNS Specification [iSNS].  Whether the Portal type is TCP 
    or UDP is indicated by isnsRegPortalPortType." 
       REFERENCE "RFC 4171, Section 6" 
       ::= { isnsRegPortalEntry 5 } 
    
   isnsRegPortalSymName        OBJECT-TYPE 
       SYNTAX                  SnmpAdminString (SIZE (0..255)) 
       MAX-ACCESS              read-only 
       STATUS                  current 
       DESCRIPTION 
   "The optional Symbolic Name for this Portal as defined in 
    the iSNS Specification [iSNS].  If not provided then the 
    string SHALL be zero length." 
       REFERENCE "RFC 4171, Section 6" 
       ::= { isnsRegPortalEntry 6 } 
    
   isnsRegPortalEsiInterval    OBJECT-TYPE 
       SYNTAX                  Unsigned32 ( 0 .. 4294967295 ) 
       MAX-ACCESS              read-only 
       STATUS                  current 
       DESCRIPTION 
   "The Entity Status Inquiry (ESI) Interval for this Portal 
    as defined in the iSNS Specification [iSNS]." 
       REFERENCE "RFC 4171, Section 6" 
       ::= { isnsRegPortalEntry 7 } 
    
   isnsRegPortalEsiPortType    OBJECT-TYPE 
       SYNTAX                  IsnsPortalPortTypeId 
       MAX-ACCESS              read-only 
       STATUS                  current 
       DESCRIPTION 
   "The port type for the ESI Port, either UDP or TCP, as 
    defined in the iSNS Specification [iSNS]." 
       REFERENCE "RFC 4171, Section 6" 
       ::= { isnsRegPortalEntry 8 } 
    
   isnsRegPortalEsiPort        OBJECT-TYPE 
       SYNTAX                  InetPortNumber 
       MAX-ACCESS              read-only 
       STATUS                  current 
       DESCRIPTION 
   "The TCP or UDP port number used for ESI monitoring.  Whether 
    the port type is TCP or UDP is indicated by 
    isnsRegPortalEsiPortType." 
    
   Gibbons                Expires July 2006                        41 
   Internet Draft              iSNS MIB                   January 2006 

       REFERENCE "RFC 4171, Section 6" 
       ::= { isnsRegPortalEntry 9 } 
    
   isnsRegPortalScnPortType    OBJECT-TYPE 
       SYNTAX                  IsnsPortalPortTypeId 
       MAX-ACCESS              read-only 
       STATUS                  current 
       DESCRIPTION 
   "The port type for the SCN Port, either UDP or TCP, as 
    defined in the iSNS Specification [iSNS]." 
       REFERENCE "RFC 4171, Section 6" 
       ::= { isnsRegPortalEntry 10 } 
    
   isnsRegPortalScnPort        OBJECT-TYPE 
       SYNTAX                  InetPortNumber 
       MAX-ACCESS              read-only 
       STATUS                  current 
       DESCRIPTION 
   "The TCP or UDP port used to receive SCN messages from the 
    iSNS Server.  Whether the port type is TCP or UDP is 
    indicated by isnsRegPortalScnPortType." 
       REFERENCE "RFC 4171, Section 6" 
       ::= { isnsRegPortalEntry 11 } 
    
   isnsRegPortalSecurityInfo   OBJECT-TYPE 
       SYNTAX                  IsnsPortalSecurityBitmapId 
       MAX-ACCESS              read-only 
       STATUS                  current 
       DESCRIPTION 
   "Indicates security attribute settings for the Portal as 
    registered in the Portal Security Bitmap attribute.  The bit 
    for bitmapVALID must be set in order for this attribute to 
    contain valid information. 
    
    Setting a bit to true (1) indicates the feature is 
    enabled." 
       REFERENCE "RFC 4171, Section 6" 
       ::= { isnsRegPortalEntry 12 } 
    
   -- 
   -- iSNS Registered Portal Group Information 
   -- 
    
   isnsRegPortalGroupInfo      OBJECT IDENTIFIER 
                                  ::= { isnsReg  3 } 
    
   -- 
   -- iSNS Registered Portal Group (PG) Table 
   -- 
    
   isnsRegPgTable              OBJECT-TYPE 
       SYNTAX                  SEQUENCE OF IsnsRegPgEntry 
    
   Gibbons                Expires July 2006                        42 
   Internet Draft              iSNS MIB                   January 2006 

       MAX-ACCESS              not-accessible 
       STATUS                  current 
       DESCRIPTION 
   "A table containing the registered Portal Groups (PGs) in 
    the iSNS Server instance.  The number of entries is 
    dependent on the number of Portal Groups registered in 
    the iSNS." 
       ::= { isnsRegPortalGroupInfo 1 } 
    
   isnsRegPgEntry              OBJECT-TYPE 
       SYNTAX                  IsnsRegPgEntry 
       MAX-ACCESS              not-accessible 
       STATUS                  current 
       DESCRIPTION 
   "Information on one registered Portal Group in the iSNS 
    server instance.  The Entity Index is part of the table 
    index to quickly find Portal Groups that support Portals 
    and iSCSI Storage Nodes in a specific Entity." 
       INDEX   { isnsSrvrInstIndex, 
                 isnsRegEntityIdx, 
                 isnsRegPgIdx } 
       ::= { isnsRegPgTable 1 } 
    
   IsnsRegPgEntry ::= 
       SEQUENCE {  
          isnsRegPgIdx                IsnsPortalGroupIndexId, 
          isnsRegPgIscsiNodeIdx       IsnsNodeIndexId, 
          isnsRegPgIscsiName          SnmpAdminString, 
          isnsRegPgPortalPrtlIdx      IsnsPortalIndexId, 
          isnsRegPgPortalAddrType     InetAddressType, 
          isnsRegPgPortalAddr         InetAddress, 
          isnsRegPgPortalPortType     IsnsPortalPortTypeId, 
          isnsRegPgPortalPort         InetPortNumber, 
          isnsRegPgPGT                IsnsPortalGroupTagIdOrZero 
                } 
    
   isnsRegPgIdx                OBJECT-TYPE 
       SYNTAX                  IsnsPortalGroupIndexId 
       MAX-ACCESS              not-accessible 
       STATUS                  current 
       DESCRIPTION 
   "The PG Index for this node.  The index is created by the 
    iSNS Server instance for uniquely identifying registered 
    objects.  The PG object is registered at the same time a 
    Portal or Storage Node is registered using the iSNS 
    protocol." 
       REFERENCE "RFC 4171, Section 6" 
       ::= { isnsRegPgEntry 1 } 
    
   isnsRegPgIscsiNodeIdx       OBJECT-TYPE 
       SYNTAX                  IsnsNodeIndexId 
       MAX-ACCESS              read-only 
    
   Gibbons                Expires July 2006                        43 
   Internet Draft              iSNS MIB                   January 2006 

       STATUS                  current 
       DESCRIPTION 
   "The iSCSI Node Index for the node associated with this PG.  
    This index can be used to reference the 
    isnsRegIscsiNodeTable." 
       REFERENCE "RFC 4171, Section 6" 
       ::= { isnsRegPgEntry 2 } 
    
   isnsRegPgIscsiName          OBJECT-TYPE 
       SYNTAX                  SnmpAdminString (SIZE (0..223)) 
       MAX-ACCESS              read-only 
       STATUS                  current 
       DESCRIPTION 
   "The iSCSI Name of the initiator or target associated with 
    the storage node.  The iSCSI Name can not be longer then 
    223 bytes.  The iSNS Server internal maximum size is 224 
    bytes to provide NULL termination.  This is the PG iSCSI Name 
    that uniquely identifies the iSCSI Storage Node that is 
    associated with this PG." 
       ::= { isnsRegPgEntry 3 } 
    
   isnsRegPgPortalPrtlIdx      OBJECT-TYPE 
       SYNTAX                  IsnsPortalIndexId 
       MAX-ACCESS              read-only 
       STATUS                  current 
       DESCRIPTION 
   "The Portal Index for the Portal associated with this PG.  
    This index can be used to reference the isnsRegPortalTable." 
       ::= { isnsRegPgEntry 4 } 
    
   isnsRegPgPortalAddrType     OBJECT-TYPE 
       SYNTAX                  InetAddressType 
       MAX-ACCESS              read-only 
       STATUS                  current 
       DESCRIPTION 
   "The type of Inet address in isnsRegPgPortalAddr." 
       ::= { isnsRegPgEntry 5 } 
    
   isnsRegPgPortalAddr         OBJECT-TYPE 
       SYNTAX                  InetAddress 
       MAX-ACCESS              read-only 
       STATUS                  current 
       DESCRIPTION 
   "The Inet Address for the Portal that is associated with  
    the PG." 
       REFERENCE "RFC 4171, Section 6" 
       ::= { isnsRegPgEntry 6 } 
    
   isnsRegPgPortalPortType     OBJECT-TYPE 
       SYNTAX                  IsnsPortalPortTypeId 
       MAX-ACCESS              read-only 
       STATUS                  current 
    
   Gibbons                Expires July 2006                        44 
   Internet Draft              iSNS MIB                   January 2006 

       DESCRIPTION 
   "The port type, either UDP or TCP, for the Portal that 
    is associated with this registered PG object." 
       REFERENCE "RFC 4171, Section 6" 
       ::= { isnsRegPgEntry 7 } 
    
   isnsRegPgPortalPort         OBJECT-TYPE 
       SYNTAX                  InetPortNumber 
       MAX-ACCESS              read-only 
       STATUS                  current 
       DESCRIPTION 
   "The port number for the Portal that is associated with 
    this registered PG object.  Whether the Portal type is 
    TCP or UDP is indicated by isnsRegPgPortalPortType." 
       REFERENCE "RFC 4171, Section 6" 
       ::= { isnsRegPgEntry 8 } 
    
   isnsRegPgPGT                OBJECT-TYPE 
       SYNTAX                  IsnsPortalGroupTagIdOrZero 
       MAX-ACCESS              read-only 
       STATUS                  current 
       DESCRIPTION 
   "The Portal Group Tag (PGT) for the registered iSCSI Portal 
    Group object in an iSNS Server instance.  This indicates 
    the tag value that the Portal uses for access to the iSCSI 
    Storage Node.  The PGT is used for coordinated access between 
    multiple Portals, as described in the iSCSI Specification 
    [iSCSI].  The value of zero indicates a NULL value, or no 
    association." 
       REFERENCE "RFC 4171, Section 6" 
       ::= { isnsRegPgEntry 9 } 
    
   -- 
   -- iSNS Registered iSCSI Node Information 
   -- 
    
   isnsRegIscsiNodeInfo  OBJECT IDENTIFIER ::= { isnsReg  4 } 
    
   -- 
   -- iSNS Registered iSCSI Node Table 
   -- 
    
   isnsRegIscsiNodeTable       OBJECT-TYPE 
       SYNTAX                  SEQUENCE OF IsnsRegIscsiNodeEntry 
       MAX-ACCESS              not-accessible 
       STATUS                  current 
       DESCRIPTION 
   "A table containing the registered iSCSI Nodes in the iSNS 
    server instance.  Storage devices register using the iSNS 
    protocol.  While a device cannot be registered in an iSNS 
    server using SNMP, an entry can be deleted in order to 
    remove 'stale' entries. The number of entries is related 
    
   Gibbons                Expires July 2006                        45 
   Internet Draft              iSNS MIB                   January 2006 

    to the number of iSCSI nodes registered in the iSNS." 
       ::= { isnsRegIscsiNodeInfo 1 } 
    
   isnsRegIscsiNodeEntry       OBJECT-TYPE 
       SYNTAX                  IsnsRegIscsiNodeEntry 
       MAX-ACCESS              not-accessible 
       STATUS                  current 
       DESCRIPTION 
   "Information on one iSCSI node that has been registered in 
    the iSNS Server instance.  The RowStatus managed object 
    provides a method to delete registered nodes that were not 
    properly deregistered / removed through iSNSP.  New rows 
    cannot be added using SNMP." 
       INDEX { isnsSrvrInstIndex, 
               isnsRegEntityIdx, 
               isnsRegIscsiNodeIdx } 
       ::= { isnsRegIscsiNodeTable 1 } 
    
   IsnsRegIscsiNodeEntry ::= SEQUENCE {  
       isnsRegIscsiNodeIdx            IsnsNodeIndexId, 
       isnsRegIscsiNodeName           SnmpAdminString, 
       isnsRegIscsiNodeType           IsnsNodeTypeId, 
       isnsRegIscsiNodeAlias          SnmpAdminString, 
       isnsRegIscsiNodeScnBitmap      IsnsScnBitmapId, 
       isnsRegIscsiNodeWwnToken       FcNameIdOrZero, 
       isnsRegIscsiNodeAuthMethod     SnmpAdminString 
                                    } 
    
   isnsRegIscsiNodeIdx         OBJECT-TYPE 
       SYNTAX                  IsnsNodeIndexId 
       MAX-ACCESS              not-accessible 
       STATUS                  current 
       DESCRIPTION 
   "The Node Index for this node.  The index is created by the 
    iSNS Server for mapping between registered objects.  The 
    index used for a specific node name is only persistent 
    across reboots for nodes that have been registered in a 
    Discovery Domain (DD).  If a node is not registered in any 
    DD, then the index used for a node can change after a 
    server reinitialization." 
       REFERENCE "RFC 4171, Section 6" 
       ::= { isnsRegIscsiNodeEntry 1 } 
    
   isnsRegIscsiNodeName        OBJECT-TYPE 
       SYNTAX                  SnmpAdminString (SIZE (0..223)) 
       MAX-ACCESS              read-only 
       STATUS                  current 
       DESCRIPTION 
   "The iSCSI Name of the initiator or target associated with 
    the storage node.  The iSCSI Name can not be longer then 
    223 bytes.  The iSNS Server internal maximum size is 224 
    bytes to provide NULL termination.  This is the iSCSI Name 
    
   Gibbons                Expires July 2006                        46 
   Internet Draft              iSNS MIB                   January 2006 

    that uniquely identifies the initiator, initiator/target, 
    target, or control node in the network." 
       REFERENCE "RFC 4171, Section 6" 
       ::= { isnsRegIscsiNodeEntry 2 } 
    
   isnsRegIscsiNodeType        OBJECT-TYPE 
       SYNTAX                  IsnsNodeTypeId 
       MAX-ACCESS              read-only 
       STATUS                  current 
       DESCRIPTION 
   "The Node Type bit-map defining the functions of this 
    iSCSI node. 
                  Bit         Node Type 
              ---------       --------- 
              All Others       RESERVED 
                 29            Control 
                 30            Initiator 
                 31            Target 
   " 
       REFERENCE "RFC 4171, Section 6" 
       ::= { isnsRegIscsiNodeEntry 3 } 
    
   isnsRegIscsiNodeAlias       OBJECT-TYPE 
       SYNTAX                  SnmpAdminString (SIZE (0..255)) 
       MAX-ACCESS              read-only 
       STATUS                  current 
       DESCRIPTION 
   "The Alias name of the iSCSI node.  This is a variable-length 
    text-based description of up to 255 bytes." 
       REFERENCE "RFC 4171, Section 6" 
       ::= { isnsRegIscsiNodeEntry 4 } 
    
   isnsRegIscsiNodeScnBitmap   OBJECT-TYPE 
       SYNTAX                  IsnsScnBitmapId 
       MAX-ACCESS              read-only 
       STATUS                  current 
       DESCRIPTION 
   "The State Change Notification (SCN) bitmap for a node. 
        Bit Field          Flag Description 
        ---------          ---------------- 
           0               INITIATOR AND SELF INFORMATION ONLY 
           1               TARGET AND SELF INFORMATION ONLY  
           2               MANAGEMENT REGISTRATION/SCN 
           3               REGISTERED OBJECT REMOVED 
           4               REGISTERED OBJECT ADDED 
           5               REGISTERED OBJECT UPDATED 
           6               DD/DDS MEMBER REMOVED (MGT REG/SCN 
                             ONLY) 
           7               DD/DDS MEMBER ADDED (MGT REG/SCN 
                             ONLY) 
    
    Setting a bit to true (1) indicates the flag is 
    
   Gibbons                Expires July 2006                        47 
   Internet Draft              iSNS MIB                   January 2006 

    enabled." 
       REFERENCE "RFC 4171, Section 6" 
       ::= { isnsRegIscsiNodeEntry 5 } 
    
   isnsRegIscsiNodeWwnToken    OBJECT-TYPE 
       SYNTAX                  FcNameIdOrZero 
       MAX-ACCESS              read-only 
       STATUS                  current 
       DESCRIPTION 
   "This contains an optional globally unique 64-bit integer 
    value that can be used to represent the World Wide Node 
    Name of the iSCSI device in a Fibre Channel fabric. This 
    identifier is used during the device registration process, 
    and MUST conform to the requirements in [FC-FS].  The 
    value of zero for this managed object indicates that a 
    Node WWN token has not been assigned." 
       REFERENCE "RFC 4171, Section 6" 
       ::= { isnsRegIscsiNodeEntry 6 } 
    
   isnsRegIscsiNodeAuthMethod  OBJECT-TYPE 
       SYNTAX                  SnmpAdminString (SIZE (0..255)) 
       MAX-ACCESS              read-only 
       STATUS                  current 
       DESCRIPTION 
   "This attribute contains a null-terminated string containing 
    UTF-8 text listing the iSCSI authentication methods enabled 
    for this iSCSI Node, in order of preference.  The text values 
    used to identify iSCSI authentication methods are embedded in 
    this string attribute and delineated by a comma.  The text 
    values are identical to those found in the main iSCSI draft; 
    additional vendor-specific text values are also possible." 
       REFERENCE "RFC 4171, Section 6" 
       ::= { isnsRegIscsiNodeEntry 7 } 
    
   -- 
   -- iSNS Registered FC Port Information 
   -- 
    
   isnsRegFcPortInfo           OBJECT IDENTIFIER 
                                      ::= { isnsReg  5 } 
    
   -- 
   -- iSNS Registered FC Port Table 
   -- 
    
   isnsRegFcPortTable          OBJECT-TYPE 
       SYNTAX                  SEQUENCE OF IsnsRegFcPortEntry 
       MAX-ACCESS              not-accessible 
       STATUS                  current 
       DESCRIPTION 
   "Information on registered FC Ports in the iSNS." 
       ::= { isnsRegFcPortInfo 1 } 
    
   Gibbons                Expires July 2006                        48 
   Internet Draft              iSNS MIB                   January 2006 

    
   isnsRegFcPortEntry          OBJECT-TYPE 
       SYNTAX                   IsnsRegFcPortEntry 
       MAX-ACCESS              not-accessible 
       STATUS                  current 
       DESCRIPTION 
   "Information on one FC Port that has been registered in 
    iSNS." 
       INDEX { isnsSrvrInstIndex, 
               isnsRegEntityIdx, 
               isnsRegFcPortWwpn } 
       ::= { isnsRegFcPortTable 1 } 
    
   IsnsRegFcPortEntry ::= SEQUENCE {  
       isnsRegFcPortWwpn              FcNameIdOrZero, 
       isnsRegFcPortID                FcAddressIdOrZero, 
       isnsRegFcPortType              Unsigned32, 
       isnsRegFcPortSymName           SnmpAdminString, 
       isnsRegFcPortFabricPortWwn     FcNameIdOrZero, 
       isnsRegFcPortHA                FcAddressIdOrZero, 
       isnsRegFcPortAddrType          InetAddressType, 
       isnsRegFcPortAddr              InetAddress, 
       isnsRegFcPortFcCos             IsnsCosBitmapId, 
       isnsRegFcPortFc4Types          OCTET STRING, 
       isnsRegFcPortFc4Descr          OCTET STRING, 
       isnsRegFcPortFc4Features       OCTET STRING, 
       isnsRegFcPortScnBitmap         IsnsScnBitmapId, 
       isnsRegFcPortRole              IsnsNodeTypeId, 
       isnsRegFcPortFcNodeWwn         FcNameIdOrZero, 
       isnsRegFcPortPpnWwn            FcNameIdOrZero 
                                   } 
    
   isnsRegFcPortWwpn           OBJECT-TYPE 
       SYNTAX                  FcNameIdOrZero 
       MAX-ACCESS              not-accessible 
       STATUS                  current 
       DESCRIPTION 
   "The FC Port's World Wide Port Name as defined in the iSNS 
    Specification [iSNS].  The value of zero is not valid for 
    this managed object." 
       REFERENCE "RFC 4171, Section 6" 
       ::= { isnsRegFcPortEntry 1 } 
    
   isnsRegFcPortID             OBJECT-TYPE 
       SYNTAX                  FcAddressIdOrZero 
       MAX-ACCESS              read-only 
       STATUS                  current 
       DESCRIPTION       
   "The FC Port's Port ID as defined in the iSNS Specification 
    [iSNS]." 
       REFERENCE "RFC 4171, Section 6" 
       ::= { isnsRegFcPortEntry 2 } 
    
   Gibbons                Expires July 2006                        49 
   Internet Draft              iSNS MIB                   January 2006 

    
   isnsRegFcPortType           OBJECT-TYPE 
       SYNTAX                  Unsigned32 ( 0 .. 65535 ) 
       MAX-ACCESS              read-only 
       STATUS                  current 
       DESCRIPTION 
   "The FC Port Port Type as defined in the iSNS Specification 
    [iSNS] and the Fibre Channel Generic Services [FC-GS] 
    Specification. Current values are as shown below: 
           unknown      (0), 
           nPort        (1), 
           nlPort       (2), 
           fNlPort      (3), 
           fPort        (129),     -- x'81' 
           flPort       (130),     -- x'82' 
           ePort        (132),     -- x'84' 
           bPort        (133),     -- x'85' 
           mFcpPort     (65297),   -- x'FF11' 
           iFcpPort     (65298),   -- x'FF12' 
           unknownEnd   (65535) 
    ." 
       REFERENCE "RFC 4171, Section 6" 
       ::= { isnsRegFcPortEntry 3 } 
    
   isnsRegFcPortSymName      OBJECT-TYPE 
       SYNTAX                SnmpAdminString (SIZE (0..255)) 
       MAX-ACCESS            read-only 
       STATUS                current 
       DESCRIPTION 
   "The optional FC Port Port Symbolic Name as defined in the 
    iSNS Specification [iSNS].  If not provided then the string 
    SHALL be zero length." 
       REFERENCE "RFC 4171, Section 6" 
       ::= { isnsRegFcPortEntry 4 } 
    
   isnsRegFcPortFabricPortWwn  OBJECT-TYPE 
       SYNTAX                  FcNameIdOrZero 
       MAX-ACCESS              read-only 
       STATUS                  current 
       DESCRIPTION 
   "The Fabric Port WWN for this entry as defined in the iSNS 
    Specification [iSNS].  The value of zero for this managed 
    object indicates that the Fabric Port WWN is not known, 
    or has not yet been registered with the iSNS Server." 
       REFERENCE "RFC 4171, Section 6" 
      ::= { isnsRegFcPortEntry 5 } 
    
   isnsRegFcPortHA             OBJECT-TYPE 
       SYNTAX                  FcAddressIdOrZero 
       MAX-ACCESS              read-only 
       STATUS                  current 
       DESCRIPTION       
    
   Gibbons                Expires July 2006                        50 
   Internet Draft              iSNS MIB                   January 2006 

   "The FC Port Hard Address as defined in the iSNS 
    Specification [iSNS]." 
       REFERENCE "RFC 4171, Section 6" 
       ::= { isnsRegFcPortEntry 6 } 
    
   isnsRegFcPortAddrType       OBJECT-TYPE 
       SYNTAX                  InetAddressType 
       MAX-ACCESS              read-only 
       STATUS                  current 
       DESCRIPTION 
   "The type of Inet address in the isnsRegFcPortAddr." 
       ::= { isnsRegFcPortEntry 7 } 
    
   isnsRegFcPortAddr           OBJECT-TYPE 
       SYNTAX                  InetAddress 
       MAX-ACCESS              read-only 
       STATUS                  current 
       DESCRIPTION 
   "The FC Port Inet Address as defined in the iSNS 
    Specification [iSNS]." 
       REFERENCE "RFC 4171, Section 6" 
       ::= { isnsRegFcPortEntry 8 } 
    
   isnsRegFcPortFcCos          OBJECT-TYPE 
       SYNTAX                  IsnsCosBitmapId 
       MAX-ACCESS              read-only 
       STATUS                  current 
       DESCRIPTION 
   "The FC Port Class of Service as defined in the iSNS 
    Specification [iSNS]." 
       REFERENCE  "RFC 4171, Section 6" 
       ::= { isnsRegFcPortEntry 9 } 
    
   isnsRegFcPortFc4Types       OBJECT-TYPE 
       SYNTAX                  OCTET STRING (SIZE (32)) 
       MAX-ACCESS              read-only 
       STATUS                  current 
       DESCRIPTION 
   "The FC Port FC-4 Types as defined in the iSNS 
    Specification [iSNS]." 
       REFERENCE "RFC 4171, Section 6" 
       ::= { isnsRegFcPortEntry 10 } 
    
   isnsRegFcPortFc4Descr       OBJECT-TYPE 
       SYNTAX                  OCTET STRING(SIZE(0..255)) 
       MAX-ACCESS              read-only 
       STATUS                  current 
       DESCRIPTION 
   "The FC Port FC-4 Descriptors as defined in the iSNS 
    Specification [iSNS]." 
        REFERENCE "RFC 4171, Section 6" 
      ::= { isnsRegFcPortEntry 11 } 
    
   Gibbons                Expires July 2006                        51 
   Internet Draft              iSNS MIB                   January 2006 

    
   isnsRegFcPortFc4Features    OBJECT-TYPE 
       SYNTAX                  OCTET STRING (SIZE (128)) 
       MAX-ACCESS              read-only 
       STATUS                  current 
       DESCRIPTION 
   "The FC Port FC-4 Features as defined in the iSNS 
    Specification [iSNS]." 
       REFERENCE "RFC 4171, Section 6" 
       ::= { isnsRegFcPortEntry 12 } 
    
   isnsRegFcPortScnBitmap      OBJECT-TYPE 
       SYNTAX                  IsnsScnBitmapId 
       MAX-ACCESS              read-only 
       STATUS                  current 
       DESCRIPTION 
   "The State Change Notification (SCN) bitmap for a FC Port. 
        Bit Field          Flag Description 
        ---------          ---------------- 
           0               INITIATOR AND SELF INFORMATION ONLY 
           1               TARGET AND SELF INFORMATION ONLY  
           2               MANAGEMENT REGISTRATION/SCN 
           3               REGISTERED OBJECT REMOVED 
           4               REGISTERED OBJECT ADDED 
           5               REGISTERED OBJECT UPDATED 
           6               DD/DDS MEMBER REMOVED (MGT REG/SCN 
                             ONLY) 
           7               DD/DDS MEMBER ADDED (MGT REG/SCN 
                             ONLY) 
    
    Setting a bit to true (1) indicates the flag is 
    enabled." 
       REFERENCE "RFC 4171, Section 6" 
       ::= { isnsRegFcPortEntry 13 } 
    
   isnsRegFcPortRole           OBJECT-TYPE 
       SYNTAX                  IsnsNodeTypeId 
       MAX-ACCESS              read-only 
       STATUS                  current 
       DESCRIPTION 
   "The Node Type bit-map defining the functions of this FC Port. 
                  Bit         Node Type 
              ---------       --------- 
              All Others       RESERVED 
                 29            Control 
                 30            Initiator 
                 31            Target 
   " 
       REFERENCE "RFC 4171, Section 6" 
       ::= { isnsRegFcPortEntry 14 } 
    
   isnsRegFcPortFcNodeWwn      OBJECT-TYPE 
    
   Gibbons                Expires July 2006                        52 
   Internet Draft              iSNS MIB                   January 2006 

       SYNTAX                  FcNameIdOrZero 
       MAX-ACCESS              read-only 
       STATUS                  current 
       DESCRIPTION 
   "The FC Node WWN of the FC Node that has been associated with 
    this FC Port as defined in the iSNS Specification [iSNS].  
    This managed object may contain the value of zero prior to 
    a device registering this value with the iSNS Server." 
       REFERENCE "RFC 4171, Section 6" 
       ::= { isnsRegFcPortEntry 15 } 
    
   isnsRegFcPortPpnWwn         OBJECT-TYPE 
       SYNTAX                  FcNameIdOrZero 
       MAX-ACCESS              read-only 
       STATUS                  current 
       DESCRIPTION 
   "The Permanent Port Name attribute is the FC Port Name WWPN of 
    the first Storage Node registered in the iSNS Database that is 
    associated with a particular FC Device (FC Node).  The PPN of 
    all subsequent Storage Node registrations that are associated 
    with that FC Device (FC Node) SHALL be set to the FC Port Name 
    WWPN of the first Storage Node, as defined in the iSNS 
    Specification [iSNS].  This managed object may contain the 
    value of zero prior to a device registering this value with 
    the iSNS Server" 
       REFERENCE "RFC 4171, Section 6" 
       ::= { isnsRegFcPortEntry 16 } 
    
   -- 
   -- iSNS Registered FC Node Information 
   -- 
    
   isnsRegFcNodeInfo     OBJECT IDENTIFIER ::= { isnsReg  6 } 
    
   -- 
   -- iSNS Registered FC Node Table 
   -- 
    
   isnsRegFcNodeTable          OBJECT-TYPE 
       SYNTAX                  SEQUENCE OF IsnsRegFcNodeEntry 
       MAX-ACCESS              not-accessible 
       STATUS                  current 
       DESCRIPTION 
   "A table containing the registered FC Nodes in the iSNS." 
       ::= { isnsRegFcNodeInfo 1 } 
    
   isnsRegFcNodeEntry          OBJECT-TYPE 
       SYNTAX                  IsnsRegFcNodeEntry 
       MAX-ACCESS              not-accessible 
       STATUS                  current 
       DESCRIPTION 
   "Information on one registered FC node that has been regisered 
    
   Gibbons                Expires July 2006                        53 
   Internet Draft              iSNS MIB                   January 2006 

    in the iSNS." 
       INDEX { isnsSrvrInstIndex, 
                isnsRegFcNodeWwn } 
       ::= { isnsRegFcNodeTable 1 } 
    
   IsnsRegFcNodeEntry ::= SEQUENCE {  
       isnsRegFcNodeWwn            FcNameIdOrZero, 
       isnsRegFcNodeSymName        SnmpAdminString, 
       isnsRegFcNodeAddrType       InetAddressType, 
       isnsRegFcNodeAddr           InetAddress, 
       isnsRegFcNodeIPA            OCTET STRING, 
       isnsRegFcNodeProxyIscsiName SnmpAdminString 
                                   } 
    
   isnsRegFcNodeWwn            OBJECT-TYPE 
       SYNTAX                  FcNameIdOrZero 
       MAX-ACCESS              not-accessible 
       STATUS                  current 
       DESCRIPTION 
   "The FC Node World Wide Node Name as defined in the iSNS 
    Specification [iSNS].  The value of zero is not valid for 
    this managed object." 
       REFERENCE "RFC 4171, Section 6" 
       ::= { isnsRegFcNodeEntry 1 } 
    
   isnsRegFcNodeSymName        OBJECT-TYPE 
       SYNTAX                  SnmpAdminString (SIZE (0..255)) 
       MAX-ACCESS              read-only 
       STATUS                  current 
       DESCRIPTION 
   "The optional FC Node Symbolic Name of the node as 
    defined in the iSNS Specification [iSNS].  This is a 
    variable-length text-based description.  If not 
    provided then the string SHALL be zero length." 
       REFERENCE "RFC 4171, Section 6" 
       ::= { isnsRegFcNodeEntry 2 } 
    
   isnsRegFcNodeAddrType       OBJECT-TYPE 
       SYNTAX                  InetAddressType 
       MAX-ACCESS              read-only 
       STATUS                  current 
       DESCRIPTION 
   "The type of Inet address in isnsRegFcNodeAddr." 
       ::= { isnsRegFcNodeEntry 3 } 
    
   isnsRegFcNodeAddr           OBJECT-TYPE 
       SYNTAX                  InetAddress 
       MAX-ACCESS              read-only 
       STATUS                  current 
       DESCRIPTION 
   "The FC Node Inet address of the node as defined in the 
    iSNS Specification [iSNS]." 
    
   Gibbons                Expires July 2006                        54 
   Internet Draft              iSNS MIB                   January 2006 

       REFERENCE "RFC 4171, Section 6" 
       ::= { isnsRegFcNodeEntry 4 } 
     
   isnsRegFcNodeIPA            OBJECT-TYPE 
       SYNTAX                  OCTET STRING (SIZE(8)) 
       MAX-ACCESS              read-only 
       STATUS                  current 
       DESCRIPTION 
   "This managed object identifies the FC Initial Process 
    Associator of the node as defined in the iSNS 
    Specification [iSNS]." 
       REFERENCE "RFC 4171, Section 6" 
       ::= { isnsRegFcNodeEntry 5 } 
    
   isnsRegFcNodeProxyIscsiName OBJECT-TYPE 
       SYNTAX                  SnmpAdminString (SIZE (0..223)) 
       MAX-ACCESS              read-only 
       STATUS                  current 
       DESCRIPTION 
   "The iSCSI Name used to represent the FC Node in the IP 
    network. It is used as a pointer to the matching iSCSI Name 
    entry in the iSNS Server.  Its value is usually registered 
    by an FC-iSCSI gateway connecting the IP network to the 
    fabric containing the FC device." 
       REFERENCE  "RFC 4171, Section 6" 
       ::= { isnsRegFcNodeEntry 6 } 
    
   -- 
   -- Basic information for the registered FC Node object 
   -- 
    
   isnsRegFcNodeInfoTable      OBJECT-TYPE 
       SYNTAX                  SEQUENCE OF IsnsRegFcNodeInfoEntry 
       MAX-ACCESS              not-accessible 
       STATUS                  current 
       DESCRIPTION 
   "A table containing basic information on registered FC Nodes 
    in the iSNS.  The number of entries in the table is dependent 
    on the number of FC Nodes registered in the iSNS." 
       ::= { isnsRegFcNodeInfo 2 } 
    
   isnsRegFcNodeInfoEntry      OBJECT-TYPE 
       SYNTAX                  IsnsRegFcNodeInfoEntry 
       MAX-ACCESS              not-accessible 
       STATUS                  current 
       DESCRIPTION 
   "Information on one FC Node that has been registered in the 
    iSNS." 
       INDEX   { isnsSrvrInstIndex, 
                  isnsRegFcNodeWwn } 
       ::= { isnsRegFcNodeInfoTable 1 } 
    
    
   Gibbons                Expires July 2006                        55 
   Internet Draft              iSNS MIB                   January 2006 

   IsnsRegFcNodeInfoEntry ::= 
       SEQUENCE {  
          isnsRegFcNodeInfoNumFcPorts   Unsigned32 
              } 
    
   isnsRegFcNodeInfoNumFcPorts OBJECT-TYPE 
       SYNTAX                  Unsigned32 ( 0 .. 4294967295 ) 
       MAX-ACCESS              read-only 
       STATUS                  current 
       DESCRIPTION 
   "The number of FC Ports associated with this FC Node." 
       ::= { isnsRegFcNodeInfoEntry 1 } 
    
   -- 
   --  Mapping from FC Node to Entity - FC Port 
   -- 
    
   isnsRegFcNodePortTable      OBJECT-TYPE 
       SYNTAX                  SEQUENCE OF IsnsRegFcNodePortEntry 
       MAX-ACCESS              not-accessible 
       STATUS                  current 
       DESCRIPTION 
   "A table containing the mapping of registered FC Nodes to 
    associated registered iFCP Ports and registered Entity 
    objects in the iSNS Server instance." 
       ::= { isnsRegFcNodeInfo 3 } 
    
   isnsRegFcNodePortEntry      OBJECT-TYPE 
       SYNTAX                  IsnsRegFcNodePortEntry 
       MAX-ACCESS              not-accessible 
       STATUS                  current 
       DESCRIPTION 
   "Information on one mapping from an FC Port and Entity to an 
    FC node registered in the iSNS." 
       INDEX { isnsSrvrInstIndex, 
               isnsRegFcNodeWwn, 
               isnsRegFcPortWwpn } 
       ::= { isnsRegFcNodePortTable 1 } 
    
   IsnsRegFcNodePortEntry ::= SEQUENCE {  
           isnsRegFcNodePortEntityEIdx IsnsEntityIndexId 
                                       } 
    
   isnsRegFcNodePortEntityEIdx OBJECT-TYPE 
       SYNTAX                  IsnsEntityIndexId 
       MAX-ACCESS              read-only 
       STATUS                  current 
       DESCRIPTION 
   "The Entity Index for the registered Entity object associated 
    with the FC Port and FC Node." 
       ::= { isnsRegFcNodePortEntry 1 } 
    
    
   Gibbons                Expires July 2006                        56 
   Internet Draft              iSNS MIB                   January 2006 

   -- 
   -- Removed all iSNS Client related objects 
   -- 
    
   -- 
   -- iSNS Notification Block -------------------------------- 
   -- 
    
   isnsNotification            OBJECT IDENTIFIER 
                                     ::= { isnsObj 3 } 
    
   isnsNotificationInfo        OBJECT IDENTIFIER 
                                     ::= { isnsNotification 1 } 
    
   isnsInstInfo                OBJECT-TYPE 
       SYNTAX                  SnmpAdminString (SIZE (0..80)) 
       MAX-ACCESS              accessible-for-notify 
       STATUS                  current 
       DESCRIPTION 
   "Textual information about the iSNS Server or client 
    notification.  An example is: iSNS Client Started, or iSNS 
    Server Started, information that would be included in the 
    appropriate notification." 
       ::= { isnsNotificationInfo 1 } 
    
   isnsAddrTypeNotifctn        OBJECT-TYPE 
       SYNTAX                  InetAddressType 
       MAX-ACCESS              accessible-for-notify 
       STATUS                  current 
       DESCRIPTION 
   "The type of Inet address in isnsSrvrAddrNotifctn." 
       ::= { isnsNotificationInfo 2 } 
    
   isnsAddrNotifctn            OBJECT-TYPE 
       SYNTAX                  InetAddress 
       MAX-ACCESS              accessible-for-notify 
       STATUS                  current 
       DESCRIPTION 
   "Identifies the IP address of the iSNS Server." 
       ::= { isnsNotificationInfo 3 } 
    
   isnsTcpPortNotifctn         OBJECT-TYPE 
       SYNTAX                  InetPortNumber 
       MAX-ACCESS              accessible-for-notify 
       STATUS                  current 
       DESCRIPTION 
   "Indicates the TCP port the iSNS Server is using, 
    or 0 if TCP based registrations are not supported." 
       ::= { isnsNotificationInfo 4 } 
    
   isnsUdpPortNotifctn         OBJECT-TYPE 
       SYNTAX                  InetPortNumber 
    
   Gibbons                Expires July 2006                        57 
   Internet Draft              iSNS MIB                   January 2006 

       MAX-ACCESS              accessible-for-notify 
       STATUS                  current 
       DESCRIPTION 
   "Indicates the UDP port the iSNS Server is using, 
    or 0 if UDP based registrations are not supported." 
       ::= { isnsNotificationInfo 5 } 
    
   isnsNotificationPrefix OBJECT IDENTIFIER 
                              ::= { isnsNotification 0 } 
    
   isnsServerStart             NOTIFICATION-TYPE 
       OBJECTS {  
           isnsInstInfo, 
           isnsAddrTypeNotifctn, 
           isnsAddrNotifctn, 
           isnsTcpPortNotifctn, 
           isnsUdpPortNotifctn 
               } 
       STATUS                  current 
       DESCRIPTION 
   "This notification is sent when an iSNS Server begins 
    operation.  The notification provides the following: 
           isnsInstInfo         : iSNS Server textual information 
           isnsAddrTypeNotifctn : iSNS Server address type 
           isnsAddrNotifctn     : iSNS Server address 
           isnsTcpPortNotifctn  : iSNS Server TCP Port 
           isnsUdpPortNotifctn  : iSNS Server UDP Port 
   " 
       ::= { isnsNotificationPrefix 1 } 
    
   isnsServerShutdown          NOTIFICATION-TYPE 
       OBJECTS {  
           isnsInstInfo, 
           isnsAddrTypeNotifctn, 
           isnsAddrNotifctn, 
           isnsTcpPortNotifctn, 
           isnsUdpPortNotifctn 
               } 
       STATUS                  current 
       DESCRIPTION 
   "This notification is sent when an iSNS Server is 
    shutdown.  The notification provides the following: 
           isnsInstInfo         : iSNS Server textual information 
           isnsAddrTypeNotifctn : iSNS Server address type 
           isnsAddrNotifctn     : iSNS Server address 
           isnsTcpPortNotifctn  : iSNS Server TCP Port 
           isnsUdpPortNotifctn  : iSNS Server UDP Port 
   " 
       ::= { isnsNotificationPrefix 2 } 
    
    
   ------------------------------------------------------------ 
    
   Gibbons                Expires July 2006                        58 
   Internet Draft              iSNS MIB                   January 2006 

    
   isnsGroups OBJECT IDENTIFIER ::= { isnsConformance 1 } 
    
   isnsServerAttributesGroup      OBJECT-GROUP 
       OBJECTS { 
          isnsSrvrInstName, 
          isnsSrvrInstIsnsVersion, 
          isnsSrvrInstVendorInfo, 
          isnsSrvrInstPhyIndex, 
          isnsSrvrInstTcpPort, 
          isnsSrvrInstUdpPort, 
          isnsSrvrInstDiscontinuityTime, 
          isnsSrvrInstRole, 
          isnsSrvrInstDiscMthdsEnbld, 
          isnsSrvrInstDiscMcGrpType, 
          isnsSrvrInstDiscMcGrp, 
          isnsSrvrInstCntrlNodeAuth, 
          isnsSrvrInstEsiNonRespThrshld, 
          isnsSrvrInstEnblCntrlNdeMgtScn, 
          isnsSrvrInstDfltDdDdsStatus,  
          isnsSrvrInstUpdateDdDdsSpprtd, 
          isnsSrvrInstUpdateDdDdsEnbld 
               } 
       STATUS                  current 
       DESCRIPTION 
   "iSNS Server attributes." 
          ::= { isnsGroups 1 } 
    
   isnsServerNumObjGroup      OBJECT-GROUP 
       OBJECTS { 
          isnsNumDds, 
          isnsNumDd, 
          isnsNumEntities, 
          isnsNumPortals, 
          isnsNumPortalGroups, 
          isnsNumIscsiNodes, 
          isnsNumFcPorts, 
          isnsNumFcNodes, 
          isnsRegEntityInfoNumPortals, 
          isnsRegEntityInfoNumPortalGroups, 
          isnsRegEntityInfoNumIscsiNodes, 
          isnsRegEntityInfoNumFcPorts, 
          isnsRegEntityInfoNumFcNodes, 
          isnsRegFcNodeInfoNumFcPorts 
               } 
       STATUS                  current 
       DESCRIPTION 
   "Managed objects indicating the number of registered objects 
    in an iSNS Server or the number of registered objects 
    associated with a registered Entity.  These managed objects 
    are optional to implement." 
          ::= { isnsGroups 2 } 
    
   Gibbons                Expires July 2006                        59 
   Internet Draft              iSNS MIB                   January 2006 

    
   isnsServerIscsiCntlNodeGroup    OBJECT-GROUP 
       OBJECTS { 
          isnsCntlNodeIscsiNodeName 
               } 
       STATUS                  current 
       DESCRIPTION 
   "iSNS Server iSCSI control node managed objects." 
          ::= { isnsGroups 3 } 
    
   isnsServerIscsiDdsDdObjGroup   OBJECT-GROUP 
       OBJECTS { 
          isnsDdsSymbolicName, 
          isnsDdsStatus, 
          isnsDdSymbolicName, 
          isnsDdFeatures, 
          isnsDdMemberIscsiName, 
          isnsDdMemberIsRegistered, 
          isnsDdMemberPortalAddrType, 
          isnsDdMemberPortalAddr, 
          isnsDdMemberPortalPortType, 
          isnsDdMemberPortalPort, 
          isnsDdMemberPortalIsRegistered 
               } 
       STATUS                  current 
       DESCRIPTION 
   "iSNS Server DDS and DD managed objects for iSCSI." 
          ::= { isnsGroups 4 } 
    
   isnsServerIfcpDdsDdObjGroup    OBJECT-GROUP 
       OBJECTS { 
          isnsDdsSymbolicName, 
          isnsDdsStatus, 
          isnsDdSymbolicName, 
          isnsDdFeatures, 
          isnsDdMemberPortalAddrType, 
          isnsDdMemberPortalAddr, 
          isnsDdMemberPortalPortType, 
          isnsDdMemberPortalPort, 
          isnsDdMemberPortalIsRegistered, 
          isnsDdMemberFcIsRegistered 
               } 
       STATUS                  current 
       DESCRIPTION 
   "iSNS Server DDS and DD managed objects for iFCP." 
          ::= { isnsGroups 5 } 
    
   isnsServerRegIscsiObjGroup   OBJECT-GROUP 
       OBJECTS { 
          isnsRegEntityEID, 
          isnsRegEntityProtocol, 
          isnsRegEntityMgtAddrType, 
    
   Gibbons                Expires July 2006                        60 
   Internet Draft              iSNS MIB                   January 2006 

          isnsRegEntityMgtAddr, 
          isnsRegEntityTimestamp, 
          isnsRegEntityVersionMin, 
          isnsRegEntityVersionMax, 
          isnsRegEntityRegPeriod, 
          isnsRegEntityInfoNumPortals, 
          isnsRegEntityInfoNumPortalGroups, 
          isnsRegEntityInfoNumIscsiNodes, 
          isnsRegEntityInfoNumFcPorts, 
          isnsRegEntityInfoNumFcNodes, 
          isnsRegPortalAddrType, 
          isnsRegPortalAddr, 
          isnsRegPortalPortType, 
          isnsRegPortalPort, 
          isnsRegPortalSymName, 
          isnsRegPortalEsiInterval, 
          isnsRegPortalEsiPortType, 
          isnsRegPortalEsiPort, 
          isnsRegPortalScnPortType, 
          isnsRegPortalScnPort, 
          isnsRegPortalSecurityInfo, 
          isnsRegPgIscsiNodeIdx, 
          isnsRegPgIscsiName, 
          isnsRegPgPortalPrtlIdx, 
          isnsRegPgPortalAddrType, 
          isnsRegPgPortalAddr, 
          isnsRegPgPortalPortType, 
          isnsRegPgPortalPort, 
          isnsRegPgPGT, 
          isnsRegIscsiNodeName, 
          isnsRegIscsiNodeType, 
          isnsRegIscsiNodeAlias, 
          isnsRegIscsiNodeScnBitmap, 
          isnsRegIscsiNodeWwnToken, 
          isnsRegIscsiNodeAuthMethod 
               } 
       STATUS                  current 
       DESCRIPTION 
   "iSNS Server registered iSCSI managed objects." 
          ::= { isnsGroups 6 } 
    
   isnsServerRegIfcpObjGroup    OBJECT-GROUP 
       OBJECTS { 
          isnsRegEntityEID, 
          isnsRegEntityProtocol, 
          isnsRegEntityMgtAddrType, 
          isnsRegEntityMgtAddr, 
          isnsRegEntityTimestamp, 
          isnsRegEntityVersionMin, 
          isnsRegEntityVersionMax, 
          isnsRegEntityRegPeriod, 
          isnsRegEntityInfoNumPortals, 
    
   Gibbons                Expires July 2006                        61 
   Internet Draft              iSNS MIB                   January 2006 

          isnsRegEntityInfoNumPortalGroups, 
          isnsRegEntityInfoNumIscsiNodes, 
          isnsRegEntityInfoNumFcPorts, 
          isnsRegEntityInfoNumFcNodes, 
          isnsRegPortalAddrType, 
          isnsRegPortalAddr, 
          isnsRegPortalPortType, 
          isnsRegPortalPort, 
          isnsRegPortalSymName, 
          isnsRegPortalEsiInterval, 
          isnsRegPortalEsiPortType, 
          isnsRegPortalEsiPort, 
          isnsRegPortalScnPortType, 
          isnsRegPortalScnPort, 
          isnsRegPortalSecurityInfo, 
          isnsRegFcPortID, 
          isnsRegFcPortType, 
          isnsRegFcPortSymName, 
          isnsRegFcPortFabricPortWwn, 
          isnsRegFcPortHA, 
          isnsRegFcPortAddrType, 
          isnsRegFcPortAddr, 
          isnsRegFcPortFcCos, 
          isnsRegFcPortFc4Types, 
          isnsRegFcPortFc4Descr, 
          isnsRegFcPortFc4Features, 
          isnsRegFcPortScnBitmap, 
          isnsRegFcPortRole, 
          isnsRegFcPortFcNodeWwn, 
          isnsRegFcPortPpnWwn, 
          isnsRegFcNodeSymName, 
          isnsRegFcNodeAddrType, 
          isnsRegFcNodeAddr, 
          isnsRegFcNodeIPA, 
          isnsRegFcNodeProxyIscsiName, 
          isnsRegFcNodePortEntityEIdx 
               } 
       STATUS                  current 
       DESCRIPTION 
   "iSNS Server registered iFCP managed objects." 
          ::= { isnsGroups 7 } 
    
   isnsNotificationObjGroup    OBJECT-GROUP 
       OBJECTS { 
          isnsInstInfo, 
          isnsAddrTypeNotifctn, 
          isnsAddrNotifctn, 
          isnsTcpPortNotifctn, 
          isnsUdpPortNotifctn 
               } 
       STATUS                  current 
       DESCRIPTION 
    
   Gibbons                Expires July 2006                        62 
   Internet Draft              iSNS MIB                   January 2006 

   "iSNS Notification managed objects." 
          ::= { isnsGroups 8 } 
    
   isnsServerNotificationGroup  NOTIFICATION-GROUP 
       NOTIFICATIONS { 
          isnsServerStart, 
          isnsServerShutdown 
                     } 
       STATUS                  current 
       DESCRIPTION 
   "iSNS Server Notification managed objects." 
          ::= { isnsGroups 9 } 
    
   -- 
   -- Compliance Information 
   -- 
    
   isnsCompliances OBJECT IDENTIFIER ::= { isnsConformance 2 } 
    
   isnsIscsiServerComplianceV1 MODULE-COMPLIANCE 
       STATUS                  current 
       DESCRIPTION 
   "Initial compliance statement for an iSNS Server 
    providing support to iSCSI clients." 
       MODULE       -- this module 
       MANDATORY-GROUPS { 
           isnsServerAttributesGroup, 
           isnsServerIscsiCntlNodeGroup, 
           isnsServerIscsiDdsDdObjGroup, 
           isnsServerRegIscsiObjGroup, 
           isnsNotificationObjGroup, 
           isnsServerNotificationGroup 
                        } 
       ::= { isnsCompliances 1 } 
    
   isnsIfcpServerComplianceV1 MODULE-COMPLIANCE 
       STATUS                  current 
       DESCRIPTION 
   "Initial compliance statement for an iSNS Server 
    providing support to iFCP Clients." 
       MODULE       -- this module 
       MANDATORY-GROUPS { 
           isnsServerAttributesGroup, 
           isnsServerIfcpDdsDdObjGroup, 
           isnsServerRegIfcpObjGroup, 
           isnsNotificationObjGroup, 
           isnsServerNotificationGroup 
                        } 
       ::= { isnsCompliances 2 } 
    
   isnsServerComplianceV1 MODULE-COMPLIANCE 
       STATUS                  current 
    
   Gibbons                Expires July 2006                        63 
   Internet Draft              iSNS MIB                   January 2006 

       DESCRIPTION 
   "This set of groups is required for full implementation 
    by an iSNS Server if it has the resources to keep 
    track of the number of registered objects in iSNS Server 
    instances over time." 
       MODULE       -- this module 
       MANDATORY-GROUPS { 
           isnsServerNumObjGroup 
                        } 
       ::= { isnsCompliances 3 } 
    
   END 

--     
--    Copyright (C) The Internet Society (2006).  
--     
--    This document is subject to the rights, licenses and 
--    restrictions contained in BCP 78, and except as set forth 
--    therein, the authors retain all their rights. 
--     
-- Disclaimer of Validity 
--     
--    This document and the information contained herein are provided 
--    on an "AS IS" basis and THE CONTRIBUTOR, THE ORGANIZATION HE/SHE 
--    REPRESENTS OR IS SPONSORED BY (IF ANY), THE INTERNET SOCIETY AND 
--    THE INTERNET ENGINEERING TASK FORCE DISCLAIM ALL WARRANTIES, 
--    EXPRESS OR IMPLIED, INCLUDING BUT NOT LIMITED TO ANY WARRANTY 
--    THAT THE USE OF THE INFORMATION HEREIN WILL NOT INFRINGE ANY 
--    RIGHTS OR ANY IMPLIED WARRANTIES OF MERCHANTABILITY OR FITNESS 
--    FOR A PARTICULAR PURPOSE. 
--     
--    Gibbons                Expires July 2006                        67 
--    Internet Draft              iSNS MIB                   January 2006 
-- 
--     
-- Acknowledgment 
--     
--    Funding for the RFC Editor function is currently provided by the 
--    Internet Society. 
--     
--  Expiration Notice 
--    This Internet-Draft expires in July 2006. 
--     
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
--     
--    Gibbons                Expires July 2006                        68
