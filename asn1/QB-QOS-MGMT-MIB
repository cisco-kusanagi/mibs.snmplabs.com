--	Quantum Bridge QOS Management Information Base
--	Version 1.0.0
--
--	Quantum Bridge Corporation
--	One High Street
--	North Andover, MA 01845
--	(978) 688-9100
--
--------------------------------------------------------------------------------------
--  01/01/2001	Initial version	
--

   QB-QOS-MGMT-MIB DEFINITIONS ::= BEGIN
   IMPORTS 
    MODULE-IDENTITY, OBJECT-TYPE, Gauge32, Integer32, Counter32, TimeTicks, IpAddress,
    NOTIFICATION-TYPE, Unsigned32
        FROM SNMPv2-SMI
    TEXTUAL-CONVENTION, DisplayString, TruthValue, RowStatus
        FROM SNMPv2-TC
    MODULE-COMPLIANCE, OBJECT-GROUP
        FROM SNMPv2-CONF
    ifIndex
        FROM IF-MIB
    qbMibs
       FROM QUANTUMBRIDGE-REG
    ;

  qbQosMIB MODULE-IDENTITY
    LAST-UPDATED "0101022155Z" -- January 2, 2001      
    ORGANIZATION "Quantum Bridge"
    CONTACT-INFO
        "mvaysman@quantumbridge.com"
    DESCRIPTION
        "This module defines objects for the management of QB's
        proprietary QOS capability. This capability is
        based on Policing and Thresholding.

        The purpose of the QB Quality of Service (qos) function is
        to share access to an interface's bandwidth based on policies
        set up by the administrator."
    ::= { qbMibs 14 }

    --
    -- Overview of Quantum Bridge QOS MIB
    --
    --
    -- The Quantum Bridge System MIB defines the MIB objects for provisioning
    -- and monitoring QOS information. 
    -- This provisioning includes configuration bandwidth parameters
    -- The monitoring presents qos statistics from each of the 
    -- Ethernet switching port.

   QbMbitRate ::= TEXTUAL-CONVENTION
    STATUS          current
    DESCRIPTION
        "A data rate in Mbits/second."
    SYNTAX          Integer32

-- ================================================================
-- Top-level organization of the MIB
-- ================================================================

   qbQosObjects          OBJECT IDENTIFIER ::= { qbQosMIB  1 }
   qbQosNotifications    OBJECT IDENTIFIER ::= { qbQosMIB  2 }
   qbQosConformance      OBJECT IDENTIFIER ::= { qbQosMIB  3 }

-- ================================================================
-- Textual Conventions (datatypes)
-- ================================================================

--
-- The Interface Configuration Table. This table contains qos cinfiguration
-- parameter for every OAS3000 Ethernet Switching interface
--
    qbQosIfConfGroup  	OBJECT IDENTIFIER ::= { qbQosObjects  1}

    qbQosIfConfTableLastUpdate OBJECT-TYPE
        SYNTAX  TimeTicks
        MAX-ACCESS  read-only
        STATUS  current
        DESCRIPTION
		 "The value of sysUpTime at the time of the last
                  creation, deletion or modification of an entry in
		  the  qbQosIfConfTable. 
		  If the number of entries has been unchanged since the
		  last re-initialization of the agent,
		  then this object contains a zero value."
        ::= { qbQosIfConfGroup  1 }

    qbQosIfConfTable OBJECT-TYPE
	SYNTAX      SEQUENCE OF QbQosIfConfEntry
	MAX-ACCESS  not-accessible
	STATUS      current
	DESCRIPTION
		"This table provides statistics for OAS300 Ethernet switching
		ports. Note that the table does not contain information about IOT
		ethernet ports."
	::= { qbQosIfConfGroup 2 }

    qbQosIfConfEntry OBJECT-TYPE
	SYNTAX       QbQosIfConfEntry
	MAX-ACCESS  not-accessible
	STATUS      current
	DESCRIPTION
		"Configuration information  about a single ethernet switching port"
	INDEX    { ifIndex }
	::= { qbQosIfConfTable 1 }

   QbQosIfConfEntry	 ::= SEQUENCE {
	qbQosIfConfPolicingAdminStatus	INTEGER
	}

   qbQosIfConfPolicingAdminStatus OBJECT-TYPE
	SYNTAX      INTEGER {
		     enable(1),
		     disable(2)
		    }
	MAX-ACCESS  read-write
	STATUS      current
	DESCRIPTION
		"The object is used to enable or disable policing
		policy on a given port."
	DEFVAL      { disable }	
	::= {  qbQosIfConfEntry 1 }

--
-- The Interface Statistics Table. This table contains qos statistics
-- for every OAS3000 Ethernet Switching interface
--
    qbQosIfStatTable OBJECT-TYPE
	SYNTAX      SEQUENCE OF QbQosIfStatEntry
	MAX-ACCESS  not-accessible
	STATUS      current
	DESCRIPTION
		"This table provides statistics for OAS300 Ethernet switching
		ports. Note that the table does not contain information about IOT
		ethernet ports."
	::= { qbQosObjects 2 }

    qbQosIfStatEntry OBJECT-TYPE
	SYNTAX       QbQosIfStatEntry
	MAX-ACCESS  not-accessible
	STATUS      current
	DESCRIPTION
		"Statistics  about a single ethernet switching port"
	INDEX    { ifIndex }
	::= { qbQosIfStatTable 1 }

   QbQosIfStatEntry	 ::= SEQUENCE {
	qbQosIfStatDiscPkts		Counter32,
	qbQosIfStatUpThreshDiscPkts	Counter32,
	qbQosIfStatDownThreshDiscPkts  Counter32
	}

   qbQosIfStatDiscPkts OBJECT-TYPE
	SYNTAX      Counter32
	MAX-ACCESS  read-only
	STATUS      current
	DESCRIPTION
		"A count of the number of packets discarded for this interface
		due to policing on this interface."
	::= {  qbQosIfStatEntry 1 }

   qbQosIfStatUpThreshDiscPkts OBJECT-TYPE       
	SYNTAX      Counter32
	MAX-ACCESS  read-only
	STATUS      current
	DESCRIPTION
		"A count of the number of upstream packets discarded for this interface
		due to thresholding on this interface."
	::= {qbQosIfStatEntry 2 }

  qbQosIfStatDownThreshDiscPkts OBJECT-TYPE       
	SYNTAX      Counter32
	MAX-ACCESS  read-only
	STATUS      current
	DESCRIPTION
		"A count of the number of downstream packets discarded for this interface
		due to thresholding on this interface."
	::= {qbQosIfStatEntry 3 }

-- ****************************************************************
-- Dws Notifications - defines a group of traps for use by this MIB.
--
-- ****************************************************************

    qbQosNotificationPrefix OBJECT IDENTIFIER ::= { qbQosNotifications 0 }

    -- At this point there are not notifications 
	
    --
    -- Compliance Statements
    --

    qbQosCompliances OBJECT IDENTIFIER ::= { qbQosConformance 1 }
    qbQosGroups      OBJECT IDENTIFIER ::= { qbQosConformance 2 }

  qbQosCompliance MODULE-COMPLIANCE
    STATUS      current
    DESCRIPTION
        "The compliance statement for all agents that support this
        MIB. A compliant agent implements all objects defined in this
        MIB."
    MODULE  -- this module
    MANDATORY-GROUPS {
        qbQosClassGroup
    }
    ::= { qbQosCompliances 1 }

--
-- Object Groups
--

  qbQosGroupInfo OBJECT-GROUP
    OBJECTS {
	qbQosIfConfPolicingAdminStatus,
	qbQosIfStatDiscPkts,
	qbQosIfStatUpThreshDiscPkts,
	qbQosIfStatDownThreshDiscPkts
	}
    STATUS      current
    DESCRIPTION
        "The set of all accessible objects in this MIB."
    ::= { qbQosGroups 1 }

END
