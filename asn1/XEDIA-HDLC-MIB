XEDIA-HDLC-MIB DEFINITIONS ::= BEGIN

IMPORTS
    MODULE-IDENTITY, OBJECT-TYPE, Counter32
        FROM SNMPv2-SMI
    MODULE-COMPLIANCE, OBJECT-GROUP
        FROM SNMPv2-CONF
    ifIndex 
        FROM IF-MIB
    xediaMibs
        FROM XEDIA-REG
    ;

xediaHdlcMIB MODULE-IDENTITY
    LAST-UPDATED "9703252155Z" -- March 25, 1997
    ORGANIZATION "Xedia Corp."
    CONTACT-INFO
        "support@xedia.com"
    DESCRIPTION
        "This module defines proprietary objects that extend those in
        IETF's the Ethernet-Like Interface MIB."
    ::= { xediaMibs 7 }


-- ================================================================
-- Top-level organization of the MIB
-- ================================================================

xhdlcObjects        OBJECT IDENTIFIER ::= { xediaHdlcMIB 1 }
xhdlcConformance    OBJECT IDENTIFIER ::= { xediaHdlcMIB 2 } 

-- ================================================================
-- Object Definitions
-- ================================================================

--
-- Xedia HDLC Statistics Table
--

xhdlcStatsTable OBJECT-TYPE
    SYNTAX      SEQUENCE OF XhdlcStatsEntry
    MAX-ACCESS  not-accessible
    STATUS      current
    DESCRIPTION
        "Additional Xedia proprietary statistics for hdlc-like
        interfaces."
    ::= { xhdlcObjects 1 }

xhdlcStatsEntry OBJECT-TYPE
    SYNTAX      XhdlcStatsEntry
    MAX-ACCESS  not-accessible
    STATUS      current
    DESCRIPTION
        "Additional Xedia proprietary statistics for single
        hdlc-like interface."
    INDEX      { ifIndex }
    ::= { xhdlcStatsTable 1 }

XhdlcStatsEntry ::= SEQUENCE {
    xhdlcStatsOutErrorUnderFlows   Counter32,
    xhdlcStatsInAborts             Counter32,
    xhdlcStatsInResidualBits       Counter32,
    xhdlcStatsInInvalidLen         Counter32,
    xhdlcStatsInOverrun            Counter32
}

xhdlcStatsOutErrorUnderFlows OBJECT-TYPE
    SYNTAX      Counter32
    MAX-ACCESS  read-only
    STATUS      current
    DESCRIPTION
        "A count of TX Errorunderflows on a particular interface."
    ::= { xhdlcStatsEntry 1 }

xhdlcStatsInAborts OBJECT-TYPE
    SYNTAX      Counter32
    MAX-ACCESS  read-only
    STATUS      current
    DESCRIPTION
        "A count of RX Aborts on a particular interface."
    ::= { xhdlcStatsEntry 2 }

xhdlcStatsInResidualBits OBJECT-TYPE
    SYNTAX      Counter32
    MAX-ACCESS  read-only
    STATUS      current
    DESCRIPTION
        "The count of residual bit errors."
    ::= { xhdlcStatsEntry 3 }

xhdlcStatsInInvalidLen OBJECT-TYPE
    SYNTAX      Counter32
    MAX-ACCESS  read-only
    STATUS      current
    DESCRIPTION
        "A count of RX invalid lengths on a particular interface."
    ::= { xhdlcStatsEntry 4 }

xhdlcStatsInOverrun OBJECT-TYPE
    SYNTAX      Counter32
    MAX-ACCESS  read-only
    STATUS      current
    DESCRIPTION
        "A count of RX Overruns on a particular interface."
    ::= { xhdlcStatsEntry 5 }

--
-- Xedia HDLC Config Table
--

xhdlcConfigTable OBJECT-TYPE
    SYNTAX      SEQUENCE OF XhdlcConfigEntry
    MAX-ACCESS  not-accessible
    STATUS      current
    DESCRIPTION
        "Xedia proprietary configuration parameters for hdlc-like
        interfaces."
    ::= { xhdlcObjects 2 }

xhdlcConfigEntry OBJECT-TYPE
    SYNTAX      XhdlcConfigEntry
    MAX-ACCESS  not-accessible
    STATUS      current
    DESCRIPTION
        "Xedia proprietary configuration parameters for single
        hdlc-like interface."
    INDEX      { ifIndex }
    ::= { xhdlcConfigTable 1 }

XhdlcConfigEntry ::= SEQUENCE {
    xhdlcConfigClocking                INTEGER,
    xhdlcConfigCrcMode                 INTEGER
}

xhdlcConfigClocking OBJECT-TYPE
    SYNTAX      INTEGER {
                    internal(1), 
                    external(2),
                    loopback(3)
                }
    MAX-ACCESS  read-write
    STATUS      current
    DESCRIPTION
        "The configured clocking of the interface."
    DEFVAL      { external}
    ::= { xhdlcConfigEntry 1 }

xhdlcConfigCrcMode OBJECT-TYPE
    SYNTAX      INTEGER {
                    crc16(1), 
                    crc32(2),
                    crcnone(3)
                }
    MAX-ACCESS  read-write
    STATUS      current
    DESCRIPTION
        "The configured CRC mode of the interface."
    DEFVAL      { crc16 }
    ::= { xhdlcConfigEntry 2 }

-- ================================================================
-- Conformance Information
-- ================================================================

xhdlcCompliances    OBJECT IDENTIFIER ::= { xhdlcConformance 1 }
xhdlcGroups         OBJECT IDENTIFIER ::= { xhdlcConformance 2 }

--
-- Compliance Statements
--

xhdlcCompliance MODULE-COMPLIANCE
    STATUS      current
    DESCRIPTION
        "The compliance statement for all agents that support this
        MIB. A compliant agent implements all objects defined in this
        MIB."
    MODULE  -- this module
    MANDATORY-GROUPS {
        xhdlcGroup
    }
    ::= { xhdlcCompliances 1 }

--
-- Object Groups
--

xhdlcGroup OBJECT-GROUP
    OBJECTS {
    xhdlcStatsOutErrorUnderFlows,
    xhdlcStatsInAborts,
    xhdlcStatsInResidualBits,
    xhdlcStatsInInvalidLen, 
    xhdlcStatsInOverrun,
    xhdlcConfigClocking,
    xhdlcConfigCrcMode
    }
    STATUS      current
    DESCRIPTION
        "The set of all accessible objects in this MIB."
    ::= { xhdlcGroups 1 }

END
