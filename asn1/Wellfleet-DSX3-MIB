Wellfleet-DSX3-MIB DEFINITIONS ::= BEGIN

-- Created by mdl2asn version 3.1
-- Creation date: Wed Aug 30 16:40:23 EDT 1995


    IMPORTS

      Gauge
        FROM RFC1155-SMI
      OBJECT-TYPE
        FROM RFC-1212
      DisplayString
        FROM RFC1213-MIB
      wfDsx3Group
        FROM Wellfleet-COMMON-MIB;


    wfDsx3ConfigTable OBJECT-TYPE
        SYNTAX	SEQUENCE OF WfDsx3ConfigEntry
        ACCESS	not-accessible
        STATUS	mandatory
        DESCRIPTION
                "The DS3/E3 Configuration table"
        ::= { wfDsx3Group 1 }

    wfDsx3ConfigEntry OBJECT-TYPE
        SYNTAX	WfDsx3ConfigEntry
        ACCESS	not-accessible
        STATUS	mandatory
        DESCRIPTION
                "per circuit DS3/E3 configuration objects; wfDsx3LineIndex
                corresponds to Wellfleet circuit number"
        INDEX	{ wfDsx3LineIndex }
        ::= { wfDsx3ConfigTable 1 }

    WfDsx3ConfigEntry ::= SEQUENCE {
    	    wfDsx3LineIndex
    		INTEGER,
    	    wfDsx3IfIndex
    		INTEGER,
    	    wfDsx3TimeElapsed
    		INTEGER,
    	    wfDsx3ValidIntervals
    		INTEGER,
    	    wfDsx3LineType
    		INTEGER,
    	    wfDsx3LineCoding
    		INTEGER,
    	    wfDsx3SendCode
    		INTEGER,
    	    wfDsx3CircuitIdentifier
    		DisplayString,
    	    wfDsx3LoopbackConfig
    		INTEGER,
    	    wfDsx3LineStatus
    		INTEGER,
    	    wfDsx3TransmitClockSource
    		INTEGER
        }

    wfDsx3LineIndex OBJECT-TYPE
        SYNTAX	INTEGER(1..65535)
        ACCESS	read-only
        STATUS	mandatory
        DESCRIPTION
                "this corresponds to the Wellfleet circuit number"
        ::= { wfDsx3ConfigEntry 1 }

    wfDsx3IfIndex OBJECT-TYPE
        SYNTAX	INTEGER
        ACCESS	read-only
        STATUS	mandatory
        DESCRIPTION
                "this is value of ifIndex from the Interfaces table of
                MIB II (RFC 1213)."
        ::= { wfDsx3ConfigEntry 2 }

    wfDsx3TimeElapsed OBJECT-TYPE
        SYNTAX	INTEGER
        ACCESS	read-only
        STATUS	mandatory
        DESCRIPTION
                "0..899 seconds elapsed within the current 15-minute interval"
        ::= { wfDsx3ConfigEntry 3 }

    wfDsx3ValidIntervals OBJECT-TYPE
        SYNTAX	INTEGER
        ACCESS	read-only
        STATUS	mandatory
        DESCRIPTION
                "0..96 previous intervals that valid data were collected.
                This is 96 unless the device was brought on line within
                    the last 24 hours."
        ::= { wfDsx3ConfigEntry 4 }

    wfDsx3LineType OBJECT-TYPE
        SYNTAX	INTEGER {
    		    ds3other(1),
    		    ds3m23(2),
    		    ds3syntran(3),
    		    ds3cbitparity(4),
    		    ds3clearchannel(5),
    		    e3other(6),
    		    e3framed(7),
    		    e3plcp(8)
    		}
        ACCESS	read-only
        STATUS	mandatory
        DESCRIPTION
                "the variety of DS3/E3 application implementing this circuit"
        ::= { wfDsx3ConfigEntry 5 }

    wfDsx3LineCoding OBJECT-TYPE
        SYNTAX	INTEGER {
    		    other(1),
    		    b3zs(2),
    		    hdb3(3)
    		}
        ACCESS	read-only
        STATUS	mandatory
        DESCRIPTION
                "the variety of Zero Code Suppression used on the link"
        ::= { wfDsx3ConfigEntry 6 }

    wfDsx3SendCode OBJECT-TYPE
        SYNTAX	INTEGER {
    		    nocode(1),
    		    linecode(2),
    		    payloadcode(3),
    		    resetcode(4),
    		    ds1loopcode(5),
    		    testpattern(6)
    		}
        ACCESS	read-only
        STATUS	mandatory
        DESCRIPTION
                "the type of code being sent across the DS3/E3 circuit by
                the device"
        ::= { wfDsx3ConfigEntry 7 }

    wfDsx3CircuitIdentifier OBJECT-TYPE
        SYNTAX	DisplayString
        ACCESS	read-only
        STATUS	mandatory
        DESCRIPTION
                "the transmission vendor's circuit identifier"
        ::= { wfDsx3ConfigEntry 8 }

    wfDsx3LoopbackConfig OBJECT-TYPE
        SYNTAX	INTEGER {
    		    noloop(1),
    		    payloadloop(2),
    		    lineloop(3),
    		    otherloop(4)
    		}
        ACCESS	read-only
        STATUS	mandatory
        DESCRIPTION
                "the loopback configuration of the DS3/E3 interface"
        ::= { wfDsx3ConfigEntry 9 }

    wfDsx3LineStatus OBJECT-TYPE
        SYNTAX	INTEGER {
    		    noalarm(1),
    		    rcrai(2),
    		    txrai(4),
    		    rcais(8),
    		    txais(16),
    		    lof(32),
    		    los(64),
    		    loopback(128),
    		    rctestcode(256),
    		    otherfailure(512)
    		}
        ACCESS	read-only
        STATUS	mandatory
        DESCRIPTION
                "the status of the DS3/E3 line"
        ::= { wfDsx3ConfigEntry 10 }

    wfDsx3TransmitClockSource OBJECT-TYPE
        SYNTAX	INTEGER {
    		    looptiming(1),
    		    localtiming(2),
    		    throughtiming(3)
    		}
        ACCESS	read-only
        STATUS	mandatory
        DESCRIPTION
                "the source of Transmit Clock for the DS3/E3 interface"
        ::= { wfDsx3ConfigEntry 11 }

    wfDsx3CurrentTable OBJECT-TYPE
        SYNTAX	SEQUENCE OF WfDsx3CurrentEntry
        ACCESS	not-accessible
        STATUS	mandatory
        DESCRIPTION
                "The DS3/E3 Current table"
        ::= { wfDsx3Group 2 }

    wfDsx3CurrentEntry OBJECT-TYPE
        SYNTAX	WfDsx3CurrentEntry
        ACCESS	not-accessible
        STATUS	mandatory
        DESCRIPTION
                "per circuit DS3/E3 current objects - wfDsx3CurrentIndex
                corresponds to Wellfleet circuit number"
        INDEX	{ wfDsx3CurrentIndex }
        ::= { wfDsx3CurrentTable 1 }

    WfDsx3CurrentEntry ::= SEQUENCE {
    	    wfDsx3CurrentIndex
    		INTEGER,
    	    wfDsx3CurrentPESs
    		Gauge,
    	    wfDsx3CurrentPSESs
    		Gauge,
    	    wfDsx3CurrentSEFSs
    		Gauge,
    	    wfDsx3CurrentUASs
    		Gauge,
    	    wfDsx3CurrentLCVs
    		Gauge,
    	    wfDsx3CurrentPCVs
    		Gauge,
    	    wfDsx3CurrentLESs
    		Gauge,
    	    wfDsx3CurrentCCVs
    		Gauge,
    	    wfDsx3CurrentCESs
    		Gauge,
    	    wfDsx3CurrentCSESs
    		Gauge,
    	    wfDsx3CurrentSASs
    		Gauge,
    	    wfDsx3CurrentAISSs
    		Gauge,
    	    wfDsx3CurrentFCs
    		Gauge,
    	    wfDsx3CurrentTimeElapsed
    		INTEGER,
    	    wfDsx3CurrentValidIntervals
    		INTEGER,
    	    wfDsx3CurrentValidFlag
    		INTEGER
        }

    wfDsx3CurrentIndex OBJECT-TYPE
        SYNTAX	INTEGER(1..65535)
        ACCESS	read-only
        STATUS	mandatory
        DESCRIPTION
                "this corresponds to the Wellfleet circuit number"
        ::= { wfDsx3CurrentEntry 1 }

    wfDsx3CurrentPESs OBJECT-TYPE
        SYNTAX	Gauge
        ACCESS	read-only
        STATUS	mandatory
        DESCRIPTION
                "the number of P-bit Errored Seconds in the current interval"
        ::= { wfDsx3CurrentEntry 2 }

    wfDsx3CurrentPSESs OBJECT-TYPE
        SYNTAX	Gauge
        ACCESS	read-only
        STATUS	mandatory
        DESCRIPTION
                "the number of P-bit Severely Errored Seconds in the
                current interval"
        ::= { wfDsx3CurrentEntry 3 }

    wfDsx3CurrentSEFSs OBJECT-TYPE
        SYNTAX	Gauge
        ACCESS	read-only
        STATUS	mandatory
        DESCRIPTION
                "the number of Severely Errored Framing Seconds in the
                current interval"
        ::= { wfDsx3CurrentEntry 4 }

    wfDsx3CurrentUASs OBJECT-TYPE
        SYNTAX	Gauge
        ACCESS	read-only
        STATUS	mandatory
        DESCRIPTION
                "the number of Unavailable Seconds in the current interval"
        ::= { wfDsx3CurrentEntry 5 }

    wfDsx3CurrentLCVs OBJECT-TYPE
        SYNTAX	Gauge
        ACCESS	read-only
        STATUS	mandatory
        DESCRIPTION
                "the number of Line Coding Violations in the current interval"
        ::= { wfDsx3CurrentEntry 6 }

    wfDsx3CurrentPCVs OBJECT-TYPE
        SYNTAX	Gauge
        ACCESS	read-only
        STATUS	mandatory
        DESCRIPTION
                "the number of P-bit Coding Violations in the current interval"
        ::= { wfDsx3CurrentEntry 7 }

    wfDsx3CurrentLESs OBJECT-TYPE
        SYNTAX	Gauge
        ACCESS	read-only
        STATUS	mandatory
        DESCRIPTION
                "the number of Line Errored Seconds in the current interval"
        ::= { wfDsx3CurrentEntry 8 }

    wfDsx3CurrentCCVs OBJECT-TYPE
        SYNTAX	Gauge
        ACCESS	read-only
        STATUS	mandatory
        DESCRIPTION
                "the number of C-bit Coding Violations in the current interval"
        ::= { wfDsx3CurrentEntry 9 }

    wfDsx3CurrentCESs OBJECT-TYPE
        SYNTAX	Gauge
        ACCESS	read-only
        STATUS	mandatory
        DESCRIPTION
                "the number of C-bit Errored Seconds in the current interval"
        ::= { wfDsx3CurrentEntry 10 }

    wfDsx3CurrentCSESs OBJECT-TYPE
        SYNTAX	Gauge
        ACCESS	read-only
        STATUS	mandatory
        DESCRIPTION
                "the number of C-bit Severely Errored Seconds
                in the current interval"
        ::= { wfDsx3CurrentEntry 11 }

    wfDsx3CurrentSASs OBJECT-TYPE
        SYNTAX	Gauge
        ACCESS	read-only
        STATUS	mandatory
        DESCRIPTION
                "the number of Seconds containing one or more SEFs or AIS defects
                in the current interval"
        ::= { wfDsx3CurrentEntry 12 }

    wfDsx3CurrentAISSs OBJECT-TYPE
        SYNTAX	Gauge
        ACCESS	read-only
        STATUS	mandatory
        DESCRIPTION
                "the number of Seconds containing one or more AIS defect
                in the current interval"
        ::= { wfDsx3CurrentEntry 13 }

    wfDsx3CurrentFCs OBJECT-TYPE
        SYNTAX	Gauge
        ACCESS	read-only
        STATUS	mandatory
        DESCRIPTION
                "the number of Path Failure Count error events detected
                in the current interval"
        ::= { wfDsx3CurrentEntry 14 }

    wfDsx3CurrentTimeElapsed OBJECT-TYPE
        SYNTAX	INTEGER
        ACCESS	read-only
        STATUS	mandatory
        DESCRIPTION
                "the number of seconds since the beginning of
                the far end current interval"
        ::= { wfDsx3CurrentEntry 15 }

    wfDsx3CurrentValidIntervals OBJECT-TYPE
        SYNTAX	INTEGER
        ACCESS	read-only
        STATUS	mandatory
        DESCRIPTION
                "the number of previous far end intervals for
                which valid data is available"
        ::= { wfDsx3CurrentEntry 16 }

    wfDsx3CurrentValidFlag OBJECT-TYPE
        SYNTAX  INTEGER {
                    valid(1),
                    invalid(2)
                }
        ACCESS  read-only
        STATUS  mandatory
        DESCRIPTION
                "Indicates whether this interval reported by the Mib Table is valid or
                invalid."
        DEFVAL  { valid }
        ::= { wfDsx3CurrentEntry 17 }


    wfDsx3IntervalTable OBJECT-TYPE
        SYNTAX	SEQUENCE OF WfDsx3IntervalEntry
        ACCESS	not-accessible
        STATUS	mandatory
        DESCRIPTION
                "The DS3/E3 Interval table"
        ::= { wfDsx3Group 3 }

    wfDsx3IntervalEntry OBJECT-TYPE
        SYNTAX	WfDsx3IntervalEntry
        ACCESS	not-accessible
        STATUS	mandatory
        DESCRIPTION
                "per circuit DS3/E3 interval objects - wfDsx3IntervalIndex
                corresponds to Wellfleet circuit number,
                wfDsx3IntervalNumber is the numbered previous
                15-minute interval"
        INDEX	{ wfDsx3IntervalIndex,
    		  wfDsx3IntervalNumber }
        ::= { wfDsx3IntervalTable 1 }

    WfDsx3IntervalEntry ::= SEQUENCE {
    	    wfDsx3IntervalIndex
    		INTEGER,
    	    wfDsx3IntervalNumber
    		INTEGER,
    	    wfDsx3IntervalPESs
    		Gauge,
    	    wfDsx3IntervalPSESs
    		Gauge,
    	    wfDsx3IntervalSEFSs
    		Gauge,
    	    wfDsx3IntervalUASs
    		Gauge,
    	    wfDsx3IntervalLCVs
    		Gauge,
    	    wfDsx3IntervalPCVs
    		Gauge,
    	    wfDsx3IntervalLESs
    		Gauge,
    	    wfDsx3IntervalCCVs
    		Gauge,
    	    wfDsx3IntervalCESs
    		Gauge,
    	    wfDsx3IntervalCSESs
    		Gauge,
    	    wfDsx3IntervalSASs
    		Gauge,
    	    wfDsx3IntervalAISSs
    		Gauge,
    	    wfDsx3IntervalFCs
    		Gauge,
    	    wfDsx3IntervalValidFlag
    		INTEGER
        }

    wfDsx3IntervalIndex OBJECT-TYPE
        SYNTAX	INTEGER(1..65535)
        ACCESS	read-only
        STATUS	mandatory
        DESCRIPTION
                "this corresponds to the Wellfleet circuit number"
        ::= { wfDsx3IntervalEntry 1 }

    wfDsx3IntervalNumber OBJECT-TYPE
        SYNTAX	INTEGER(1..96)
        ACCESS	read-only
        STATUS	mandatory
        DESCRIPTION
                "1..96 where 1 is the most recent 15-minute interval and 96 is
                the least"
        ::= { wfDsx3IntervalEntry 2 }

    wfDsx3IntervalPESs OBJECT-TYPE
        SYNTAX	Gauge
        ACCESS	read-only
        STATUS	mandatory
        DESCRIPTION
                "the number of P-bit Errored Seconds in the specified interval"
        ::= { wfDsx3IntervalEntry 3 }

    wfDsx3IntervalPSESs OBJECT-TYPE
        SYNTAX	Gauge
        ACCESS	read-only
        STATUS	mandatory
        DESCRIPTION
                "the number of P-bit Severely Errored Seconds in the
                specified interval"
        ::= { wfDsx3IntervalEntry 4 }

    wfDsx3IntervalSEFSs OBJECT-TYPE
        SYNTAX	Gauge
        ACCESS	read-only
        STATUS	mandatory
        DESCRIPTION
                "the number of Severely Errored Framing Seconds in the
                specified interval"
        ::= { wfDsx3IntervalEntry 5 }

    wfDsx3IntervalUASs OBJECT-TYPE
        SYNTAX	Gauge
        ACCESS	read-only
        STATUS	mandatory
        DESCRIPTION
                "the number of Unavailable Seconds in the specified interval"
        ::= { wfDsx3IntervalEntry 6 }

    wfDsx3IntervalLCVs OBJECT-TYPE
        SYNTAX	Gauge
        ACCESS	read-only
        STATUS	mandatory
        DESCRIPTION
                "the number of Line Coding Violations in the specified interval"
        ::= { wfDsx3IntervalEntry 7 }

    wfDsx3IntervalPCVs OBJECT-TYPE
        SYNTAX	Gauge
        ACCESS	read-only
        STATUS	mandatory
        DESCRIPTION
                "the number of P-bit Coding Violations in the specified interval"
        ::= { wfDsx3IntervalEntry 8 }

    wfDsx3IntervalLESs OBJECT-TYPE
        SYNTAX	Gauge
        ACCESS	read-only
        STATUS	mandatory
        DESCRIPTION
                "the number of Line Errored Seconds in the specified interval"
        ::= { wfDsx3IntervalEntry 9 }

    wfDsx3IntervalCCVs OBJECT-TYPE
        SYNTAX	Gauge
        ACCESS	read-only
        STATUS	mandatory
        DESCRIPTION
                "the number of C-bit Coding Violations in the specified interval"
        ::= { wfDsx3IntervalEntry 10 }

    wfDsx3IntervalCESs OBJECT-TYPE
        SYNTAX	Gauge
        ACCESS	read-only
        STATUS	mandatory
        DESCRIPTION
                "the number of C-bit Errored Seconds in the specified interval"
        ::= { wfDsx3IntervalEntry 11 }

    wfDsx3IntervalCSESs OBJECT-TYPE
        SYNTAX	Gauge
        ACCESS	read-only
        STATUS	mandatory
        DESCRIPTION
                "the number of C-bit Severely Errored Seconds
                in the specified interval"
        ::= { wfDsx3IntervalEntry 12 }

    wfDsx3IntervalSASs OBJECT-TYPE
        SYNTAX	Gauge
        ACCESS	read-only
        STATUS	mandatory
        DESCRIPTION
                "the number of Seconds containing one or more SEFs or AIS defects
                in the specified interval"
        ::= { wfDsx3IntervalEntry 13 }

    wfDsx3IntervalAISSs OBJECT-TYPE
        SYNTAX	Gauge
        ACCESS	read-only
        STATUS	mandatory
        DESCRIPTION
                "the number of Seconds containing one or more AIS defect
                in the specified interval"
        ::= { wfDsx3IntervalEntry 14 }

    wfDsx3IntervalFCs OBJECT-TYPE
        SYNTAX	Gauge
        ACCESS	read-only
        STATUS	mandatory
        DESCRIPTION
                "the number of Path Failure Count error events detected
                in the specified interval"
        ::= { wfDsx3IntervalEntry 15 }

    wfDsx3IntervalValidFlag OBJECT-TYPE
        SYNTAX  INTEGER {
                    valid(1),
                    invalid(2)
                }
        ACCESS  read-only
        STATUS  mandatory
        DESCRIPTION
                "Indicates whether this interval reported by the Mib Table is valid or
                invalid."
        DEFVAL  { valid }
        ::= { wfDsx3IntervalEntry 16 }


    wfDsx3TotalTable OBJECT-TYPE
        SYNTAX	SEQUENCE OF WfDsx3TotalEntry
        ACCESS	not-accessible
        STATUS	mandatory
        DESCRIPTION
                "The DS3/E3 Total table"
        ::= { wfDsx3Group 4 }

    wfDsx3TotalEntry OBJECT-TYPE
        SYNTAX	WfDsx3TotalEntry
        ACCESS	not-accessible
        STATUS	mandatory
        DESCRIPTION
                "per circuit DS3/E3 total objects - wfDsx3TotalIndex
                corresponds to Wellfleet circuit number"
        INDEX	{ wfDsx3TotalIndex }
        ::= { wfDsx3TotalTable 1 }

    WfDsx3TotalEntry ::= SEQUENCE {
    	    wfDsx3TotalIndex
    		INTEGER,
    	    wfDsx3TotalPESs
    		Gauge,
    	    wfDsx3TotalPSESs
    		Gauge,
    	    wfDsx3TotalSEFSs
    		Gauge,
    	    wfDsx3TotalUASs
    		Gauge,
    	    wfDsx3TotalLCVs
    		Gauge,
    	    wfDsx3TotalPCVs
    		Gauge,
    	    wfDsx3TotalLESs
    		Gauge,
    	    wfDsx3TotalCCVs
    		Gauge,
    	    wfDsx3TotalCESs
    		Gauge,
    	    wfDsx3TotalCSESs
    		Gauge,
    	    wfDsx3TotalSASs
    		Gauge,
    	    wfDsx3TotalAISSs
    		Gauge,
    	    wfDsx3TotalFCs
    		Gauge,
    	    wfDsx3TotalValidFlag
    		INTEGER
        }

    wfDsx3TotalIndex OBJECT-TYPE
        SYNTAX	INTEGER(1..65535)
        ACCESS	read-only
        STATUS	mandatory
        DESCRIPTION
                "this corresponds to the Wellfleet circuit number"
        ::= { wfDsx3TotalEntry 1 }

    wfDsx3TotalPESs OBJECT-TYPE
        SYNTAX	Gauge
        ACCESS	read-only
        STATUS	mandatory
        DESCRIPTION
                "the number of P-bit Errored Seconds in the last 24 hours"
        ::= { wfDsx3TotalEntry 2 }

    wfDsx3TotalPSESs OBJECT-TYPE
        SYNTAX	Gauge
        ACCESS	read-only
        STATUS	mandatory
        DESCRIPTION
                "the number of P-bit Severely Errored Seconds in the
                last 24 hours"
        ::= { wfDsx3TotalEntry 3 }

    wfDsx3TotalSEFSs OBJECT-TYPE
        SYNTAX	Gauge
        ACCESS	read-only
        STATUS	mandatory
        DESCRIPTION
                "the number of Severely Errored Framing Seconds in the
                last 24 hours"
        ::= { wfDsx3TotalEntry 4 }

    wfDsx3TotalUASs OBJECT-TYPE
        SYNTAX	Gauge
        ACCESS	read-only
        STATUS	mandatory
        DESCRIPTION
                "the number of Unavailable Seconds in the last 24 hours"
        ::= { wfDsx3TotalEntry 5 }

    wfDsx3TotalLCVs OBJECT-TYPE
        SYNTAX	Gauge
        ACCESS	read-only
        STATUS	mandatory
        DESCRIPTION
                "the number of Line Coding Violations in the last 24 hours"
        ::= { wfDsx3TotalEntry 6 }

    wfDsx3TotalPCVs OBJECT-TYPE
        SYNTAX	Gauge
        ACCESS	read-only
        STATUS	mandatory
        DESCRIPTION
                "the number of P-bit Coding Violations in the last 24 hours"
        ::= { wfDsx3TotalEntry 7 }

    wfDsx3TotalLESs OBJECT-TYPE
        SYNTAX	Gauge
        ACCESS	read-only
        STATUS	mandatory
        DESCRIPTION
                "the number of Line Errored Seconds in the last 24 hours"
        ::= { wfDsx3TotalEntry 8 }

    wfDsx3TotalCCVs OBJECT-TYPE
        SYNTAX	Gauge
        ACCESS	read-only
        STATUS	mandatory
        DESCRIPTION
                "the number of C-bit Coding Violations in the last 24 hours"
        ::= { wfDsx3TotalEntry 9 }

    wfDsx3TotalCESs OBJECT-TYPE
        SYNTAX	Gauge
        ACCESS	read-only
        STATUS	mandatory
        DESCRIPTION
                "the number of C-bit Errored Seconds in the last 24 hours"
        ::= { wfDsx3TotalEntry 10 }

    wfDsx3TotalCSESs OBJECT-TYPE
        SYNTAX	Gauge
        ACCESS	read-only
        STATUS	mandatory
        DESCRIPTION
                "the number of C-bit Severely Errored Seconds
                in the last 24 hours"
        ::= { wfDsx3TotalEntry 11 }

    wfDsx3TotalSASs OBJECT-TYPE
        SYNTAX	Gauge
        ACCESS	read-only
        STATUS	mandatory
        DESCRIPTION
                "the number of Seconds containing one or more SEFs or AIS defects
                in the last 24 hours"
        ::= { wfDsx3TotalEntry 12 }

    wfDsx3TotalAISSs OBJECT-TYPE
        SYNTAX	Gauge
        ACCESS	read-only
        STATUS	mandatory
        DESCRIPTION
                "the number of Seconds containing one or more AIS defect
                in the last 24 hours"
        ::= { wfDsx3TotalEntry 13 }

    wfDsx3TotalFCs OBJECT-TYPE
        SYNTAX	Gauge
        ACCESS	read-only
        STATUS	mandatory
        DESCRIPTION
                "the number of Path Failure Count error events detected
                in the last 24 hours"
        ::= { wfDsx3TotalEntry 14 }

    wfDsx3TotalValidFlag OBJECT-TYPE
        SYNTAX  INTEGER {
                    valid(1),
                    invalid(2)
                }
        ACCESS  read-only
        STATUS  mandatory
        DESCRIPTION
                "Indicates whether this interval reported by the Mib Table is valid or
                invalid."
        DEFVAL  { valid }
        ::= { wfDsx3TotalEntry 15 }


    wfDsx3FarEndConfigTable OBJECT-TYPE
        SYNTAX	SEQUENCE OF WfDsx3FarEndConfigEntry
        ACCESS	not-accessible
        STATUS	mandatory
        DESCRIPTION
                "The DS3/E3 Far End Configuration table"
        ::= { wfDsx3Group 5 }

    wfDsx3FarEndConfigEntry OBJECT-TYPE
        SYNTAX	WfDsx3FarEndConfigEntry
        ACCESS	not-accessible
        STATUS	mandatory
        DESCRIPTION
                "per circuit DS3/E3 far end config objects -
                wfDsx3FarEndLineIndex corresponds to Wellfleet circuit
                number"
        INDEX	{ wfDsx3FarEndLineIndex }
        ::= { wfDsx3FarEndConfigTable 1 }

    WfDsx3FarEndConfigEntry ::= SEQUENCE {
    	    wfDsx3FarEndLineIndex
    		INTEGER,
    	    wfDsx3FarEndEquipCode
    		DisplayString,
    	    wfDsx3FarEndLocationIDCode
    		DisplayString,
    	    wfDsx3FarEndFrameIDCode
    		DisplayString,
    	    wfDsx3FarEndUnitCode
    		DisplayString,
    	    wfDsx3FarEndFacilityIDCode
    		DisplayString
        }

    wfDsx3FarEndLineIndex OBJECT-TYPE
        SYNTAX	INTEGER(1..65535)
        ACCESS	read-only
        STATUS	mandatory
        DESCRIPTION
                "this corresponds to the Wellfleet circuit number"
        ::= { wfDsx3FarEndConfigEntry 1 }

    wfDsx3FarEndEquipCode OBJECT-TYPE
        SYNTAX	DisplayString
        ACCESS	read-write
        STATUS	mandatory
        DESCRIPTION
                "equipment description code - C-bit parity only"
        ::= { wfDsx3FarEndConfigEntry 2 }

    wfDsx3FarEndLocationIDCode OBJECT-TYPE
        SYNTAX	DisplayString
        ACCESS	read-write
        STATUS	mandatory
        DESCRIPTION
                "equipment location code - C-bit parity only"
        ::= { wfDsx3FarEndConfigEntry 3 }

    wfDsx3FarEndFrameIDCode OBJECT-TYPE
        SYNTAX	DisplayString
        ACCESS	read-write
        STATUS	mandatory
        DESCRIPTION
                "code for the equipment location within a building"
        ::= { wfDsx3FarEndConfigEntry 4 }

    wfDsx3FarEndUnitCode OBJECT-TYPE
        SYNTAX	DisplayString
        ACCESS	read-write
        STATUS	mandatory
        DESCRIPTION
                "code for the equipment location within a bay"
        ::= { wfDsx3FarEndConfigEntry 5 }

    wfDsx3FarEndFacilityIDCode OBJECT-TYPE
        SYNTAX	DisplayString
        ACCESS	read-write
        STATUS	mandatory
        DESCRIPTION
                "path identification code"
        ::= { wfDsx3FarEndConfigEntry 6 }

    wfDsx3FarEndCurrentTable OBJECT-TYPE
        SYNTAX	SEQUENCE OF WfDsx3FarEndCurrentEntry
        ACCESS	not-accessible
        STATUS	mandatory
        DESCRIPTION
                "The DS3/E3 Far End Current table"
        ::= { wfDsx3Group 6 }

    wfDsx3FarEndCurrentEntry OBJECT-TYPE
        SYNTAX	WfDsx3FarEndCurrentEntry
        ACCESS	not-accessible
        STATUS	mandatory
        DESCRIPTION
                "per circuit DS3/E3 far end current objects
                wfDsx3FarEndCurrentIndex corresponds to Wellfleet circuit
                number"
        INDEX	{ wfDsx3FarEndCurrentIndex }
        ::= { wfDsx3FarEndCurrentTable 1 }

    WfDsx3FarEndCurrentEntry ::= SEQUENCE {
    	    wfDsx3FarEndCurrentIndex
    		INTEGER,
    	    wfDsx3FarEndTimeElapsed
    		INTEGER,
    	    wfDsx3FarEndValidIntervals
    		INTEGER,
    	    wfDsx3FarEndCurrentCESs
    		Gauge,
    	    wfDsx3FarEndCurrentCSESs
    		Gauge,
    	    wfDsx3FarEndCurrentCCVs
    		Gauge,
    	    wfDsx3FarEndCurrentUASs
    		Gauge,
    	    wfDsx3FarEndCurrentSASs
    		Gauge,
    	    wfDsx3FarEndCurrentFCs
    		Gauge,
    	    wfDsx3FarEndCurrentValidFlag
    		INTEGER
        }

    wfDsx3FarEndCurrentIndex OBJECT-TYPE
        SYNTAX	INTEGER(1..1024)
        ACCESS	read-only
        STATUS	mandatory
        DESCRIPTION
                "this corresponds to the Wellfleet circuit number"
        ::= { wfDsx3FarEndCurrentEntry 1 }

    wfDsx3FarEndTimeElapsed OBJECT-TYPE
        SYNTAX	INTEGER
        ACCESS	read-only
        STATUS	mandatory
        DESCRIPTION
                "the number of seconds since the beginning of
                the far end current interval"
        ::= { wfDsx3FarEndCurrentEntry 2 }

    wfDsx3FarEndValidIntervals OBJECT-TYPE
        SYNTAX	INTEGER
        ACCESS	read-only
        STATUS	mandatory
        DESCRIPTION
                "the number of previous far end intervals for
                which valid data is available"
        ::= { wfDsx3FarEndCurrentEntry 3 }

    wfDsx3FarEndCurrentCESs OBJECT-TYPE
        SYNTAX	Gauge
        ACCESS	read-only
        STATUS	mandatory
        DESCRIPTION
                "the number of C-bit Errored Seconds in
                the current far end interval"
        ::= { wfDsx3FarEndCurrentEntry 4 }

    wfDsx3FarEndCurrentCSESs OBJECT-TYPE
        SYNTAX	Gauge
        ACCESS	read-only
        STATUS	mandatory
        DESCRIPTION
                "the number of C-bit Severely Errored Seconds
                in the current far end interval"
        ::= { wfDsx3FarEndCurrentEntry 5 }

    wfDsx3FarEndCurrentCCVs OBJECT-TYPE
        SYNTAX	Gauge
        ACCESS	read-only
        STATUS	mandatory
        DESCRIPTION
                "the number of C-bit Coding Violations
                in the current far end interval"
        ::= { wfDsx3FarEndCurrentEntry 6 }

    wfDsx3FarEndCurrentUASs OBJECT-TYPE
        SYNTAX	Gauge
        ACCESS	read-only
        STATUS	mandatory
        DESCRIPTION
                "the number of Unavailable Seconds
                in the current far end interval"
        ::= { wfDsx3FarEndCurrentEntry 7 }

    wfDsx3FarEndCurrentSASs OBJECT-TYPE
        SYNTAX	Gauge
        ACCESS	read-only
        STATUS	mandatory
        DESCRIPTION
                "the number of Seconds containing one or more SEFs or AIS defects
                in the current far end interval"
        ::= { wfDsx3FarEndCurrentEntry 8 }

    wfDsx3FarEndCurrentFCs OBJECT-TYPE
        SYNTAX	Gauge
        ACCESS	read-only
        STATUS	mandatory
        DESCRIPTION
                "the number of Path Failure Count error events detected
                in the current far end interval"
        ::= { wfDsx3FarEndCurrentEntry 9 }

    wfDsx3FarEndCurrentValidFlag OBJECT-TYPE
        SYNTAX  INTEGER {
                    valid(1),
                    invalid(2)
                }
        ACCESS  read-only
        STATUS  mandatory
        DESCRIPTION
                "Indicates whether this interval reported by the Mib Table is valid or
                invalid."
        DEFVAL  { valid }
        ::= { wfDsx3FarEndCurrentEntry 10 }


    wfDsx3FarEndIntervalTable OBJECT-TYPE
        SYNTAX	SEQUENCE OF WfDsx3FarEndIntervalEntry
        ACCESS	not-accessible
        STATUS	mandatory
        DESCRIPTION
                "The DS3/E3 Far End Interval table"
        ::= { wfDsx3Group 7 }

    wfDsx3FarEndIntervalEntry OBJECT-TYPE
        SYNTAX	WfDsx3FarEndIntervalEntry
        ACCESS	not-accessible
        STATUS	mandatory
        DESCRIPTION
                "per circuit DS3/E3 far end interval objects -
                wfDsx3FarEndIntervalIndex corresponds to Wellfleet circuit
                number, wfDsx3FarEndIntervalNumber is the numbered previous
                15-minute interval"
        INDEX	{ wfDsx3FarEndIntervalIndex,
    		  wfDsx3FarEndIntervalNumber }
        ::= { wfDsx3FarEndIntervalTable 1 }

    WfDsx3FarEndIntervalEntry ::= SEQUENCE {
    	    wfDsx3FarEndIntervalIndex
    		INTEGER,
    	    wfDsx3FarEndIntervalNumber
    		INTEGER,
    	    wfDsx3FarEndIntervalCESs
    		Gauge,
    	    wfDsx3FarEndIntervalCSESs
    		Gauge,
    	    wfDsx3FarEndIntervalCCVs
    		Gauge,
    	    wfDsx3FarEndIntervalUASs
    		Gauge,
    	    wfDsx3FarEndIntervalSASs
    		Gauge,
    	    wfDsx3FarEndIntervalFCs
    		Gauge,
    	    wfDsx3FarEndIntervalValidFlag
    		INTEGER
        }

    wfDsx3FarEndIntervalIndex OBJECT-TYPE
        SYNTAX	INTEGER(1..65535)
        ACCESS	read-only
        STATUS	mandatory
        DESCRIPTION
                "this corresponds to the Wellfleet circuit number"
        ::= { wfDsx3FarEndIntervalEntry 1 }

    wfDsx3FarEndIntervalNumber OBJECT-TYPE
        SYNTAX	INTEGER(1..96)
        ACCESS	read-only
        STATUS	mandatory
        DESCRIPTION
                "1..96 where 1 is the most recent 15-minute interval and 96 is
                the least"
        ::= { wfDsx3FarEndIntervalEntry 2 }

    wfDsx3FarEndIntervalCESs OBJECT-TYPE
        SYNTAX	Gauge
        ACCESS	read-only
        STATUS	mandatory
        DESCRIPTION
                "the count of C-bit Errored Seconds in the specified interval"
        ::= { wfDsx3FarEndIntervalEntry 3 }

    wfDsx3FarEndIntervalCSESs OBJECT-TYPE
        SYNTAX	Gauge
        ACCESS	read-only
        STATUS	mandatory
        DESCRIPTION
                "the count of C-bit Severely Errored Seconds in the
                specified interval"
        ::= { wfDsx3FarEndIntervalEntry 4 }

    wfDsx3FarEndIntervalCCVs OBJECT-TYPE
        SYNTAX	Gauge
        ACCESS	read-only
        STATUS	mandatory
        DESCRIPTION
                "the count of C-bit Code Violation error events in the
                specified interval"
        ::= { wfDsx3FarEndIntervalEntry 5 }

    wfDsx3FarEndIntervalUASs OBJECT-TYPE
        SYNTAX	Gauge
        ACCESS	read-only
        STATUS	mandatory
        DESCRIPTION
                "the count of Unavailable Seconds in the specified interval"
        ::= { wfDsx3FarEndIntervalEntry 6 }

    wfDsx3FarEndIntervalSASs OBJECT-TYPE
        SYNTAX	Gauge
        ACCESS	read-only
        STATUS	mandatory
        DESCRIPTION
                "the number of Seconds containing one or more SEFs or AIS defects
                in the specified far end interval"
        ::= { wfDsx3FarEndIntervalEntry 7 }

    wfDsx3FarEndIntervalFCs OBJECT-TYPE
        SYNTAX	Gauge
        ACCESS	read-only
        STATUS	mandatory
        DESCRIPTION
                "the number of Path Failure Count error events detected
                in the specified far end interval"
        ::= { wfDsx3FarEndIntervalEntry 8 }

    wfDsx3FarEndIntervalValidFlag OBJECT-TYPE
        SYNTAX  INTEGER {
                    valid(1),
                    invalid(2)
                }
        ACCESS  read-only
        STATUS  mandatory
        DESCRIPTION
                "Indicates whether this interval reported by the Mib Table is valid or
                invalid."
        DEFVAL  { valid }
        ::= { wfDsx3FarEndIntervalEntry 9 }


    wfDsx3FarEndTotalTable OBJECT-TYPE
        SYNTAX	SEQUENCE OF WfDsx3FarEndTotalEntry
        ACCESS	not-accessible
        STATUS	mandatory
        DESCRIPTION
                "The DS3/E3 Far End Total table"
        ::= { wfDsx3Group 8 }

    wfDsx3FarEndTotalEntry OBJECT-TYPE
        SYNTAX	WfDsx3FarEndTotalEntry
        ACCESS	not-accessible
        STATUS	mandatory
        DESCRIPTION
                "per circuit far end DS3/E3 total objects - wfDsx3FarEndTotalIndex
                corresponds to Wellfleet circuit number"
        INDEX	{ wfDsx3FarEndTotalIndex }
        ::= { wfDsx3FarEndTotalTable 1 }

    WfDsx3FarEndTotalEntry ::= SEQUENCE {
    	    wfDsx3FarEndTotalIndex
    		INTEGER,
    	    wfDsx3FarEndTotalCESs
    		Gauge,
    	    wfDsx3FarEndTotalCSESs
    		Gauge,
    	    wfDsx3FarEndTotalCCVs
    		Gauge,
    	    wfDsx3FarEndTotalUASs
    		Gauge,
    	    wfDsx3FarEndTotalSASs
    		Gauge,
    	    wfDsx3FarEndTotalFCs
    		Gauge,
    	    wfDsx3FarEndTotalValidFlag
    		INTEGER
        }

    wfDsx3FarEndTotalIndex OBJECT-TYPE
        SYNTAX	INTEGER(1..65535)
        ACCESS	read-only
        STATUS	mandatory
        DESCRIPTION
                "this corresponds to the Wellfleet circuit number"
        ::= { wfDsx3FarEndTotalEntry 1 }

    wfDsx3FarEndTotalCESs OBJECT-TYPE
        SYNTAX	Gauge
        ACCESS	read-only
        STATUS	mandatory
        DESCRIPTION
                "total count of C-bit Errored Seconds"
        ::= { wfDsx3FarEndTotalEntry 2 }

    wfDsx3FarEndTotalCSESs OBJECT-TYPE
        SYNTAX	Gauge
        ACCESS	read-only
        STATUS	mandatory
        DESCRIPTION
                "total count of C-bit Severely Errored Seconds"
        ::= { wfDsx3FarEndTotalEntry 3 }

    wfDsx3FarEndTotalCCVs OBJECT-TYPE
        SYNTAX	Gauge
        ACCESS	read-only
        STATUS	mandatory
        DESCRIPTION
                "total count of C-bit Code Violation error events"
        ::= { wfDsx3FarEndTotalEntry 4 }

    wfDsx3FarEndTotalUASs OBJECT-TYPE
        SYNTAX	Gauge
        ACCESS	read-only
        STATUS	mandatory
        DESCRIPTION
                "total count of Unavailable Seconds"
        ::= { wfDsx3FarEndTotalEntry 5 }

    wfDsx3FarEndTotalSASs OBJECT-TYPE
        SYNTAX	Gauge
        ACCESS	read-only
        STATUS	mandatory
        DESCRIPTION
                "the number of Seconds containing one or more SEFs or AIS defects
                at the far end in the last 24 hours."
        ::= { wfDsx3FarEndTotalEntry 6 }

    wfDsx3FarEndTotalFCs OBJECT-TYPE
        SYNTAX	Gauge
        ACCESS	read-only
        STATUS	mandatory
        DESCRIPTION
                "the number of Path Failure Count error events detected
                at the far end in the last 24 hours."
        ::= { wfDsx3FarEndTotalEntry 7 }

    wfDsx3FarEndTotalValidFlag OBJECT-TYPE
        SYNTAX  INTEGER {
                    valid(1),
                    invalid(2)
                }
        ACCESS  read-only
        STATUS  mandatory
        DESCRIPTION
                "Indicates whether this interval reported by the Mib Table is valid or
                invalid."
        DEFVAL  { valid }
        ::= { wfDsx3FarEndTotalEntry 8 }


    wfAtmInterfaceDs3PlcpTable OBJECT-TYPE
        SYNTAX	SEQUENCE OF WfAtmInterfaceDs3PlcpEntry
        ACCESS	not-accessible
        STATUS	mandatory
        DESCRIPTION
                "The Atm Interface DS3 PLCP table"
        ::= { wfDsx3Group 9 }

    wfAtmInterfaceDs3PlcpEntry OBJECT-TYPE
        SYNTAX	WfAtmInterfaceDs3PlcpEntry
        ACCESS	not-accessible
        STATUS	mandatory
        DESCRIPTION
                "This table contains ATM interface DS3 PLCP parameters
                and state variables, one entry per ATM interface port."
        INDEX	{ wfAtmInterfaceDs3PlcpIndex }
        ::= { wfAtmInterfaceDs3PlcpTable 1 }

    WfAtmInterfaceDs3PlcpEntry ::= SEQUENCE {
    	    wfAtmInterfaceDs3PlcpIndex
    		INTEGER,
    	    wfAtmInterfaceDs3PlcpSEFSs
    		Gauge,
    	    wfAtmInterfaceDs3PlcpAlarmState
    		INTEGER,
    	    wfAtmInterfaceDs3PlcpUASs
    		Gauge
        }

    wfAtmInterfaceDs3PlcpIndex OBJECT-TYPE
        SYNTAX	INTEGER(1..65535)
        ACCESS	read-only
        STATUS	mandatory
        DESCRIPTION
                "this corresponds to the Wellfleet circuit number"
        ::= { wfAtmInterfaceDs3PlcpEntry 1 }

    wfAtmInterfaceDs3PlcpSEFSs OBJECT-TYPE
        SYNTAX	Gauge
        ACCESS	read-only
        STATUS	mandatory
        DESCRIPTION
                "the number of DS3 PLCP Severely Errored Framing Second (SEFS)"
        ::= { wfAtmInterfaceDs3PlcpEntry 2 }

    wfAtmInterfaceDs3PlcpAlarmState OBJECT-TYPE
        SYNTAX	INTEGER {
    		    noalarm(1),
    		    farendalarm(2),
    		    lof(3)
    		}
        ACCESS	read-only
        STATUS	mandatory
        DESCRIPTION
                "the state of the DS3 PLCP"
        ::= { wfAtmInterfaceDs3PlcpEntry 3 }

    wfAtmInterfaceDs3PlcpUASs OBJECT-TYPE
        SYNTAX	Gauge
        ACCESS	read-only
        STATUS	mandatory
        DESCRIPTION
                "the number of Unavailable Seconds encountered by the PLCP"
        ::= { wfAtmInterfaceDs3PlcpEntry 4 }


    wfDsx3DayCurrentTable OBJECT-TYPE
        SYNTAX	SEQUENCE OF WfDsx3DayCurrentEntry
        ACCESS	not-accessible
        STATUS	mandatory
        DESCRIPTION
                "The DS3/E3 Current table"
        ::= { wfDsx3Group 11 }

    wfDsx3DayCurrentEntry OBJECT-TYPE
        SYNTAX	WfDsx3DayCurrentEntry
        ACCESS	not-accessible
        STATUS	mandatory
        DESCRIPTION
                "per circuit DS3/E3 current objects - wfDsx3DayCurrentIndex
                corresponds to Wellfleet circuit number"
        INDEX	{ wfDsx3DayCurrentIndex }
        ::= { wfDsx3DayCurrentTable 1 }

    WfDsx3DayCurrentEntry ::= SEQUENCE {
    	    wfDsx3DayCurrentIndex
    		INTEGER,
    	    wfDsx3DayCurrentPESs
    		Gauge,
    	    wfDsx3DayCurrentPSESs
    		Gauge,
    	    wfDsx3DayCurrentSEFSs
    		Gauge,
    	    wfDsx3DayCurrentUASs
    		Gauge,
    	    wfDsx3DayCurrentLCVs
    		Gauge,
    	    wfDsx3DayCurrentPCVs
    		Gauge,
    	    wfDsx3DayCurrentLESs
    		Gauge,
    	    wfDsx3DayCurrentCCVs
    		Gauge,
    	    wfDsx3DayCurrentCESs
    		Gauge,
    	    wfDsx3DayCurrentCSESs
    		Gauge,
    	    wfDsx3DayCurrentSASs
    		Gauge,
    	    wfDsx3DayCurrentAISSs
    		Gauge,
    	    wfDsx3DayCurrentFCs
    		Gauge,
    	    wfDsx3DayCurrentTimeElapsed
    		INTEGER,
    	    wfDsx3DayCurrentValidIntervals
    		INTEGER,
    	    wfDsx3DayCurrentValidFlag
    		INTEGER
        }

    wfDsx3DayCurrentIndex OBJECT-TYPE
        SYNTAX	INTEGER(1..65535)
        ACCESS	read-only
        STATUS	mandatory
        DESCRIPTION
                "this corresponds to the Wellfleet circuit number"
        ::= { wfDsx3DayCurrentEntry 1 }

    wfDsx3DayCurrentPESs OBJECT-TYPE
        SYNTAX	Gauge
        ACCESS	read-only
        STATUS	mandatory
        DESCRIPTION
                "the number of P-bit Errored Seconds in the current interval"
        ::= { wfDsx3DayCurrentEntry 2 }

    wfDsx3DayCurrentPSESs OBJECT-TYPE
        SYNTAX	Gauge
        ACCESS	read-only
        STATUS	mandatory
        DESCRIPTION
                "the number of P-bit Severely Errored Seconds in the
                current interval"
        ::= { wfDsx3DayCurrentEntry 3 }

    wfDsx3DayCurrentSEFSs OBJECT-TYPE
        SYNTAX	Gauge
        ACCESS	read-only
        STATUS	mandatory
        DESCRIPTION
                "the number of Severely Errored Framing Seconds in the
                current interval"
        ::= { wfDsx3DayCurrentEntry 4 }

    wfDsx3DayCurrentUASs OBJECT-TYPE
        SYNTAX	Gauge
        ACCESS	read-only
        STATUS	mandatory
        DESCRIPTION
                "the number of Unavailable Seconds in the current interval"
        ::= { wfDsx3DayCurrentEntry 5 }

    wfDsx3DayCurrentLCVs OBJECT-TYPE
        SYNTAX	Gauge
        ACCESS	read-only
        STATUS	mandatory
        DESCRIPTION
                "the number of Line Coding Violations in the current interval"
        ::= { wfDsx3DayCurrentEntry 6 }

    wfDsx3DayCurrentPCVs OBJECT-TYPE
        SYNTAX	Gauge
        ACCESS	read-only
        STATUS	mandatory
        DESCRIPTION
                "the number of P-bit Coding Violations in the current interval"
        ::= { wfDsx3DayCurrentEntry 7 }

    wfDsx3DayCurrentLESs OBJECT-TYPE
        SYNTAX	Gauge
        ACCESS	read-only
        STATUS	mandatory
        DESCRIPTION
                "the number of Line Errored Seconds in the current interval"
        ::= { wfDsx3DayCurrentEntry 8 }

    wfDsx3DayCurrentCCVs OBJECT-TYPE
        SYNTAX	Gauge
        ACCESS	read-only
        STATUS	mandatory
        DESCRIPTION
                "the number of C-bit Coding Violations in the current interval"
        ::= { wfDsx3DayCurrentEntry 9 }

    wfDsx3DayCurrentCESs OBJECT-TYPE
        SYNTAX	Gauge
        ACCESS	read-only
        STATUS	mandatory
        DESCRIPTION
                "the number of C-bit Errored Seconds in the current interval"
        ::= { wfDsx3DayCurrentEntry 10 }

    wfDsx3DayCurrentCSESs OBJECT-TYPE
        SYNTAX	Gauge
        ACCESS	read-only
        STATUS	mandatory
        DESCRIPTION
                "the number of C-bit Severely Errored Seconds
                in the current interval"
        ::= { wfDsx3DayCurrentEntry 11 }

    wfDsx3DayCurrentSASs OBJECT-TYPE
        SYNTAX	Gauge
        ACCESS	read-only
        STATUS	mandatory
        DESCRIPTION
                "the number of Seconds containing one or more SEFs or AIS defects
                in the current interval"
        ::= { wfDsx3DayCurrentEntry 12 }

    wfDsx3DayCurrentAISSs OBJECT-TYPE
        SYNTAX	Gauge
        ACCESS	read-only
        STATUS	mandatory
        DESCRIPTION
                "the number of Seconds containing one or more AIS defect
                in the current interval"
        ::= { wfDsx3DayCurrentEntry 13 }

    wfDsx3DayCurrentFCs OBJECT-TYPE
        SYNTAX	Gauge
        ACCESS	read-only
        STATUS	mandatory
        DESCRIPTION
                "the number of Path Failure Count error events detected
                in the current interval"
        ::= { wfDsx3DayCurrentEntry 14 }

    wfDsx3DayCurrentTimeElapsed OBJECT-TYPE
        SYNTAX	INTEGER
        ACCESS	read-only
        STATUS	mandatory
        DESCRIPTION
                "the number of seconds since the beginning of
                the far end current interval"
        ::= { wfDsx3DayCurrentEntry 15 }

    wfDsx3DayCurrentValidIntervals OBJECT-TYPE
        SYNTAX	INTEGER
        ACCESS	read-only
        STATUS	mandatory
        DESCRIPTION
                "the number of previous far end intervals for
                which valid data is available"
        ::= { wfDsx3DayCurrentEntry 16 }

    wfDsx3DayCurrentValidFlag OBJECT-TYPE
        SYNTAX  INTEGER {
                    valid(1),
                    invalid(2)
                }
        ACCESS  read-only
        STATUS  mandatory
        DESCRIPTION
                "Indicates whether this interval reported by the Mib Table is valid or
                invalid."
        DEFVAL  { valid }
        ::= { wfDsx3DayCurrentEntry 17 }


    wfDsx3DayIntervalTable OBJECT-TYPE
        SYNTAX	SEQUENCE OF WfDsx3DayIntervalEntry
        ACCESS	not-accessible
        STATUS	mandatory
        DESCRIPTION
                "The DS3/E3 Interval table"
        ::= { wfDsx3Group 12 }

    wfDsx3DayIntervalEntry OBJECT-TYPE
        SYNTAX	WfDsx3DayIntervalEntry
        ACCESS	not-accessible
        STATUS	mandatory
        DESCRIPTION
                "per circuit DS3/E3 interval objects - wfDsx3DayIntervalIndex
                corresponds to Wellfleet circuit number,
                wfDsx3DayIntervalNumber is the numbered previous
                15-minute interval"
        INDEX	{ wfDsx3DayIntervalIndex,
    		  wfDsx3DayIntervalNumber }
        ::= { wfDsx3DayIntervalTable 1 }

    WfDsx3DayIntervalEntry ::= SEQUENCE {
    	    wfDsx3DayIntervalIndex
    		INTEGER,
    	    wfDsx3DayIntervalNumber
    		INTEGER,
    	    wfDsx3DayIntervalPESs
    		Gauge,
    	    wfDsx3DayIntervalPSESs
    		Gauge,
    	    wfDsx3DayIntervalSEFSs
    		Gauge,
    	    wfDsx3DayIntervalUASs
    		Gauge,
    	    wfDsx3DayIntervalLCVs
    		Gauge,
    	    wfDsx3DayIntervalPCVs
    		Gauge,
    	    wfDsx3DayIntervalLESs
    		Gauge,
    	    wfDsx3DayIntervalCCVs
    		Gauge,
    	    wfDsx3DayIntervalCESs
    		Gauge,
    	    wfDsx3DayIntervalCSESs
    		Gauge,
    	    wfDsx3DayIntervalSASs
    		Gauge,
    	    wfDsx3DayIntervalAISSs
    		Gauge,
    	    wfDsx3DayIntervalFCs
    		Gauge,
    	    wfDsx3DayIntervalValidFlag
    		INTEGER
        }

    wfDsx3DayIntervalIndex OBJECT-TYPE
        SYNTAX	INTEGER(1..65535)
        ACCESS	read-only
        STATUS	mandatory
        DESCRIPTION
                "this corresponds to the Wellfleet circuit number"
        ::= { wfDsx3DayIntervalEntry 1 }

    wfDsx3DayIntervalNumber OBJECT-TYPE
        SYNTAX	INTEGER(1..96)
        ACCESS	read-only
        STATUS	mandatory
        DESCRIPTION
                "1..96 where 1 is the most recent 15-minute interval and 96 is
                the least"
        ::= { wfDsx3DayIntervalEntry 2 }

    wfDsx3DayIntervalPESs OBJECT-TYPE
        SYNTAX	Gauge
        ACCESS	read-only
        STATUS	mandatory
        DESCRIPTION
                "the number of P-bit Errored Seconds in the specified interval"
        ::= { wfDsx3DayIntervalEntry 3 }

    wfDsx3DayIntervalPSESs OBJECT-TYPE
        SYNTAX	Gauge
        ACCESS	read-only
        STATUS	mandatory
        DESCRIPTION
                "the number of P-bit Severely Errored Seconds in the
                specified interval"
        ::= { wfDsx3DayIntervalEntry 4 }

    wfDsx3DayIntervalSEFSs OBJECT-TYPE
        SYNTAX	Gauge
        ACCESS	read-only
        STATUS	mandatory
        DESCRIPTION
                "the number of Severely Errored Framing Seconds in the
                specified interval"
        ::= { wfDsx3DayIntervalEntry 5 }

    wfDsx3DayIntervalUASs OBJECT-TYPE
        SYNTAX	Gauge
        ACCESS	read-only
        STATUS	mandatory
        DESCRIPTION
                "the number of Unavailable Seconds in the specified interval"
        ::= { wfDsx3DayIntervalEntry 6 }

    wfDsx3DayIntervalLCVs OBJECT-TYPE
        SYNTAX	Gauge
        ACCESS	read-only
        STATUS	mandatory
        DESCRIPTION
                "the number of Line Coding Violations in the specified interval"
        ::= { wfDsx3DayIntervalEntry 7 }

    wfDsx3DayIntervalPCVs OBJECT-TYPE
        SYNTAX	Gauge
        ACCESS	read-only
        STATUS	mandatory
        DESCRIPTION
                "the number of P-bit Coding Violations in the specified interval"
        ::= { wfDsx3DayIntervalEntry 8 }

    wfDsx3DayIntervalLESs OBJECT-TYPE
        SYNTAX	Gauge
        ACCESS	read-only
        STATUS	mandatory
        DESCRIPTION
                "the number of Line Errored Seconds in the specified interval"
        ::= { wfDsx3DayIntervalEntry 9 }

    wfDsx3DayIntervalCCVs OBJECT-TYPE
        SYNTAX	Gauge
        ACCESS	read-only
        STATUS	mandatory
        DESCRIPTION
                "the number of C-bit Coding Violations in the specified interval"
        ::= { wfDsx3DayIntervalEntry 10 }

    wfDsx3DayIntervalCESs OBJECT-TYPE
        SYNTAX	Gauge
        ACCESS	read-only
        STATUS	mandatory
        DESCRIPTION
                "the number of C-bit Errored Seconds in the specified interval"
        ::= { wfDsx3DayIntervalEntry 11 }

    wfDsx3DayIntervalCSESs OBJECT-TYPE
        SYNTAX	Gauge
        ACCESS	read-only
        STATUS	mandatory
        DESCRIPTION
                "the number of C-bit Severely Errored Seconds
                in the specified interval"
        ::= { wfDsx3DayIntervalEntry 12 }

    wfDsx3DayIntervalSASs OBJECT-TYPE
        SYNTAX	Gauge
        ACCESS	read-only
        STATUS	mandatory
        DESCRIPTION
                "the number of Seconds containing one or more SEFs or AIS defects
                in the specified interval"
        ::= { wfDsx3DayIntervalEntry 13 }

    wfDsx3DayIntervalAISSs OBJECT-TYPE
        SYNTAX	Gauge
        ACCESS	read-only
        STATUS	mandatory
        DESCRIPTION
                "the number of Seconds containing one or more AIS defect
                in the specified interval"
        ::= { wfDsx3DayIntervalEntry 14 }

    wfDsx3DayIntervalFCs OBJECT-TYPE
        SYNTAX	Gauge
        ACCESS	read-only
        STATUS	mandatory
        DESCRIPTION
                "the number of Path Failure Count error events detected
                in the specified interval"
        ::= { wfDsx3DayIntervalEntry 15 }

    wfDsx3DayIntervalValidFlag OBJECT-TYPE
        SYNTAX  INTEGER {
                    valid(1),
                    invalid(2)
                }
        ACCESS  read-only
        STATUS  mandatory
        DESCRIPTION
                "Indicates whether this interval reported by the Mib Table is valid or
                invalid."
        DEFVAL  { valid }
        ::= { wfDsx3DayIntervalEntry 16 }


    wfDsx3DayTotalTable OBJECT-TYPE
        SYNTAX	SEQUENCE OF WfDsx3DayTotalEntry
        ACCESS	not-accessible
        STATUS	mandatory
        DESCRIPTION
                "The DS3/E3 Total table"
        ::= { wfDsx3Group 13 }

    wfDsx3DayTotalEntry OBJECT-TYPE
        SYNTAX	WfDsx3DayTotalEntry
        ACCESS	not-accessible
        STATUS	mandatory
        DESCRIPTION
                "per circuit DS3/E3 total objects - wfDsx3DayTotalIndex
                corresponds to Wellfleet circuit number"
        INDEX	{ wfDsx3DayTotalIndex }
        ::= { wfDsx3DayTotalTable 1 }

    WfDsx3DayTotalEntry ::= SEQUENCE {
    	    wfDsx3DayTotalIndex
    		INTEGER,
    	    wfDsx3DayTotalPESs
    		Gauge,
    	    wfDsx3DayTotalPSESs
    		Gauge,
    	    wfDsx3DayTotalSEFSs
    		Gauge,
    	    wfDsx3DayTotalUASs
    		Gauge,
    	    wfDsx3DayTotalLCVs
    		Gauge,
    	    wfDsx3DayTotalPCVs
    		Gauge,
    	    wfDsx3DayTotalLESs
    		Gauge,
    	    wfDsx3DayTotalCCVs
    		Gauge,
    	    wfDsx3DayTotalCESs
    		Gauge,
    	    wfDsx3DayTotalCSESs
    		Gauge,
    	    wfDsx3DayTotalSASs
    		Gauge,
    	    wfDsx3DayTotalAISSs
    		Gauge,
    	    wfDsx3DayTotalFCs
    		Gauge,
    	    wfDsx3DayTotalValidFlag
    		INTEGER
        }

    wfDsx3DayTotalIndex OBJECT-TYPE
        SYNTAX	INTEGER(1..65535)
        ACCESS	read-only
        STATUS	mandatory
        DESCRIPTION
                "this corresponds to the Wellfleet circuit number"
        ::= { wfDsx3DayTotalEntry 1 }

    wfDsx3DayTotalPESs OBJECT-TYPE
        SYNTAX	Gauge
        ACCESS	read-only
        STATUS	mandatory
        DESCRIPTION
                "the number of P-bit Errored Seconds in the last 24 hours"
        ::= { wfDsx3DayTotalEntry 2 }

    wfDsx3DayTotalPSESs OBJECT-TYPE
        SYNTAX	Gauge
        ACCESS	read-only
        STATUS	mandatory
        DESCRIPTION
                "the number of P-bit Severely Errored Seconds in the
                last 24 hours"
        ::= { wfDsx3DayTotalEntry 3 }

    wfDsx3DayTotalSEFSs OBJECT-TYPE
        SYNTAX	Gauge
        ACCESS	read-only
        STATUS	mandatory
        DESCRIPTION
                "the number of Severely Errored Framing Seconds in the
                last 24 hours"
        ::= { wfDsx3DayTotalEntry 4 }

    wfDsx3DayTotalUASs OBJECT-TYPE
        SYNTAX	Gauge
        ACCESS	read-only
        STATUS	mandatory
        DESCRIPTION
                "the number of Unavailable Seconds in the last 24 hours"
        ::= { wfDsx3DayTotalEntry 5 }

    wfDsx3DayTotalLCVs OBJECT-TYPE
        SYNTAX	Gauge
        ACCESS	read-only
        STATUS	mandatory
        DESCRIPTION
                "the number of Line Coding Violations in the last 24 hours"
        ::= { wfDsx3DayTotalEntry 6 }

    wfDsx3DayTotalPCVs OBJECT-TYPE
        SYNTAX	Gauge
        ACCESS	read-only
        STATUS	mandatory
        DESCRIPTION
                "the number of P-bit Coding Violations in the last 24 hours"
        ::= { wfDsx3DayTotalEntry 7 }

    wfDsx3DayTotalLESs OBJECT-TYPE
        SYNTAX	Gauge
        ACCESS	read-only
        STATUS	mandatory
        DESCRIPTION
                "the number of Line Errored Seconds in the last 24 hours"
        ::= { wfDsx3DayTotalEntry 8 }

    wfDsx3DayTotalCCVs OBJECT-TYPE
        SYNTAX	Gauge
        ACCESS	read-only
        STATUS	mandatory
        DESCRIPTION
                "the number of C-bit Coding Violations in the last 24 hours"
        ::= { wfDsx3DayTotalEntry 9 }

    wfDsx3DayTotalCESs OBJECT-TYPE
        SYNTAX	Gauge
        ACCESS	read-only
        STATUS	mandatory
        DESCRIPTION
                "the number of C-bit Errored Seconds in the last 24 hours"
        ::= { wfDsx3DayTotalEntry 10 }

    wfDsx3DayTotalCSESs OBJECT-TYPE
        SYNTAX	Gauge
        ACCESS	read-only
        STATUS	mandatory
        DESCRIPTION
                "the number of C-bit Severely Errored Seconds
                in the last 24 hours"
        ::= { wfDsx3DayTotalEntry 11 }

    wfDsx3DayTotalSASs OBJECT-TYPE
        SYNTAX	Gauge
        ACCESS	read-only
        STATUS	mandatory
        DESCRIPTION
                "the number of Seconds containing one or more SEFs or AIS defects
                in the last 24 hours"
        ::= { wfDsx3DayTotalEntry 12 }

    wfDsx3DayTotalAISSs OBJECT-TYPE
        SYNTAX	Gauge
        ACCESS	read-only
        STATUS	mandatory
        DESCRIPTION
                "the number of Seconds containing one or more AIS defect
                in the last 24 hours"
        ::= { wfDsx3DayTotalEntry 13 }

    wfDsx3DayTotalFCs OBJECT-TYPE
        SYNTAX	Gauge
        ACCESS	read-only
        STATUS	mandatory
        DESCRIPTION
                "the number of Path Failure Count error events detected
                in the last 24 hours"
        ::= { wfDsx3DayTotalEntry 14 }

    wfDsx3DayTotalValidFlag OBJECT-TYPE
        SYNTAX  INTEGER {
                    valid(1),
                    invalid(2)
                }
        ACCESS  read-only
        STATUS  mandatory
        DESCRIPTION
                "Indicates whether this interval reported by the Mib Table is valid or
                invalid."
        DEFVAL  { valid }
        ::= { wfDsx3DayTotalEntry 15 }


    wfDsx3FarEndDayCurrentTable OBJECT-TYPE
        SYNTAX	SEQUENCE OF WfDsx3FarEndDayCurrentEntry
        ACCESS	not-accessible
        STATUS	mandatory
        DESCRIPTION
                "The DS3/E3 Far End Current table"
        ::= { wfDsx3Group 14 }

    wfDsx3FarEndDayCurrentEntry OBJECT-TYPE
        SYNTAX	WfDsx3FarEndDayCurrentEntry
        ACCESS	not-accessible
        STATUS	mandatory
        DESCRIPTION
                "per circuit DS3/E3 far end current objects
                wfDsx3FarEndDayCurrentIndex corresponds to Wellfleet circuit
                number"
        INDEX	{ wfDsx3FarEndDayCurrentIndex }
        ::= { wfDsx3FarEndDayCurrentTable 1 }

    WfDsx3FarEndDayCurrentEntry ::= SEQUENCE {
    	    wfDsx3FarEndDayCurrentIndex
    		INTEGER,
    	    wfDsx3FarEndDayTimeElapsed
    		INTEGER,
    	    wfDsx3FarEndDayValidIntervals
    		INTEGER,
    	    wfDsx3FarEndDayCurrentCESs
    		Gauge,
    	    wfDsx3FarEndDayCurrentCSESs
    		Gauge,
    	    wfDsx3FarEndDayCurrentCCVs
    		Gauge,
    	    wfDsx3FarEndDayCurrentUASs
    		Gauge,
    	    wfDsx3FarEndDayCurrentSASs
    		Gauge,
    	    wfDsx3FarEndDayCurrentFCs
    		Gauge,
    	    wfDsx3FarEndDayCurrentValidFlag
    		INTEGER
        }

    wfDsx3FarEndDayCurrentIndex OBJECT-TYPE
        SYNTAX	INTEGER(1..1024)
        ACCESS	read-only
        STATUS	mandatory
        DESCRIPTION
                "this corresponds to the Wellfleet circuit number"
        ::= { wfDsx3FarEndDayCurrentEntry 1 }

    wfDsx3FarEndDayTimeElapsed OBJECT-TYPE
        SYNTAX	INTEGER
        ACCESS	read-only
        STATUS	mandatory
        DESCRIPTION
                "the number of seconds since the beginning of
                the far end current interval"
        ::= { wfDsx3FarEndDayCurrentEntry 2 }

    wfDsx3FarEndDayValidIntervals OBJECT-TYPE
        SYNTAX	INTEGER
        ACCESS	read-only
        STATUS	mandatory
        DESCRIPTION
                "the number of previous far end intervals for
                which valid data is available"
        ::= { wfDsx3FarEndDayCurrentEntry 3 }

    wfDsx3FarEndDayCurrentCESs OBJECT-TYPE
        SYNTAX	Gauge
        ACCESS	read-only
        STATUS	mandatory
        DESCRIPTION
                "the number of C-bit Errored Seconds in
                the current far end interval"
        ::= { wfDsx3FarEndDayCurrentEntry 4 }

    wfDsx3FarEndDayCurrentCSESs OBJECT-TYPE
        SYNTAX	Gauge
        ACCESS	read-only
        STATUS	mandatory
        DESCRIPTION
                "the number of C-bit Severely Errored Seconds
                in the current far end interval"
        ::= { wfDsx3FarEndDayCurrentEntry 5 }

    wfDsx3FarEndDayCurrentCCVs OBJECT-TYPE
        SYNTAX	Gauge
        ACCESS	read-only
        STATUS	mandatory
        DESCRIPTION
                "the number of C-bit Coding Violations
                in the current far end interval"
        ::= { wfDsx3FarEndDayCurrentEntry 6 }

    wfDsx3FarEndDayCurrentUASs OBJECT-TYPE
        SYNTAX	Gauge
        ACCESS	read-only
        STATUS	mandatory
        DESCRIPTION
                "the number of Unavailable Seconds
                in the current far end interval"
        ::= { wfDsx3FarEndDayCurrentEntry 7 }

    wfDsx3FarEndDayCurrentSASs OBJECT-TYPE
        SYNTAX	Gauge
        ACCESS	read-only
        STATUS	mandatory
        DESCRIPTION
                "the number of Seconds containing one or more SEFs or AIS defects
                in the current far end interval"
        ::= { wfDsx3FarEndDayCurrentEntry 8 }

    wfDsx3FarEndDayCurrentFCs OBJECT-TYPE
        SYNTAX	Gauge
        ACCESS	read-only
        STATUS	mandatory
        DESCRIPTION
                "the number of Path Failure Count error events detected
                in the current far end interval"
        ::= { wfDsx3FarEndDayCurrentEntry 9 }

    wfDsx3FarEndDayCurrentValidFlag OBJECT-TYPE
        SYNTAX  INTEGER {
                    valid(1),
                    invalid(2)
                }
        ACCESS  read-only
        STATUS  mandatory
        DESCRIPTION
                "Indicates whether this interval reported by the Mib Table is valid or
                invalid."
        DEFVAL  { valid }
        ::= { wfDsx3FarEndDayCurrentEntry 10 }


    wfDsx3FarEndDayIntervalTable OBJECT-TYPE
        SYNTAX	SEQUENCE OF WfDsx3FarEndDayIntervalEntry
        ACCESS	not-accessible
        STATUS	mandatory
        DESCRIPTION
                "The DS3/E3 Far End Interval table"
        ::= { wfDsx3Group 15 }

    wfDsx3FarEndDayIntervalEntry OBJECT-TYPE
        SYNTAX	WfDsx3FarEndDayIntervalEntry
        ACCESS	not-accessible
        STATUS	mandatory
        DESCRIPTION
                "per circuit DS3/E3 far end interval objects -
                wfDsx3FarEndDayIntervalIndex corresponds to Wellfleet circuit
                number, wfDsx3FarEndDayIntervalNumber is the numbered previous
                15-minute interval"
        INDEX	{ wfDsx3FarEndDayIntervalIndex,
    		  wfDsx3FarEndDayIntervalNumber }
        ::= { wfDsx3FarEndDayIntervalTable 1 }

    WfDsx3FarEndDayIntervalEntry ::= SEQUENCE {
    	    wfDsx3FarEndDayIntervalIndex
    		INTEGER,
    	    wfDsx3FarEndDayIntervalNumber
    		INTEGER,
    	    wfDsx3FarEndDayIntervalCESs
    		Gauge,
    	    wfDsx3FarEndDayIntervalCSESs
    		Gauge,
    	    wfDsx3FarEndDayIntervalCCVs
    		Gauge,
    	    wfDsx3FarEndDayIntervalUASs
    		Gauge,
    	    wfDsx3FarEndDayIntervalSASs
    		Gauge,
    	    wfDsx3FarEndDayIntervalFCs
    		Gauge,
    	    wfDsx3FarEndDayIntervalValidFlag
    		INTEGER
        }

    wfDsx3FarEndDayIntervalIndex OBJECT-TYPE
        SYNTAX	INTEGER(1..65535)
        ACCESS	read-only
        STATUS	mandatory
        DESCRIPTION
                "this corresponds to the Wellfleet circuit number"
        ::= { wfDsx3FarEndDayIntervalEntry 1 }

    wfDsx3FarEndDayIntervalNumber OBJECT-TYPE
        SYNTAX	INTEGER(1..96)
        ACCESS	read-only
        STATUS	mandatory
        DESCRIPTION
                "1..96 where 1 is the most recent 15-minute interval and 96 is
                the least"
        ::= { wfDsx3FarEndDayIntervalEntry 2 }

    wfDsx3FarEndDayIntervalCESs OBJECT-TYPE
        SYNTAX	Gauge
        ACCESS	read-only
        STATUS	mandatory
        DESCRIPTION
                "the count of C-bit Errored Seconds in the specified interval"
        ::= { wfDsx3FarEndDayIntervalEntry 3 }

    wfDsx3FarEndDayIntervalCSESs OBJECT-TYPE
        SYNTAX	Gauge
        ACCESS	read-only
        STATUS	mandatory
        DESCRIPTION
                "the count of C-bit Severely Errored Seconds in the
                specified interval"
        ::= { wfDsx3FarEndDayIntervalEntry 4 }

    wfDsx3FarEndDayIntervalCCVs OBJECT-TYPE
        SYNTAX	Gauge
        ACCESS	read-only
        STATUS	mandatory
        DESCRIPTION
                "the count of C-bit Code Violation error events in the
                specified interval"
        ::= { wfDsx3FarEndDayIntervalEntry 5 }

    wfDsx3FarEndDayIntervalUASs OBJECT-TYPE
        SYNTAX	Gauge
        ACCESS	read-only
        STATUS	mandatory
        DESCRIPTION
                "the count of Unavailable Seconds in the specified interval"
        ::= { wfDsx3FarEndDayIntervalEntry 6 }

    wfDsx3FarEndDayIntervalSASs OBJECT-TYPE
        SYNTAX	Gauge
        ACCESS	read-only
        STATUS	mandatory
        DESCRIPTION
                "the number of Seconds containing one or more SEFs or AIS defects
                in the specified far end interval"
        ::= { wfDsx3FarEndDayIntervalEntry 7 }

    wfDsx3FarEndDayIntervalFCs OBJECT-TYPE
        SYNTAX	Gauge
        ACCESS	read-only
        STATUS	mandatory
        DESCRIPTION
                "the number of Path Failure Count error events detected
                in the specified far end interval"
        ::= { wfDsx3FarEndDayIntervalEntry 8 }

    wfDsx3FarEndDayIntervalValidFlag OBJECT-TYPE
        SYNTAX  INTEGER {
                    valid(1),
                    invalid(2)
                }
        ACCESS  read-only
        STATUS  mandatory
        DESCRIPTION
                "Indicates whether this interval reported by the Mib Table is valid or
                invalid."
        DEFVAL  { valid }
        ::= { wfDsx3FarEndDayIntervalEntry 9 }


    wfDsx3FarEndDayTotalTable OBJECT-TYPE
        SYNTAX	SEQUENCE OF WfDsx3FarEndDayTotalEntry
        ACCESS	not-accessible
        STATUS	mandatory
        DESCRIPTION
                "The DS3/E3 Far End Total table"
        ::= { wfDsx3Group 16 }

    wfDsx3FarEndDayTotalEntry OBJECT-TYPE
        SYNTAX	WfDsx3FarEndDayTotalEntry
        ACCESS	not-accessible
        STATUS	mandatory
        DESCRIPTION
                "per circuit far end DS3/E3 total objects - wfDsx3FarEndDayTotalIndex
                corresponds to Wellfleet circuit number"
        INDEX	{ wfDsx3FarEndDayTotalIndex }
        ::= { wfDsx3FarEndDayTotalTable 1 }

    WfDsx3FarEndDayTotalEntry ::= SEQUENCE {
    	    wfDsx3FarEndDayTotalIndex
    		INTEGER,
    	    wfDsx3FarEndDayTotalCESs
    		Gauge,
    	    wfDsx3FarEndDayTotalCSESs
    		Gauge,
    	    wfDsx3FarEndDayTotalCCVs
    		Gauge,
    	    wfDsx3FarEndDayTotalUASs
    		Gauge,
    	    wfDsx3FarEndDayTotalSASs
    		Gauge,
    	    wfDsx3FarEndDayTotalFCs
    		Gauge,
    	    wfDsx3FarEndDayTotalValidFlag
    		INTEGER
        }

    wfDsx3FarEndDayTotalIndex OBJECT-TYPE
        SYNTAX	INTEGER(1..65535)
        ACCESS	read-only
        STATUS	mandatory
        DESCRIPTION
                "this corresponds to the Wellfleet circuit number"
        ::= { wfDsx3FarEndDayTotalEntry 1 }

    wfDsx3FarEndDayTotalCESs OBJECT-TYPE
        SYNTAX	Gauge
        ACCESS	read-only
        STATUS	mandatory
        DESCRIPTION
                "total count of C-bit Errored Seconds"
        ::= { wfDsx3FarEndDayTotalEntry 2 }

    wfDsx3FarEndDayTotalCSESs OBJECT-TYPE
        SYNTAX	Gauge
        ACCESS	read-only
        STATUS	mandatory
        DESCRIPTION
                "total count of C-bit Severely Errored Seconds"
        ::= { wfDsx3FarEndDayTotalEntry 3 }

    wfDsx3FarEndDayTotalCCVs OBJECT-TYPE
        SYNTAX	Gauge
        ACCESS	read-only
        STATUS	mandatory
        DESCRIPTION
                "total count of C-bit Code Violation error events"
        ::= { wfDsx3FarEndDayTotalEntry 4 }

    wfDsx3FarEndDayTotalUASs OBJECT-TYPE
        SYNTAX	Gauge
        ACCESS	read-only
        STATUS	mandatory
        DESCRIPTION
                "total count of Unavailable Seconds"
        ::= { wfDsx3FarEndDayTotalEntry 5 }

    wfDsx3FarEndDayTotalSASs OBJECT-TYPE
        SYNTAX	Gauge
        ACCESS	read-only
        STATUS	mandatory
        DESCRIPTION
                "the number of Seconds containing one or more SEFs or AIS defects
                at the far end in the last 24 hours."
        ::= { wfDsx3FarEndDayTotalEntry 6 }

    wfDsx3FarEndDayTotalFCs OBJECT-TYPE
        SYNTAX	Gauge
        ACCESS	read-only
        STATUS	mandatory
        DESCRIPTION
                "the number of Path Failure Count error events detected
                at the far end in the last 24 hours."
        ::= { wfDsx3FarEndDayTotalEntry 7 }

    wfDsx3FarEndDayTotalValidFlag OBJECT-TYPE
        SYNTAX  INTEGER {
                    valid(1),
                    invalid(2)
                }
        ACCESS  read-only
        STATUS  mandatory
        DESCRIPTION
                "Indicates whether this interval reported by the Mib Table is valid or
                invalid."
        DEFVAL  { valid }
        ::= { wfDsx3FarEndDayTotalEntry 8 }


    wfDsx3ThrAlrtTable OBJECT-TYPE
        SYNTAX	SEQUENCE OF WfDsx3ThrAlrtEntry
        ACCESS	not-accessible
        STATUS	mandatory
        DESCRIPTION
		"Current statistics Alarm Threshold Crossing table."
        ::= { wfDsx3Group 18 }

    wfDsx3ThrAlrtEntry OBJECT-TYPE
        SYNTAX	WfDsx3ThrAlrtEntry
        ACCESS	not-accessible
        STATUS	mandatory
        DESCRIPTION
		"An entry in the Dsx3 ThrAlrt table"
        INDEX	{ wfDsx3ThrAlrtIndex }
        ::= { wfDsx3ThrAlrtTable 1 }

    WfDsx3ThrAlrtEntry ::= SEQUENCE {
    	    wfDsx3ThrAlrtDelete
    		INTEGER,
    	    wfDsx3ThrAlrtIndex
    		INTEGER,
    	    wfDsx3ThrAlrtPESs
    		Gauge,
    	    wfDsx3ThrAlrtPSESs
    		Gauge,
    	    wfDsx3ThrAlrtSEFSs
    		Gauge,
    	    wfDsx3ThrAlrtUASs
    		Gauge,
    	    wfDsx3ThrAlrtLCVs
    		Gauge,
    	    wfDsx3ThrAlrtPCVs
    		Gauge,
    	    wfDsx3ThrAlrtLESs
    		Gauge,
    	    wfDsx3ThrAlrtCCVs
    		Gauge,
    	    wfDsx3ThrAlrtCESs
    		Gauge,
    	    wfDsx3ThrAlrtCSESs
    		Gauge,
    	    wfDsx3ThrAlrtSASs
    		Gauge,
    	    wfDsx3ThrAlrtAISSs
    		Gauge,
    	    wfDsx3ThrAlrtFCs
    		Gauge
        }

    wfDsx3ThrAlrtDelete OBJECT-TYPE
        SYNTAX	INTEGER {
    		    created(1),
    		    deleted(2)
    		}
        ACCESS	read-write
        STATUS	mandatory
        DESCRIPTION
                "Create/Delete parameter"
        DEFVAL	{ created }
        ::= { wfDsx3ThrAlrtEntry 1 }

    wfDsx3ThrAlrtIndex OBJECT-TYPE
        SYNTAX	INTEGER
        ACCESS	read-only
        STATUS	mandatory
        DESCRIPTION
                "The instance ID that identifies the port."
        ::= { wfDsx3ThrAlrtEntry 2 }

    wfDsx3ThrAlrtPESs OBJECT-TYPE
        SYNTAX	Gauge
        ACCESS	read-write
        STATUS	mandatory
        DESCRIPTION
		"The number of P-bit Errored Seconds which must be received
		prior to the generation of a Threshold Crossing Alert."
        DEFVAL	{ 25 }
        ::= { wfDsx3ThrAlrtEntry 3 }

    wfDsx3ThrAlrtPSESs OBJECT-TYPE
        SYNTAX	Gauge
        ACCESS	read-write
        STATUS	mandatory
        DESCRIPTION
		"The number of P-bit Severely Errored Seconds which must be received
		prior to the generation of a Threshold Crossing Alert."
        DEFVAL	{ 4 }
        ::= { wfDsx3ThrAlrtEntry 4 }

    wfDsx3ThrAlrtSEFSs OBJECT-TYPE
        SYNTAX	Gauge
        ACCESS	read-write
        STATUS	mandatory
        DESCRIPTION
		"The number of Severely Errored Framing Seconds which must be received
		prior to the generation of a Threshold Crossing Alert."
        DEFVAL	{ 0 }
        ::= { wfDsx3ThrAlrtEntry 5 }

    wfDsx3ThrAlrtUASs OBJECT-TYPE
        SYNTAX	Gauge
        ACCESS	read-write
        STATUS	mandatory
        DESCRIPTION
		"The number of Unavailable Seconds which must be received
		prior to the generation of a Threshold Crossing Alert."
        DEFVAL	{ 10 }
        ::= { wfDsx3ThrAlrtEntry 6 }

    wfDsx3ThrAlrtLCVs OBJECT-TYPE
        SYNTAX	Gauge
        ACCESS	read-write
        STATUS	mandatory
        DESCRIPTION
		"The number of Line Coding Violations which must be received
		prior to the generation of a Threshold Crossing Alert."
        DEFVAL	{ 387 }
        ::= { wfDsx3ThrAlrtEntry 7 }

    wfDsx3ThrAlrtPCVs OBJECT-TYPE
        SYNTAX	Gauge
        ACCESS	read-write
        STATUS	mandatory
        DESCRIPTION
		"The number of P-bit Coding Violations which must be received
		prior to the generation of a Threshold Crossing Alert."
        DEFVAL	{ 382 }
        ::= { wfDsx3ThrAlrtEntry 8 }

    wfDsx3ThrAlrtLESs OBJECT-TYPE
        SYNTAX	Gauge
        ACCESS	read-write
        STATUS	mandatory
        DESCRIPTION
		"The number of Line Errored Seconds which must be received
		prior to the generation of a Threshold Crossing Alert."
        DEFVAL	{ 25 }
        ::= { wfDsx3ThrAlrtEntry 9 }

    wfDsx3ThrAlrtCCVs OBJECT-TYPE
        SYNTAX	Gauge
        ACCESS	read-write
        STATUS	mandatory
        DESCRIPTION
		"The number of C-bit Coding Violations which must be received
		prior to the generation of a Threshold Crossing Alert."
        DEFVAL	{ 382 }
        ::= { wfDsx3ThrAlrtEntry 10 }

    wfDsx3ThrAlrtCESs OBJECT-TYPE
        SYNTAX	Gauge
        ACCESS	read-write
        STATUS	mandatory
        DESCRIPTION
		"The number of C-bit Errored Seconds which must be received
		prior to the generation of a Threshold Crossing Alert."
        DEFVAL	{ 25 }
        ::= { wfDsx3ThrAlrtEntry 11 }

    wfDsx3ThrAlrtCSESs OBJECT-TYPE
        SYNTAX	Gauge
        ACCESS	read-write
        STATUS	mandatory
        DESCRIPTION
		"The number of C-bit Severely Errored Seconds which must be received
		prior to the generation of a Threshold Crossing Alert."
        DEFVAL	{ 4 }
        ::= { wfDsx3ThrAlrtEntry 12 }

    wfDsx3ThrAlrtSASs OBJECT-TYPE
        SYNTAX	Gauge
        ACCESS	read-write
        STATUS	mandatory
        DESCRIPTION
		"The number of SEF/AIS Seconds which must be received
		prior to the generation of a Threshold Crossing Alert."
        DEFVAL	{ 0 }
        ::= { wfDsx3ThrAlrtEntry 13 }

    wfDsx3ThrAlrtAISSs OBJECT-TYPE
        SYNTAX	Gauge
        ACCESS	read-write
        STATUS	mandatory
        DESCRIPTION
		"The number of AIS defect Seconds which must be received
		prior to the generation of a Threshold Crossing Alert."
        DEFVAL	{ 0 }
        ::= { wfDsx3ThrAlrtEntry 14 }

    wfDsx3ThrAlrtFCs OBJECT-TYPE
        SYNTAX	Gauge
        ACCESS	read-write
        STATUS	mandatory
        DESCRIPTION
		"The number of Path Failure Counts which must be received
		prior to the generation of a Threshold Crossing Alert."
        DEFVAL	{ 0 }
        ::= { wfDsx3ThrAlrtEntry 15 }



    wfDsx3FarEndThrAlrtTable OBJECT-TYPE
        SYNTAX	SEQUENCE OF WfDsx3FarEndThrAlrtEntry
        ACCESS	not-accessible
        STATUS	mandatory
        DESCRIPTION
		"Current Far End statistics Alarm Threshold Crossing table."
        ::= { wfDsx3Group 19 }

    wfDsx3FarEndThrAlrtEntry OBJECT-TYPE
        SYNTAX	WfDsx3FarEndThrAlrtEntry
        ACCESS	not-accessible
        STATUS	mandatory
        DESCRIPTION
		"An entry in the Dsx3 ThrAlrt table"
        INDEX	{ wfDsx3FarEndThrAlrtIndex }
        ::= { wfDsx3FarEndThrAlrtTable 1 }

    WfDsx3FarEndThrAlrtEntry ::= SEQUENCE {
    	    wfDsx3FarEndThrAlrtDelete
    		INTEGER,
    	    wfDsx3FarEndThrAlrtIndex
    		INTEGER,
    	    wfDsx3FarEndThrAlrtCESs
    		Gauge,
    	    wfDsx3FarEndThrAlrtCSESs
    		Gauge,
    	    wfDsx3FarEndThrAlrtCCVs
    		Gauge,
    	    wfDsx3FarEndThrAlrtUASs
    		Gauge,
    	    wfDsx3FarEndThrAlrtSASs
    		Gauge,
    	    wfDsx3FarEndThrAlrtFCs
    		Gauge
        }

    wfDsx3FarEndThrAlrtDelete OBJECT-TYPE
        SYNTAX	INTEGER {
    		    created(1),
    		    deleted(2)
    		}
        ACCESS	read-write
        STATUS	mandatory
        DESCRIPTION
                "Create/Delete parameter"
        DEFVAL	{ created }
        ::= { wfDsx3FarEndThrAlrtEntry 1 }

    wfDsx3FarEndThrAlrtIndex OBJECT-TYPE
        SYNTAX	INTEGER
        ACCESS	read-only
        STATUS	mandatory
        DESCRIPTION
                "The instance ID that identifies the port."
        ::= { wfDsx3FarEndThrAlrtEntry 2 }

    wfDsx3FarEndThrAlrtCESs OBJECT-TYPE
        SYNTAX	Gauge
        ACCESS	read-write
        STATUS	mandatory
        DESCRIPTION
		"The number of C-bit Errored Seconds which must be received
		prior to the generation of a Threshold Crossing Alert."
        DEFVAL	{ 25 }
        ::= { wfDsx3FarEndThrAlrtEntry 3 }

    wfDsx3FarEndThrAlrtCSESs OBJECT-TYPE
        SYNTAX	Gauge
        ACCESS	read-write
        STATUS	mandatory
        DESCRIPTION
		"The number of C-bit Severely Errored Seconds which must be received
		prior to the generation of a Threshold Crossing Alert."
        DEFVAL	{ 4 }
        ::= { wfDsx3FarEndThrAlrtEntry 4 }

    wfDsx3FarEndThrAlrtCCVs OBJECT-TYPE
        SYNTAX	Gauge
        ACCESS	read-write
        STATUS	mandatory
        DESCRIPTION
		"The number of C-bit Coding Violations which must be received
		prior to the generation of a Threshold Crossing Alert."
        DEFVAL	{ 382 }
        ::= { wfDsx3FarEndThrAlrtEntry 5 }

    wfDsx3FarEndThrAlrtUASs OBJECT-TYPE
        SYNTAX	Gauge
        ACCESS	read-write
        STATUS	mandatory
        DESCRIPTION
		"The number of Unavailable Seconds which must be received
		prior to the generation of a Threshold Crossing Alert."
        DEFVAL	{ 10 }
        ::= { wfDsx3FarEndThrAlrtEntry 6 }

    wfDsx3FarEndThrAlrtSASs OBJECT-TYPE
        SYNTAX	Gauge
        ACCESS	read-write
        STATUS	mandatory
        DESCRIPTION
		"The number of SEF/AIS Seconds which must be received
		prior to the generation of a Threshold Crossing Alert."
        DEFVAL	{ 0 }
        ::= { wfDsx3FarEndThrAlrtEntry 7 }

    wfDsx3FarEndThrAlrtFCs OBJECT-TYPE
        SYNTAX	Gauge
        ACCESS	read-write
        STATUS	mandatory
        DESCRIPTION
		"The number of Path Failure Counts which must be received
		prior to the generation of a Threshold Crossing Alert."
        DEFVAL	{ 0 }
        ::= { wfDsx3FarEndThrAlrtEntry 8 }



    wfDsx3DayThrAlrtTable OBJECT-TYPE
        SYNTAX	SEQUENCE OF WfDsx3DayThrAlrtEntry
        ACCESS	not-accessible
        STATUS	mandatory
        DESCRIPTION
		"Current Day statistics Alarm Threshold Crossing table."
        ::= { wfDsx3Group 20 }

    wfDsx3DayThrAlrtEntry OBJECT-TYPE
        SYNTAX	WfDsx3DayThrAlrtEntry
        ACCESS	not-accessible
        STATUS	mandatory
        DESCRIPTION
		"An entry in the Dsx3 ThrAlrt table"
        INDEX	{ wfDsx3DayThrAlrtIndex }
        ::= { wfDsx3DayThrAlrtTable 1 }

    WfDsx3DayThrAlrtEntry ::= SEQUENCE {
    	    wfDsx3DayThrAlrtDelete
    		INTEGER,
    	    wfDsx3DayThrAlrtIndex
    		INTEGER,
    	    wfDsx3DayThrAlrtPESs
    		Gauge,
    	    wfDsx3DayThrAlrtPSESs
    		Gauge,
    	    wfDsx3DayThrAlrtSEFSs
    		Gauge,
    	    wfDsx3DayThrAlrtUASs
    		Gauge,
    	    wfDsx3DayThrAlrtLCVs
    		Gauge,
    	    wfDsx3DayThrAlrtPCVs
    		Gauge,
    	    wfDsx3DayThrAlrtLESs
    		Gauge,
    	    wfDsx3DayThrAlrtCCVs
    		Gauge,
    	    wfDsx3DayThrAlrtCESs
    		Gauge,
    	    wfDsx3DayThrAlrtCSESs
    		Gauge,
    	    wfDsx3DayThrAlrtSASs
    		Gauge,
    	    wfDsx3DayThrAlrtAISSs
    		Gauge,
    	    wfDsx3DayThrAlrtFCs
    		Gauge
        }

    wfDsx3DayThrAlrtDelete OBJECT-TYPE
        SYNTAX	INTEGER {
    		    created(1),
    		    deleted(2)
    		}
        ACCESS	read-write
        STATUS	mandatory
        DESCRIPTION
                "Create/Delete parameter"
        DEFVAL	{ created }
        ::= { wfDsx3DayThrAlrtEntry 1 }

    wfDsx3DayThrAlrtIndex OBJECT-TYPE
        SYNTAX	INTEGER
        ACCESS	read-only
        STATUS	mandatory
        DESCRIPTION
                "The instance ID that identifies the port."
        ::= { wfDsx3DayThrAlrtEntry 2 }

    wfDsx3DayThrAlrtPESs OBJECT-TYPE
        SYNTAX	Gauge
        ACCESS	read-write
        STATUS	mandatory
        DESCRIPTION
		"The number of P-bit Errored Seconds which must be received
		prior to the generation of a Threshold Crossing Alert."
        DEFVAL	{ 250 }
        ::= { wfDsx3DayThrAlrtEntry 3 }

    wfDsx3DayThrAlrtPSESs OBJECT-TYPE
        SYNTAX	Gauge
        ACCESS	read-write
        STATUS	mandatory
        DESCRIPTION
		"The number of P-bit Severely Errored Seconds which must be received
		prior to the generation of a Threshold Crossing Alert."
        DEFVAL	{ 40 }
        ::= { wfDsx3DayThrAlrtEntry 4 }

    wfDsx3DayThrAlrtSEFSs OBJECT-TYPE
        SYNTAX	Gauge
        ACCESS	read-write
        STATUS	mandatory
        DESCRIPTION
		"The number of Severely Errored Framing Seconds which must be received
		prior to the generation of a Threshold Crossing Alert."
        DEFVAL	{ 0 }
        ::= { wfDsx3DayThrAlrtEntry 5 }

    wfDsx3DayThrAlrtUASs OBJECT-TYPE
        SYNTAX	Gauge
        ACCESS	read-write
        STATUS	mandatory
        DESCRIPTION
		"The number of Unavailable Seconds which must be received
		prior to the generation of a Threshold Crossing Alert."
        DEFVAL	{ 10 }
        ::= { wfDsx3DayThrAlrtEntry 6 }

    wfDsx3DayThrAlrtLCVs OBJECT-TYPE
        SYNTAX	Gauge
        ACCESS	read-write
        STATUS	mandatory
        DESCRIPTION
		"The number of Line Coding Violations which must be received
		prior to the generation of a Threshold Crossing Alert."
        DEFVAL	{ 3865 }
        ::= { wfDsx3DayThrAlrtEntry 7 }

    wfDsx3DayThrAlrtPCVs OBJECT-TYPE
        SYNTAX	Gauge
        ACCESS	read-write
        STATUS	mandatory
        DESCRIPTION
		"The number of P-bit Coding Violations which must be received
		prior to the generation of a Threshold Crossing Alert."
        DEFVAL	{ 3820 }
        ::= { wfDsx3DayThrAlrtEntry 8 }

    wfDsx3DayThrAlrtLESs OBJECT-TYPE
        SYNTAX	Gauge
        ACCESS	read-write
        STATUS	mandatory
        DESCRIPTION
		"The number of Line Errored Seconds which must be received
		prior to the generation of a Threshold Crossing Alert."
        DEFVAL	{ 250 }
        ::= { wfDsx3DayThrAlrtEntry 9 }

    wfDsx3DayThrAlrtCCVs OBJECT-TYPE
        SYNTAX	Gauge
        ACCESS	read-write
        STATUS	mandatory
        DESCRIPTION
		"The number of C-bit Coding Violations which must be received
		prior to the generation of a Threshold Crossing Alert."
        DEFVAL	{ 3820 }
        ::= { wfDsx3DayThrAlrtEntry 10 }

    wfDsx3DayThrAlrtCESs OBJECT-TYPE
        SYNTAX	Gauge
        ACCESS	read-write
        STATUS	mandatory
        DESCRIPTION
		"The number of C-bit Errored Seconds which must be received
		prior to the generation of a Threshold Crossing Alert."
        DEFVAL	{ 250 }
        ::= { wfDsx3DayThrAlrtEntry 11 }

    wfDsx3DayThrAlrtCSESs OBJECT-TYPE
        SYNTAX	Gauge
        ACCESS	read-write
        STATUS	mandatory
        DESCRIPTION
		"The number of C-bit Severely Errored Seconds which must be received
		prior to the generation of a Threshold Crossing Alert."
        DEFVAL	{ 0 }
        ::= { wfDsx3DayThrAlrtEntry 12 }

    wfDsx3DayThrAlrtSASs OBJECT-TYPE
        SYNTAX	Gauge
        ACCESS	read-write
        STATUS	mandatory
        DESCRIPTION
		"The number of SEF/AIS Seconds which must be received
		prior to the generation of a Threshold Crossing Alert."
        DEFVAL	{ 8 }
        ::= { wfDsx3DayThrAlrtEntry 13 }

    wfDsx3DayThrAlrtAISSs OBJECT-TYPE
        SYNTAX	Gauge
        ACCESS	read-write
        STATUS	mandatory
        DESCRIPTION
		"The number of AIS defect Seconds which must be received
		prior to the generation of a Threshold Crossing Alert."
        DEFVAL	{ 0 }
        ::= { wfDsx3DayThrAlrtEntry 14 }

    wfDsx3DayThrAlrtFCs OBJECT-TYPE
        SYNTAX	Gauge
        ACCESS	read-write
        STATUS	mandatory
        DESCRIPTION
		"The number of Path Failure Counts which must be received
		prior to the generation of a Threshold Crossing Alert."
        DEFVAL	{ 0 }
        ::= { wfDsx3DayThrAlrtEntry 15 }




    wfDsx3FarEndDayThrAlrtTable OBJECT-TYPE
        SYNTAX	SEQUENCE OF WfDsx3FarEndDayThrAlrtEntry
        ACCESS	not-accessible
        STATUS	mandatory
        DESCRIPTION
		"Current Far End Day statistics Alarm Threshold Crossing table."
        ::= { wfDsx3Group 21 }

    wfDsx3FarEndDayThrAlrtEntry OBJECT-TYPE
        SYNTAX	WfDsx3FarEndDayThrAlrtEntry
        ACCESS	not-accessible
        STATUS	mandatory
        DESCRIPTION
		"An entry in the Dsx3 ThrAlrt table"
        INDEX	{ wfDsx3FarEndDayThrAlrtIndex }
        ::= { wfDsx3FarEndDayThrAlrtTable 1 }

    WfDsx3FarEndDayThrAlrtEntry ::= SEQUENCE {
    	    wfDsx3FarEndDayThrAlrtDelete
    		INTEGER,
    	    wfDsx3FarEndDayThrAlrtIndex
    		INTEGER,
    	    wfDsx3FarEndDayThrAlrtCESs
    		Gauge,
    	    wfDsx3FarEndDayThrAlrtCSESs
    		Gauge,
    	    wfDsx3FarEndDayThrAlrtCCVs
    		Gauge,
    	    wfDsx3FarEndDayThrAlrtUASs
    		Gauge,
    	    wfDsx3FarEndDayThrAlrtSASs
    		Gauge,
    	    wfDsx3FarEndDayThrAlrtFCs
    		Gauge
        }

    wfDsx3FarEndDayThrAlrtDelete OBJECT-TYPE
        SYNTAX	INTEGER {
    		    created(1),
    		    deleted(2)
    		}
        ACCESS	read-write
        STATUS	mandatory
        DESCRIPTION
                "Create/Delete parameter"
        DEFVAL	{ created }
        ::= { wfDsx3FarEndDayThrAlrtEntry 1 }

    wfDsx3FarEndDayThrAlrtIndex OBJECT-TYPE
        SYNTAX	INTEGER
        ACCESS	read-only
        STATUS	mandatory
        DESCRIPTION
                "The instance ID that identifies the port."
        ::= { wfDsx3FarEndDayThrAlrtEntry 2 }

    wfDsx3FarEndDayThrAlrtCESs OBJECT-TYPE
        SYNTAX	Gauge
        ACCESS	read-write
        STATUS	mandatory
        DESCRIPTION
		"The number of C-bit Errored Seconds which must be received
		prior to the generation of a Threshold Crossing Alert."
        DEFVAL	{ 250 }
        ::= { wfDsx3FarEndDayThrAlrtEntry 3 }

    wfDsx3FarEndDayThrAlrtCSESs OBJECT-TYPE
        SYNTAX	Gauge
        ACCESS	read-write
        STATUS	mandatory
        DESCRIPTION
		"The number of C-bit Severely Errored Seconds which must be received
		prior to the generation of a Threshold Crossing Alert."
        DEFVAL	{ 0 }
        ::= { wfDsx3FarEndDayThrAlrtEntry 4 }

    wfDsx3FarEndDayThrAlrtCCVs OBJECT-TYPE
        SYNTAX	Gauge
        ACCESS	read-write
        STATUS	mandatory
        DESCRIPTION
		"The number of C-bit Coding Violations which must be received
		prior to the generation of a Threshold Crossing Alert."
        DEFVAL	{ 3820 }
        ::= { wfDsx3FarEndDayThrAlrtEntry 5 }

    wfDsx3FarEndDayThrAlrtUASs OBJECT-TYPE
        SYNTAX	Gauge
        ACCESS	read-write
        STATUS	mandatory
        DESCRIPTION
		"The number of Unavailable Seconds which must be received
		prior to the generation of a Threshold Crossing Alert."
        DEFVAL	{ 10 }
        ::= { wfDsx3FarEndDayThrAlrtEntry 6 }

    wfDsx3FarEndDayThrAlrtSASs OBJECT-TYPE
        SYNTAX	Gauge
        ACCESS	read-write
        STATUS	mandatory
        DESCRIPTION
		"The number of SEF/AIS Seconds which must be received
		prior to the generation of a Threshold Crossing Alert."
        DEFVAL	{ 8 }
        ::= { wfDsx3FarEndDayThrAlrtEntry 7 }

    wfDsx3FarEndDayThrAlrtFCs OBJECT-TYPE
        SYNTAX	Gauge
        ACCESS	read-write
        STATUS	mandatory
        DESCRIPTION
		"The number of Path Failure Counts which must be received
		prior to the generation of a Threshold Crossing Alert."
        DEFVAL	{ 0 }
        ::= { wfDsx3FarEndDayThrAlrtEntry 8 }




    END  -- Wellfleet-DSX3-MIB
