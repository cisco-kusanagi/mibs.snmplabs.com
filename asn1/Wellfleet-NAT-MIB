Wellfleet-NAT-MIB DEFINITIONS ::= BEGIN

--

    IMPORTS

      IpAddress, Counter, Gauge
        FROM RFC1155-SMI
      OBJECT-TYPE
        FROM RFC-1212
      DisplayString
        FROM RFC1213-MIB
      wfNatGroup
        FROM Wellfleet-COMMON-MIB;




    wfNatBase	OBJECT IDENTIFIER ::= { wfNatGroup 1 }

    wfNatBaseDelete OBJECT-TYPE
        SYNTAX	INTEGER {
    		    created(1),
    		    deleted(2)
    		}
        ACCESS	read-write
        STATUS	mandatory
        DESCRIPTION
                "'This value determines whether NAT is configured'"
        DEFVAL	{ created }
        ::= { wfNatBase 1 }

    wfNatBaseDisable OBJECT-TYPE
        SYNTAX	INTEGER {
    		    enabled(1),
    		    disabled(2)
    		}
        ACCESS	read-write
        STATUS	mandatory
        DESCRIPTION
                "'The administrative status of NAT in the router.  The
                value 'enabled' denotes that the NAT Process is active
                on at least one interface; 'disabled' disables it on
                all interfaces.'"
        DEFVAL	{ enabled }
        ::= { wfNatBase 2 }

    wfNatBaseState OBJECT-TYPE
        SYNTAX	INTEGER {
    		    up(1),
    		    init(2),
    		    down(3),
                    not-present (4)
    		}
        ACCESS	read-only
        STATUS	mandatory
        DESCRIPTION
                "'The state of NAT'"
        DEFVAL  { not-present }
        ::= { wfNatBase 3 }

    wfNatBaseSoloistSlotMask OBJECT-TYPE
        SYNTAX	Gauge
        ACCESS	read-write
        STATUS	mandatory
        DESCRIPTION
                "Slot mask for which slots the soloist gate is
                eligible to run on.  The MSBit represents slot
                1, the next most significant bit represents slot 2,
                and so on...  Slots can be 1-14.
                Default is all slots."
        DEFVAL	{ 4294705152 }
        ::= { wfNatBase 4 }

    wfNatBaseSoloistSlot OBJECT-TYPE
        SYNTAX	INTEGER
        ACCESS	read-only
        STATUS	mandatory
        DESCRIPTION
                "Slot on which NAT soloist gate is running. Slots
                can be 1-14. Default is zero."
        DEFVAL { 0 }
        ::= { wfNatBase 5 }

    wfNatBaseLogMask OBJECT-TYPE
        SYNTAX	INTEGER
        ACCESS	read-write
        STATUS	mandatory
        DESCRIPTION
                "A parameter to specify which NAT log messages should be logged.
                Each bit represents a message as defined below.  A 1 in that
                bit location means to log it and a 0 means not to put that
                log message in the log.  Changing this value will NOT restart
                NAT, but will take effct immediately(if there are any messages
                to be logged.

                bit 31                                bit 0
                +---------------------------------------+
                |                                       |
                +---------------------------------------+


                NAT_DBG_MIB_LOG           	0x00000001
                NAT_DBG_IP_LOG           	0x00000002
                NAT_DBG_FWD_LOG           	0x00000004
                NAT_DBG_MAPPING_LOG           	0x00000008
                NAT_DBG_AGING_LOG           	0x00000010
                NAT_DBG_SYNCH_LOG           	0x00000020

                "
        DEFVAL	{ 0 }
        ::= { wfNatBase 6 }

    wfNatBaseMapTimeout OBJECT-TYPE
        SYNTAX	INTEGER {
                enabled (1),
                disabled (2)
    		}
        ACCESS	read-write
        STATUS	mandatory
        DESCRIPTION
                "This controls whether or not the dynamic mapping table
                 entries are aged out when unused."
        DEFVAL  { enabled }
        ::= { wfNatBase 7 }

    wfNatBaseMapMaxTimeout OBJECT-TYPE
        SYNTAX	INTEGER(0..2147483647)
        ACCESS	read-write
        STATUS	mandatory
        DESCRIPTION
                "The maximum time in seconds before unused NAT mapping
                 table entries are deleted. This timeout or aging does
                 not apply to static mapping entries."
        DEFVAL  { 3600 }
        ::= { wfNatBase 8 }

    wfNatBaseMapDynMapsCount OBJECT-TYPE
        SYNTAX	Gauge
        ACCESS	read-only
        STATUS	mandatory
        DESCRIPTION
                "Number of Dynamic Mappings in the dymanic mapping table"
        DEFVAL  { 0 }
        ::= { wfNatBase 9 }

    wfNatBaseFtpSessionCount OBJECT-TYPE
        SYNTAX	Gauge
        ACCESS	read-only
        STATUS	mandatory
        DESCRIPTION
                "Number of FTP sessions detected on this box translated by NAT"
        DEFVAL  { 0 }
        ::= { wfNatBase 10 }

    wfNatBaseNto1TrTotCount   OBJECT-TYPE
        SYNTAX	Gauge
        ACCESS	read-only
        STATUS	mandatory
        DESCRIPTION
                "Total number of active Nto1 translation counts on the box."
        DEFVAL  { 0 }
        ::= { wfNatBase 11 }

    wfNatBaseSynchronization OBJECT-TYPE
        SYNTAX  INTEGER {
                    enabled(1),
                    disabled(2)
                }
        ACCESS  read-write
        STATUS  mandatory
        DESCRIPTION
                "The administrative status of NAT Synchronization in the router.
		 The value `enabled' denotes that the NAT Synchronization is
		 active and is synchronizing with the peer specified in noraml
		 conditions.; `disabled' disables it on the box and all the peer
		 connections will be teared down.'"
        DEFVAL  { disabled }
        ::= { wfNatBase 12 }

    wfNatBaseSynRouterID OBJECT-TYPE
        SYNTAX  IpAddress
        ACCESS  read-write
        STATUS  mandatory
        DESCRIPTION
                "This represents the Router Identifier for NAT Synchronization
		 Only. This is used to detect the duplicate TCP connection
		 between peers. The value of it can be any integer which is
		 unique between all the NAT Syn peers this router has.
		 An IP Address of one of the router interfaces can be used as
		 the RouterID. Changing the value will result into breaking and
		 reconnecting using new ID with all the peers.'"
        ::= { wfNatBase 13 }

    wfNatBaseSynPort OBJECT-TYPE
        SYNTAX  INTEGER
        ACCESS  read-write
        STATUS  mandatory
        DESCRIPTION
                "This represents the TCP port on which the connection requests
		 from the peers will be accepted. When NAT Synchronization
		 Protocol comes up, it will open a listen connection for this
		 port number. This attribute value has to be the same on all
		 the peers that want to make the TCP connection.'"
        DEFVAL  { 670 }
        ::= { wfNatBase 14 }

    wfNatBaseSynKeepAlvInterval OBJECT-TYPE
        SYNTAX  INTEGER
        ACCESS  read-write
        STATUS  mandatory
        DESCRIPTION
                "Idle session timeout period, in seconds.  If an established
                TCP connection remains inactive for this interval, KEEPALIVE
                messages will be sent to the peer (if the Keepalive Timer is
                non-zero).  Setting the Idle Timer to zero disables the
                keepalive feature."
        DEFVAL  { 120 }
        ::= { wfNatBase 15 }

    wfNatBaseSynKeepAlvTimer OBJECT-TYPE
        SYNTAX  INTEGER
        ACCESS  read-write
        STATUS  mandatory
        DESCRIPTION
                "KEEPALIVE retransmit timeout period, in seconds.  This is
                the interval at which unacknowledged KEEPALIVE messages will
                be retransmitted.  If the Idle Timer is set to zero, this
                timer ignored.  If the Idle Timer is non-zero and this timer
                IS zero, no KEEPALIVEs are sent and the session is terminated
                upon expiration of the Idle Timer."
        DEFVAL  { 3 }
        ::= { wfNatBase 16 }

    wfNatBaseSynKeepAlvRetries OBJECT-TYPE
        SYNTAX  INTEGER
        ACCESS  read-write
        STATUS  mandatory
        DESCRIPTION
                "Number of unacknowledged KEEPALIVE messages retransmitted
                before the TCP session is terminated.  If this count is set
                to zero, only one KEEPALIVE message will be sent."
        DEFVAL  { 5 }
        ::= { wfNatBase 17 }

       wfNatBaseLocalToLocalEnable OBJECT-TYPE
        SYNTAX  INTEGER {
                    enabled(1),
                    disabled(2)
                }
        ACCESS  read-write
        STATUS  mandatory
        DESCRIPTION
                "Allow forwarding of traffic from one local
                 NAT interface to another local NAT interface."
        DEFVAL  { enabled }
        ::= { wfNatBase 18 }                                    

    wfNatBaseInstallUniPrivAddr OBJECT-TYPE
        SYNTAX  INTEGER {
                    enabled(1),
                    disabled(2)
                }
        ACCESS  read-write
        STATUS  mandatory
        DESCRIPTION
                "This MIB was added in BayRS 14.20 to address a
		compatibility issue concerning non-DNS NAT
		translations when upgrading from a pre-14.20
		NAT configuration to a 14.20 or greater version
		of BayRS software.  This MIB should remain enabled.
		Disabling this MIB will cause Uni-directional NAT
		to no longer function correctly on the router."
        DEFVAL  { enabled }
        ::= { wfNatBase 19 }


    wfNatAddrRangeTable OBJECT-TYPE
        SYNTAX	SEQUENCE OF WfNatAddrRangeEntry
        ACCESS	not-accessible
        STATUS	mandatory
        DESCRIPTION
                "Table of address ranges that have been designated
                as the set of external apparent addresses that are
                to be mapped in place of internal actual addresses.
                These addresses would be the non-public reigistered
                addresses."
        ::= { wfNatGroup 2 }

    wfNatAddrRangeEntry OBJECT-TYPE
        SYNTAX	WfNatAddrRangeEntry
        ACCESS	not-accessible
        STATUS	mandatory
        DESCRIPTION
                "'Information describing each of the available address
                ranges.'"
        INDEX	{ wfNatAddrRangeAddress,
                  wfNatAddrRangePrefixLen }
        ::= { wfNatAddrRangeTable 1 }

    WfNatAddrRangeEntry ::= SEQUENCE {
    	    wfNatAddrRangeDelete
    		INTEGER,
    	    wfNatAddrRangeDisable
    		INTEGER,
            wfNatAddrRangeAddress
                IpAddress,
            wfNatAddrRangePrefixLen
                INTEGER
        }

    wfNatAddrRangeDelete OBJECT-TYPE
        SYNTAX	INTEGER {
    		    created(1),
    		    deleted(2)
    		}
        ACCESS	read-write
        STATUS	mandatory
        DESCRIPTION
                "'Create/Delete parameter. Default is created.
                Users perform a set operation on this
                object in order to create/delete an address
                range entry.'"
        DEFVAL	{ created }
        ::= { wfNatAddrRangeEntry 1 }

    wfNatAddrRangeDisable OBJECT-TYPE
        SYNTAX	INTEGER {
    		    enabled(1),
    		    disabled(2)
    		}
        ACCESS	read-write
        STATUS	mandatory
        DESCRIPTION
                "'Enable/Disable parameter. Default is enabled.
                Users perform a set operation on this
                object in order to enable/disable an address
                range entry.'"
        DEFVAL	{ enabled }
        ::= { wfNatAddrRangeEntry 2 }

    wfNatAddrRangeAddress OBJECT-TYPE
        SYNTAX	IpAddress
        ACCESS	read-write
        STATUS	mandatory
        DESCRIPTION
                "'The IP beginning address of this range entry."
        ::= { wfNatAddrRangeEntry 3 }

    wfNatAddrRangePrefixLen OBJECT-TYPE
        SYNTAX	INTEGER
        ACCESS	read-write
        STATUS	mandatory
        DESCRIPTION
                "'The IP address mask that in conjunction with the
                start address defines the address range of the entry.'"
        ::= { wfNatAddrRangeEntry 4 }




    wfNatLocalAddrRangeTable OBJECT-TYPE
        SYNTAX	SEQUENCE OF WfNatLocalAddrRangeEntry
        ACCESS	not-accessible
        STATUS	mandatory
        DESCRIPTION
                "Table of address ranges that have been designated
                as the set of local addresses that are to be mapped
                via NAT."
        ::= { wfNatGroup 3 }

    wfNatLocalAddrRangeEntry OBJECT-TYPE
        SYNTAX	WfNatLocalAddrRangeEntry
        ACCESS	not-accessible
        STATUS	mandatory
        DESCRIPTION
                "'Information describing each of the available address
                ranges.'"
        INDEX	{ wfNatLocalAddrRangeAddress,
                  wfNatLocalAddrRangePrefixLen }
        ::= { wfNatLocalAddrRangeTable 1 }

    WfNatLocalAddrRangeEntry ::= SEQUENCE {
    	    wfNatLocalAddrRangeDelete
    		INTEGER,
    	    wfNatLocalAddrRangeDisable
    		INTEGER,
            wfNatLocalAddrRangeAddress
                IpAddress,
            wfNatLocalAddrRangePrefixLen
                INTEGER,
            wfNatLocalAddrRangeNto1Addr
                IpAddress
        }

    wfNatLocalAddrRangeDelete OBJECT-TYPE
        SYNTAX	INTEGER {
    		    created(1),
    		    deleted(2)
    		}
        ACCESS	read-write
        STATUS	mandatory
        DESCRIPTION
                "'Create/Delete parameter. Default is created.
                Users perform a set operation on this
                object in order to create/delete an address
                range entry.'"
        DEFVAL	{ created }
        ::= { wfNatLocalAddrRangeEntry 1 }

    wfNatLocalAddrRangeDisable OBJECT-TYPE
        SYNTAX	INTEGER {
    		    enabled(1),
    		    disabled(2)
    		}
        ACCESS	read-write
        STATUS	mandatory
        DESCRIPTION
                "'Enable/Disable parameter. Default is enabled.
                Users perform a set operation on this
                object in order to enable/disable an address
                range entry.'"
        DEFVAL	{ enabled }
        ::= { wfNatLocalAddrRangeEntry 2 }

    wfNatLocalAddrRangeAddress OBJECT-TYPE
        SYNTAX	IpAddress
        ACCESS	read-write
        STATUS	mandatory
        DESCRIPTION
                "'The IP beginning address of this range entry."
        ::= { wfNatLocalAddrRangeEntry 3 }

    wfNatLocalAddrRangePrefixLen OBJECT-TYPE
        SYNTAX	INTEGER
        ACCESS	read-write
        STATUS	mandatory
        DESCRIPTION
                "'The IP address mask that in conjunction with the
                start address defines the address range of the entry.'"
        ::= { wfNatLocalAddrRangeEntry 4 }

    wfNatLocalAddrRangeNto1Addr OBJECT-TYPE
        SYNTAX	IpAddress
        ACCESS	read-write
        STATUS	mandatory
        DESCRIPTION
                "Nto1 translation address used for this range."
        DEFVAL	{ 0 }
        ::= { wfNatLocalAddrRangeEntry 5 }




    wfNatStaticMapTable OBJECT-TYPE
        SYNTAX	SEQUENCE OF WfNatStaticMapEntry
        ACCESS	not-accessible
        STATUS	mandatory
        DESCRIPTION
                "'This table creates instances of pre-defined
                NAT mappings.'"
        ::= { wfNatGroup 4 }

    wfNatStaticMapEntry OBJECT-TYPE
        SYNTAX	WfNatStaticMapEntry
        ACCESS	not-accessible
        STATUS	mandatory
        DESCRIPTION
                "'A single local-to-global address mapping.'"
        INDEX	{ wfNatStaticMapLocalAddress,
    		  wfNatStaticMapGlobalAddress,
                  wfNatStaticMapProtocol,
                  wfNatStaticMapLocalPort,
                  wfNatStaticMapGlobalPort }
        ::= { wfNatStaticMapTable 1 }

    WfNatStaticMapEntry ::= SEQUENCE {
            wfNatStaticMapDelete
                INTEGER,
            wfNatStaticMapDisable
                INTEGER,
    	    wfNatStaticMapLocalAddress
    		IpAddress,
    	    wfNatStaticMapGlobalAddress
    		IpAddress,
            wfNatStaticMapProtocol
                INTEGER,
            wfNatStaticMapLocalPort
                INTEGER,
            wfNatStaticMapGlobalPort
                INTEGER
        }

    wfNatStaticMapDelete OBJECT-TYPE
        SYNTAX	INTEGER {
    		    created(1),
    		    deleted(2)
    		}
        ACCESS	read-write
        STATUS	mandatory
        DESCRIPTION
                "'Create/Delete parameter. Default is created.
                Users perform a set operation on this
                object in order to create/delete a static
                address mapping entry.'"
        DEFVAL	{ created }
        ::= { wfNatStaticMapEntry 1 }

    wfNatStaticMapDisable OBJECT-TYPE
        SYNTAX	INTEGER {
    		    enabled(1),
    		    disabled(2)
    		}
        ACCESS	read-write
        STATUS	mandatory
        DESCRIPTION
                "'Enable/Disable parameter. Default is enabled.
                Users perform a set operation on this
                object in order to enable/disable a static
                address mapping entry.'"
        DEFVAL	{ enabled }
		::= { wfNatStaticMapEntry 2 }

    wfNatStaticMapLocalAddress OBJECT-TYPE
        SYNTAX	IpAddress
        ACCESS	read-write
        STATUS	mandatory
        DESCRIPTION
                "'The local or private address of the mapping pair.'"
        ::= { wfNatStaticMapEntry 3 }

    wfNatStaticMapGlobalAddress OBJECT-TYPE
        SYNTAX	IpAddress
        ACCESS	read-write
        STATUS	mandatory
        DESCRIPTION
                "'The global or external address of the mapping pair.'"
        ::= { wfNatStaticMapEntry 4 }

    wfNatStaticMapProtocol OBJECT-TYPE
        SYNTAX	INTEGER
        ACCESS	read-write
        STATUS	mandatory
        DESCRIPTION
                "'The IP protocol of the mapping pair.'"
        ::= { wfNatStaticMapEntry 5 }

    wfNatStaticMapLocalPort OBJECT-TYPE
        SYNTAX	INTEGER
        ACCESS	read-write
        STATUS	mandatory
        DESCRIPTION
                "'The local UDP or TCP port of the mapping pair.
                  This will only be relevent if the protocol is
                  either UDP or TCP.'"
        ::= { wfNatStaticMapEntry 6 }

    wfNatStaticMapGlobalPort OBJECT-TYPE
        SYNTAX	INTEGER
        ACCESS	read-write
        STATUS	mandatory
        DESCRIPTION
                "'The global UDP or TCP port of the mapping pair.
                  This will only be relevent if the protocol is
                  either UDP or TCP.'"
        ::= { wfNatStaticMapEntry 7 }




    wfNatMapTable OBJECT-TYPE
        SYNTAX  SEQUENCE OF WfNatMapEntry
        ACCESS	not-accessible
        STATUS	mandatory
        DESCRIPTION
                "'This table defines the current set of address
                mappings that are in effect.'"
        ::= { wfNatGroup 5 }

    wfNatMapEntry OBJECT-TYPE
        SYNTAX	WfNatMapEntry
        ACCESS	not-accessible
        STATUS	mandatory
        DESCRIPTION
                ""
        INDEX	{ wfNatMapLocalAddress,
    		  wfNatMapGlobalAddress,
                  wfNatMapProtocol,
                  wfNatMapLocalPort,
                  wfNatMapGlobalPort }
        ::= { wfNatMapTable 1 }

    WfNatMapEntry ::= SEQUENCE {
            wfNatMapLocalAddress
                IpAddress,
            wfNatMapGlobalAddress
                IpAddress,
            wfNatMapProtocol
                INTEGER,
            wfNatMapLocalPort
                INTEGER,
            wfNatMapGlobalPort
                INTEGER,
            wfNatMapTxCount
                Counter,
            wfNatMapRxCount
                Counter,
            wfNatMapTimeout
                Counter,
            wfNatMapMode
		INTEGER
        }

    wfNatMapLocalAddress OBJECT-TYPE
        SYNTAX	IpAddress
        ACCESS	read-only
        STATUS	mandatory
        DESCRIPTION
                "'The local address of the mapping pair.'"
        ::= { wfNatMapEntry 1 }

    wfNatMapGlobalAddress OBJECT-TYPE
        SYNTAX	IpAddress
        ACCESS	read-only
        STATUS	mandatory
        DESCRIPTION
                "'The global address of the mapping pair.'"
        ::= { wfNatMapEntry 2 }

    wfNatMapProtocol OBJECT-TYPE
        SYNTAX	INTEGER
        ACCESS	read-only
        STATUS	mandatory
        DESCRIPTION
                "'The IP protocol of the mapping pair.'"
        ::= { wfNatMapEntry 3 }

    wfNatMapLocalPort OBJECT-TYPE
        SYNTAX	INTEGER
        ACCESS	read-only
        STATUS	mandatory
        DESCRIPTION
                "'When the mapping is for a TCP connection, this
                denotes the TCP port number on the local side.'"
        ::= { wfNatMapEntry 4 }

    wfNatMapGlobalPort OBJECT-TYPE
        SYNTAX	INTEGER
        ACCESS	read-only
        STATUS	mandatory
        DESCRIPTION
                "'When the mapping is for a TCP connection, this
                denotes the TCP port number on the global side.'"
        ::= { wfNatMapEntry 5 }

    wfNatMapTxCount OBJECT-TYPE
        SYNTAX	Counter
        ACCESS	read-only
        STATUS	mandatory
        DESCRIPTION
                "'Number of packets for this mapping pair that have
                been mapped from the local to the global network.'"
        ::= { wfNatMapEntry 6 }

    wfNatMapRxCount OBJECT-TYPE
        SYNTAX	Counter
        ACCESS	read-only
        STATUS	mandatory
        DESCRIPTION
                "'Number of packets for this mapping pair that have
                been mapped from the global to the local network.'"
        ::= { wfNatMapEntry 7 }

    wfNatMapTimeout OBJECT-TYPE
        SYNTAX	Counter
        ACCESS	read-only
        STATUS	mandatory
        DESCRIPTION
                "'The time in seconds since this mapping entry was
                  last used. This is used to age out mapping entries.'"
        ::= { wfNatMapEntry 8 }
    wfNatMapMode OBJECT-TYPE
        SYNTAX	INTEGER
        ACCESS	read-only
        STATUS	mandatory
        DESCRIPTION
                "This is the bit mask representing the type of this
		mapping. Each bit specifies the type as follows:

		The mapping could be only ONE of the foolowing three...
		0x01000000 - This mapping is origianted on this router,
			     i.e. this NAT router performed the translation
		0x02000000 - This mapping is learned from the peer, i.e.
			     this translation was learned from the peer using
			     NAT Synchronization feature.
		0x04000000 - This mapping is owned, i.e. it was originally
			     learned from peer, but this router received traffic
		 	     which used this mapping.

		...and only ONE of the following three.

		0x00000010 - This mapping is the STATIC mapping.
		0x00000020 - This mapping is Dynamic(1 to 1) mapping.
		0x00000040 - This mapping is N to 1 mapping."
        DEFVAL	{ 0 }
        ::= { wfNatMapEntry 9 }




    wfNatIfTable OBJECT-TYPE
        SYNTAX	SEQUENCE OF WfNatIfEntry
        ACCESS	not-accessible
        STATUS	mandatory
        DESCRIPTION
                "'The set of interface that are participating
                in the NAT protocol.'"
        ::= { wfNatGroup 6 }

    wfNatIfEntry OBJECT-TYPE
        SYNTAX	WfNatIfEntry
        ACCESS	not-accessible
        STATUS	mandatory
        DESCRIPTION
                "'An single instance of a NAT interface entry.'"
        INDEX	{ wfNatIfIpAddress,
    		  wfNatIfCircuit }
        ::= { wfNatIfTable 1 }

    WfNatIfEntry ::= SEQUENCE {
    	    wfNatIfDelete
    		INTEGER,
    	    wfNatIfDisable
    		INTEGER,
    	    wfNatIfIpAddress
    		IpAddress,
    	    wfNatIfCircuit
    		INTEGER,
            wfNatIfType
                INTEGER,
            wfNatIfState
                INTEGER,
            wfNatIfTxCount
                Counter,
            wfNatIfRxCount
                Counter,
            wfNatIfPktDropCount
                Counter,
            wfNatIfDomain
               DisplayString
        }

    wfNatIfDelete OBJECT-TYPE
        SYNTAX	INTEGER {
    		    created(1),
    		    deleted(2)
    		}
        ACCESS	read-write
        STATUS	mandatory
        DESCRIPTION
                "This variable determines in a NAT Interface has been
                configured on the router."
        DEFVAL	{ created }
        ::= { wfNatIfEntry 1 }

    wfNatIfDisable OBJECT-TYPE
        SYNTAX	INTEGER {
    		    enabled(1),
    		    disabled(2)
    		}
        ACCESS	read-write
        STATUS	mandatory
        DESCRIPTION
                "'The NAT interface's administrative status.  The value
                'enabled' denotes that NAT has been configured
                on the interface. The value 'disabled' denotes that
                the interface is not running NAT.'"
        DEFVAL	{ enabled }
        ::= { wfNatIfEntry 2 }

    wfNatIfIpAddress OBJECT-TYPE
        SYNTAX	IpAddress
        ACCESS	read-only
        STATUS	mandatory
        DESCRIPTION
                "The IP address of this NAT interface."
        ::= { wfNatIfEntry 3 }

    wfNatIfCircuit OBJECT-TYPE
        SYNTAX	INTEGER
        ACCESS	read-write
        STATUS	mandatory
        DESCRIPTION
                "The circuit number of this interface."
        ::= { wfNatIfEntry 4 }

    wfNatIfType OBJECT-TYPE
        SYNTAX	INTEGER {
                    uniDirInbound(1),
                    uniDirOutbound(2),
                    biDirectional(3)
                }
        ACCESS	read-write
        STATUS	mandatory
        DESCRIPTION
                "Denotes  the type of NAT interface being defined."
        DEFVAL{ uniDirInbound }
        ::= { wfNatIfEntry 5 }

    wfNatIfState OBJECT-TYPE
        SYNTAX	INTEGER {
    		    up(1),
    		    down(2),
    		    init(3)
    		}
        ACCESS	read-only
        STATUS	mandatory
        DESCRIPTION
                "'The state of NAT on this interface'"
        DEFVAL	{ down }
        ::= { wfNatIfEntry 6 }

    wfNatIfTxCount OBJECT-TYPE
        SYNTAX	Counter
        ACCESS	read-only
        STATUS	mandatory
        DESCRIPTION
                "Number of packets mapped over this interface from
                the local to the global network.'"
        ::= { wfNatIfEntry 7 }

    wfNatIfRxCount OBJECT-TYPE
        SYNTAX	Counter
        ACCESS	read-only
        STATUS	mandatory
        DESCRIPTION
                "Number of packets mapped over this interface from
                the global to the local network.'"
        ::= { wfNatIfEntry 8 }

    wfNatIfPktDropCount OBJECT-TYPE
        SYNTAX	Counter
        ACCESS	read-only
        STATUS	mandatory
        DESCRIPTION
                "Number of packets dropped on this interface"
        ::= { wfNatIfEntry 9 }
    wfNatIfDomain OBJECT-TYPE
        SYNTAX  DisplayString
        ACCESS  read-write
        STATUS  mandatory
        DESCRIPTION
                "When wfNatIfType is set to biDirectional, specifies
		 the Address Domain Name that this interface is
                 connected to, otherwise set to null."
        ::= { wfNatIfEntry 10 }



    wfNatSynPeerTable OBJECT-TYPE
        SYNTAX  SEQUENCE OF WfNatSynPeerEntry
        ACCESS  not-accessible
        STATUS  mandatory
        DESCRIPTION
                "The Nat Synchronization Peer table contains configuration
		and statistical information regarding this router's NAT peers"
        ::= { wfNatGroup 7 }

    wfNatSynPeerEntry OBJECT-TYPE
        SYNTAX  WfNatSynPeerEntry
        ACCESS  not-accessible
        STATUS  mandatory
        DESCRIPTION
                "An entry in the NAT Synchronization-Peer table"
        INDEX   { wfNatSynPeerRouterID }
        ::= { wfNatSynPeerTable 1 }

    WfNatSynPeerEntry ::= SEQUENCE {
            wfNatSynPeerDelete
                INTEGER,
            wfNatSynPeerDisable
                INTEGER,
            wfNatSynPeerState
                INTEGER,
            wfNatSynPeerConnType
                INTEGER,
            wfNatSynPeerRouterID
                IpAddress,
            wfNatSynPeerAddress
                IpAddress,
            wfNatSynPeerTransSent
                INTEGER,
            wfNatSynPeerTransRecd
                INTEGER
        }

    wfNatSynPeerDelete OBJECT-TYPE
        SYNTAX  INTEGER {
                    created(1),
                    deleted(2)
                }
        ACCESS  read-write
        STATUS  mandatory
        DESCRIPTION
                "Create/Delete: if set to delete,
		this instance of the peer entry is deleted,
		which results into the termination of peer connection."
        DEFVAL  { created }
        ::= { wfNatSynPeerEntry 1 }

    wfNatSynPeerDisable OBJECT-TYPE
        SYNTAX  INTEGER {
                    enabled(1),
                    disabled(2)
                }
        ACCESS  read-write
        STATUS  mandatory
        DESCRIPTION
                "Enable/Disable: controls whether the peer connection
		is enabled or disabled, disabling this results into
		the termination of TCP connection"
        DEFVAL  { enabled }
        ::= { wfNatSynPeerEntry 2 }

    wfNatSynPeerState OBJECT-TYPE
        SYNTAX  INTEGER {
                    not-present(1),
                    init(2),
                    established(3),
                    down(4)
                }
        ACCESS  read-only
        STATUS  mandatory
        DESCRIPTION
                "the administrative state of the peer connection"
        DEFVAL  { not-present }
        ::= { wfNatSynPeerEntry 3 }

    wfNatSynPeerConnType OBJECT-TYPE
        SYNTAX  INTEGER {
                    active(1),
                    passive(2)
        }
        ACCESS  read-only
        STATUS  mandatory
        DESCRIPTION
                "the type of the TCP connection with the peer,
		whether this connection is accepted from the peer or it was
		actively initialted by this router to the peer."
        ::= { wfNatSynPeerEntry 4}

    wfNatSynPeerRouterID OBJECT-TYPE
        SYNTAX  IpAddress
        ACCESS  read-only
        STATUS  mandatory
        DESCRIPTION
                "A unique non-zero RouterID of the peer that
		this router is expecting from the connection
                This is also the instance of the Peer Entry."
        ::= { wfNatSynPeerEntry 5}

    wfNatSynPeerAddress OBJECT-TYPE
        SYNTAX  IpAddress
        ACCESS  read-write
        STATUS  mandatory
        DESCRIPTION
                "the IP Address of the peer,
		where the router will send a connect request"
        ::= { wfNatSynPeerEntry 6}

    wfNatSynPeerTransSent OBJECT-TYPE
        SYNTAX  INTEGER
        ACCESS  read-only
        STATUS  mandatory
        DESCRIPTION
                "The number of translations sent to this peer by the router"
        ::= { wfNatSynPeerEntry 7}

    wfNatSynPeerTransRecd OBJECT-TYPE
        SYNTAX  INTEGER
        ACCESS  read-only
        STATUS  mandatory
        DESCRIPTION
                "The number of translations received from this peer by the router"
        ::= { wfNatSynPeerEntry 8}




    wfNatAddressRangeTable OBJECT-TYPE
        SYNTAX  SEQUENCE OF WfNatAddressRangeEntry
        ACCESS  not-accessible
        STATUS  mandatory
        DESCRIPTION
                "Table of address ranges. This table was replaced by
		wfNatSrcAddressFilterTable and wfNatTranslationPoolTable"
        ::= { wfNatGroup 8 }

    wfNatAddressRangeEntry OBJECT-TYPE
        SYNTAX  WfNatAddressRangeEntry
        ACCESS  not-accessible
        STATUS  mandatory
        DESCRIPTION
                "Information describing each of the available address ranges."
        INDEX   { wfNatAddressRangeAddress,
                  wfNatAddressRangePrefixLen,
                   wfNatAddressRangeIndex}
        ::= { wfNatAddressRangeTable 1 }

    WfNatAddressRangeEntry ::= SEQUENCE {
            wfNatAddressRangeDelete
                INTEGER,
            wfNatAddressRangeDisable
                INTEGER,
            wfNatAddressRangeAddress
                IpAddress,
            wfNatAddressRangePrefixLen
                INTEGER,
            wfNatAddressRangeIndex
                INTEGER,
            wfNatAddressRangeNto1Addr
                IpAddress,
            wfNatAddressRangeType
                INTEGER,
            wfNatAddressRangeDomain
               DisplayString,
            wfNatAddressRangeTransPool
               INTEGER,
            wfNatAddressRangeStaticNextHop
               IpAddress,
            wfNatAddressRangeUnnumCct
               INTEGER
        }


    wfNatAddressRangeDelete OBJECT-TYPE
        SYNTAX  INTEGER {
                created(1),
                deleted(2)
            }
        ACCESS  read-write
        STATUS  mandatory
        DESCRIPTION
                "Create/Delete parameter. Default is created. Users perform
		 a set operation on this object in order to create/delete
		 an address range entry."
        DEFVAL  { created }
        ::= { wfNatAddressRangeEntry 1 }

    wfNatAddressRangeDisable OBJECT-TYPE
        SYNTAX  INTEGER {
                enabled(1),
                disabled(2)
            }
        ACCESS  read-write
        STATUS  mandatory
        DESCRIPTION
                "Enable/Disable parameter. Default is enabled. Users perform
		 a set operation on this object in order to enable/disable
		 an address range entry."
        DEFVAL  { enabled }
        ::= { wfNatAddressRangeEntry 2 }

    wfNatAddressRangeAddress OBJECT-TYPE
        SYNTAX  IpAddress
        ACCESS  read-only
        STATUS  mandatory
        DESCRIPTION
                "The IP beginning address of this range entry."
        ::= { wfNatAddressRangeEntry 3 }

    wfNatAddressRangePrefixLen OBJECT-TYPE
        SYNTAX  INTEGER (1 .. 32)
        ACCESS  read-only
        STATUS  mandatory
        DESCRIPTION
                 "The number of contiguous bits set in the IP address mask
		  which are used to define the address range of the entry."
        ::= { wfNatAddressRangeEntry 4 }

    wfNatAddressRangeIndex OBJECT-TYPE
        SYNTAX  INTEGER
        ACCESS  read-only
        STATUS  mandatory
        DESCRIPTION
                "A unique value for this entry in wfNatAddressRangeTable."
        ::= { wfNatAddressRangeEntry 5 }

    wfNatAddressRangeNto1Addr OBJECT-TYPE
        SYNTAX  IpAddress
        ACCESS  read-write
        STATUS  mandatory
        DESCRIPTION
                "When wfNatAddressRangeType is set to srcAddrFilter,
		 specifies the N-to-1 translation address used for
                 this range, otherwise set to zero."
        DEFVAL  { 0 }
        ::= { wfNatAddressRangeEntry 6 }

    wfNatAddressRangeType OBJECT-TYPE
        SYNTAX  INTEGER {
                    sourceAddrFilter(1),
                    translationPool(2),
                    domainSrcAddrFilter(3),
                    domainTransPool(4)
                }
        ACCESS  read-write
        STATUS  mandatory
        DESCRIPTION
                "Denotes the type of address range being defined.
	sourceAddrFilter: 	a range of IP addresses used to detect packets
		which need traditional NAT forwarding.
  	translationPool: 	for traditional NAT forwarding, a range of
		IP addresses from which translation addresses are picked.
	domainSrcAddrFilter: 	a range of IP addresses used to detect domain
		specific packets which need domain specific NAT forwarding.
    	domainTransPool:	for domain specific NAT forwarding, a range of
		IP addresses from which domain specific translation addresses
		are picked."
        DEFVAL{ sourceAddrFilter }
        ::= { wfNatAddressRangeEntry 7 }

    wfNatAddressRangeDomain OBJECT-TYPE
        SYNTAX  DisplayString
        ACCESS  read-write
        STATUS  mandatory
        DESCRIPTION
                "When wfNatAddressRangeType is set to  domainSrcAddrFilter or
		 domainTransPool, specifies the Address Domain Name that this
		 address range is valid for, otherwise set to null."
        ::= { wfNatAddressRangeEntry 8 }

    wfNatAddressRangeTransPool OBJECT-TYPE
        SYNTAX  INTEGER {
                    inbound(1),
                    outbound(2)
                }
        ACCESS  read-write
        STATUS  mandatory
        DESCRIPTION
                "This attribute is only valid for the wfNatAddressRangeType as
		 domainSrcAddrFilter(3). The value of this attribute decides
		 where to get the translation address for this range from.
		 This could be either the translation Pool defined for the
		 inbound domain or the outbound domain for the packet in
		 question."
        DEFVAL{ outbound }
        ::= { wfNatAddressRangeEntry 9 }

   wfNatAddressRangeStaticNextHop OBJECT-TYPE
        SYNTAX  IpAddress
        ACCESS  read-write
        STATUS  mandatory
        DESCRIPTION
                "The IP address of the next hop of this range entry."
        DEFVAL{ 0 }
        ::= { wfNatAddressRangeEntry 10 }

   wfNatAddressRangeUnnumCct OBJECT-TYPE
        SYNTAX  INTEGER
        ACCESS  read-write
        STATUS  mandatory
        DESCRIPTION
                "This Nat Address range over the unnumbered interface."
        DEFVAL{ 0 }
        ::= { wfNatAddressRangeEntry 11 }

   wfNatStaticMappingTable OBJECT-TYPE
        SYNTAX  SEQUENCE OF WfNatStaticMappingEntry
        ACCESS  not-accessible
        STATUS  mandatory
        DESCRIPTION
                "`This table creates instances of pre-defined NAT translations.'"
        ::= { wfNatGroup 9 }

    wfNatStaticMappingEntry OBJECT-TYPE
        SYNTAX  WfNatStaticMappingEntry
        ACCESS  not-accessible
        STATUS  mandatory
        DESCRIPTION
                "A single original source address to translated address
		 translation."
        INDEX   {  wfNatStaticMappingTransAddress,
                  wfNatStaticMappingProtocol,
                  wfNatStaticMappingTransPort }
        ::= { wfNatStaticMappingTable 1 }

    WfNatStaticMappingEntry ::= SEQUENCE {
            wfNatStaticMappingDelete
                INTEGER,
            wfNatStaticMappingDisable
                INTEGER,
            wfNatStaticMappingOrigAddress
                IpAddress,
            wfNatStaticMappingTransAddress
                IpAddress,
            wfNatStaticMappingProtocol
                INTEGER,
            wfNatStaticMappingOrigPort
                INTEGER,
            wfNatStaticMappingTransPort
                INTEGER,
            wfNatStaticMappingInDomain
	        DisplayString,
            wfNatStaticMappingOutDomain
	        DisplayString,
            wfNatStaticMappingStaticNextHop
                IpAddress,
            wfNatStaticMappingUnnumCct
                INTEGER
        }



    wfNatStaticMappingDelete OBJECT-TYPE
        SYNTAX  INTEGER {
                created(1),
                deleted(2)
            }
        ACCESS  read-write
        STATUS  mandatory
        DESCRIPTION
                "Create/Delete parameter. Default is created. Users perform a set
		 operation on this object in order to create/delete a static
		 address translation entry."
        DEFVAL  { created }
        ::= { wfNatStaticMappingEntry 1 }

    wfNatStaticMappingDisable OBJECT-TYPE
        SYNTAX  INTEGER {
                enabled(1),
                disabled(2)
            }
        ACCESS  read-write
        STATUS  mandatory
        DESCRIPTION
                "Enable/Disable parameter. Default is enabled. Users perform a
		 set operation on this object in order to enable/disable a static
		 address translation entry."
        DEFVAL  { enabled }
        ::= { wfNatStaticMappingEntry 2 }

    wfNatStaticMappingOrigAddress OBJECT-TYPE
        SYNTAX  IpAddress
        ACCESS  read-write
        STATUS  mandatory
        DESCRIPTION
                "The original (un-translated) address of the translation."
        ::= { wfNatStaticMappingEntry 3 }

    wfNatStaticMappingTransAddress OBJECT-TYPE
        SYNTAX  IpAddress
        ACCESS  read-only
        STATUS  mandatory
        DESCRIPTION
                "The translated address of the translation."
        ::= { wfNatStaticMappingEntry 4 }

    wfNatStaticMappingProtocol OBJECT-TYPE
        SYNTAX  INTEGER
        ACCESS  read-only
        STATUS  mandatory
        DESCRIPTION
                "The IP protocol of the translation. Example values are
		 6 for TCP, and 17 for UDP."
        ::= { wfNatStaticMappingEntry 5 }

   wfNatStaticMappingOrigPort OBJECT-TYPE
        SYNTAX  INTEGER
        ACCESS  read-write
        STATUS  mandatory
        DESCRIPTION
                "The original (domain specific) UDP or TCP port of the
		 translation. This will only be relevent if the protocol
                 is either UDP or TCP."
        ::= { wfNatStaticMappingEntry 6 }

    wfNatStaticMappingTransPort OBJECT-TYPE
        SYNTAX  INTEGER
        ACCESS  read-only
        STATUS  mandatory
        DESCRIPTION
                "The translated UDP or TCP port of the translation. This will
		 only be relevent if the protocol is either UDP or TCP."
        ::= { wfNatStaticMappingEntry 7 }

     wfNatStaticMappingInDomain OBJECT-TYPE
         SYNTAX  DisplayString
         ACCESS  read-write
         STATUS  mandatory
         DESCRIPTION
		"This attribute specifies the name of the address domain that this
		 source translation shall be valid for. In other words, this
		 translation shall only be valid for source addresses coming
		 inbound from this domain."
	DEFVAL  { "private" }
        ::= { wfNatStaticMappingEntry 8 }

     wfNatStaticMappingOutDomain OBJECT-TYPE
         SYNTAX  DisplayString
         ACCESS  read-write
         STATUS  mandatory
         DESCRIPTION
		"This attribute specifies the name of the outbound address
		 domain that this translation will be valid for. In other words,
  		 this translation only applies to translations that will be
		 forwarded out into this address domain."
	DEFVAL  { "public" }
        ::= { wfNatStaticMappingEntry 9}

   wfNatStaticMappingStaticNextHop OBJECT-TYPE
        SYNTAX  IpAddress
        ACCESS  read-write
        STATUS  mandatory
        DESCRIPTION
                "The IP address of the next hop of this static entry."
        DEFVAL{ 0 }
        ::= { wfNatStaticMappingEntry 10 }

   wfNatStaticMappingUnnumCct OBJECT-TYPE
        SYNTAX  INTEGER
        ACCESS  read-write
        STATUS  mandatory
        DESCRIPTION
                "This Nat static translation over the unnumbered interface."
        DEFVAL{ 0 }
        ::= { wfNatStaticMappingEntry 11 }


    wfNatMappingTable OBJECT-TYPE
        SYNTAX  SEQUENCE OF WfNatMappingEntry
        ACCESS  not-accessible
        STATUS  mandatory
        DESCRIPTION
                "This table defines the current set of address translations
		 that are in effect."
        ::= { wfNatGroup 10 }

    wfNatMappingEntry OBJECT-TYPE
        SYNTAX  WfNatMappingEntry
        ACCESS  not-accessible
        STATUS  mandatory
        DESCRIPTION
                "A single original source address to translated address
		 translation."
        INDEX   { wfNatMappingTransAddress,
                  wfNatMappingProtocol,
                  wfNatMappingTransPort }
        ::= { wfNatMappingTable 1 }

    WfNatMappingEntry ::= SEQUENCE {
            wfNatMappingOrigAddress
                IpAddress,
            wfNatMappingTransAddress
                IpAddress,
            wfNatMappingProtocol
                INTEGER,
            wfNatMappingOrigPort
                INTEGER,
            wfNatMappingTransPort
                INTEGER,
            wfNatMappingTxCount
                Counter,
            wfNatMappingRxCount
                Counter,
            wfNatMappingTimeout
                Counter,
            wfNatMappingMode
	        INTEGER,
            wfNatMappingInDomain
	        DisplayString,
            wfNatMappingOutDomain
	        DisplayString
	}

    wfNatMappingOrigAddress OBJECT-TYPE
        SYNTAX  IpAddress
        ACCESS  read-only
        STATUS  mandatory
        DESCRIPTION
                "The original (un-translated) address of the translation."
        ::= { wfNatMappingEntry 1 }

    wfNatMappingTransAddress OBJECT-TYPE
        SYNTAX  IpAddress
        ACCESS  read-only
        STATUS  mandatory
        DESCRIPTION
                "The translated address of the translation."
        ::= { wfNatMappingEntry 2 }

    wfNatMappingProtocol OBJECT-TYPE
        SYNTAX  INTEGER
        ACCESS  read-only
        STATUS  mandatory
        DESCRIPTION
                "`The IP protocol of the translation.'"
        ::= { wfNatMappingEntry 3 }

    wfNatMappingOrigPort OBJECT-TYPE
        SYNTAX  INTEGER
        ACCESS  read-only
        STATUS  mandatory
        DESCRIPTION
                "When the translation is for a TCP connection, this denotes
		 the original TCP port number."
        ::= { wfNatMappingEntry 4 }

    wfNatMappingTransPort OBJECT-TYPE
        SYNTAX  INTEGER
        ACCESS  read-only
        STATUS  mandatory
        DESCRIPTION
                "When the translation is for a TCP connection, this denotes
		 the translated TCP port number."
        ::= { wfNatMappingEntry 5 }

    wfNatMappingTxCount OBJECT-TYPE
        SYNTAX  Counter
        ACCESS  read-only
        STATUS  mandatory
        DESCRIPTION
                "Number of packets forwarded by NAT using this translation."
        ::= { wfNatMappingEntry 6 }

    wfNatMappingRxCount OBJECT-TYPE
        SYNTAX  Counter
        ACCESS  read-only
        STATUS  mandatory
        DESCRIPTION
                "Number of packets received by NAT using this translation."
        ::= { wfNatMappingEntry 7 }

    wfNatMappingTimeout OBJECT-TYPE
        SYNTAX  Counter
        ACCESS  read-only
        STATUS  mandatory
        DESCRIPTION
                "The time in seconds since this translation entry was last used.
		 This is used to age out translation entries."
        ::= { wfNatMappingEntry 8 }

    wfNatMappingMode OBJECT-TYPE
        SYNTAX  INTEGER
        ACCESS  read-only
        STATUS  mandatory
        DESCRIPTION
                "This is the bit mask representing the type of this translation.
		 Each bit specifies the type as follows:

                  The translation could be only ONE of the following three...

                  0x01000000 - This translation is origianted on this router,
				i.e. this NAT router performed the translation.
                  0x02000000 - This translation is learned from the peer,
				i.e. this translation was learned from the
                                peer using NAT Synchronization feature.
                  0x04000000 - This translation is owned,
				i.e. it was originally  learned from peer, but
				this router received traffic which used this
				translation.

                  ...and only ONE of the following three.

                  0x00000010 - This translation is the STATIC translation.
                  0x00000020 - This translation is Dynamic(1 to 1) translation.
                  0x00000040 - This translation is N to 1 translation."
        DEFVAL  { 0 }
        ::= { wfNatMappingEntry 9 }

     wfNatMappingInDomain OBJECT-TYPE
         SYNTAX DisplayString
         ACCESS  read-only
         STATUS  mandatory
         DESCRIPTION
		"This attribute specifies the name of the address domain that this
		 source translation shall be valid for. In ther words, this
		 translation shall only be valid for source addresses coming
		 inbound from this domain."
        ::= { wfNatMappingEntry 10 }


     wfNatMappingOutDomain OBJECT-TYPE
         SYNTAX DisplayString
         ACCESS  read-only
         STATUS  mandatory
         DESCRIPTION
	   	"This attribute specifies the name of the outbound address domain
		 that this translation will be valid for. In other words,  this
		 translation only applies to translations that will be forwarded
		 out into this address domain."
        ::= { wfNatMappingEntry 11}



    wfNatIntfTable OBJECT-TYPE
        SYNTAX	SEQUENCE OF WfNatIntfEntry
        ACCESS	not-accessible
        STATUS	mandatory
        DESCRIPTION
                "'The list of configured NAT interfaces.'"
        ::= { wfNatGroup 11 }

    wfNatIntfEntry OBJECT-TYPE
        SYNTAX	WfNatIntfEntry
        ACCESS	not-accessible
        STATUS	mandatory
        DESCRIPTION
                "'A NAT interface description.'"
        INDEX	{ wfNatIntfIpAddress,
    		  wfNatIntfCircuit }
        ::= { wfNatIntfTable 1 }

    WfNatIntfEntry ::= SEQUENCE {
    	    wfNatIntfDelete
    		INTEGER,
    	    wfNatIntfDisable
    		INTEGER,
    	    wfNatIntfIpAddress
    		IpAddress,
    	    wfNatIntfCircuit
    		INTEGER,
            wfNatIntfDomain
               DisplayString,
            wfNatIntfState
                INTEGER,
            wfNatIntfTxCount
                Counter,
            wfNatIntfRxCount
                Counter,
            wfNatIntfPktDropCount
                Counter
        }

    wfNatIntfDelete OBJECT-TYPE
        SYNTAX	INTEGER {
    		    created(1),
    		    deleted(2)
    		}
        ACCESS	read-write
        STATUS	mandatory
        DESCRIPTION
                "This variable determines if a NAT Interface has been
                configured on the router."
        DEFVAL	{ created }
        ::= { wfNatIntfEntry 1 }

    wfNatIntfDisable OBJECT-TYPE
        SYNTAX	INTEGER {
    		    enabled(1),
    		    disabled(2)
    		}
        ACCESS	read-write
        STATUS	mandatory
        DESCRIPTION
                "'The NAT interface's administrative status.  The value
                'enabled' denotes that NAT has been configured
                on the interface. The value 'disabled' denotes that
                the interface is not running NAT.'"
        DEFVAL	{ enabled }
        ::= { wfNatIntfEntry 2 }

	
    wfNatIntfIpAddress OBJECT-TYPE
        SYNTAX	IpAddress
        ACCESS	read-only
        STATUS	mandatory
        DESCRIPTION
                "The IP address of this NAT interface."
        ::= { wfNatIntfEntry 3 }

    wfNatIntfCircuit OBJECT-TYPE
        SYNTAX	INTEGER
        ACCESS	read-write
        STATUS	mandatory
        DESCRIPTION
                "The circuit number of this interface."
        ::= { wfNatIntfEntry 4 }

    wfNatIntfDomain OBJECT-TYPE
        SYNTAX  DisplayString
        ACCESS  read-write
        STATUS  mandatory
        DESCRIPTION
	         "This attribute specifies the Address Domain
		 Name that this interface is connected to.
		 Unidirectional NAT interfaces should be set
		 with domain name of 'private' or 'public'"
	DEFVAL  { "private" }
        ::= { wfNatIntfEntry 5 }
	
	
    wfNatIntfState OBJECT-TYPE
        SYNTAX	INTEGER {
    		    up(1),
    		    down(2),
    		    init(3)
    		}
        ACCESS	read-only
        STATUS	mandatory
        DESCRIPTION
                "'The state of NAT on this interface'"
        DEFVAL	{ down }
        ::= { wfNatIntfEntry 6 }

    wfNatIntfTxCount OBJECT-TYPE
        SYNTAX	Counter
        ACCESS	read-only
        STATUS	mandatory
        DESCRIPTION
                "Number of packets mapped over this interface from
                the local to the global network.'"
        ::= { wfNatIntfEntry 7 }

    wfNatIntfRxCount OBJECT-TYPE
        SYNTAX	Counter
        ACCESS	read-only
        STATUS	mandatory
        DESCRIPTION
                "Number of packets mapped over this interface from
                the global to the local network.'"
        ::= { wfNatIntfEntry 8 }

    wfNatIntfPktDropCount OBJECT-TYPE
        SYNTAX	Counter
        ACCESS	read-only
        STATUS	mandatory
        DESCRIPTION
                "Number of packets dropped on this interface"
        ::= { wfNatIntfEntry 9 }

	

    wfNatSrcAddressFilterTable OBJECT-TYPE
        SYNTAX  SEQUENCE OF WfNatSrcAddressFilterEntry
        ACCESS  not-accessible
        STATUS  mandatory
        DESCRIPTION
                "Table of NAT source address filters."
        ::= { wfNatGroup 12 }

    wfNatSrcAddressFilterEntry OBJECT-TYPE
        SYNTAX  WfNatSrcAddressFilterEntry
        ACCESS  not-accessible
        STATUS  mandatory
        DESCRIPTION
                "Information describing each of the available source
		address filters."
        INDEX   { wfNatSrcAddressFilterAddress,
                  wfNatSrcAddressFilterPrefixLen,
                   wfNatSrcAddressFilterIndex}
        ::= { wfNatSrcAddressFilterTable 1 }

    WfNatSrcAddressFilterEntry ::= SEQUENCE {
            wfNatSrcAddressFilterDelete
                INTEGER,
            wfNatSrcAddressFilterDisable
                INTEGER,
            wfNatSrcAddressFilterAddress
                IpAddress,
            wfNatSrcAddressFilterPrefixLen
                INTEGER,
            wfNatSrcAddressFilterIndex
                INTEGER,
            wfNatSrcAddressFilterNto1Addr
                IpAddress,
            wfNatSrcAddressFilterDomain
               DisplayString,
            wfNatSrcAddressFilterTransPoolSelector
               INTEGER,
            wfNatSrcAddressFilterStaticNextHop
               IpAddress,
            wfNatSrcAddressFilterUnnumCct
               INTEGER
        }


    wfNatSrcAddressFilterDelete OBJECT-TYPE
        SYNTAX  INTEGER {
                created(1),
                deleted(2)
            }
        ACCESS  read-write
        STATUS  mandatory
        DESCRIPTION
                "Create/Delete parameter. Default is created. Users perform
		 a set operation on this object in order to create/delete
		 a source address filter entry."
        DEFVAL  { created }
        ::= { wfNatSrcAddressFilterEntry 1 }

    wfNatSrcAddressFilterDisable OBJECT-TYPE
        SYNTAX  INTEGER {
                enabled(1),
                disabled(2)
            }
        ACCESS  read-write
        STATUS  mandatory
        DESCRIPTION
                "Enable/Disable parameter. Default is enabled. Users perform
		 a set operation on this object in order to enable/disable
		 a source address filter entry."
        DEFVAL  { enabled }
        ::= { wfNatSrcAddressFilterEntry 2 }

    wfNatSrcAddressFilterAddress OBJECT-TYPE
        SYNTAX  IpAddress
        ACCESS  read-only
        STATUS  mandatory
        DESCRIPTION
                "The IP beginning address of this source address filter entry."
        ::= { wfNatSrcAddressFilterEntry 3 }

    wfNatSrcAddressFilterPrefixLen OBJECT-TYPE
        SYNTAX  INTEGER (1 .. 32)
        ACCESS  read-only
        STATUS  mandatory
        DESCRIPTION
                 "The number of contiguous bits set in the IP address mask
		  which are used to define the address range of the entry."
        ::= { wfNatSrcAddressFilterEntry 4 }

    wfNatSrcAddressFilterIndex OBJECT-TYPE
        SYNTAX  INTEGER
        ACCESS  read-only
        STATUS  mandatory
        DESCRIPTION
                "A unique value for this entry in wfNatSrcAddressFilterTable."
        ::= { wfNatSrcAddressFilterEntry 5 }

    wfNatSrcAddressFilterNto1Addr OBJECT-TYPE
        SYNTAX  IpAddress
        ACCESS  read-write
        STATUS  mandatory
        DESCRIPTION
		 "specifies the N-to-1 translation address used for
                 this source address filter, otherwise set to zero."
        DEFVAL  { 0 }
        ::= { wfNatSrcAddressFilterEntry 6 }

    wfNatSrcAddressFilterDomain OBJECT-TYPE
        SYNTAX  DisplayString
        ACCESS  read-write
        STATUS  mandatory
        DESCRIPTION
		 "The value of this attribute specifies the Address
		 Domain Name that this source address filter is valid for.
		 For Unidirectional NAT this value must be 'public'"
	DEFVAL  { "private" }
        ::= { wfNatSrcAddressFilterEntry 7 }

    wfNatSrcAddressFilterTransPoolSelector OBJECT-TYPE
        SYNTAX  INTEGER {
                    inbound(1),
                    outbound(2)
                }
        ACCESS  read-write
        STATUS  mandatory
        DESCRIPTION
		 "The value of this attribute selects where to
		 get the translation address for this source address
		 filter from.  This could be either the translation
		 Pool defined for the inbound domain or the outbound
		 domain for the packet in question."
	DEFVAL{ outbound }
        ::= { wfNatSrcAddressFilterEntry 8 }

   wfNatSrcAddressFilterStaticNextHop OBJECT-TYPE
        SYNTAX  IpAddress
        ACCESS  read-write
        STATUS  mandatory
        DESCRIPTION
                "The IP address of the next hop of this source address
                 filter entry."
        DEFVAL{ 0 }
        ::= { wfNatSrcAddressFilterEntry 9 }

   wfNatSrcAddressFilterUnnumCct OBJECT-TYPE
        SYNTAX  INTEGER
        ACCESS  read-write
        STATUS  mandatory
        DESCRIPTION
                "This Nat source address filter over the unnumbered interface."
        DEFVAL{ 0 }
        ::= { wfNatSrcAddressFilterEntry 10 }


	
    wfNatTranslationPoolTable OBJECT-TYPE
        SYNTAX  SEQUENCE OF WfNatTranslationPoolEntry
        ACCESS  not-accessible
        STATUS  mandatory
        DESCRIPTION
                "Table of address ranges."
        ::= { wfNatGroup 13 }


	
    wfNatTranslationPoolEntry OBJECT-TYPE
        SYNTAX  WfNatTranslationPoolEntry
        ACCESS  not-accessible
        STATUS  mandatory
        DESCRIPTION
                "Information describing each of the available
                 translation pool."
        INDEX   { wfNatTranslationPoolAddress,
                  wfNatTranslationPoolPrefixLen,
                   wfNatTranslationPoolIndex}
        ::= { wfNatTranslationPoolTable 1 }

    WfNatTranslationPoolEntry ::= SEQUENCE {
            wfNatTranslationPoolDelete
                INTEGER,
            wfNatTranslationPoolDisable
                INTEGER,
            wfNatTranslationPoolAddress
                IpAddress,
            wfNatTranslationPoolPrefixLen
                INTEGER,
            wfNatTranslationPoolIndex
                INTEGER,
            wfNatTranslationPoolDomain
               DisplayString
        }


    wfNatTranslationPoolDelete OBJECT-TYPE
        SYNTAX  INTEGER {
                created(1),
                deleted(2)
            }
        ACCESS  read-write
        STATUS  mandatory
        DESCRIPTION
                "Create/Delete parameter. Default is created. Users perform
		 a set operation on this object in order to create/delete
		 a translation pool entry."
        DEFVAL  { created }
        ::= { wfNatTranslationPoolEntry 1 }

    wfNatTranslationPoolDisable OBJECT-TYPE
        SYNTAX  INTEGER {
                enabled(1),
                disabled(2)
            }
        ACCESS  read-write
        STATUS  mandatory
        DESCRIPTION
                "Enable/Disable parameter. Default is enabled. Users perform
		 a set operation on this object in order to enable/disable
		 a translation pool entry."
        DEFVAL  { enabled }
        ::= { wfNatTranslationPoolEntry 2 }

    wfNatTranslationPoolAddress OBJECT-TYPE
        SYNTAX  IpAddress
        ACCESS  read-only
        STATUS  mandatory
        DESCRIPTION
                "The IP beginning address of this translation pool entry."
        ::= { wfNatTranslationPoolEntry 3 }

    wfNatTranslationPoolPrefixLen OBJECT-TYPE
        SYNTAX  INTEGER (1 .. 32)
        ACCESS  read-only
        STATUS  mandatory
        DESCRIPTION
                 "The number of contiguous bits set in the IP address mask
		  which are used to define the address range of the entry."
        ::= { wfNatTranslationPoolEntry 4 }

    wfNatTranslationPoolIndex OBJECT-TYPE
        SYNTAX  INTEGER
        ACCESS  read-only
        STATUS  mandatory
        DESCRIPTION
                "A unique value for this entry in wfNatTranslationPoolTable."
        ::= { wfNatTranslationPoolEntry 5 }


    wfNatTranslationPoolDomain OBJECT-TYPE
        SYNTAX  DisplayString
        ACCESS  read-write
        STATUS  mandatory
        DESCRIPTION
		 "The value of this attribute specifies the Address
		 Domain Name that this translation pool is valid for.
		 For Unidirectional NAT this value must be 'public'"
	DEFVAL  { "public" }
        ::= { wfNatTranslationPoolEntry 6 }

	
	
END  -- Wellfleet-NPT-MIB
