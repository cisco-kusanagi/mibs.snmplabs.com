Wellfleet-ATM-MIB DEFINITIONS ::= BEGIN

-- Created by mdl2asn version 3.1
-- Creation date: Wed Aug 30 16:37:09 EDT 1995


    IMPORTS

      Counter, Gauge, TimeTicks
        FROM RFC1155-SMI
      OBJECT-TYPE
        FROM RFC-1212
      DisplayString
        FROM RFC1213-MIB
      wfSonetGroup, wfAtmGroup, wfAtmInterfaceGroup
        FROM Wellfleet-COMMON-MIB;

    wfAtmCommonGroup      OBJECT IDENTIFIER ::= { wfAtmInterfaceGroup 1 }
    wfAtmLinkModuleGroup  OBJECT IDENTIFIER ::= { wfAtmInterfaceGroup 2 }
    wfAtmCellSwitchGroup  OBJECT IDENTIFIER ::= { wfAtmInterfaceGroup 3 }

    wfAtm		OBJECT IDENTIFIER ::= { wfAtmGroup 1 }

    wfAtmDelete OBJECT-TYPE
        SYNTAX	INTEGER {
    		    created(1),
    		    deleted(2)
    		}
        ACCESS	read-write
        STATUS	mandatory
        DESCRIPTION
                "Indication to create or delete an ATM Base record."
        DEFVAL	{ created }
        ::= { wfAtm 1 }

    wfAtmInterfaceNumber OBJECT-TYPE
        SYNTAX	INTEGER
        ACCESS	read-only
        STATUS	mandatory
        DESCRIPTION
                "Number of ATM interfaces in the Wellfleet Router (entries
                in the wfAtmInterfaceTable), regardless of their current state,
                present on this system."
        ::= { wfAtm 2 }

    wfAtmOverallStatus OBJECT-TYPE
        SYNTAX	INTEGER {
    		    healthy(1),
    		    interfaceanomaly(2),
    		    otheranomaly(3)
    		}
        ACCESS	read-only
        STATUS	mandatory
        DESCRIPTION
                "Overall status of ATM interfaces in the Wellfleet Router(entries
                in the wfAtmInterfaceTable) present on this system. Healthy indicates
                each configured interfaces are in the UP state.  An interface
                anomaly is indicative of one or more of the configured
                interfaces being in the DOWN State.  Other Anomaly is indicative
                of one or more ATM interfaces being in the INIT or NOT PRESENT
                state"
        DEFVAL	{ healthy }
        ::= { wfAtm 3 }

    wfAtmGlobalSigStkVersion OBJECT-TYPE
        SYNTAX	INTEGER {
    		    u30(1),
    		    u31(2),
    		    sym(3),
    		    u40(4)
    		}
        ACCESS	read-write
        STATUS	mandatory
        DESCRIPTION
                "Global signalling stack Version. This value will be used to
                by management entities to know the global version of signalling.
                The intent here is to have passive placeholder.  Active versions
                of signalling are maintained on a per ATM interface basis in
                wfAtmSscopEntry and wfAtmSigEntry.  If this is considered
                of no value, please remove at your earliest convenience."
        DEFVAL	{ u30 }
        ::= { wfAtm 4 }

    wfAtmInterfaceTable OBJECT-TYPE
        SYNTAX	SEQUENCE OF WfAtmInterfaceEntry
        ACCESS	not-accessible
        STATUS	mandatory
        DESCRIPTION
                "ATM Interface Table - Router Resident
                The statistical and configuration parameters for an ATM Interface.
                There is one MIB instance of this record per Sync or HSSI line
                configured for ATM DXI support. The Physical ATM DXI interface
                is managed via this table."
        ::= { wfAtmGroup 2 }

    wfAtmInterfaceEntry OBJECT-TYPE
        SYNTAX	WfAtmInterfaceEntry
        ACCESS	not-accessible
        STATUS	mandatory
        DESCRIPTION
                "The attributes for a particular ATM DXI Interface"
        INDEX	{ wfAtmInterfaceLineNumber,
    		  wfAtmInterfaceLLIndex }
        ::= { wfAtmInterfaceTable 1 }

    WfAtmInterfaceEntry ::= SEQUENCE {
    	    wfAtmInterfaceDelete
    		INTEGER,
    	    wfAtmInterfaceDisable
    		INTEGER,
    	    wfAtmInterfaceState
    		INTEGER,
    	    wfAtmInterfaceCircuit
    		INTEGER,
    	    wfAtmInterfaceMaxSupportedVCs
    		INTEGER,
    	    wfAtmInterfaceVCsInUse
    		INTEGER,
    	    wfAtmInterfaceDescr
    		DisplayString,
    	    wfAtmInterfaceType
    		INTEGER,
    	    wfAtmInterfaceLastChange
    		TimeTicks,
    	    wfAtmInterfacePlcp
    		OBJECT IDENTIFIER,
    	    wfAtmMpeNull
    		INTEGER,
    	    wfAtmCsNull
    		INTEGER,
    	    wfAtmInterfaceMulticast
    		INTEGER,
    	    wfAtmDrops
    		Counter,
    	    wfAtmInterfaceLmiDisable
    		INTEGER,
    	    wfAtmInterfaceLineNumber
    		INTEGER,
    	    wfAtmInterfaceLLIndex
    		INTEGER,
    	    wfAtmInterfaceDxiMode
    		INTEGER,
    	    wfAtmUnknownVCPkts
    		Counter
        }

    wfAtmInterfaceDelete OBJECT-TYPE
        SYNTAX	INTEGER {
    		    created(1),
    		    deleted(2)
    		}
        ACCESS	read-write
        STATUS	mandatory
        DESCRIPTION
                "Indication to create or delete an ATM DXI interface. This will
                remove ATMNET access over this interface The ATM Interface
                entry  instance is removed from the MIB in this case."
        DEFVAL	{ created }
        ::= { wfAtmInterfaceEntry 1 }

    wfAtmInterfaceDisable OBJECT-TYPE
        SYNTAX	INTEGER {
    		    enabled(1),
    		    disabled(2)
    		}
        ACCESS	read-write
        STATUS	mandatory
        DESCRIPTION
                "Indicates when an ATM DXI interface is to be enabled or disabled.
                Disabling will disable ATM Access over this interface. The ATM
                Interface instance is NOT removed from the MIB in this case."
        DEFVAL	{ enabled }
        ::= { wfAtmInterfaceEntry 2 }

    wfAtmInterfaceState OBJECT-TYPE
        SYNTAX	INTEGER {
    		    up(1),
    		    down(2),
    		    init(3),
    		    notpresent(4)
    		}
        ACCESS	read-only
        STATUS	mandatory
        DESCRIPTION
                "Indicates the state for this interface.
                The state indicates Not Present when the interface has been
                configured but has not been initialized.  Init state indicates
                that the interface is in the process of being initialized by the
                system.  Up state indicates that the interface is operating
                normally.  Down state indicates that the ATM DXI interface is
                physically or logically disabled."
        DEFVAL	{ notpresent }
        ::= { wfAtmInterfaceEntry 3 }

    wfAtmInterfaceCircuit OBJECT-TYPE
        SYNTAX	INTEGER
        ACCESS	read-only
        STATUS	mandatory
        DESCRIPTION
                "The Wellfleet circuit number of this entry"
        ::= { wfAtmInterfaceEntry 4 }

    wfAtmInterfaceMaxSupportedVCs OBJECT-TYPE
        SYNTAX	INTEGER
        ACCESS	read-write
        STATUS	mandatory
        DESCRIPTION
                "Maximum number of VCs allowed on this interface. Initially set by
                configuration system for PVCs only"
        DEFVAL	{ 512 }
        ::= { wfAtmInterfaceEntry 5 }

    wfAtmInterfaceVCsInUse OBJECT-TYPE
        SYNTAX	INTEGER
        ACCESS	read-only
        STATUS	mandatory
        DESCRIPTION
                "The number of VCs that are currently configured on this interface"
        ::= { wfAtmInterfaceEntry 6 }

    wfAtmInterfaceDescr OBJECT-TYPE
        SYNTAX	DisplayString
        ACCESS	read-write
        STATUS	mandatory
        DESCRIPTION
                "A textual string describing this ATM interface."
        ::= { wfAtmInterfaceEntry 7 }

    wfAtmInterfaceType OBJECT-TYPE
        SYNTAX	INTEGER {
    		    other(1),
    		    ds1(2),
    		    ds3(3)
    		}
        ACCESS	read-only
        STATUS	mandatory
        DESCRIPTION
                "The transmission type used at the ATM interface."
        DEFVAL	{ other }
        ::= { wfAtmInterfaceEntry 8 }

    wfAtmInterfaceLastChange OBJECT-TYPE
        SYNTAX	TimeTicks
        ACCESS	read-only
        STATUS	mandatory
        DESCRIPTION
                "The value of sysUpTime at the time the interface
                entered its current operational state. If the current
                state was entered prior to the last re-initialization
                of the local network management subsystem, then this
                object contains a zero value."
        ::= { wfAtmInterfaceEntry 9 }

    wfAtmInterfacePlcp OBJECT-TYPE
        SYNTAX	OBJECT IDENTIFIER
        ACCESS	read-only
        STATUS	mandatory
        DESCRIPTION
                "Identifies the OID of the PLCP object in the MIB
                If no additional transmission and/or media
                specific information is available, this object has
                the value { 0 0 }. "
        ::= { wfAtmInterfaceEntry 10 }

    wfAtmMpeNull OBJECT-TYPE
        SYNTAX	INTEGER {
    		    mpe1294(1),
    		    null(2),
    		    mpe1483(3)
    		}
        ACCESS	read-write
        STATUS	mandatory
        DESCRIPTION
                "Used to select Null, Multi-Protocol Encapsulation
                (RFC 1294) or Multi-Protocol Encapsulation (RFC 1483)
                layer for this Interface. Null is considered VC Based
                Multiplexing and is not supported for Bridging."
        DEFVAL	{ mpe1483 }
        ::= { wfAtmInterfaceEntry 11 }

    wfAtmCsNull OBJECT-TYPE
        SYNTAX	INTEGER {
    		    aal34(1),
    		    null(2),
    		    aal5(3)
    		}
        ACCESS	read-write
        STATUS	mandatory
        DESCRIPTION
                "Used to configure the type of CS_PDU encapsulation supported on the ATM
                DXI interface based on the ATM Forum's ATM DXI specification. This
                configuration is on a per Interface basis. The supported values are
                AAL3/4, AAL5 and Null (no CS_PDU encapsulation). Null is a propriatary
                configurable value when no CS_PDU encapsulation is desired."
        DEFVAL	{ aal5 }
        ::= { wfAtmInterfaceEntry 12 }

    wfAtmInterfaceMulticast OBJECT-TYPE
        SYNTAX	INTEGER {
    		    enabled(1),
    		    disabled(2)
    		}
        ACCESS	read-write
        STATUS	mandatory
        DESCRIPTION
                "This indicates whether the ATM service provider offers  multicast service"
        DEFVAL	{ disabled }
        ::= { wfAtmInterfaceEntry 13 }

    wfAtmDrops OBJECT-TYPE
        SYNTAX	Counter
        ACCESS	read-only
        STATUS	mandatory
        DESCRIPTION
                "The cumulative count of packet drops on this ATM Interface."
        ::= { wfAtmInterfaceEntry 14 }

    wfAtmInterfaceLmiDisable OBJECT-TYPE
        SYNTAX	INTEGER {
    		    enabled(1),
    		    disabled(2)
    		}
        ACCESS	read-write
        STATUS	mandatory
        DESCRIPTION
                "Indicates when an LMI entry is to be enabled or disabled. Disabling
                will temporarily disable the ability to report
                CSU/DSU traps and the ability to retrieve statistical information
                from the CSU/DSU.  The ATM LMI instance is NOT removed from the MIB
                in this case."
        DEFVAL	{ disabled }
        ::= { wfAtmInterfaceEntry 15 }

    wfAtmInterfaceLineNumber OBJECT-TYPE
        SYNTAX	INTEGER
        ACCESS	read-only
        STATUS	mandatory
        DESCRIPTION
                "Instance identifier. This value corresponds to the line number of the
                Wellfleet router."
        ::= { wfAtmInterfaceEntry 16 }

    wfAtmInterfaceLLIndex OBJECT-TYPE
        SYNTAX	INTEGER
        ACCESS	read-only
        STATUS	mandatory
        DESCRIPTION
                "Instance identifier. This value corresponds to the port's
                llindex number. The Lower layer index uniquely identifies the lower
                layer in cases where the lower layer may be something other than the
                physical layer."
        ::= { wfAtmInterfaceEntry 17 }

    wfAtmInterfaceDxiMode OBJECT-TYPE
        SYNTAX	INTEGER {
    		    mode1a(1),
    		    mode1b(2),
    		    mode2(3),
    		    modep2(4)
    		}
        ACCESS	read-write
        STATUS	mandatory
        DESCRIPTION
                "ATM DXI Mode. This attribute specifies the ATM DXI Mode for this
                interface based on the ATM Forum's ATM DXI specification. Currently
                supported is Modes 1a, 1b, 2 and Proprietary 2 (which is an earlier
                version of Mode 2)."
        DEFVAL	{ mode1a }
        ::= { wfAtmInterfaceEntry 18 }

    wfAtmUnknownVCPkts OBJECT-TYPE
        SYNTAX	Counter
        ACCESS	read-only
        STATUS	mandatory
        DESCRIPTION
                "The count of packets received with an unknown VC"
        ::= { wfAtmInterfaceEntry 19 }

    wfAtmLmiTable OBJECT-TYPE
        SYNTAX	SEQUENCE OF WfAtmLmiEntry
        ACCESS	not-accessible
        STATUS	mandatory
        DESCRIPTION
                "ATM Local Management Interface Table - Router Resident
                The statistical and configuration parameters for an ATM DXI
                Local Management Interface.   There is one LMI MIB instance per Sync
                or HSSI line configured for ATM DXI support. The LMI interface is
                managed via this table."
        ::= { wfAtmGroup 3 }

    wfAtmLmiEntry OBJECT-TYPE
        SYNTAX	WfAtmLmiEntry
        ACCESS	not-accessible
        STATUS	mandatory
        DESCRIPTION
                "The attributes for a particular ATM Lmi"
        INDEX	{ wfAtmLmiLineNumber,
    		  wfAtmLmiLLIndex }
        ::= { wfAtmLmiTable 1 }

    WfAtmLmiEntry ::= SEQUENCE {
    	    wfAtmLmiState
    		INTEGER,
    	    wfAtmLmiCircuit
    		INTEGER,
    	    wfAtmLmiNoVCErrors
    		Counter,
    	    wfAtmLmiProxyRequests
    		Counter,
    	    wfAtmLmiCsuDsuResponses
    		Counter,
    	    wfAtmLmiCsuDsuTraps
    		Counter,
    	    wfAtmLmiOtherErrors
    		Counter,
    	    wfAtmLmiLineNumber
    		INTEGER,
    	    wfAtmLmiLLIndex
    		INTEGER
        }

    wfAtmLmiState OBJECT-TYPE
        SYNTAX	INTEGER {
    		    up(1),
    		    down(2),
    		    init(3),
    		    notpresent(4)
    		}
        ACCESS	read-only
        STATUS	mandatory
        DESCRIPTION
                "Indicates the state of the LMI for this interface
                The state indicates Not Present when the LMI has been
                configured but has not been initialized.  Init state indicates
                that the LMI is in the process of being initialized by the
                system.  Up state indicates that the LMI is operating
                normally.  Down state indicates that the LMI is
                physically or logically disabled."
        DEFVAL	{ notpresent }
        ::= { wfAtmLmiEntry 1 }

    wfAtmLmiCircuit OBJECT-TYPE
        SYNTAX	INTEGER
        ACCESS	read-only
        STATUS	mandatory
        DESCRIPTION
                "The circuit number of this entry"
        ::= { wfAtmLmiEntry 2 }

    wfAtmLmiNoVCErrors OBJECT-TYPE
        SYNTAX	Counter
        ACCESS	read-only
        STATUS	mandatory
        DESCRIPTION
                "The number of Frames dropped that couldn't be associated with
                the LMI VPI/VCI"
        ::= { wfAtmLmiEntry 3 }

    wfAtmLmiProxyRequests OBJECT-TYPE
        SYNTAX	Counter
        ACCESS	read-only
        STATUS	mandatory
        DESCRIPTION
                "The number of SNMP Proxy Requests"
        ::= { wfAtmLmiEntry 4 }

    wfAtmLmiCsuDsuResponses OBJECT-TYPE
        SYNTAX	Counter
        ACCESS	read-only
        STATUS	mandatory
        DESCRIPTION
                "The number of CSU/DSU SNMP Responses to Proxy Requests"
        ::= { wfAtmLmiEntry 5 }

    wfAtmLmiCsuDsuTraps OBJECT-TYPE
        SYNTAX	Counter
        ACCESS	read-only
        STATUS	mandatory
        DESCRIPTION
                "The number of CSU/DSU SNMP Traps Received"
        ::= { wfAtmLmiEntry 6 }

    wfAtmLmiOtherErrors OBJECT-TYPE
        SYNTAX	Counter
        ACCESS	read-only
        STATUS	mandatory
        DESCRIPTION
                "The number of frames dropped to format or other errors."
        ::= { wfAtmLmiEntry 7 }

    wfAtmLmiLineNumber OBJECT-TYPE
        SYNTAX	INTEGER
        ACCESS	read-only
        STATUS	mandatory
        DESCRIPTION
                "Instance identifier. This value corresponds to the line number of the
                Wellfleet router."
        ::= { wfAtmLmiEntry 8 }

    wfAtmLmiLLIndex OBJECT-TYPE
        SYNTAX	INTEGER
        ACCESS	read-only
        STATUS	mandatory
        DESCRIPTION
                "Instance identifier. This value corresponds to the port's llindex
                number. The Lower layer index uniquely identifies the lower
                layer in cases where the lower layer may be something other than the
                physical layer."
        ::= { wfAtmLmiEntry 9 }

    wfAtmPlcpTable OBJECT-TYPE
        SYNTAX	SEQUENCE OF WfAtmPlcpEntry
        ACCESS	not-accessible
        STATUS	mandatory
        DESCRIPTION
                "The ATM PLCP Table - CSU/DSU Resident
                The PLCP object reflects information about either DS1 or DS3
                PLCP framing status and performance.  There is one instance of
                this object for every ATM DS1 or DS3 UNI.
                The PLCP object is separated from the other ATM objects for
                two reasons.  First, there may be ATM UNIs which use physical
                media other than DS1 or DS3, and thus the PLCP object may not
                apply to them.  Second, the PLCP object may also be applied
                towards management of SMDS Interfaces (SIPs).
                This PLCP object is essentially a superset of the PLCP object
                described in the Internet Draft MIB for SMDS (SIPs).  It contains
                variables of interest to some ATM service providers and customers."
        ::= { wfAtmGroup 4 }

    wfAtmPlcpEntry OBJECT-TYPE
        SYNTAX	WfAtmPlcpEntry
        ACCESS	not-accessible
        STATUS	mandatory
        DESCRIPTION
                "per linenumber/llindex PLCP objects"
        INDEX	{ wfAtmPlcpLineNumber,
    		  wfAtmPlcpLLIndex }
        ::= { wfAtmPlcpTable 1 }

    WfAtmPlcpEntry ::= SEQUENCE {
    	    wfAtmPlcpCct
    		INTEGER,
    	    wfAtmPlcpPhysical
    		OBJECT IDENTIFIER,
    	    wfAtmPlcpLof
    		INTEGER,
    	    wfAtmPlcpLofCFA
    		INTEGER,
    	    wfAtmPlcpYellow
    		INTEGER,
    	    wfAtmPlcpYellowCFA
    		INTEGER,
    	    wfAtmPlcpStatus
    		INTEGER,
    	    wfAtmPlcpSeconds
    		Counter,
    	    wfAtmPlcpBipErrors
    		Counter,
    	    wfAtmPlcpBipESecs
    		Counter,
    	    wfAtmPlcpBipSESecs
    		Counter,
    	    wfAtmPlcpFebes
    		Counter,
    	    wfAtmPlcpFebeESecs
    		Counter,
    	    wfAtmPlcpFebeSESecs
    		Counter,
    	    wfAtmPlcpFrameErrors
    		Counter,
    	    wfAtmPlcpSevereFrameErrors
    		Counter,
    	    wfAtmPlcpSEFS
    		Counter,
    	    wfAtmPlcpUAS
    		Counter,
    	    wfAtmPlcpLineNumber
    		INTEGER,
    	    wfAtmPlcpLLIndex
    		INTEGER
        }

    wfAtmPlcpCct OBJECT-TYPE
        SYNTAX	INTEGER
        ACCESS	read-only
        STATUS	mandatory
        DESCRIPTION
                "Identifies the DS1 or DS3 PLCP port for which this entry
                contains information.  This corresponds to the Wellfleet
                circuit number"
        ::= { wfAtmPlcpEntry 1 }

    wfAtmPlcpPhysical OBJECT-TYPE
        SYNTAX	OBJECT IDENTIFIER
        ACCESS	read-only
        STATUS	mandatory
        DESCRIPTION
                "Identifies the OID of the first object in the standard
                DS1 or DS3 MIB"
        ::= { wfAtmPlcpEntry 2 }

    wfAtmPlcpLof OBJECT-TYPE
        SYNTAX	INTEGER {
    		    true(1),
    		    false(2)
    		}
        ACCESS	read-only
        STATUS	mandatory
        DESCRIPTION
                "True if Loss of Frame has been detected"
        DEFVAL	{ false }
        ::= { wfAtmPlcpEntry 3 }

    wfAtmPlcpLofCFA OBJECT-TYPE
        SYNTAX	INTEGER {
    		    true(1),
    		    false(2)
    		}
        ACCESS	read-only
        STATUS	mandatory
        DESCRIPTION
                "True if Loss of Frame has been detected over the CFA time
                period"
        DEFVAL	{ false }
        ::= { wfAtmPlcpEntry 4 }

    wfAtmPlcpYellow OBJECT-TYPE
        SYNTAX	INTEGER {
    		    true(1),
    		    false(2)
    		}
        ACCESS	read-only
        STATUS	mandatory
        DESCRIPTION
                "True if PLCP Yellow (Remote Alarm Indication) has been detected"
        DEFVAL	{ false }
        ::= { wfAtmPlcpEntry 5 }

    wfAtmPlcpYellowCFA OBJECT-TYPE
        SYNTAX	INTEGER {
    		    true(1),
    		    false(2)
    		}
        ACCESS	read-only
        STATUS	mandatory
        DESCRIPTION
                "True if PLCP Yellow (Remote Alarm Indication) has been detected
                over the CFA time period"
        DEFVAL	{ false }
        ::= { wfAtmPlcpEntry 6 }

    wfAtmPlcpStatus OBJECT-TYPE
        SYNTAX	INTEGER {
    		    connected(1),
    		    up(2),
    		    down(3),
    		    other(4),
    		    outofframe(5)
    		}
        ACCESS	read-only
        STATUS	mandatory
        DESCRIPTION
                "The value of this variable indicates the PLCP
                status as indicated by the three-bit PLCP LSS
                code received from the remote end.  Connected is
                LSS code #0, linkUp is LSS code #6, and linkDown is
                code #3.  OtherCode means that one of the other five
                possible code values is being received.  OutOfFrame
                means that the PLCP is in the out of frame state,
                and therefore there is no code being received."
        DEFVAL	{ down }
        ::= { wfAtmPlcpEntry 7 }

    wfAtmPlcpSeconds OBJECT-TYPE
        SYNTAX	Counter
        ACCESS	read-only
        STATUS	mandatory
        DESCRIPTION
                "The count of seconds elapsed since event counting
                began or since the counters were last cleared.  The
                implementation may optionally allow this variable to
                be set.  If set, the set value is ignored, and this
                variable and all other event counters for this
                object are reset to zero."
        ::= { wfAtmPlcpEntry 8 }

    wfAtmPlcpBipErrors OBJECT-TYPE
        SYNTAX	Counter
        ACCESS	read-only
        STATUS	mandatory
        DESCRIPTION
                "The count of PLCP Bit Interleaved Parity (BIP)
                errors detected."
        ::= { wfAtmPlcpEntry 9 }

    wfAtmPlcpBipESecs OBJECT-TYPE
        SYNTAX	Counter
        ACCESS	read-only
        STATUS	mandatory
        DESCRIPTION
                "BIP Errored Seconds. The count of seconds during
                which one or more BIP errors were detected."
        ::= { wfAtmPlcpEntry 10 }

    wfAtmPlcpBipSESecs OBJECT-TYPE
        SYNTAX	Counter
        ACCESS	read-only
        STATUS	mandatory
        DESCRIPTION
                "BIP Severely Errored Seconds. The count of seconds
                during which five (5) or more BIP errors were detected."
        ::= { wfAtmPlcpEntry 11 }

    wfAtmPlcpFebes OBJECT-TYPE
        SYNTAX	Counter
        ACCESS	read-only
        STATUS	mandatory
        DESCRIPTION
                "The count of PLCP Far End Block Errors (FEBE)
                detected."
        ::= { wfAtmPlcpEntry 12 }

    wfAtmPlcpFebeESecs OBJECT-TYPE
        SYNTAX	Counter
        ACCESS	read-only
        STATUS	mandatory
        DESCRIPTION
                "FEBE Errored Seconds. The count of seconds during
                which one or more FEBE errors were detected."
        ::= { wfAtmPlcpEntry 13 }

    wfAtmPlcpFebeSESecs OBJECT-TYPE
        SYNTAX	Counter
        ACCESS	read-only
        STATUS	mandatory
        DESCRIPTION
                "FEBE Severely Errored Seconds. The count of seconds
                during which five (5) or more FEBE errors were detected."
        ::= { wfAtmPlcpEntry 14 }

    wfAtmPlcpFrameErrors OBJECT-TYPE
        SYNTAX	Counter
        ACCESS	read-only
        STATUS	mandatory
        DESCRIPTION
                "The count of PLCP Frame bit errors detected."
        ::= { wfAtmPlcpEntry 15 }

    wfAtmPlcpSevereFrameErrors OBJECT-TYPE
        SYNTAX	Counter
        ACCESS	read-only
        STATUS	mandatory
        DESCRIPTION
                "The count of PLCP Severe Frame errors (aka Out Of
                Frame Events) detected."
        ::= { wfAtmPlcpEntry 16 }

    wfAtmPlcpSEFS OBJECT-TYPE
        SYNTAX	Counter
        ACCESS	read-only
        STATUS	mandatory
        DESCRIPTION
                "Severely Errored Framing Seconds. The count of
                seconds during which one or more PLCP Severe Frame
                errors were detected."
        ::= { wfAtmPlcpEntry 17 }

    wfAtmPlcpUAS OBJECT-TYPE
        SYNTAX	Counter
        ACCESS	read-only
        STATUS	mandatory
        DESCRIPTION
                "Unavailable Seconds. The count of seconds during
                which the PLCP service was declared to be unavailable."
        ::= { wfAtmPlcpEntry 18 }

    wfAtmPlcpLineNumber OBJECT-TYPE
        SYNTAX	INTEGER
        ACCESS	read-only
        STATUS	mandatory
        DESCRIPTION
                "Instance identifier. This value corresponds to the line number
                of the Wellfleet router."
        ::= { wfAtmPlcpEntry 19 }

    wfAtmPlcpLLIndex OBJECT-TYPE
        SYNTAX	INTEGER
        ACCESS	read-only
        STATUS	mandatory
        DESCRIPTION
                "Instance identifier. This value corresponds to the port's
                llindex. The Lower layer index uniquely identifies the lower
                   layer in cases where the lower layer may be something other than the
                physical layer."
        ::= { wfAtmPlcpEntry 20 }

    wfAtmUniTable OBJECT-TYPE
        SYNTAX	SEQUENCE OF WfAtmUniEntry
        ACCESS	not-accessible
        STATUS	mandatory
        DESCRIPTION
                "The ATM UNI Table - CSU/DSU Resident
                The ATM User Network Interface (UNI) object reflects information
                about a particular ATM UNI.  In particular it contains information,
                both configuration and performance, from the 'ATM' or Cell layer
                of the ATM protocol hierarchy.  It optionally keeps some information
                on a per-VPI/VCI basis.  It 'points to' its associated
                physical layer object, for example the DS1 or DS3 PLCP object.
                It also 'points to' the (one or more) higher layer object(s),
                namely the ATM Adaptation Layer (AAL) object(s) which further
                process the ATM Cells.
                It should be noted that in the ATM UNI MIB, the receive (transmit)
                direction refers to data received from (transmitted to)
                the ATM UNI interface.

                 ** For DL200 and DL3200 there is only one ATM UNI per DL unit
                 ** and only one AAL object (specifically VBR) per ATM UNI.
                "
        ::= { wfAtmGroup 5 }

    wfAtmUniEntry OBJECT-TYPE
        SYNTAX	WfAtmUniEntry
        ACCESS	not-accessible
        STATUS	mandatory
        DESCRIPTION
                "per linenumber/llindex User Network Interface (UNI) objects -
                wfAtmUniLineNumber and wfAtmUniLLIndex corresponds to Wellfleet
                linenumber/llindex number"
        INDEX	{ wfAtmUniLineNumber,
    		  wfAtmUniLLIndex }
        ::= { wfAtmUniTable 1 }

    WfAtmUniEntry ::= SEQUENCE {
    	    wfAtmUniCct
    		INTEGER,
    	    wfAtmUniPhysical
    		OBJECT IDENTIFIER,
    	    wfAtmUniAal
    		OBJECT IDENTIFIER,
    	    wfAtmUniSeconds
    		Counter,
    	    wfAtmUniLineNumber
    		INTEGER,
    	    wfAtmUniLLIndex
    		INTEGER
        }

    wfAtmUniCct OBJECT-TYPE
        SYNTAX	INTEGER
        ACCESS	read-only
        STATUS	mandatory
        DESCRIPTION
                "This corresponds to the Wellfleet circuit number"
        ::= { wfAtmUniEntry 1 }

    wfAtmUniPhysical OBJECT-TYPE
        SYNTAX	OBJECT IDENTIFIER
        ACCESS	read-only
        STATUS	mandatory
        DESCRIPTION
                "Identifies the OID of the first object in the standard
                DS1 or DS3 MIB corresponding to this ATM UNI port"
        ::= { wfAtmUniEntry 2 }

    wfAtmUniAal OBJECT-TYPE
        SYNTAX	OBJECT IDENTIFIER
        ACCESS	read-only
        STATUS	mandatory
        DESCRIPTION
                "Identifies the AAL MIB corresponding to this ATM UNI port.
                There is only one AAL currently for the DXI application."
        ::= { wfAtmUniEntry 3 }

    wfAtmUniSeconds OBJECT-TYPE
        SYNTAX	Counter
        ACCESS	read-only
        STATUS	mandatory
        DESCRIPTION
                "The count of seconds elapsed since event counting
                 began or since the counters were last cleared.The
                 implementation may optionally allow this variable to
                 be set.If set, the set value is ignored, and this
                  variable and all other event counters for this
                 object are reset to zero."
        ::= { wfAtmUniEntry 4 }

    wfAtmUniLineNumber OBJECT-TYPE
        SYNTAX	INTEGER
        ACCESS	read-only
        STATUS	mandatory
        DESCRIPTION
                "Instance identifier. This value corresponds to the line number
                of the Wellfleet router."
        ::= { wfAtmUniEntry 5 }

    wfAtmUniLLIndex OBJECT-TYPE
        SYNTAX	INTEGER
        ACCESS	read-only
        STATUS	mandatory
        DESCRIPTION
                "Instance identifier. This value corresponds to the port's llindex.
                The Lower layer index uniquely identifies the lower
                layer in cases where the lower layer may be something other than the
                physical layer."
        ::= { wfAtmUniEntry 6 }

    wfAtmUniAtmTable OBJECT-TYPE
        SYNTAX	SEQUENCE OF WfAtmUniAtmEntry
        ACCESS	not-accessible
        STATUS	mandatory
        DESCRIPTION
                "The ATM UNIATM Table CSU/DSU Resident
                This list contains ATM Layer parameters, one entry
                per ATM UNI port.  The counts maintained in this table
                are totals for the UNI, across all VPI/VCIs."
        ::= { wfAtmGroup 6 }

    wfAtmUniAtmEntry OBJECT-TYPE
        SYNTAX	WfAtmUniAtmEntry
        ACCESS	not-accessible
        STATUS	mandatory
        DESCRIPTION
                "per linenumber/llindex UNI ATM Layer objects -
                wfAtmUniAtmLineNumber and wfAtmUniAtmLLIndex corresponds to
                Wellfleet  linenumber/llindex number"
        INDEX	{ wfAtmUniAtmLineNumber,
    		  wfAtmUniAtmLLIndex }
        ::= { wfAtmUniAtmTable 1 }

    WfAtmUniAtmEntry ::= SEQUENCE {
    	    wfAtmUniAtmCct
    		INTEGER,
    	    wfAtmUniAtmNoBuffers
    		Counter,
    	    wfAtmUniAtmHECs
    		Counter,
    	    wfAtmUniAtmCHECs
    		Counter,
    	    wfAtmUniAtmNullCells
    		Counter,
    	    wfAtmUniAtmMisdeliveredCells
    		Counter,
    	    wfAtmUniAtmReceives
    		Counter,
    	    wfAtmUniAtmTransmits
    		Counter,
    	    wfAtmUniAtmLineNumber
    		INTEGER,
    	    wfAtmUniAtmLLIndex
    		INTEGER
        }

    wfAtmUniAtmCct OBJECT-TYPE
        SYNTAX	INTEGER
        ACCESS	read-only
        STATUS	mandatory
        DESCRIPTION
                "The ATM UNI port for which corresponds to the Wellfleet
                circuit number"
        ::= { wfAtmUniAtmEntry 1 }

    wfAtmUniAtmNoBuffers OBJECT-TYPE
        SYNTAX	Counter
        ACCESS	read-only
        STATUS	mandatory
        DESCRIPTION
                "Received ATM cells discarded due to the lack of
                available cell buffers"
        ::= { wfAtmUniAtmEntry 2 }

    wfAtmUniAtmHECs OBJECT-TYPE
        SYNTAX	Counter
        ACCESS	read-only
        STATUS	mandatory
        DESCRIPTION
                "Received ATM cells discarded due to an uncorrected
                HEC"
        ::= { wfAtmUniAtmEntry 3 }

    wfAtmUniAtmCHECs OBJECT-TYPE
        SYNTAX	Counter
        ACCESS	read-only
        STATUS	mandatory
        DESCRIPTION
                "Received ATM cells for which a HEC error was detected
                and corrected"
        ::= { wfAtmUniAtmEntry 4 }

    wfAtmUniAtmNullCells OBJECT-TYPE
        SYNTAX	Counter
        ACCESS	read-only
        STATUS	mandatory
        DESCRIPTION
                "Received Null (unassigned , empty) cells"
        ::= { wfAtmUniAtmEntry 5 }

    wfAtmUniAtmMisdeliveredCells OBJECT-TYPE
        SYNTAX	Counter
        ACCESS	read-only
        STATUS	mandatory
        DESCRIPTION
                "Received cells with an invalid VPI/VCI and were discarded"
        ::= { wfAtmUniAtmEntry 6 }

    wfAtmUniAtmReceives OBJECT-TYPE
        SYNTAX	Counter
        ACCESS	read-only
        STATUS	mandatory
        DESCRIPTION
                "Valid (non-null) ATM Cells received at this layer and passed
                up"
        ::= { wfAtmUniAtmEntry 7 }

    wfAtmUniAtmTransmits OBJECT-TYPE
        SYNTAX	Counter
        ACCESS	read-only
        STATUS	mandatory
        DESCRIPTION
                "Valid (non-null) ATM Cells transmitted at this layer and passed
                down to the PLCP layer"
        ::= { wfAtmUniAtmEntry 8 }

    wfAtmUniAtmLineNumber OBJECT-TYPE
        SYNTAX	INTEGER
        ACCESS	read-only
        STATUS	mandatory
        DESCRIPTION
                "Instance identifier. This value corresponds to the line number
                of the Wellfleet router."
        ::= { wfAtmUniAtmEntry 9 }

    wfAtmUniAtmLLIndex OBJECT-TYPE
        SYNTAX	INTEGER
        ACCESS	read-only
        STATUS	mandatory
        DESCRIPTION
                "Instance identifier. This value corresponds to the port's llindex.
                The Lower layer index uniquely identifies the lower
                layer in cases where the lower layer may be something other than the
                physical layer."
        ::= { wfAtmUniAtmEntry 10 }

    wfAtmVbrTable OBJECT-TYPE
        SYNTAX	SEQUENCE OF WfAtmVbrEntry
        ACCESS	not-accessible
        STATUS	mandatory
        DESCRIPTION
                "The ATM VBR Table - CSU/DSU Resident
                The ATM Variable Bit Rate (VBR) object is one of several types
                of ATM Adaptation Layer (AAL) objects.
                The ATM VBR object reflects information about a VBR service
                carried by an ATM UNI on behalf of a DTE interface (e.g. a DXI).
                In particular, it contains both configuration and performance
                information about the Segmentation and Reassembly (SAR) sublayer
                and the Convergence Sublayer (CS).
                Each instance of the VBR object has only one corresponding DTE
                interface, and only one corresponding ATM UNI, although it may
                correspond to several VPI/VCIs within a particular ATM UNI.
                The VBR object optionally keeps some information
                on a per-VPI/VCI basis.
                It should be noted that in the ATM VBR MIB, the receive (transmit)
                direction refers to data received from (transmitted to)
                the ATM UNI interface.

                ** For DL200 and DL3200 DSUs, there is only one ATM UNI per DSU
                ** and only one AAL object (specifically VBR) per ATM UNI.
                ** For these products, the DSU does not perform the
                ** integrity checks for the VBR CS layer, and thus will not
                ** provide all variables for the VBR CS table.  The Router/Host
                ** is expected to perform these checks and provide these variables.
                "
        ::= { wfAtmGroup 8 }

    wfAtmVbrEntry OBJECT-TYPE
        SYNTAX	WfAtmVbrEntry
        ACCESS	not-accessible
        STATUS	mandatory
        DESCRIPTION
                "per linenumber/llindex VBR AAL objects -
                wfAtmVbrLineNumber and wfAtmVbrLLIndex corresponds to
                Wellfleet  linenumber/llindex number"
        INDEX	{ wfAtmVbrLineNumber,
    		  wfAtmVbrLLIndex }
        ::= { wfAtmVbrTable 1 }

    WfAtmVbrEntry ::= SEQUENCE {
    	    wfAtmVbrCct
    		INTEGER,
    	    wfAtmVbrAtmUni
    		OBJECT IDENTIFIER,
    	    wfAtmVbrDxi
    		OBJECT IDENTIFIER,
    	    wfAtmVbrSeconds
    		Counter,
    	    wfAtmVbrLineNumber
    		INTEGER,
    	    wfAtmVbrLLIndex
    		INTEGER
        }

    wfAtmVbrCct OBJECT-TYPE
        SYNTAX	INTEGER
        ACCESS	read-only
        STATUS	mandatory
        DESCRIPTION
                "Identifies the ATM VBR object which corresponds to the
                Wellfleet circuit number"
        ::= { wfAtmVbrEntry 1 }

    wfAtmVbrAtmUni OBJECT-TYPE
        SYNTAX	OBJECT IDENTIFIER
        ACCESS	read-only
        STATUS	mandatory
        DESCRIPTION
                "Identifies the OID of the first object in the ATM UNI
                MIB corresponding to this ATM VBR-AAL"
        ::= { wfAtmVbrEntry 2 }

    wfAtmVbrDxi OBJECT-TYPE
        SYNTAX	OBJECT IDENTIFIER
        ACCESS	read-only
        STATUS	mandatory
        DESCRIPTION
                "Identifies the DXI MIB corresponding to this ATM VBR-AAL.
                There is only one AAL currently for the DXI application."
        ::= { wfAtmVbrEntry 3 }

    wfAtmVbrSeconds OBJECT-TYPE
        SYNTAX	Counter
        ACCESS	read-only
        STATUS	mandatory
        DESCRIPTION
                "The count of seconds elapsed since event counting
                began or since the counters were last cleared.  The
                implementation may optionally allow this variable to
                be set.  If set, the set value is ignored, and this
                variable and all other event counters for this
                object are reset to zero."
        ::= { wfAtmVbrEntry 4 }

    wfAtmVbrLineNumber OBJECT-TYPE
        SYNTAX	INTEGER
        ACCESS	read-only
        STATUS	mandatory
        DESCRIPTION
                "Instance identifier. This value corresponds to the line number
                of the Wellfleet router."
        ::= { wfAtmVbrEntry 5 }

    wfAtmVbrLLIndex OBJECT-TYPE
        SYNTAX	INTEGER
        ACCESS	read-only
        STATUS	mandatory
        DESCRIPTION
                "Instance identifier. This value corresponds to the port's llindex.
                The Lower layer index uniquely identifies the lower
                layer in cases where the lower layer may be something other than the
                physical layer."
        ::= { wfAtmVbrEntry 6 }

    wfAtmVbrSarTable OBJECT-TYPE
        SYNTAX	SEQUENCE OF WfAtmVbrSarEntry
        ACCESS	not-accessible
        STATUS	mandatory
        DESCRIPTION
                "The ATM VBR SAR Table CSU/DSU Resident
                This table contains ATM VBR-AAL, SAR Layer parameters,
                the entry per ATM VBR-AAL object. The counts maintained
                in this table are totals for the VBR, across all
                VPI/VCIs within the VBR."
        ::= { wfAtmGroup 9 }

    wfAtmVbrSarEntry OBJECT-TYPE
        SYNTAX	WfAtmVbrSarEntry
        ACCESS	not-accessible
        STATUS	mandatory
        DESCRIPTION
                "per linenumber/llindex VBR AAL SAR sublayer objects -
                wfAtmSarLineNumber and wfAtmSarLLIndex corresponds to
                Wellfleet  linenumber/llindex number"
        INDEX	{ wfAtmVbrSarLineNumber,
    		  wfAtmVbrSarLLIndex }
        ::= { wfAtmVbrSarTable 1 }

    WfAtmVbrSarEntry ::= SEQUENCE {
    	    wfAtmVbrSarCct
    		INTEGER,
    	    wfAtmVbrSarAssemblyTimer
    		INTEGER,
    	    wfAtmVbrSarCrc10Errors
    		Counter,
    	    wfAtmVbrSarCellMidErrors
    		Counter,
    	    wfAtmVbrSarCsPduSizeTooBigErrors
    		Counter,
    	    wfAtmVbrSarNoBufferErrors
    		Counter,
    	    wfAtmVbrSarComNoProcessErrors
    		Counter,
    	    wfAtmVbrSarEomNoProcessErrors
    		Counter,
    	    wfAtmVbrSarCellSequenceErrors
    		Counter,
    	    wfAtmVbrSarCellLengthErrors
    		Counter,
    	    wfAtmVbrSarBomBeforeEomErrors
    		Counter,
    	    wfAtmVbrSarTimeouts
    		Counter,
    	    wfAtmVbrSarLengthExceeds
    		Counter,
    	    wfAtmVbrSarReceives
    		Counter,
    	    wfAtmVbrSarTransmits
    		Counter,
    	    wfAtmVbrSarLineNumber
    		INTEGER,
    	    wfAtmVbrSarLLIndex
    		INTEGER
        }

    wfAtmVbrSarCct OBJECT-TYPE
        SYNTAX	INTEGER
        ACCESS	read-only
        STATUS	mandatory
        DESCRIPTION
                "identifies the VBR_SAR object which corresponds to the
                Wellfleet circuit number"
        ::= { wfAtmVbrSarEntry 1 }

    wfAtmVbrSarAssemblyTimer OBJECT-TYPE
        SYNTAX	INTEGER(1..65535)
        ACCESS	read-only
        STATUS	mandatory
        DESCRIPTION
                "The maximum time period (milliseconds) allowed for CS_PDU
                assembly process to complete.  This is the time between
                receipt of a BOM and receipt of an EOM SAR_PDU."
        ::= { wfAtmVbrSarEntry 2 }

    wfAtmVbrSarCrc10Errors OBJECT-TYPE
        SYNTAX	Counter
        ACCESS	read-only
        STATUS	mandatory
        DESCRIPTION
                "The count of received SAR_PDUs discarded due to CRC10 error"
        ::= { wfAtmVbrSarEntry 3 }

    wfAtmVbrSarCellMidErrors OBJECT-TYPE
        SYNTAX	Counter
        ACCESS	read-only
        STATUS	mandatory
        DESCRIPTION
                "The count of received SAR_PDUs discarded due to an invalid
                MID field value"
        ::= { wfAtmVbrSarEntry 4 }

    wfAtmVbrSarCsPduSizeTooBigErrors OBJECT-TYPE
        SYNTAX	Counter
        ACCESS	read-only
        STATUS	mandatory
        DESCRIPTION
                "The count of received SAR_PDUs discarded due to CS_PDU
                size is too big . NOTE: This attribute needs to be moved to
                router based CS object."
        ::= { wfAtmVbrSarEntry 5 }

    wfAtmVbrSarNoBufferErrors OBJECT-TYPE
        SYNTAX	Counter
        ACCESS	read-only
        STATUS	mandatory
        DESCRIPTION
                "No CS_PDU assembly buffer space"
        ::= { wfAtmVbrSarEntry 6 }

    wfAtmVbrSarComNoProcessErrors OBJECT-TYPE
        SYNTAX	Counter
        ACCESS	read-only
        STATUS	mandatory
        DESCRIPTION
                "Received COM SAR_PDUs discarded due to lack of an active
                CS_PDU assembly process"
        ::= { wfAtmVbrSarEntry 7 }

    wfAtmVbrSarEomNoProcessErrors OBJECT-TYPE
        SYNTAX	Counter
        ACCESS	read-only
        STATUS	mandatory
        DESCRIPTION
                "Received EOM SAR_PDUs discarded due to lack of an active
                CS_PDU assembly process"
        ::= { wfAtmVbrSarEntry 8 }

    wfAtmVbrSarCellSequenceErrors OBJECT-TYPE
        SYNTAX	Counter
        ACCESS	read-only
        STATUS	mandatory
        DESCRIPTION
                "The count of active CS_PDU assembly processes
                closed (aborted, accumulation discarded) due to
                detecting a SAR sequence number error in a
                received SAR_PDU."
        ::= { wfAtmVbrSarEntry 9 }

    wfAtmVbrSarCellLengthErrors OBJECT-TYPE
        SYNTAX	Counter
        ACCESS	read-only
        STATUS	mandatory
        DESCRIPTION
                "The count of active CS_PDU assembly processes
                closed (aborted, accumulation discarded) due to
                detecting a length field error in a
                received SAR_PDU."
        ::= { wfAtmVbrSarEntry 10 }

    wfAtmVbrSarBomBeforeEomErrors OBJECT-TYPE
        SYNTAX	Counter
        ACCESS	read-only
        STATUS	mandatory
        DESCRIPTION
                "The count of active CS_PDU assembly processes
                closed (aborted, accumulation discarded) due to
                receiving a new BOM or SSM SAR_PDU for the
                same VPI/VCI (and MID) before receiving the
                EOM SAR_PDU."
        ::= { wfAtmVbrSarEntry 11 }

    wfAtmVbrSarTimeouts OBJECT-TYPE
        SYNTAX	Counter
        ACCESS	read-only
        STATUS	mandatory
        DESCRIPTION
                "The count of active CS_PDU assembly processes
                closed (aborted, accumulation discarded) due to
                expiration of the assembly timer."
        ::= { wfAtmVbrSarEntry 12 }

    wfAtmVbrSarLengthExceeds OBJECT-TYPE
        SYNTAX	Counter
        ACCESS	read-only
        STATUS	mandatory
        DESCRIPTION
                "The count of active CS_PDU assembly processes
                closed (aborted, accumulation discarded) due to
                receiving more SAR_PDUs (and their payloads)
                than will fit in the CS_PDU assembly buffer."
        ::= { wfAtmVbrSarEntry 13 }

    wfAtmVbrSarReceives OBJECT-TYPE
        SYNTAX	Counter
        ACCESS	read-only
        STATUS	mandatory
        DESCRIPTION
                "The count of received SAR_PDUs (all types,
                i.e. BOM, COM, EOM, SSM) successfully
                accumulated into a CS_PDU assembly buffer."
        ::= { wfAtmVbrSarEntry 14 }

    wfAtmVbrSarTransmits OBJECT-TYPE
        SYNTAX	Counter
        ACCESS	read-only
        STATUS	mandatory
        DESCRIPTION
                "The count of SAR_PDUs (all types, i.e. BOM,
                COM, EOM, SSM) transmitted to the ATM layer
                from a CS_PDU segmentation process."
        ::= { wfAtmVbrSarEntry 15 }

    wfAtmVbrSarLineNumber OBJECT-TYPE
        SYNTAX	INTEGER
        ACCESS	read-only
        STATUS	mandatory
        DESCRIPTION
                "Instance identifier. This value corresponds to the line number
                of the Wellfleet router."
        ::= { wfAtmVbrSarEntry 16 }

    wfAtmVbrSarLLIndex OBJECT-TYPE
        SYNTAX	INTEGER
        ACCESS	read-only
        STATUS	mandatory
        DESCRIPTION
                "Instance identifier. This value corresponds to the port's llindex.
                The Lower layer index uniquely identifies the lower layer in
                cases where the lower layer may be something other than the
                physical layer."
        ::= { wfAtmVbrSarEntry 17 }

    wfAtmVbrCsTable OBJECT-TYPE
        SYNTAX	SEQUENCE OF WfAtmVbrCsEntry
        ACCESS	not-accessible
        STATUS	mandatory
        DESCRIPTION
                "The ATM VBR CS Table - Router Resident
                This table contains ATM VBR-AAL, CS Layer parameters,
                one entry per ATM VBR-AAL object.  The counts maintained
                in this table are totals for the VBR, across all
                VPI/VCIs within the VBR."
        ::= { wfAtmGroup 11 }

    wfAtmVbrCsEntry OBJECT-TYPE
        SYNTAX	WfAtmVbrCsEntry
        ACCESS	not-accessible
        STATUS	mandatory
        DESCRIPTION
                "per linenumber/llindex VBR_CS objects -
                wfAtmVbrCsLineNumber and wfAtmVbrCsLLIndex corresponds to
                Wellfleet  linenumber/llindex number"
        INDEX	{ wfAtmVbrCsLineNumber,
    		  wfAtmVbrCsLLIndex }
        ::= { wfAtmVbrCsTable 1 }

    WfAtmVbrCsEntry ::= SEQUENCE {
    	    wfAtmVbrCsCct
    		INTEGER,
    	    wfAtmVbrCsBETagMismatches
    		Counter,
    	    wfAtmVbrCsLengthMismatches
    		Counter,
    	    wfAtmVbrCsMisdeliveredPdus
    		Counter,
    	    wfAtmVbrCsReceives
    		Counter,
    	    wfAtmVbrCsTransmits
    		Counter,
    	    wfAtmVbrCsLineNumber
    		INTEGER,
    	    wfAtmVbrCsLLIndex
    		INTEGER
        }

    wfAtmVbrCsCct OBJECT-TYPE
        SYNTAX	INTEGER
        ACCESS	read-only
        STATUS	mandatory
        DESCRIPTION
                "Identifies the VBR_CS object which corresponds to the Wellfleet
                circuit number"
        ::= { wfAtmVbrCsEntry 1 }

    wfAtmVbrCsBETagMismatches OBJECT-TYPE
        SYNTAX	Counter
        ACCESS	read-only
        STATUS	mandatory
        DESCRIPTION
                "The count of received CS_PDUs discarded due to a mismatch when
                comparing the BETag fields in the CS_PDU header and trailer."
        ::= { wfAtmVbrCsEntry 2 }

    wfAtmVbrCsLengthMismatches OBJECT-TYPE
        SYNTAX	Counter
        ACCESS	read-only
        STATUS	mandatory
        DESCRIPTION
                "The count of received CS_PDUs discarded due to a mismatch when
                comparing the CS_PDU header BASize field, the CS_PDU trailer length
                field and the actual length of the CS_PDU received."
        ::= { wfAtmVbrCsEntry 3 }

    wfAtmVbrCsMisdeliveredPdus OBJECT-TYPE
        SYNTAX	Counter
        ACCESS	read-only
        STATUS	mandatory
        DESCRIPTION
                "The count of received SAR_PDUs discarded due to an invalid
                VPI/VCI detected at this layer."
        ::= { wfAtmVbrCsEntry 4 }

    wfAtmVbrCsReceives OBJECT-TYPE
        SYNTAX	Counter
        ACCESS	read-only
        STATUS	mandatory
        DESCRIPTION
                "The count of the valid CS_PDUs received from the SAR layer and
                passed on to the next upper layer for further processing."
        ::= { wfAtmVbrCsEntry 5 }

    wfAtmVbrCsTransmits OBJECT-TYPE
        SYNTAX	Counter
        ACCESS	read-only
        STATUS	mandatory
        DESCRIPTION
                "The count of CS_PDUs received from upper layers and sent to the
                SAR layer for segmentation and transmission"
        ::= { wfAtmVbrCsEntry 6 }

    wfAtmVbrCsLineNumber OBJECT-TYPE
        SYNTAX	INTEGER
        ACCESS	read-only
        STATUS	mandatory
        DESCRIPTION
                "Instance identifier. This value corresponds to the line number
                of the Wellfleet router."
        ::= { wfAtmVbrCsEntry 7 }

    wfAtmVbrCsLLIndex OBJECT-TYPE
        SYNTAX	INTEGER
        ACCESS	read-only
        STATUS	mandatory
        DESCRIPTION
                "Instance identifier. This value corresponds to the port's
                llindex number. The Lower layer index uniquely identifies the
                lower layer in cases where the lower layer may be something other
                than the physical layer."
        ::= { wfAtmVbrCsEntry 8 }

    wfAtmVbrCsVciTable OBJECT-TYPE
        SYNTAX	SEQUENCE OF WfAtmVbrCsVciEntry
        ACCESS	not-accessible
        STATUS	mandatory
        DESCRIPTION
                "The ATM VBR CS_VCI Table - Router Resident
                This table contains ATM VBR-AAL, CS Layer parameters,
                one entry per ATM VPI/VCI for which information has been
                recorded per ATM VBR-AAL object."
        ::= { wfAtmGroup 12 }

    wfAtmVbrCsVciEntry OBJECT-TYPE
        SYNTAX	WfAtmVbrCsVciEntry
        ACCESS	not-accessible
        STATUS	mandatory
        DESCRIPTION
                "per virtual circuit VBR_CS objects"
        INDEX	{ wfAtmVbrCsVciLineNumber,
    		  wfAtmVbrCsVciLLIndex,
    		  wfAtmVbrCsVciIndex }
        ::= { wfAtmVbrCsVciTable 1 }

    WfAtmVbrCsVciEntry ::= SEQUENCE {
    	    wfAtmVbrCsVciVbrCct
    		INTEGER,
    	    wfAtmVbrCsVciIndex
    		INTEGER,
    	    wfAtmVbrCsVciBETagMismatches
    		Counter,
    	    wfAtmVbrCsVciLengthMismatches
    		Counter,
    	    wfAtmVbrCsVciMisdeliveredPdus
    		Counter,
    	    wfAtmVbrCsVciReceives
    		Counter,
    	    wfAtmVbrCsVciTransmits
    		Counter,
    	    wfAtmVbrCsVciOctetReceives
    		Counter,
    	    wfAtmVbrCsVciOctetTransmits
    		Counter,
    	    wfAtmVbrCsVciLineNumber
    		INTEGER,
    	    wfAtmVbrCsVciLLIndex
    		INTEGER
        }

    wfAtmVbrCsVciVbrCct OBJECT-TYPE
        SYNTAX	INTEGER
        ACCESS	read-only
        STATUS	mandatory
        DESCRIPTION
                "Identifies the VBR_CS object which corresponds to the Wellfleet
                circuit number"
        ::= { wfAtmVbrCsVciEntry 1 }

    wfAtmVbrCsVciIndex OBJECT-TYPE
        SYNTAX	INTEGER(1..8388608)
        ACCESS	read-only
        STATUS	mandatory
        DESCRIPTION
                "Identifies the VPI/VCI object for which this entry
                contains information."
        ::= { wfAtmVbrCsVciEntry 2 }

    wfAtmVbrCsVciBETagMismatches OBJECT-TYPE
        SYNTAX	Counter
        ACCESS	read-only
        STATUS	mandatory
        DESCRIPTION
                "The count of received CSVCI_PDUs discarded due to a mismatch when
                comparing the BETag fields in the CSVCI_PDU header and trailer."
        ::= { wfAtmVbrCsVciEntry 3 }

    wfAtmVbrCsVciLengthMismatches OBJECT-TYPE
        SYNTAX	Counter
        ACCESS	read-only
        STATUS	mandatory
        DESCRIPTION
                "The count of received CSVCI_PDUs discarded due to a mismatch when
                comparing the CSVCI_PDU header BASize field, the CSVCI_PDU trailer
                length field and the actual length of the CSVCI_PDU received."
        ::= { wfAtmVbrCsVciEntry 4 }

    wfAtmVbrCsVciMisdeliveredPdus OBJECT-TYPE
        SYNTAX	Counter
        ACCESS	read-only
        STATUS	mandatory
        DESCRIPTION
                "The count of received SAR_PDUs discarded due to an invalid
                VPI/VCI detected at this layer."
        ::= { wfAtmVbrCsVciEntry 5 }

    wfAtmVbrCsVciReceives OBJECT-TYPE
        SYNTAX	Counter
        ACCESS	read-only
        STATUS	mandatory
        DESCRIPTION
                "The count of the valid CSVCI_PDUs received from the SAR layer and
                passed on to the next upper layer for further processing."
        ::= { wfAtmVbrCsVciEntry 6 }

    wfAtmVbrCsVciTransmits OBJECT-TYPE
        SYNTAX	Counter
        ACCESS	read-only
        STATUS	mandatory
        DESCRIPTION
                "The count of CSVCI_PDUs received from upper layers and sent to the
                SAR layer for segmentation and transmission"
        ::= { wfAtmVbrCsVciEntry 7 }

    wfAtmVbrCsVciOctetReceives OBJECT-TYPE
        SYNTAX	Counter
        ACCESS	read-only
        STATUS	mandatory
        DESCRIPTION
                "The octet count of the valid CSVCI_PDUs received from the
                SAR layer and passed on to the next upper layer for further
                 processing."
        ::= { wfAtmVbrCsVciEntry 8 }

    wfAtmVbrCsVciOctetTransmits OBJECT-TYPE
        SYNTAX	Counter
        ACCESS	read-only
        STATUS	mandatory
        DESCRIPTION
                "The count of CSVCI_PDUs received from upper layers and sent to the
                SAR layer for segmentation and transmission"
        ::= { wfAtmVbrCsVciEntry 9 }

    wfAtmVbrCsVciLineNumber OBJECT-TYPE
        SYNTAX	INTEGER
        ACCESS	read-only
        STATUS	mandatory
        DESCRIPTION
                "Instance identifier. This value corresponds to the line number
                of the Wellfleet router."
        ::= { wfAtmVbrCsVciEntry 10 }

    wfAtmVbrCsVciLLIndex OBJECT-TYPE
        SYNTAX	INTEGER
        ACCESS	read-only
        STATUS	mandatory
        DESCRIPTION
                "Instance identifier. This value corresponds to the port's
                llindex number. The Lower layer index uniquely identifies the
                lower layer in cases where the lower layer may be something other
                than the physical layer."
        ::= { wfAtmVbrCsVciEntry 11 }

    wfAtmMpeTable OBJECT-TYPE
        SYNTAX	SEQUENCE OF WfAtmMpeEntry
        ACCESS	not-accessible
        STATUS	mandatory
        DESCRIPTION
                "The ATM MPE Table - Router Resident
                This table contains ATM DXI MPE Layer parameters,
                 one entry per ATM Circuit.The counts maintained
                 in this table are totals for the MPE Layer, across all
                 VPI/VCIs."
        ::= { wfAtmGroup 13 }

    wfAtmMpeEntry OBJECT-TYPE
        SYNTAX	WfAtmMpeEntry
        ACCESS	not-accessible
        STATUS	mandatory
        DESCRIPTION
                "per circuit MPE objects - wfAtmMpeIndex
                corresponds to Wellfleet circuit number"
        INDEX	{ wfAtmMpeIndex }
        ::= { wfAtmMpeTable 1 }

    WfAtmMpeEntry ::= SEQUENCE {
    	    wfAtmMpeIndex
    		INTEGER,
    	    wfAtmMpeInvalidNlpids
    		Counter,
    	    wfAtmMpeInvalidPids
    		Counter,
    	    wfAtmMpeInvalidOuis
    		Counter,
    	    wfAtmMpeMisdeliveredPdus
    		Counter,
    	    wfAtmMpeUnsupportedControlFields
    		Counter,
    	    wfAtmMpeInvalidSAP
    		Counter
        }

    wfAtmMpeIndex OBJECT-TYPE
        SYNTAX	INTEGER(1..1024)
        ACCESS	read-only
        STATUS	mandatory
        DESCRIPTION
                "Identifies the MPE object for which this entry
                contains information.  This corresponds to the Wellfleet
                circuit number"
        ::= { wfAtmMpeEntry 1 }

    wfAtmMpeInvalidNlpids OBJECT-TYPE
        SYNTAX	Counter
        ACCESS	read-only
        STATUS	mandatory
        DESCRIPTION
                "The count of received MPE_PDUs discarded due to an unknown
                or unsupported NLPID"
        ::= { wfAtmMpeEntry 2 }

    wfAtmMpeInvalidPids OBJECT-TYPE
        SYNTAX	Counter
        ACCESS	read-only
        STATUS	mandatory
        DESCRIPTION
                "The count of received MPE_PDUs discarded due to an unknown
                or unsupported PID"
        ::= { wfAtmMpeEntry 3 }

    wfAtmMpeInvalidOuis OBJECT-TYPE
        SYNTAX	Counter
        ACCESS	read-only
        STATUS	mandatory
        DESCRIPTION
                "The count of received MPE_PDUs discarded due to an unknown
                or unsupported OUI"
        ::= { wfAtmMpeEntry 4 }

    wfAtmMpeMisdeliveredPdus OBJECT-TYPE
        SYNTAX	Counter
        ACCESS	read-only
        STATUS	mandatory
        DESCRIPTION
                "The count of received MPE_PDUs discarded due to an inactive
                SAP."
        ::= { wfAtmMpeEntry 5 }

    wfAtmMpeUnsupportedControlFields OBJECT-TYPE
        SYNTAX	Counter
        ACCESS	read-only
        STATUS	mandatory
        DESCRIPTION
                "The count of received MPE_PDUs discarded due to an unknown
                or unsupported Control field"
        ::= { wfAtmMpeEntry 6 }

    wfAtmMpeInvalidSAP OBJECT-TYPE
        SYNTAX	Counter
        ACCESS	read-only
        STATUS	mandatory
        DESCRIPTION
                "The cound of received MPE_PDUs discarded due to either a
                bad SSAP or DSAP (RFC1483)"
        ::= { wfAtmMpeEntry 7 }

    wfAtmPvcTable OBJECT-TYPE
        SYNTAX	SEQUENCE OF WfAtmPvcEntry
        ACCESS	not-accessible
        STATUS	mandatory
        DESCRIPTION
                "The ATM PVC Table - Router Resident
                This table contains Virtual Circuit configuration and stats parameters,
                one entry per ATM VPI/PVC for which information has been
                recorded."
        ::= { wfAtmGroup 14 }

    wfAtmPvcEntry OBJECT-TYPE
        SYNTAX	WfAtmPvcEntry
        ACCESS	not-accessible
        STATUS	mandatory
        DESCRIPTION
                "per virtual circuit  objects"
        INDEX	{ wfAtmPvcLineNumber,
    		  wfAtmPvcLLIndex,
    		  wfAtmPvcVpi,
    		  wfAtmPvcVci }
        ::= { wfAtmPvcTable 1 }

    WfAtmPvcEntry ::= SEQUENCE {
    	    wfAtmPvcDelete
    		INTEGER,
    	    wfAtmPvcCct
    		INTEGER,
    	    wfAtmPvcVpi
    		INTEGER,
    	    wfAtmPvcVci
    		INTEGER,
    	    wfAtmPvcReceives
    		Counter,
    	    wfAtmPvcTransmits
    		Counter,
    	    wfAtmPvcOctetReceives
    		Counter,
    	    wfAtmPvcOctetTransmits
    		Counter,
    	    wfAtmPvcMode
    		INTEGER,
    	    wfAtmPvcDirectAccessCct
    		INTEGER,
    	    wfAtmPvcState
    		INTEGER,
    	    wfAtmPvcMpeNull
    		INTEGER,
    	    wfAtmPvcCsNull
    		INTEGER,
    	    wfAtmPvcDisable
    		INTEGER,
    	    wfAtmPvcDrops
    		Counter,
    	    wfAtmPvcMulticast
    		INTEGER,
    	    wfAtmPvcLineNumber
    		INTEGER,
    	    wfAtmPvcLLIndex
    		INTEGER
        }

    wfAtmPvcDelete OBJECT-TYPE
        SYNTAX	INTEGER {
    		    created(1),
    		    deleted(2)
    		}
        ACCESS	read-write
        STATUS	mandatory
        DESCRIPTION
                "Used to create/delete an instance of this object.
                This action will result in a PVC being added or
                removed from service."
        DEFVAL	{ created }
        ::= { wfAtmPvcEntry 1 }

    wfAtmPvcCct OBJECT-TYPE
        SYNTAX	INTEGER
        ACCESS	read-only
        STATUS	mandatory
        DESCRIPTION
                "Identifies the object which corresponds to the Wellfleet
                circuit number"
        ::= { wfAtmPvcEntry 2 }

    wfAtmPvcVpi OBJECT-TYPE
        SYNTAX	INTEGER(0..255)
        ACCESS	read-only
        STATUS	mandatory
        DESCRIPTION
                "The VPI associated with this PVC"
        ::= { wfAtmPvcEntry 3 }

    wfAtmPvcVci OBJECT-TYPE
        SYNTAX	INTEGER(32..65535)
        ACCESS	read-only
        STATUS	mandatory
        DESCRIPTION
                "The VCI associated with this PVC"
        ::= { wfAtmPvcEntry 4 }

    wfAtmPvcReceives OBJECT-TYPE
        SYNTAX	Counter
        ACCESS	read-only
        STATUS	mandatory
        DESCRIPTION
                "The count of the valid PVC_PDUs received from the SAR layer and
                passed on to the next upper layer for further processing."
        ::= { wfAtmPvcEntry 5 }

    wfAtmPvcTransmits OBJECT-TYPE
        SYNTAX	Counter
        ACCESS	read-only
        STATUS	mandatory
        DESCRIPTION
                "The count of PVC_PDUs received from upper layers and sent to the
                SAR layer for segmentation and transmission"
        ::= { wfAtmPvcEntry 6 }

    wfAtmPvcOctetReceives OBJECT-TYPE
        SYNTAX	Counter
        ACCESS	read-only
        STATUS	mandatory
        DESCRIPTION
                "The octet count of the valid PVC_PDUs received from the SAR
                layer and passed on to the next upper layer for further
                 processing."
        ::= { wfAtmPvcEntry 7 }

    wfAtmPvcOctetTransmits OBJECT-TYPE
        SYNTAX	Counter
        ACCESS	read-only
        STATUS	mandatory
        DESCRIPTION
                "The octet count of PVC_PDUs received from upper layers and
                sent to the SAR layer for segmentation and transmission"
        ::= { wfAtmPvcEntry 8 }

    wfAtmPvcMode OBJECT-TYPE
        SYNTAX	INTEGER {
    		    groupaccess(1),
    		    hybridaccess(2),
    		    direct(3)
    		}
        ACCESS	read-write
        STATUS	mandatory
        DESCRIPTION
                "The mode of the given VC.
                GROUP - treats the VC as one of many vc's on a circuit.
                HYBRID - treats the VC as one of many vc's on a circuit for
                  protocol traffic, but as a separate circuit for bridging.
                DIRECT - treats the VC as a separate circuit for all applications."
        DEFVAL	{ groupaccess }
        ::= { wfAtmPvcEntry 9 }

    wfAtmPvcDirectAccessCct OBJECT-TYPE
        SYNTAX	INTEGER
        ACCESS	read-write
        STATUS	mandatory
        DESCRIPTION
                "Circuit number to use for this VC for hybrid or direct access
                routing"
        ::= { wfAtmPvcEntry 10 }

    wfAtmPvcState OBJECT-TYPE
        SYNTAX	INTEGER {
    		    up(1),
    		    down(2),
    		    init(3),
    		    notpresent(4)
    		}
        ACCESS	read-only
        STATUS	mandatory
        DESCRIPTION
                "Indicates the state of the PVC.
                The state indicates Not Present when the PVC has been
                configured but has not been initialized.  Init state indicates
                that the PVC is in the process of being initialized by the
                system.  Up state indicates that the PVC is operating
                normally.  Down state indicates that the PVC is
                disabled."
        DEFVAL	{ notpresent }
        ::= { wfAtmPvcEntry 11 }

    wfAtmPvcMpeNull OBJECT-TYPE
        SYNTAX	INTEGER {
    		    mpe1294(1),
    		    null(2),
    		    mpe1483(3)
    		}
        ACCESS	read-write
        STATUS	mandatory
        DESCRIPTION
                "Used to select Null, Multi-Protocol Encapsulation
                (RFC 1294) or Multi-Protocol Encapsulation (RFC 1483)
                layer for this PVC. Null is considered VC Based
                Multiplexing and is not supported for Bridging."
        DEFVAL	{ mpe1483 }
        ::= { wfAtmPvcEntry 12 }

    wfAtmPvcCsNull OBJECT-TYPE
        SYNTAX	INTEGER {
    		    aal34(1),
    		    null(2),
    		    aal5(3)
    		}
        ACCESS	read-write
        STATUS	mandatory
        DESCRIPTION
                "Used to configure the type of CS_PDU encapsulation supported on
                the ATM DXI PVC based on the ATM Forum's ATM DXI specification.
                This configuration is on a per Direct VC basis. The supported
                values are  AAL3/4, AAL5 and Null (no CS_PDU encapsulation). Null
                is a propriatary configurable value when no CS_PDU encapsulation
                is desired."
        DEFVAL	{ aal5 }
        ::= { wfAtmPvcEntry 13 }

    wfAtmPvcDisable OBJECT-TYPE
        SYNTAX	INTEGER {
    		    enabled(1),
    		    disabled(2)
    		}
        ACCESS	read-write
        STATUS	mandatory
        DESCRIPTION
                "Used to enable/disable a PVC"
        DEFVAL	{ enabled }
        ::= { wfAtmPvcEntry 14 }

    wfAtmPvcDrops OBJECT-TYPE
        SYNTAX	Counter
        ACCESS	read-only
        STATUS	mandatory
        DESCRIPTION
                "The total count of packets  dropped on this VC"
        ::= { wfAtmPvcEntry 15 }

    wfAtmPvcMulticast OBJECT-TYPE
        SYNTAX	INTEGER {
    		    unicast(1),
    		    multicast(2)
    		}
        ACCESS	read-write
        STATUS	mandatory
        DESCRIPTION
                "Indicates whether this VPI/VCI is used for multicast or
                single destination."
        DEFVAL	{ unicast }
        ::= { wfAtmPvcEntry 16 }

    wfAtmPvcLineNumber OBJECT-TYPE
        SYNTAX	INTEGER
        ACCESS	read-only
        STATUS	mandatory
        DESCRIPTION
                "Instance identifier. This value corresponds to the line number
                of the Wellfleet router."
        ::= { wfAtmPvcEntry 17 }

    wfAtmPvcLLIndex OBJECT-TYPE
        SYNTAX	INTEGER
        ACCESS	read-only
        STATUS	mandatory
        DESCRIPTION
                "Instance identifier. This value corresponds to the port's
                llindex number. The Lower layer index uniquely identifies the
                lower layer in cases where the lower layer may be something other
                than the physical layer."
        ::= { wfAtmPvcEntry 18 }

    wfAtmDxiTable OBJECT-TYPE
        SYNTAX	SEQUENCE OF WfAtmDxiEntry
        ACCESS	not-accessible
        STATUS	mandatory
        DESCRIPTION
                "The ATM DXI Table - An entry in this table is either resident in
                the Wellfleet MIB or in the Digital Link MIB via the SNMP Proxy.
                The Component attribute determines local or remote residency.

                The ATM Data Exchange Interface (DXI) object reflects
                information about an ATM DXI interface between an ATM DSU
                and a Router/Host.  In particular, it contains both
                configuration and performance information specific to the DXI
                (ATM) interface.
                Each DXI instance typically corresponds to several (ATM)
                DXIADDRs.  The DXI object optionally keeps some information
                on a per-DXIADDR basis.
                Each instance of the DXI object typically has only one
                corresponding ATM -AAL object, but the MIB has been
                structured so that a DXI may have more than one.
                It should be noted that in the DXI MIB, the receive (transmit)
                direction refers to data received from (transmitted to)
                the ATM interface.

                With a 23-bit DXIADDR, the range of valid DXIADDR index values is
                1 thru 2**23 inclusive.  Note that the 23-bit binary DXIADDR field
                (with values 0 thru 2**23-1) from the Frame Relay header must be
                incremented by one to yield the DXIADDR index for accessing the
                tables in the MIB.  The DXIADDR consisting of all zeros (with
                corresponding MIB index value of 1) is reserved for the DXI
                Local Management Interface (LMI) with the DSU.

                DxiAddr ::= INTEGER (1..8388608)

                 ** For DL200 and DL3200 DSUs, there is only one ATM DXI per DSU
                 ** and only one AAL object (specifically VBR) per ATM DXI.
                 ** For these products, the mapping between the DXI (Frame Relay)
                 ** DXIADDR and the ATM VPI/VCI is fixed.  The LMI DXIADDR has no
                 ** corresponding VPI/VCI.  Otherwise, the eight most significant
                 ** bits of the DXIADDR map into the the VPI (the eight most
                 ** significant bits of the VPI/VCI), the fifteen least
                 ** significant bits of the DXIADDR map into the fifteen least
                 ** significant bits of the VCI, and the most significant bit of
                 ** the VCI is set to zero."
        ::= { wfAtmGroup 15 }

    wfAtmDxiEntry OBJECT-TYPE
        SYNTAX	WfAtmDxiEntry
        ACCESS	not-accessible
        STATUS	mandatory
        DESCRIPTION
                "per linenumber/llindex ATM DXI objects -
                wfAtmDxiLineNumber and wfAtmDxiLLIndex corresponds to
                Wellfleet  linenumber/llindex number"
        INDEX	{ wfAtmDxiLineNumber,
    		  wfAtmDxiLLIndex,
    		  wfAtmDxiComponent }
        ::= { wfAtmDxiTable 1 }

    WfAtmDxiEntry ::= SEQUENCE {
    	    wfAtmDxiCct
    		INTEGER,
    	    wfAtmDxiComponent
    		INTEGER,
    	    wfAtmDxiMaxLmiPduLengthErrors
    		Counter,
    	    wfAtmDxiSeconds
    		Counter,
    	    wfAtmDxiDiscardedFrames
    		Counter,
    	    wfAtmDxiAbortedFrames
    		Counter,
    	    wfAtmDxiNonOctetAlignedFrames
    		Counter,
    	    wfAtmDxiTooLongFrames
    		Counter,
    	    wfAtmDxiTooShortFrames
    		Counter,
    	    wfAtmDxiFrameChecksumErrors
    		Counter,
    	    wfAtmDxiFrameHeaderErrors
    		Counter,
    	    wfAtmDxiValidFrameReceives
    		Counter,
    	    wfAtmDxiFrameTransmits
    		Counter,
    	    wfAtmDxiLineNumber
    		INTEGER,
    	    wfAtmDxiLLIndex
    		INTEGER
        }

    wfAtmDxiCct OBJECT-TYPE
        SYNTAX	INTEGER
        ACCESS	read-only
        STATUS	mandatory
        DESCRIPTION
                "Identifies the ATM DXI cct which corresponds to the Wellfleet
                circuit number"
        ::= { wfAtmDxiEntry 1 }

    wfAtmDxiComponent OBJECT-TYPE
        SYNTAX	INTEGER {
    		    router(1),
    		    csudsu(2)
    		}
        ACCESS	read-only
        STATUS	mandatory
        DESCRIPTION
                "Identifies the component where the ATM DXI parameters are
                resident - either the router or CSU/DSU."
        ::= { wfAtmDxiEntry 2 }

    wfAtmDxiMaxLmiPduLengthErrors OBJECT-TYPE
        SYNTAX	Counter
        ACCESS	read-only
        STATUS	mandatory
        DESCRIPTION
                "The maximum length of an LMI PDU, measured in octets"
        ::= { wfAtmDxiEntry 3 }

    wfAtmDxiSeconds OBJECT-TYPE
        SYNTAX	Counter
        ACCESS	read-only
        STATUS	mandatory
        DESCRIPTION
                "The count of seconds elapsed since event counting began
                or since the counters were last cleared. The implementation
                may optionally allow this variable to be set. If set, the set
                value is ignored , and this variable and all other event
                counters for this object are reset to zero."
        ::= { wfAtmDxiEntry 4 }

    wfAtmDxiDiscardedFrames OBJECT-TYPE
        SYNTAX	Counter
        ACCESS	read-only
        STATUS	mandatory
        DESCRIPTION
                "The count of received frames discarded due to lack of
                buffer space."
        ::= { wfAtmDxiEntry 5 }

    wfAtmDxiAbortedFrames OBJECT-TYPE
        SYNTAX	Counter
        ACCESS	read-only
        STATUS	mandatory
        DESCRIPTION
                "The count of the received frames aborted (and discarded) before
                the closing flag"
        ::= { wfAtmDxiEntry 6 }

    wfAtmDxiNonOctetAlignedFrames OBJECT-TYPE
        SYNTAX	Counter
        ACCESS	read-only
        STATUS	mandatory
        DESCRIPTION
                "The count of the received frames discarded due to not being octet
                aligned."
        ::= { wfAtmDxiEntry 7 }

    wfAtmDxiTooLongFrames OBJECT-TYPE
        SYNTAX	Counter
        ACCESS	read-only
        STATUS	mandatory
        DESCRIPTION
                "The count of the received frames discarded due to being longer
                than the maximum allowed frame length"
        ::= { wfAtmDxiEntry 8 }

    wfAtmDxiTooShortFrames OBJECT-TYPE
        SYNTAX	Counter
        ACCESS	read-only
        STATUS	mandatory
        DESCRIPTION
                "The count of the received frames discarded due to being shorter
                than the minimum allowed frame length (less than 6 octets long)"
        ::= { wfAtmDxiEntry 9 }

    wfAtmDxiFrameChecksumErrors OBJECT-TYPE
        SYNTAX	Counter
        ACCESS	read-only
        STATUS	mandatory
        DESCRIPTION
                "The count of the received frames discarded due to detected checksum
                error (CRC16)"
        ::= { wfAtmDxiEntry 10 }

    wfAtmDxiFrameHeaderErrors OBJECT-TYPE
        SYNTAX	Counter
        ACCESS	read-only
        STATUS	mandatory
        DESCRIPTION
                "The count of the received frames discarded due to detected frame
                relay header errors"
        ::= { wfAtmDxiEntry 11 }

    wfAtmDxiValidFrameReceives OBJECT-TYPE
        SYNTAX	Counter
        ACCESS	read-only
        STATUS	mandatory
        DESCRIPTION
                "The count of the valid frames received."
        ::= { wfAtmDxiEntry 12 }

    wfAtmDxiFrameTransmits OBJECT-TYPE
        SYNTAX	Counter
        ACCESS	read-only
        STATUS	mandatory
        DESCRIPTION
                "The count of CSVCI_PDUs received from upper layers and sent to the
                SAR layer for segmentation and transmission"
        ::= { wfAtmDxiEntry 13 }

    wfAtmDxiLineNumber OBJECT-TYPE
        SYNTAX	INTEGER
        ACCESS	read-only
        STATUS	mandatory
        DESCRIPTION
                "Instance identifier. This value corresponds to the line number
                of the Wellfleet router."
        ::= { wfAtmDxiEntry 14 }

    wfAtmDxiLLIndex OBJECT-TYPE
        SYNTAX	INTEGER
        ACCESS	read-only
        STATUS	mandatory
        DESCRIPTION
                "Instance identifier. This value corresponds to the port's
                llindex number. The Lower layer index uniquely identifies the
                lower layer in cases where the lower layer may be something other
                than the physical layer."
        ::= { wfAtmDxiEntry 15 }

    wfAtmDxiDxiAddrTable OBJECT-TYPE
        SYNTAX	SEQUENCE OF WfAtmDxiDxiAddrEntry
        ACCESS	not-accessible
        STATUS	mandatory
        DESCRIPTION
                "The ATM DXI DXIADDR Table - Router and CSU/DSU Resident
                This table contains ATM DXI parameters, one entry per DXI
                DXIADDR for which information has been recorded per DXI
                DXIADDR Layer. Since the DXIADDR consisting of all zeros (with
                corresponding MIB index value of 1) is reserved
                for the DXI Local Management Interface (LMI) with
                the DSU, there is always at least one entry in the
                table. "
        ::= { wfAtmGroup 16 }

    wfAtmDxiDxiAddrEntry OBJECT-TYPE
        SYNTAX	WfAtmDxiDxiAddrEntry
        ACCESS	not-accessible
        STATUS	mandatory
        DESCRIPTION
                "per DXIADDR ATM DXI objects"
        INDEX	{ wfAtmDxiDxiAddrLineNumber,
    		  wfAtmDxiDxiAddrLLIndex,
    		  wfAtmDxiDxiAddrDxiComponent,
    		  wfAtmDxiDxiAddrIndex }
        ::= { wfAtmDxiDxiAddrTable 1 }

    WfAtmDxiDxiAddrEntry ::= SEQUENCE {
    	    wfAtmDxiDxiAddrDxiCct
    		INTEGER,
    	    wfAtmDxiDxiAddrDxiComponent
    		INTEGER,
    	    wfAtmDxiDxiAddrIndex
    		INTEGER,
    	    wfAtmDxiDxiAddrAtmVbr
    		OBJECT IDENTIFIER,
    	    wfAtmDxiDxiAddrVpiVci
    		INTEGER,
    	    wfAtmDxiDxiAddrReceives
    		Counter,
    	    wfAtmDxiDxiAddrTransmits
    		Counter,
    	    wfAtmDxiDxiAddrLineNumber
    		INTEGER,
    	    wfAtmDxiDxiAddrLLIndex
    		INTEGER
        }

    wfAtmDxiDxiAddrDxiCct OBJECT-TYPE
        SYNTAX	INTEGER
        ACCESS	read-only
        STATUS	mandatory
        DESCRIPTION
                "Identifies the Atm Dxi object for which this entry
                contains information.  This attribute corresponds to the Wellfleet
                circuit number"
        ::= { wfAtmDxiDxiAddrEntry 1 }

    wfAtmDxiDxiAddrDxiComponent OBJECT-TYPE
        SYNTAX	INTEGER {
    		    router(1),
    		    csudsu(2)
    		}
        ACCESS	read-only
        STATUS	mandatory
        DESCRIPTION
                "Identifies the component where the ATM DXI parameters are
                resident - either the router or CSU/DSU."
        ::= { wfAtmDxiDxiAddrEntry 2 }

    wfAtmDxiDxiAddrIndex OBJECT-TYPE
        SYNTAX	INTEGER(1..8388608)
        ACCESS	read-only
        STATUS	mandatory
        DESCRIPTION
                "Identifies the DXIADDR object for which this entry
                contains information."
        ::= { wfAtmDxiDxiAddrEntry 3 }

    wfAtmDxiDxiAddrAtmVbr OBJECT-TYPE
        SYNTAX	OBJECT IDENTIFIER
        ACCESS	read-only
        STATUS	mandatory
        DESCRIPTION
                "The object identifier of the first object in the
                ATM VBR-AAL MIB which corresponds to this DXIADDR
                of this DXI port.  If there is only one ATM VBR-AAL
                object associated with this DXI object, then the
                LMI DXIADDR entry in this table will have a valid
                value for this variable, even though the
                LMI DXIADDR has no valid VPI/VCI value.'"
        ::= { wfAtmDxiDxiAddrEntry 4 }

    wfAtmDxiDxiAddrVpiVci OBJECT-TYPE
        SYNTAX	INTEGER(1..8388608)
        ACCESS	read-only
        STATUS	mandatory
        DESCRIPTION
                "The VPI/VCI of the ATM UNI of the ATM VBR-AAL
                object which corresponds to this DXIADDR of this
                DXI port.  For the LMI DXIADDR there is no valid
                VPI/VCI value."
        ::= { wfAtmDxiDxiAddrEntry 5 }

    wfAtmDxiDxiAddrReceives OBJECT-TYPE
        SYNTAX	Counter
        ACCESS	read-only
        STATUS	mandatory
        DESCRIPTION
                "The count of the valid frames received from the next lower
                layer and passed on to the next upper layer for further
                processing."
        ::= { wfAtmDxiDxiAddrEntry 6 }

    wfAtmDxiDxiAddrTransmits OBJECT-TYPE
        SYNTAX	Counter
        ACCESS	read-only
        STATUS	mandatory
        DESCRIPTION
                "The count of frames received from upper layers and sent to the
                next lower layer for transmission"
        ::= { wfAtmDxiDxiAddrEntry 7 }

    wfAtmDxiDxiAddrLineNumber OBJECT-TYPE
        SYNTAX	INTEGER
        ACCESS	read-only
        STATUS	mandatory
        DESCRIPTION
                "Instance identifier. This value corresponds to the line number
                of the Wellfleet router."
        ::= { wfAtmDxiDxiAddrEntry 8 }

    wfAtmDxiDxiAddrLLIndex OBJECT-TYPE
        SYNTAX	INTEGER
        ACCESS	read-only
        STATUS	mandatory
        DESCRIPTION
                "Instance identifier. This value corresponds to the port's
                llindex number. The Lower layer index uniquely identifies the
                lower layer in cases where the lower layer may be something other
                than the physical layer."
        ::= { wfAtmDxiDxiAddrEntry 9 }

    wfAtmInterfaceConfTable OBJECT-TYPE
        SYNTAX	SEQUENCE OF WfAtmInterfaceConfEntry
        ACCESS	not-accessible
        STATUS	mandatory
        DESCRIPTION
                "This table contains ATM local interface configuration parameters,
                one entry per ATM interface port, beyond those supported using the
                ifTable."
        ::= { wfAtmCommonGroup 1 }

    wfAtmInterfaceConfEntry OBJECT-TYPE
        SYNTAX	WfAtmInterfaceConfEntry
        ACCESS	not-accessible
        STATUS	mandatory
        DESCRIPTION
                "Entry definition."
        INDEX	{ wfAtmInterfaceConfIndex }
        ::= { wfAtmInterfaceConfTable 1 }

    WfAtmInterfaceConfEntry ::= SEQUENCE {
    	    wfAtmInterfaceConfDelete
    		INTEGER,
    	    wfAtmInterfaceConfIndex
    		INTEGER,
    	    wfAtmInterfaceAdminStatus
    		INTEGER,
    	    wfAtmInterfaceOperStatus
    		INTEGER,
    	    wfAtmInterfaceMaxVpcs
    		INTEGER,
    	    wfAtmInterfaceMaxVccs
    		INTEGER,
    	    wfAtmInterfaceConfVpcs
    		INTEGER,
    	    wfAtmInterfaceConfVccs
    		INTEGER,
    	    wfAtmInterfaceMaxActiveVpiBits
    		INTEGER,
    	    wfAtmInterfaceMaxActiveVciBits
    		INTEGER,
    	    wfAtmInterfaceIlmiVpi
    		INTEGER,
    	    wfAtmInterfaceIlmiVci
    		INTEGER,
    	    wfAtmInterfaceAddressType
    		INTEGER,
    	    wfAtmInterfaceCct
    		INTEGER,
    	    wfAtmInterfaceDrops
    		Counter,
    	    wfAtmInterfaceSigEnable
    		INTEGER,
    	    wfAtmInterfaceDebug
    		INTEGER,
    	    wfAtmInterfaceUseHwMacAddr
    		INTEGER,
    	    wfAtmInterfaceHwMacOverride
    		OCTET STRING,
            wfAtmServicePqOverride
                INTEGER
        }

    wfAtmInterfaceConfDelete OBJECT-TYPE
        SYNTAX	INTEGER {
    		    create(1),
    		    delete(2)
    		}
        ACCESS	read-write
        STATUS	mandatory
        DESCRIPTION
                "Create/delete MIB instance parameter."
        DEFVAL	{ create }
        ::= { wfAtmInterfaceConfEntry 1 }

    wfAtmInterfaceConfIndex OBJECT-TYPE
        SYNTAX	INTEGER
        ACCESS	read-only
        STATUS	mandatory
        DESCRIPTION
                "Uniquely identifies the interface (port) that contains the
                appropriate management information."
        ::= { wfAtmInterfaceConfEntry 2 }

    wfAtmInterfaceAdminStatus OBJECT-TYPE
        SYNTAX	INTEGER {
    		    up(1),
    		    down(2)
    		}
        ACCESS	read-write
        STATUS	mandatory
        DESCRIPTION
                "Specifies the desired administrative state of the Interface. The up and
                down states indicate that the traffic flow is enabled and disabled
                respectively for the VCL."
        DEFVAL	{ up }
        ::= { wfAtmInterfaceConfEntry 3 }

    wfAtmInterfaceOperStatus OBJECT-TYPE
        SYNTAX	INTEGER {
    		    up(1),
    		    down(2),
    		    init(3),
    		    notpresent(4)
    		}
        ACCESS	read-only
        STATUS	mandatory
        DESCRIPTION
                "Indicates the current operational status of the Interface. The up and
                down states indicate that the Interface is currently operational, or not
                operational, respectively. The Init state indicates the status
                of the Interface is in the process of being initialized and has not yet
                completed. The 'Not Present' state indicates a problem with that
                Interface and is not able to bring the Interface up."
        DEFVAL	{ notpresent }
        ::= { wfAtmInterfaceConfEntry 4 }

    wfAtmInterfaceMaxVpcs OBJECT-TYPE
        SYNTAX	INTEGER(1..4096)
        ACCESS	read-write
        STATUS	mandatory
        DESCRIPTION
                "The maximum number of VPCs supported at the ATM interface."
        DEFVAL	{ 256 }
        ::= { wfAtmInterfaceConfEntry 5 }

    wfAtmInterfaceMaxVccs OBJECT-TYPE
        SYNTAX	INTEGER(1..65536)
        ACCESS	read-write
        STATUS	mandatory
        DESCRIPTION
                "The maximum number of VCCs supported at the ATM interface."
        DEFVAL	{ 65536 }
        ::= { wfAtmInterfaceConfEntry 6 }

    wfAtmInterfaceConfVpcs OBJECT-TYPE
        SYNTAX	INTEGER
        ACCESS	read-only
        STATUS	mandatory
        DESCRIPTION
                "The number of VPCs configured for use at the ATM interface."
        ::= { wfAtmInterfaceConfEntry 7 }

    wfAtmInterfaceConfVccs OBJECT-TYPE
        SYNTAX	INTEGER
        ACCESS	read-only
        STATUS	mandatory
        DESCRIPTION
                "The number of VCCs configured for use at the ATM interface."
        ::= { wfAtmInterfaceConfEntry 8 }

    wfAtmInterfaceMaxActiveVpiBits OBJECT-TYPE
        SYNTAX	INTEGER(1..12)
        ACCESS	read-write
        STATUS	mandatory
        DESCRIPTION
                "The maximum number of active VPI bits configured for use at the
                ATM interface."
        DEFVAL	{ 8 }
        ::= { wfAtmInterfaceConfEntry 9 }

    wfAtmInterfaceMaxActiveVciBits OBJECT-TYPE
        SYNTAX	INTEGER(1..16)
        ACCESS	read-write
        STATUS	mandatory
        DESCRIPTION
                "The maximum number of active VCI bits configured for use at the
                ATM interface."
        DEFVAL	{ 16 }
        ::= { wfAtmInterfaceConfEntry 10 }

    wfAtmInterfaceIlmiVpi OBJECT-TYPE
        SYNTAX	INTEGER {
    		    default(1)
    		}
        ACCESS	read-write
        STATUS	mandatory
        DESCRIPTION
                "The VPI value of the VCC supporting the ILMI at this ATM interface.
                If the values of wfAtmInterfaceIlmiVpi and wfAtmInterfaceIlmiVci
                are both equal to zero then the ILMI is not supported at this ATM
                interface. Subract 1 from the default! (ILMI VPI = 0)."
        DEFVAL	{ default }
        ::= { wfAtmInterfaceConfEntry 11 }

    wfAtmInterfaceIlmiVci OBJECT-TYPE
        SYNTAX	INTEGER {
    		    default(16)
    		}
        ACCESS	read-write
        STATUS	mandatory
        DESCRIPTION
                "The VCI value of the VCC supporting the ILMI at this ATM interface.
                If the values of wfAtmInterfaceIlmiVpi and wfAtmInterfaceIlmiVci
                are both equal to zero then the ILMI is not supported at this ATM
                interface."
        DEFVAL	{ default }
        ::= { wfAtmInterfaceConfEntry 12 }

    wfAtmInterfaceAddressType OBJECT-TYPE
        SYNTAX	INTEGER {
    		    private(1),
    		    nsape164(2),
    		    nativee164(3),
    		    other(4)
    		}
        ACCESS	read-only
        STATUS	mandatory
        DESCRIPTION
                "The type of ATM address configured for use at the ATM interface."
        ::= { wfAtmInterfaceConfEntry 13 }

    wfAtmInterfaceCct OBJECT-TYPE
        SYNTAX	INTEGER
        ACCESS	read-only
        STATUS	mandatory
        DESCRIPTION
                "The Wellfleet circuit number of this entry"
        ::= { wfAtmInterfaceConfEntry 14 }

    wfAtmInterfaceDrops OBJECT-TYPE
        SYNTAX	Counter
        ACCESS	read-only
        STATUS	mandatory
        DESCRIPTION
                "The cumulative count of packet drops on this ATM Interface above the
                SSCS layer."
        ::= { wfAtmInterfaceConfEntry 15 }

    wfAtmInterfaceSigEnable OBJECT-TYPE
        SYNTAX	INTEGER {
    		    enabled(1),
    		    disabled(2)
    		}
        ACCESS	read-write
        STATUS	mandatory
        DESCRIPTION
                "Spawning of ATM Signalling by the Control gate is determined by this attr"
        DEFVAL	{ disabled }
        ::= { wfAtmInterfaceConfEntry 16 }

    wfAtmInterfaceDebug OBJECT-TYPE
        SYNTAX	INTEGER {
    		    disabled(1),
    		    msgs(2),
                    msgsIn(4),
                    msgsOut(8),
                    appMsgs(16),
                    drvMsgs(32),
                    trilMsgs(64),
                    pvcFsm(128),
                    svcFsm(256),
                    oam(512),
    		    all(2147483647)
    		}
        ACCESS	read-write
        STATUS	mandatory
        DESCRIPTION
                "This flag will enable certain debug messages depending on the value set.
                The values are as follows:

                 1 - disable debugging (default)
                 2 - enable Signalling Layer Manager inbound and outbound messages
                 4 - enable CC inbound messages
                 8 - enable CC outbound messages
                 16 - enable CC<->APP messages
                 32 - enable CC<->DRV messages
                 64 - enable CC<->TRILL messages
                 128 - enable CC PVC Interface FSM messages
                 256 - enable CC PVC Interface FSM messages
                 4294967295 - All of the above"
        DEFVAL	{ disabled }
        ::= { wfAtmInterfaceConfEntry 17 }

    wfAtmInterfaceUseHwMacAddr OBJECT-TYPE
        SYNTAX	INTEGER {
    		    enabled(1),
    		    disabled(2)
    		}
        ACCESS	read-write
        STATUS	mandatory
        DESCRIPTION
                "If this is enabled, then the auto-generated ESI portion of
   		 the ATM address user suffix will be supplied by the hardware
   		 driver. If disabled, it will come from 
		 wfAtmInterfaceHwMacOverride."
        DEFVAL	{ enabled }
        ::= { wfAtmInterfaceConfEntry 18 }

    wfAtmInterfaceHwMacOverride OBJECT-TYPE
        SYNTAX	OCTET STRING
        ACCESS	read-write
        STATUS	mandatory
        DESCRIPTION
                "If wfAtmInterfaceUseHwMacAddr is disabled, this 48-bit Mac 
		 address will replace the hardware driver's address during
   		 auto-generation of the ESI portion of the ATM address user 
		 suffix."
        ::= { wfAtmInterfaceConfEntry 19 }

     wfAtmServicePqOverride OBJECT-TYPE
        SYNTAX  INTEGER {
                enabled (1),
                disabled(2)
                }
        ACCESS  read-write
        STATUS  mandatory
        DESCRIPTION
                " This value denotes whether driver level PQ is to be applied
                  to packets or driver decides to use the priority set by
                  service level PQ, if both service level and driver level PQ
                  is used."
        DEFVAL  { disabled }
        ::= { wfAtmInterfaceConfEntry 20}

    wfAtmServiceRecordTable OBJECT-TYPE
        SYNTAX	SEQUENCE OF WfAtmServiceRecordEntry
        ACCESS	not-accessible
        STATUS	mandatory
        DESCRIPTION
                "This table contains ATM service record configuration parameters,
                one entry per ATM Wellfleet cct."
        ::= { wfAtmCommonGroup 2 }

    wfAtmServiceRecordEntry OBJECT-TYPE
        SYNTAX	WfAtmServiceRecordEntry
        ACCESS	not-accessible
        STATUS	mandatory
        DESCRIPTION
                "Entry definition."
        INDEX	{ wfAtmServiceRecordIndex,
    		  wfAtmServiceRecordCct }
        ::= { wfAtmServiceRecordTable 1 }

    WfAtmServiceRecordEntry ::= SEQUENCE {
    	    wfAtmServiceRecordDelete
    		INTEGER,
    	    wfAtmServiceRecordEnable
    		INTEGER,
    	    wfAtmServiceRecordIndex
    		INTEGER,
    	    wfAtmServiceRecordCct
    		INTEGER,
    	    wfAtmServiceRecordAalEncapsType
    		INTEGER,
    	    wfAtmServiceRecordState
    		INTEGER,
    	    wfAtmServiceRecordVcType
    		INTEGER,
    	    wfAtmServiceRecordNetworkPrefix
    		OCTET STRING,
    	    wfAtmServiceRecordUserSuffix
    		OCTET STRING,
    	    wfAtmServiceRecordAtmAddress
    		OCTET STRING,
    	    wfAtmServiceRecordFlag
    		INTEGER,
    	    wfAtmServiceRecordMtu
    		INTEGER,
            wfAtmServiceRecordLossPriorityPolicy
                INTEGER,
            wfAtmServiceRecordDebug
                INTEGER,
            wfAtmServiceRecordName
                DisplayString,
            wfAtmServiceRecordWanSvcRoutingMode
                INTEGER
        }

    wfAtmServiceRecordDelete OBJECT-TYPE
        SYNTAX	INTEGER {
    		    create(1),
    		    delete(2)
    		}
        ACCESS	read-write
        STATUS	mandatory
        DESCRIPTION
                "Create/delete MIB instance parameter."
        DEFVAL	{ create }
        ::= { wfAtmServiceRecordEntry 1 }

    wfAtmServiceRecordEnable OBJECT-TYPE
        SYNTAX	INTEGER {
    		    enabled(1),
    		    disabled(2)
    		}
        ACCESS	read-write
        STATUS	mandatory
        DESCRIPTION
                "Enable/Disable MIB instance parameter."
        DEFVAL	{ enabled }
        ::= { wfAtmServiceRecordEntry 2 }

    wfAtmServiceRecordIndex OBJECT-TYPE
        SYNTAX	INTEGER
        ACCESS	read-only
        STATUS	mandatory
        DESCRIPTION
                "Uniquely identifies the interface (port) that contains the
                appropriate port information."
        ::= { wfAtmServiceRecordEntry 3 }

    wfAtmServiceRecordCct OBJECT-TYPE
        SYNTAX	INTEGER
        ACCESS	read-only
        STATUS	mandatory
        DESCRIPTION
                "The Wellfleet circuit number of this entry"
        ::= { wfAtmServiceRecordEntry 4 }

    wfAtmServiceRecordAalEncapsType OBJECT-TYPE
        SYNTAX	INTEGER {
    		    routedproto(1),
    		    bridged8023(2),
    		    bridged8025(3),
    		    bridged8026(4),
    		    lane8023(5),
    		    lane8025(6),
    		    llcencaps(7),
    		    frsscs(8),
    		    other(9),
    		    unknown(10),
    		    frinterwork(11),
		    mpsencaps(12)
    		}
        ACCESS	read-write
        STATUS	mandatory
        DESCRIPTION
                "The type of data encapsulation used over both AAL3/4 and
                AAL5 SSCS layer. Currently, the only values supported are :
                     ATM_SERVICEREC_ENCAPS_LLCENCAPS - RFC1483
                     ATM_SERVICEREC_ENCAPS_FRSSCS - RFC1294
                     ATM_SERVICEREC_ENCAPS_ROUTEDPROTO - NONE"
        DEFVAL	{ llcencaps }
        ::= { wfAtmServiceRecordEntry 5 }

    wfAtmServiceRecordState OBJECT-TYPE
        SYNTAX	INTEGER {
    		    up(1),
    		    down(2),
    		    init(3),
    		    reject(4),
    		    notpresent(5),
                    oamlost(6)
    		}                    
        ACCESS	read-only
        STATUS	mandatory
        DESCRIPTION
                "State of Service Record"
        DEFVAL	{ notpresent }
        ::= { wfAtmServiceRecordEntry 6 }

    wfAtmServiceRecordVcType OBJECT-TYPE
        SYNTAX	INTEGER {
    		    pvc(1),
    		    svc(2),
		    control(3),
                    muxedSvc(4)
    		}
        ACCESS	read-write
        STATUS	mandatory
        DESCRIPTION
                "The type of VC for each encapsulation. Applicable for LLC
                and null type encapsulation enforced from SM - aks.
                'muxedSvc' indicates SVCs that can be shared between
                applications for encapsulations that support muxing.
                'control' should not a configurable option. It is defined for
                 consistency with wfAtmVclVcType"
        DEFVAL	{ pvc }
        ::= { wfAtmServiceRecordEntry 7 }

    wfAtmServiceRecordNetworkPrefix OBJECT-TYPE
        SYNTAX	OCTET STRING (SIZE (13))
        ACCESS	read-write
        STATUS	mandatory
        DESCRIPTION
                "ATM Address Network portion"
        ::= { wfAtmServiceRecordEntry 8 }

    wfAtmServiceRecordUserSuffix OBJECT-TYPE
        SYNTAX	OCTET STRING (SIZE (7))
        ACCESS	read-write
        STATUS	mandatory
        DESCRIPTION
                "ATM Address User portion"
        ::= { wfAtmServiceRecordEntry 9 }

    wfAtmServiceRecordAtmAddress OBJECT-TYPE
        SYNTAX	OCTET STRING
        ACCESS	read-only
        STATUS	mandatory
        DESCRIPTION
                "ATM Address Complete - Inserted by Router after verification of
                network and user portions"
        ::= { wfAtmServiceRecordEntry 10 }

    wfAtmServiceRecordFlag OBJECT-TYPE
        SYNTAX	INTEGER {
    		    autoaddr(1)
    		}
        ACCESS	read-write
        STATUS	mandatory
        DESCRIPTION
                "This will be used for internal purposes to have Site Manager flag
                specific configurations."
        DEFVAL	{ autoaddr }
        ::= { wfAtmServiceRecordEntry 11 }

    wfAtmServiceRecordMtu OBJECT-TYPE
        SYNTAX	INTEGER(0..9188)
        ACCESS	read-write
        STATUS	mandatory
        DESCRIPTION
                "The size of the largest packet to be used for send/receive on all
                logical interfaces defined on this service record. This attribute is 
		an alias for 'ifMtu'."
        ::= { wfAtmServiceRecordEntry 12 }

    wfAtmServiceRecordLossPriorityPolicy OBJECT-TYPE
        SYNTAX  INTEGER {
                enabled(1),
                disabled(2)
        }
        ACCESS  read-write
        STATUS  mandatory
        DESCRIPTION
                "This is relevant only for Frame Relay Switch product.
                 This indicates the policy for translating FR DE to
                 ATM CLP on IP truks over ATM. "
        DEFVAL  { disabled }
        ::= { wfAtmServiceRecordEntry 13 }

    wfAtmServiceRecordDebug OBJECT-TYPE
        SYNTAX  INTEGER {
                    disabled(1),
                    pvcFsm(2),
                    svcFsm(4),
                    llcSvcMux(8),
                    all(2147483647)
                }
        ACCESS  read-write
        STATUS  mandatory
        DESCRIPTION
                "This flag will enable certain debug messages depending on the value set.
                The values are as follows:
 
                 1 - disable debugging (default)
                 2 - enable Service State Machine debugging
                 4294967295 - All of the above"
        DEFVAL  { disabled }
        ::= { wfAtmServiceRecordEntry 14 }
 
    wfAtmServiceRecordName OBJECT-TYPE
        SYNTAX  DisplayString
        ACCESS  read-write
        STATUS  mandatory
        DESCRIPTION
                "User name for circuit"
        ::= { wfAtmServiceRecordEntry 15 }

    wfAtmServiceRecordWanSvcRoutingMode OBJECT-TYPE
        SYNTAX  INTEGER {
                    disabled(1),
                    normal(2),
                    dialOptimized(3)
                }
        ACCESS  read-write
        STATUS  mandatory
        DESCRIPTION
                "This applies ONLY to WAN SVC type ATM service records.
                 It specifies the route updates mode for the WAN SVCs."
        DEFVAL { disabled }
        ::= { wfAtmServiceRecordEntry 16 }


    wfAtmSVCOptionsTable OBJECT-TYPE
        SYNTAX	SEQUENCE OF WfAtmSVCOptionsEntry
        ACCESS	not-accessible
        STATUS	mandatory
        DESCRIPTION
                "This table contains ATM WAN SVC configuration parameters,
                 one entry for each remote ATM destination for which user
                 wishes to specify some/all of the VC config parameters."
        ::= { wfAtmCommonGroup 13 }

    wfAtmSVCOptionsEntry OBJECT-TYPE
        SYNTAX	WfAtmSVCOptionsEntry
        ACCESS	not-accessible
        STATUS	mandatory
        DESCRIPTION
                "Entry definition."
        INDEX	{ wfAtmSVCOptionsCct,
    		  wfAtmSVCOptionsIndex }
        ::= { wfAtmSVCOptionsTable 1 }

    WfAtmSVCOptionsEntry ::= SEQUENCE {
    	    wfAtmSVCOptionsDelete
    		INTEGER,
            wfAtmSVCOptionsDisable
                INTEGER,
            wfAtmSVCOptionsCct
                INTEGER,
            wfAtmSVCOptionsIndex
                INTEGER,
            wfAtmSVCOptionsAdjHostAtmAddr
                OCTET STRING,
            wfAtmSVCOptionsXmtPeakCellRate
                INTEGER,
            wfAtmSVCOptionsXmtSustCellRate
                INTEGER,
            wfAtmSVCOptionsRcvPeakCellRate
                INTEGER,
            wfAtmSVCOptionsRcvSustCellRate
                INTEGER,
            wfAtmSVCOptionsName
                DisplayString
        }

    wfAtmSVCOptionsDelete OBJECT-TYPE
        SYNTAX	INTEGER {
    		    create(1),
    		    delete(2)
    		}
        ACCESS	read-write
        STATUS	mandatory
        DESCRIPTION
                "Create/delete MIB instance parameter."
        DEFVAL	{ create }
        ::= { wfAtmSVCOptionsEntry 1 }

    wfAtmSVCOptionsDisable OBJECT-TYPE
        SYNTAX	INTEGER {
    		    enabled(1),
    		    disabled(2)
    		}
        ACCESS	read-write
        STATUS	mandatory
        DESCRIPTION
                "Enable/Disable MIB instance parameter."
        DEFVAL	{ enabled }
        ::= { wfAtmSVCOptionsEntry 2 }

    wfAtmSVCOptionsCct OBJECT-TYPE
        SYNTAX	INTEGER
        ACCESS	read-only
        STATUS	mandatory
        DESCRIPTION
                "Circuit Number to which this SVC Options Entry belongs
                 to. (Instance Id 1)"
        ::= { wfAtmSVCOptionsEntry 3 }

    wfAtmSVCOptionsIndex OBJECT-TYPE
        SYNTAX	INTEGER
        ACCESS	read-only
        STATUS	mandatory
        DESCRIPTION
                "Sequential index number assigned by configuration tool
                 (Instance Id 2)"
        ::= { wfAtmSVCOptionsEntry 4 }

    wfAtmSVCOptionsAdjHostAtmAddr OBJECT-TYPE
        SYNTAX	OCTET STRING (SIZE (20))
        ACCESS	read-write
        STATUS	mandatory
        DESCRIPTION
                "ATM Address of the adjacent host to which these SVC config
                 parameters apply."
        ::= { wfAtmSVCOptionsEntry 5 }

    wfAtmSVCOptionsXmtPeakCellRate OBJECT-TYPE
        SYNTAX	INTEGER
        ACCESS	read-write
        STATUS	mandatory
        DESCRIPTION
                "Forward Peak Cell Rate (in cells/sec) of the SVC to
                 this adjacent host"
        DEFVAL  { 4716 }
        ::= { wfAtmSVCOptionsEntry 6 }

    wfAtmSVCOptionsXmtSustCellRate OBJECT-TYPE
        SYNTAX	INTEGER
        ACCESS	read-write
        STATUS	mandatory
        DESCRIPTION
                "Forward Sustainable Cell Rate (in cells/sec) of the SVC to
                 this adjacent host"
        DEFVAL  { 4716 }
        ::= { wfAtmSVCOptionsEntry 7 }

    wfAtmSVCOptionsRcvPeakCellRate OBJECT-TYPE
        SYNTAX	INTEGER
        ACCESS	read-write
        STATUS	mandatory
        DESCRIPTION
                "Backward Peak Cell Rate (in cells/sec) of the SVC to
                 this adjacent host"
        DEFVAL  { 4716 }
        ::= { wfAtmSVCOptionsEntry 8 }

    wfAtmSVCOptionsRcvSustCellRate OBJECT-TYPE
        SYNTAX	INTEGER
        ACCESS	read-write
        STATUS	mandatory
        DESCRIPTION
                "Backward Sustainable Cell Rate (in cells/sec) of the SVC to
                 this adjacent host"
        DEFVAL  { 4716 }
        ::= { wfAtmSVCOptionsEntry 9 }

    wfAtmSVCOptionsName OBJECT-TYPE
        SYNTAX  DisplayString
        ACCESS  read-write
        STATUS  mandatory
        DESCRIPTION
                "User name for SVC Options Record"
        ::= { wfAtmSVCOptionsEntry 10 }

    wfAtmVclConfTable OBJECT-TYPE
        SYNTAX	SEQUENCE OF WfAtmVclConfEntry
        ACCESS	not-accessible
        STATUS	mandatory
        DESCRIPTION
                ""
        ::= { wfAtmCommonGroup 5 }

    wfAtmVclConfEntry OBJECT-TYPE
        SYNTAX	WfAtmVclConfEntry
        ACCESS	not-accessible
        STATUS	mandatory
        DESCRIPTION
                "Entry definition."
        INDEX	{ wfAtmVclConfIndex,
    		  wfAtmVclConfVpi,
    		  wfAtmVclConfVci }
        ::= { wfAtmVclConfTable 1 }

    WfAtmVclConfEntry ::= SEQUENCE {
    	    wfAtmVclConfDelete
    		INTEGER,
    	    wfAtmVclConfIndex
    		INTEGER,
    	    wfAtmVclConfVpi
    		INTEGER,
    	    wfAtmVclConfVci
    		INTEGER,
    	    wfAtmVclAdminStatus
    		INTEGER,
    	    wfAtmVclOperStatus
    		INTEGER,
    	    wfAtmVclLastChange
    		TimeTicks,
    	    wfAtmVclXmtPeakCellRate
    		INTEGER,
    	    wfAtmVclXmtSustainableCellRate
    		INTEGER,
    	    wfAtmVclXmtBurstSize
    		INTEGER,
    	    wfAtmVclXmtQosClass
    		INTEGER,
    	    wfAtmVclRcvPeakCellRate
    		INTEGER,
    	    wfAtmVclRcvSustainableCellRate
    		INTEGER,
    	    wfAtmVclRcvBurstSize
    		INTEGER,
    	    wfAtmVclRcvQosClass
    		INTEGER,
    	    wfAtmVclAalType
    		INTEGER,
    	    wfAtmVclAalCpcsTransmitSduSize
    		INTEGER,
    	    wfAtmVclAalCpcsReceiveSduSize
    		INTEGER,
    	    wfAtmVclAalEncapsType
    		INTEGER,
    	    wfAtmVclCongestionIndication
    		INTEGER,
    	    wfAtmVclCellLossPriority
    		INTEGER,
    	    wfAtmVclCct
    		INTEGER,
    	    wfAtmVclDirectAccessCct
    		INTEGER,
    	    wfAtmVclMulticast
    		INTEGER,
    	    wfAtmVclMode
    		INTEGER,
    	    wfAtmVclDrops
    		Counter,
    	    wfAtmVclVcIndex
    		INTEGER,
    	    wfAtmVclVcType
    		INTEGER,
    	    wfAtmVclXmtTagging
    		INTEGER,
    	    wfAtmVclRcvTagging
    		INTEGER,
            wfAtmVclOamLpbkEnable
                INTEGER,
            wfAtmVclOamLpbkCellInterval
                INTEGER,
            wfAtmVclOamLpbkThreshold1
                INTEGER,
	    wfAtmVclOamLpbkThreshold2
                INTEGER,
            wfAtmVclOamAlarmEnable
                INTEGER,
    	    wfAtmVclVcGroup
    		INTEGER,
    	    wfAtmVclServiceClass
    		INTEGER,
            wfAtmVclServiceCategory
                INTEGER,
    	    wfAtmVclVBRType
    		INTEGER,
    	    wfAtmVclXmtMinimumCellRate
    		INTEGER,
            wfAtmVclXmtInitialCellRate
                INTEGER,
            wfAtmVclXmtRateIncreaseFactor
                INTEGER,
            wfAtmVclXmtRateDecreaseFactor
                INTEGER
        }

    wfAtmVclConfDelete OBJECT-TYPE
        SYNTAX	INTEGER {
    		    create(1),
    		    delete(2)
    		}
        ACCESS	read-write
        STATUS	mandatory
        DESCRIPTION
                "Create/delete MIB instance parameter."
        DEFVAL	{ create }
        ::= { wfAtmVclConfEntry 1 }

    wfAtmVclConfIndex OBJECT-TYPE
        SYNTAX	INTEGER
        ACCESS	read-only
        STATUS	mandatory
        DESCRIPTION
                "Uniquely identifies the interface (port) that contains the
                appropriate management information."
        ::= { wfAtmVclConfEntry 2 }

    wfAtmVclConfVpi OBJECT-TYPE
        SYNTAX	INTEGER
        ACCESS	read-only
        STATUS	mandatory
        DESCRIPTION
                "The VPI value of the VCL. The maximum VPI value cannot exceed the
                value allowable by the wfAtmInterfaceMaxActiveVpiBits."
        ::= { wfAtmVclConfEntry 3 }

    wfAtmVclConfVci OBJECT-TYPE
        SYNTAX	INTEGER
        ACCESS	read-only
        STATUS	mandatory
        DESCRIPTION
                "The VCI value of the VCL. The maximum VCI value cannot exceed the
                value allowable by the wfAtmInterfaceMaxActiveVciBits."
        ::= { wfAtmVclConfEntry 4 }

    wfAtmVclAdminStatus OBJECT-TYPE
        SYNTAX	INTEGER {
    		    up(1),
    		    down(2)
    		}
        ACCESS	read-write
        STATUS	mandatory
        DESCRIPTION
                "Specifies the desired administrative state of the VCL. The up and
                down states indicate that the traffic flow is enabled and disabled
                respectively for the VCL."
        DEFVAL	{ up }
        ::= { wfAtmVclConfEntry 5 }

    wfAtmVclOperStatus OBJECT-TYPE
        SYNTAX	INTEGER {
    		    up(1),
    		    down(2),
    		    init(3),
    		    notpresent(4),
                    oamlost(5),
                    misconfig(6)
    		}
        ACCESS	read-only
        STATUS	mandatory
        DESCRIPTION
                "Indicates the current operational status of the VCL. The up and
                down states indicate that the VCL is currently operational, or not
                operational, respectively. The Init state indicates the status
                of the VCL is in the process of being initialized and has not yet
                completed. The 'Not Present' state indicates a problem with that
                VCL and is not able to bring the VCC up.  The 'misconfig' state
                indicates the VC is misconfigured."
        DEFVAL	{ notpresent }
        ::= { wfAtmVclConfEntry 6 }

    wfAtmVclLastChange OBJECT-TYPE
        SYNTAX	TimeTicks
        ACCESS	read-only
        STATUS	mandatory
        DESCRIPTION
                "The value of MIBII's sysUpTime at the time this VCL entered its
                current operational state. If the current state was entered prior
                to the last re-initialization of the agent then this object
                contains a zero value."
        ::= { wfAtmVclConfEntry 7 }

    wfAtmVclXmtPeakCellRate OBJECT-TYPE
        SYNTAX	INTEGER(0..365566)
        ACCESS	read-write
        STATUS	mandatory
        DESCRIPTION
                "Transmit (Forward) Peak Cell Rate in cells/second. This specifies
                the upper bound on the traffic that can be submitted on an ATM
                connection."
        DEFVAL	{ 4716 }
        ::= { wfAtmVclConfEntry 8 }

    wfAtmVclXmtSustainableCellRate OBJECT-TYPE
        SYNTAX	INTEGER(0..365566)
        ACCESS	read-write
        STATUS	mandatory
        DESCRIPTION
                "Transmit (Forward) Sustainable Cell Rate in cells/second. This specifies
                the upper bound on the conforming average rate of an ATM connection,
                where 'average rate' is the number of cells transmitted divided by
                the 'duration of the connection'."
        DEFVAL	{ 4716 }
        ::= { wfAtmVclConfEntry 9 }

    wfAtmVclXmtBurstSize OBJECT-TYPE
        SYNTAX  INTEGER(1..65535)
        ACCESS	read-write
        STATUS	mandatory
        DESCRIPTION
                "Transmit (Forward) Burst Size in cells."
        DEFVAL	{ 40 }
        ::= { wfAtmVclConfEntry 10 }

    wfAtmVclXmtQosClass OBJECT-TYPE
        SYNTAX	INTEGER {
    		    class0(1),
    		    class1(2),
    		    class2(3),
    		    class3(4)
    		}
        ACCESS	read-write
        STATUS	mandatory
        DESCRIPTION
                "Transmit (Forward) Quality of Service as specified in Appendix A,
                Section 4 of the ATM Forum UNI Specification, Version 3.0"
        DEFVAL	{ class3 }
        ::= { wfAtmVclConfEntry 11 }

    wfAtmVclRcvPeakCellRate OBJECT-TYPE
        SYNTAX	INTEGER(0..365566)
        ACCESS	read-write
        STATUS	mandatory
        DESCRIPTION
                "Receive (Backward) Peak Cell Rate in cells/second. This specifies
                the upper bound on the traffic that can be submitted on an ATM
                connection."
        DEFVAL	{ 4716 }
        ::= { wfAtmVclConfEntry 12 }

    wfAtmVclRcvSustainableCellRate OBJECT-TYPE
        SYNTAX	INTEGER(0..365566)
        ACCESS	read-write
        STATUS	mandatory
        DESCRIPTION
                "Receive (Backward) Sustainable Cell Rate in cells/second. This specifies
                the upper bound on the conforming average rate of an ATM connection,
                where 'average rate' is the number of cells transmitted divided by
                the 'duration of the connection'."
        DEFVAL	{ 4716 }
        ::= { wfAtmVclConfEntry 13 }

    wfAtmVclRcvBurstSize OBJECT-TYPE
        SYNTAX	INTEGER(1..65535)
        ACCESS	read-write
        STATUS	mandatory
        DESCRIPTION
                "Receive (Backward) Burst Size in cells."
        DEFVAL	{ 40 }
        ::= { wfAtmVclConfEntry 14 }

    wfAtmVclRcvQosClass OBJECT-TYPE
        SYNTAX	INTEGER {
    		    class0(1),
    		    class1(2),
    		    class2(3),
    		    class3(4)
    		}
        ACCESS	read-write
        STATUS	mandatory
        DESCRIPTION
                "Receive (Backward) Quality of Service as specified in Appendix A,
                Section 4 of the ATM Forum UNI Specification, Version 3.0"
        DEFVAL	{ class3 }
        ::= { wfAtmVclConfEntry 15 }

    wfAtmVclAalType OBJECT-TYPE
        SYNTAX	INTEGER {
    		    type1(1),
    		    type34(2),
    		    type5(3),
    		    other(4),
    		    unknown(5)
    		}
        ACCESS	read-write
        STATUS	mandatory
        DESCRIPTION
                "The type of AAL used on the VCL."
        DEFVAL	{ type5 }
        ::= { wfAtmVclConfEntry 16 }

    wfAtmVclAalCpcsTransmitSduSize OBJECT-TYPE
        SYNTAX	INTEGER(1..65535)
        ACCESS	read-write
        STATUS	mandatory
        DESCRIPTION
                "The maximum AAL CPCS SDU size in octets that is supported on the
                transmit direction of this VCC."
        DEFVAL	{ 4608 }
        ::= { wfAtmVclConfEntry 17 }

    wfAtmVclAalCpcsReceiveSduSize OBJECT-TYPE
        SYNTAX	INTEGER(1..65535)
        ACCESS	read-write
        STATUS	mandatory
        DESCRIPTION
                "The maximum AAL CPCS SDU size in octets that is supported on the
                receive direction of this VCC."
        DEFVAL	{ 4608 }
        ::= { wfAtmVclConfEntry 18 }

    wfAtmVclAalEncapsType OBJECT-TYPE
        SYNTAX	INTEGER {
    		    routedproto(1),
    		    bridged8023(2),
    		    bridged8025(3),
    		    bridged8026(4),
    		    lane8023(5),
    		    lane8025(6),
    		    llcencaps(7),
    		    frsscs(8),
    		    other(9),
    		    unknown(10)
    		}
        ACCESS	read-write
        STATUS	mandatory
        DESCRIPTION
                "The type of data encapsulation used over both AAL3/4 and
                AAL5 SSCS layer. Currently, the only values supported are :
                     ATM_VCLENCAPS_LLCENCAPS - RFC1483
                     ATM_VCLENCAPS_ROUTEDPROTO - NONE"
        DEFVAL	{ llcencaps }
        ::= { wfAtmVclConfEntry 19 }

    wfAtmVclCongestionIndication OBJECT-TYPE
        SYNTAX	INTEGER {
    		    off(1),
    		    on(2)
    		}
        ACCESS	read-write
        STATUS	mandatory
        DESCRIPTION
                "The desired state of the Congestion Indication (CI) bit in the
                payload field of each ATM cell for this VCL."
        DEFVAL	{ off }
        ::= { wfAtmVclConfEntry 20 }

    wfAtmVclCellLossPriority OBJECT-TYPE
        SYNTAX	INTEGER {
    		    off(1),
    		    on(2),
                    drop-preference(3)
    		}
        ACCESS	read-write
        STATUS	mandatory
        DESCRIPTION
                "The desired state of the Cell Loss Priority (CLP) bit in the ATM
                header of each cell for this VCL.  For 'drop-preference', the CLP
                bit will be set if the internal drop preference bit is set."
        DEFVAL	{ off }
        ::= { wfAtmVclConfEntry 21 }

    wfAtmVclCct OBJECT-TYPE
        SYNTAX	INTEGER
        ACCESS	read-write
        STATUS	mandatory
        DESCRIPTION
                "Identifies the object which corresponds to the Wellfleet circuit
                number"
        ::= { wfAtmVclConfEntry 22 }

    wfAtmVclDirectAccessCct OBJECT-TYPE
        SYNTAX	INTEGER
        ACCESS	read-write
        STATUS	mandatory
        DESCRIPTION
                "Circuit number to use for this VC for hybrid or direct access
                routing"
        ::= { wfAtmVclConfEntry 23 }

    wfAtmVclMulticast OBJECT-TYPE
        SYNTAX	INTEGER {
    		    unicast(1),
    		    multicast(2)
    		}
        ACCESS	read-write
        STATUS	mandatory
        DESCRIPTION
                "Indicates whether this VPI/VCI is used for multicast or
                single destination."
        DEFVAL	{ unicast }
        ::= { wfAtmVclConfEntry 24 }

    wfAtmVclMode OBJECT-TYPE
        SYNTAX	INTEGER {
    		    groupaccess(1),
    		    hybridaccess(2),
    		    direct(3)
    		}
        ACCESS	read-write
        STATUS	mandatory
        DESCRIPTION
                "The mode of the given VC.
                GROUP - treats the VC as one of many vc's on a circuit.
                HYBRID - treats the VC as one of many vc's on a circuit for
                         protocol traffic, but as a separate circuit for bridging.
                DIRECT - treats the VC as a separate circuit for all applications."
        DEFVAL	{ groupaccess }
        ::= { wfAtmVclConfEntry 25 }

    wfAtmVclDrops OBJECT-TYPE
        SYNTAX	Counter
        ACCESS	read-only
        STATUS	mandatory
        DESCRIPTION
                "The total count of packets above the SSCS layer dropped on this VC"
        ::= { wfAtmVclConfEntry 26 }

    wfAtmVclVcIndex OBJECT-TYPE
        SYNTAX	INTEGER
        ACCESS	read-only
        STATUS	mandatory
        DESCRIPTION
                "Driver-defined VCI for quick table lookup"
        ::= { wfAtmVclConfEntry 27 }

    wfAtmVclVcType OBJECT-TYPE
        SYNTAX	INTEGER {
    		    permanent(1),
    		    switched(2),
    		    control(3),
                    switchedMux(4)
    		}
        ACCESS	read-only
        STATUS	mandatory
        DESCRIPTION
                "Type of VC can be either permanent or switched. Only
		 permanent VCs can be modfied. switchedMux is same as switched
                 but is included here to be consistent with
                 wfAtmServiceRecordVcType"
        DEFVAL	{ permanent }
        ::= { wfAtmVclConfEntry 28 }

    wfAtmVclXmtTagging OBJECT-TYPE
        SYNTAX	INTEGER {
    		    on(1),
    		    off(2)
    		}
        ACCESS	read-write
        STATUS	mandatory
        DESCRIPTION
                "Tagging forward VC messages if peak/sustainable rates exceeded"
        DEFVAL	{ off }
        ::= { wfAtmVclConfEntry 29 }

    wfAtmVclRcvTagging OBJECT-TYPE
        SYNTAX	INTEGER {
    		    on(1),
    		    off(2)
    		}
        ACCESS	read-write
        STATUS	mandatory
        DESCRIPTION
                "Tagging backward VC messages if peak/sustainable rates exceeded"
        DEFVAL	{ off }
        ::= { wfAtmVclConfEntry 30 }

   wfAtmVclOamLpbkEnable OBJECT-TYPE
        SYNTAX  INTEGER {
                    enabled(1),
                    disabled(2)
                }
        ACCESS  read-write
        STATUS  mandatory
        DESCRIPTION
              " PVC OAM F5 Loopback function. "
        DEFVAL  { disabled }
        ::= { wfAtmVclConfEntry 31 }

  wfAtmVclOamLpbkCellInterval OBJECT-TYPE
        SYNTAX  INTEGER (1..255)
        ACCESS  read-write
        STATUS  mandatory
        DESCRIPTION
                " This is the time interval between two consecutive OAM 
                  loopback cells in numbers of second. "
        DEFVAL  { 5 }
        ::= { wfAtmVclConfEntry 32 }

  wfAtmVclOamLpbkThreshold1 OBJECT-TYPE
        SYNTAX  INTEGER (1..255)
        ACCESS  read-write
        STATUS  mandatory
        DESCRIPTION
                "This is the number of consecutive loopback OAM cells lost 
                 before the VC connection is declared down."
        DEFVAL  { 1 }
        ::= { wfAtmVclConfEntry 33 }

  wfAtmVclOamLpbkThreshold2 OBJECT-TYPE
        SYNTAX  INTEGER (1..255)
        ACCESS  read-write
        STATUS  mandatory
        DESCRIPTION
                "This is the number of consecutive loopback OAM cells received
                 before the VC connection is declared up."
        DEFVAL  { 2 }
        ::= { wfAtmVclConfEntry 34 }

   wfAtmVclOamAlarmEnable OBJECT-TYPE
        SYNTAX  INTEGER {
                    enabled(1),
                    disabled(2)
                }
        ACCESS  read-write
        STATUS  mandatory
        DESCRIPTION
              " PVC OAM F5 alarm function. "
        DEFVAL  { disabled }
        ::= { wfAtmVclConfEntry 35 }

    wfAtmVclVcGroup  OBJECT-TYPE
        SYNTAX	INTEGER 
        ACCESS	read-write
        STATUS	mandatory
        DESCRIPTION
                "The group of VCs this VC is a member of.  All VCs in a given
		group will have the same VcGroup."
        ::= { wfAtmVclConfEntry 36 }

    wfAtmVclServiceClass OBJECT-TYPE
        SYNTAX	INTEGER(0..7)
        ACCESS	read-write
        STATUS	mandatory
        DESCRIPTION
                "The internal service class of the traffic this VC will carry"
        ::= { wfAtmVclConfEntry 37 }

   wfAtmVclServiceCategory OBJECT-TYPE
        SYNTAX  INTEGER {
                    other(1),
                    cbr(2),
                    vbrRt(3),
                    vbrNRt(4),
                    abr(5),
                    ubr(6),
                    ubrplus(7)
                }
        ACCESS  read-write
        STATUS  mandatory
        DESCRIPTION
              " The service category for a connection.

                other    -- none of the following
                cbr      -- constant bit rate
                vbrRt    -- real-time variable bit rate
                vbrNRt   -- non real-time variable bit rate
                abr      -- available bit rate
                ubr      -- unspecified bit rate
                ubrplus  -- unspecified bit rate +

                Note:
                May not be supported on all ATM-based platforms."
        DEFVAL  { other }
        ::= { wfAtmVclConfEntry 38 }

    wfAtmVclVBRType OBJECT-TYPE
        SYNTAX	INTEGER {
    		    type1(1),
                    type2(2)
    		}
        ACCESS	read-write
        STATUS	mandatory
        DESCRIPTION
                "Type 1 VBR:  CLP=0+1 cells are rescheduled by PCR or SCR according
                              to the GCRA state.

                 Type 2 VBR:  CLP=0 cells are rescheduled by PCR or SCR according
                              to the GCRA state.  CLP=1 cells are always rescheduled
                              by PCR.

                 Note:
                 May not be supported on all ATM-based platforms."
        DEFVAL	{ type1 }
        ::= { wfAtmVclConfEntry 39 }

    wfAtmVclXmtMinimumCellRate OBJECT-TYPE
        SYNTAX	INTEGER(0..365566)
        ACCESS	read-write
        STATUS	mandatory
        DESCRIPTION
                "Transmit (Forward) Minimum Cell Rate in cells/second. This specifies
                 the minimum cell rate required by an ATM connection (the source is
                 always allowed to send at at LEAST this rate).

                 Note:
                 May not be supported on all ATM-based platforms and/or service categories."
        DEFVAL	{ 10 }
        ::= { wfAtmVclConfEntry 40 }

    wfAtmVclXmtInitialCellRate OBJECT-TYPE
        SYNTAX	INTEGER(0..365566)
        ACCESS	read-write
        STATUS	mandatory
        DESCRIPTION
                "Transmit (Forward) Initial Cell Rate in cells/second. The ICR is the
                 rate at which the source should send initially and after an idle period.

                 Note:
                 May not be supported on all ATM-based platforms and/or service categories."
        DEFVAL	{ 4716 }
        ::= { wfAtmVclConfEntry 41 }

    wfAtmVclXmtRateIncreaseFactor OBJECT-TYPE
        SYNTAX	INTEGER(0..15)
        ACCESS	read-write
        STATUS	mandatory
        DESCRIPTION
                "Rate increase factor (RIF) controls the amount by which the cell Tx rate
                 may increase upon receipt of an RM (Resource Management) cell.

                 The value is a power of 2 from 1/32768 to 1.
                 Legal values are 0-15 (0==1, 15==1/32768).

                 The default is 4 (2**-4==1/16) as specified by af-tm-0056.000.

                 Note:
                 May not be supported on all ATM-based platforms and/or service categories."
        DEFVAL	{ 4 }
        ::= { wfAtmVclConfEntry 42 }

    wfAtmVclXmtRateDecreaseFactor OBJECT-TYPE
        SYNTAX	INTEGER(0..15)
        ACCESS	read-write
        STATUS	mandatory
        DESCRIPTION
                "Rate decrease factor (RDF) controls the decrease in the cell Tx rate.

                 The value is a power of 2 from 1/32768 to 1.
                 Legal values are 0-15 (0==1, 15==1/32768).

                 The default is 4 (2**-4==1/16) as specified by af-tm-0056.000.

                 Note:
                 May not be supported on all ATM-based platforms and/or service categories."
        DEFVAL	{ 4 }
        ::= { wfAtmVclConfEntry 43 }

    wfAtmVclStatsTable OBJECT-TYPE
        SYNTAX	SEQUENCE OF WfAtmVclStatsEntry
        ACCESS	not-accessible
        STATUS	mandatory
        DESCRIPTION
                ""
        ::= { wfAtmCommonGroup 6 }

    wfAtmVclStatsEntry OBJECT-TYPE
        SYNTAX	WfAtmVclStatsEntry
        ACCESS	not-accessible
        STATUS	mandatory
        DESCRIPTION
                "Entry definition."
        INDEX	{ wfAtmVclStatsIndex,
    		  wfAtmVclStatsVpi,
    		  wfAtmVclStatsVci }
        ::= { wfAtmVclStatsTable 1 }

    WfAtmVclStatsEntry ::= SEQUENCE {
    	    wfAtmVclStatsIndex
    		INTEGER,
    	    wfAtmVclStatsVpi
    		INTEGER,
    	    wfAtmVclStatsVci
    		INTEGER,
    	    wfAtmVclStatsVcIndex
    		INTEGER,
    	    wfAtmVclXmtCells
    		OCTET STRING,
    	    wfAtmVclRcvCells
    		OCTET STRING,
    	    wfAtmVclRcvSequenceNumErrs
    		Counter,
    	    wfAtmVclRcvInvalidLenErrs
    		Counter,
    	    wfAtmVclRcvMissingEomErrs
    		Counter,
    	    wfAtmVclRcvBufferOflowErrs
    		Counter,
    	    wfAtmVclRcvMaxLenExceedErrs
    		Counter,
    	    wfAtmVclRcvTrailerErrs
    		Counter,
    	    wfAtmVclRcvAbortErrs
    		Counter,
    	    wfAtmVclRcvPacketLengthErrs
    		Counter,
    	    wfAtmVclRcvReassemAbortErrs
    		Counter,
    	    wfAtmVclRcvCrcErrs
    		Counter,
    	    wfAtmVclXmtOamCells
    		Counter,
    	    wfAtmVclRcvOamCells
    		Counter,
    	    wfAtmVclRcvOamCrcErrs
    		Counter
        }

    wfAtmVclStatsIndex OBJECT-TYPE
        SYNTAX	INTEGER
        ACCESS	read-only
        STATUS	mandatory
        DESCRIPTION
                "Uniquely identifies the interface that contains the
                appropriate management information."
        ::= { wfAtmVclStatsEntry 1 }

    wfAtmVclStatsVpi OBJECT-TYPE
        SYNTAX	INTEGER
        ACCESS	read-only
        STATUS	mandatory
        DESCRIPTION
                "The Virtual Path Identifier (VPI) value of the VCL."
        ::= { wfAtmVclStatsEntry 2 }

    wfAtmVclStatsVci OBJECT-TYPE
        SYNTAX	INTEGER
        ACCESS	read-only
        STATUS	mandatory
        DESCRIPTION
                "The Virtual Channel Identifier (VCI) value of the VCL."
        ::= { wfAtmVclStatsEntry 3 }

    wfAtmVclStatsVcIndex OBJECT-TYPE
        SYNTAX	INTEGER
        ACCESS	read-only
        STATUS	mandatory
        DESCRIPTION
                "Uniquely identifies the virtual channel connection."
        ::= { wfAtmVclStatsEntry 4 }

    wfAtmVclXmtCells OBJECT-TYPE
        SYNTAX	OCTET STRING
        ACCESS	read-only
        STATUS	mandatory
        DESCRIPTION
                "Accumulated total of user cells transmitted for this VCL. This
                attribute is a 64-bit counter. Does not include OAM cells."
        ::= { wfAtmVclStatsEntry 5 }

    wfAtmVclRcvCells OBJECT-TYPE
        SYNTAX	OCTET STRING
        ACCESS	read-only
        STATUS	mandatory
        DESCRIPTION
                "Accumulated total of user cells received for this VCL. This
                attribute is a 64-bit counter. Does not include OAM cells."
        ::= { wfAtmVclStatsEntry 6 }

    wfAtmVclRcvSequenceNumErrs OBJECT-TYPE
        SYNTAX	Counter
        ACCESS	read-only
        STATUS	mandatory
        DESCRIPTION
                "Number of times data was being reassembled and a SAR Protocol
                Data Unit (PDU) was received out of order for this VCL. This
                count is valid only when the adaptation layer protocol is
                AAL 3/4."
        ::= { wfAtmVclStatsEntry 7 }

    wfAtmVclRcvInvalidLenErrs OBJECT-TYPE
        SYNTAX	Counter
        ACCESS	read-only
        STATUS	mandatory
        DESCRIPTION
                ""
        ::= { wfAtmVclStatsEntry 8 }

    wfAtmVclRcvMissingEomErrs OBJECT-TYPE
        SYNTAX	Counter
        ACCESS	read-only
        STATUS	mandatory
        DESCRIPTION
                ""
        ::= { wfAtmVclStatsEntry 9 }

    wfAtmVclRcvBufferOflowErrs OBJECT-TYPE
        SYNTAX	Counter
        ACCESS	read-only
        STATUS	mandatory
        DESCRIPTION
                ""
        ::= { wfAtmVclStatsEntry 10 }

    wfAtmVclRcvMaxLenExceedErrs OBJECT-TYPE
        SYNTAX	Counter
        ACCESS	read-only
        STATUS	mandatory
        DESCRIPTION
                ""
        ::= { wfAtmVclStatsEntry 11 }

    wfAtmVclRcvTrailerErrs OBJECT-TYPE
        SYNTAX	Counter
        ACCESS	read-only
        STATUS	mandatory
        DESCRIPTION
                ""
        ::= { wfAtmVclStatsEntry 12 }

    wfAtmVclRcvAbortErrs OBJECT-TYPE
        SYNTAX	Counter
        ACCESS	read-only
        STATUS	mandatory
        DESCRIPTION
                ""
        ::= { wfAtmVclStatsEntry 13 }

    wfAtmVclRcvPacketLengthErrs OBJECT-TYPE
        SYNTAX	Counter
        ACCESS	read-only
        STATUS	mandatory
        DESCRIPTION
                ""
        ::= { wfAtmVclStatsEntry 14 }

    wfAtmVclRcvReassemAbortErrs OBJECT-TYPE
        SYNTAX	Counter
        ACCESS	read-only
        STATUS	mandatory
        DESCRIPTION
                ""
        ::= { wfAtmVclStatsEntry 15 }

    wfAtmVclRcvCrcErrs OBJECT-TYPE
        SYNTAX	Counter
        ACCESS	read-only
        STATUS	mandatory
        DESCRIPTION
                ""
        ::= { wfAtmVclStatsEntry 16 }

    wfAtmVclXmtOamCells OBJECT-TYPE
        SYNTAX	Counter
        ACCESS	read-only
        STATUS	mandatory
        DESCRIPTION
                "Count of OAM cells transmitted successfully."
        ::= { wfAtmVclStatsEntry 17 }

    wfAtmVclRcvOamCells OBJECT-TYPE
        SYNTAX	Counter
        ACCESS	read-only
        STATUS	mandatory
        DESCRIPTION
                "Count of OAM cells received successfully."
        ::= { wfAtmVclStatsEntry 18 }

    wfAtmVclRcvOamCrcErrs OBJECT-TYPE
        SYNTAX	Counter
        ACCESS	read-only
        STATUS	mandatory
        DESCRIPTION
                "Count of OAM cells received with CRC10 error."
        ::= { wfAtmVclStatsEntry 19 }

    wfAtmSigTable OBJECT-TYPE
        SYNTAX	SEQUENCE OF WfAtmSigEntry
        ACCESS	not-accessible
        STATUS	mandatory
        DESCRIPTION
                "This table includes the ATM Signalling MIB record for Q.93B"
        ::= { wfAtmCommonGroup 7 }

    wfAtmSigEntry OBJECT-TYPE
        SYNTAX	WfAtmSigEntry
        ACCESS	not-accessible
        STATUS	mandatory
        DESCRIPTION
                "This entry contains attributes needed for ATM Q.93B"
        INDEX	{ wfAtmSigLineNumber }
        ::= { wfAtmSigTable 1 }

    WfAtmSigEntry ::= SEQUENCE {
    	    wfAtmSigDelete
    		INTEGER,
    	    wfAtmSigDisable
    		INTEGER,
    	    wfAtmSigLineNumber
    		INTEGER,
    	    wfAtmSigAtmCct
    		INTEGER,
    	    wfAtmSigState
    		INTEGER,
    	    wfAtmSigMaxServiceUsers
    		INTEGER,
    	    wfAtmSigMaxPtPtConnections
    		INTEGER,
    	    wfAtmSigMaxPtMultConnections
    		INTEGER,
    	    wfAtmSigMaxPartiesInMultConnect
    		INTEGER,
    	    wfAtmSigMaxRoutingRegistrations
    		INTEGER,
    	    wfAtmSigMinBufferThreshold
    		INTEGER,
    	    wfAtmSigTimerResolution
    		INTEGER,
    	    wfAtmSigVpi
    		INTEGER,
    	    wfAtmSigVci
    		INTEGER,
    	    wfAtmSigStandard
    		INTEGER,
    	    wfAtmSigInterfaceType
    		INTEGER,
    	    wfAtmSigMinVciPtPt
    		INTEGER,
    	    wfAtmSigMaxVciPtPt
    		INTEGER,
    	    wfAtmSigMinVpiPtPt
    		INTEGER,
    	    wfAtmSigMaxVpiPtPt
    		INTEGER,
    	    wfAtmSigMinVciPtMltPt
    		INTEGER,
    	    wfAtmSigMaxVciPtMltPt
    		INTEGER,
    	    wfAtmSigMinVpiPtMltPt
    		INTEGER,
    	    wfAtmSigMaxVpiPtMltPt
    		INTEGER,
    	    wfAtmSigT303
    		INTEGER,
    	    wfAtmSigT308
    		INTEGER,
    	    wfAtmSigT309
    		INTEGER,
    	    wfAtmSigT310
    		INTEGER,
    	    wfAtmSigT313
    		INTEGER,
    	    wfAtmSigT316
    		INTEGER,
    	    wfAtmSigT316c
    		INTEGER,
    	    wfAtmSigT322
    		INTEGER,
    	    wfAtmSigTDisc
    		INTEGER,
    	    wfAtmSigT398
    		INTEGER,
    	    wfAtmSigT399
    		INTEGER,
    	    wfAtmSigNumRst
    		INTEGER,
    	    wfAtmSigNumStat
    		INTEGER,
    	    wfAtmSigRestart
    		INTEGER,
    	    wfAtmSigDebug
    		INTEGER,
    	    wfAtmSigCallsSec
    		INTEGER,
    	    wfAtmSigT301
    		INTEGER,
	    wfAtmSigT304
    		INTEGER,
	    wfAtmSigT397
    		INTEGER
        }

    wfAtmSigDelete OBJECT-TYPE
        SYNTAX	INTEGER {
    		    created(1),
    		    deleted(2)
    		}
        ACCESS	read-write
        STATUS	mandatory
        DESCRIPTION
                "Create/Delete parameter. Default is created."
        DEFVAL	{ created }
        ::= { wfAtmSigEntry 1 }

    wfAtmSigDisable OBJECT-TYPE
        SYNTAX	INTEGER {
    		    enabled(1),
    		    disabled(2)
    		}
        ACCESS	read-write
        STATUS	mandatory
        DESCRIPTION
                "Enable/Disable parameter"
        DEFVAL	{ enabled }
        ::= { wfAtmSigEntry 2 }

    wfAtmSigLineNumber OBJECT-TYPE
        SYNTAX	INTEGER
        ACCESS	read-only
        STATUS	mandatory
        DESCRIPTION
                "Instance identifier. This value is the line number of the router."
        ::= { wfAtmSigEntry 3 }

    wfAtmSigAtmCct OBJECT-TYPE
        SYNTAX	INTEGER
        ACCESS	read-only
        STATUS	mandatory
        DESCRIPTION
                "Circuit number of ATM driver associated with this Q.93B instance"
        ::= { wfAtmSigEntry 4 }

    wfAtmSigState OBJECT-TYPE
        SYNTAX	INTEGER {
    		    up(1),
    		    down(2),
    		    init(3),
    		    notpresent(4)
    		}
        ACCESS	read-only
        STATUS	mandatory
        DESCRIPTION
                "Indicates the state of the Q.93B entity"
        DEFVAL	{ notpresent }
        ::= { wfAtmSigEntry 5 }

    wfAtmSigMaxServiceUsers OBJECT-TYPE
        SYNTAX	INTEGER(1..32767)
        ACCESS	read-write
        STATUS	mandatory
        DESCRIPTION
                "Max number of SAPs (service access points) allowed for users to connect"
        DEFVAL	{ 20 }
        ::= { wfAtmSigEntry 6 }

    wfAtmSigMaxPtPtConnections OBJECT-TYPE
        SYNTAX	INTEGER(1..32767)
        ACCESS	read-write
        STATUS	mandatory
        DESCRIPTION
                "Max number of simultaneous point to point connections allowed per port"
        DEFVAL	{ 1000 }
        ::= { wfAtmSigEntry 7 }

    wfAtmSigMaxPtMultConnections OBJECT-TYPE
        SYNTAX	INTEGER(1..32767)
        ACCESS	read-write
        STATUS	mandatory
        DESCRIPTION
                "Max number of simultaneous point to multipt connections allowed per port"
        DEFVAL	{ 40 }
        ::= { wfAtmSigEntry 8 }

    wfAtmSigMaxPartiesInMultConnect OBJECT-TYPE
        SYNTAX	INTEGER(1..32767)
        ACCESS	read-write
        STATUS	mandatory
        DESCRIPTION
                "Max number of simultaneous parties in a point to multipoint connection"
        DEFVAL	{ 1 }
        ::= { wfAtmSigEntry 9 }

    wfAtmSigMaxRoutingRegistrations OBJECT-TYPE
        SYNTAX	INTEGER(1..32767)
        ACCESS	read-write
        STATUS	mandatory
        DESCRIPTION
                "Max number of registrations / routing entries allowed per port"
        ::= { wfAtmSigEntry 10 }

    wfAtmSigMinBufferThreshold OBJECT-TYPE
        SYNTAX	INTEGER(1..10)
        ACCESS	read-write
        STATUS	mandatory
        DESCRIPTION
                "Min percentage of buffer pool that must be free to enable new calls (sub)"
        DEFVAL	{ 2 }
        ::= { wfAtmSigEntry 11 }

    wfAtmSigTimerResolution OBJECT-TYPE
        SYNTAX	INTEGER(0..255000)
        ACCESS	read-write
        STATUS	mandatory
        DESCRIPTION
                "Number of system ticks elapsed between successive timer events in tenths"
        DEFVAL	{ 1024 }
        ::= { wfAtmSigEntry 12 }

    wfAtmSigVpi OBJECT-TYPE
        SYNTAX	INTEGER(1..255)
        ACCESS	read-write
        STATUS	mandatory
        DESCRIPTION
                "Virtual Path Identifier for the Signalling VC"
        ::= { wfAtmSigEntry 13 }

    wfAtmSigVci OBJECT-TYPE
        SYNTAX	INTEGER(1..65535)
        ACCESS	read-write
        STATUS	mandatory
        DESCRIPTION
                "Virtual Channel Identifier for the Signalling VC"
        DEFVAL	{ 5 }
        ::= { wfAtmSigEntry 14 }

    wfAtmSigStandard OBJECT-TYPE
        SYNTAX	INTEGER {
    		    v30(1),
    		    v31(2),
    		    v40(3),
    		    sym(4)
    		}
        ACCESS	read-write
        STATUS	mandatory
        DESCRIPTION
                "Sig Protocol Standard, Uni3.0, Uni3.1, or Trillium Symmetrical Uni (sub)"
        DEFVAL	{ v30 }
        ::= { wfAtmSigEntry 15 }

    wfAtmSigInterfaceType OBJECT-TYPE
        SYNTAX	INTEGER {
    		    user(1),
    		    network(2)
    		}
        ACCESS	read-write
        STATUS	mandatory
        DESCRIPTION
                "Network Interface type, either USER or NETWORK side (sub)"
        DEFVAL	{ user }
        ::= { wfAtmSigEntry 16 }

    wfAtmSigMinVciPtPt OBJECT-TYPE
        SYNTAX	INTEGER(32..65535)
        ACCESS	read-write
        STATUS	mandatory
        DESCRIPTION
                "Minimum VCI number that can be associated with a Point to Point VC"
        DEFVAL	{ 32 }
        ::= { wfAtmSigEntry 17 }

    wfAtmSigMaxVciPtPt OBJECT-TYPE
        SYNTAX	INTEGER(32..65535)
        ACCESS	read-write
        STATUS	mandatory
        DESCRIPTION
                "Maximum VCI number that can be associated with a Point to Point VC"
        DEFVAL	{ 65535 }
        ::= { wfAtmSigEntry 18 }

    wfAtmSigMinVpiPtPt OBJECT-TYPE
        SYNTAX	INTEGER(1..255)
        ACCESS	read-write
        STATUS	mandatory
        DESCRIPTION
                "Minimum VPI number that can be associated with a Point to Point VC"
        ::= { wfAtmSigEntry 19 }

    wfAtmSigMaxVpiPtPt OBJECT-TYPE
        SYNTAX	INTEGER(1..255)
        ACCESS	read-write
        STATUS	mandatory
        DESCRIPTION
                "Maximum VPI number that can be associated with a Point to Point VC"
        ::= { wfAtmSigEntry 20 }

    wfAtmSigMinVciPtMltPt OBJECT-TYPE
        SYNTAX	INTEGER(32..65535)
        ACCESS	read-write
        STATUS	mandatory
        DESCRIPTION
                "Minimum VCI number that can be associated with a Point to Multipoint VC"
        DEFVAL	{ 32 }
        ::= { wfAtmSigEntry 21 }

    wfAtmSigMaxVciPtMltPt OBJECT-TYPE
        SYNTAX	INTEGER(32..65535)
        ACCESS	read-write
        STATUS	mandatory
        DESCRIPTION
                "Maximum VCI number that can be associated with a Point to Multipoint VC"
        DEFVAL	{ 65535 }
        ::= { wfAtmSigEntry 22 }

    wfAtmSigMinVpiPtMltPt OBJECT-TYPE
        SYNTAX	INTEGER(1..255)
        ACCESS	read-write
        STATUS	mandatory
        DESCRIPTION
                "Minimum VPI number that can be associated with a Point to Multipoint VC"
        ::= { wfAtmSigEntry 23 }

    wfAtmSigMaxVpiPtMltPt OBJECT-TYPE
        SYNTAX	INTEGER(1..255)
        ACCESS	read-write
        STATUS	mandatory
        DESCRIPTION
                "Maximum VPI number that can be associated with a Point to Multipoint VC"
        ::= { wfAtmSigEntry 24 }

    wfAtmSigT303 OBJECT-TYPE
        SYNTAX	INTEGER(1..24)
        ACCESS	read-write
        STATUS	mandatory
        DESCRIPTION
                "Q.93B Setup Sent Timer"
        DEFVAL	{ 4 }
        ::= { wfAtmSigEntry 25 }

    wfAtmSigT308 OBJECT-TYPE
        SYNTAX	INTEGER(1..180)
        ACCESS	read-write
        STATUS	mandatory
        DESCRIPTION
                "Q.93B Release Sent Timer"
        DEFVAL	{ 30 }
        ::= { wfAtmSigEntry 26 }

    wfAtmSigT309 OBJECT-TYPE
        SYNTAX	INTEGER(1..540)
        ACCESS	read-write
        STATUS	mandatory
        DESCRIPTION
                "Q.93B - SAAL Data Link Connect Timer"
        DEFVAL	{ 10 }
        ::= { wfAtmSigEntry 27 }

    wfAtmSigT310 OBJECT-TYPE
        SYNTAX	INTEGER(1..60)
        ACCESS	read-write
        STATUS	mandatory
        DESCRIPTION
                "Q.93B Call Proceeding Received Timer"
        DEFVAL	{ 10 }
        ::= { wfAtmSigEntry 28 }

    wfAtmSigT313 OBJECT-TYPE
        SYNTAX	INTEGER(1..24)
        ACCESS	read-write
        STATUS	mandatory
        DESCRIPTION
                "Q.93B Connect Sent Timer"
        DEFVAL	{ 4 }
        ::= { wfAtmSigEntry 29 }

    wfAtmSigT316 OBJECT-TYPE
        SYNTAX	INTEGER(1..720)
        ACCESS	read-write
        STATUS	mandatory
        DESCRIPTION
                "Q.93B Restart Request Sent on Interface Timer"
        DEFVAL	{ 120 }
        ::= { wfAtmSigEntry 30 }

    wfAtmSigT316c OBJECT-TYPE
        SYNTAX	INTEGER(1..720)
        ACCESS	read-write
        STATUS	mandatory
        DESCRIPTION
                "Q.93B Restart Request Sent on Channel Timer"
        DEFVAL	{ 120 }
        ::= { wfAtmSigEntry 31 }

    wfAtmSigT322 OBJECT-TYPE
        SYNTAX	INTEGER(1..24)
        ACCESS	read-write
        STATUS	mandatory
        DESCRIPTION
                "Q.93B Status Enquiry Sent Timer"
        DEFVAL	{ 4 }
        ::= { wfAtmSigEntry 32 }

    wfAtmSigTDisc OBJECT-TYPE
        SYNTAX	INTEGER(1..180)
        ACCESS	read-write
        STATUS	mandatory
        DESCRIPTION
                "Q.93B SAAL Data Link Disconnect Timer"
        DEFVAL	{ 4 }
        ::= { wfAtmSigEntry 33 }

    wfAtmSigT398 OBJECT-TYPE
        SYNTAX	INTEGER(1..24)
        ACCESS	read-write
        STATUS	mandatory
        DESCRIPTION
                "Q.93B Drop Party Sent Timer - Multipoint Connections only"
        DEFVAL	{ 4 }
        ::= { wfAtmSigEntry 34 }

    wfAtmSigT399 OBJECT-TYPE
        SYNTAX	INTEGER(1..84)
        ACCESS	read-write
        STATUS	mandatory
        DESCRIPTION
                "Q.93B Add Party Sent Timer - Multipoint Connections only"
        DEFVAL	{ 14 }
        ::= { wfAtmSigEntry 35 }

    wfAtmSigNumRst OBJECT-TYPE
        SYNTAX	INTEGER(1..100)
        ACCESS	read-write
        STATUS	mandatory
        DESCRIPTION
                "Number of restarts to be retransmitted before link considered down"
        DEFVAL	{ 3 }
        ::= { wfAtmSigEntry 36 }

    wfAtmSigNumStat OBJECT-TYPE
        SYNTAX	INTEGER(1..100)
        ACCESS	read-write
        STATUS	mandatory
        DESCRIPTION
                "Number of status enquiries to be retransmitted before link considered down"
        DEFVAL	{ 3 }
        ::= { wfAtmSigEntry 37 }

    wfAtmSigRestart OBJECT-TYPE
        SYNTAX	INTEGER {
    		    on(1),
    		    off(2)
    		}
        ACCESS	read-write
        STATUS	mandatory
        DESCRIPTION
                "Q.93B send restart when the link comes up. (sub)"
        DEFVAL	{ on }
        ::= { wfAtmSigEntry 38 }

    wfAtmSigDebug OBJECT-TYPE
        SYNTAX	INTEGER {
    		    disabled(1),
    		    status(2),
    		    detail(4),
    		    all(2147483647)
    		}
        ACCESS	read-write
        STATUS	mandatory
        DESCRIPTION
                "This flag will enable certain debug messages depending on the value set.
                The values are as follows:

                 1 - disable debugging
                 2 - Signalling Status events
                 4294967295 - All of the above"
        DEFVAL	{ status }
        ::= { wfAtmSigEntry 39 }

    wfAtmSigCallsSec OBJECT-TYPE
        SYNTAX	INTEGER(0..100)
        ACCESS	read-write
        STATUS	mandatory
        DESCRIPTION
                "The number of signaling messages per second allowed to flow 
                 out of the interface (call pacing). Zero turns this 
                 feature off."
        DEFVAL	{ 0 }
        ::= { wfAtmSigEntry 40 }

    wfAtmSigT301 OBJECT-TYPE
        SYNTAX	INTEGER(180..1024)
        ACCESS	read-write
        STATUS	mandatory
        DESCRIPTION
                "Q.93B Alert Received Timer"
        DEFVAL	{ 180 }
        ::= { wfAtmSigEntry 41 }

    wfAtmSigT304 OBJECT-TYPE
        SYNTAX	INTEGER(30..120)
        ACCESS	read-write
        STATUS	mandatory
        DESCRIPTION
                "Q.93B Setup Ack Received Timer"
        DEFVAL	{ 30 }
        ::= { wfAtmSigEntry 42 }

    wfAtmSigT397 OBJECT-TYPE
        SYNTAX	INTEGER(180..1024)
        ACCESS	read-write
        STATUS	mandatory
        DESCRIPTION
                "Q.93B Alerting or Add Party Alterting Received Timer"
        DEFVAL	{ 180 }
        ::= { wfAtmSigEntry 43 }

    wfAtmSscopTable OBJECT-TYPE
        SYNTAX	SEQUENCE OF WfAtmSscopEntry
        ACCESS	not-accessible
        STATUS	mandatory
        DESCRIPTION
                "This table includes the ATM SSCOP MIB record for Q.SAAL"
        ::= { wfAtmCommonGroup 8 }

    wfAtmSscopEntry OBJECT-TYPE
        SYNTAX	WfAtmSscopEntry
        ACCESS	not-accessible
        STATUS	mandatory
        DESCRIPTION
                "This entry contains attributes needed for ATM Q.SAAL"
        INDEX	{ wfAtmSscopLineNumber }
        ::= { wfAtmSscopTable 1 }

    WfAtmSscopEntry ::= SEQUENCE {
    	    wfAtmSscopDelete
    		INTEGER,
    	    wfAtmSscopDisable
    		INTEGER,
    	    wfAtmSscopLineNumber
    		INTEGER,
    	    wfAtmSscopAtmCct
    		INTEGER,
    	    wfAtmSscopState
    		INTEGER,
    	    wfAtmSscopLowThreshold
    		INTEGER,
    	    wfAtmSscopUpThreshold
    		INTEGER,
    	    wfAtmSscopArbitration
    		INTEGER,
    	    wfAtmSscopPollTimer
    		INTEGER,
    	    wfAtmSscopKeepAliveTimer
    		INTEGER,
    	    wfAtmSscopNoResponseTimer
    		INTEGER,
    	    wfAtmSscopConnectControlTimer
    		INTEGER,
    	    wfAtmSscopMaxCc
    		INTEGER,
    	    wfAtmSscopMaxPd
    		INTEGER,
    	    wfAtmSscopMaxStat
    		INTEGER,
    	    wfAtmSscopIdleTimer
    		INTEGER,
    	    wfAtmSscopStandard
    		INTEGER,
    	    wfAtmSscopDebug
    		INTEGER
        }

    wfAtmSscopDelete OBJECT-TYPE
        SYNTAX	INTEGER {
    		    created(1),
    		    deleted(2)
    		}
        ACCESS	read-write
        STATUS	mandatory
        DESCRIPTION
                "Create/Delete parameter. Default is created."
        DEFVAL	{ created }
        ::= { wfAtmSscopEntry 1 }

    wfAtmSscopDisable OBJECT-TYPE
        SYNTAX	INTEGER {
    		    enabled(1),
    		    disabled(2)
    		}
        ACCESS	read-write
        STATUS	mandatory
        DESCRIPTION
                "Enable/Disable parameter"
        DEFVAL	{ enabled }
        ::= { wfAtmSscopEntry 2 }

    wfAtmSscopLineNumber OBJECT-TYPE
        SYNTAX	INTEGER
        ACCESS	read-only
        STATUS	mandatory
        DESCRIPTION
                "Instance identifier. This value is the line number of the router."
        ::= { wfAtmSscopEntry 3 }

    wfAtmSscopAtmCct OBJECT-TYPE
        SYNTAX	INTEGER
        ACCESS	read-only
        STATUS	mandatory
        DESCRIPTION
                "Circuit number of ATM driver associated with this Q.SAAL instance"
        ::= { wfAtmSscopEntry 4 }

    wfAtmSscopState OBJECT-TYPE
        SYNTAX	INTEGER {
    		    up(1),
    		    down(2),
    		    init(3),
    		    notpresent(4)
    		}
        ACCESS	read-only
        STATUS	mandatory
        DESCRIPTION
                "Indicates the state of the Q.SAAL entity"
        DEFVAL	{ notpresent }
        ::= { wfAtmSscopEntry 5 }

    wfAtmSscopLowThreshold OBJECT-TYPE
        SYNTAX	INTEGER(1..10)
        ACCESS	read-write
        STATUS	mandatory
        DESCRIPTION
                "Congestion is reached when % of buffer pool goes below this threshold (sub)"
        DEFVAL	{ 2 }
        ::= { wfAtmSscopEntry 6 }

    wfAtmSscopUpThreshold OBJECT-TYPE
        SYNTAX	INTEGER(1..10)
        ACCESS	read-write
        STATUS	mandatory
        DESCRIPTION
                "Congestion is stopped when % of buffer pool goes above this threshold (sub)"
        DEFVAL	{ 2 }
        ::= { wfAtmSscopEntry 7 }

    wfAtmSscopArbitration OBJECT-TYPE
        SYNTAX	INTEGER {
    		    passive(1),
    		    active(2)
    		}
        ACCESS	read-write
        STATUS	mandatory
        DESCRIPTION
                "Determines if Q.SAAL initiates link connection or waits for connect (sub)"
        DEFVAL	{ active }
        ::= { wfAtmSscopEntry 8 }

    wfAtmSscopPollTimer OBJECT-TYPE
        SYNTAX	INTEGER(1..120)
        ACCESS	read-write
        STATUS	mandatory
        DESCRIPTION
                "SSCOP Poll Timer.  The Maximum time between transmission of a POLL PDU in tenths/sec"
        DEFVAL	{ 7 }
        ::= { wfAtmSscopEntry 9 }

    wfAtmSscopKeepAliveTimer OBJECT-TYPE
        SYNTAX	INTEGER(1..120)
        ACCESS	read-write
        STATUS	mandatory
        DESCRIPTION
                "SSCOP Keep Alive Timer. If no pending SD or SDP PDU's transmit a POLL PDU in tenths/sec"
        DEFVAL	{ 20 }
        ::= { wfAtmSscopEntry 10 }

    wfAtmSscopNoResponseTimer OBJECT-TYPE
        SYNTAX	INTEGER(1..120)
        ACCESS	read-write
        STATUS	mandatory
        DESCRIPTION
                "SSCOP No Response Timer. Max time between receipt of a STAT PDU in tenths/sec"
        DEFVAL	{ 70 }
        ::= { wfAtmSscopEntry 11 }

    wfAtmSscopConnectControlTimer OBJECT-TYPE
        SYNTAX	INTEGER(1..120)
        ACCESS	read-write
        STATUS	mandatory
        DESCRIPTION
                "SSCOP CC Timer. Time between xmt of BGN, END as long as ACK not received in tenths/sec"
        DEFVAL	{ 10 }
        ::= { wfAtmSscopEntry 12 }

    wfAtmSscopMaxCc OBJECT-TYPE
        SYNTAX	INTEGER(1..20)
        ACCESS	read-write
        STATUS	mandatory
        DESCRIPTION
                "SSCOP MaxCC.  Maximum number of transmissions of a BGN, END or RS PDU."
        DEFVAL	{ 4 }
        ::= { wfAtmSscopEntry 13 }

    wfAtmSscopMaxPd OBJECT-TYPE
        SYNTAX	INTEGER(1..120)
        ACCESS	read-write
        STATUS	mandatory
        DESCRIPTION
                "SSCOP MaxPD.  Maximum value of VT(PD) before transmitting POLL PDU."
        DEFVAL	{ 25 }
        ::= { wfAtmSscopEntry 14 }

    wfAtmSscopMaxStat OBJECT-TYPE
        SYNTAX	INTEGER(1..120)
        ACCESS	read-write
        STATUS	mandatory
        DESCRIPTION
                "SSCOP MaxSTAT.  Maximum number of list elements permissible in a STAT PDU"
        DEFVAL	{ 67 }
        ::= { wfAtmSscopEntry 15 }

    wfAtmSscopIdleTimer OBJECT-TYPE
        SYNTAX	INTEGER(1..400)
        ACCESS	read-write
        STATUS	mandatory
        DESCRIPTION
                "SSCOP Idle Timer. Timer used to determine when to enter the
                transient connection phase.  Units in tenths/second."
        DEFVAL	{ 150 }
        ::= { wfAtmSscopEntry 16 }

    wfAtmSscopStandard OBJECT-TYPE
        SYNTAX	INTEGER {
    		    v30(1),
    		    v31(2),
                    v40(3)
    		}
        ACCESS	read-write
        STATUS	mandatory
        DESCRIPTION
                "SSCOP version switch. UNI_V30, UNI_V31 and UNI_V40 for now. 
                Probably no more than this."
        DEFVAL	{ v30 }
        ::= { wfAtmSscopEntry 17 }

    wfAtmSscopDebug OBJECT-TYPE
        SYNTAX	INTEGER {
    		    disabled(1),
    		    status(2),
    		    detail(4),
    		    all(2147483647)
    		}
        ACCESS	read-write
        STATUS	mandatory
        DESCRIPTION
                "This flag will enable certain debug messages depending on the value set.
                The values are as follows:

                 1 - disable debugging
                 2 - SSCOP Status events
                 4294967295 - All of the above"
        DEFVAL	{ status }
        ::= { wfAtmSscopEntry 18 }

    wfAtmIlmiTable OBJECT-TYPE
        SYNTAX	SEQUENCE OF WfAtmIlmiEntry
        ACCESS	not-accessible
        STATUS	mandatory
        DESCRIPTION
                "This table includes the ATM ILMI MIB record for UME/ILMI"
        ::= { wfAtmCommonGroup 9 }

    wfAtmIlmiEntry OBJECT-TYPE
        SYNTAX	WfAtmIlmiEntry
        ACCESS	not-accessible
        STATUS	mandatory
        DESCRIPTION
                "This entry contains attributes needed for ATM UME/ILMI"
        INDEX	{ wfAtmIlmiLineNumber }
        ::= { wfAtmIlmiTable 1 }

    WfAtmIlmiEntry ::= SEQUENCE {
    	    wfAtmIlmiDelete
    		INTEGER,
    	    wfAtmIlmiDisable
    		INTEGER,
    	    wfAtmIlmiLineNumber
    		INTEGER,
    	    wfAtmIlmiAtmCct
    		INTEGER,
    	    wfAtmIlmiState
    		INTEGER,
    	    wfAtmIlmiLowThreshold
    		INTEGER,
    	    wfAtmIlmiUpThreshold
    		INTEGER,
    	    wfAtmIlmiVpi
    		INTEGER,
    	    wfAtmIlmiVci
    		INTEGER,
    	    wfAtmIlmiInterfaceType
    		INTEGER,
    	    wfAtmIlmiLocalPort
    		INTEGER,
    	    wfAtmIlmiRemotePort
    		INTEGER,
    	    wfAtmIlmiGetTimer
    		INTEGER,
    	    wfAtmIlmiGetRetryCnt
    		INTEGER,
    	    wfAtmIlmiGetNextTimer
    		INTEGER,
    	    wfAtmIlmiGetNextRetryCnt
    		INTEGER,
    	    wfAtmIlmiSetTimer
    		INTEGER,
    	    wfAtmIlmiSetRetryCnt
    		INTEGER,
    	    wfAtmIlmiLocalOid
    		OBJECT IDENTIFIER,
    	    wfAtmIlmiDebug
    		INTEGER,
            wfAtmIlmiNetPrefixTimer
                INTEGER
        }

    wfAtmIlmiDelete OBJECT-TYPE
        SYNTAX	INTEGER {
    		    created(1),
    		    deleted(2)
    		}
        ACCESS	read-write
        STATUS	mandatory
        DESCRIPTION
                "Create/Delete parameter. Default is created."
        DEFVAL	{ created }
        ::= { wfAtmIlmiEntry 1 }

    wfAtmIlmiDisable OBJECT-TYPE
        SYNTAX	INTEGER {
    		    enabled(1),
    		    disabled(2)
    		}
        ACCESS	read-write
        STATUS	mandatory
        DESCRIPTION
                "Enable/Disable parameter"
        DEFVAL	{ enabled }
        ::= { wfAtmIlmiEntry 2 }

    wfAtmIlmiLineNumber OBJECT-TYPE
        SYNTAX	INTEGER
        ACCESS	read-only
        STATUS	mandatory
        DESCRIPTION
                "Instance identifier. This value is the line number of the router."
        ::= { wfAtmIlmiEntry 3 }

    wfAtmIlmiAtmCct OBJECT-TYPE
        SYNTAX	INTEGER
        ACCESS	read-only
        STATUS	mandatory
        DESCRIPTION
                "Circuit number of ATM driver associated with this UME/ILMI instance"
        ::= { wfAtmIlmiEntry 4 }

    wfAtmIlmiState OBJECT-TYPE
        SYNTAX	INTEGER {
    		    up(1),
    		    down(2),
    		    init(3),
    		    notpresent(4)
    		}
        ACCESS	read-only
        STATUS	mandatory
        DESCRIPTION
                "Indicates the state of the UME/ILMI entity"
        DEFVAL	{ notpresent }
        ::= { wfAtmIlmiEntry 5 }

    wfAtmIlmiLowThreshold OBJECT-TYPE
        SYNTAX	INTEGER(1..10)
        ACCESS	read-write
        STATUS	mandatory
        DESCRIPTION
                "Congestion is reached when % of buffer pool goes below this threshold (sub)"
        DEFVAL	{ 2 }
        ::= { wfAtmIlmiEntry 6 }

    wfAtmIlmiUpThreshold OBJECT-TYPE
        SYNTAX	INTEGER(1..10)
        ACCESS	read-write
        STATUS	mandatory
        DESCRIPTION
                "Congestion is stopped when % of buffer pool goes above this threshold (sub)"
        DEFVAL	{ 2 }
        ::= { wfAtmIlmiEntry 7 }

    wfAtmIlmiVpi OBJECT-TYPE
        SYNTAX	INTEGER(1..255)
        ACCESS	read-write
        STATUS	mandatory
        DESCRIPTION
                "Virtual Path Identifier for the UME/ILMI VC"
        ::= { wfAtmIlmiEntry 8 }

    wfAtmIlmiVci OBJECT-TYPE
        SYNTAX	INTEGER(1..65535)
        ACCESS	read-write
        STATUS	mandatory
        DESCRIPTION
                "Virtual Channel Identifier for the UME/ILMI VC"
        DEFVAL	{ 16 }
        ::= { wfAtmIlmiEntry 9 }

    wfAtmIlmiInterfaceType OBJECT-TYPE
        SYNTAX	INTEGER {
    		    user(1),
    		    network(2)
    		}
        ACCESS	read-write
        STATUS	mandatory
        DESCRIPTION
                "Network Interface type, either USER or NETWORK side of the UME/ILMI"
        DEFVAL	{ user }
        ::= { wfAtmIlmiEntry 10 }

    wfAtmIlmiLocalPort OBJECT-TYPE
        SYNTAX	INTEGER
        ACCESS	read-only
        STATUS	mandatory
        DESCRIPTION
                "AAL UME/ILMI local port identifier"
        ::= { wfAtmIlmiEntry 11 }

    wfAtmIlmiRemotePort OBJECT-TYPE
        SYNTAX	INTEGER
        ACCESS	read-only
        STATUS	mandatory
        DESCRIPTION
                "AAL UME/ILMI remote port identifier"
        ::= { wfAtmIlmiEntry 12 }

    wfAtmIlmiGetTimer OBJECT-TYPE
        SYNTAX	INTEGER(1..120)
        ACCESS	read-write
        STATUS	mandatory
        DESCRIPTION
                "UME/ILMI Get request timer"
        DEFVAL	{ 3 }
        ::= { wfAtmIlmiEntry 13 }

    wfAtmIlmiGetRetryCnt OBJECT-TYPE
        SYNTAX	INTEGER(1..100)
        ACCESS	read-write
        STATUS	mandatory
        DESCRIPTION
                "Max number of retransmissions of the UME/ILMI GET request before link down"
        DEFVAL	{ 3 }
        ::= { wfAtmIlmiEntry 14 }

    wfAtmIlmiGetNextTimer OBJECT-TYPE
        SYNTAX	INTEGER(1..120)
        ACCESS	read-write
        STATUS	mandatory
        DESCRIPTION
                "UME/ILMI GetNext request timer"
        DEFVAL	{ 3 }
        ::= { wfAtmIlmiEntry 15 }

    wfAtmIlmiGetNextRetryCnt OBJECT-TYPE
        SYNTAX	INTEGER(1..100)
        ACCESS	read-write
        STATUS	mandatory
        DESCRIPTION
                "Max number of retransmits of the UME/ILMI GETNEXT request before link down"
        DEFVAL	{ 3 }
        ::= { wfAtmIlmiEntry 16 }

    wfAtmIlmiSetTimer OBJECT-TYPE
        SYNTAX	INTEGER(1..120)
        ACCESS	read-write
        STATUS	mandatory
        DESCRIPTION
                "UME/ILMI Set request timer"
        DEFVAL	{ 3 }
        ::= { wfAtmIlmiEntry 17 }

    wfAtmIlmiSetRetryCnt OBJECT-TYPE
        SYNTAX	INTEGER(1..100)
        ACCESS	read-write
        STATUS	mandatory
        DESCRIPTION
                "Max number of retransmissions of the UME/ILMI SET request before link down"
        DEFVAL	{ 3 }
        ::= { wfAtmIlmiEntry 18 }

    wfAtmIlmiLocalOid OBJECT-TYPE
        SYNTAX	OBJECT IDENTIFIER
        ACCESS	read-only
        STATUS	mandatory
        DESCRIPTION
                "Identifies the OID of the first object in the standard
                DS1 or DS3 MIB corresponding to this ATM UNI port"
        ::= { wfAtmIlmiEntry 19 }

    wfAtmIlmiDebug OBJECT-TYPE
        SYNTAX	INTEGER {
    		    disabled(1),
    		    status(2),
    		    detail(4),
    		    all(2147483647)
    		}
        ACCESS	read-write
        STATUS	mandatory
        DESCRIPTION
                "This flag will enable certain debug messages depending on the value set.
                The values are as follows:

                 1 - disable debugging
                 2 - ILMI Status events
                 4294967295 - All of the above"
        DEFVAL	{ status }
        ::= { wfAtmIlmiEntry 20 }

    wfAtmIlmiNetPrefixTimer OBJECT-TYPE
        SYNTAX  INTEGER(1..120)
        ACCESS  read-write
        STATUS  mandatory
        DESCRIPTION
                "Time to wait for a Net prefix before restarting UME"
        DEFVAL  { 8 }
        ::= { wfAtmIlmiEntry 21 }
 
    wfAtmNetPrefixTable OBJECT-TYPE
        SYNTAX	SEQUENCE OF WfAtmNetPrefixEntry
        ACCESS	not-accessible
        STATUS	mandatory
        DESCRIPTION
                "This table includes the ATM Network Address Prefix record"
        ::= { wfAtmCommonGroup 10 }

    wfAtmNetPrefixEntry OBJECT-TYPE
        SYNTAX	WfAtmNetPrefixEntry
        ACCESS	not-accessible
        STATUS	mandatory
        DESCRIPTION
                "This entry contains attributes needed for a ATM Network Address Prefix"
        INDEX	{ wfAtmNetPrefixPort,
    		  wfAtmNetPrefixPrefix }
        ::= { wfAtmNetPrefixTable 1 }

    WfAtmNetPrefixEntry ::= SEQUENCE {
    	    wfAtmNetPrefixPort
    		INTEGER,
    	    wfAtmNetPrefixPrefix
    		OCTET STRING,
    	    wfAtmNetPrefixStatus
    		INTEGER
        }

    wfAtmNetPrefixPort OBJECT-TYPE
        SYNTAX	INTEGER
        ACCESS	read-only
        STATUS	mandatory
        DESCRIPTION
                "Port which uniquely identifies the UNI (ie. InterfaceIndex or line number)"
        ::= { wfAtmNetPrefixEntry 1 }

    wfAtmNetPrefixPrefix OBJECT-TYPE
        SYNTAX	OCTET STRING
        ACCESS	read-only
        STATUS	mandatory
        DESCRIPTION
                "Network Prefix used on this UNI"
        ::= { wfAtmNetPrefixEntry 2 }

    wfAtmNetPrefixStatus OBJECT-TYPE
        SYNTAX	INTEGER {
    		    valid(1),
    		    invalid(2)
    		}
        ACCESS	read-only
        STATUS	mandatory
        DESCRIPTION
                "Status of Network Prefix (being used or not being used)"
        DEFVAL	{ valid }
        ::= { wfAtmNetPrefixEntry 3 }

    wfAtmTableDebugTable OBJECT-TYPE
        SYNTAX  SEQUENCE OF WfAtmTableDebugEntry
        ACCESS  not-accessible
        STATUS  mandatory
        DESCRIPTION
                "This is used to display the contents of internal ATM tables in the event log, for debug purposes."
        ::= { wfAtmCommonGroup 11 }
 
    wfAtmTableDebugEntry OBJECT-TYPE
        SYNTAX  WfAtmTableDebugEntry
        ACCESS  not-accessible
        STATUS  mandatory
        DESCRIPTION
                "This entry contains attributes needed for debugging internal ATM tables."
        INDEX   { wfAtmTableDebugSlot }
        ::= { wfAtmTableDebugTable 1 }
 
    WfAtmTableDebugEntry ::= SEQUENCE {
            wfAtmTableDebugDelete
                INTEGER,
            wfAtmTableDebugSlot
                INTEGER,
            wfAtmTableDebugType
                INTEGER
        }
 
    wfAtmTableDebugDelete OBJECT-TYPE
        SYNTAX  INTEGER {
                    created(1),
                    deleted(2)
                }
        ACCESS  read-write
        STATUS  mandatory
        DESCRIPTION
                "Create/Delete attribute."
        ::= { wfAtmTableDebugEntry 1 }
 
    wfAtmTableDebugSlot OBJECT-TYPE
        SYNTAX  INTEGER
        ACCESS  read-only
        STATUS  mandatory
        DESCRIPTION
                "Slot that we want to dump ATM tables from."
        ::= { wfAtmTableDebugEntry 2 }
 
    wfAtmTableDebugType OBJECT-TYPE
        SYNTAX  INTEGER
        ACCESS  read-write
        STATUS  mandatory
        DESCRIPTION
                "Slot that we want to dump ATM tables from."
        ::= { wfAtmTableDebugEntry 3 }
 
    wfAtmAlcDrvTable OBJECT-TYPE
        SYNTAX	SEQUENCE OF WfAtmAlcDrvEntry
        ACCESS	not-accessible
        STATUS	mandatory
        DESCRIPTION
                "This table contains line record entries for each driver
                responsible for the management and control of an ATM/ALC interface."
        ::= { wfAtmLinkModuleGroup 1 }

    wfAtmAlcDrvEntry OBJECT-TYPE
        SYNTAX	WfAtmAlcDrvEntry
        ACCESS	not-accessible
        STATUS	mandatory
        DESCRIPTION
                "Entry definition."
        INDEX	{ wfAtmAlcSlot,
    		  wfAtmAlcPort }
        ::= { wfAtmAlcDrvTable 1 }

    WfAtmAlcDrvEntry ::= SEQUENCE {
    	    wfAtmAlcDelete
    		INTEGER,
    	    wfAtmAlcDisable
    		INTEGER,
    	    wfAtmAlcState
    		INTEGER,
    	    wfAtmAlcSlot
    		INTEGER,
    	    wfAtmAlcPort
    		INTEGER,
    	    wfAtmAlcCct
    		INTEGER,
    	    wfAtmAlcLineNumber
    		INTEGER,
    	    wfAtmAlcType
    		INTEGER,
    	    wfAtmAlcMtu
    		INTEGER,
    	    wfAtmAlcSpeed
    		INTEGER,
    	    wfAtmAlcLastChange
    		TimeTicks,
    	    wfAtmAlcInterfaceStatus
    		INTEGER,
    	    wfAtmAlcInterfaceIndex
    		INTEGER,
    	    wfAtmAlcDpNotify
    		INTEGER,
    	    wfAtmAlcDpNotifyTimeout
    		INTEGER,
    	    wfAtmAlcConfControlQSize
    		INTEGER,
    	    wfAtmAlcConfIntqSize
    		INTEGER,
    	    wfAtmAlcConfLogqSize
    		INTEGER,
    	    wfAtmAlcConfNumXmtQueues
    		INTEGER,
    	    wfAtmAlcUseDebugger
    		INTEGER,
    	    wfAtmAlcConfXmtClipSlotMax
    		INTEGER,
    	    wfAtmAlcXmtClipSlotMax
    		INTEGER,
    	    wfAtmAlcConfXmtClipQueueMax
    		INTEGER,
    	    wfAtmAlcXmtClipQueueMax
    		INTEGER,
    	    wfAtmAlcConfXmtClipQueueMin
    		INTEGER,
    	    wfAtmAlcXmtClipQueueMin
    		INTEGER,
    	    wfAtmAlcXmtQueueBurst
    		INTEGER,
    	    wfAtmAlcXmtPackets
    		Counter,
    	    wfAtmAlcXmtPacketClips
    		Counter,
    	    wfAtmAlcXmtOctets
    		Counter,
    	    wfAtmAlcOutQLen
    		Gauge,
    	    wfAtmAlcRcvPackets
    		Counter,
    	    wfAtmAlcRcvReplenMisses
    		Counter,
    	    wfAtmAlcConfRcvBuffersMax
    		INTEGER,
    	    wfAtmAlcRcvBuffersMax
    		INTEGER,
    	    wfAtmAlcMadrCt
    		INTEGER,
    	    wfAtmAlcMadr
    		OCTET STRING,
    	    wfAtmAlcVcInactEnable
    		INTEGER,
	    wfAtmAlcXmtBadVcs
		Counter
        }

    wfAtmAlcDelete OBJECT-TYPE
        SYNTAX	INTEGER {
    		    create(1),
    		    delete(2)
    		}
        ACCESS	read-write
        STATUS	mandatory
        DESCRIPTION
                "Create/delete MIB instance parameter."
        DEFVAL	{ create }
        ::= { wfAtmAlcDrvEntry 1 }

    wfAtmAlcDisable OBJECT-TYPE
        SYNTAX	INTEGER {
    		    enabled(1),
    		    disabled(2)
    		}
        ACCESS	read-write
        STATUS	mandatory
        DESCRIPTION
                "Enable/disable driver parameter."
        DEFVAL	{ enabled }
        ::= { wfAtmAlcDrvEntry 2 }

    wfAtmAlcState OBJECT-TYPE
        SYNTAX	INTEGER {
    		    up(1),
    		    down(2),
    		    init(3),
    		    download(4),
    		    config(5),
    		    notpresent(20)
    		}
        ACCESS	read-only
        STATUS	mandatory
        DESCRIPTION
                "Driver state parameter. This parameter does not represent the state
                of the physical interface!"
        DEFVAL	{ notpresent }
        ::= { wfAtmAlcDrvEntry 3 }

    wfAtmAlcSlot OBJECT-TYPE
        SYNTAX	INTEGER(1..14)
        ACCESS	read-only
        STATUS	mandatory
        DESCRIPTION
                "Slot number -- instance id."
        ::= { wfAtmAlcDrvEntry 4 }

    wfAtmAlcPort OBJECT-TYPE
        SYNTAX	INTEGER {
    		    one(1),
    		    two(2),
    		    three(3),
    		    four(4)
    		}
        ACCESS	read-only
        STATUS	mandatory
        DESCRIPTION
                "Physical port number -- instance id."
        ::= { wfAtmAlcDrvEntry 5 }

    wfAtmAlcCct OBJECT-TYPE
        SYNTAX	INTEGER(1..1023)
        ACCESS	read-write
        STATUS	mandatory
        DESCRIPTION
                "Circuit number for the driver."
        ::= { wfAtmAlcDrvEntry 6 }

    wfAtmAlcLineNumber OBJECT-TYPE
        SYNTAX	INTEGER
        ACCESS	read-write
        STATUS	mandatory
        DESCRIPTION
                "Index value used to uniquely identify an instance of a physical
                ATM port. This index is generally chosen by SiteManager and shall
                be used as an instance identifier for ATM MIB objects."
        ::= { wfAtmAlcDrvEntry 7 }

    wfAtmAlcType OBJECT-TYPE
        SYNTAX	INTEGER {
    		    typesonet(1),
    		    typeds3(2),
    		    type100mb(3)
    		}
        ACCESS	read-only
        STATUS	mandatory
        DESCRIPTION
                "The type of interface. This attribute is an alias for 'ifType."
        ::= { wfAtmAlcDrvEntry 8 }

    wfAtmAlcMtu OBJECT-TYPE
        SYNTAX	INTEGER {
    		    default(4608)
    		}
        ACCESS	read-only
        STATUS	mandatory
        DESCRIPTION
                "The size of the largest packet which can be sent/received on the
                interface, specified in octets. This attribute is an alias for
                'ifMtu'."
        ::= { wfAtmAlcDrvEntry 9 }

    wfAtmAlcSpeed OBJECT-TYPE
        SYNTAX	INTEGER {
    		    speed155mb(155520000),
    		    speed100mb(100000000),
    		    speed45mb(44736000)
    		}
        ACCESS	read-only
        STATUS	mandatory
        DESCRIPTION
                "An estimate of the interface's current bandwidth in bits per
                second. This attribute is an alias for 'ifSpeed'."
        ::= { wfAtmAlcDrvEntry 10 }

    wfAtmAlcLastChange OBJECT-TYPE
        SYNTAX	TimeTicks
        ACCESS	read-only
        STATUS	mandatory
        DESCRIPTION
                "The time (in hundreths of a second) since the network management
                portion of the system was last re-initialized. This attribute is
                an alias for 'ifLastChange' in the MIBII System Group."
        ::= { wfAtmAlcDrvEntry 11 }

    wfAtmAlcInterfaceStatus OBJECT-TYPE
        SYNTAX	INTEGER {
    		    up(1),
    		    down(2),
    		    testing(3),
    		    unknown(4),
    		    dormant(5)
    		}
        ACCESS	read-only
        STATUS	mandatory
        DESCRIPTION
                "MIB-II ifOperStatus"
        DEFVAL	{ unknown }
        ::= { wfAtmAlcDrvEntry 12 }

    wfAtmAlcInterfaceIndex OBJECT-TYPE
        SYNTAX	INTEGER
        ACCESS	read-only
        STATUS	mandatory
        DESCRIPTION
                "MIB-II interface index"
        ::= { wfAtmAlcDrvEntry 13 }

    wfAtmAlcDpNotify OBJECT-TYPE
        SYNTAX	INTEGER {
    		    enabled(1),
    		    disabled(2)
    		}
        ACCESS	read-write
        STATUS	mandatory
        DESCRIPTION
                "Data Path (DP) notify function. This function, when enabled,
                will disable the DP interface when the physical interface becomes
                non-operational."
        DEFVAL	{ enabled }
        ::= { wfAtmAlcDrvEntry 14 }

    wfAtmAlcDpNotifyTimeout OBJECT-TYPE
        SYNTAX	INTEGER(0..3600)
        ACCESS	read-write
        STATUS	mandatory
        DESCRIPTION
                "Data Path (DP) notify function timeout period. This value specifies
                the number of seconds to wait before implementing the DP notify
                function. A timer will get set to this value when the state of
                the physical interface transitions from operational to
                non-operational when the DP notify function is enabled."
        DEFVAL	{ 3 }
        ::= { wfAtmAlcDrvEntry 15 }

    wfAtmAlcConfControlQSize OBJECT-TYPE
        SYNTAX	INTEGER {
    		    default(10)
    		}
        ACCESS	read-write
        STATUS	mandatory
        DESCRIPTION
                "Number of command elements in each of the two Host Interface control qs"
        DEFVAL	{ default }
        ::= { wfAtmAlcDrvEntry 16 }

    wfAtmAlcConfIntqSize OBJECT-TYPE
        SYNTAX	INTEGER {
    		    default(100)
    		}
        ACCESS	read-write
        STATUS	mandatory
        DESCRIPTION
                "Number of elements in the Host Interface interrupt queue"
        DEFVAL	{ default }
        ::= { wfAtmAlcDrvEntry 17 }

    wfAtmAlcConfLogqSize OBJECT-TYPE
        SYNTAX	INTEGER {
    		    default(25)
    		}
        ACCESS	read-write
        STATUS	mandatory
        DESCRIPTION
                "Number of elements in the Host Interface log queue"
        DEFVAL	{ default }
        ::= { wfAtmAlcDrvEntry 18 }

    wfAtmAlcConfNumXmtQueues OBJECT-TYPE
        SYNTAX	INTEGER(12..29)
        ACCESS	read-write
        STATUS	mandatory
        DESCRIPTION
                "Number of transmit queues in the Host Interface between the Host Driver
                and the CoP Driver"
        DEFVAL	{ 24 }
        ::= { wfAtmAlcDrvEntry 19 }

    wfAtmAlcUseDebugger OBJECT-TYPE
        SYNTAX	INTEGER {
    		    enabled(1),
    		    disabled(2)
    		}
        ACCESS	read-write
        STATUS	mandatory
        DESCRIPTION
                "This attribute controls a debugger which may be built into the Coprocessor
                image.  Shipped code does not include this debugger."
        DEFVAL	{ disabled }
        ::= { wfAtmAlcDrvEntry 20 }

    wfAtmAlcConfXmtClipSlotMax OBJECT-TYPE
        SYNTAX	INTEGER
        ACCESS	read-write
        STATUS	mandatory
        DESCRIPTION
                "Number of frames the slot may queue up for transmit before the Host Driver
                begins to clip.  Setting this attribute forces the driver to use the non
                zero value of the attribute rather than selecting a clip point
                automatically."
        ::= { wfAtmAlcDrvEntry 21 }

    wfAtmAlcXmtClipSlotMax OBJECT-TYPE
        SYNTAX	INTEGER
        ACCESS	read-only
        STATUS	mandatory
        DESCRIPTION
                "Number of buffers per slot beyond which the driver will clip on transmit.
                Set by the driver.  May be forced by setting
                wfAtmAlcConfXmtClipSlotMax != 0"
        ::= { wfAtmAlcDrvEntry 22 }

    wfAtmAlcConfXmtClipQueueMax OBJECT-TYPE
        SYNTAX	INTEGER
        ACCESS	read-write
        STATUS	mandatory
        DESCRIPTION
                "Number of frames a transmit queue may queue up before the Host Driver
                begins to clip.  Setting this attribute forces the driver to use the non
                zero value of the attribute rather than selecting a clip point
                automatically."
        ::= { wfAtmAlcDrvEntry 23 }

    wfAtmAlcXmtClipQueueMax OBJECT-TYPE
        SYNTAX	INTEGER
        ACCESS	read-only
        STATUS	mandatory
        DESCRIPTION
                "Number of buffers per transmit queue beyond which the driver will clip
                on transmit.  Set by the driver.  May be forced by setting
                wfAtmAlcConfXmtClipQueueMax != 0"
        ::= { wfAtmAlcDrvEntry 24 }

    wfAtmAlcConfXmtClipQueueMin OBJECT-TYPE
        SYNTAX	INTEGER
        ACCESS	read-write
        STATUS	mandatory
        DESCRIPTION
                "Number of frames a transmit queue will always be permitted to queue up
                regardless of the current value of wfAtmOutQLen relative to
                wfAtmXmtClipSlotMax.  Setting this attribute forces the driver to
                use the nonzero value of the attribute rather than selecting a clip point
                automatically."
        ::= { wfAtmAlcDrvEntry 25 }

    wfAtmAlcXmtClipQueueMin OBJECT-TYPE
        SYNTAX	INTEGER
        ACCESS	read-only
        STATUS	mandatory
        DESCRIPTION
                "Number of buffers each transmit queue is guaranteed to get before the
                driver clips due to the value of wfAtmXmtClipSlotMax.  Set by the
                driver.  May be forced by setting wfAtmAlcConfXmtClipQueueMin != 0"
        ::= { wfAtmAlcDrvEntry 26 }

    wfAtmAlcXmtQueueBurst OBJECT-TYPE
        SYNTAX	INTEGER {
    		    default(40)
    		}
        ACCESS	read-write
        STATUS	mandatory
        DESCRIPTION
                "Burst count for all transmit queues in CoP. Specifies the number
                of buffer(ettes) the CoP will process from a transmit queue in one
                service opportunity. A value of 0 (zero) will cause the CoP to
                burst forever (i.e., until either all data is transmitted from the
                queue or no more buffer(ette)s are available to transmit into."
        DEFVAL	{ default }
        ::= { wfAtmAlcDrvEntry 27 }

    wfAtmAlcXmtPackets OBJECT-TYPE
        SYNTAX	Counter
        ACCESS	read-only
        STATUS	mandatory
        DESCRIPTION
                "Count of Service Data Units (SDUs) transmitted without error."
        ::= { wfAtmAlcDrvEntry 28 }

    wfAtmAlcXmtPacketClips OBJECT-TYPE
        SYNTAX	Counter
        ACCESS	read-only
        STATUS	mandatory
        DESCRIPTION
                "Count of packets dropped on transmit."
        ::= { wfAtmAlcDrvEntry 29 }

    wfAtmAlcXmtOctets OBJECT-TYPE
        SYNTAX	Counter
        ACCESS	read-only
        STATUS	mandatory
        DESCRIPTION
                "Count of octets transmitted without error over the link interface.
                These octets are associated with user data only and not overhead or
                padding octets."
        ::= { wfAtmAlcDrvEntry 30 }

    wfAtmAlcOutQLen OBJECT-TYPE
        SYNTAX	Gauge
        ACCESS	read-only
        STATUS	mandatory
        DESCRIPTION
                "This attribute is an alias for 'ifOutQLen' in the MIBII interface
                group."
        ::= { wfAtmAlcDrvEntry 31 }

    wfAtmAlcRcvPackets OBJECT-TYPE
        SYNTAX	Counter
        ACCESS	read-only
        STATUS	mandatory
        DESCRIPTION
                "Count of Service Data Units (SDUs) received without error."
        ::= { wfAtmAlcDrvEntry 32 }

    wfAtmAlcRcvReplenMisses OBJECT-TYPE
        SYNTAX	Counter
        ACCESS	read-only
        STATUS	mandatory
        DESCRIPTION
                "Number of packet buffer misses while attempting to replenish driver
                receive ring."
        ::= { wfAtmAlcDrvEntry 33 }

    wfAtmAlcConfRcvBuffersMax OBJECT-TYPE
        SYNTAX	INTEGER
        ACCESS	read-write
        STATUS	mandatory
        DESCRIPTION
                "Number of buffers the driver will try to maintain on its receive queue.
                Setting this attribute forces the driver to use the non
                zero value of the attribute rather than selecting a buffer count
                automatically."
        ::= { wfAtmAlcDrvEntry 34 }

    wfAtmAlcRcvBuffersMax OBJECT-TYPE
        SYNTAX	INTEGER
        ACCESS	read-only
        STATUS	mandatory
        DESCRIPTION
                "Number of buffers which the driver will attempt to maintain on the receive
                queue.  Set by the driver.  May be forced by setting
                wfAtmAlcConfRcvBuffersMax != 0"
        ::= { wfAtmAlcDrvEntry 35 }

    wfAtmAlcMadrCt OBJECT-TYPE
        SYNTAX	INTEGER
        ACCESS	read-only
        STATUS	mandatory
        DESCRIPTION
                "Number of PROM-based MAC addresses."
        ::= { wfAtmAlcDrvEntry 36 }

    wfAtmAlcMadr OBJECT-TYPE
        SYNTAX	OCTET STRING
        ACCESS	read-only
        STATUS	mandatory
        DESCRIPTION
                "First MAC address in canonical format (i.e., 00-00-a2...). The number of
                subsequent MAC addresses is specified by wfAtmAlcMadrCt which are
                sequential."
        ::= { wfAtmAlcDrvEntry 37 }

    wfAtmAlcVcInactEnable OBJECT-TYPE
        SYNTAX	INTEGER {
    		    enable(1),
    		    disable(2)
    		}
        ACCESS	read-write
        STATUS	mandatory
        DESCRIPTION
                "Inactivity timeout function. When this function is enabled, all activated
                VCs will be polled, at an interval specified by wfAtmAlcCopVcInactTimeout,
                for inactivity."
        DEFVAL	{ enable }
        ::= { wfAtmAlcDrvEntry 38 }

    wfAtmAlcXmtBadVcs OBJECT-TYPE
	SYNTAX	Counter
        ACCESS	read-only
        STATUS	mandatory
        DESCRIPTION
                "Count of packets dropped on transmit because of an invalid VPI/VCI."
        ::= { wfAtmAlcDrvEntry 39 }

    wfAtmAlcXmtqTable OBJECT-TYPE
        SYNTAX	SEQUENCE OF WfAtmAlcXmtqEntry
        ACCESS	not-accessible
        STATUS	mandatory
        DESCRIPTION
                "Object created by the Host Driver, one for each transmit queue"
        ::= { wfAtmLinkModuleGroup 2 }

    wfAtmAlcXmtqEntry OBJECT-TYPE
        SYNTAX	WfAtmAlcXmtqEntry
        ACCESS	not-accessible
        STATUS	mandatory
        DESCRIPTION
                "An entry in the ATM Transmit Queue Table"
        INDEX	{ wfAtmAlcXmtqIndex,
    		  wfAtmAlcXmtqNumber }
        ::= { wfAtmAlcXmtqTable 1 }

    WfAtmAlcXmtqEntry ::= SEQUENCE {
    	    wfAtmAlcXmtqIndex
    		INTEGER,
    	    wfAtmAlcXmtqNumber
    		INTEGER,
    	    wfAtmAlcXmtqState
    		INTEGER,
    	    wfAtmAlcXmtqStickyMask
    		INTEGER,
    	    wfAtmAlcXmtqVcs
    		INTEGER,
    	    wfAtmAlcXmtqOutQLen
    		Gauge,
    	    wfAtmAlcXmtqOctets
    		Counter,
    	    wfAtmAlcXmtqPackets
    		Counter,
    	    wfAtmAlcXmtqPacketClips
    		Counter
        }

    wfAtmAlcXmtqIndex OBJECT-TYPE
        SYNTAX	INTEGER
        ACCESS	read-only
        STATUS	mandatory
        DESCRIPTION
                "Uniquely identifies the interface (port) that contains the
                appropriate management information."
        ::= { wfAtmAlcXmtqEntry 1 }

    wfAtmAlcXmtqNumber OBJECT-TYPE
        SYNTAX	INTEGER(3..28)
        ACCESS	read-only
        STATUS	mandatory
        DESCRIPTION
                "Identifies a particular instance of a transmit queue."
        ::= { wfAtmAlcXmtqEntry 2 }

    wfAtmAlcXmtqState OBJECT-TYPE
        SYNTAX	INTEGER {
    		    created(1),
    		    initdone(2),
    		    msgsent(3),
    		    notpresent(20)
    		}
        ACCESS	read-only
        STATUS	mandatory
        DESCRIPTION
                "State of the transmit queue."
        DEFVAL	{ notpresent }
        ::= { wfAtmAlcXmtqEntry 3 }

    wfAtmAlcXmtqStickyMask OBJECT-TYPE
        SYNTAX	INTEGER(1..2147483647)
        ACCESS	read-only
        STATUS	mandatory
        DESCRIPTION
                ""
        ::= { wfAtmAlcXmtqEntry 4 }

    wfAtmAlcXmtqVcs OBJECT-TYPE
        SYNTAX	INTEGER
        ACCESS	read-only
        STATUS	mandatory
        DESCRIPTION
                "Number of Virtual Connections (VCs) configured for this queue."
        ::= { wfAtmAlcXmtqEntry 5 }

    wfAtmAlcXmtqOutQLen OBJECT-TYPE
        SYNTAX	Gauge
        ACCESS	read-only
        STATUS	mandatory
        DESCRIPTION
                ""
        ::= { wfAtmAlcXmtqEntry 6 }

    wfAtmAlcXmtqOctets OBJECT-TYPE
        SYNTAX	Counter
        ACCESS	read-only
        STATUS	mandatory
        DESCRIPTION
                ""
        ::= { wfAtmAlcXmtqEntry 7 }

    wfAtmAlcXmtqPackets OBJECT-TYPE
        SYNTAX	Counter
        ACCESS	read-only
        STATUS	mandatory
        DESCRIPTION
                ""
        ::= { wfAtmAlcXmtqEntry 8 }

    wfAtmAlcXmtqPacketClips OBJECT-TYPE
        SYNTAX	Counter
        ACCESS	read-only
        STATUS	mandatory
        DESCRIPTION
                ""
        ::= { wfAtmAlcXmtqEntry 9 }

    wfAtmAlcCopConfTable OBJECT-TYPE
        SYNTAX	SEQUENCE OF WfAtmAlcCopConfEntry
        ACCESS	not-accessible
        STATUS	mandatory
        DESCRIPTION
                "This table contains basic CONFIGURATION information for the
                ATM/ALC CoProcessor (CoP) environment."
        ::= { wfAtmLinkModuleGroup 3 }

    wfAtmAlcCopConfEntry OBJECT-TYPE
        SYNTAX	WfAtmAlcCopConfEntry
        ACCESS	not-accessible
        STATUS	mandatory
        DESCRIPTION
                "Entry definition."
        INDEX	{ wfAtmAlcCopConfIndex }
        ::= { wfAtmAlcCopConfTable 1 }

    WfAtmAlcCopConfEntry ::= SEQUENCE {
    	    wfAtmAlcCopConfDelete
    		INTEGER,
    	    wfAtmAlcCopConfIndex
    		INTEGER,
    	    wfAtmAlcCopBufSize
    		INTEGER,
    	    wfAtmAlcCopConfXmtBufs
    		INTEGER,
    	    wfAtmAlcCopConfRcvBufs
    		INTEGER,
    	    wfAtmAlcCopDmaHighWatermark
    		INTEGER,
    	    wfAtmAlcCopDmaLowWatermark
    		INTEGER,
    	    wfAtmAlcCopCacheControl
    		INTEGER,
    	    wfAtmAlcCopHwModId
    		INTEGER,
    	    wfAtmAlcCopVcInactTimeout
    		INTEGER
        }

    wfAtmAlcCopConfDelete OBJECT-TYPE
        SYNTAX	INTEGER {
    		    create(1),
    		    delete(2)
    		}
        ACCESS	read-write
        STATUS	mandatory
        DESCRIPTION
                "Create/delete MIB instance parameter."
        DEFVAL	{ create }
        ::= { wfAtmAlcCopConfEntry 1 }

    wfAtmAlcCopConfIndex OBJECT-TYPE
        SYNTAX	INTEGER
        ACCESS	read-only
        STATUS	mandatory
        DESCRIPTION
                "Uniquely identifies the interface that contains the
                appropriate management information."
        ::= { wfAtmAlcCopConfEntry 2 }

    wfAtmAlcCopBufSize OBJECT-TYPE
        SYNTAX	INTEGER(128..1024)
        ACCESS	read-write
        STATUS	mandatory
        DESCRIPTION
                "Size in bytes of buffer(ettes)."
        DEFVAL	{ 532 }
        ::= { wfAtmAlcCopConfEntry 3 }

    wfAtmAlcCopConfXmtBufs OBJECT-TYPE
        SYNTAX	INTEGER(10..90)
        ACCESS	read-write
        STATUS	mandatory
        DESCRIPTION
                "Percentage of transmit buffers to allocate in relation to
                the total packet memory size."
        DEFVAL	{ 55 }
        ::= { wfAtmAlcCopConfEntry 4 }

    wfAtmAlcCopConfRcvBufs OBJECT-TYPE
        SYNTAX	INTEGER(10..90)
        ACCESS	read-write
        STATUS	mandatory
        DESCRIPTION
                "Percentage of receive buffers to allocate in relation to
                the total packet memory size."
        DEFVAL	{ 45 }
        ::= { wfAtmAlcCopConfEntry 5 }

    wfAtmAlcCopDmaHighWatermark OBJECT-TYPE
        SYNTAX	INTEGER(1..512)
        ACCESS	read-write
        STATUS	mandatory
        DESCRIPTION
                "DMA FIFO high watermark. This value determines the mark upon which
                the DMA controller will generate an interrupt specifying FIFO
                'almost full'."
        DEFVAL	{ 32 }
        ::= { wfAtmAlcCopConfEntry 6 }

    wfAtmAlcCopDmaLowWatermark OBJECT-TYPE
        SYNTAX	INTEGER(1..512)
        ACCESS	read-write
        STATUS	mandatory
        DESCRIPTION
                "DMA FIFO low watermark. This value determines the mark upon which
                the DMA controller will generate an interrupt specifying FIFO
                'almost empty'."
        DEFVAL	{ 128 }
        ::= { wfAtmAlcCopConfEntry 7 }

    wfAtmAlcCopCacheControl OBJECT-TYPE
        SYNTAX	INTEGER {
    		    both(1),
    		    icache(2),
    		    dcache(3),
    		    none(4)
    		}
        ACCESS	read-write
        STATUS	mandatory
        DESCRIPTION
                "Determines the state of the cache control register in the CoP."
        DEFVAL	{ both }
        ::= { wfAtmAlcCopConfEntry 8 }

    wfAtmAlcCopHwModId OBJECT-TYPE
        SYNTAX	INTEGER
        ACCESS	read-only
        STATUS	mandatory
        DESCRIPTION
                "Link module hardware identifier. Includes physical interface type."
        ::= { wfAtmAlcCopConfEntry 9 }

    wfAtmAlcCopVcInactTimeout OBJECT-TYPE
        SYNTAX	INTEGER(60..3600)
        ACCESS	read-write
        STATUS	mandatory
        DESCRIPTION
                "Inactivity timeout value for all VCs on this interface in seconds.
                If no cells have been transmitted or received on an VC over the given
                timeout period then the VC will be closed."
        DEFVAL	{ 1200 }
        ::= { wfAtmAlcCopConfEntry 10 }

    wfAtmAlcCopHwTable OBJECT-TYPE
        SYNTAX	SEQUENCE OF WfAtmAlcCopHwEntry
        ACCESS	not-accessible
        STATUS	mandatory
        DESCRIPTION
                "This table contains hardware information relating to the ATM/ALC
                link module."
        ::= { wfAtmLinkModuleGroup 4 }

    wfAtmAlcCopHwEntry OBJECT-TYPE
        SYNTAX	WfAtmAlcCopHwEntry
        ACCESS	not-accessible
        STATUS	mandatory
        DESCRIPTION
                "Entry definition."
        INDEX	{ wfAtmAlcCopHwIndex }
        ::= { wfAtmAlcCopHwTable 1 }

    WfAtmAlcCopHwEntry ::= SEQUENCE {
    	    wfAtmAlcCopHwIndex
    		INTEGER,
    	    wfAtmAlcCopType
    		INTEGER,
    	    wfAtmAlcCopPktMemSize
    		INTEGER,
    	    wfAtmAlcCopCtlMemSize
    		INTEGER,
    	    wfAtmAlcCopInsMemSize
    		INTEGER,
    	    wfAtmAlcCopAlcClockSpeed
    		INTEGER,
    	    wfAtmAlcCopAlcVersion
    		INTEGER,
    	    wfAtmAlcCopNtcVersion
    		INTEGER,
    	    wfAtmAlcCopAtcVersion
    		INTEGER
        }

    wfAtmAlcCopHwIndex OBJECT-TYPE
        SYNTAX	INTEGER
        ACCESS	read-only
        STATUS	mandatory
        DESCRIPTION
                "Uniquely identifies the interface that contains the
                appropriate management information."
        ::= { wfAtmAlcCopHwEntry 1 }

    wfAtmAlcCopType OBJECT-TYPE
        SYNTAX	INTEGER {
    		    m68040(1),
    		    m68060(2)
    		}
        ACCESS	read-only
        STATUS	mandatory
        DESCRIPTION
                "CoProcessor type."
        ::= { wfAtmAlcCopHwEntry 2 }

    wfAtmAlcCopPktMemSize OBJECT-TYPE
        SYNTAX	INTEGER
        ACCESS	read-only
        STATUS	mandatory
        DESCRIPTION
                "Size, in octets, of packet memory on the link module."
        ::= { wfAtmAlcCopHwEntry 3 }

    wfAtmAlcCopCtlMemSize OBJECT-TYPE
        SYNTAX	INTEGER
        ACCESS	read-only
        STATUS	mandatory
        DESCRIPTION
                "Size, in octets, of control memory on the link module."
        ::= { wfAtmAlcCopHwEntry 4 }

    wfAtmAlcCopInsMemSize OBJECT-TYPE
        SYNTAX	INTEGER
        ACCESS	read-only
        STATUS	mandatory
        DESCRIPTION
                "Size, in octets, of module memory on the link module."
        ::= { wfAtmAlcCopHwEntry 5 }

    wfAtmAlcCopAlcClockSpeed OBJECT-TYPE
        SYNTAX	INTEGER
        ACCESS	read-only
        STATUS	mandatory
        DESCRIPTION
                "Clock speed of the Adaptation Layer Controller (ALC) device."
        ::= { wfAtmAlcCopHwEntry 6 }

    wfAtmAlcCopAlcVersion OBJECT-TYPE
        SYNTAX	INTEGER
        ACCESS	read-only
        STATUS	mandatory
        DESCRIPTION
                "Revision of the Adaptation Layer Controller (ALC) device."
        ::= { wfAtmAlcCopHwEntry 7 }

    wfAtmAlcCopNtcVersion OBJECT-TYPE
        SYNTAX	INTEGER
        ACCESS	read-only
        STATUS	mandatory
        DESCRIPTION
                "Revision of the Network Termination Controller (NTC) device."
        ::= { wfAtmAlcCopHwEntry 8 }

    wfAtmAlcCopAtcVersion OBJECT-TYPE
        SYNTAX	INTEGER
        ACCESS	read-only
        STATUS	mandatory
        DESCRIPTION
                "Revision of the Address Translation Controller (ATC) device."
        ::= { wfAtmAlcCopHwEntry 9 }

    wfAtmAlcCopInfoTable OBJECT-TYPE
        SYNTAX	SEQUENCE OF WfAtmAlcCopInfoEntry
        ACCESS	not-accessible
        STATUS	mandatory
        DESCRIPTION
                "This table contains general CoP information."
        ::= { wfAtmLinkModuleGroup 5 }

    wfAtmAlcCopInfoEntry OBJECT-TYPE
        SYNTAX	WfAtmAlcCopInfoEntry
        ACCESS	not-accessible
        STATUS	mandatory
        DESCRIPTION
                "Entry definition."
        INDEX	{ wfAtmAlcCopInfoIndex }
        ::= { wfAtmAlcCopInfoTable 1 }

    WfAtmAlcCopInfoEntry ::= SEQUENCE {
    	    wfAtmAlcCopInfoIndex
    		INTEGER,
    	    wfAtmAlcCopState
    		INTEGER,
    	    wfAtmAlcCopConfigState
    		INTEGER,
    	    wfAtmAlcCopTotalBufs
    		INTEGER,
    	    wfAtmAlcCopTotalXmtBufs
    		INTEGER,
    	    wfAtmAlcCopTotalRcvBufs
    		INTEGER
        }

    wfAtmAlcCopInfoIndex OBJECT-TYPE
        SYNTAX	INTEGER
        ACCESS	read-only
        STATUS	mandatory
        DESCRIPTION
                "Uniquely identifies the interface that contains the
                appropriate management information."
        ::= { wfAtmAlcCopInfoEntry 1 }

    wfAtmAlcCopState OBJECT-TYPE
        SYNTAX	INTEGER {
    		    operational(1),
    		    nonoperational(2),
    		    init(3),
    		    config(4)
    		}
        ACCESS	read-only
        STATUS	mandatory
        DESCRIPTION
                "State of the CoP driver."
        ::= { wfAtmAlcCopInfoEntry 2 }

    wfAtmAlcCopConfigState OBJECT-TYPE
        SYNTAX	INTEGER {
    		    dma(1),
    		    sar(2),
    		    sartraf(4),
    		    sarpcrq(8),
    		    sarscrq(16),
    		    frmgen(32),
    		    frmrcv(64),
    		    frmxmt(128),
    		    frmoam(256),
    		    frmstats(512),
    		    frmcsi(1024),
    		    frmdma(2048),
    		    done(4095)
    		}
        ACCESS	read-only
        STATUS	mandatory
        DESCRIPTION
                "State of the configuration process. The CoP driver performs
                a series of configuration events for all the major components
                on the link module. This state show where in the configuration
                process the CoP driver resides. Until done, no data will be
                allowed to be transmitted or received."
        ::= { wfAtmAlcCopInfoEntry 3 }

    wfAtmAlcCopTotalBufs OBJECT-TYPE
        SYNTAX	INTEGER
        ACCESS	read-only
        STATUS	mandatory
        DESCRIPTION
                "Total number of buffers available for use in packet memory."
        ::= { wfAtmAlcCopInfoEntry 4 }

    wfAtmAlcCopTotalXmtBufs OBJECT-TYPE
        SYNTAX	INTEGER
        ACCESS	read-only
        STATUS	mandatory
        DESCRIPTION
                "Number of buffers allocated for transmit."
        ::= { wfAtmAlcCopInfoEntry 5 }

    wfAtmAlcCopTotalRcvBufs OBJECT-TYPE
        SYNTAX	INTEGER
        ACCESS	read-only
        STATUS	mandatory
        DESCRIPTION
                "Number of buffers allocated for receive."
        ::= { wfAtmAlcCopInfoEntry 6 }

    wfAtmAlcCopDataPathTable OBJECT-TYPE
        SYNTAX	SEQUENCE OF WfAtmAlcCopDataPathEntry
        ACCESS	not-accessible
        STATUS	mandatory
        DESCRIPTION
                "This table contains CoP data path statistics such as the number of
                packets, buffers, and cells transmitted and received."
        ::= { wfAtmLinkModuleGroup 6 }

    wfAtmAlcCopDataPathEntry OBJECT-TYPE
        SYNTAX	WfAtmAlcCopDataPathEntry
        ACCESS	not-accessible
        STATUS	mandatory
        DESCRIPTION
                "Entry definition."
        INDEX	{ wfAtmAlcCopDataPathIndex }
        ::= { wfAtmAlcCopDataPathTable 1 }

    WfAtmAlcCopDataPathEntry ::= SEQUENCE {
    	    wfAtmAlcCopDataPathIndex
    		INTEGER,
    	    wfAtmAlcCopXmtPackets
    		Counter,
    	    wfAtmAlcCopXmtBuffers
    		Counter,
    	    wfAtmAlcCopXmtErrBuffers
    		Counter,
    	    wfAtmAlcCopXmtCells
    		OCTET STRING,
    	    wfAtmAlcCopXmtUnassCells
    		Counter,
    	    wfAtmAlcCopXmtIdleCells
    		Counter,
    	    wfAtmAlcCopXmtUserCells
    		Counter,
    	    wfAtmAlcCopXmtOctets
    		Counter,
    	    wfAtmAlcCopRcvPackets
    		Counter,
    	    wfAtmAlcCopRcvClipPackets
    		Counter,
    	    wfAtmAlcCopRcvBuffers
    		Counter,
    	    wfAtmAlcCopRcvErrBuffers
    		Counter,
    	    wfAtmAlcCopRcvClipBuffers
    		Counter,
    	    wfAtmAlcCopRcvSarDropBuffers
    		Counter,
    	    wfAtmAlcCopRcvCells
    		OCTET STRING,
    	    wfAtmAlcCopRcvDropCells
    		Counter,
    	    wfAtmAlcCopRcvUnassCells
    		Counter,
    	    wfAtmAlcCopRcvIdleCells
    		Counter,
    	    wfAtmAlcCopRcvUserCells
    		Counter,
    	    wfAtmAlcCopRcvSarDropCells
    		Counter,
    	    wfAtmAlcCopRcvOctets
    		Counter,
    	    wfAtmAlcCopXmtOamCells
    		Counter,
    	    wfAtmAlcCopRcvOamCells
    		Counter,
    	    wfAtmAlcCopRcvOamCrcErrs
    		Counter
        }

    wfAtmAlcCopDataPathIndex OBJECT-TYPE
        SYNTAX	INTEGER
        ACCESS	read-only
        STATUS	mandatory
        DESCRIPTION
                "Uniquely identifies the interface that contains the
                appropriate management information."
        ::= { wfAtmAlcCopDataPathEntry 1 }

    wfAtmAlcCopXmtPackets OBJECT-TYPE
        SYNTAX	Counter
        ACCESS	read-only
        STATUS	mandatory
        DESCRIPTION
                "Total number of packets transferred to the link module."
        ::= { wfAtmAlcCopDataPathEntry 2 }

    wfAtmAlcCopXmtBuffers OBJECT-TYPE
        SYNTAX	Counter
        ACCESS	read-only
        STATUS	mandatory
        DESCRIPTION
                "Total number of CoP buffers used for segmentation (transmit)."
        ::= { wfAtmAlcCopDataPathEntry 3 }

    wfAtmAlcCopXmtErrBuffers OBJECT-TYPE
        SYNTAX	Counter
        ACCESS	read-only
        STATUS	mandatory
        DESCRIPTION
                "Total number of CoP transmit buffers returned in error by SAR
                device."
        ::= { wfAtmAlcCopDataPathEntry 4 }

    wfAtmAlcCopXmtCells OBJECT-TYPE
        SYNTAX	OCTET STRING
        ACCESS	read-only
        STATUS	mandatory
        DESCRIPTION
                "Total number of assigned ATM layer cells transmitted at the
                transceiver transmit interface (T-count). This attribute is
                a 64-bit counter."
        ::= { wfAtmAlcCopDataPathEntry 5 }

    wfAtmAlcCopXmtUnassCells OBJECT-TYPE
        SYNTAX	Counter
        ACCESS	read-only
        STATUS	mandatory
        DESCRIPTION
                ""
        ::= { wfAtmAlcCopDataPathEntry 6 }

    wfAtmAlcCopXmtIdleCells OBJECT-TYPE
        SYNTAX	Counter
        ACCESS	read-only
        STATUS	mandatory
        DESCRIPTION
                ""
        ::= { wfAtmAlcCopDataPathEntry 7 }

    wfAtmAlcCopXmtUserCells OBJECT-TYPE
        SYNTAX	Counter
        ACCESS	read-only
        STATUS	mandatory
        DESCRIPTION
                ""
        ::= { wfAtmAlcCopDataPathEntry 8 }

    wfAtmAlcCopXmtOctets OBJECT-TYPE
        SYNTAX	Counter
        ACCESS	read-only
        STATUS	mandatory
        DESCRIPTION
                "Count of octets transmitted (segmented) successfully."
        ::= { wfAtmAlcCopDataPathEntry 9 }

    wfAtmAlcCopRcvPackets OBJECT-TYPE
        SYNTAX	Counter
        ACCESS	read-only
        STATUS	mandatory
        DESCRIPTION
                "Total number of packets completely reassembled."
        ::= { wfAtmAlcCopDataPathEntry 10 }

    wfAtmAlcCopRcvClipPackets OBJECT-TYPE
        SYNTAX	Counter
        ACCESS	read-only
        STATUS	mandatory
        DESCRIPTION
                "Total number of packets dropped because no host buffers available
                to hold the incoming data."
        ::= { wfAtmAlcCopDataPathEntry 11 }

    wfAtmAlcCopRcvBuffers OBJECT-TYPE
        SYNTAX	Counter
        ACCESS	read-only
        STATUS	mandatory
        DESCRIPTION
                "Total number of CoP buffers used for reassembly."
        ::= { wfAtmAlcCopDataPathEntry 12 }

    wfAtmAlcCopRcvErrBuffers OBJECT-TYPE
        SYNTAX	Counter
        ACCESS	read-only
        STATUS	mandatory
        DESCRIPTION
                "Total number of CoP receive buffers returned in error by SAR
                device."
        ::= { wfAtmAlcCopDataPathEntry 13 }

    wfAtmAlcCopRcvClipBuffers OBJECT-TYPE
        SYNTAX	Counter
        ACCESS	read-only
        STATUS	mandatory
        DESCRIPTION
                "Total number of CoP buffers dropped because no receive buffer space
                were available to hold the incoming data."
        ::= { wfAtmAlcCopDataPathEntry 14 }

    wfAtmAlcCopRcvSarDropBuffers OBJECT-TYPE
        SYNTAX	Counter
        ACCESS	read-only
        STATUS	mandatory
        DESCRIPTION
                "Total number of CoP buffers dropped by the SAR device."
        ::= { wfAtmAlcCopDataPathEntry 15 }

    wfAtmAlcCopRcvCells OBJECT-TYPE
        SYNTAX	OCTET STRING
        ACCESS	read-only
        STATUS	mandatory
        DESCRIPTION
                "Total number of assigned ATM layer cells received at the
                transciever receive interface that have not been discarded
                (R-count). This attribute is a 64-bit counter."
        ::= { wfAtmAlcCopDataPathEntry 16 }

    wfAtmAlcCopRcvDropCells OBJECT-TYPE
        SYNTAX	Counter
        ACCESS	read-only
        STATUS	mandatory
        DESCRIPTION
                "Total number of cells received at the transceiver receive interface
                that have been discarded (D-count).

                The cells may have been discarded due to the following reasons:
                    physical layer cells
                    ATM layer cell with uncorrectable HEC error
                    ATM layer cell which has been discarded via the discard mask
                    protocol error"
        ::= { wfAtmAlcCopDataPathEntry 17 }

    wfAtmAlcCopRcvUnassCells OBJECT-TYPE
        SYNTAX	Counter
        ACCESS	read-only
        STATUS	mandatory
        DESCRIPTION
                ""
        ::= { wfAtmAlcCopDataPathEntry 18 }

    wfAtmAlcCopRcvIdleCells OBJECT-TYPE
        SYNTAX	Counter
        ACCESS	read-only
        STATUS	mandatory
        DESCRIPTION
                ""
        ::= { wfAtmAlcCopDataPathEntry 19 }

    wfAtmAlcCopRcvUserCells OBJECT-TYPE
        SYNTAX	Counter
        ACCESS	read-only
        STATUS	mandatory
        DESCRIPTION
                ""
        ::= { wfAtmAlcCopDataPathEntry 20 }

    wfAtmAlcCopRcvSarDropCells OBJECT-TYPE
        SYNTAX	Counter
        ACCESS	read-only
        STATUS	mandatory
        DESCRIPTION
                ""
        ::= { wfAtmAlcCopDataPathEntry 21 }

    wfAtmAlcCopRcvOctets OBJECT-TYPE
        SYNTAX	Counter
        ACCESS	read-only
        STATUS	mandatory
        DESCRIPTION
                "Count of octets received (reassembled) successfully."
        ::= { wfAtmAlcCopDataPathEntry 22 }

    wfAtmAlcCopXmtOamCells OBJECT-TYPE
        SYNTAX	Counter
        ACCESS	read-only
        STATUS	mandatory
        DESCRIPTION
                "Count of OAM cells transmitted successfully."
        ::= { wfAtmAlcCopDataPathEntry 23 }

    wfAtmAlcCopRcvOamCells OBJECT-TYPE
        SYNTAX	Counter
        ACCESS	read-only
        STATUS	mandatory
        DESCRIPTION
                "Count of OAM cells received successfully."
        ::= { wfAtmAlcCopDataPathEntry 24 }

    wfAtmAlcCopRcvOamCrcErrs OBJECT-TYPE
        SYNTAX	Counter
        ACCESS	read-only
        STATUS	mandatory
        DESCRIPTION
                "Count of OAM cells received with CRC10 error."
        ::= { wfAtmAlcCopDataPathEntry 25 }

    wfAtmAlcCopErrorTable OBJECT-TYPE
        SYNTAX	SEQUENCE OF WfAtmAlcCopErrorEntry
        ACCESS	not-accessible
        STATUS	mandatory
        DESCRIPTION
                "This table contains CoP error statistics."
        ::= { wfAtmLinkModuleGroup 7 }

    wfAtmAlcCopErrorEntry OBJECT-TYPE
        SYNTAX	WfAtmAlcCopErrorEntry
        ACCESS	not-accessible
        STATUS	mandatory
        DESCRIPTION
                "Entry definition."
        INDEX	{ wfAtmAlcCopErrorIndex }
        ::= { wfAtmAlcCopErrorTable 1 }

    WfAtmAlcCopErrorEntry ::= SEQUENCE {
    	    wfAtmAlcCopErrorIndex
    		INTEGER,
    	    wfAtmAlcCopHecDetects
    		Counter,
    	    wfAtmAlcCopHecCorrects
    		Counter,
    	    wfAtmAlcCopB2Febes
    		Counter,
    	    wfAtmAlcCopB3Febes
    		Counter,
    	    wfAtmAlcCopF1Febes
    		Counter,
    	    wfAtmAlcCopF3Febes
    		Counter,
    	    wfAtmAlcCopG1Febes
    		Counter,
    	    wfAtmAlcCopDropIntqEvents
    		Counter,
    	    wfAtmAlcCopDropLogqEvents
    		Counter,
    	    wfAtmAlcCopDmaFifoOverruns
    		Counter,
    	    wfAtmAlcCopDmaFifoUnderruns
    		Counter,
    	    wfAtmAlcCopLossSignals
    		Counter,
    	    wfAtmAlcCopLossFrames
    		Counter,
    	    wfAtmAlcCopLossPointers
    		Counter,
    	    wfAtmAlcCopOutCellDelins
    		Counter,
    	    wfAtmAlcCopInCellDelins
    		Counter,
    	    wfAtmAlcCopBufOverflows
    		Counter,
    	    wfAtmAlcCopXmtQueueFulls
    		Counter,
    	    wfAtmAlcCopXmtAtes
    		Counter,
    	    wfAtmAlcCopRcvQueueEmptys
    		Counter,
    	    wfAtmAlcCopRcvWriteFails
    		Counter,
    	    wfAtmAlcCopRcvQueueFulls
    		Counter,
    	    wfAtmAlcCopRcvAtes
    		Counter
        }

    wfAtmAlcCopErrorIndex OBJECT-TYPE
        SYNTAX	INTEGER
        ACCESS	read-only
        STATUS	mandatory
        DESCRIPTION
                "Uniquely identifies the interface that contains the
                appropriate management information."
        ::= { wfAtmAlcCopErrorEntry 1 }

    wfAtmAlcCopHecDetects OBJECT-TYPE
        SYNTAX	Counter
        ACCESS	read-only
        STATUS	mandatory
        DESCRIPTION
                ""
        ::= { wfAtmAlcCopErrorEntry 2 }

    wfAtmAlcCopHecCorrects OBJECT-TYPE
        SYNTAX	Counter
        ACCESS	read-only
        STATUS	mandatory
        DESCRIPTION
                ""
        ::= { wfAtmAlcCopErrorEntry 3 }

    wfAtmAlcCopB2Febes OBJECT-TYPE
        SYNTAX	Counter
        ACCESS	read-only
        STATUS	mandatory
        DESCRIPTION
                ""
        ::= { wfAtmAlcCopErrorEntry 4 }

    wfAtmAlcCopB3Febes OBJECT-TYPE
        SYNTAX	Counter
        ACCESS	read-only
        STATUS	mandatory
        DESCRIPTION
                ""
        ::= { wfAtmAlcCopErrorEntry 5 }

    wfAtmAlcCopF1Febes OBJECT-TYPE
        SYNTAX	Counter
        ACCESS	read-only
        STATUS	mandatory
        DESCRIPTION
                ""
        ::= { wfAtmAlcCopErrorEntry 6 }

    wfAtmAlcCopF3Febes OBJECT-TYPE
        SYNTAX	Counter
        ACCESS	read-only
        STATUS	mandatory
        DESCRIPTION
                ""
        ::= { wfAtmAlcCopErrorEntry 7 }

    wfAtmAlcCopG1Febes OBJECT-TYPE
        SYNTAX	Counter
        ACCESS	read-only
        STATUS	mandatory
        DESCRIPTION
                ""
        ::= { wfAtmAlcCopErrorEntry 8 }

    wfAtmAlcCopDropIntqEvents OBJECT-TYPE
        SYNTAX	Counter
        ACCESS	read-only
        STATUS	mandatory
        DESCRIPTION
                ""
        ::= { wfAtmAlcCopErrorEntry 9 }

    wfAtmAlcCopDropLogqEvents OBJECT-TYPE
        SYNTAX	Counter
        ACCESS	read-only
        STATUS	mandatory
        DESCRIPTION
                ""
        ::= { wfAtmAlcCopErrorEntry 10 }

    wfAtmAlcCopDmaFifoOverruns OBJECT-TYPE
        SYNTAX	Counter
        ACCESS	read-only
        STATUS	mandatory
        DESCRIPTION
                ""
        ::= { wfAtmAlcCopErrorEntry 11 }

    wfAtmAlcCopDmaFifoUnderruns OBJECT-TYPE
        SYNTAX	Counter
        ACCESS	read-only
        STATUS	mandatory
        DESCRIPTION
                ""
        ::= { wfAtmAlcCopErrorEntry 12 }

    wfAtmAlcCopLossSignals OBJECT-TYPE
        SYNTAX	Counter
        ACCESS	read-only
        STATUS	mandatory
        DESCRIPTION
                "Number of occurences of when the framer device detected loss
                of signal (i.e., no signal detect/no light)."
        ::= { wfAtmAlcCopErrorEntry 13 }

    wfAtmAlcCopLossFrames OBJECT-TYPE
        SYNTAX	Counter
        ACCESS	read-only
        STATUS	mandatory
        DESCRIPTION
                ""
        ::= { wfAtmAlcCopErrorEntry 14 }

    wfAtmAlcCopLossPointers OBJECT-TYPE
        SYNTAX	Counter
        ACCESS	read-only
        STATUS	mandatory
        DESCRIPTION
                ""
        ::= { wfAtmAlcCopErrorEntry 15 }

    wfAtmAlcCopOutCellDelins OBJECT-TYPE
        SYNTAX	Counter
        ACCESS	read-only
        STATUS	mandatory
        DESCRIPTION
                "Number of occurences of when the framer device went out of
                cell delineation."
        ::= { wfAtmAlcCopErrorEntry 16 }

    wfAtmAlcCopInCellDelins OBJECT-TYPE
        SYNTAX	Counter
        ACCESS	read-only
        STATUS	mandatory
        DESCRIPTION
                "Number of occurences of when the framer device went into
                cell delineation."
        ::= { wfAtmAlcCopErrorEntry 17 }

    wfAtmAlcCopBufOverflows OBJECT-TYPE
        SYNTAX	Counter
        ACCESS	read-only
        STATUS	mandatory
        DESCRIPTION
                ""
        ::= { wfAtmAlcCopErrorEntry 18 }

    wfAtmAlcCopXmtQueueFulls OBJECT-TYPE
        SYNTAX	Counter
        ACCESS	read-only
        STATUS	mandatory
        DESCRIPTION
                ""
        ::= { wfAtmAlcCopErrorEntry 19 }

    wfAtmAlcCopXmtAtes OBJECT-TYPE
        SYNTAX	Counter
        ACCESS	read-only
        STATUS	mandatory
        DESCRIPTION
                ""
        ::= { wfAtmAlcCopErrorEntry 20 }

    wfAtmAlcCopRcvQueueEmptys OBJECT-TYPE
        SYNTAX	Counter
        ACCESS	read-only
        STATUS	mandatory
        DESCRIPTION
                ""
        ::= { wfAtmAlcCopErrorEntry 21 }

    wfAtmAlcCopRcvWriteFails OBJECT-TYPE
        SYNTAX	Counter
        ACCESS	read-only
        STATUS	mandatory
        DESCRIPTION
                ""
        ::= { wfAtmAlcCopErrorEntry 22 }

    wfAtmAlcCopRcvQueueFulls OBJECT-TYPE
        SYNTAX	Counter
        ACCESS	read-only
        STATUS	mandatory
        DESCRIPTION
                ""
        ::= { wfAtmAlcCopErrorEntry 23 }

    wfAtmAlcCopRcvAtes OBJECT-TYPE
        SYNTAX	Counter
        ACCESS	read-only
        STATUS	mandatory
        DESCRIPTION
                ""
        ::= { wfAtmAlcCopErrorEntry 24 }

    wfAtmAlcSarConfTable OBJECT-TYPE
        SYNTAX	SEQUENCE OF WfAtmAlcSarConfEntry
        ACCESS	not-accessible
        STATUS	mandatory
        DESCRIPTION
                "This table contains configuration information for the
                ATM/ALC SAR device."
        ::= { wfAtmLinkModuleGroup 8 }

    wfAtmAlcSarConfEntry OBJECT-TYPE
        SYNTAX	WfAtmAlcSarConfEntry
        ACCESS	not-accessible
        STATUS	mandatory
        DESCRIPTION
                "Entry definition."
        INDEX	{ wfAtmAlcSarConfIndex }
        ::= { wfAtmAlcSarConfTable 1 }

    WfAtmAlcSarConfEntry ::= SEQUENCE {
    	    wfAtmAlcSarConfDelete
    		INTEGER,
    	    wfAtmAlcSarConfIndex
    		INTEGER,
    	    wfAtmAlcSarDmaBurstLength
    		INTEGER,
    	    wfAtmAlcSarDmaModeBw
    		INTEGER,
    	    wfAtmAlcSarDmaModeBmode
    		INTEGER,
    	    wfAtmAlcSarDmaModeOrder
    		INTEGER,
    	    wfAtmAlcSarDmaModeMmode
    		INTEGER,
    	    wfAtmAlcSarDmaModeCmode
    		INTEGER,
    	    wfAtmAlcSarDmaModeSync
    		INTEGER,
    	    wfAtmAlcSarControlRif
    		INTEGER,
    	    wfAtmAlcSarControlLoop
    		INTEGER,
    	    wfAtmAlcSarModeRtmr
    		INTEGER,
    	    wfAtmAlcSarModeRid
    		INTEGER,
    	    wfAtmAlcSarModeAal
    		INTEGER,
    	    wfAtmAlcSarModeDmask
    		INTEGER,
    	    wfAtmAlcSarModeDchain
    		INTEGER,
    	    wfAtmAlcSarModeSmode
    		INTEGER,
    	    wfAtmAlcSarModeBchain
    		INTEGER,
    	    wfAtmAlcSarModeHec
    		INTEGER,
    	    wfAtmAlcSarModeVpf
    		INTEGER,
    	    wfAtmAlcSarModeBas
    		INTEGER,
    	    wfAtmAlcSarModeAm
    		INTEGER,
    	    wfAtmAlcSarModeTrtl
    		INTEGER,
    	    wfAtmAlcSarTimeoutCtrPeriod
    		INTEGER,
    	    wfAtmAlcSarTimeoutCtrInt
    		INTEGER,
    	    wfAtmAlcSarMaxReceivePktLen
    		INTEGER
        }

    wfAtmAlcSarConfDelete OBJECT-TYPE
        SYNTAX	INTEGER {
    		    create(1),
    		    delete(2)
    		}
        ACCESS	read-write
        STATUS	mandatory
        DESCRIPTION
                "Create/delete MIB instance parameter."
        DEFVAL	{ create }
        ::= { wfAtmAlcSarConfEntry 1 }

    wfAtmAlcSarConfIndex OBJECT-TYPE
        SYNTAX	INTEGER
        ACCESS	read-only
        STATUS	mandatory
        DESCRIPTION
                "Uniquely identifies the interface that contains the
                appropriate management information."
        ::= { wfAtmAlcSarConfEntry 2 }

    wfAtmAlcSarDmaBurstLength OBJECT-TYPE
        SYNTAX	INTEGER(1..256)
        ACCESS	read-write
        STATUS	mandatory
        DESCRIPTION
                "Limits the max number of SAR DMA access cycles in a
                single block."
        DEFVAL	{ 1 }
        ::= { wfAtmAlcSarConfEntry 3 }

    wfAtmAlcSarDmaModeBw OBJECT-TYPE
        SYNTAX	INTEGER {
    		    bit32(1),
    		    bit64(2)
    		}
        ACCESS	read-write
        STATUS	mandatory
        DESCRIPTION
                "SAR memory interface width."
        DEFVAL	{ bit32 }
        ::= { wfAtmAlcSarConfEntry 4 }

    wfAtmAlcSarDmaModeBmode OBJECT-TYPE
        SYNTAX	INTEGER {
    		    intel(1),
    		    motorola(2)
    		}
        ACCESS	read-write
        STATUS	mandatory
        DESCRIPTION
                "SAR memory control signal mode."
        DEFVAL	{ intel }
        ::= { wfAtmAlcSarConfEntry 5 }

    wfAtmAlcSarDmaModeOrder OBJECT-TYPE
        SYNTAX	INTEGER {
    		    bigendian(1),
    		    littleendian(2)
    		}
        ACCESS	read-write
        STATUS	mandatory
        DESCRIPTION
                "SAR memory byte ordering convention."
        DEFVAL	{ bigendian }
        ::= { wfAtmAlcSarConfEntry 6 }

    wfAtmAlcSarDmaModeMmode OBJECT-TYPE
        SYNTAX	INTEGER {
    		    system(1),
    		    ram(2)
    		}
        ACCESS	read-write
        STATUS	mandatory
        DESCRIPTION
                "SAR memory mode."
        DEFVAL	{ ram }
        ::= { wfAtmAlcSarConfEntry 7 }

    wfAtmAlcSarDmaModeCmode OBJECT-TYPE
        SYNTAX	INTEGER {
    		    standard(1),
    		    fast(2)
    		}
        ACCESS	read-write
        STATUS	mandatory
        DESCRIPTION
                "SAR memory cycle time."
        DEFVAL	{ fast }
        ::= { wfAtmAlcSarConfEntry 8 }

    wfAtmAlcSarDmaModeSync OBJECT-TYPE
        SYNTAX	INTEGER {
    		    async(1),
    		    sync(2)
    		}
        ACCESS	read-write
        STATUS	mandatory
        DESCRIPTION
                "READY/DTACK signal treatment."
        DEFVAL	{ async }
        ::= { wfAtmAlcSarConfEntry 9 }

    wfAtmAlcSarControlRif OBJECT-TYPE
        SYNTAX	INTEGER {
    		    one(1)
    		}
        ACCESS	read-write
        STATUS	mandatory
        DESCRIPTION
                "Receive buffer ready interrupt frequency."
        DEFVAL	{ one }
        ::= { wfAtmAlcSarConfEntry 10 }

    wfAtmAlcSarControlLoop OBJECT-TYPE
        SYNTAX	INTEGER {
    		    enabled(1),
    		    disabled(2)
    		}
        ACCESS	read-write
        STATUS	mandatory
        DESCRIPTION
                "Loop transmit cell stream into receive cell stream interface."
        DEFVAL	{ disabled }
        ::= { wfAtmAlcSarConfEntry 11 }

    wfAtmAlcSarModeRtmr OBJECT-TYPE
        SYNTAX	INTEGER {
    		    notag(1),
    		    oneoctettag(2),
    		    twooctettag(3),
    		    threeoctettag(4)
    		}
        ACCESS	read-write
        STATUS	mandatory
        DESCRIPTION
                "Receive routing tag length."
        DEFVAL	{ notag }
        ::= { wfAtmAlcSarConfEntry 12 }

    wfAtmAlcSarModeRid OBJECT-TYPE
        SYNTAX	INTEGER {
    		    vci(1),
    		    mid(2)
    		}
        ACCESS	read-write
        STATUS	mandatory
        DESCRIPTION
                "Reassembly ID select."
        DEFVAL	{ vci }
        ::= { wfAtmAlcSarConfEntry 13 }

    wfAtmAlcSarModeAal OBJECT-TYPE
        SYNTAX	INTEGER {
    		    set(1),
    		    clear(2)
    		}
        ACCESS	read-write
        STATUS	mandatory
        DESCRIPTION
                "Default receive status/descriptor type field setting."
        DEFVAL	{ clear }
        ::= { wfAtmAlcSarConfEntry 14 }

    wfAtmAlcSarModeDmask OBJECT-TYPE
        SYNTAX	INTEGER {
    		    enabled(1),
    		    disabled(2)
    		}
        ACCESS	read-write
        STATUS	mandatory
        DESCRIPTION
                "Disable transmit queue masking."
        DEFVAL	{ enabled }
        ::= { wfAtmAlcSarConfEntry 15 }

    wfAtmAlcSarModeDchain OBJECT-TYPE
        SYNTAX	INTEGER {
    		    enabled(1),
    		    disabled(2)
    		}
        ACCESS	read-write
        STATUS	mandatory
        DESCRIPTION
                "Transmit cell stream daisy chain enable."
        DEFVAL	{ disabled }
        ::= { wfAtmAlcSarConfEntry 16 }

    wfAtmAlcSarModeSmode OBJECT-TYPE
        SYNTAX	INTEGER {
    		    enabled(1),
    		    disabled(2)
    		}
        ACCESS	read-write
        STATUS	mandatory
        DESCRIPTION
                "Receive streaming mode enable."
        DEFVAL	{ enabled }
        ::= { wfAtmAlcSarConfEntry 17 }

    wfAtmAlcSarModeBchain OBJECT-TYPE
        SYNTAX	INTEGER {
    		    enabled(1),
    		    disabled(2)
    		}
        ACCESS	read-write
        STATUS	mandatory
        DESCRIPTION
                "Receive buffer chaining mode enable."
        DEFVAL	{ disabled }
        ::= { wfAtmAlcSarConfEntry 18 }

    wfAtmAlcSarModeHec OBJECT-TYPE
        SYNTAX	INTEGER {
    		    enabled(1),
    		    disabled(2)
    		}
        ACCESS	read-write
        STATUS	mandatory
        DESCRIPTION
                "Header error check operation."
        DEFVAL	{ enabled }
        ::= { wfAtmAlcSarConfEntry 19 }

    wfAtmAlcSarModeVpf OBJECT-TYPE
        SYNTAX	INTEGER {
    		    enabled(1),
    		    disabled(2)
    		}
        ACCESS	read-write
        STATUS	mandatory
        DESCRIPTION
                "Virtual path filter enable."
        DEFVAL	{ disabled }
        ::= { wfAtmAlcSarConfEntry 20 }

    wfAtmAlcSarModeBas OBJECT-TYPE
        SYNTAX	INTEGER {
    		    enabled(1),
    		    disabled(2)
    		}
        ACCESS	read-write
        STATUS	mandatory
        DESCRIPTION
                "Buffer ageing support."
        DEFVAL	{ disabled }
        ::= { wfAtmAlcSarConfEntry 21 }

    wfAtmAlcSarModeAm OBJECT-TYPE
        SYNTAX	INTEGER {
    		    trickle(1),
    		    burst(2)
    		}
        ACCESS	read-write
        STATUS	mandatory
        DESCRIPTION
                "Traffic rate averaging method."
        DEFVAL	{ trickle }
        ::= { wfAtmAlcSarConfEntry 22 }

    wfAtmAlcSarModeTrtl OBJECT-TYPE
        SYNTAX	INTEGER {
    		    notag(1),
    		    oneoctettag(2),
    		    twooctettag(3),
    		    threeoctettag(4)
    		}
        ACCESS	read-write
        STATUS	mandatory
        DESCRIPTION
                "Transmit routing tag length."
        DEFVAL	{ notag }
        ::= { wfAtmAlcSarConfEntry 23 }

    wfAtmAlcSarTimeoutCtrPeriod OBJECT-TYPE
        SYNTAX	INTEGER
        ACCESS	read-write
        STATUS	mandatory
        DESCRIPTION
                "Number of DCCK clock periods required to increment the
                receive buffer ageing time base counter."
        ::= { wfAtmAlcSarConfEntry 24 }

    wfAtmAlcSarTimeoutCtrInt OBJECT-TYPE
        SYNTAX	INTEGER
        ACCESS	read-write
        STATUS	mandatory
        DESCRIPTION
                "Maximum time period allowed between the arrival of an
                incoming packet and the host servicing the receive buffer."
        ::= { wfAtmAlcSarConfEntry 25 }

    wfAtmAlcSarMaxReceivePktLen OBJECT-TYPE
        SYNTAX	INTEGER {
    		    default(4608)
    		}
        ACCESS	read-write
        STATUS	mandatory
        DESCRIPTION
                "Maximum number of bytes of incoming packet data that can
                be received."
        DEFVAL	{ default }
        ::= { wfAtmAlcSarConfEntry 26 }

    wfAtmAlcSarTrafficMgtTable OBJECT-TYPE
        SYNTAX	SEQUENCE OF WfAtmAlcSarTrafficMgtEntry
        ACCESS	not-accessible
        STATUS	mandatory
        DESCRIPTION
                "This table contains information relating to the traffic
                management controller in the ATM/ALC SAR device."
        ::= { wfAtmLinkModuleGroup 9 }

    wfAtmAlcSarTrafficMgtEntry OBJECT-TYPE
        SYNTAX	WfAtmAlcSarTrafficMgtEntry
        ACCESS	not-accessible
        STATUS	mandatory
        DESCRIPTION
                "Entry definition."
        INDEX	{ wfAtmAlcSarTrafficMgtIndex }
        ::= { wfAtmAlcSarTrafficMgtTable 1 }

    WfAtmAlcSarTrafficMgtEntry ::= SEQUENCE {
    	    wfAtmAlcSarTrafficMgtDelete
    		INTEGER,
    	    wfAtmAlcSarTrafficMgtIndex
    		INTEGER,
    	    wfAtmAlcSarPeakCellRateEna
    		INTEGER,
    	    wfAtmAlcSarAvgCellRateEna
    		INTEGER,
    	    wfAtmAlcSarPeakCellRate
    		INTEGER,
    	    wfAtmAlcSarAvgCellRate
    		INTEGER,
    	    wfAtmAlcSarMaxBurstSize
    		INTEGER
        }

    wfAtmAlcSarTrafficMgtDelete OBJECT-TYPE
        SYNTAX	INTEGER {
    		    create(1),
    		    delete(2)
    		}
        ACCESS	read-write
        STATUS	mandatory
        DESCRIPTION
                "Create/delete MIB instance parameter."
        DEFVAL	{ create }
        ::= { wfAtmAlcSarTrafficMgtEntry 1 }

    wfAtmAlcSarTrafficMgtIndex OBJECT-TYPE
        SYNTAX	INTEGER
        ACCESS	read-only
        STATUS	mandatory
        DESCRIPTION
                "Uniquely identifies the interface that contains the
                appropriate management information."
        ::= { wfAtmAlcSarTrafficMgtEntry 2 }

    wfAtmAlcSarPeakCellRateEna OBJECT-TYPE
        SYNTAX	INTEGER {
    		    enabled(1),
    		    disabled(2)
    		}
        ACCESS	read-write
        STATUS	mandatory
        DESCRIPTION
                "Enable counter for SAR peak transmission rate."
        DEFVAL	{ enabled }
        ::= { wfAtmAlcSarTrafficMgtEntry 3 }

    wfAtmAlcSarAvgCellRateEna OBJECT-TYPE
        SYNTAX	INTEGER {
    		    enabled(1),
    		    disabled(2)
    		}
        ACCESS	read-write
        STATUS	mandatory
        DESCRIPTION
                "Enable counter for SAR average trasnmission rate."
        DEFVAL	{ enabled }
        ::= { wfAtmAlcSarTrafficMgtEntry 4 }

    wfAtmAlcSarPeakCellRate OBJECT-TYPE
        SYNTAX	INTEGER {
    		    default(365566)
    		}
        ACCESS	read-write
        STATUS	mandatory
        DESCRIPTION
                "Desired value for SAR total peak cell rate (cells/second)."
        DEFVAL	{ default }
        ::= { wfAtmAlcSarTrafficMgtEntry 5 }

    wfAtmAlcSarAvgCellRate OBJECT-TYPE
        SYNTAX	INTEGER {
    		    default(365566)
    		}
        ACCESS	read-write
        STATUS	mandatory
        DESCRIPTION
                "Desired value for SAR total average cell rate (cells/second)."
        DEFVAL	{ default }
        ::= { wfAtmAlcSarTrafficMgtEntry 6 }

    wfAtmAlcSarMaxBurstSize OBJECT-TYPE
        SYNTAX	INTEGER {
    		    default(40)
    		}
        ACCESS	read-write
        STATUS	mandatory
        DESCRIPTION
                "Desired value for SAR maximum burst size (cells)."
        DEFVAL	{ default }
        ::= { wfAtmAlcSarTrafficMgtEntry 7 }

    wfAtmAlcSarRateQueueTable OBJECT-TYPE
        SYNTAX	SEQUENCE OF WfAtmAlcSarRateQueueEntry
        ACCESS	not-accessible
        STATUS	mandatory
        DESCRIPTION
                "This table contains information relating to the peak rate
                queues provided by the ATM/ALC SAR device."
        ::= { wfAtmLinkModuleGroup 10 }

    wfAtmAlcSarRateQueueEntry OBJECT-TYPE
        SYNTAX	WfAtmAlcSarRateQueueEntry
        ACCESS	not-accessible
        STATUS	mandatory
        DESCRIPTION
                "Entry definition."
        INDEX	{ wfAtmAlcSarRateQueueIndex,
    		  wfAtmAlcSarRateQueueNumber }
        ::= { wfAtmAlcSarRateQueueTable 1 }

    WfAtmAlcSarRateQueueEntry ::= SEQUENCE {
    	    wfAtmAlcSarRateQueueIndex
    		INTEGER,
    	    wfAtmAlcSarRateQueueNumber
    		INTEGER,
    	    wfAtmAlcSarRateQueueState
    		INTEGER,
    	    wfAtmAlcSarRateQueuePcr
    		INTEGER,
    	    wfAtmAlcSarRateQueueVcs
    		INTEGER,
    	    wfAtmAlcSarRateQueueDef
    		INTEGER
        }

    wfAtmAlcSarRateQueueIndex OBJECT-TYPE
        SYNTAX	INTEGER
        ACCESS	read-only
        STATUS	mandatory
        DESCRIPTION
                "Uniquely identifies the interface that contains the
                appropriate management information."
        ::= { wfAtmAlcSarRateQueueEntry 1 }

    wfAtmAlcSarRateQueueNumber OBJECT-TYPE
        SYNTAX	INTEGER(1..12)
        ACCESS	read-only
        STATUS	mandatory
        DESCRIPTION
                "Identifies a particular instance of a rate queue."
        ::= { wfAtmAlcSarRateQueueEntry 2 }

    wfAtmAlcSarRateQueueState OBJECT-TYPE
        SYNTAX	INTEGER {
    		    enabled(1),
    		    disabled(2)
    		}
        ACCESS	read-only
        STATUS	mandatory
        DESCRIPTION
                "Rate queue state parameter: enabled or disabled."
        ::= { wfAtmAlcSarRateQueueEntry 3 }

    wfAtmAlcSarRateQueuePcr OBJECT-TYPE
        SYNTAX	INTEGER
        ACCESS	read-only
        STATUS	mandatory
        DESCRIPTION
                "Peak Cell Rate (PCR) of rate queue defined in bits per second."
        ::= { wfAtmAlcSarRateQueueEntry 4 }

    wfAtmAlcSarRateQueueVcs OBJECT-TYPE
        SYNTAX	INTEGER
        ACCESS	read-only
        STATUS	mandatory
        DESCRIPTION
                "Number of Virtual Connections (VCs) configured for this queue."
        ::= { wfAtmAlcSarRateQueueEntry 5 }

    wfAtmAlcSarRateQueueDef OBJECT-TYPE
        SYNTAX	INTEGER {
    		    implicit(1),
    		    explicit(2)
    		}
        ACCESS	read-only
        STATUS	mandatory
        DESCRIPTION
                "Indicates the method by which this queue was defined: IMPLICIT means
                that the driver defined the queue when a VC was added; EXPLICIT means
                that the queue was explicitly defined by an entity other than the driver."
        ::= { wfAtmAlcSarRateQueueEntry 6 }

    wfAtmAlcFrmConfTable OBJECT-TYPE
        SYNTAX	SEQUENCE OF WfAtmAlcFrmConfEntry
        ACCESS	not-accessible
        STATUS	mandatory
        DESCRIPTION
                "This table contains configuration information for the
                ATM/ALC FRAMER device."
        ::= { wfAtmLinkModuleGroup 11 }

    wfAtmAlcFrmConfEntry OBJECT-TYPE
        SYNTAX	WfAtmAlcFrmConfEntry
        ACCESS	not-accessible
        STATUS	mandatory
        DESCRIPTION
                "Entry definition."
        INDEX	{ wfAtmAlcFrmConfIndex }
        ::= { wfAtmAlcFrmConfTable 1 }

    WfAtmAlcFrmConfEntry ::= SEQUENCE {
    	    wfAtmAlcFrmConfDelete
    		INTEGER,
    	    wfAtmAlcFrmConfIndex
    		INTEGER,
    	    wfAtmAlcFrmGenEnable
    		INTEGER,
    	    wfAtmAlcFrmGenFramingMode
    		INTEGER,
    	    wfAtmAlcFrmGenScramblerEna
    		INTEGER,
    	    wfAtmAlcFrmGenDescrambleEna
    		INTEGER,
    	    wfAtmAlcFrmGenLoopback
    		INTEGER,
    	    wfAtmAlcFrmGenSyncFoundCnt
    		INTEGER,
    	    wfAtmAlcFrmGenSyncLostCnt
    		INTEGER,
    	    wfAtmAlcFrmRcvCellEnable
    		INTEGER,
    	    wfAtmAlcFrmRcvOamCrcCheck
    		INTEGER,
    	    wfAtmAlcFrmRcvOamCrcGen
    		INTEGER,
    	    wfAtmAlcFrmRcvCellInsPrio
    		INTEGER,
    	    wfAtmAlcFrmRcvInsertPcr
    		INTEGER,
    	    wfAtmAlcFrmRcvGfcIgnore
    		INTEGER,
    	    wfAtmAlcFrmRcvDescrambleCtl
    		INTEGER,
    	    wfAtmAlcFrmRcvHecRcvMask
    		INTEGER,
    	    wfAtmAlcFrmRcvErrCorrectEna
    		INTEGER,
    	    wfAtmAlcFrmRcvByteAlignment
    		INTEGER,
    	    wfAtmAlcFrmRcvCellSyncFound
    		INTEGER,
    	    wfAtmAlcFrmRcvCellSyncLost
    		INTEGER,
    	    wfAtmAlcFrmRcvExtUserCell
    		INTEGER,
    	    wfAtmAlcFrmRcvExtMetaSig
    		INTEGER,
    	    wfAtmAlcFrmRcvExtBcastSig
    		INTEGER,
    	    wfAtmAlcFrmRcvExtPointSig
    		INTEGER,
    	    wfAtmAlcFrmRcvExtIlmiSig
    		INTEGER,
    	    wfAtmAlcFrmRcvExtF4F5PrfMan
    		INTEGER,
    	    wfAtmAlcFrmRcvExtF1F3PlOam
    		INTEGER,
    	    wfAtmAlcFrmRcvExtF4Segment
    		INTEGER,
    	    wfAtmAlcFrmRcvExtF4EndEnd
    		INTEGER,
    	    wfAtmAlcFrmRcvExtF5Segment
    		INTEGER,
    	    wfAtmAlcFrmRcvExtF5EndEnd
    		INTEGER,
    	    wfAtmAlcFrmRcvDisUserCell
    		INTEGER,
    	    wfAtmAlcFrmRcvDisMetaSig
    		INTEGER,
    	    wfAtmAlcFrmRcvDisBcastSig
    		INTEGER,
    	    wfAtmAlcFrmRcvDisPointSig
    		INTEGER,
    	    wfAtmAlcFrmRcvDisIlmiSig
    		INTEGER,
    	    wfAtmAlcFrmRcvDisUnassCell
    		INTEGER,
    	    wfAtmAlcFrmRcvDisF4Segment
    		INTEGER,
    	    wfAtmAlcFrmRcvDisF4EndEnd
    		INTEGER,
    	    wfAtmAlcFrmRcvDisF5Segment
    		INTEGER,
    	    wfAtmAlcFrmRcvDisF5EndEnd
    		INTEGER,
    	    wfAtmAlcFrmXmtCellEnable
    		INTEGER,
    	    wfAtmAlcFrmXmtOamCrcCheck
    		INTEGER,
    	    wfAtmAlcFrmXmtOamCrcGen
    		INTEGER,
    	    wfAtmAlcFrmXmtCellInsPrio
    		INTEGER,
    	    wfAtmAlcFrmXmtInsertPcr
    		INTEGER,
    	    wfAtmAlcFrmXmtGfcIgnore
    		INTEGER,
    	    wfAtmAlcFrmXmtCellDecouple
    		INTEGER,
    	    wfAtmAlcFrmXmtScrambleCtl
    		INTEGER,
    	    wfAtmAlcFrmXmtHecXmtMask
    		INTEGER,
    	    wfAtmAlcFrmXmtExtUserCell
    		INTEGER,
    	    wfAtmAlcFrmXmtExtMetaSig
    		INTEGER,
    	    wfAtmAlcFrmXmtExtBcastSig
    		INTEGER,
    	    wfAtmAlcFrmXmtExtPointSig
    		INTEGER,
    	    wfAtmAlcFrmXmtExtIlmiSig
    		INTEGER,
    	    wfAtmAlcFrmXmtExtF4F5PrfMan
    		INTEGER,
    	    wfAtmAlcFrmXmtExtF4Segment
    		INTEGER,
    	    wfAtmAlcFrmXmtExtF4EndEnd
    		INTEGER,
    	    wfAtmAlcFrmXmtExtF5Segment
    		INTEGER,
    	    wfAtmAlcFrmXmtExtF5EndEnd
    		INTEGER,
    	    wfAtmAlcFrmXmtDisUserCell
    		INTEGER,
    	    wfAtmAlcFrmXmtDisMetaSig
    		INTEGER,
    	    wfAtmAlcFrmXmtDisBcastSig
    		INTEGER,
    	    wfAtmAlcFrmXmtDisPointSig
    		INTEGER,
    	    wfAtmAlcFrmXmtDisIlmiSig
    		INTEGER,
    	    wfAtmAlcFrmXmtDisUnassCell
    		INTEGER,
    	    wfAtmAlcFrmXmtDisF4Segment
    		INTEGER,
    	    wfAtmAlcFrmXmtDisF4EndEnd
    		INTEGER,
    	    wfAtmAlcFrmXmtDisF5Segment
    		INTEGER,
    	    wfAtmAlcFrmXmtDisF5EndEnd
    		INTEGER,
    	    wfAtmAlcFrmOamEnable
    		INTEGER,
    	    wfAtmAlcFrmOamInvertBip
    		INTEGER,
    	    wfAtmAlcFrmOamTxPathFerf
    		INTEGER,
    	    wfAtmAlcFrmOamTxSectionFerf
    		INTEGER,
    	    wfAtmAlcFrmOamTxPathAis
    		INTEGER,
    	    wfAtmAlcFrmOamTxSectionAis
    		INTEGER,
    	    wfAtmAlcFrmOamTxPathFebe
    		INTEGER,
    	    wfAtmAlcFrmOamTxSectionFebe
    		INTEGER,
    	    wfAtmAlcFrmStatsSwEnable
    		INTEGER,
    	    wfAtmAlcFrmStatsMode
    		INTEGER,
    	    wfAtmAlcFrmStatsReceive
    		INTEGER,
    	    wfAtmAlcFrmStatsTransmit
    		INTEGER,
    	    wfAtmAlcFrmStatsMask
    		INTEGER,
    	    wfAtmAlcFrmStatsTimeout
    		INTEGER,
    	    wfAtmAlcFrmStatsTimerEna
    		INTEGER,
    	    wfAtmAlcFrmStatsOflowEna
    		INTEGER,
    	    wfAtmAlcFrmStatsForceDma
    		INTEGER,
    	    wfAtmAlcFrmCsiEnable
    		INTEGER,
    	    wfAtmAlcFrmCsiLoop
    		INTEGER,
    	    wfAtmAlcFrmCsiRcvAtcEnable
    		INTEGER,
    	    wfAtmAlcFrmCsiRcvAte
    		INTEGER,
    	    wfAtmAlcFrmCsiRcvClpBitOpt
    		INTEGER,
    	    wfAtmAlcFrmCsiRcvCongBitOpt
    		INTEGER,
    	    wfAtmAlcFrmCsiRoutingTag
    		INTEGER,
    	    wfAtmAlcFrmCsiXmtAtcEnable
    		INTEGER,
    	    wfAtmAlcFrmCsiXmtAte
    		INTEGER,
    	    wfAtmAlcFrmCsiXmtClpBitOpt
    		INTEGER,
    	    wfAtmAlcFrmCsiXmtCongBitOpt
    		INTEGER,
    	    wfAtmAlcFrmCsiOmitHec
    		INTEGER,
    	    wfAtmAlcFrmCsiRcvHecEnable
    		INTEGER,
    	    wfAtmAlcFrmCsiRcvHecMask
    		INTEGER,
    	    wfAtmAlcFrmDmaChan0Enable
    		INTEGER,
    	    wfAtmAlcFrmDmaChan1Enable
    		INTEGER,
    	    wfAtmAlcFrmDmaChan2Enable
    		INTEGER,
    	    wfAtmAlcFrmDmaChan3Enable
    		INTEGER,
    	    wfAtmAlcFrmDmaChan4Enable
    		INTEGER,
    	    wfAtmAlcFrmDmaChan5Enable
    		INTEGER,
    	    wfAtmAlcFrmDmaEnable
    		INTEGER,
    	    wfAtmAlcFrmDmaStop
    		INTEGER,
    	    wfAtmAlcFrmDmaPrioritySel
    		INTEGER,
    	    wfAtmAlcFrmDmaFastXferMode
    		INTEGER
        }

    wfAtmAlcFrmConfDelete OBJECT-TYPE
        SYNTAX	INTEGER {
    		    create(1),
    		    delete(2)
    		}
        ACCESS	read-write
        STATUS	mandatory
        DESCRIPTION
                "Create/delete MIB instance parameter."
        DEFVAL	{ create }
        ::= { wfAtmAlcFrmConfEntry 1 }

    wfAtmAlcFrmConfIndex OBJECT-TYPE
        SYNTAX	INTEGER
        ACCESS	read-only
        STATUS	mandatory
        DESCRIPTION
                "Uniquely identifies the interface that contains the
                appropriate management information."
        ::= { wfAtmAlcFrmConfEntry 2 }

    wfAtmAlcFrmGenEnable OBJECT-TYPE
        SYNTAX	INTEGER {
    		    enabled(1),
    		    disabled(2)
    		}
        ACCESS	read-write
        STATUS	mandatory
        DESCRIPTION
                "Rx/Tx framer enable."
        DEFVAL	{ enabled }
        ::= { wfAtmAlcFrmConfEntry 3 }

    wfAtmAlcFrmGenFramingMode OBJECT-TYPE
        SYNTAX	INTEGER {
    		    cell(1),
    		    sdh(2),
    		    sonet(3),
    		    ds3(4),
    		    e3(5),
    		    sonetsts1(6),
    		    ds3nonplcp(7)
    		}
        ACCESS	read-write
        STATUS	mandatory
        DESCRIPTION
                "Framing (transceiver) mode."
        DEFVAL	{ sonet }
        ::= { wfAtmAlcFrmConfEntry 4 }

    wfAtmAlcFrmGenScramblerEna OBJECT-TYPE
        SYNTAX	INTEGER {
    		    enabled(1),
    		    disabled(2)
    		}
        ACCESS	read-write
        STATUS	mandatory
        DESCRIPTION
                "1+x(6)+x(7) frame scrambler. Only applies to
                framing standards such as SONET/SDH."
        DEFVAL	{ enabled }
        ::= { wfAtmAlcFrmConfEntry 5 }

    wfAtmAlcFrmGenDescrambleEna OBJECT-TYPE
        SYNTAX	INTEGER {
    		    enabled(1),
    		    disabled(2)
    		}
        ACCESS	read-write
        STATUS	mandatory
        DESCRIPTION
                "1+x(6)+x(7) frame descrambler. Only applies to
                framing standards such as SONET/SDH."
        DEFVAL	{ enabled }
        ::= { wfAtmAlcFrmConfEntry 6 }

    wfAtmAlcFrmGenLoopback OBJECT-TYPE
        SYNTAX	INTEGER {
    		    enabled(1),
    		    disabled(2)
    		}
        ACCESS	read-write
        STATUS	mandatory
        DESCRIPTION
                "Transmit to receive framer loopback."
        DEFVAL	{ disabled }
        ::= { wfAtmAlcFrmConfEntry 7 }

    wfAtmAlcFrmGenSyncFoundCnt OBJECT-TYPE
        SYNTAX	INTEGER(1..15)
        ACCESS	read-write
        STATUS	mandatory
        DESCRIPTION
                "Frame sync found count."
        DEFVAL	{ 7 }
        ::= { wfAtmAlcFrmConfEntry 8 }

    wfAtmAlcFrmGenSyncLostCnt OBJECT-TYPE
        SYNTAX	INTEGER(1..15)
        ACCESS	read-write
        STATUS	mandatory
        DESCRIPTION
                "Frame sync lost count."
        DEFVAL	{ 8 }
        ::= { wfAtmAlcFrmConfEntry 9 }

    wfAtmAlcFrmRcvCellEnable OBJECT-TYPE
        SYNTAX	INTEGER {
    		    enabled(1),
    		    disabled(2)
    		}
        ACCESS	read-write
        STATUS	mandatory
        DESCRIPTION
                "Cell receiver enable."
        DEFVAL	{ enabled }
        ::= { wfAtmAlcFrmConfEntry 10 }

    wfAtmAlcFrmRcvOamCrcCheck OBJECT-TYPE
        SYNTAX	INTEGER {
    		    enabled(1),
    		    disabled(2)
    		}
        ACCESS	read-write
        STATUS	mandatory
        DESCRIPTION
                "OAM cell CRC check."
        DEFVAL	{ disabled }
        ::= { wfAtmAlcFrmConfEntry 11 }

    wfAtmAlcFrmRcvOamCrcGen OBJECT-TYPE
        SYNTAX	INTEGER {
    		    enabled(1),
    		    disabled(2)
    		}
        ACCESS	read-write
        STATUS	mandatory
        DESCRIPTION
                "OAM cell CRC generate."
        DEFVAL	{ enabled }
        ::= { wfAtmAlcFrmConfEntry 12 }

    wfAtmAlcFrmRcvCellInsPrio OBJECT-TYPE
        SYNTAX	INTEGER {
    		    user(1),
    		    insert(2)
    		}
        ACCESS	read-write
        STATUS	mandatory
        DESCRIPTION
                "Cell insert priority."
        DEFVAL	{ user }
        ::= { wfAtmAlcFrmConfEntry 13 }

    wfAtmAlcFrmRcvInsertPcr OBJECT-TYPE
        SYNTAX	INTEGER {
    		    default(4)
    		}
        ACCESS	read-write
        STATUS	mandatory
        DESCRIPTION
                "Peak cell insertion rate."
        DEFVAL	{ default }
        ::= { wfAtmAlcFrmConfEntry 14 }

    wfAtmAlcFrmRcvGfcIgnore OBJECT-TYPE
        SYNTAX	INTEGER {
    		    vpi12(1),
    		    vpi8(2)
    		}
        ACCESS	read-write
        STATUS	mandatory
        DESCRIPTION
                "GFC field ignore."
        DEFVAL	{ vpi8 }
        ::= { wfAtmAlcFrmConfEntry 15 }

    wfAtmAlcFrmRcvDescrambleCtl OBJECT-TYPE
        SYNTAX	INTEGER {
    		    enabled(1),
    		    disabled(2)
    		}
        ACCESS	read-write
        STATUS	mandatory
        DESCRIPTION
                "Descramble control. Only applies to framing standards
                such as SONET/SDH."
        DEFVAL	{ enabled }
        ::= { wfAtmAlcFrmConfEntry 16 }

    wfAtmAlcFrmRcvHecRcvMask OBJECT-TYPE
        SYNTAX	INTEGER {
    		    enabled(1),
    		    disabled(2)
    		}
        ACCESS	read-write
        STATUS	mandatory
        DESCRIPTION
                "HEC receive mask."
        DEFVAL	{ enabled }
        ::= { wfAtmAlcFrmConfEntry 17 }

    wfAtmAlcFrmRcvErrCorrectEna OBJECT-TYPE
        SYNTAX	INTEGER {
    		    enabled(1),
    		    disabled(2)
    		}
        ACCESS	read-write
        STATUS	mandatory
        DESCRIPTION
                "Error correction enable."
        DEFVAL	{ enabled }
        ::= { wfAtmAlcFrmConfEntry 18 }

    wfAtmAlcFrmRcvByteAlignment OBJECT-TYPE
        SYNTAX	INTEGER {
    		    nonalign(1),
    		    align(2)
    		}
        ACCESS	read-write
        STATUS	mandatory
        DESCRIPTION
                "Byte alignment."
        DEFVAL	{ nonalign }
        ::= { wfAtmAlcFrmConfEntry 19 }

    wfAtmAlcFrmRcvCellSyncFound OBJECT-TYPE
        SYNTAX	INTEGER(1..15)
        ACCESS	read-write
        STATUS	mandatory
        DESCRIPTION
                "Cell sync found count."
        DEFVAL	{ 7 }
        ::= { wfAtmAlcFrmConfEntry 20 }

    wfAtmAlcFrmRcvCellSyncLost OBJECT-TYPE
        SYNTAX	INTEGER(1..15)
        ACCESS	read-write
        STATUS	mandatory
        DESCRIPTION
                "Cell sync lost count."
        DEFVAL	{ 8 }
        ::= { wfAtmAlcFrmConfEntry 21 }

    wfAtmAlcFrmRcvExtUserCell OBJECT-TYPE
        SYNTAX	INTEGER {
    		    disabled(1),
    		    defined(2),
    		    undefined(3),
    		    invalid(4)
    		}
        ACCESS	read-write
        STATUS	mandatory
        DESCRIPTION
                "Extract user defined cell."
        DEFVAL	{ disabled }
        ::= { wfAtmAlcFrmConfEntry 22 }

    wfAtmAlcFrmRcvExtMetaSig OBJECT-TYPE
        SYNTAX	INTEGER {
    		    enabled(1),
    		    disabled(2)
    		}
        ACCESS	read-write
        STATUS	mandatory
        DESCRIPTION
                "Extract meta signalling."
        DEFVAL	{ disabled }
        ::= { wfAtmAlcFrmConfEntry 23 }

    wfAtmAlcFrmRcvExtBcastSig OBJECT-TYPE
        SYNTAX	INTEGER {
    		    enabled(1),
    		    disabled(2)
    		}
        ACCESS	read-write
        STATUS	mandatory
        DESCRIPTION
                "Extract broadcast signalling."
        DEFVAL	{ disabled }
        ::= { wfAtmAlcFrmConfEntry 24 }

    wfAtmAlcFrmRcvExtPointSig OBJECT-TYPE
        SYNTAX	INTEGER {
    		    enabled(1),
    		    disabled(2)
    		}
        ACCESS	read-write
        STATUS	mandatory
        DESCRIPTION
                "Extract point-point signalling."
        DEFVAL	{ disabled }
        ::= { wfAtmAlcFrmConfEntry 25 }

    wfAtmAlcFrmRcvExtIlmiSig OBJECT-TYPE
        SYNTAX	INTEGER {
    		    enabled(1),
    		    disabled(2)
    		}
        ACCESS	read-write
        STATUS	mandatory
        DESCRIPTION
                "Extract ILMI signalling."
        DEFVAL	{ disabled }
        ::= { wfAtmAlcFrmConfEntry 26 }

    wfAtmAlcFrmRcvExtF4F5PrfMan OBJECT-TYPE
        SYNTAX	INTEGER {
    		    enabled(1),
    		    disabled(2)
    		}
        ACCESS	read-write
        STATUS	mandatory
        DESCRIPTION
                "Extract F4/F5 performance man."
        DEFVAL	{ disabled }
        ::= { wfAtmAlcFrmConfEntry 27 }

    wfAtmAlcFrmRcvExtF1F3PlOam OBJECT-TYPE
        SYNTAX	INTEGER {
    		    enabled(1),
    		    disabled(2)
    		}
        ACCESS	read-write
        STATUS	mandatory
        DESCRIPTION
                "Extract F1/F3 PL-OAM."
        DEFVAL	{ disabled }
        ::= { wfAtmAlcFrmConfEntry 28 }

    wfAtmAlcFrmRcvExtF4Segment OBJECT-TYPE
        SYNTAX	INTEGER {
    		    enabled(1),
    		    disabled(2)
    		}
        ACCESS	read-write
        STATUS	mandatory
        DESCRIPTION
                "Extract F4 segment (FM and AD)."
        DEFVAL	{ disabled }
        ::= { wfAtmAlcFrmConfEntry 29 }

    wfAtmAlcFrmRcvExtF4EndEnd OBJECT-TYPE
        SYNTAX	INTEGER {
    		    enabled(1),
    		    disabled(2)
    		}
        ACCESS	read-write
        STATUS	mandatory
        DESCRIPTION
                "Extract F4 end-end (FM and AD)."
        DEFVAL	{ disabled }
        ::= { wfAtmAlcFrmConfEntry 30 }

    wfAtmAlcFrmRcvExtF5Segment OBJECT-TYPE
        SYNTAX	INTEGER {
    		    enabled(1),
    		    disabled(2)
    		}
        ACCESS	read-write
        STATUS	mandatory
        DESCRIPTION
                "Extract F5 segment (FM and AD)."
        DEFVAL	{ disabled }
        ::= { wfAtmAlcFrmConfEntry 31 }

    wfAtmAlcFrmRcvExtF5EndEnd OBJECT-TYPE
        SYNTAX	INTEGER {
    		    enabled(1),
    		    disabled(2)
    		}
        ACCESS	read-write
        STATUS	mandatory
        DESCRIPTION
                "Extract F5 end-end (FM and AD)."
        DEFVAL	{ disabled }
        ::= { wfAtmAlcFrmConfEntry 32 }

    wfAtmAlcFrmRcvDisUserCell OBJECT-TYPE
        SYNTAX	INTEGER {
    		    disabled(1),
    		    defined(2),
    		    undefined(3),
    		    invalid(4)
    		}
        ACCESS	read-write
        STATUS	mandatory
        DESCRIPTION
                "Discard user defined cell."
        DEFVAL	{ disabled }
        ::= { wfAtmAlcFrmConfEntry 33 }

    wfAtmAlcFrmRcvDisMetaSig OBJECT-TYPE
        SYNTAX	INTEGER {
    		    enabled(1),
    		    disabled(2)
    		}
        ACCESS	read-write
        STATUS	mandatory
        DESCRIPTION
                "Discard meta signalling."
        DEFVAL	{ disabled }
        ::= { wfAtmAlcFrmConfEntry 34 }

    wfAtmAlcFrmRcvDisBcastSig OBJECT-TYPE
        SYNTAX	INTEGER {
    		    enabled(1),
    		    disabled(2)
    		}
        ACCESS	read-write
        STATUS	mandatory
        DESCRIPTION
                "Discard broadcast signalling."
        DEFVAL	{ disabled }
        ::= { wfAtmAlcFrmConfEntry 35 }

    wfAtmAlcFrmRcvDisPointSig OBJECT-TYPE
        SYNTAX	INTEGER {
    		    enabled(1),
    		    disabled(2)
    		}
        ACCESS	read-write
        STATUS	mandatory
        DESCRIPTION
                "Discard point-point signalling."
        DEFVAL	{ disabled }
        ::= { wfAtmAlcFrmConfEntry 36 }

    wfAtmAlcFrmRcvDisIlmiSig OBJECT-TYPE
        SYNTAX	INTEGER {
    		    enabled(1),
    		    disabled(2)
    		}
        ACCESS	read-write
        STATUS	mandatory
        DESCRIPTION
                "Discard ILMI signalling."
        DEFVAL	{ disabled }
        ::= { wfAtmAlcFrmConfEntry 37 }

    wfAtmAlcFrmRcvDisUnassCell OBJECT-TYPE
        SYNTAX	INTEGER {
    		    enabled(1),
    		    disabled(2)
    		}
        ACCESS	read-write
        STATUS	mandatory
        DESCRIPTION
                "Discard unassigned cell."
        DEFVAL	{ enabled }
        ::= { wfAtmAlcFrmConfEntry 38 }

    wfAtmAlcFrmRcvDisF4Segment OBJECT-TYPE
        SYNTAX	INTEGER {
    		    enabled(1),
    		    disabled(2)
    		}
        ACCESS	read-write
        STATUS	mandatory
        DESCRIPTION
                "Discard F4 segment (FM and AD)."
        DEFVAL	{ disabled }
        ::= { wfAtmAlcFrmConfEntry 39 }

    wfAtmAlcFrmRcvDisF4EndEnd OBJECT-TYPE
        SYNTAX	INTEGER {
    		    enabled(1),
    		    disabled(2)
    		}
        ACCESS	read-write
        STATUS	mandatory
        DESCRIPTION
                "Discard F4 end-end (FM and AD)."
        DEFVAL	{ disabled }
        ::= { wfAtmAlcFrmConfEntry 40 }

    wfAtmAlcFrmRcvDisF5Segment OBJECT-TYPE
        SYNTAX	INTEGER {
    		    enabled(1),
    		    disabled(2)
    		}
        ACCESS	read-write
        STATUS	mandatory
        DESCRIPTION
                "Discard F5 segment (FM and AD)."
        DEFVAL	{ disabled }
        ::= { wfAtmAlcFrmConfEntry 41 }

    wfAtmAlcFrmRcvDisF5EndEnd OBJECT-TYPE
        SYNTAX	INTEGER {
    		    enabled(1),
    		    disabled(2)
    		}
        ACCESS	read-write
        STATUS	mandatory
        DESCRIPTION
                "Discard F5 end-end (FM and AD)."
        DEFVAL	{ disabled }
        ::= { wfAtmAlcFrmConfEntry 42 }

    wfAtmAlcFrmXmtCellEnable OBJECT-TYPE
        SYNTAX	INTEGER {
    		    enabled(1),
    		    disabled(2)
    		}
        ACCESS	read-write
        STATUS	mandatory
        DESCRIPTION
                "Cell transmitter enable."
        DEFVAL	{ enabled }
        ::= { wfAtmAlcFrmConfEntry 43 }

    wfAtmAlcFrmXmtOamCrcCheck OBJECT-TYPE
        SYNTAX	INTEGER {
    		    enabled(1),
    		    disabled(2)
    		}
        ACCESS	read-write
        STATUS	mandatory
        DESCRIPTION
                "OAM cell CRC check."
        DEFVAL	{ disabled }
        ::= { wfAtmAlcFrmConfEntry 44 }

    wfAtmAlcFrmXmtOamCrcGen OBJECT-TYPE
        SYNTAX	INTEGER {
    		    enabled(1),
    		    disabled(2)
    		}
        ACCESS	read-write
        STATUS	mandatory
        DESCRIPTION
                "OAM cell CRC generate."
        DEFVAL	{ enabled }
        ::= { wfAtmAlcFrmConfEntry 45 }

    wfAtmAlcFrmXmtCellInsPrio OBJECT-TYPE
        SYNTAX	INTEGER {
    		    user(1),
    		    insert(2)
    		}
        ACCESS	read-write
        STATUS	mandatory
        DESCRIPTION
                "Cell insert priority."
        DEFVAL	{ user }
        ::= { wfAtmAlcFrmConfEntry 46 }

    wfAtmAlcFrmXmtInsertPcr OBJECT-TYPE
        SYNTAX	INTEGER {
    		    default(4)
    		}
        ACCESS	read-write
        STATUS	mandatory
        DESCRIPTION
                "Peak cell insertion rate."
        DEFVAL	{ default }
        ::= { wfAtmAlcFrmConfEntry 47 }

    wfAtmAlcFrmXmtGfcIgnore OBJECT-TYPE
        SYNTAX	INTEGER {
    		    vpi12(1),
    		    vpi8(2)
    		}
        ACCESS	read-write
        STATUS	mandatory
        DESCRIPTION
                "GFC field ignore."
        DEFVAL	{ vpi8 }
        ::= { wfAtmAlcFrmConfEntry 48 }

    wfAtmAlcFrmXmtCellDecouple OBJECT-TYPE
        SYNTAX	INTEGER {
    		    idle(1),
    		    unassign(2)
    		}
        ACCESS	read-write
        STATUS	mandatory
        DESCRIPTION
                "Cell rate decoupling."
        DEFVAL	{ unassign }
        ::= { wfAtmAlcFrmConfEntry 49 }

    wfAtmAlcFrmXmtScrambleCtl OBJECT-TYPE
        SYNTAX	INTEGER {
    		    enabled(1),
    		    disabled(2)
    		}
        ACCESS	read-write
        STATUS	mandatory
        DESCRIPTION
                "Scramble control. Only applies to framing standards
                such as SONET/SDH."
        DEFVAL	{ enabled }
        ::= { wfAtmAlcFrmConfEntry 50 }

    wfAtmAlcFrmXmtHecXmtMask OBJECT-TYPE
        SYNTAX	INTEGER {
    		    enabled(1),
    		    disabled(2)
    		}
        ACCESS	read-write
        STATUS	mandatory
        DESCRIPTION
                "HEC transmit mask."
        DEFVAL	{ enabled }
        ::= { wfAtmAlcFrmConfEntry 51 }

    wfAtmAlcFrmXmtExtUserCell OBJECT-TYPE
        SYNTAX	INTEGER {
    		    disabled(1),
    		    defined(2),
    		    undefined(3),
    		    invalid(4)
    		}
        ACCESS	read-write
        STATUS	mandatory
        DESCRIPTION
                "Extract user defined cell."
        DEFVAL	{ disabled }
        ::= { wfAtmAlcFrmConfEntry 52 }

    wfAtmAlcFrmXmtExtMetaSig OBJECT-TYPE
        SYNTAX	INTEGER {
    		    enabled(1),
    		    disabled(2)
    		}
        ACCESS	read-write
        STATUS	mandatory
        DESCRIPTION
                "Extract meta signalling."
        DEFVAL	{ disabled }
        ::= { wfAtmAlcFrmConfEntry 53 }

    wfAtmAlcFrmXmtExtBcastSig OBJECT-TYPE
        SYNTAX	INTEGER {
    		    enabled(1),
    		    disabled(2)
    		}
        ACCESS	read-write
        STATUS	mandatory
        DESCRIPTION
                "Extract broadcast signalling."
        DEFVAL	{ disabled }
        ::= { wfAtmAlcFrmConfEntry 54 }

    wfAtmAlcFrmXmtExtPointSig OBJECT-TYPE
        SYNTAX	INTEGER {
    		    enabled(1),
    		    disabled(2)
    		}
        ACCESS	read-write
        STATUS	mandatory
        DESCRIPTION
                "Extract point-point signalling."
        DEFVAL	{ disabled }
        ::= { wfAtmAlcFrmConfEntry 55 }

    wfAtmAlcFrmXmtExtIlmiSig OBJECT-TYPE
        SYNTAX	INTEGER {
    		    enabled(1),
    		    disabled(2)
    		}
        ACCESS	read-write
        STATUS	mandatory
        DESCRIPTION
                "Extract ILMI signalling."
        DEFVAL	{ disabled }
        ::= { wfAtmAlcFrmConfEntry 56 }

    wfAtmAlcFrmXmtExtF4F5PrfMan OBJECT-TYPE
        SYNTAX	INTEGER {
    		    enabled(1),
    		    disabled(2)
    		}
        ACCESS	read-write
        STATUS	mandatory
        DESCRIPTION
                "Extract F4/F5 performance man."
        DEFVAL	{ disabled }
        ::= { wfAtmAlcFrmConfEntry 57 }

    wfAtmAlcFrmXmtExtF4Segment OBJECT-TYPE
        SYNTAX	INTEGER {
    		    enabled(1),
    		    disabled(2)
    		}
        ACCESS	read-write
        STATUS	mandatory
        DESCRIPTION
                "Extract F4 segment (FM and AD)."
        DEFVAL	{ disabled }
        ::= { wfAtmAlcFrmConfEntry 58 }

    wfAtmAlcFrmXmtExtF4EndEnd OBJECT-TYPE
        SYNTAX	INTEGER {
    		    enabled(1),
    		    disabled(2)
    		}
        ACCESS	read-write
        STATUS	mandatory
        DESCRIPTION
                "Extract F4 end-end (FM and AD)."
        DEFVAL	{ disabled }
        ::= { wfAtmAlcFrmConfEntry 59 }

    wfAtmAlcFrmXmtExtF5Segment OBJECT-TYPE
        SYNTAX	INTEGER {
    		    enabled(1),
    		    disabled(2)
    		}
        ACCESS	read-write
        STATUS	mandatory
        DESCRIPTION
                "Extract F5 segment (FM and AD)."
        DEFVAL	{ disabled }
        ::= { wfAtmAlcFrmConfEntry 60 }

    wfAtmAlcFrmXmtExtF5EndEnd OBJECT-TYPE
        SYNTAX	INTEGER {
    		    enabled(1),
    		    disabled(2)
    		}
        ACCESS	read-write
        STATUS	mandatory
        DESCRIPTION
                "Extract F5 end-end (FM and AD)."
        DEFVAL	{ disabled }
        ::= { wfAtmAlcFrmConfEntry 61 }

    wfAtmAlcFrmXmtDisUserCell OBJECT-TYPE
        SYNTAX	INTEGER {
    		    disabled(1),
    		    defined(2),
    		    undefined(3),
    		    invalid(4)
    		}
        ACCESS	read-write
        STATUS	mandatory
        DESCRIPTION
                "Discard user defined cell."
        DEFVAL	{ disabled }
        ::= { wfAtmAlcFrmConfEntry 62 }

    wfAtmAlcFrmXmtDisMetaSig OBJECT-TYPE
        SYNTAX	INTEGER {
    		    enabled(1),
    		    disabled(2)
    		}
        ACCESS	read-write
        STATUS	mandatory
        DESCRIPTION
                "Discard meta signalling."
        DEFVAL	{ disabled }
        ::= { wfAtmAlcFrmConfEntry 63 }

    wfAtmAlcFrmXmtDisBcastSig OBJECT-TYPE
        SYNTAX	INTEGER {
    		    enabled(1),
    		    disabled(2)
    		}
        ACCESS	read-write
        STATUS	mandatory
        DESCRIPTION
                "Discard broadcast signalling."
        DEFVAL	{ disabled }
        ::= { wfAtmAlcFrmConfEntry 64 }

    wfAtmAlcFrmXmtDisPointSig OBJECT-TYPE
        SYNTAX	INTEGER {
    		    enabled(1),
    		    disabled(2)
    		}
        ACCESS	read-write
        STATUS	mandatory
        DESCRIPTION
                "Discard point-point signalling."
        DEFVAL	{ disabled }
        ::= { wfAtmAlcFrmConfEntry 65 }

    wfAtmAlcFrmXmtDisIlmiSig OBJECT-TYPE
        SYNTAX	INTEGER {
    		    enabled(1),
    		    disabled(2)
    		}
        ACCESS	read-write
        STATUS	mandatory
        DESCRIPTION
                "Discard ILMI signalling."
        DEFVAL	{ disabled }
        ::= { wfAtmAlcFrmConfEntry 66 }

    wfAtmAlcFrmXmtDisUnassCell OBJECT-TYPE
        SYNTAX	INTEGER {
    		    enabled(1),
    		    disabled(2)
    		}
        ACCESS	read-write
        STATUS	mandatory
        DESCRIPTION
                "Discard unassigned cell."
        DEFVAL	{ disabled }
        ::= { wfAtmAlcFrmConfEntry 67 }

    wfAtmAlcFrmXmtDisF4Segment OBJECT-TYPE
        SYNTAX	INTEGER {
    		    enabled(1),
    		    disabled(2)
    		}
        ACCESS	read-write
        STATUS	mandatory
        DESCRIPTION
                "Discard F4 segment (FM and AD)."
        DEFVAL	{ disabled }
        ::= { wfAtmAlcFrmConfEntry 68 }

    wfAtmAlcFrmXmtDisF4EndEnd OBJECT-TYPE
        SYNTAX	INTEGER {
    		    enabled(1),
    		    disabled(2)
    		}
        ACCESS	read-write
        STATUS	mandatory
        DESCRIPTION
                "Discard F4 end-end (FM and AD)."
        DEFVAL	{ disabled }
        ::= { wfAtmAlcFrmConfEntry 69 }

    wfAtmAlcFrmXmtDisF5Segment OBJECT-TYPE
        SYNTAX	INTEGER {
    		    enabled(1),
    		    disabled(2)
    		}
        ACCESS	read-write
        STATUS	mandatory
        DESCRIPTION
                "Discard F5 segment (FM and AD)."
        DEFVAL	{ disabled }
        ::= { wfAtmAlcFrmConfEntry 70 }

    wfAtmAlcFrmXmtDisF5EndEnd OBJECT-TYPE
        SYNTAX	INTEGER {
    		    enabled(1),
    		    disabled(2)
    		}
        ACCESS	read-write
        STATUS	mandatory
        DESCRIPTION
                "Discard F5 end-end (FM and AD)."
        DEFVAL	{ disabled }
        ::= { wfAtmAlcFrmConfEntry 71 }

    wfAtmAlcFrmOamEnable OBJECT-TYPE
        SYNTAX	INTEGER {
    		    enabled(1),
    		    disabled(2)
    		}
        ACCESS	read-write
        STATUS	mandatory
        DESCRIPTION
                "OAM controller enable."
        DEFVAL	{ disabled }
        ::= { wfAtmAlcFrmConfEntry 72 }

    wfAtmAlcFrmOamInvertBip OBJECT-TYPE
        SYNTAX	INTEGER {
    		    normal(1),
    		    invert(2)
    		}
        ACCESS	read-write
        STATUS	mandatory
        DESCRIPTION
                "Invert BIP."
        DEFVAL	{ normal }
        ::= { wfAtmAlcFrmConfEntry 73 }

    wfAtmAlcFrmOamTxPathFerf OBJECT-TYPE
        SYNTAX	INTEGER {
    		    clear(1),
    		    auto(2),
    		    set(3)
    		}
        ACCESS	read-write
        STATUS	mandatory
        DESCRIPTION
                "Tx path FERF."
        DEFVAL	{ clear }
        ::= { wfAtmAlcFrmConfEntry 74 }

    wfAtmAlcFrmOamTxSectionFerf OBJECT-TYPE
        SYNTAX	INTEGER {
    		    clear(1),
    		    auto(2),
    		    set(3)
    		}
        ACCESS	read-write
        STATUS	mandatory
        DESCRIPTION
                "Tx section FERF."
        DEFVAL	{ clear }
        ::= { wfAtmAlcFrmConfEntry 75 }

    wfAtmAlcFrmOamTxPathAis OBJECT-TYPE
        SYNTAX	INTEGER {
    		    clear(1),
    		    set(2)
    		}
        ACCESS	read-write
        STATUS	mandatory
        DESCRIPTION
                "Tx path AIS."
        DEFVAL	{ clear }
        ::= { wfAtmAlcFrmConfEntry 76 }

    wfAtmAlcFrmOamTxSectionAis OBJECT-TYPE
        SYNTAX	INTEGER {
    		    clear(1),
    		    set(2)
    		}
        ACCESS	read-write
        STATUS	mandatory
        DESCRIPTION
                "Tx section AIS."
        DEFVAL	{ clear }
        ::= { wfAtmAlcFrmConfEntry 77 }

    wfAtmAlcFrmOamTxPathFebe OBJECT-TYPE
        SYNTAX	INTEGER {
    		    enabled(1),
    		    disabled(2)
    		}
        ACCESS	read-write
        STATUS	mandatory
        DESCRIPTION
                "Tx path FEBE (B3)."
        DEFVAL	{ disabled }
        ::= { wfAtmAlcFrmConfEntry 78 }

    wfAtmAlcFrmOamTxSectionFebe OBJECT-TYPE
        SYNTAX	INTEGER {
    		    enabled(1),
    		    disabled(2)
    		}
        ACCESS	read-write
        STATUS	mandatory
        DESCRIPTION
                "Tx section FEBE (B3)."
        DEFVAL	{ disabled }
        ::= { wfAtmAlcFrmConfEntry 79 }

    wfAtmAlcFrmStatsSwEnable OBJECT-TYPE
        SYNTAX	INTEGER {
    		    enabled(1),
    		    disabled(2)
    		}
        ACCESS	read-write
        STATUS	mandatory
        DESCRIPTION
                "Switch statistics handler."
        DEFVAL	{ disabled }
        ::= { wfAtmAlcFrmConfEntry 80 }

    wfAtmAlcFrmStatsMode OBJECT-TYPE
        SYNTAX	INTEGER {
    		    disabled(1),
    		    header(2),
    		    header16(3),
    		    header32(4)
    		}
        ACCESS	read-write
        STATUS	mandatory
        DESCRIPTION
                "Statistics controller mode."
        DEFVAL	{ disabled }
        ::= { wfAtmAlcFrmConfEntry 81 }

    wfAtmAlcFrmStatsReceive OBJECT-TYPE
        SYNTAX	INTEGER {
    		    enabled(1),
    		    disabled(2)
    		}
        ACCESS	read-write
        STATUS	mandatory
        DESCRIPTION
                "Receive user statistics."
        DEFVAL	{ disabled }
        ::= { wfAtmAlcFrmConfEntry 82 }

    wfAtmAlcFrmStatsTransmit OBJECT-TYPE
        SYNTAX	INTEGER {
    		    enabled(1),
    		    disabled(2)
    		}
        ACCESS	read-write
        STATUS	mandatory
        DESCRIPTION
                "Transmit statistics."
        DEFVAL	{ disabled }
        ::= { wfAtmAlcFrmConfEntry 83 }

    wfAtmAlcFrmStatsMask OBJECT-TYPE
        SYNTAX	INTEGER {
    		    disabled(1),
    		    hmask(2),
    		    invalid(3),
    		    lmask(4)
    		}
        ACCESS	read-write
        STATUS	mandatory
        DESCRIPTION
                "VP/VC filter mask."
        DEFVAL	{ disabled }
        ::= { wfAtmAlcFrmConfEntry 84 }

    wfAtmAlcFrmStatsTimeout OBJECT-TYPE
        SYNTAX	INTEGER
        ACCESS	read-write
        STATUS	mandatory
        DESCRIPTION
                "Statistics DMA transfer timeout."
        ::= { wfAtmAlcFrmConfEntry 85 }

    wfAtmAlcFrmStatsTimerEna OBJECT-TYPE
        SYNTAX	INTEGER {
    		    enabled(1),
    		    disabled(2)
    		}
        ACCESS	read-write
        STATUS	mandatory
        DESCRIPTION
                "Timer enable (DMA)."
        DEFVAL	{ disabled }
        ::= { wfAtmAlcFrmConfEntry 86 }

    wfAtmAlcFrmStatsOflowEna OBJECT-TYPE
        SYNTAX	INTEGER {
    		    enabled(1),
    		    disabled(2)
    		}
        ACCESS	read-write
        STATUS	mandatory
        DESCRIPTION
                "Overflow enable (DMA)."
        DEFVAL	{ disabled }
        ::= { wfAtmAlcFrmConfEntry 87 }

    wfAtmAlcFrmStatsForceDma OBJECT-TYPE
        SYNTAX	INTEGER {
    		    other(1),
    		    dma(2)
    		}
        ACCESS	read-write
        STATUS	mandatory
        DESCRIPTION
                "Force DMA transfer."
        DEFVAL	{ other }
        ::= { wfAtmAlcFrmConfEntry 88 }

    wfAtmAlcFrmCsiEnable OBJECT-TYPE
        SYNTAX	INTEGER {
    		    enabled(1),
    		    disabled(2)
    		}
        ACCESS	read-write
        STATUS	mandatory
        DESCRIPTION
                "Cell stream enable."
        DEFVAL	{ enabled }
        ::= { wfAtmAlcFrmConfEntry 89 }

    wfAtmAlcFrmCsiLoop OBJECT-TYPE
        SYNTAX	INTEGER {
    		    enabled(1),
    		    disabled(2)
    		}
        ACCESS	read-write
        STATUS	mandatory
        DESCRIPTION
                "CSI rx/tx loopback."
        DEFVAL	{ disabled }
        ::= { wfAtmAlcFrmConfEntry 90 }

    wfAtmAlcFrmCsiRcvAtcEnable OBJECT-TYPE
        SYNTAX	INTEGER {
    		    enabled(1),
    		    disabled(2)
    		}
        ACCESS	read-write
        STATUS	mandatory
        DESCRIPTION
                "Receive ATC enable."
        DEFVAL	{ enabled }
        ::= { wfAtmAlcFrmConfEntry 91 }

    wfAtmAlcFrmCsiRcvAte OBJECT-TYPE
        SYNTAX	INTEGER {
    		    discard(1),
    		    forward(2)
    		}
        ACCESS	read-write
        STATUS	mandatory
        DESCRIPTION
                "Address translation error (receive)."
        DEFVAL	{ discard }
        ::= { wfAtmAlcFrmConfEntry 92 }

    wfAtmAlcFrmCsiRcvClpBitOpt OBJECT-TYPE
        SYNTAX	INTEGER {
    		    header(1),
    		    xlat(2),
    		    force0(3),
    		    force1(4)
    		}
        ACCESS	read-write
        STATUS	mandatory
        DESCRIPTION
                "CLP bit option (receive)."
        DEFVAL	{ header }
        ::= { wfAtmAlcFrmConfEntry 93 }

    wfAtmAlcFrmCsiRcvCongBitOpt OBJECT-TYPE
        SYNTAX	INTEGER {
    		    header(1),
    		    xlat(2),
    		    force0(3),
    		    force1(4)
    		}
        ACCESS	read-write
        STATUS	mandatory
        DESCRIPTION
                "PLT congestion bit option (receive)."
        DEFVAL	{ header }
        ::= { wfAtmAlcFrmConfEntry 94 }

    wfAtmAlcFrmCsiRoutingTag OBJECT-TYPE
        SYNTAX	INTEGER {
    		    tag0(1),
    		    tag1(2),
    		    tag2(3),
    		    tag3(4)
    		}
        ACCESS	read-write
        STATUS	mandatory
        DESCRIPTION
                "Routing tag byte size."
        DEFVAL	{ tag0 }
        ::= { wfAtmAlcFrmConfEntry 95 }

    wfAtmAlcFrmCsiXmtAtcEnable OBJECT-TYPE
        SYNTAX	INTEGER {
    		    enabled(1),
    		    disabled(2)
    		}
        ACCESS	read-write
        STATUS	mandatory
        DESCRIPTION
                "Transmit ATC enable."
        DEFVAL	{ disabled }
        ::= { wfAtmAlcFrmConfEntry 96 }

    wfAtmAlcFrmCsiXmtAte OBJECT-TYPE
        SYNTAX	INTEGER {
    		    discard(1),
    		    forward(2)
    		}
        ACCESS	read-write
        STATUS	mandatory
        DESCRIPTION
                "Address translation error (transmit)."
        DEFVAL	{ discard }
        ::= { wfAtmAlcFrmConfEntry 97 }

    wfAtmAlcFrmCsiXmtClpBitOpt OBJECT-TYPE
        SYNTAX	INTEGER {
    		    header(1),
    		    xlat(2),
    		    force0(3),
    		    force1(4)
    		}
        ACCESS	read-write
        STATUS	mandatory
        DESCRIPTION
                "CLP bit option (transmit)."
        DEFVAL	{ header }
        ::= { wfAtmAlcFrmConfEntry 98 }

    wfAtmAlcFrmCsiXmtCongBitOpt OBJECT-TYPE
        SYNTAX	INTEGER {
    		    header(1),
    		    xlat(2),
    		    force0(3),
    		    force1(4)
    		}
        ACCESS	read-write
        STATUS	mandatory
        DESCRIPTION
                "PLT congestion bit option (transmit)."
        DEFVAL	{ header }
        ::= { wfAtmAlcFrmConfEntry 99 }

    wfAtmAlcFrmCsiOmitHec OBJECT-TYPE
        SYNTAX	INTEGER {
    		    cell53byte(1),
    		    cell52byte(2)
    		}
        ACCESS	read-write
        STATUS	mandatory
        DESCRIPTION
                "Omit HEC byte on transmit."
        DEFVAL	{ cell53byte }
        ::= { wfAtmAlcFrmConfEntry 100 }

    wfAtmAlcFrmCsiRcvHecEnable OBJECT-TYPE
        SYNTAX	INTEGER {
    		    enabled(1),
    		    disabled(2)
    		}
        ACCESS	read-write
        STATUS	mandatory
        DESCRIPTION
                "HEC generator enable."
        DEFVAL	{ enabled }
        ::= { wfAtmAlcFrmConfEntry 101 }

    wfAtmAlcFrmCsiRcvHecMask OBJECT-TYPE
        SYNTAX	INTEGER {
    		    enabled(1),
    		    disabled(2)
    		}
        ACCESS	read-write
        STATUS	mandatory
        DESCRIPTION
                "ASCI rx path HEC mask."
        DEFVAL	{ enabled }
        ::= { wfAtmAlcFrmConfEntry 102 }

    wfAtmAlcFrmDmaChan0Enable OBJECT-TYPE
        SYNTAX	INTEGER {
    		    enabled(1),
    		    disabled(2)
    		}
        ACCESS	read-write
        STATUS	mandatory
        DESCRIPTION
                "DMA channel 0 enable."
        DEFVAL	{ disabled }
        ::= { wfAtmAlcFrmConfEntry 103 }

    wfAtmAlcFrmDmaChan1Enable OBJECT-TYPE
        SYNTAX	INTEGER {
    		    enabled(1),
    		    disabled(2)
    		}
        ACCESS	read-write
        STATUS	mandatory
        DESCRIPTION
                "DMA channel 1 enable."
        DEFVAL	{ disabled }
        ::= { wfAtmAlcFrmConfEntry 104 }

    wfAtmAlcFrmDmaChan2Enable OBJECT-TYPE
        SYNTAX	INTEGER {
    		    enabled(1),
    		    disabled(2)
    		}
        ACCESS	read-write
        STATUS	mandatory
        DESCRIPTION
                "DMA channel 2 enable."
        DEFVAL	{ disabled }
        ::= { wfAtmAlcFrmConfEntry 105 }

    wfAtmAlcFrmDmaChan3Enable OBJECT-TYPE
        SYNTAX	INTEGER {
    		    enabled(1),
    		    disabled(2)
    		}
        ACCESS	read-write
        STATUS	mandatory
        DESCRIPTION
                "DMA channel 3 enable."
        DEFVAL	{ disabled }
        ::= { wfAtmAlcFrmConfEntry 106 }

    wfAtmAlcFrmDmaChan4Enable OBJECT-TYPE
        SYNTAX	INTEGER {
    		    enabled(1),
    		    disabled(2)
    		}
        ACCESS	read-write
        STATUS	mandatory
        DESCRIPTION
                "DMA channel 4 enable."
        DEFVAL	{ disabled }
        ::= { wfAtmAlcFrmConfEntry 107 }

    wfAtmAlcFrmDmaChan5Enable OBJECT-TYPE
        SYNTAX	INTEGER {
    		    enabled(1),
    		    disabled(2)
    		}
        ACCESS	read-write
        STATUS	mandatory
        DESCRIPTION
                "DMA channel 5 enable."
        DEFVAL	{ disabled }
        ::= { wfAtmAlcFrmConfEntry 108 }

    wfAtmAlcFrmDmaEnable OBJECT-TYPE
        SYNTAX	INTEGER {
    		    enabled(1),
    		    disabled(2)
    		}
        ACCESS	read-write
        STATUS	mandatory
        DESCRIPTION
                "DMA controller enable."
        DEFVAL	{ enabled }
        ::= { wfAtmAlcFrmConfEntry 109 }

    wfAtmAlcFrmDmaStop OBJECT-TYPE
        SYNTAX	INTEGER {
    		    notstopped(1),
    		    stopped(2)
    		}
        ACCESS	read-write
        STATUS	mandatory
        DESCRIPTION
                "DMA stop."
        DEFVAL	{ notstopped }
        ::= { wfAtmAlcFrmConfEntry 110 }

    wfAtmAlcFrmDmaPrioritySel OBJECT-TYPE
        SYNTAX	INTEGER {
    		    chan0prio(1),
    		    chan5prio(2)
    		}
        ACCESS	read-write
        STATUS	mandatory
        DESCRIPTION
                "Priority select."
        DEFVAL	{ chan0prio }
        ::= { wfAtmAlcFrmConfEntry 111 }

    wfAtmAlcFrmDmaFastXferMode OBJECT-TYPE
        SYNTAX	INTEGER {
    		    descdma(1),
    		    fastdma(2)
    		}
        ACCESS	read-write
        STATUS	mandatory
        DESCRIPTION
                "Fast transfer mode."
        DEFVAL	{ descdma }
        ::= { wfAtmAlcFrmConfEntry 112 }

    wfAtmizerCfgTable OBJECT-TYPE
        SYNTAX	SEQUENCE OF WfAtmizerCfgEntry
        ACCESS	not-accessible
        STATUS	mandatory
        DESCRIPTION
                "ARE ATMizer Configuration Record"
        ::= { wfAtmCellSwitchGroup 1 }

    wfAtmizerCfgEntry OBJECT-TYPE
        SYNTAX	WfAtmizerCfgEntry
        ACCESS	not-accessible
        STATUS	mandatory
        DESCRIPTION
                "Information about a Transmit/Receive pair of ATMizers"
        INDEX	{ wfAtmizerCfgSlot }
        ::= { wfAtmizerCfgTable 1 }

    WfAtmizerCfgEntry ::= SEQUENCE {
    	    wfAtmizerCfgSlot
    		INTEGER,
    	    wfAtmizerCfgMaxVcl
    		INTEGER,
    	    wfAtmizerCfgCurrVcl
    		INTEGER,
    	    wfAtmizerCfgRxQueueLenMax
    		INTEGER,
    	    wfAtmizerCfgRxQueueTmoMax
    		INTEGER,
    	    wfAtmizerCfgRxBuffersMax
    		INTEGER,
    	    wfAtmizerCfgRxPagesMax
    		INTEGER,
    	    wfAtmizerCfgTxBuffersMax
    		INTEGER,
    	    wfAtmizerCfgTxPagesMax
    		INTEGER,
    	    wfAtmizerCfgTxPercentRsrcs
    		INTEGER,
    	    wfAtmizerCfgHeartbeatPeriod
    		INTEGER,
    	    wfAtmizerRxBuffersMax
    		INTEGER,
    	    wfAtmizerRxPagesMax
    		INTEGER,
    	    wfAtmizerTxBuffersMax
    		INTEGER,
    	    wfAtmizerTxPagesMax
    		INTEGER,
    	    wfAtmizerTxPercentRsrcs
    		INTEGER,
            wfAtmizerTxPerVcClipEnable
                INTEGER,
            wfAtmizerCfgTxVcBuffersMax
                INTEGER,
            wfAtmizerTxVcBuffersMax
                INTEGER
        }

    wfAtmizerCfgSlot OBJECT-TYPE
        SYNTAX	INTEGER(1..14)
        ACCESS	read-only
        STATUS	mandatory
        DESCRIPTION
                "Slot number -- instance id."
        ::= { wfAtmizerCfgEntry 1 }

    wfAtmizerCfgMaxVcl OBJECT-TYPE
        SYNTAX	INTEGER
        ACCESS	read-only
        STATUS	mandatory
        DESCRIPTION
                "The maximum size of a Virtual Channel Links (VCLs) which can be
                supported by the ATMizers."
        ::= { wfAtmizerCfgEntry 2 }

    wfAtmizerCfgCurrVcl OBJECT-TYPE
        SYNTAX	INTEGER
        ACCESS	read-only
        STATUS	mandatory
        DESCRIPTION
                "The number of  Virtual Channel Links (VCLs) currently active on the slot."
        ::= { wfAtmizerCfgEntry 3 }

    wfAtmizerCfgRxQueueLenMax OBJECT-TYPE
        SYNTAX	INTEGER {
    		    default(150)
    		}
        ACCESS	read-write
        STATUS	mandatory
        DESCRIPTION
                "The maximum size of a receive buffer list which will be delivered
                by the RX ATMizer to the driver."
        DEFVAL	{ default }
        ::= { wfAtmizerCfgEntry 4 }

    wfAtmizerCfgRxQueueTmoMax OBJECT-TYPE
        SYNTAX	INTEGER {
    		    default(100)
    		}
        ACCESS	read-write
        STATUS	mandatory
        DESCRIPTION
                "The maximum amount of idle time (in microseconds) the RX ATMizer will wait
                before delivering its queue of receive buffers to the driver."
        DEFVAL	{ default }
        ::= { wfAtmizerCfgEntry 5 }

    wfAtmizerCfgRxBuffersMax OBJECT-TYPE
        SYNTAX	INTEGER
        ACCESS	read-write
        STATUS	mandatory
        DESCRIPTION
                "The maximum number of receive buffers which the RX ATMizer can own
                before encountering a lack of resources. This is a
                configurable option and does not indicate the true value."
        ::= { wfAtmizerCfgEntry 6 }

    wfAtmizerCfgRxPagesMax OBJECT-TYPE
        SYNTAX	INTEGER
        ACCESS	read-write
        STATUS	mandatory
        DESCRIPTION
                "The maximum number of additional physical pages which the RX ATMizer
                can own before encountering a lack of resources. This is a
                configurable option and does not indicate the true value."
        ::= { wfAtmizerCfgEntry 7 }

    wfAtmizerCfgTxBuffersMax OBJECT-TYPE
        SYNTAX	INTEGER
        ACCESS	read-write
        STATUS	mandatory
        DESCRIPTION
                "The maximum number of transmit buffers which the TX ATMizer can own
                before it begins clipping. This is a configurable option
                and does not indicate the true value."
        ::= { wfAtmizerCfgEntry 8 }

    wfAtmizerCfgTxPagesMax OBJECT-TYPE
        SYNTAX	INTEGER
        ACCESS	read-write
        STATUS	mandatory
        DESCRIPTION
                "The maximum number of additional physical pages which the TX ATMizer
                can own before encountering a lack of resources. This is
                a configurable option and does not indicate the true value."
        ::= { wfAtmizerCfgEntry 9 }

    wfAtmizerCfgTxPercentRsrcs OBJECT-TYPE
        SYNTAX	INTEGER {
                    default(50)
                }
        ACCESS	read-write
        STATUS	mandatory
        DESCRIPTION
                "The maximum percentage of transmit buffers which the
                transmit driver can hold before it begins clipping. This
                is a configurable option and does not indicate the true value."
        DEFVAL  { default }
        ::= { wfAtmizerCfgEntry 10 }

    wfAtmizerCfgHeartbeatPeriod OBJECT-TYPE
        SYNTAX	INTEGER {
    		    default(3)
    		}
        ACCESS	read-write
        STATUS	mandatory
        DESCRIPTION
                "The timer period, in seconds, which defines how often heartbeat messages
                are sent to the ATMizers."
        DEFVAL	{ default }
        ::= { wfAtmizerCfgEntry 11 }

    wfAtmizerRxBuffersMax OBJECT-TYPE
        SYNTAX	INTEGER
        ACCESS	read-only
        STATUS	mandatory
        DESCRIPTION
                "The maximum number of receive buffers which the RX ATMizer can own
                before encountering a lack of resources. This value
                indicates the true value of the Rx buffers available."
        ::= { wfAtmizerCfgEntry 12 }

    wfAtmizerRxPagesMax OBJECT-TYPE
        SYNTAX	INTEGER
        ACCESS	read-only
        STATUS	mandatory
        DESCRIPTION
                "The maximum number of additional physical pages which the RX ATMizer
                can own before encountering a lack of resources. This
                value indicates the true value of the Rx Pages available."
        ::= { wfAtmizerCfgEntry 13 }

    wfAtmizerTxBuffersMax OBJECT-TYPE
        SYNTAX	INTEGER
        ACCESS	read-only
        STATUS	mandatory
        DESCRIPTION
                "The maximum number of transmit buffers which the TX ATMizer can own
                before it begins clipping. This value indicates the true
                value of the Tx buffers available."
        ::= { wfAtmizerCfgEntry 14 }

    wfAtmizerTxPagesMax OBJECT-TYPE
        SYNTAX	INTEGER
        ACCESS	read-only
        STATUS	mandatory
        DESCRIPTION
                "The maximum number of additional physical pages which the TX ATMizer
                can own before encountering a lack of resources. This
                value indicates the true value of the Tx pagess available."
        ::= { wfAtmizerCfgEntry 15 }

    wfAtmizerTxPercentRsrcs OBJECT-TYPE
        SYNTAX	INTEGER
        ACCESS	read-only
        STATUS	mandatory
        DESCRIPTION
                "The maximum percentage of transmit buffers which the
                transmit driver can hold before it begins clipping."
        ::= { wfAtmizerCfgEntry 16 }

    wfAtmizerTxPerVcClipEnable OBJECT-TYPE
        SYNTAX  INTEGER {
                    enable(1),
                    disable(2)
                }
        ACCESS  read-write
        STATUS  mandatory
        DESCRIPTION
                "Enable/disable Transmit per-VC buffer clipping threshold"
        DEFVAL  { disable }
        ::= { wfAtmizerCfgEntry 17 }
 
    wfAtmizerCfgTxVcBuffersMax OBJECT-TYPE
        SYNTAX  INTEGER
        ACCESS  read-write
        STATUS  mandatory
        DESCRIPTION
                "The maximum number of buffers which the TX ATMizer can queue
                 for a particular virtual connection before clipping. This
                 is a configurable option and does not indicate the true value."
        ::= { wfAtmizerCfgEntry 18 }
 
    wfAtmizerTxVcBuffersMax OBJECT-TYPE
        SYNTAX  INTEGER  
        ACCESS  read-only
        STATUS  mandatory
        DESCRIPTION
                "The maximum number of buffers which the TX ATMizer can queue
                 for a particular virtual connection before clipping."
        ::= { wfAtmizerCfgEntry 19 }

    wfAtmizerDrvCfgTable OBJECT-TYPE
        SYNTAX	SEQUENCE OF WfAtmizerDrvCfgEntry
        ACCESS	not-accessible
        STATUS	mandatory
        DESCRIPTION
                "ATMizer Line Driver Configuration Record"
        ::= { wfAtmCellSwitchGroup 2 }

    wfAtmizerDrvCfgEntry OBJECT-TYPE
        SYNTAX	WfAtmizerDrvCfgEntry
        ACCESS	not-accessible
        STATUS	mandatory
        DESCRIPTION
                "Information about a particular driver"
        INDEX	{ wfAtmizerDrvCfgSlot,
    		  wfAtmizerDrvCfgPort }
        ::= { wfAtmizerDrvCfgTable 1 }

    WfAtmizerDrvCfgEntry ::= SEQUENCE {
    	    wfAtmizerDrvCfgDelete
    		INTEGER,
    	    wfAtmizerDrvCfgEnable
    		INTEGER,
    	    wfAtmizerDrvCfgState
    		INTEGER,
    	    wfAtmizerDrvCfgSlot
    		INTEGER,
    	    wfAtmizerDrvCfgPort
    		INTEGER,
    	    wfAtmizerDrvCfgCct
    		INTEGER,
    	    wfAtmizerDrvCfgLineNumber
    		INTEGER,
    	    wfAtmizerDrvCfgType
    		INTEGER,
    	    wfAtmizerDrvCfgMtu
    		INTEGER,
    	    wfAtmizerDrvCfgSpeed
    		INTEGER,
    	    wfAtmizerDrvCfgDpNotify
    		INTEGER,
    	    wfAtmizerDrvCfgDpNotifyTimeout
    		INTEGER,
    	    wfAtmizerDrvCfgVcInactEnable
    		INTEGER,
    	    wfAtmizerDrvCfgVcInactTimeout
    		INTEGER,
    	    wfAtmizerDrvCfgMadrCt
    		INTEGER,
    	    wfAtmizerDrvCfgMadr
    		OCTET STRING,
    	    wfAtmizerDrvCfgFramingMode
    		INTEGER,
    	    wfAtmizerDrvCfgClkSource
    		INTEGER,
    	    wfAtmizerDrvCfgLogLevel
    		INTEGER,
    	    wfAtmizerDrvCfgDsx3SendCode
    		INTEGER,
    	    wfAtmizerDrvCfgDsx3LoopbackConfig
    		INTEGER,
    	    wfAtmizerDrvCfgDs3Scrambling
    		INTEGER,
    	    wfAtmizerDrvCfgDs3LineBuildOut
    		INTEGER,
    	    wfAtmizerDrvCfgModule
    		INTEGER,
            wfAtmizerFramingMode
                INTEGER,
	    wfAtmizerDrvCfgIwfCct
		INTEGER,
	    wfAtmizerDrvCfgCcType
		INTEGER,
            wfAtmizerDrvCfgMaxVcls
		INTEGER,
            wfAtmizerDrvCfgCurrVcls
		INTEGER,
	    wfAtmizerDrvCfgScrSum
                INTEGER,
	    wfAtmizerDrvCfgExtRate
                INTEGER
        }

    wfAtmizerDrvCfgDelete OBJECT-TYPE
        SYNTAX	INTEGER {
    		    create(1),
    		    delete(2)
    		}
        ACCESS	read-write
        STATUS	mandatory
        DESCRIPTION
                "Create/delete MIB instance parameter."
        DEFVAL	{ create }
        ::= { wfAtmizerDrvCfgEntry 1 }

    wfAtmizerDrvCfgEnable OBJECT-TYPE
        SYNTAX	INTEGER {
    		    enable(1),
    		    disable(2)
    		}
        ACCESS	read-write
        STATUS	mandatory
        DESCRIPTION
                "Enable/disable driver parameter."
        DEFVAL	{ enable }
        ::= { wfAtmizerDrvCfgEntry 2 }

    wfAtmizerDrvCfgState OBJECT-TYPE
        SYNTAX	INTEGER {
    		    up(1),
    		    down(2),
    		    init(3),
    		    notpresent(20)
    		}
        ACCESS	read-only
        STATUS	mandatory
        DESCRIPTION
                "Driver state parameter. This parameter does not represent the state
                of the physical interface!"
        DEFVAL	{ notpresent }
        ::= { wfAtmizerDrvCfgEntry 3 }

    wfAtmizerDrvCfgSlot OBJECT-TYPE
        SYNTAX	INTEGER(1..14)
        ACCESS	read-only
        STATUS	mandatory
        DESCRIPTION
                "Slot number -- instance id."
        ::= { wfAtmizerDrvCfgEntry 4 }

    wfAtmizerDrvCfgPort OBJECT-TYPE
        SYNTAX	INTEGER {
    		    one(1),
    		    two(2),
    		    three(3),
    		    four(4)
    		}
        ACCESS	read-only
        STATUS	mandatory
        DESCRIPTION
                "Physical port number -- instance id."
        ::= { wfAtmizerDrvCfgEntry 5 }

    wfAtmizerDrvCfgCct OBJECT-TYPE
        SYNTAX	INTEGER(1..1023)
        ACCESS	read-write
        STATUS	mandatory
        DESCRIPTION
                "Circuit number for the driver."
        ::= { wfAtmizerDrvCfgEntry 6 }

    wfAtmizerDrvCfgLineNumber OBJECT-TYPE
        SYNTAX	INTEGER
        ACCESS	read-write
        STATUS	mandatory
        DESCRIPTION
                "The LineNumber is an Index value used to uniquely identify
                an instance of a physical ATM port. This value shall be used
                as an instance identifier for ATM MIB objects."
        ::= { wfAtmizerDrvCfgEntry 7 }

    wfAtmizerDrvCfgType OBJECT-TYPE
        SYNTAX	INTEGER {
    		    sonet(1),
    		    ds3(2),
    		    e3(3),
    		    ds1(4),
    		    e1(5)
    		}
        ACCESS	read-only
        STATUS	mandatory
        DESCRIPTION
                "The type of interface. This attribute is an alias for 'ifType."
        ::= { wfAtmizerDrvCfgEntry 8 }

    wfAtmizerDrvCfgMtu OBJECT-TYPE
        SYNTAX	INTEGER(0..9188)
        ACCESS	read-write
        STATUS	mandatory
        DESCRIPTION
                "The size of the largest packet which can be sent/received on the
                interface, specified in octets. This attribute is an alias for
                'ifMtu'."
        DEFVAL	{ 4608 }
        ::= { wfAtmizerDrvCfgEntry 9 }

    wfAtmizerDrvCfgSpeed OBJECT-TYPE
        SYNTAX	INTEGER {
		    speed622mb(622080000),
    		    speed155mb(155520000),
    		    speed140mb(140000000),
    		    speed100mb(100000000),
    		    speed45mb(44736000),
    		    speed35mb(34368000),
                    speed2p048mb(2048000),
                    speed1p544mb(1544000)
    		}
        ACCESS	read-only
        STATUS	mandatory
        DESCRIPTION
                "An estimate of the interface's current bandwidth in bits per
                second. This attribute is an alias for 'ifSpeed'."
        ::= { wfAtmizerDrvCfgEntry 10 }

    wfAtmizerDrvCfgDpNotify OBJECT-TYPE
        SYNTAX	INTEGER {
    		    enable(1),
    		    disable(2)
    		}
        ACCESS	read-write
        STATUS	mandatory
        DESCRIPTION
                "Data Path (DP) notify function. This function, when enabled,
                will disable the DP interface when the physical interface becomes
                non-operational."
        DEFVAL	{ enable }
        ::= { wfAtmizerDrvCfgEntry 11 }

    wfAtmizerDrvCfgDpNotifyTimeout OBJECT-TYPE
        SYNTAX	INTEGER(0..3600)
        ACCESS	read-write
        STATUS	mandatory
        DESCRIPTION
                "Data Path (DP) notify function timeout period. This value specifies
                the number of seconds to wait before implementing the DP notify
                function. A timer will get set to this value when the state of
                the physical interface transitions from operational to
                non-operational when the DP notify function is enabled."
        DEFVAL	{ 1 }
        ::= { wfAtmizerDrvCfgEntry 12 }

    wfAtmizerDrvCfgVcInactEnable OBJECT-TYPE
        SYNTAX	INTEGER {
    		    enable(1),
    		    disable(2)
    		}
        ACCESS	read-write
        STATUS	mandatory
        DESCRIPTION
                "Inactivity timeout value for all SVCs on this interface in seconds.
                If no cells have been transmitted or received on an SVC over the given
                timeout period then the SVC will be closed.  If this value is set to
                zero, then the SVCs inactivity timer will be disabled for this interface."
        DEFVAL	{ enable }
        ::= { wfAtmizerDrvCfgEntry 13 }

    wfAtmizerDrvCfgVcInactTimeout OBJECT-TYPE
        SYNTAX	INTEGER(60..3600)
        ACCESS	read-write
        STATUS	mandatory
        DESCRIPTION
                "Inactivity timeout value for all SVCs on this interface in seconds.
                If no cells have been transmitted or received on an SVC over the given
                timeout period then the SVC will be closed."
        DEFVAL	{ 1200 }
        ::= { wfAtmizerDrvCfgEntry 14 }

    wfAtmizerDrvCfgMadrCt OBJECT-TYPE
        SYNTAX	INTEGER
        ACCESS	read-only
        STATUS	mandatory
        DESCRIPTION
                "Number of PROM-based MAC addresses."
        ::= { wfAtmizerDrvCfgEntry 15 }

    wfAtmizerDrvCfgMadr OBJECT-TYPE
        SYNTAX	OCTET STRING
        ACCESS	read-only
        STATUS	mandatory
        DESCRIPTION
                "First MAC address in canonical format (i.e., 00-00-a2...). The number of
                subsequent MAC addresses is specified by wfAtmizerDrvCfgMadrCt which are
                sequential."
        ::= { wfAtmizerDrvCfgEntry 16 }

    wfAtmizerDrvCfgFramingMode OBJECT-TYPE
        SYNTAX	INTEGER {
    		    sdh(1),
    		    sonet(2),
    		    cbit(3),
    		    m23(4),
    		    g751(5),
    		    g832(6),
                    cbitnofallback(7),
                    clearchannel(8),
                    t1adm(9),
                    e1adm(10),
                    t1plcp(11),
                    e1plcp(12),
                    t3cbitplcp(13),
                    t3m23plcp(14)
    		}
        ACCESS	read-write
        STATUS	mandatory
        DESCRIPTION
                "The framing (transceiver) mode for the physical interface"
        DEFVAL	{ sonet }
        ::= { wfAtmizerDrvCfgEntry 17 }

    wfAtmizerDrvCfgClkSource OBJECT-TYPE
        SYNTAX	INTEGER {
    		    intrn(1),
    		    extrn(2)
    		}
        ACCESS	read-write
        STATUS	mandatory
        DESCRIPTION
                "Source of the physical interface clocking signal, either internal or
                external."
        DEFVAL	{ intrn }
        ::= { wfAtmizerDrvCfgEntry 18 }

    wfAtmizerDrvCfgLogLevel OBJECT-TYPE
        SYNTAX	INTEGER {
    		    atmcdbg(1),
    		    atmcdb2(2),
    		    vcmsg(4)
    		}
        ACCESS	read-write
        STATUS	mandatory
        DESCRIPTION
                "Bit mask which controls the amount of logging done by the ATM driver.
                If a bit in the mask is set, it enables logging of an event class.  If
                a bit is cleared, it disables logging of an event class.

                     -----------------------------------
                     |                                 |
                     -----------------------------------
                      31                              0

                       bit 0 - Link Module Coprocessor debug events
                       bit 1 - VC setup/teardown events"
        ::= { wfAtmizerDrvCfgEntry 19 }

    wfAtmizerDrvCfgDsx3SendCode OBJECT-TYPE
        SYNTAX	INTEGER {
    		    none(1),
    		    line(2),
    		    payload(3),
    		    reset(4),
    		    loop(5),
    		    pattern(6)
    		}
        ACCESS	read-write
        STATUS	mandatory
        DESCRIPTION
                "This variable indicates what type of code is being sent across
                DS3/E3 interface by the device. (These are optional for E3
                interfaces.) The values mean:

                ATM_DSX3_SEND_CODE_NONE    : Sending looped or normal data.
                ATM_DSX3_SEND_CODE_LINE    : Sending a request for line loopback.
                ATM_DSX3_SEND_CODE_PAYLOAD : Sending a request for a payload
                 loopback. (i.e., all Ds1/E1s in a
                 DS3/E3 frame)
                ATM_DSX3_SEND_CODE_RESET   : Sending a loopback deactivation
                 request.
                ATM_DSX3_SEND_CODE_DS1_LOOP: Requesting to loopback a particular
                 DS1/E1 within a DS3/E3 frame.
                ATM_DSX3_SEND_TEST_PATTERN : Sending a test pattern."
        DEFVAL	{ none }
        ::= { wfAtmizerDrvCfgEntry 20 }

    wfAtmizerDrvCfgDsx3LoopbackConfig OBJECT-TYPE
        SYNTAX	INTEGER {
    		    none(1),
    		    payload(2),
    		    line(3),
    		    other(4)
    		}
        ACCESS	read-write
        STATUS	mandatory
        DESCRIPTION
                "This variable represents the loopback configuration of the DS3/E3
                interface. Ther values mean:

                ATM_DSX3_LOOPBACK_NONE    :  Not in the loopback state/ A device
                 that is not capable of performing a
                 loopback on the interface shall always
                 return this as it's value.
                ATM_DSX3_LOOPBACK_PAYLOAD :  The received signal at this interface
                 is looped through the
                 device. Typically the received signal
                 is looped back for retransmission
                 after it has passed through the
                 device's framing function.

                ATM_DSX3_LOOPBACK_LINE    :  The received signal at this interface
                 does not go through the device
                 (minimum penetration) but is looped
                 back out.

                ATM_DSX3_LOOPBACK_OTHER   :  Loopback's that are not defined here."
        DEFVAL	{ none }
        ::= { wfAtmizerDrvCfgEntry 21 }

    wfAtmizerDrvCfgDs3Scrambling OBJECT-TYPE
        SYNTAX	INTEGER {
    		    on(1),
    		    off(2)
    		}
        ACCESS	read-write
        STATUS	mandatory
        DESCRIPTION
                "This variable represents if scrambling is turned on or off"
        DEFVAL	{ off }
        ::= { wfAtmizerDrvCfgEntry 22 }

    wfAtmizerDrvCfgDs3LineBuildOut OBJECT-TYPE
        SYNTAX	INTEGER {
    		    short(1),
    		    long(2)
    		}
        ACCESS	read-write
        STATUS	mandatory
        DESCRIPTION
                "This variable represents the Line Build Out for the DS3 short and
                long cables. "
        DEFVAL	{ short }
        ::= { wfAtmizerDrvCfgEntry 23 }

    wfAtmizerDrvCfgModule OBJECT-TYPE
        SYNTAX	INTEGER 
        ACCESS	read-only
        STATUS	mandatory
        DESCRIPTION
                "Module number for ASN type platforms. For non-ASN
                 platforms this attribute will not be used."
        ::= { wfAtmizerDrvCfgEntry 24 }

    wfAtmizerFramingMode OBJECT-TYPE
        SYNTAX	INTEGER 
        ACCESS	read-only
        STATUS	mandatory
        DESCRIPTION
                "The actual framing (transceiver) mode for the physical interface"
        ::= { wfAtmizerDrvCfgEntry 25 }

    wfAtmizerDrvCfgIwfCct OBJECT-TYPE
	SYNTAX	INTEGER(1..1023)
	ACCESS	read-write
	STATUS	mandatory
	DESCRIPTION
		"This variable represents the circuit number associated with
		  FR/ATM Interworking Service record. "
	::= { wfAtmizerDrvCfgEntry 26 }

    wfAtmizerDrvCfgCcType OBJECT-TYPE
        SYNTAX  INTEGER{
                none(1),
                mplsMlm(2),
                atmCc(4)
        }
        ACCESS  read-write
        STATUS  mandatory
        DESCRIPTION
                "Which one is the Call Control module, ATM or MPLS?"
        DEFVAL  {none}
        ::= { wfAtmizerDrvCfgEntry 27 }

    wfAtmizerDrvCfgMaxVcls OBJECT-TYPE
        SYNTAX	INTEGER
        ACCESS	read-only
        STATUS	mandatory
        DESCRIPTION
                "The maximum number of Virtual Channel Links (VCLs) that are
                 supported at the ATM driver interface."
        ::= { wfAtmizerDrvCfgEntry 28 }

    wfAtmizerDrvCfgCurrVcls OBJECT-TYPE
        SYNTAX	INTEGER
        ACCESS	read-only
        STATUS	mandatory
        DESCRIPTION
                "The number of Virtual Channel Links (VCLs) currently active."
        ::= { wfAtmizerDrvCfgEntry 29 }

    wfAtmizerDrvCfgScrSum OBJECT-TYPE
	SYNTAX	INTEGER
	ACCESS	read-only
	STATUS	mandatory
	DESCRIPTION
		"Total sum of all VC Sustainable Cell Rates (SCR). Used for Call
                 Admission Control (CAC)."
	::= { wfAtmizerDrvCfgEntry 30 }

    wfAtmizerDrvCfgExtRate OBJECT-TYPE
	SYNTAX	INTEGER
	ACCESS	read-write
	STATUS	mandatory
	DESCRIPTION
		"A user specified value for line speed which, if non-zero,
		will be reported as ifEntry.ifSpeed. It has no effect on
		operation of the interface."
        DEFVAL	{ 0 }
	::= { wfAtmizerDrvCfgEntry 31 }


    wfAtmizerIntfStatsTable OBJECT-TYPE
        SYNTAX	SEQUENCE OF WfAtmizerIntfStatsEntry
        ACCESS	not-accessible
        STATUS	mandatory
        DESCRIPTION
                "ARE Line Driver Statistics Record"
        ::= { wfAtmCellSwitchGroup 3 }

    wfAtmizerIntfStatsEntry OBJECT-TYPE
        SYNTAX	WfAtmizerIntfStatsEntry
        ACCESS	not-accessible
        STATUS	mandatory
        DESCRIPTION
                "Information about a particular driver"
        INDEX	{ wfAtmizerIntfSlot,
    		  wfAtmizerIntfPort }
        ::= { wfAtmizerIntfStatsTable 1 }

    WfAtmizerIntfStatsEntry ::= SEQUENCE {
    	    wfAtmizerIntfSlot
    		INTEGER,
    	    wfAtmizerIntfPort
    		INTEGER,
    	    wfAtmizerIntfLastChange
    		TimeTicks,
    	    wfAtmizerIntfOutQLen
    		Gauge,
    	    wfAtmizerIntfStatus
    		INTEGER,
    	    wfAtmizerIntfIndex
    		INTEGER,
    	    wfAtmizerIntfOcdEvents
    		Counter,
    	    wfAtmizerIntfTcAlarmState
    		INTEGER,
    	    wfAtmizerIntfRxPacketsOkWrap
    		Counter,
    	    wfAtmizerIntfRxPacketsOk
    		Counter,
    	    wfAtmizerIntfRxCellsOkWrap
    		Counter,
    	    wfAtmizerIntfRxCellsOk
    		Counter,
    	    wfAtmizerIntfRxOamCount
    		Counter,
    	    wfAtmizerIntfRxFlowCtrlCount
    		Counter,
    	    wfAtmizerIntfRxInvalidHeaders
    		Counter,
    	    wfAtmizerIntfRxOverSizedSDUs
    		Counter,
    	    wfAtmizerIntfRxCrcErrors
    		Counter,
    	    wfAtmizerIntfRxCrc10Errors
    		Counter,
    	    wfAtmizerIntfRxLackBufCredits
    		Counter,
    	    wfAtmizerIntfRxLackPageCredits
    		Counter,
    	    wfAtmizerIntfRxLackBufResc
    		Counter,
    	    wfAtmizerIntfRxLackPageResc
    		Counter,
    	    wfAtmizerIntfTxPacketsOkWrap
    		Counter,
    	    wfAtmizerIntfTxPacketsOk
    		Counter,
    	    wfAtmizerIntfTxCellsOkWrap
    		Counter,
    	    wfAtmizerIntfTxCellsOk
    		Counter,
    	    wfAtmizerIntfTxOamCount
    		Counter,
    	    wfAtmizerIntfTxFlowCtrlCount
    		Counter,
    	    wfAtmizerIntfTxBadVcs
    		Counter,
    	    wfAtmizerIntfTxOverSizedSDUs
    		Counter,
    	    wfAtmizerIntfTxLackBufCredits
    		Counter,
    	    wfAtmizerIntfTxLackPageCredits
    		Counter,
    	    wfAtmizerIntfTxDrvClipCount
    		Counter,
    	    wfAtmizerIntfHecDetectedCount
    		Counter,
    	    wfAtmizerIntfHecCorrectedCount
    		Counter,
	    wfAtmizerIntfRxOctets
		Counter,
	    wfAtmizerIntfTxOctets
		Counter,
	    wfAtmizerIntfRxUTOPIAErrors
		Counter,
	    wfAtmizerIntfRxLengthErrors
		Counter,
	    wfAtmizerIntfRxAbortMessages
		Counter,
	    wfAtmizerIntfRxSequenceNumberErrors
		Counter
        }

    wfAtmizerIntfSlot OBJECT-TYPE
        SYNTAX	INTEGER(1..14)
        ACCESS	read-only
        STATUS	mandatory
        DESCRIPTION
                "Slot number -- instance id."
        ::= { wfAtmizerIntfStatsEntry 1 }

    wfAtmizerIntfPort OBJECT-TYPE
        SYNTAX	INTEGER {
    		    one(1),
    		    two(2),
    		    three(3),
    		    four(4)
    		}
        ACCESS	read-only
        STATUS	mandatory
        DESCRIPTION
                "Physical port number -- instance id."
        ::= { wfAtmizerIntfStatsEntry 2 }

    wfAtmizerIntfLastChange OBJECT-TYPE
        SYNTAX	TimeTicks
        ACCESS	read-only
        STATUS	mandatory
        DESCRIPTION
                "The time (in hundreths of a second) since the network management
                portion of the system was last re-initialized. This attribute is
                an alias for 'ifLastChange' in the MIBII System Group."
        ::= { wfAtmizerIntfStatsEntry 3 }

    wfAtmizerIntfOutQLen OBJECT-TYPE
        SYNTAX	Gauge
        ACCESS	read-only
        STATUS	mandatory
        DESCRIPTION
                "This attribute is an alias for 'ifOutQLen' in the MIBII interface
                group."
        ::= { wfAtmizerIntfStatsEntry 4 }

    wfAtmizerIntfStatus OBJECT-TYPE
        SYNTAX	INTEGER {
    		    up(1),
    		    down(2),
    		    testing(3),
    		    unknown(4),
    		    dormant(5)
    		}
        ACCESS	read-only
        STATUS	mandatory
        DESCRIPTION
                "MIB-II ifOperStatus"
        DEFVAL	{ unknown }
        ::= { wfAtmizerIntfStatsEntry 5 }

    wfAtmizerIntfIndex OBJECT-TYPE
        SYNTAX	INTEGER
        ACCESS	read-only
        STATUS	mandatory
        DESCRIPTION
                "MIB-II interface index"
        ::= { wfAtmizerIntfStatsEntry 6 }

    wfAtmizerIntfOcdEvents OBJECT-TYPE
        SYNTAX	Counter
        ACCESS	read-only
        STATUS	mandatory
        DESCRIPTION
                "The number of times the Out of Cell Delineation (OCD) events occur. If
                seven consecutive ATM cells have Header Error Control (HEC) violations,
                an OCD event occurs. A high number of OCD events may indicate a problem
                with the TC sublayer."
        ::= { wfAtmizerIntfStatsEntry 7 }

    wfAtmizerIntfTcAlarmState OBJECT-TYPE
        SYNTAX	INTEGER {
    		    no-alarm(1),
    		    failure(2)
    		}
        ACCESS	read-only
        STATUS	mandatory
        DESCRIPTION
                "This variable indicates if there is an alarm present for the TC sublayer.
                The value ATM_LCD_FAILURE indicates that a Loss of Cell Delineation (LCD)
                failure state has been declared for the TC sublayer. Transition from
                failure to the ATM_NO_ALARM state occurs when six consecutive ATM cells
                are received with valid HEC, followed by about 10 seconds of acceptable
                working signal."
        ::= { wfAtmizerIntfStatsEntry 8 }

    wfAtmizerIntfRxPacketsOkWrap OBJECT-TYPE
        SYNTAX	Counter
        ACCESS	read-only
        STATUS	mandatory
        DESCRIPTION
                "The number of times the wfAtmizerIntfRxPacketsOk counter has wrapped."
        ::= { wfAtmizerIntfStatsEntry 9 }

    wfAtmizerIntfRxPacketsOk OBJECT-TYPE
        SYNTAX	Counter
        ACCESS	read-only
        STATUS	mandatory
        DESCRIPTION
                "The number of Service Data Units (SDUs) received without error."
        ::= { wfAtmizerIntfStatsEntry 10 }

    wfAtmizerIntfRxCellsOkWrap OBJECT-TYPE
        SYNTAX	Counter
        ACCESS	read-only
        STATUS	mandatory
        DESCRIPTION
                "The number of times the wfAtmizerIntfRxCellsOk counter has wrapped."
        ::= { wfAtmizerIntfStatsEntry 11 }

    wfAtmizerIntfRxCellsOk OBJECT-TYPE
        SYNTAX	Counter
        ACCESS	read-only
        STATUS	mandatory
        DESCRIPTION
                "The number of reassembled Service Data Unit (SDU) cells received without
                error."
        ::= { wfAtmizerIntfStatsEntry 12 }

    wfAtmizerIntfRxOamCount OBJECT-TYPE
        SYNTAX	Counter
        ACCESS	read-only
        STATUS	mandatory
        DESCRIPTION
                "The number of F4/F5 OAM Cells received on this interface."
        ::= { wfAtmizerIntfStatsEntry 13 }

    wfAtmizerIntfRxFlowCtrlCount OBJECT-TYPE
        SYNTAX	Counter
        ACCESS	read-only
        STATUS	mandatory
        DESCRIPTION
                "The number of Flow Control OAM Cells received on this interface."
        ::= { wfAtmizerIntfStatsEntry 14 }

    wfAtmizerIntfRxInvalidHeaders OBJECT-TYPE
        SYNTAX	Counter
        ACCESS	read-only
        STATUS	mandatory
        DESCRIPTION
                "The number of receive cells dropped because of bad header fields
                (invalid VPI/VCI, non-zero GFC, bad PTI field)."
        ::= { wfAtmizerIntfStatsEntry 15 }

    wfAtmizerIntfRxOverSizedSDUs OBJECT-TYPE
        SYNTAX	Counter
        ACCESS	read-only
        STATUS	mandatory
        DESCRIPTION
                "The number of receive packets dropped because the reassembled SDU
                was greater than the MTU for this interface."
        ::= { wfAtmizerIntfStatsEntry 16 }

    wfAtmizerIntfRxCrcErrors OBJECT-TYPE
        SYNTAX	Counter
        ACCESS	read-only
        STATUS	mandatory
        DESCRIPTION
                "The number of received cells dropped because of an invalid CRC."
        ::= { wfAtmizerIntfStatsEntry 17 }

    wfAtmizerIntfRxCrc10Errors OBJECT-TYPE
        SYNTAX	Counter
        ACCESS	read-only
        STATUS	mandatory
        DESCRIPTION
                "The number of OAM cells dropped because of an invalid CRC-10."
        ::= { wfAtmizerIntfStatsEntry 18 }

    wfAtmizerIntfRxLackBufCredits OBJECT-TYPE
        SYNTAX	Counter
        ACCESS	read-only
        STATUS	mandatory
        DESCRIPTION
                "The number of received packets lost on this interface because no receive
                buffer space was available to the receiver for incoming data."
        ::= { wfAtmizerIntfStatsEntry 19 }

    wfAtmizerIntfRxLackPageCredits OBJECT-TYPE
        SYNTAX	Counter
        ACCESS	read-only
        STATUS	mandatory
        DESCRIPTION
                "The number of received packets lost on this interface because no physical
                pages were available to the receiver for incoming data."
        ::= { wfAtmizerIntfStatsEntry 20 }

    wfAtmizerIntfRxLackBufResc OBJECT-TYPE
        SYNTAX	Counter
        ACCESS	read-only
        STATUS	mandatory
        DESCRIPTION
                "The number of received packets lost on this interface because there were
                no free system buffers available."
        ::= { wfAtmizerIntfStatsEntry 21 }

    wfAtmizerIntfRxLackPageResc OBJECT-TYPE
        SYNTAX	Counter
        ACCESS	read-only
        STATUS	mandatory
        DESCRIPTION
                "The number of received packets lost on this interface because there were
                no free system pages available."
        ::= { wfAtmizerIntfStatsEntry 22 }

    wfAtmizerIntfTxPacketsOkWrap OBJECT-TYPE
        SYNTAX	Counter
        ACCESS	read-only
        STATUS	mandatory
        DESCRIPTION
                "The number of times the wfAtmizerIntfTxPacketsOk counter has wrapped."
        ::= { wfAtmizerIntfStatsEntry 23 }

    wfAtmizerIntfTxPacketsOk OBJECT-TYPE
        SYNTAX	Counter
        ACCESS	read-only
        STATUS	mandatory
        DESCRIPTION
                "The number of Service Data Units (SDUs) transmitted without error."
        ::= { wfAtmizerIntfStatsEntry 24 }

    wfAtmizerIntfTxCellsOkWrap OBJECT-TYPE
        SYNTAX	Counter
        ACCESS	read-only
        STATUS	mandatory
        DESCRIPTION
                "The number of times the wfAtmizerIntfTxCellsOk counter has wrapped."
        ::= { wfAtmizerIntfStatsEntry 25 }

    wfAtmizerIntfTxCellsOk OBJECT-TYPE
        SYNTAX	Counter
        ACCESS	read-only
        STATUS	mandatory
        DESCRIPTION
                "The number of segmented Service Data Unit (SDU) cells transmitted without
                error."
        ::= { wfAtmizerIntfStatsEntry 26 }

    wfAtmizerIntfTxOamCount OBJECT-TYPE
        SYNTAX	Counter
        ACCESS	read-only
        STATUS	mandatory
        DESCRIPTION
                "The number of F4/F5 OAM Cells transmitted on this interface."
        ::= { wfAtmizerIntfStatsEntry 27 }

    wfAtmizerIntfTxFlowCtrlCount OBJECT-TYPE
        SYNTAX	Counter
        ACCESS	read-only
        STATUS	mandatory
        DESCRIPTION
                "The number of Flow Control OAM Cells transmitted on this interface."
        ::= { wfAtmizerIntfStatsEntry 28 }

    wfAtmizerIntfTxBadVcs OBJECT-TYPE
        SYNTAX	Counter
        ACCESS	read-only
        STATUS	mandatory
        DESCRIPTION
                "Count of packets dropped on transmit because of an invalid VPI/VCI."
        ::= { wfAtmizerIntfStatsEntry 29 }

    wfAtmizerIntfTxOverSizedSDUs OBJECT-TYPE
        SYNTAX	Counter
        ACCESS	read-only
        STATUS	mandatory
        DESCRIPTION
                "The number of transmit packets dropped because their SDU size was greater
                than the MTU for this interface."
        ::= { wfAtmizerIntfStatsEntry 30 }

    wfAtmizerIntfTxLackBufCredits OBJECT-TYPE
        SYNTAX	Counter
        ACCESS	read-only
        STATUS	mandatory
        DESCRIPTION
                "The number of transmit packets lost on this interface because no buffer
                space was available to the transmitter for outgoing data."
        ::= { wfAtmizerIntfStatsEntry 31 }

    wfAtmizerIntfTxLackPageCredits OBJECT-TYPE
        SYNTAX	Counter
        ACCESS	read-only
        STATUS	mandatory
        DESCRIPTION
                "The number of transmit packets lost on this interface because no physical
                pages were available to the transmitter for outgoing data."
        ::= { wfAtmizerIntfStatsEntry 32 }

    wfAtmizerIntfTxDrvClipCount OBJECT-TYPE
        SYNTAX	Counter
        ACCESS	read-only
        STATUS	mandatory
        DESCRIPTION
                "The number of transmit packets lost on this interface because no buffer
                space was available to the host transmit driver for outgoing data."
        ::= { wfAtmizerIntfStatsEntry 33 }

    wfAtmizerIntfHecDetectedCount OBJECT-TYPE
        SYNTAX	Counter
        ACCESS	read-only
        STATUS	mandatory
        DESCRIPTION
                "Number of uncorrectable HEC errors detected on this interface."
        ::= { wfAtmizerIntfStatsEntry 34 }

    wfAtmizerIntfHecCorrectedCount OBJECT-TYPE
        SYNTAX	Counter
        ACCESS	read-only
        STATUS	mandatory
        DESCRIPTION
                "Number of correctable HEC errors detected on this interface."
        ::= { wfAtmizerIntfStatsEntry 35 }

    wfAtmizerIntfRxOctets OBJECT-TYPE
        SYNTAX	Counter
        ACCESS	read-only
        STATUS	mandatory
        DESCRIPTION
                "Count of octets received successfully.

                 Note:
                 May not be supported on all ATM-based platforms."
        ::= { wfAtmizerIntfStatsEntry 36 }

    wfAtmizerIntfTxOctets OBJECT-TYPE
        SYNTAX	Counter
        ACCESS	read-only
        STATUS	mandatory
        DESCRIPTION
                "Count of octets transmitted successfully.

                 Note:
                 May not be supported on all ATM-based platforms."
        ::= { wfAtmizerIntfStatsEntry 37 }

    wfAtmizerIntfRxUTOPIAErrors OBJECT-TYPE
        SYNTAX	Counter
        ACCESS	read-only
        STATUS	mandatory
        DESCRIPTION
                "Count of cells dropped as a result of UTOPIA parity errors
                 or state machine errors (short or long cells).

                 Note:
                 May not be supported on all ATM-based platforms."
        ::= { wfAtmizerIntfStatsEntry 38 }

    wfAtmizerIntfRxLengthErrors OBJECT-TYPE
        SYNTAX	Counter
        ACCESS	read-only
        STATUS	mandatory
        DESCRIPTION
                "Count of Rx length errors.  AAL5 CPCS-PDU length violation.

                 Note:
                 May not be supported on all ATM-based platforms."
        ::= { wfAtmizerIntfStatsEntry 39 }

    wfAtmizerIntfRxAbortMessages OBJECT-TYPE
        SYNTAX	Counter
        ACCESS	read-only
        STATUS	mandatory
        DESCRIPTION
                "Count of abort messages received (AAL5 length field equals 0).

                 Note:
                 May not be supported on all ATM-based platforms."
        ::= { wfAtmizerIntfStatsEntry 40 }

    wfAtmizerIntfRxSequenceNumberErrors OBJECT-TYPE
        SYNTAX	Counter
        ACCESS	read-only
        STATUS	mandatory
        DESCRIPTION
                "Count of AAL1 sequence number errors.

                 Note:
                 May not be supported on all ATM-based platforms."
        ::= { wfAtmizerIntfStatsEntry 41 }


    wfAtmizerVclStatsTable OBJECT-TYPE
        SYNTAX	SEQUENCE OF WfAtmizerVclStatsEntry
        ACCESS	not-accessible
        STATUS	mandatory
        DESCRIPTION
                "Virtual Channel Statistics Record"
        ::= { wfAtmCellSwitchGroup 4 }

    wfAtmizerVclStatsEntry OBJECT-TYPE
        SYNTAX	WfAtmizerVclStatsEntry
        ACCESS	not-accessible
        STATUS	mandatory
        DESCRIPTION
                "Information about a particular virtual channel"
        INDEX	{ wfAtmizerVclIndex,
    		  wfAtmizerVclVpi,
    		  wfAtmizerVclVci }
        ::= { wfAtmizerVclStatsTable 1 }

    WfAtmizerVclStatsEntry ::= SEQUENCE {
    	    wfAtmizerVclIndex
    		INTEGER,
    	    wfAtmizerVclVpi
    		INTEGER,
    	    wfAtmizerVclVci
    		INTEGER,
    	    wfAtmizerVclRxPacketsOkWrap
    		Counter,
    	    wfAtmizerVclRxPacketsOk
    		Counter,
    	    wfAtmizerVclRxCellsOkWrap
    		Counter,
    	    wfAtmizerVclRxCellsOk
    		Counter,
    	    wfAtmizerVclRxOamCount
    		Counter,
    	    wfAtmizerVclRxFlowCtrlCount
    		Counter,
    	    wfAtmizerVclRxInvalidHeaders
    		Counter,
    	    wfAtmizerVclRxOverSizedSDUs
    		Counter,
    	    wfAtmizerVclRxCrcErrors
    		Counter,
    	    wfAtmizerVclRxCrc10Errors
    		Counter,
    	    wfAtmizerVclRxLackBufCredits
    		Counter,
    	    wfAtmizerVclRxLackPageCredits
    		Counter,
    	    wfAtmizerVclRxLackBufResc
    		Counter,
    	    wfAtmizerVclRxLackPageResc
    		Counter,
    	    wfAtmizerVclTxPacketsOkWrap
    		Counter,
    	    wfAtmizerVclTxPacketsOk
    		Counter,
    	    wfAtmizerVclTxCellsOkWrap
    		Counter,
    	    wfAtmizerVclTxCellsOk
    		Counter,
    	    wfAtmizerVclTxOamCount
    		Counter,
    	    wfAtmizerVclTxFlowCtrlCount
    		Counter,
    	    wfAtmizerVclTxOverSizedSDUs
    		Counter,
    	    wfAtmizerVclTxLackBufCredits
    		Counter,
    	    wfAtmizerVclTxLackPageCredits
    		Counter,
	    wfAtmizerVclRxOctets
		Counter,
	    wfAtmizerVclTxOctets
		Counter,
	    wfAtmizerVclTxClipFrames
		Counter,
	    wfAtmizerVclRxLengthErrors
		Counter,
	    wfAtmizerVclRxAbortMessages
		Counter,
	    wfAtmizerVclRxSequenceNumberErrors
		Counter
        }

    wfAtmizerVclIndex OBJECT-TYPE
        SYNTAX	INTEGER
        ACCESS	read-only
        STATUS	mandatory
        DESCRIPTION
                "Instance id - Index number of this physical interface."
        ::= { wfAtmizerVclStatsEntry 1 }

    wfAtmizerVclVpi OBJECT-TYPE
        SYNTAX	INTEGER
        ACCESS	read-only
        STATUS	mandatory
        DESCRIPTION
                "Instance id - Virtual Path Id for this VCL."
        ::= { wfAtmizerVclStatsEntry 2 }

    wfAtmizerVclVci OBJECT-TYPE
        SYNTAX	INTEGER
        ACCESS	read-only
        STATUS	mandatory
        DESCRIPTION
                "Instance id - Virtual Channel Id for this VCL."
        ::= { wfAtmizerVclStatsEntry 3 }

    wfAtmizerVclRxPacketsOkWrap OBJECT-TYPE
        SYNTAX	Counter
        ACCESS	read-only
        STATUS	mandatory
        DESCRIPTION
                "Number of times the wfAtmizerVclRxPacketsOk has wrapped."
        ::= { wfAtmizerVclStatsEntry 4 }

    wfAtmizerVclRxPacketsOk OBJECT-TYPE
        SYNTAX	Counter
        ACCESS	read-only
        STATUS	mandatory
        DESCRIPTION
                "Number of packets received on this VCL."
        ::= { wfAtmizerVclStatsEntry 5 }

    wfAtmizerVclRxCellsOkWrap OBJECT-TYPE
        SYNTAX	Counter
        ACCESS	read-only
        STATUS	mandatory
        DESCRIPTION
                "Number of times the wfAtmizerVclRxCellsOk has wrapped."
        ::= { wfAtmizerVclStatsEntry 6 }

    wfAtmizerVclRxCellsOk OBJECT-TYPE
        SYNTAX	Counter
        ACCESS	read-only
        STATUS	mandatory
        DESCRIPTION
                "Number of cells received on this VCL."
        ::= { wfAtmizerVclStatsEntry 7 }

    wfAtmizerVclRxOamCount OBJECT-TYPE
        SYNTAX	Counter
        ACCESS	read-only
        STATUS	mandatory
        DESCRIPTION
                "The number of OAM cells received on this VCL."
        ::= { wfAtmizerVclStatsEntry 8 }

    wfAtmizerVclRxFlowCtrlCount OBJECT-TYPE
        SYNTAX	Counter
        ACCESS	read-only
        STATUS	mandatory
        DESCRIPTION
                "The number of Flow Control cells received on this VCL."
        ::= { wfAtmizerVclStatsEntry 9 }

    wfAtmizerVclRxInvalidHeaders OBJECT-TYPE
        SYNTAX	Counter
        ACCESS	read-only
        STATUS	mandatory
        DESCRIPTION
                "The number of receive cells dropped because of an invalid ATM header."
        ::= { wfAtmizerVclStatsEntry 10 }

    wfAtmizerVclRxOverSizedSDUs OBJECT-TYPE
        SYNTAX	Counter
        ACCESS	read-only
        STATUS	mandatory
        DESCRIPTION
                "The number of receive packets dropped on this VCL because the reassembled
                SDU was greater than the MTU for this interface."
        ::= { wfAtmizerVclStatsEntry 11 }

    wfAtmizerVclRxCrcErrors OBJECT-TYPE
        SYNTAX	Counter
        ACCESS	read-only
        STATUS	mandatory
        DESCRIPTION
                "The number of received cells dropped on this VCL because of an
                invalid CRC."
        ::= { wfAtmizerVclStatsEntry 12 }

    wfAtmizerVclRxCrc10Errors OBJECT-TYPE
        SYNTAX	Counter
        ACCESS	read-only
        STATUS	mandatory
        DESCRIPTION
                "The number of OAM cells dropped on this VCL because of an invalid CRC-10."
        ::= { wfAtmizerVclStatsEntry 13 }

    wfAtmizerVclRxLackBufCredits OBJECT-TYPE
        SYNTAX	Counter
        ACCESS	read-only
        STATUS	mandatory
        DESCRIPTION
                "The number of received packets lost on this VCL because no receive
                buffer space was available to the receiver for incoming data."
        ::= { wfAtmizerVclStatsEntry 14 }

    wfAtmizerVclRxLackPageCredits OBJECT-TYPE
        SYNTAX	Counter
        ACCESS	read-only
        STATUS	mandatory
        DESCRIPTION
                "The number of received packets lost on this VCL because no physical
                pages were available to the receiver for incoming data."
        ::= { wfAtmizerVclStatsEntry 15 }

    wfAtmizerVclRxLackBufResc OBJECT-TYPE
        SYNTAX	Counter
        ACCESS	read-only
        STATUS	mandatory
        DESCRIPTION
                "The number of received packets lost on this VCL because there were
                no free system buffers available."
        ::= { wfAtmizerVclStatsEntry 16 }

    wfAtmizerVclRxLackPageResc OBJECT-TYPE
        SYNTAX	Counter
        ACCESS	read-only
        STATUS	mandatory
        DESCRIPTION
                "The number of received packets lost on this VCL because there were
                no free system pages available."
        ::= { wfAtmizerVclStatsEntry 17 }

    wfAtmizerVclTxPacketsOkWrap OBJECT-TYPE
        SYNTAX	Counter
        ACCESS	read-only
        STATUS	mandatory
        DESCRIPTION
                "Number of times the wfAtmizerVclTxPacketsOk has wrapped."
        ::= { wfAtmizerVclStatsEntry 18 }

    wfAtmizerVclTxPacketsOk OBJECT-TYPE
        SYNTAX	Counter
        ACCESS	read-only
        STATUS	mandatory
        DESCRIPTION
                "Number of packets transmitted on this VCL."
        ::= { wfAtmizerVclStatsEntry 19 }

    wfAtmizerVclTxCellsOkWrap OBJECT-TYPE
        SYNTAX	Counter
        ACCESS	read-only
        STATUS	mandatory
        DESCRIPTION
                "Number of times the wfAtmizerVclTxCellsOk has wrapped."
        ::= { wfAtmizerVclStatsEntry 20 }

    wfAtmizerVclTxCellsOk OBJECT-TYPE
        SYNTAX	Counter
        ACCESS	read-only
        STATUS	mandatory
        DESCRIPTION
                "Number of cells transmitted on this VCL."
        ::= { wfAtmizerVclStatsEntry 21 }

    wfAtmizerVclTxOamCount OBJECT-TYPE
        SYNTAX	Counter
        ACCESS	read-only
        STATUS	mandatory
        DESCRIPTION
                "The number of OAM cells transmitted on this VCL."
        ::= { wfAtmizerVclStatsEntry 22 }

    wfAtmizerVclTxFlowCtrlCount OBJECT-TYPE
        SYNTAX	Counter
        ACCESS	read-only
        STATUS	mandatory
        DESCRIPTION
                "The number of Flow Control cells received on this VCL."
        ::= { wfAtmizerVclStatsEntry 23 }

    wfAtmizerVclTxOverSizedSDUs OBJECT-TYPE
        SYNTAX	Counter
        ACCESS	read-only
        STATUS	mandatory
        DESCRIPTION
                "The number of transmit packets dropped on this VCL because their SDU size
                was greater than the MTU for this interface."
        ::= { wfAtmizerVclStatsEntry 24 }

    wfAtmizerVclTxLackBufCredits OBJECT-TYPE
        SYNTAX	Counter
        ACCESS	read-only
        STATUS	mandatory
        DESCRIPTION
                "The number of transmit packets lost on this VCL because no buffer
                space was available to the transmitter for outgoing data."
        ::= { wfAtmizerVclStatsEntry 25 }

    wfAtmizerVclTxLackPageCredits OBJECT-TYPE
        SYNTAX	Counter
        ACCESS	read-only
        STATUS	mandatory
        DESCRIPTION
                "The number of transmit packets lost on this VCL because no physical
                pages were available to the transmitter for outgoing data."
        ::= { wfAtmizerVclStatsEntry 26 }

    wfAtmizerVclRxOctets OBJECT-TYPE
        SYNTAX	Counter
        ACCESS	read-only
        STATUS	mandatory
        DESCRIPTION
                "Count of octets received successfully.

                 Note:
                 May not be supported on all ATM-based platforms."
        ::= { wfAtmizerVclStatsEntry 27 }

    wfAtmizerVclTxOctets OBJECT-TYPE
        SYNTAX	Counter
        ACCESS	read-only
        STATUS	mandatory
        DESCRIPTION
                "Count of octets transmitted successfully.

                 Note:
                 May not be supported on all ATM-based platforms."
        ::= { wfAtmizerVclStatsEntry 28 }

    wfAtmizerVclTxClipFrames OBJECT-TYPE
        SYNTAX	Counter
        ACCESS	read-only
        STATUS	mandatory
        DESCRIPTION
                "Number of frames clipped (dropped) due to transmit congestion.

                 Note:
                 May not be supported on all ATM-based platforms."
        ::= { wfAtmizerVclStatsEntry 29 }

    wfAtmizerVclRxLengthErrors OBJECT-TYPE
        SYNTAX	Counter
        ACCESS	read-only
        STATUS	mandatory
        DESCRIPTION
                "Count of Rx length errors.  AAL5 CPCS-PDU length violation.

                 Note:
                 May not be supported on all ATM-based platforms."
        ::= { wfAtmizerVclStatsEntry 30 }

    wfAtmizerVclRxAbortMessages OBJECT-TYPE
        SYNTAX	Counter
        ACCESS	read-only
        STATUS	mandatory
        DESCRIPTION
                "Count of abort messages received (AAL5 length field equals 0).

                 Note:
                 May not be supported on all ATM-based platforms."
        ::= { wfAtmizerVclStatsEntry 31 }

    wfAtmizerVclRxSequenceNumberErrors OBJECT-TYPE
        SYNTAX	Counter
        ACCESS	read-only
        STATUS	mandatory
        DESCRIPTION
                "Count of AAL1 sequence number errors.

                 Note:
                 May not be supported on all ATM-based platforms."
        ::= { wfAtmizerVclStatsEntry 32 }


    wfAtmizerDebugTable OBJECT-TYPE
        SYNTAX	SEQUENCE OF WfAtmizerDebugEntry
        ACCESS	not-accessible
        STATUS	mandatory
        DESCRIPTION
                "ARE ATMizer Debug Record"
        ::= { wfAtmCellSwitchGroup 5 }

    wfAtmizerDebugEntry OBJECT-TYPE
        SYNTAX	WfAtmizerDebugEntry
        ACCESS	not-accessible
        STATUS	mandatory
        DESCRIPTION
                "Information about a Transmit/Receive pair of ATMizers"
        INDEX	{ wfAtmizerDebugSlot }
        ::= { wfAtmizerDebugTable 1 }

    WfAtmizerDebugEntry ::= SEQUENCE {
    	    wfAtmizerDebugSlot
    		INTEGER,
    	    wfAtmizerDebugCmd
    		INTEGER,
    	    wfAtmizerDebugCmdSize
    		INTEGER,
    	    wfAtmizerDebugParam1
    		INTEGER,
    	    wfAtmizerDebugParam2
    		INTEGER,
    	    wfAtmizerDebugParam3
    		INTEGER,
    	    wfAtmizerDebugParam4
    		INTEGER,
    	    wfAtmizerDebugParam5
    		INTEGER,
    	    wfAtmizerDebugParam6
    		INTEGER,
    	    wfAtmizerDebugParam7
    		INTEGER,
    	    wfAtmizerDebugParam8
    		INTEGER,
    	    wfAtmizerDebugParam9
    		INTEGER,
    	    wfAtmizerDebugParam10
    		INTEGER,
    	    wfAtmizerDebugRxDone
    		INTEGER,
    	    wfAtmizerDebugRxValue
    		OCTET STRING,
    	    wfAtmizerDebugTxDone
    		INTEGER,
    	    wfAtmizerDebugTxValue
    		OCTET STRING
        }

    wfAtmizerDebugSlot OBJECT-TYPE
        SYNTAX	INTEGER(1..14)
        ACCESS	read-only
        STATUS	mandatory
        DESCRIPTION
                "Slot number -- instance id."
        ::= { wfAtmizerDebugEntry 1 }

    wfAtmizerDebugCmd OBJECT-TYPE
        SYNTAX	INTEGER
        ACCESS	read-write
        STATUS	mandatory
        DESCRIPTION
                "Debug command to be issued to ATMizers."
        ::= { wfAtmizerDebugEntry 2 }

    wfAtmizerDebugCmdSize OBJECT-TYPE
        SYNTAX	INTEGER
        ACCESS	read-write
        STATUS	mandatory
        DESCRIPTION
                "Number of parameters to the debug command."
        ::= { wfAtmizerDebugEntry 3 }

    wfAtmizerDebugParam1 OBJECT-TYPE
        SYNTAX	INTEGER
        ACCESS	read-write
        STATUS	mandatory
        DESCRIPTION
                "The first parameter to the ATMizer debug command."
        ::= { wfAtmizerDebugEntry 4 }

    wfAtmizerDebugParam2 OBJECT-TYPE
        SYNTAX	INTEGER
        ACCESS	read-write
        STATUS	mandatory
        DESCRIPTION
                "The second parameter to the ATMizer debug command."
        ::= { wfAtmizerDebugEntry 5 }

    wfAtmizerDebugParam3 OBJECT-TYPE
        SYNTAX	INTEGER
        ACCESS	read-write
        STATUS	mandatory
        DESCRIPTION
                "The third parameter to the ATMizer debug command."
        ::= { wfAtmizerDebugEntry 6 }

    wfAtmizerDebugParam4 OBJECT-TYPE
        SYNTAX	INTEGER
        ACCESS	read-write
        STATUS	mandatory
        DESCRIPTION
                "The fourth parameter to the ATMizer debug command."
        ::= { wfAtmizerDebugEntry 7 }

    wfAtmizerDebugParam5 OBJECT-TYPE
        SYNTAX	INTEGER
        ACCESS	read-write
        STATUS	mandatory
        DESCRIPTION
                "The fifth parameter to the ATMizer debug command."
        ::= { wfAtmizerDebugEntry 8 }

    wfAtmizerDebugParam6 OBJECT-TYPE
        SYNTAX	INTEGER
        ACCESS	read-write
        STATUS	mandatory
        DESCRIPTION
                "The sixth parameter to the ATMizer debug command."
        ::= { wfAtmizerDebugEntry 9 }

    wfAtmizerDebugParam7 OBJECT-TYPE
        SYNTAX	INTEGER
        ACCESS	read-write
        STATUS	mandatory
        DESCRIPTION
                "The seventh parameter to the ATMizer debug command."
        ::= { wfAtmizerDebugEntry 10 }

    wfAtmizerDebugParam8 OBJECT-TYPE
        SYNTAX	INTEGER
        ACCESS	read-write
        STATUS	mandatory
        DESCRIPTION
                "The eighth parameter to the ATMizer debug command."
        ::= { wfAtmizerDebugEntry 11 }

    wfAtmizerDebugParam9 OBJECT-TYPE
        SYNTAX	INTEGER
        ACCESS	read-write
        STATUS	mandatory
        DESCRIPTION
                "The nineth parameter to the ATMizer debug command."
        ::= { wfAtmizerDebugEntry 12 }

    wfAtmizerDebugParam10 OBJECT-TYPE
        SYNTAX	INTEGER
        ACCESS	read-write
        STATUS	mandatory
        DESCRIPTION
                "The tenth parameter to the ATMizer debug command."
        ::= { wfAtmizerDebugEntry 13 }

    wfAtmizerDebugRxDone OBJECT-TYPE
        SYNTAX	INTEGER {
    		    inprog(1),
    		    done(2),
    		    err(16)
    		}
        ACCESS	read-write
        STATUS	mandatory
        DESCRIPTION
                "Completion flag indicating that the RX ATMizer has completed the
                debug command and the result is available in wfAtmizerDebugRxValue."
        DEFVAL	{ inprog }
        ::= { wfAtmizerDebugEntry 14 }

    wfAtmizerDebugRxValue OBJECT-TYPE
        SYNTAX	OCTET STRING
        ACCESS	read-write
        STATUS	mandatory
        DESCRIPTION
                "The result of the RX ATMizer debug operation."
        ::= { wfAtmizerDebugEntry 15 }

    wfAtmizerDebugTxDone OBJECT-TYPE
        SYNTAX	INTEGER {
    		    inprog(1),
    		    done(2),
    		    err(16)
    		}
        ACCESS	read-write
        STATUS	mandatory
        DESCRIPTION
                "Completion flag indicating that the TX ATMizer has completed the
                debug command and the result is available in wfAtmizerDebugTxValue."
        DEFVAL	{ inprog }
        ::= { wfAtmizerDebugEntry 16 }

    wfAtmizerDebugTxValue OBJECT-TYPE
        SYNTAX	OCTET STRING
        ACCESS	read-write
        STATUS	mandatory
        DESCRIPTION
                "The result of the TX ATMizer debug operation."
        ::= { wfAtmizerDebugEntry 17 }

    wfSonetMediumTable OBJECT-TYPE
        SYNTAX	SEQUENCE OF WfSonetMediumEntry
        ACCESS	not-accessible
        STATUS	mandatory
        DESCRIPTION
                "Statistics for the SONET medium table"
        ::= { wfSonetGroup 1 }

    wfSonetMediumEntry OBJECT-TYPE
        SYNTAX	WfSonetMediumEntry
        ACCESS	not-accessible
        STATUS	mandatory
        DESCRIPTION
                "An entry in the medium table"
        INDEX	{ wfSonetMediumIndex }
        ::= { wfSonetMediumTable 1 }

    WfSonetMediumEntry ::= SEQUENCE {
    	    wfSonetMediumIndex
    		INTEGER,
    	    wfSonetMediumType
    		INTEGER,
    	    wfSonetMediumTimeElapsed
    		INTEGER,
    	    wfSonetMediumValidIntervals
    		INTEGER,
    	    wfSonetMediumLineCoding
    		INTEGER,
    	    wfSonetMediumLineType
    		INTEGER,
    	    wfSonetMediumCircuitIdentifier
    		DisplayString
        }

    wfSonetMediumIndex OBJECT-TYPE
        SYNTAX	INTEGER
        ACCESS	read-only
        STATUS	mandatory
        DESCRIPTION
                "Index for this physical Sonet interface."
        ::= { wfSonetMediumEntry 1 }

    wfSonetMediumType OBJECT-TYPE
        SYNTAX	INTEGER
        ACCESS	read-only
        STATUS	mandatory
        DESCRIPTION
                "This variable identifies whether a SONET or a SDH signal is used
                across this interface."
        ::= { wfSonetMediumEntry 2 }

    wfSonetMediumTimeElapsed OBJECT-TYPE
        SYNTAX	INTEGER
        ACCESS	read-only
        STATUS	mandatory
        DESCRIPTION
                "The number of seconds that have elapsed since the beginning of
                the current error-measurement period."
        ::= { wfSonetMediumEntry 3 }

    wfSonetMediumValidIntervals OBJECT-TYPE
        SYNTAX	INTEGER
        ACCESS	read-only
        STATUS	mandatory
        DESCRIPTION
                "The number of previous intervals for which valid data has been stored."
        ::= { wfSonetMediumEntry 4 }

    wfSonetMediumLineCoding OBJECT-TYPE
        SYNTAX	INTEGER {
    		    other(1),
    		    b3zs(2),
    		    cmi(3),
    		    nrz(4),
    		    rz(5)
    		}
        ACCESS	read-only
        STATUS	mandatory
        DESCRIPTION
                "This variable describes the line coding for this interface."
        DEFVAL	{ nrz }
        ::= { wfSonetMediumEntry 5 }

    wfSonetMediumLineType OBJECT-TYPE
        SYNTAX	INTEGER {
    		    other(1),
    		    shortsinglemode(2),
    		    longsinglemode(3),
    		    multimode(4),
    		    coax(5),
    		    utp(6)
    		}
        ACCESS	read-only
        STATUS	mandatory
        DESCRIPTION
                "This variable describes the line type for this interface."
        DEFVAL	{ shortsinglemode }
        ::= { wfSonetMediumEntry 6 }

    wfSonetMediumCircuitIdentifier OBJECT-TYPE
        SYNTAX	DisplayString
        ACCESS	read-only
        STATUS	mandatory
        DESCRIPTION
                "This variable contains the transmission vendor's circuit identifier."
        ::= { wfSonetMediumEntry 7 }

    wfSonetSectionCurrentTable OBJECT-TYPE
        SYNTAX	SEQUENCE OF WfSonetSectionCurrentEntry
        ACCESS	not-accessible
        STATUS	mandatory
        DESCRIPTION
                "Statistics for the SONET section current table"
        ::= { wfSonetGroup 2 }

    wfSonetSectionCurrentEntry OBJECT-TYPE
        SYNTAX	WfSonetSectionCurrentEntry
        ACCESS	not-accessible
        STATUS	mandatory
        DESCRIPTION
                "An entry in the Section current table"
        INDEX	{ wfSonetSectionCurrentIndex }
        ::= { wfSonetSectionCurrentTable 1 }

    WfSonetSectionCurrentEntry ::= SEQUENCE {
    	    wfSonetSectionCurrentIndex
    		INTEGER,
    	    wfSonetSectionCurrentStatus
    		INTEGER,
    	    wfSonetSectionCurrentESs
    		Gauge,
    	    wfSonetSectionCurrentSESs
    		Gauge,
    	    wfSonetSectionCurrentSEFSs
    		Gauge,
    	    wfSonetSectionCurrentCVs
    		Gauge
        }

    wfSonetSectionCurrentIndex OBJECT-TYPE
        SYNTAX	INTEGER
        ACCESS	read-only
        STATUS	mandatory
        DESCRIPTION
                "Index for this physical Sonet interface."
        ::= { wfSonetSectionCurrentEntry 1 }

    wfSonetSectionCurrentStatus OBJECT-TYPE
        SYNTAX	INTEGER {
    		    nodefect(1),
    		    los(2),
    		    lof(4)
    		}
        ACCESS	read-only
        STATUS	mandatory
        DESCRIPTION
                "This variable is a bitmask indicating the status of the interface."
        DEFVAL	{ nodefect }
        ::= { wfSonetSectionCurrentEntry 2 }

    wfSonetSectionCurrentESs OBJECT-TYPE
        SYNTAX	Gauge
        ACCESS	read-only
        STATUS	mandatory
        DESCRIPTION
                "The counter associated with the number of Errored Seconds encountered
                by a SONET/SDH Section in the current 15 minute interval."
        ::= { wfSonetSectionCurrentEntry 3 }

    wfSonetSectionCurrentSESs OBJECT-TYPE
        SYNTAX	Gauge
        ACCESS	read-only
        STATUS	mandatory
        DESCRIPTION
                "The counter associated with the number of Severely Errored Seconds
                encountered by a SONET/SDH Section in the current 15 minute interval."
        ::= { wfSonetSectionCurrentEntry 4 }

    wfSonetSectionCurrentSEFSs OBJECT-TYPE
        SYNTAX	Gauge
        ACCESS	read-only
        STATUS	mandatory
        DESCRIPTION
                "The counter associated with the number of Severely Errored Framing Seconds
                encountered by a SONET/SDH Section in the current 15 minute interval."
        ::= { wfSonetSectionCurrentEntry 5 }

    wfSonetSectionCurrentCVs OBJECT-TYPE
        SYNTAX	Gauge
        ACCESS	read-only
        STATUS	mandatory
        DESCRIPTION
                "The counter associated with the number of Coding Violations encountered
                by a SONET/SDH Section in the current 15 minute interval."
        ::= { wfSonetSectionCurrentEntry 6 }

    wfSonetSectionIntervalTable OBJECT-TYPE
        SYNTAX	SEQUENCE OF WfSonetSectionIntervalEntry
        ACCESS	not-accessible
        STATUS	mandatory
        DESCRIPTION
                "Statistics for the SONET section interval table"
        ::= { wfSonetGroup 3 }

    wfSonetSectionIntervalEntry OBJECT-TYPE
        SYNTAX	WfSonetSectionIntervalEntry
        ACCESS	not-accessible
        STATUS	mandatory
        DESCRIPTION
                "An entry in the Section Interval table"
        INDEX	{ wfSonetSectionIntervalIndex,
    		  wfSonetSectionIntervalNumber }
        ::= { wfSonetSectionIntervalTable 1 }

    WfSonetSectionIntervalEntry ::= SEQUENCE {
    	    wfSonetSectionIntervalIndex
    		INTEGER,
    	    wfSonetSectionIntervalNumber
    		INTEGER,
    	    wfSonetSectionIntervalESs
    		Gauge,
    	    wfSonetSectionIntervalSESs
    		Gauge,
    	    wfSonetSectionIntervalSEFSs
    		Gauge,
    	    wfSonetSectionIntervalCVs
    		Gauge
        }

    wfSonetSectionIntervalIndex OBJECT-TYPE
        SYNTAX	INTEGER
        ACCESS	read-only
        STATUS	mandatory
        DESCRIPTION
                "Index for this physical Sonet interface."
        ::= { wfSonetSectionIntervalEntry 1 }

    wfSonetSectionIntervalNumber OBJECT-TYPE
        SYNTAX	INTEGER
        ACCESS	read-only
        STATUS	mandatory
        DESCRIPTION
                "A number between 1 and 96, which identifies the interval for which the
                set of statistics is available.  The interval identified by 1 is the
                most recently completed 15 minute interval, and the interval identified
                by N is the interval immediately preceding the one identified by N-1."
        ::= { wfSonetSectionIntervalEntry 2 }

    wfSonetSectionIntervalESs OBJECT-TYPE
        SYNTAX	Gauge
        ACCESS	read-only
        STATUS	mandatory
        DESCRIPTION
                "The counter associated with the number of Errored Seconds encountered
                by a SONET/SDH Section in a particular 15 minute interval."
        ::= { wfSonetSectionIntervalEntry 3 }

    wfSonetSectionIntervalSESs OBJECT-TYPE
        SYNTAX	Gauge
        ACCESS	read-only
        STATUS	mandatory
        DESCRIPTION
                "The counter associated with the number of Severely Errored Seconds
                encountered by a SONET/SDH Section in a particular 15 minute interval."
        ::= { wfSonetSectionIntervalEntry 4 }

    wfSonetSectionIntervalSEFSs OBJECT-TYPE
        SYNTAX	Gauge
        ACCESS	read-only
        STATUS	mandatory
        DESCRIPTION
                "The counter associated with the number of Severely Errored Framing Seconds
                encountered by a SONET/SDH Section in a particular 15 minute interval."
        ::= { wfSonetSectionIntervalEntry 5 }

    wfSonetSectionIntervalCVs OBJECT-TYPE
        SYNTAX	Gauge
        ACCESS	read-only
        STATUS	mandatory
        DESCRIPTION
                "The counter associated with the number of Coding Violations encountered
                by a SONET/SDH Section in a particular 15 minute interval."
        ::= { wfSonetSectionIntervalEntry 6 }

    wfSonetLineCurrentTable OBJECT-TYPE
        SYNTAX	SEQUENCE OF WfSonetLineCurrentEntry
        ACCESS	not-accessible
        STATUS	mandatory
        DESCRIPTION
                "Statistics for the SONET line current table"
        ::= { wfSonetGroup 4 }

    wfSonetLineCurrentEntry OBJECT-TYPE
        SYNTAX	WfSonetLineCurrentEntry
        ACCESS	not-accessible
        STATUS	mandatory
        DESCRIPTION
                "An entry in the Line current table"
        INDEX	{ wfSonetLineCurrentIndex }
        ::= { wfSonetLineCurrentTable 1 }

    WfSonetLineCurrentEntry ::= SEQUENCE {
    	    wfSonetLineCurrentIndex
    		INTEGER,
    	    wfSonetLineCurrentStatus
    		INTEGER,
    	    wfSonetLineCurrentESs
    		Gauge,
    	    wfSonetLineCurrentSESs
    		Gauge,
    	    wfSonetLineCurrentCVs
    		Gauge,
    	    wfSonetLineCurrentUASs
    		Gauge
        }

    wfSonetLineCurrentIndex OBJECT-TYPE
        SYNTAX	INTEGER
        ACCESS	read-only
        STATUS	mandatory
        DESCRIPTION
                "Index for this physical Sonet interface."
        ::= { wfSonetLineCurrentEntry 1 }

    wfSonetLineCurrentStatus OBJECT-TYPE
        SYNTAX	INTEGER {
    		    nodefect(1),
    		    ais(2),
    		    rdi(4)
    		}
        ACCESS	read-only
        STATUS	mandatory
        DESCRIPTION
                "This variable is a bitmask indicating the status of the interface."
        DEFVAL	{ nodefect }
        ::= { wfSonetLineCurrentEntry 2 }

    wfSonetLineCurrentESs OBJECT-TYPE
        SYNTAX	Gauge
        ACCESS	read-only
        STATUS	mandatory
        DESCRIPTION
                "The counter associated with the number of Errored Seconds encountered
                by a SONET/SDH Line in the current 15 minute interval."
        ::= { wfSonetLineCurrentEntry 3 }

    wfSonetLineCurrentSESs OBJECT-TYPE
        SYNTAX	Gauge
        ACCESS	read-only
        STATUS	mandatory
        DESCRIPTION
                "The counter associated with the number of Severely Errored Seconds
                encountered by a SONET/SDH Line in the current 15 minute interval."
        ::= { wfSonetLineCurrentEntry 4 }

    wfSonetLineCurrentCVs OBJECT-TYPE
        SYNTAX	Gauge
        ACCESS	read-only
        STATUS	mandatory
        DESCRIPTION
                "The counter associated with the number of Coding Violations encountered
                by a SONET/SDH Line in the current 15 minute interval."
        ::= { wfSonetLineCurrentEntry 5 }

    wfSonetLineCurrentUASs OBJECT-TYPE
        SYNTAX	Gauge
        ACCESS	read-only
        STATUS	mandatory
        DESCRIPTION
                "The counter associated with the number of Unavailable Seconds encountered
                by a SONET/SDH Line in the current 15 minute interval."
        ::= { wfSonetLineCurrentEntry 6 }

    wfSonetLineIntervalTable OBJECT-TYPE
        SYNTAX	SEQUENCE OF WfSonetLineIntervalEntry
        ACCESS	not-accessible
        STATUS	mandatory
        DESCRIPTION
                "Statistics for the SONET line interval table"
        ::= { wfSonetGroup 5 }

    wfSonetLineIntervalEntry OBJECT-TYPE
        SYNTAX	WfSonetLineIntervalEntry
        ACCESS	not-accessible
        STATUS	mandatory
        DESCRIPTION
                "An entry in the Line Interval table"
        INDEX	{ wfSonetLineIntervalIndex,
    		  wfSonetLineIntervalNumber }
        ::= { wfSonetLineIntervalTable 1 }

    WfSonetLineIntervalEntry ::= SEQUENCE {
    	    wfSonetLineIntervalIndex
    		INTEGER,
    	    wfSonetLineIntervalNumber
    		INTEGER,
    	    wfSonetLineIntervalESs
    		Gauge,
    	    wfSonetLineIntervalSESs
    		Gauge,
    	    wfSonetLineIntervalCVs
    		Gauge,
    	    wfSonetLineIntervalUASs
    		Gauge
        }

    wfSonetLineIntervalIndex OBJECT-TYPE
        SYNTAX	INTEGER
        ACCESS	read-only
        STATUS	mandatory
        DESCRIPTION
                "Index for this physical Sonet interface."
        ::= { wfSonetLineIntervalEntry 1 }

    wfSonetLineIntervalNumber OBJECT-TYPE
        SYNTAX	INTEGER
        ACCESS	read-only
        STATUS	mandatory
        DESCRIPTION
                "A number between 1 and 96, which identifies the interval for which the
                set of statistics is available.  The interval identified by 1 is the
                most recently completed 15 minute interval, and the interval identified
                by N is the interval immediately preceding the one identified by N-1."
        ::= { wfSonetLineIntervalEntry 2 }

    wfSonetLineIntervalESs OBJECT-TYPE
        SYNTAX	Gauge
        ACCESS	read-only
        STATUS	mandatory
        DESCRIPTION
                "The counter associated with the number of Errored Seconds encountered
                by a SONET/SDH Line in a particular 15 minute interval."
        ::= { wfSonetLineIntervalEntry 3 }

    wfSonetLineIntervalSESs OBJECT-TYPE
        SYNTAX	Gauge
        ACCESS	read-only
        STATUS	mandatory
        DESCRIPTION
                "The counter associated with the number of Severely Errored Seconds
                encountered by a SONET/SDH Line in a particular 15 minute interval."
        ::= { wfSonetLineIntervalEntry 4 }

    wfSonetLineIntervalCVs OBJECT-TYPE
        SYNTAX	Gauge
        ACCESS	read-only
        STATUS	mandatory
        DESCRIPTION
                "The counter associated with the number of Coding Violations encountered
                by a SONET/SDH Line in a particular 15 minute interval."
        ::= { wfSonetLineIntervalEntry 5 }

    wfSonetLineIntervalUASs OBJECT-TYPE
        SYNTAX	Gauge
        ACCESS	read-only
        STATUS	mandatory
        DESCRIPTION
                "The counter associated with the number of Unavailable Seconds encountered
                by a SONET/SDH Line in a particular 15 minute interval."
        ::= { wfSonetLineIntervalEntry 6 }

    wfSonetFarEndLineCurrentTable OBJECT-TYPE
        SYNTAX	SEQUENCE OF WfSonetFarEndLineCurrentEntry
        ACCESS	not-accessible
        STATUS	mandatory
        DESCRIPTION
                "Statistics for the SONET far end line current table"
        ::= { wfSonetGroup 6 }

    wfSonetFarEndLineCurrentEntry OBJECT-TYPE
        SYNTAX	WfSonetFarEndLineCurrentEntry
        ACCESS	not-accessible
        STATUS	mandatory
        DESCRIPTION
                "An entry in the FarEndLine current table"
        INDEX	{ wfSonetFarEndLineCurrentIndex }
        ::= { wfSonetFarEndLineCurrentTable 1 }

    WfSonetFarEndLineCurrentEntry ::= SEQUENCE {
    	    wfSonetFarEndLineCurrentIndex
    		INTEGER,
    	    wfSonetFarEndLineCurrentESs
    		Gauge,
    	    wfSonetFarEndLineCurrentSESs
    		Gauge,
    	    wfSonetFarEndLineCurrentCVs
    		Gauge,
    	    wfSonetFarEndLineCurrentUASs
    		Gauge
        }

    wfSonetFarEndLineCurrentIndex OBJECT-TYPE
        SYNTAX	INTEGER
        ACCESS	read-only
        STATUS	mandatory
        DESCRIPTION
                "Index for this physical Sonet interface."
        ::= { wfSonetFarEndLineCurrentEntry 1 }

    wfSonetFarEndLineCurrentESs OBJECT-TYPE
        SYNTAX	Gauge
        ACCESS	read-only
        STATUS	mandatory
        DESCRIPTION
                "The counter associated with the number of Far End Errored Seconds
                encountered by a SONET/SDH Medium/Section/Line in the current 15 minute
                interval."
        ::= { wfSonetFarEndLineCurrentEntry 2 }

    wfSonetFarEndLineCurrentSESs OBJECT-TYPE
        SYNTAX	Gauge
        ACCESS	read-only
        STATUS	mandatory
        DESCRIPTION
                "The counter associated with the number of Far End Severely Errored Seconds
                encountered by a SONET/SDH Medium/Section/Line in the current 15 minute
                interval."
        ::= { wfSonetFarEndLineCurrentEntry 3 }

    wfSonetFarEndLineCurrentCVs OBJECT-TYPE
        SYNTAX	Gauge
        ACCESS	read-only
        STATUS	mandatory
        DESCRIPTION
                "The counter associated with the number of Far End Coding Violations
                encountered by a SONET/SDH Medium/Section/Line in the current 15 minute
                interval."
        ::= { wfSonetFarEndLineCurrentEntry 4 }

    wfSonetFarEndLineCurrentUASs OBJECT-TYPE
        SYNTAX	Gauge
        ACCESS	read-only
        STATUS	mandatory
        DESCRIPTION
                "The counter associated with the number of Far End Unavailable Seconds
                encountered by a SONET/SDH Medium/Section/Line in the current 15 minute
                interval."
        ::= { wfSonetFarEndLineCurrentEntry 5 }

    wfSonetFarEndLineIntervalTable OBJECT-TYPE
        SYNTAX	SEQUENCE OF WfSonetFarEndLineIntervalEntry
        ACCESS	not-accessible
        STATUS	mandatory
        DESCRIPTION
                "Statistics for the SONET far end line interval table"
        ::= { wfSonetGroup 7 }

    wfSonetFarEndLineIntervalEntry OBJECT-TYPE
        SYNTAX	WfSonetFarEndLineIntervalEntry
        ACCESS	not-accessible
        STATUS	mandatory
        DESCRIPTION
                "An entry in the FarEndLine Interval table"
        INDEX	{ wfSonetFarEndLineIntervalIndex,
    		  wfSonetFarEndLineIntervalNumber }
        ::= { wfSonetFarEndLineIntervalTable 1 }

    WfSonetFarEndLineIntervalEntry ::= SEQUENCE {
    	    wfSonetFarEndLineIntervalIndex
    		INTEGER,
    	    wfSonetFarEndLineIntervalNumber
    		INTEGER,
    	    wfSonetFarEndLineIntervalESs
    		Gauge,
    	    wfSonetFarEndLineIntervalSESs
    		Gauge,
    	    wfSonetFarEndLineIntervalCVs
    		Gauge,
    	    wfSonetFarEndLineIntervalUASs
    		Gauge
        }

    wfSonetFarEndLineIntervalIndex OBJECT-TYPE
        SYNTAX	INTEGER
        ACCESS	read-only
        STATUS	mandatory
        DESCRIPTION
                "Index for this physical Sonet interface."
        ::= { wfSonetFarEndLineIntervalEntry 1 }

    wfSonetFarEndLineIntervalNumber OBJECT-TYPE
        SYNTAX	INTEGER
        ACCESS	read-only
        STATUS	mandatory
        DESCRIPTION
                "A number between 1 and 96, which identifies the interval for which the
                set of statistics is available.  The interval identified by 1 is the
                most recently completed 15 minute interval, and the interval identified
                by N is the interval immediately preceding the one identified by N-1."
        ::= { wfSonetFarEndLineIntervalEntry 2 }

    wfSonetFarEndLineIntervalESs OBJECT-TYPE
        SYNTAX	Gauge
        ACCESS	read-only
        STATUS	mandatory
        DESCRIPTION
                "The counter associated with the number of Far End Errored Seconds
                encountered by a SONET/SDH Medium/Section/Line in the current 15 minute
                interval."
        ::= { wfSonetFarEndLineIntervalEntry 3 }

    wfSonetFarEndLineIntervalSESs OBJECT-TYPE
        SYNTAX	Gauge
        ACCESS	read-only
        STATUS	mandatory
        DESCRIPTION
                "The counter associated with the number of Far End Severely Errored Seconds
                encountered by a SONET/SDH Medium/Section/Line in the current 15 minute
                interval."
        ::= { wfSonetFarEndLineIntervalEntry 4 }

    wfSonetFarEndLineIntervalCVs OBJECT-TYPE
        SYNTAX	Gauge
        ACCESS	read-only
        STATUS	mandatory
        DESCRIPTION
                "The counter associated with the number of Far End Coding Violations
                encountered by a SONET/SDH Medium/Section/Line in the current 15 minute
                interval."
        ::= { wfSonetFarEndLineIntervalEntry 5 }

    wfSonetFarEndLineIntervalUASs OBJECT-TYPE
        SYNTAX	Gauge
        ACCESS	read-only
        STATUS	mandatory
        DESCRIPTION
                "The counter associated with the number of Far End Unavailable Seconds
                encountered by a SONET/SDH Medium/Section/Line in the current 15 minute
                interval."
        ::= { wfSonetFarEndLineIntervalEntry 6 }

    wfSonetPathCurrentTable OBJECT-TYPE
        SYNTAX	SEQUENCE OF WfSonetPathCurrentEntry
        ACCESS	not-accessible
        STATUS	mandatory
        DESCRIPTION
                "Statistics for the SONET path current table"
        ::= { wfSonetGroup 8 }

    wfSonetPathCurrentEntry OBJECT-TYPE
        SYNTAX	WfSonetPathCurrentEntry
        ACCESS	not-accessible
        STATUS	mandatory
        DESCRIPTION
                "An entry in the Path current table"
        INDEX	{ wfSonetPathCurrentIndex }
        ::= { wfSonetPathCurrentTable 1 }

    WfSonetPathCurrentEntry ::= SEQUENCE {
    	    wfSonetPathCurrentIndex
    		INTEGER,
    	    wfSonetPathCurrentWidth
    		INTEGER,
    	    wfSonetPathCurrentStatus
    		INTEGER,
    	    wfSonetPathCurrentESs
    		Gauge,
    	    wfSonetPathCurrentSESs
    		Gauge,
    	    wfSonetPathCurrentCVs
    		Gauge,
    	    wfSonetPathCurrentUASs
    		Gauge
        }

    wfSonetPathCurrentIndex OBJECT-TYPE
        SYNTAX	INTEGER
        ACCESS	read-only
        STATUS	mandatory
        DESCRIPTION
                "Index for this physical Sonet interface."
        ::= { wfSonetPathCurrentEntry 1 }

    wfSonetPathCurrentWidth OBJECT-TYPE
        SYNTAX	INTEGER {
    		    sts1(1),
    		    sts3cstm1(2),
    		    sts12cstm4(3),
    		    sts24c(4),
    		    sts48cstm16(5)
    		}
        ACCESS	read-only
        STATUS	mandatory
        DESCRIPTION
                "A value that indicates the type of the SONET/SDH Path."
        DEFVAL	{ sts3cstm1 }
        ::= { wfSonetPathCurrentEntry 2 }

    wfSonetPathCurrentStatus OBJECT-TYPE
        SYNTAX	INTEGER {
    		    nodefect(1),
    		    stslop(2),
    		    stsais(4),
    		    stsrdi(8),
    		    unequipped(16),
    		    siglabelmis(32)
    		}
        ACCESS	read-only
        STATUS	mandatory
        DESCRIPTION
                "This variable is a bitmask indicating the status of the interface."
        DEFVAL	{ nodefect }
        ::= { wfSonetPathCurrentEntry 3 }

    wfSonetPathCurrentESs OBJECT-TYPE
        SYNTAX	Gauge
        ACCESS	read-only
        STATUS	mandatory
        DESCRIPTION
                "The counter associated with the number of Errored Seconds encountered
                by a SONET/SDH Path in the current 15 minute interval."
        ::= { wfSonetPathCurrentEntry 4 }

    wfSonetPathCurrentSESs OBJECT-TYPE
        SYNTAX	Gauge
        ACCESS	read-only
        STATUS	mandatory
        DESCRIPTION
                "The counter associated with the number of Severely Errored Seconds
                encountered by a SONET/SDH Path in the current 15 minute interval."
        ::= { wfSonetPathCurrentEntry 5 }

    wfSonetPathCurrentCVs OBJECT-TYPE
        SYNTAX	Gauge
        ACCESS	read-only
        STATUS	mandatory
        DESCRIPTION
                "The counter associated with the number of Coding Violations encountered
                by a SONET/SDH Path in the current 15 minute interval."
        ::= { wfSonetPathCurrentEntry 6 }

    wfSonetPathCurrentUASs OBJECT-TYPE
        SYNTAX	Gauge
        ACCESS	read-only
        STATUS	mandatory
        DESCRIPTION
                "The counter associated with the number of Unavailable Seconds encountered
                by a SONET/SDH Path in the current 15 minute interval."
        ::= { wfSonetPathCurrentEntry 7 }

    wfSonetPathIntervalTable OBJECT-TYPE
        SYNTAX	SEQUENCE OF WfSonetPathIntervalEntry
        ACCESS	not-accessible
        STATUS	mandatory
        DESCRIPTION
                "Statistics for the SONET path interval table"
        ::= { wfSonetGroup 9 }

    wfSonetPathIntervalEntry OBJECT-TYPE
        SYNTAX	WfSonetPathIntervalEntry
        ACCESS	not-accessible
        STATUS	mandatory
        DESCRIPTION
                "An entry in the Path Interval table"
        INDEX	{ wfSonetPathIntervalIndex,
    		  wfSonetPathIntervalNumber }
        ::= { wfSonetPathIntervalTable 1 }

    WfSonetPathIntervalEntry ::= SEQUENCE {
    	    wfSonetPathIntervalIndex
    		INTEGER,
    	    wfSonetPathIntervalNumber
    		INTEGER,
    	    wfSonetPathIntervalESs
    		Gauge,
    	    wfSonetPathIntervalSESs
    		Gauge,
    	    wfSonetPathIntervalCVs
    		Gauge,
    	    wfSonetPathIntervalUASs
    		Gauge
        }

    wfSonetPathIntervalIndex OBJECT-TYPE
        SYNTAX	INTEGER
        ACCESS	read-only
        STATUS	mandatory
        DESCRIPTION
                "Index for this physical Sonet interface."
        ::= { wfSonetPathIntervalEntry 1 }

    wfSonetPathIntervalNumber OBJECT-TYPE
        SYNTAX	INTEGER
        ACCESS	read-only
        STATUS	mandatory
        DESCRIPTION
                "A number between 1 and 96, which identifies the interval for which the
                set of statistics is available.  The interval identified by 1 is the
                most recently completed 15 minute interval, and the interval identified
                by N is the interval immediately preceding the one identified by N-1."
        ::= { wfSonetPathIntervalEntry 2 }

    wfSonetPathIntervalESs OBJECT-TYPE
        SYNTAX	Gauge
        ACCESS	read-only
        STATUS	mandatory
        DESCRIPTION
                "The counter associated with the number of Errored Seconds encountered
                by a SONET/SDH Path in a particular 15 minute interval."
        ::= { wfSonetPathIntervalEntry 3 }

    wfSonetPathIntervalSESs OBJECT-TYPE
        SYNTAX	Gauge
        ACCESS	read-only
        STATUS	mandatory
        DESCRIPTION
                "The counter associated with the number of Severely Errored Seconds
                encountered by a SONET/SDH Path in a particular 15 minute interval."
        ::= { wfSonetPathIntervalEntry 4 }

    wfSonetPathIntervalCVs OBJECT-TYPE
        SYNTAX	Gauge
        ACCESS	read-only
        STATUS	mandatory
        DESCRIPTION
                "The counter associated with the number of Coding Violations encountered
                by a SONET/SDH Path in a particular 15 minute interval."
        ::= { wfSonetPathIntervalEntry 5 }

    wfSonetPathIntervalUASs OBJECT-TYPE
        SYNTAX	Gauge
        ACCESS	read-only
        STATUS	mandatory
        DESCRIPTION
                "The counter associated with the number of Unavailable Seconds encountered
                by a SONET/SDH Path in a particular 15 minute interval."
        ::= { wfSonetPathIntervalEntry 6 }

    wfSonetFarEndPathCurrentTable OBJECT-TYPE
        SYNTAX	SEQUENCE OF WfSonetFarEndPathCurrentEntry
        ACCESS	not-accessible
        STATUS	mandatory
        DESCRIPTION
                "Statistics for the SONET far end path current table"
        ::= { wfSonetGroup 10 }

    wfSonetFarEndPathCurrentEntry OBJECT-TYPE
        SYNTAX	WfSonetFarEndPathCurrentEntry
        ACCESS	not-accessible
        STATUS	mandatory
        DESCRIPTION
                "An entry in the Far End Path current table"
        INDEX	{ wfSonetFarEndPathCurrentIndex }
        ::= { wfSonetFarEndPathCurrentTable 1 }

    WfSonetFarEndPathCurrentEntry ::= SEQUENCE {
    	    wfSonetFarEndPathCurrentIndex
    		INTEGER,
    	    wfSonetFarEndPathCurrentESs
    		Gauge,
    	    wfSonetFarEndPathCurrentSESs
    		Gauge,
    	    wfSonetFarEndPathCurrentCVs
    		Gauge,
    	    wfSonetFarEndPathCurrentUASs
    		Gauge
        }

    wfSonetFarEndPathCurrentIndex OBJECT-TYPE
        SYNTAX	INTEGER
        ACCESS	read-only
        STATUS	mandatory
        DESCRIPTION
                "Index for this physical Sonet interface."
        ::= { wfSonetFarEndPathCurrentEntry 1 }

    wfSonetFarEndPathCurrentESs OBJECT-TYPE
        SYNTAX	Gauge
        ACCESS	read-only
        STATUS	mandatory
        DESCRIPTION
                "The counter associated with the number of Far End Errored Seconds
                encountered by a SONET/SDH Path in the current 15 minute interval."
        ::= { wfSonetFarEndPathCurrentEntry 2 }

    wfSonetFarEndPathCurrentSESs OBJECT-TYPE
        SYNTAX	Gauge
        ACCESS	read-only
        STATUS	mandatory
        DESCRIPTION
                "The counter associated with the number of Far End Severely Errored Seconds
                encountered by a SONET/SDH Path in the current 15 minute interval."
        ::= { wfSonetFarEndPathCurrentEntry 3 }

    wfSonetFarEndPathCurrentCVs OBJECT-TYPE
        SYNTAX	Gauge
        ACCESS	read-only
        STATUS	mandatory
        DESCRIPTION
                "The counter associated with the number of Far End Coding Violations
                encountered by a SONET/SDH Path in the current 15 minute interval."
        ::= { wfSonetFarEndPathCurrentEntry 4 }

    wfSonetFarEndPathCurrentUASs OBJECT-TYPE
        SYNTAX	Gauge
        ACCESS	read-only
        STATUS	mandatory
        DESCRIPTION
                "The counter associated with the number of Far End Unavailable Seconds
                encountered by a SONET/SDH Path in the current 15 minute interval."
        ::= { wfSonetFarEndPathCurrentEntry 5 }

    wfSonetFarEndPathIntervalTable OBJECT-TYPE
        SYNTAX	SEQUENCE OF WfSonetFarEndPathIntervalEntry
        ACCESS	not-accessible
        STATUS	mandatory
        DESCRIPTION
                "Statistics for the SONET far end path interval table"
        ::= { wfSonetGroup 11 }

    wfSonetFarEndPathIntervalEntry OBJECT-TYPE
        SYNTAX	WfSonetFarEndPathIntervalEntry
        ACCESS	not-accessible
        STATUS	mandatory
        DESCRIPTION
                "An entry in the Far End Path Interval table"
        INDEX	{ wfSonetFarEndPathIntervalIndex,
    		  wfSonetFarEndPathIntervalNumber }
        ::= { wfSonetFarEndPathIntervalTable 1 }

    WfSonetFarEndPathIntervalEntry ::= SEQUENCE {
    	    wfSonetFarEndPathIntervalIndex
    		INTEGER,
    	    wfSonetFarEndPathIntervalNumber
    		INTEGER,
    	    wfSonetFarEndPathIntervalESs
    		Gauge,
    	    wfSonetFarEndPathIntervalSESs
    		Gauge,
    	    wfSonetFarEndPathIntervalCVs
    		Gauge,
    	    wfSonetFarEndPathIntervalUASs
    		Gauge
        }

    wfSonetFarEndPathIntervalIndex OBJECT-TYPE
        SYNTAX	INTEGER
        ACCESS	read-only
        STATUS	mandatory
        DESCRIPTION
                "Index for this physical Sonet interface."
        ::= { wfSonetFarEndPathIntervalEntry 1 }

    wfSonetFarEndPathIntervalNumber OBJECT-TYPE
        SYNTAX	INTEGER
        ACCESS	read-only
        STATUS	mandatory
        DESCRIPTION
                "A number between 1 and 96, which identifies the interval for which the
                set of statistics is available.  The interval identified by 1 is the
                most recently completed 15 minute interval, and the interval identified
                by N is the interval immediately preceding the one identified by N-1."
        ::= { wfSonetFarEndPathIntervalEntry 2 }

    wfSonetFarEndPathIntervalESs OBJECT-TYPE
        SYNTAX	Gauge
        ACCESS	read-only
        STATUS	mandatory
        DESCRIPTION
                "The counter associated with the number of Far End Errored Seconds
                encountered by a SONET/SDH Path in a particular 15 minute interval."
        ::= { wfSonetFarEndPathIntervalEntry 3 }

    wfSonetFarEndPathIntervalSESs OBJECT-TYPE
        SYNTAX	Gauge
        ACCESS	read-only
        STATUS	mandatory
        DESCRIPTION
                "The counter associated with the number of Far End Severely Errored Seconds
                encountered by a SONET/SDH Path in a particular 15 minute interval."
        ::= { wfSonetFarEndPathIntervalEntry 4 }

    wfSonetFarEndPathIntervalCVs OBJECT-TYPE
        SYNTAX	Gauge
        ACCESS	read-only
        STATUS	mandatory
        DESCRIPTION
                "The counter associated with the number of Far End Coding Violations
                encountered by a SONET/SDH Path in a particular 15 minute interval."
        ::= { wfSonetFarEndPathIntervalEntry 5 }

    wfSonetFarEndPathIntervalUASs OBJECT-TYPE
        SYNTAX	Gauge
        ACCESS	read-only
        STATUS	mandatory
        DESCRIPTION
                "The counter associated with the number of Far End Unavailable Seconds
                encountered by a SONET/SDH Path in a particular 15 minute interval."
        ::= { wfSonetFarEndPathIntervalEntry 6 }


    wfAtmVcGroupTable OBJECT-TYPE
        SYNTAX	SEQUENCE OF WfAtmVcGroupEntry
        ACCESS	not-accessible
        STATUS	mandatory
        DESCRIPTION
                "This table contains VC grouping configuration paramters,
                one entry per VC group."
        ::= { wfAtmCommonGroup 12 }

    wfAtmVcGroupEntry OBJECT-TYPE
        SYNTAX	WfAtmVcGroupEntry
        ACCESS	not-accessible
        STATUS	mandatory
        DESCRIPTION
                "Entry definition."
        INDEX	{ wfAtmVcGroupCct,
    		  wfAtmVcGroupIndex }
        ::= { wfAtmVcGroupTable 1 }

    WfAtmVcGroupEntry ::= SEQUENCE {
    	    wfAtmVcGroupDelete
    		INTEGER,
    	    wfAtmVcGroupCct
    		INTEGER,
    	    wfAtmVcGroupIndex
    		INTEGER,
    	    wfAtmVcGroupName
                DisplayString
        }

    wfAtmVcGroupDelete OBJECT-TYPE
        SYNTAX	INTEGER {
    		    create(1),
    		    delete(2)
    		}
        ACCESS	read-write
        STATUS	mandatory
        DESCRIPTION
                "Create/delete MIB instance parameter."
        DEFVAL	{ create }
        ::= { wfAtmVcGroupEntry 1 }

    wfAtmVcGroupCct OBJECT-TYPE
        SYNTAX	INTEGER
        ACCESS	read-only
        STATUS	mandatory
        DESCRIPTION
                "The circuit number that this VC group is configured for."
        ::= { wfAtmVcGroupEntry 2 }

    wfAtmVcGroupIndex OBJECT-TYPE
        SYNTAX	INTEGER
        ACCESS	read-only
        STATUS	mandatory
        DESCRIPTION
                "Uniquely identifies the VC group on a given circuit"
        ::= { wfAtmVcGroupEntry 3 }

    wfAtmVcGroupName OBJECT-TYPE
        SYNTAX  DisplayString
        ACCESS  read-write
        STATUS  mandatory
        DESCRIPTION
                "The name for the VC group"
        ::= { wfAtmVcGroupEntry 4 }

    END  -- Wellfleet-ATM-MIB
