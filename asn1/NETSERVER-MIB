NETSERVER-MIB DEFINITIONS ::= BEGIN


	IMPORTS
	TEXTUAL-CONVENTION FROM SNMPv2-TC
    OBJECT-TYPE                             FROM RFC-1212
    Counter, TimeTicks, Gauge,enterprises   FROM RFC1155-SMI
    DisplayString, mib-2     		     	FROM RFC1213-MIB
	 TRAP-TYPE FROM RFC-1215;

auspex     OBJECT IDENTIFIER ::= { enterprises 80 }
netServer  OBJECT IDENTIFIER ::= { auspex 3 }


axProductInfo       OBJECT IDENTIFIER ::= { netServer 1 }
axNP                OBJECT IDENTIFIER ::= { netServer 2 }
axFSP               OBJECT IDENTIFIER ::= { netServer 3 }
axTrapData          OBJECT IDENTIFIER ::= { netServer 4 }

axFP                OBJECT IDENTIFIER ::= { axFSP 2 }
fpHTFS              OBJECT IDENTIFIER ::= { axFP 3 }
axSP                OBJECT IDENTIFIER ::= { axFSP 3 }
spRaid              OBJECT IDENTIFIER ::= { axSP 2 }
npProtocols         OBJECT IDENTIFIER ::= { axNP 3 }
axFab		 	    OBJECT IDENTIFIER ::= { axFSP 4 }
fabRaid				OBJECT IDENTIFIER ::= { axFab 5 }


-- The netServer ProductInfo Group

   
axProductName OBJECT-TYPE
   SYNTAX OCTET STRING
   ACCESS read-only
   STATUS mandatory
   DESCRIPTION
          "Name of the file server product."
   ::= { axProductInfo 1 }
   
axSWVersion OBJECT-TYPE
   SYNTAX OCTET STRING
   ACCESS read-only
   STATUS mandatory
   DESCRIPTION
          "Version of the M16 Kernel on Netserver"
   ::= { axProductInfo 2 }
   
axNumNPFSP OBJECT-TYPE
   SYNTAX INTEGER
   ACCESS read-only
   STATUS mandatory
   DESCRIPTION
          "Number of NPFSP boards on file server."
   ::= { axProductInfo 3 }
   
   
--NP Group
npTable OBJECT-TYPE
   SYNTAX SEQUENCE OF NPEntry
   ACCESS not-accessible
   STATUS mandatory
   DESCRIPTION
          "A table for all NPs(Network Processors) on the file server."
   ::= { axNP 1 }
   
npEntry OBJECT-TYPE
   SYNTAX NPEntry
   ACCESS not-accessible
   STATUS mandatory
   DESCRIPTION
          "An entry for each NP on the file server."
   INDEX { npIndex }
   ::= { npTable 1 }
   
NPEntry ::= SEQUENCE {
	npIndex			INTEGER,
	npBusyCount		Counter,
	npIdleCount		Counter
   }
   
npIndex OBJECT-TYPE
   SYNTAX INTEGER
   ACCESS read-only
   STATUS mandatory
   DESCRIPTION
          "A unique number for identifying an NP in the system."
   ::= { npEntry 1 } 
   
npBusyCount OBJECT-TYPE
   SYNTAX Counter
   ACCESS read-only
   STATUS mandatory
   DESCRIPTION
          "Busy counts of NP."
   ::= { npEntry 2 } 
   
npIdleCount OBJECT-TYPE
   SYNTAX Counter
   ACCESS read-only
   STATUS mandatory
   DESCRIPTION
          "Idle counts of NP."
   ::= { npEntry 3 } 
   
npIfTable OBJECT-TYPE
   SYNTAX SEQUENCE OF NPIfEntry
   ACCESS not-accessible
   STATUS mandatory
   DESCRIPTION
          "Table containing information for each interface of NP. 
	   It maps the interface with the NP"
   ::= { axNP 2 }
   
npIfEntry OBJECT-TYPE
   SYNTAX NPIfEntry
   ACCESS not-accessible
   STATUS mandatory
   DESCRIPTION
          "Entry for each interface"
   INDEX { npIndex, npIfIndex }
   ::= { npIfTable 1 }
   
NPIfEntry ::= SEQUENCE {
	npIfIndex		INTEGER,
	npIfifIndex		INTEGER,
	npIfType		DisplayString,
	npIfSpeed		INTEGER,
	npIfInOctets		Counter,
	npIfInUcastPkts		Counter,	
	npIfInNUcastPkts	Counter,	
	npIfInDiscards		Counter,	
	npIfInErrors		Counter,	
	npIfInUnknownProto	Counter,	
	npIfOutOctets		Counter,	
	npIfOutUcastPkts	Counter,	
	npIfOutNUcastPkts	Counter,	
	npIfOutDiscards		Counter,	
	npIfOutErrors		Counter,	
	npIfOutCollisions	Counter,	
	npIfOutQLen		Gauge,
	npIfAdminStatus   	INTEGER,
    npIfOperStatus    	INTEGER
   }
   
npIfIndex OBJECT-TYPE
   SYNTAX INTEGER
   ACCESS read-only
   STATUS mandatory
   DESCRIPTION
          "A unique number for an interface for a given NP"
   ::= { npIfEntry 1 } 
   
npIfifIndex OBJECT-TYPE
   SYNTAX INTEGER
   ACCESS read-only
   STATUS mandatory
   DESCRIPTION
          "Corresponding ifINdex in ifTable of mib-2"
   ::= { npIfEntry 2 } 
   
npIfType OBJECT-TYPE
   SYNTAX DisplayString
   ACCESS read-only
   STATUS mandatory
   DESCRIPTION
          "Type of network interface "
   ::= { npIfEntry 3 } 
   
npIfSpeed OBJECT-TYPE
   SYNTAX INTEGER
   ACCESS read-only
   STATUS mandatory
   DESCRIPTION
          "Nominal Interface Speed (in millions of bits per second)"

   ::= { npIfEntry 4 }                   
   
   
npIfInOctets OBJECT-TYPE
   SYNTAX Counter
   ACCESS read-only
   STATUS mandatory
   DESCRIPTION
          "The total number of octets received on the interface, 
		   including framing characters"
   ::= { npIfEntry 5 } 
   
npIfInUcastPkts OBJECT-TYPE
   SYNTAX Counter
   ACCESS read-only
   STATUS mandatory
   DESCRIPTION
          "The number of subnetwork-unicast packets delivered to a 
		   higher-layer protocol"
   ::= { npIfEntry 6 } 

npIfInNUcastPkts OBJECT-TYPE
   SYNTAX Counter
   ACCESS read-only
   STATUS mandatory
   DESCRIPTION
          "The number of non-unicast (i.e., subnetwork-broadcast 
	   or multicast) packets delivered to a higher-layer protocol"
   ::= { npIfEntry 7 } 

npIfInDiscards OBJECT-TYPE
   SYNTAX Counter
   ACCESS read-only
   STATUS mandatory
   DESCRIPTION
          "The inbound packet discard count even though no errors were 
	   detected.  One reason for discarding could be to free up 
	   buffer space"
   ::= { npIfEntry 8 } 

npIfInErrors OBJECT-TYPE
   SYNTAX Counter
   ACCESS read-only
   STATUS mandatory
   DESCRIPTION
          "The input-packet error count for an interface for a given NP"
   ::= { npIfEntry 9 } 

npIfInUnknownProto OBJECT-TYPE
   SYNTAX Counter
   ACCESS read-only
   STATUS mandatory
   DESCRIPTION
          "The input-packet discard count due to an unknown or 
	   unsupported protocol"
   ::= { npIfEntry 10 } 

npIfOutOctets OBJECT-TYPE
   SYNTAX Counter
   ACCESS read-only
   STATUS mandatory
   DESCRIPTION
          "The total number of octets transmitted out of the 
	   interface, including framing characters"
   ::= { npIfEntry 11 } 

npIfOutUcastPkts OBJECT-TYPE
   SYNTAX Counter
   ACCESS read-only
   STATUS mandatory
   DESCRIPTION
          "The total number of packets that higher-level protocols 
	   requested be transmitted to a subnetwork-unicast address, 
	   including those that were discarded or not sent"
   ::= { npIfEntry 12 } 

npIfOutNUcastPkts OBJECT-TYPE
   SYNTAX Counter
   ACCESS read-only
   STATUS mandatory
   DESCRIPTION
          "The total number of packets that higher-level protocols 
	   requested be transmitted to a  non-unicast (i.e., a 
	   subnetwork-broadcast or multicast) address, including 
	   those that were discarded or not sent"
   ::= { npIfEntry 13 } 

npIfOutDiscards OBJECT-TYPE
   SYNTAX Counter
   ACCESS read-only
   STATUS mandatory
   DESCRIPTION
          "The number of outbound packets that were chosen to be 
	   discarded even though no errors had been detected to 
	   prevent their being transmitted. One possibel reason for 
	   discarding such a packet could be to free up buffer space"
   ::= { npIfEntry 14 } 

npIfOutErrors OBJECT-TYPE
   SYNTAX Counter
   ACCESS read-only
   STATUS mandatory
   DESCRIPTION
          "The number of outbound packets that could not be 
	   transmitted because of errors"
   ::= { npIfEntry 15 } 

npIfOutCollisions OBJECT-TYPE
   SYNTAX Counter
   ACCESS read-only
   STATUS mandatory
   DESCRIPTION
          "The output-packet collision count for an interface 
	   for a given NP"
   ::= { npIfEntry 16 } 

npIfOutQLen OBJECT-TYPE
   SYNTAX Gauge
   ACCESS read-only
   STATUS mandatory
   DESCRIPTION
          "The output-packet queue length (in packets) for an 
	   interface for a given NP"
   ::= { npIfEntry 17 } 

npIfAdminStatus OBJECT-TYPE
    SYNTAX  INTEGER 
    		{
              up(1),       -- ready to pass packets
              down(2),
              testing(3)   -- in some test mode
             }
    ACCESS  read-write
    STATUS  mandatory
    DESCRIPTION
          "The desired state of the interface.  The testing(3) state indicates that no operational
           packets can be passed."
    ::= { npIfEntry 18 }

npIfOperStatus OBJECT-TYPE
    SYNTAX  INTEGER 
    		{
               up(1),       -- ready to pass packets
               down(2),
               testing(3)   -- in some test mode
             }
     ACCESS  read-only
     STATUS  mandatory
     DESCRIPTION
            "The current operational state of the interface. The testing(3) state indicates that no 
            operational packets can be passed."
     ::= { npIfEntry 19 }


-- npProtocols group

npIPTable OBJECT-TYPE
   SYNTAX SEQUENCE OF NPIPEntry
   ACCESS not-accessible
   STATUS mandatory
   DESCRIPTION
          "Table for Internet Protocol statistics for each NP 
	   of the system."
   ::= { npProtocols 1 }
   
npIPEntry OBJECT-TYPE
   SYNTAX NPIPEntry
   ACCESS not-accessible
   STATUS mandatory
   DESCRIPTION
          "An entry for each NP in the system."
   INDEX { npIndex }
   ::= { npIPTable 1 }
   
NPIPEntry ::= SEQUENCE {
        npIPForwarding		INTEGER,
        npIPDefaultTTL		INTEGER,
        npIPInReceives		Counter,
        npIPInHdrErrors		Counter,
        npIPInAddrErrors	Counter,
        npIPForwDatagrams	Counter,
        npIPInUnknownProtos	Counter,
        npIPInDiscards		Counter,
        npIPInDelivers		Counter,
        npIPOutRequests		Counter,
        npIPOutDiscards		Counter,
        npIPOutNoRoutes		Counter,
        npIPReasmTimeout	Counter,
        npIPReasmReqds		Counter,
        npIPReasmOKs		Counter,
        npIPReasmFails		Counter,
        npIPFragOKs		Counter,
        npIPFragFails		Counter,
        npIPFragCreates		Counter,
        npIPRoutingDiscards	Counter
   }

npIPForwarding OBJECT-TYPE
   SYNTAX INTEGER  {
           forwarding(1),
           not-forwarding(2)
   }
   ACCESS read-only
   STATUS mandatory
   DESCRIPTION
          "It has two values : 
	   forwarding(1) -- acting as gateway
	   notforwarding(2) -- NOT acting as gateway"
   ::= { npIPEntry 1 } 

npIPDefaultTTL OBJECT-TYPE
   SYNTAX INTEGER
   ACCESS read-only
   STATUS mandatory
   DESCRIPTION
          "NP IP default Time To Live."
   ::= { npIPEntry 2 } 
   
npIPInReceives OBJECT-TYPE
   SYNTAX Counter
   ACCESS read-only
   STATUS mandatory
   DESCRIPTION
          "NP IP received packet count."
   ::= { npIPEntry 3 } 

npIPInHdrErrors OBJECT-TYPE
   SYNTAX Counter
   ACCESS read-only
   STATUS mandatory
   DESCRIPTION
          "NP IP header error count."
   ::= { npIPEntry 4 } 

npIPInAddrErrors OBJECT-TYPE
   SYNTAX Counter
   ACCESS read-only
   STATUS mandatory
   DESCRIPTION
          "NP IP address error count."
   ::= { npIPEntry 5 } 

npIPForwDatagrams OBJECT-TYPE
   SYNTAX Counter
   ACCESS read-only
   STATUS mandatory
   DESCRIPTION
          "NP IP forwarded datagram count."
   ::= { npIPEntry 6 } 
   
npIPInUnknownProtos OBJECT-TYPE
   SYNTAX Counter
   ACCESS read-only
   STATUS mandatory
   DESCRIPTION
          "NP IP input packet with unknown protocol."
   ::= { npIPEntry 7 } 

npIPInDiscards OBJECT-TYPE
   SYNTAX Counter
   ACCESS read-only
   STATUS mandatory
   DESCRIPTION
          "NP IP discarded input packet count."
   ::= { npIPEntry 8 } 

npIPInDelivers OBJECT-TYPE
   SYNTAX Counter
   ACCESS read-only
   STATUS mandatory
   DESCRIPTION
          "NP IP delivered input packet count."
   ::= { npIPEntry 9 } 

npIPOutRequests OBJECT-TYPE
   SYNTAX Counter
   ACCESS read-only
   STATUS mandatory
   DESCRIPTION
          "NP IP tx packet count."
   ::= { npIPEntry 10 } 

npIPOutDiscards OBJECT-TYPE
   SYNTAX Counter
   ACCESS read-only
   STATUS mandatory
   DESCRIPTION
          "NP IP discarded out packet count."
   ::= { npIPEntry 11 } 

npIPOutNoRoutes OBJECT-TYPE
   SYNTAX Counter
   ACCESS read-only
   STATUS mandatory
   DESCRIPTION
          "NP IP tx fails due to no route count."
   ::= { npIPEntry 12 } 

npIPReasmTimeout OBJECT-TYPE
   SYNTAX Counter
   ACCESS read-only
   STATUS mandatory
   DESCRIPTION
          "NP IP reassembly time out count."
   ::= { npIPEntry 13 } 

npIPReasmReqds OBJECT-TYPE
   SYNTAX Counter
   ACCESS read-only
   STATUS mandatory
   DESCRIPTION
          "NP IP reassembly required count."
   ::= { npIPEntry 14 } 

npIPReasmOKs OBJECT-TYPE
   SYNTAX Counter
   ACCESS read-only
   STATUS mandatory
   DESCRIPTION
          "NP IP reassembly success count."
   ::= { npIPEntry 15 } 

npIPReasmFails OBJECT-TYPE
   SYNTAX Counter
   ACCESS read-only
   STATUS mandatory
   DESCRIPTION
          "NP IP reassembly failure count."
   ::= { npIPEntry 16 } 

npIPFragOKs OBJECT-TYPE
   SYNTAX Counter
   ACCESS read-only
   STATUS mandatory
   DESCRIPTION
          "NP IP fragmentation success count."
   ::= { npIPEntry 17 } 

npIPFragFails OBJECT-TYPE
   SYNTAX Counter
   ACCESS read-only
   STATUS mandatory
   DESCRIPTION
          "NP IP fragmentation failure count."
   ::= { npIPEntry 18 } 

npIPFragCreates OBJECT-TYPE
   SYNTAX Counter
   ACCESS read-only
   STATUS mandatory
   DESCRIPTION
          "NP IP fragment created count."
   ::= { npIPEntry 19 } 

npIPRoutingDiscards OBJECT-TYPE
   SYNTAX Counter
   ACCESS read-only
   STATUS mandatory
   DESCRIPTION
          "NP IP discarded route count."
   ::= { npIPEntry 20 } 

npICMPTable OBJECT-TYPE
   SYNTAX SEQUENCE OF NPICMPEntry
   ACCESS not-accessible
   STATUS mandatory
   DESCRIPTION
          "Table for Internet Control Message Protocol statistics for 
	   each NP of the system."
   ::= { npProtocols 2 }
   
npICMPEntry OBJECT-TYPE
   SYNTAX NPICMPEntry
   ACCESS not-accessible
   STATUS mandatory
   DESCRIPTION
          "An entry for each NP in the system."
   INDEX { npIndex }
   ::= { npICMPTable 1 }
   
NPICMPEntry ::= SEQUENCE {
        npICMPInMsgs		Counter,
        npICMPInErrors		Counter,
        npICMPInDestUnreachs	Counter,
        npICMPInTimeExcds	Counter,
        npICMPInParmProbs	Counter,
        npICMPInSrcQuenchs	Counter,
        npICMPInRedirects	Counter,
        npICMPInEchos		Counter,
        npICMPInEchoReps	Counter,
        npICMPInTimestamps	Counter,
        npICMPInTimestampReps	Counter,
        npICMPInAddrMasks	Counter,
        npICMPInAddrMaskReps	Counter,
        npICMPOutMsgs		Counter,
        npICMPOutErrors		Counter,
        npICMPOutDestUnreachs	Counter,
        npICMPOutTimeExcds	Counter,
        npICMPOutParmProbs	Counter,
        npICMPOutSrcQuenchs	Counter,
        npICMPOutRedirects	Counter,
        npICMPOutEchos		Counter,
        npICMPOutEchoReps	Counter,
        npICMPOutTimestamps	Counter,
        npICMPOutTimestampReps	Counter,
        npICMPOutAddrMasks	Counter,
        npICMPOutAddrMaskReps	Counter
   }

npICMPInMsgs OBJECT-TYPE
   SYNTAX Counter
   ACCESS read-only
   STATUS mandatory
   DESCRIPTION
          "NP ICMP input message count."
   ::= { npICMPEntry 1 } 

npICMPInErrors OBJECT-TYPE
   SYNTAX Counter
   ACCESS read-only
   STATUS mandatory
   DESCRIPTION
          "NP ICMP input error packet count."
   ::= { npICMPEntry 2 } 
   
npICMPInDestUnreachs OBJECT-TYPE
   SYNTAX Counter
   ACCESS read-only
   STATUS mandatory
   DESCRIPTION
          "NP ICMP input destination unreachable count."
   ::= { npICMPEntry 3 } 

npICMPInTimeExcds OBJECT-TYPE
   SYNTAX Counter
   ACCESS read-only
   STATUS mandatory
   DESCRIPTION
          "NP ICMP input time exceeded count."
   ::= { npICMPEntry 4 } 

npICMPInParmProbs OBJECT-TYPE
   SYNTAX Counter
   ACCESS read-only
   STATUS mandatory
   DESCRIPTION
          "NP ICMP input parameter problem packet count."
   ::= { npICMPEntry 5 } 

npICMPInSrcQuenchs OBJECT-TYPE
   SYNTAX Counter
   ACCESS read-only
   STATUS mandatory
   DESCRIPTION
          "NP ICMP input source quench packet count."
   ::= { npICMPEntry 6 } 
   
npICMPInRedirects OBJECT-TYPE
   SYNTAX Counter
   ACCESS read-only
   STATUS mandatory
   DESCRIPTION
          "NP ICMP input redirect packet count."
   ::= { npICMPEntry 7 } 

npICMPInEchos OBJECT-TYPE
   SYNTAX Counter
   ACCESS read-only
   STATUS mandatory
   DESCRIPTION
          "NP ICMP input echo count."
   ::= { npICMPEntry 8 } 

npICMPInEchoReps OBJECT-TYPE
   SYNTAX Counter
   ACCESS read-only
   STATUS mandatory
   DESCRIPTION
          "NP ICMP input echo reply count."
   ::= { npICMPEntry 9 } 

npICMPInTimestamps OBJECT-TYPE
   SYNTAX Counter
   ACCESS read-only
   STATUS mandatory
   DESCRIPTION
          "NP ICMP input timestamp count."
   ::= { npICMPEntry 10 } 

npICMPInTimestampReps OBJECT-TYPE
   SYNTAX Counter
   ACCESS read-only
   STATUS mandatory
   DESCRIPTION
          "NP ICMP input timestamp reply count."
   ::= { npICMPEntry 11 } 

npICMPInAddrMasks OBJECT-TYPE
   SYNTAX Counter
   ACCESS read-only
   STATUS mandatory
   DESCRIPTION
          "NP ICMP input address mask count."
   ::= { npICMPEntry 12 } 

npICMPInAddrMaskReps OBJECT-TYPE
   SYNTAX Counter
   ACCESS read-only
   STATUS mandatory
   DESCRIPTION
          "NP ICMP input address mask reply count."
   ::= { npICMPEntry 13 } 

npICMPOutMsgs OBJECT-TYPE
   SYNTAX Counter
   ACCESS read-only
   STATUS mandatory
   DESCRIPTION
          "NP ICMP output message count."
   ::= { npICMPEntry 14 } 

npICMPOutErrors OBJECT-TYPE
   SYNTAX Counter
   ACCESS read-only
   STATUS mandatory
   DESCRIPTION
          "NP ICMP output error packet count."
   ::= { npICMPEntry 15 } 

npICMPOutDestUnreachs OBJECT-TYPE
   SYNTAX Counter
   ACCESS read-only
   STATUS mandatory
   DESCRIPTION
          "NP ICMP output destination unreachable count."
   ::= { npICMPEntry 16 } 

npICMPOutTimeExcds OBJECT-TYPE
   SYNTAX Counter
   ACCESS read-only
   STATUS mandatory
   DESCRIPTION
          "NP ICMP output time exceeded count."
   ::= { npICMPEntry 17 } 

npICMPOutParmProbs OBJECT-TYPE
   SYNTAX Counter
   ACCESS read-only
   STATUS mandatory
   DESCRIPTION
          "NP ICMP output parameter problem packet count."
   ::= { npICMPEntry 18 } 

npICMPOutSrcQuenchs OBJECT-TYPE
   SYNTAX Counter
   ACCESS read-only
   STATUS mandatory
   DESCRIPTION
          "NP ICMP output source quench packet count."
   ::= { npICMPEntry 19 } 

npICMPOutRedirects OBJECT-TYPE
   SYNTAX Counter
   ACCESS read-only
   STATUS mandatory
   DESCRIPTION
          "NP ICMP output redirect packet count."
   ::= { npICMPEntry 20 } 

npICMPOutEchos OBJECT-TYPE
   SYNTAX Counter
   ACCESS read-only
   STATUS mandatory
   DESCRIPTION
          "NP ICMP output echo count."
   ::= { npICMPEntry 21 } 

npICMPOutEchoReps OBJECT-TYPE
   SYNTAX Counter
   ACCESS read-only
   STATUS mandatory
   DESCRIPTION
          "NP ICMP output echo reply count."
   ::= { npICMPEntry 22 } 

npICMPOutTimestamps OBJECT-TYPE
   SYNTAX Counter
   ACCESS read-only
   STATUS mandatory
   DESCRIPTION
          "NP ICMP output timestamp count."
   ::= { npICMPEntry 23 } 

npICMPOutTimestampReps OBJECT-TYPE
   SYNTAX Counter
   ACCESS read-only
   STATUS mandatory
   DESCRIPTION
          "NP ICMP output timestamp reply count."
   ::= { npICMPEntry 24 } 

npICMPOutAddrMasks OBJECT-TYPE
   SYNTAX Counter
   ACCESS read-only
   STATUS mandatory
   DESCRIPTION
          "NP ICMP output address mask count."
   ::= { npICMPEntry 25 } 

npICMPOutAddrMaskReps OBJECT-TYPE
   SYNTAX Counter
   ACCESS read-only
   STATUS mandatory
   DESCRIPTION
          "NP ICMP output address mask reply count."
   ::= { npICMPEntry 26 } 

npTCPTable OBJECT-TYPE
   SYNTAX SEQUENCE OF NPTCPEntry
   ACCESS not-accessible
   STATUS mandatory
   DESCRIPTION
          "Table for Transmission Control Protocol statistics for 
		   each NP of the system."
   ::= { npProtocols 3 }
   
npTCPEntry OBJECT-TYPE
   SYNTAX NPTCPEntry
   ACCESS not-accessible
   STATUS mandatory
   DESCRIPTION
          "An entry for each NP in the system."
   INDEX { npIndex }
   ::= { npTCPTable 1 }
   
NPTCPEntry ::= SEQUENCE {
        npTCPRtoAlgorithm	INTEGER,
        npTCPRtoMin		INTEGER,
        npTCPRtoMax		INTEGER,
        npTCPMaxConn		INTEGER,
        npTCPActiveOpens	Counter,
        npTCPPassiveOpens	Counter,
        npTCPAttemptFails	Counter,
        npTCPEstabResets	Counter,
        npTCPCurrEstab		INTEGER,
        npTCPInSegs		Counter,
        npTCPOutSegs		Counter,
        npTCPRetransSegs	Counter,
        npTCPInErrs		Counter,
        npTCPOutRsts		Counter
   }

npTCPRtoAlgorithm OBJECT-TYPE
   SYNTAX INTEGER  {
           other(1),
           constant(2),
           rsre(3),
           vanj(4)
   }
   ACCESS read-only
   STATUS mandatory
   DESCRIPTION
          "NP TCP Round Trip Algorithm type."
   ::= { npTCPEntry 1 } 

npTCPRtoMin OBJECT-TYPE
   SYNTAX INTEGER
   ACCESS read-only
   STATUS mandatory
   DESCRIPTION
          "NP TCP minimum RTO."
   ::= { npTCPEntry 2 } 
   
npTCPRtoMax OBJECT-TYPE
   SYNTAX INTEGER
   ACCESS read-only
   STATUS mandatory
   DESCRIPTION
          "NP TCP maximum RTO."
   ::= { npTCPEntry 3 } 

npTCPMaxConn OBJECT-TYPE
   SYNTAX INTEGER
   ACCESS read-only
   STATUS mandatory
   DESCRIPTION
          "NP TCP maximum number of connections."
   ::= { npTCPEntry 4 } 

npTCPActiveOpens OBJECT-TYPE
   SYNTAX Counter
   ACCESS read-only
   STATUS mandatory
   DESCRIPTION
          "NP TCP active open count."
   ::= { npTCPEntry 5 } 

npTCPPassiveOpens OBJECT-TYPE
   SYNTAX Counter
   ACCESS read-only
   STATUS mandatory
   DESCRIPTION
          "NP TCP passive open count."
   ::= { npTCPEntry 6 } 
   
npTCPAttemptFails OBJECT-TYPE
   SYNTAX Counter
   ACCESS read-only
   STATUS mandatory
   DESCRIPTION
          "NP TCP connect attempt fails."
   ::= { npTCPEntry 7 } 

npTCPEstabResets OBJECT-TYPE
   SYNTAX Counter
   ACCESS read-only
   STATUS mandatory
   DESCRIPTION
          "NP TCP reset of established session."
   ::= { npTCPEntry 8 } 

npTCPCurrEstab OBJECT-TYPE
   SYNTAX INTEGER
   ACCESS read-only
   STATUS mandatory
   DESCRIPTION
          "NP TCP current established session count."
   ::= { npTCPEntry 9 } 

npTCPInSegs OBJECT-TYPE
   SYNTAX Counter
   ACCESS read-only
   STATUS mandatory
   DESCRIPTION
          "NP TCP input segments count."
   ::= { npTCPEntry 10 } 

npTCPOutSegs OBJECT-TYPE
   SYNTAX Counter
   ACCESS read-only
   STATUS mandatory
   DESCRIPTION
          "NP TCP output segments count."
   ::= { npTCPEntry 11 } 

npTCPRetransSegs OBJECT-TYPE
   SYNTAX Counter
   ACCESS read-only
   STATUS mandatory
   DESCRIPTION
          "NP TCP retransmitted segments count."
   ::= { npTCPEntry 12 } 

npTCPInErrs OBJECT-TYPE
   SYNTAX Counter
   ACCESS read-only
   STATUS mandatory
   DESCRIPTION
          "NP TCP input error packets count."
   ::= { npTCPEntry 13 } 

npTCPOutRsts OBJECT-TYPE
   SYNTAX Counter
   ACCESS read-only
   STATUS mandatory
   DESCRIPTION
          "NP TCP output reset packets count."
   ::= { npTCPEntry 14 } 

npUDPTable OBJECT-TYPE
   SYNTAX SEQUENCE OF NPUDPEntry
   ACCESS not-accessible
   STATUS mandatory
   DESCRIPTION
          "Table for User Datagram Protocol statistics for each NP 
		   of the system."
   ::= { npProtocols 4 }
   
npUDPEntry OBJECT-TYPE
   SYNTAX NPUDPEntry
   ACCESS not-accessible
   STATUS mandatory
   DESCRIPTION
          "An entry for each NP in the system."
   INDEX { npIndex }
   ::= { npUDPTable 1 }
   
NPUDPEntry ::= SEQUENCE {
        npUDPInDatagrams	Counter,
        npUDPNoPorts		Counter,
        npUDPInErrors		Counter,
        npUDPOutDatagrams	Counter
   }

npUDPInDatagrams OBJECT-TYPE
   SYNTAX Counter
   ACCESS read-only
   STATUS mandatory
   DESCRIPTION
          "NP UDP input datagram count."
   ::= { npUDPEntry 1 } 

npUDPNoPorts OBJECT-TYPE
   SYNTAX Counter
   ACCESS read-only
   STATUS mandatory
   DESCRIPTION
          "NP UDP number of ports."
   ::= { npUDPEntry 2 } 
   
npUDPInErrors OBJECT-TYPE
   SYNTAX Counter
   ACCESS read-only
   STATUS mandatory
   DESCRIPTION
          "NP UDP input error count."
   ::= { npUDPEntry 3 } 

npUDPOutDatagrams OBJECT-TYPE
   SYNTAX Counter
   ACCESS read-only
   STATUS mandatory
   DESCRIPTION
          "Np UDP output datagram count."
   ::= { npUDPEntry 4 } 

npNFSTable OBJECT-TYPE
   SYNTAX SEQUENCE OF NPNFSEntry
   ACCESS not-accessible
   STATUS mandatory
   DESCRIPTION
          "Table for Network File System statistics for each NP in the system."
   ::= { npProtocols 5 }
   
npNFSEntry OBJECT-TYPE
   SYNTAX NPNFSEntry
   ACCESS not-accessible
   STATUS mandatory
   DESCRIPTION
          "An entry for each NP in the system."
   INDEX { npIndex }
   ::= { npNFSTable 1 }
   
NPNFSEntry ::= SEQUENCE {
	npNFSDCounts		Counter,
	npNFSDNJobs		Counter,
	npNFSDBusyCounts	Counter
   }

npNFSDCounts OBJECT-TYPE
   SYNTAX Counter
   ACCESS read-only
   STATUS mandatory
   DESCRIPTION
          "NP NFS count (obtained from NFS daemon)"
   ::= { npNFSEntry 1 } 

npNFSDNJobs OBJECT-TYPE
   SYNTAX Counter
   ACCESS read-only
   STATUS mandatory
   DESCRIPTION
          "NP NFS number of jobs (obtained from NFS daemon)"
   ::= { npNFSEntry 2 } 
   
npNFSDBusyCounts OBJECT-TYPE
   SYNTAX Counter
   ACCESS read-only
   STATUS mandatory
   DESCRIPTION
          "NP NFS busy count (obtained from NFS daemon)"
   ::= { npNFSEntry 3 } 




npSMBTable OBJECT-TYPE
   SYNTAX SEQUENCE OF NPSMBEntry
   ACCESS not-accessible
   STATUS mandatory
   DESCRIPTION
          "Contains statistical counts for the SMB protocol per NP"
   ::= { npProtocols 6 }
   
npSMBEntry OBJECT-TYPE
   SYNTAX NPSMBEntry
   ACCESS not-accessible
   STATUS mandatory
   DESCRIPTION
          "An entry for each NP in the system."
   INDEX { npIndex }
   ::= { npSMBTable 1 }
   
NPSMBEntry ::= SEQUENCE {
	npSMBRcvd		Counter,
	npSMBBytesRcvd		Counter,
	npSMBBytesSent		Counter,
	npSMBReads		Counter,
	npSMBWrites		Counter,
	npSMBOpens		Counter,
	npSMBCloses		Counter,
	npSMBErrors		Counter,
	npSMBLocksHeld		INTEGER
   }

npSMBRcvd OBJECT-TYPE
   SYNTAX Counter
   ACCESS read-only
   STATUS mandatory
   DESCRIPTION
          "The total number of SMB netbios messages received."
   ::= { npSMBEntry 1 } 
  
npSMBBytesRcvd OBJECT-TYPE
   SYNTAX Counter
   ACCESS read-only
   STATUS mandatory
   DESCRIPTION
          "The total number of SMB related bytes rvcd by this NP 
           from a client (does not include netbios header bytes)."
   ::= { npSMBEntry 2 } 

npSMBBytesSent OBJECT-TYPE
   SYNTAX Counter
   ACCESS read-only
   STATUS mandatory
   DESCRIPTION
          "The total SMB related bytes sent by this NP to a client  
	       (does not include netbios header bytes)."
   ::= { npSMBEntry 3 } 

npSMBReads OBJECT-TYPE
   SYNTAX Counter
   ACCESS read-only
   STATUS mandatory
   DESCRIPTION
          "The total number of SMB reads consisting of the following
           opcodes: SMB-COM-READ, SMB-COM-LOCK-AND-READ, SMB-COM-READ-RAW,
           SMB-COM-READ-MPX, SMB-COM-READ-MPX-SECONDARY and SMB-COM-READ-ANDX."

   ::= { npSMBEntry 4 } 

npSMBWrites OBJECT-TYPE
   SYNTAX Counter
   ACCESS read-only
   STATUS mandatory
   DESCRIPTION
          "The total number of SMB writes consisting of the following 
           opcodes: SMB-COM-WRITE, SMB-COM-WRITE-AND-UNLOCK, 
           SMB-COM-WRITE-RAW, SMB-COM-WRITE-MPX, SMB-COM-WRITE-COMPLETE,
           SMB-COM-WRITE-ANDX and SMB-COM-WRITE-AND-CLOSE."
   ::= { npSMBEntry 5 } 

npSMBOpens OBJECT-TYPE
   SYNTAX Counter
   ACCESS read-only
   STATUS mandatory
   DESCRIPTION
          "The total number of SMB opens consisting of the SMB-COM-OPEN,
		   SMB-COM-CREATE,SMB-COM-CREATE-TEMPORARY,SMB-COM-CREATE-NEW,
           TRANS2-OPEN2, NT-TRANSACT-CREATE  and 
           SMB-COM-OPEN-ANDX opcodes received."
   ::= { npSMBEntry 6 } 

npSMBCloses OBJECT-TYPE
   SYNTAX Counter
   ACCESS read-only
   STATUS mandatory
   DESCRIPTION
          "The total number of SMB SMB-COM-CLOSE opcodes recieved."
   ::= { npSMBEntry 7 } 

npSMBErrors OBJECT-TYPE
   SYNTAX Counter
   ACCESS read-only
   STATUS mandatory
   DESCRIPTION
          "The total number of invalid netbios messages recieved."
   ::= { npSMBEntry 8 } 

npSMBLocksHeld OBJECT-TYPE
   SYNTAX INTEGER
   ACCESS read-only
   STATUS mandatory
   DESCRIPTION
          "The total number of locks currently held"
   ::= { npSMBEntry 9 } 

--FSP Group
fspTable OBJECT-TYPE
   SYNTAX SEQUENCE OF FSPEntry
   ACCESS not-accessible
   STATUS mandatory
   DESCRIPTION
          "A table for all FSPs(File and Storage Processors) on the file server."
   ::= { axFSP 1 }
   
fspEntry OBJECT-TYPE
   SYNTAX FSPEntry
   ACCESS not-accessible
   STATUS mandatory
   DESCRIPTION
          "An entry for one FSP on the file server."
   INDEX { fspIndex }
   ::= { fspTable 1 }
   
FSPEntry ::= SEQUENCE {
	fspIndex		INTEGER,
	fspBusyCount		Counter,
	fspIdleCount		Counter
     }
   
fspIndex OBJECT-TYPE
   SYNTAX INTEGER
   ACCESS read-only
   STATUS mandatory
   DESCRIPTION
          "A unique number for identifying an FSP in the system."
   ::= { fspEntry 1 } 
   
fspBusyCount OBJECT-TYPE
   SYNTAX Counter
   ACCESS read-only
   STATUS mandatory
   DESCRIPTION
          "Busy counts of FSP."
   ::= { fspEntry 2 } 
   
fspIdleCount OBJECT-TYPE
   SYNTAX Counter
   ACCESS read-only
   STATUS mandatory
   DESCRIPTION
          "Idle counts of FSP."
   ::= { fspEntry 3 } 
   
fpLFSTable OBJECT-TYPE
   SYNTAX SEQUENCE OF FPLFSEntry
   ACCESS not-accessible
   STATUS mandatory
   DESCRIPTION
          "Table for FP File System Services Statistics 
		   for each FSP on the system."
   ::= { axFP 1 }
   
fpLFSEntry OBJECT-TYPE
   SYNTAX FPLFSEntry
   ACCESS not-accessible
   STATUS mandatory
   DESCRIPTION
          "An entry for each FSP in the system."
   INDEX { fspIndex }
   ::= { fpLFSTable 1 }

FPLFSEntry ::= SEQUENCE {
	fpLFSVersion		INTEGER,
	fpLFSMounts		Counter,
	fpLFSUMounts		Counter,
	fpLFSReads		Counter,
	fpLFSWrites		Counter,
	fpLFSReaddirs		Counter,
	fpLFSReadlinks		Counter,
	fpLFSMkdirs		Counter,
	fpLFSMknods		Counter,
	fpLFSReaddirPluses	Counter,
	fpLFSFsstats		Counter,
	fpLFSNull		Counter,
	fpLFSFsinfo		Counter,
	fpLFSGetattrs		Counter,
	fpLFSSetattrs		Counter,
	fpLFSLookups		Counter,
	fpLFSCreates		Counter,
	fpLFSRemoves		Counter,
	fpLFSRenames		Counter,
	fpLFSLinks		Counter,
	fpLFSSymlinks		Counter,
	fpLFSRmdirs		Counter,
	fpLFSCkpntons		Counter,
	fpLFSCkpntoffs		Counter,
	fpLFSClears		Counter,
	fpLFSIsolateFs		Counter,
	fpLFSReleaseFs		Counter,
	fpLFSIsolationStates	Counter,
	fpLFSDiagnostics	Counter,
	fpLFSPurges		Counter
     }

fpLFSVersion OBJECT-TYPE
   SYNTAX INTEGER
   ACCESS read-only
   STATUS mandatory
   DESCRIPTION
          "FP file system services statistics version."
   ::= { fpLFSEntry 1 }

   
fpLFSMounts OBJECT-TYPE
   SYNTAX Counter
   ACCESS read-only
   STATUS mandatory
   DESCRIPTION
          "FP file system services - FC-MOUNT - Counter."
   ::= { fpLFSEntry 2 } 
   
fpLFSUMounts OBJECT-TYPE
   SYNTAX Counter
   ACCESS read-only
   STATUS mandatory
   DESCRIPTION
          "FP file system services - FC-UMOUNT - Counter."
   ::= { fpLFSEntry 3 } 
   
fpLFSReads OBJECT-TYPE
   SYNTAX Counter
   ACCESS read-only
   STATUS mandatory
   DESCRIPTION
          "FP file system services - FC-READ - Counter."
   ::= { fpLFSEntry 4 } 
   
fpLFSWrites OBJECT-TYPE
   SYNTAX Counter
   ACCESS read-only
   STATUS mandatory
   DESCRIPTION
          "FP file system services - FC-WRITE - Counter."
   ::= { fpLFSEntry 5 } 
   
fpLFSReaddirs OBJECT-TYPE
   SYNTAX Counter
   ACCESS read-only
   STATUS mandatory
   DESCRIPTION
          "FP file system services - FC-READDIR - Counter."
   ::= { fpLFSEntry 6 } 
   
fpLFSReadlinks OBJECT-TYPE
   SYNTAX Counter
   ACCESS read-only
   STATUS mandatory
   DESCRIPTION
          "FP file system services - FC-READLINK - Counter."
   ::= { fpLFSEntry 7 } 
   
fpLFSMkdirs OBJECT-TYPE
   SYNTAX Counter
   ACCESS read-only
   STATUS mandatory
   DESCRIPTION
          "FP file system services - FC-MKDIR - Counter."
   ::= { fpLFSEntry 8 } 
   
fpLFSMknods OBJECT-TYPE
   SYNTAX Counter
   ACCESS read-only
   STATUS mandatory
   DESCRIPTION
          "FP file system services - FC-MKNOD - Counter."
   ::= { fpLFSEntry 9 } 
	
fpLFSReaddirPluses OBJECT-TYPE
   SYNTAX Counter
   ACCESS read-only
   STATUS mandatory
   DESCRIPTION
          "FP file system services - FC-READDIR-PLUS - Counter."
   ::= { fpLFSEntry 10 } 
   
fpLFSFsstats OBJECT-TYPE
   SYNTAX Counter
   ACCESS read-only
   STATUS mandatory
   DESCRIPTION
          "FP file system services - FC-FSSTAT - Counter."
   ::= { fpLFSEntry 11 } 
   
fpLFSNull OBJECT-TYPE
   SYNTAX Counter
   ACCESS read-only
   STATUS mandatory
   DESCRIPTION
          "FP file system services - FC-NULL - Counter."
   ::= { fpLFSEntry 12 } 
   
   
fpLFSFsinfo OBJECT-TYPE
   SYNTAX Counter
   ACCESS read-only
   STATUS mandatory
   DESCRIPTION
          "FP file system services - FC-FSINFO - Counter."
   ::= { fpLFSEntry 13 } 
   
   
fpLFSGetattrs OBJECT-TYPE
   SYNTAX Counter
   ACCESS read-only
   STATUS mandatory
   DESCRIPTION
          "FP file system services - FC-GETATTR - Counter."
   ::= { fpLFSEntry 14 } 
   
fpLFSSetattrs OBJECT-TYPE
   SYNTAX Counter
   ACCESS read-only
   STATUS mandatory
   DESCRIPTION
          "FP file system services - FC-SETATTR - Counter."
   ::= { fpLFSEntry 15 } 
   
fpLFSLookups OBJECT-TYPE
   SYNTAX Counter
   ACCESS read-only
   STATUS mandatory
   DESCRIPTION
          "FP file system services - FC-LOOKUP - Counter."
   ::= { fpLFSEntry 16 } 

fpLFSCreates OBJECT-TYPE
   SYNTAX Counter
   ACCESS read-only
   STATUS mandatory
   DESCRIPTION
          "FP file system services - FC-CREATE - Counter."
   ::= { fpLFSEntry 17 } 
   
fpLFSRemoves OBJECT-TYPE
   SYNTAX Counter
   ACCESS read-only
   STATUS mandatory
   DESCRIPTION
          "FP file system services - FC-REMOVE - Counter."
   ::= { fpLFSEntry 18 } 
   
fpLFSRenames OBJECT-TYPE
   SYNTAX Counter
   ACCESS read-only
   STATUS mandatory
   DESCRIPTION
          "FP file system services - FC-RENAME - Counter."
   ::= { fpLFSEntry 19 } 
   
fpLFSLinks OBJECT-TYPE
   SYNTAX Counter
   ACCESS read-only
   STATUS mandatory
   DESCRIPTION
          "FP file system services - FC-LINK - Counter."
   ::= { fpLFSEntry 20 } 
   
fpLFSSymlinks OBJECT-TYPE
   SYNTAX Counter
   ACCESS read-only
   STATUS mandatory
   DESCRIPTION
          "FP file system services - FC-SYMLINK - Counter."
   ::= { fpLFSEntry 21 } 
   
fpLFSRmdirs OBJECT-TYPE
   SYNTAX Counter
   ACCESS read-only
   STATUS mandatory
   DESCRIPTION
          "FP file system services - FC-RMDIR - Counter."
   ::= { fpLFSEntry 22 } 
   
fpLFSCkpntons OBJECT-TYPE
   SYNTAX Counter
   ACCESS read-only
   STATUS mandatory
   DESCRIPTION
          "FP file system services - FC-CKPNTON - Counter."
   ::= { fpLFSEntry 23 } 
   
fpLFSCkpntoffs OBJECT-TYPE
   SYNTAX Counter
   ACCESS read-only
   STATUS mandatory
   DESCRIPTION
          "FP file system services - FC-CKPNTOFFS - Counter."
   ::= { fpLFSEntry 24 } 
   
fpLFSClears OBJECT-TYPE
   SYNTAX Counter
   ACCESS read-only
   STATUS mandatory
   DESCRIPTION
          "FP file system services - FC-CLEAR - Counter."
   ::= { fpLFSEntry 25 } 
   
fpLFSIsolateFs OBJECT-TYPE
   SYNTAX Counter
   ACCESS read-only
   STATUS mandatory
   DESCRIPTION
          "FP file system services - FC-ISOLATE-FS - Counter."
   ::= { fpLFSEntry 26 } 
   
fpLFSReleaseFs OBJECT-TYPE
   SYNTAX Counter
   ACCESS read-only
   STATUS mandatory
   DESCRIPTION
          "FP file system services - FC-RELEASE-FS - Counter."
   ::= { fpLFSEntry 27 } 
   
fpLFSIsolationStates OBJECT-TYPE
   SYNTAX Counter
   ACCESS read-only
   STATUS mandatory
   DESCRIPTION
          "FP file system services - FC-ISOLATION-STATE - Counter."
   ::= { fpLFSEntry 28 } 
   
fpLFSDiagnostics OBJECT-TYPE
   SYNTAX Counter
   ACCESS read-only
   STATUS mandatory
   DESCRIPTION
          "FP file system services - FC-DIAGNOSTIC - Counter."
   ::= { fpLFSEntry 29 } 
   
fpLFSPurges OBJECT-TYPE
   SYNTAX Counter
   ACCESS read-only
   STATUS mandatory
   DESCRIPTION
          "FP file system services - FC-PURGE - Counter."
   ::= { fpLFSEntry 30 }  


fpFileSystemTable OBJECT-TYPE
   SYNTAX SEQUENCE OF FPFSEntry
   ACCESS not-accessible
   STATUS mandatory
   DESCRIPTION
          "Table containg File systems on each FSP"
   ::= { axFP 2 }
   
fpFSEntry OBJECT-TYPE
   SYNTAX FPFSEntry
   ACCESS not-accessible
   STATUS mandatory
   DESCRIPTION
          "Entry for each File System"
   INDEX { fspIndex, fpFSIndex }
   ::= { fpFileSystemTable 1 }
   
FPFSEntry ::= SEQUENCE {
	fpFSIndex		INTEGER,
	fpHrFSIndex		INTEGER
     }

fpFSIndex OBJECT-TYPE
   SYNTAX INTEGER
   ACCESS read-only
   STATUS mandatory
   DESCRIPTION
          "Uniquely identifies each FS on FSP"
   ::= { fpFSEntry 1 } 
   
fpHrFSIndex OBJECT-TYPE
   SYNTAX INTEGER
   ACCESS read-only
   STATUS mandatory
   DESCRIPTION
          "Index of the corresponding FS entry in host resource mib"
   ::= { fpFSEntry 2 } 

   
  --
  --
  --fpDNLCStatTable
  --
  --
fpDNLCTStatTable OBJECT-TYPE
   SYNTAX SEQUENCE OF FPDNLCSEntry
   ACCESS not-accessible
   STATUS mandatory
   DESCRIPTION
          "DNLC is part of StackOS module. This table 
		   displays DNLC Statistics."
   ::= { fpHTFS 1 }

fpDNLCSEntry OBJECT-TYPE
   SYNTAX FPDNLCSEntry
   ACCESS not-accessible
   STATUS mandatory
   DESCRIPTION
          "Each entry for a FSP board."
   INDEX { fspIndex }
   ::= { fpDNLCTStatTable 1 }

FPDNLCSEntry ::= SEQUENCE {
        fpDNLCHit          INTEGER,
        fpDNLCMiss         INTEGER,
        fpDNLCEnter        INTEGER,
        fpDNLCConflict     INTEGER,
        fpDNLCPurgevfsp    INTEGER,
        fpDNLCPurgevp      INTEGER,
        fpDNLCHashsz       INTEGER
     }

fpDNLCHit OBJECT-TYPE
   SYNTAX INTEGER
   ACCESS read-only
   STATUS mandatory
   DESCRIPTION
          "DNLC hit on a given FSP."
   ::= { fpDNLCSEntry 1 }

fpDNLCMiss OBJECT-TYPE
   SYNTAX INTEGER
   ACCESS read-only
   STATUS mandatory
   DESCRIPTION
          "DNLC miss on a given FSP."
   ::= { fpDNLCSEntry 2 }

fpDNLCEnter OBJECT-TYPE
   SYNTAX INTEGER
   ACCESS read-only
   STATUS mandatory
   DESCRIPTION
          "Number of DNLC entries made (total)."
   ::= { fpDNLCSEntry 3 }

fpDNLCConflict OBJECT-TYPE
   SYNTAX INTEGER
   ACCESS read-only
   STATUS mandatory
   DESCRIPTION
          "Times entry found in DNLC on dnlc-enter."
   ::= { fpDNLCSEntry 4 }

fpDNLCPurgevfsp OBJECT-TYPE
   SYNTAX INTEGER
   ACCESS read-only
   STATUS mandatory
   DESCRIPTION
          "Entries purged based on vfsp."
   ::= { fpDNLCSEntry 5 }

fpDNLCPurgevp OBJECT-TYPE
   SYNTAX INTEGER
   ACCESS read-only
   STATUS mandatory
   DESCRIPTION
          "Entries purge based on vp."
   ::= { fpDNLCSEntry 6 }

fpDNLCHashsz OBJECT-TYPE
   SYNTAX INTEGER
   ACCESS read-only
   STATUS mandatory
   DESCRIPTION
          "Number of hash buckets in dnlc hash table."
   ::= { fpDNLCSEntry 7 }

--
-- Page Table
--

fpPageStatTable OBJECT-TYPE
   SYNTAX SEQUENCE OF FPPageEntry
   ACCESS not-accessible
   STATUS mandatory
   DESCRIPTION
          "Page is part of StackOS module. This table gives the 
		   Page Statistics for all FSPs."
   ::= { fpHTFS 2 }

fpPageEntry OBJECT-TYPE
   SYNTAX FPPageEntry
   ACCESS not-accessible
   STATUS mandatory
   DESCRIPTION
          "Each Entry in the table displays Page Statistics for a FSP."
   INDEX { fspIndex }
   ::= { fpPageStatTable 1 }

FPPageEntry ::= SEQUENCE {
        fpPAGETotalmem        INTEGER,
        fpPAGEFreelistcnt     INTEGER,
        fpPAGECachelistcnt    INTEGER,
        fpPAGEDirtyflistcnt   INTEGER,
        fpPAGEDirtydlistcnt   INTEGER,
        fpPAGECachehit        INTEGER,
        fpPAGECachemiss       INTEGER,
        fpPAGEWritehit        INTEGER,
        fpPAGEWritemiss       INTEGER,
        fpPAGEZcref           INTEGER,
        fpPAGEZcbreak         INTEGER,
        fpPAGEOutscan         INTEGER,
        fpPAGEOutputpage      INTEGER,
        fpPAGEFsflushscan     INTEGER,
        fpPAGEFsflushputpage  INTEGER,
        fpPAGEOutcnt          INTEGER
     }

fpPAGETotalmem OBJECT-TYPE
   SYNTAX INTEGER
   ACCESS read-only
   STATUS mandatory
   DESCRIPTION
          "Allocated memory for pages."
   ::= { fpPageEntry 1 }


fpPAGEFreelistcnt OBJECT-TYPE
   SYNTAX INTEGER
   ACCESS read-only
   STATUS mandatory
   DESCRIPTION
          "Pages on freelist."
   ::= { fpPageEntry 2 }


fpPAGECachelistcnt OBJECT-TYPE
   SYNTAX INTEGER
   ACCESS read-only
   STATUS mandatory
   DESCRIPTION
          "Pages on cachelist."
   ::= { fpPageEntry 3 }


fpPAGEDirtyflistcnt OBJECT-TYPE
   SYNTAX INTEGER
   ACCESS read-only
   STATUS mandatory
   DESCRIPTION
          "Pages on dirtyflist."
   ::= { fpPageEntry 4 }



fpPAGEDirtydlistcnt OBJECT-TYPE
   SYNTAX INTEGER
   ACCESS read-only
   STATUS mandatory
   DESCRIPTION
          "Pages on dirtydlist"
   ::= { fpPageEntry 5 }


fpPAGECachehit OBJECT-TYPE
   SYNTAX INTEGER
   ACCESS read-only
   STATUS mandatory
   DESCRIPTION
          "Page cache hit."
   ::= { fpPageEntry 6 }


fpPAGECachemiss OBJECT-TYPE
   SYNTAX INTEGER
   ACCESS read-only
   STATUS mandatory
   DESCRIPTION
          "Page cache miss."
   ::= { fpPageEntry 7 }


fpPAGEWritehit OBJECT-TYPE
   SYNTAX INTEGER
   ACCESS read-only
   STATUS mandatory
   DESCRIPTION
          "Page cache write hit."
   ::= { fpPageEntry 8 }

fpPAGEWritemiss OBJECT-TYPE
   SYNTAX INTEGER
   ACCESS read-only
   STATUS mandatory
   DESCRIPTION
          "Page cache write miss."
   ::= { fpPageEntry 9 }

fpPAGEZcref OBJECT-TYPE
   SYNTAX INTEGER
   ACCESS read-only
   STATUS mandatory
   DESCRIPTION
          "Page Zref."
   ::= { fpPageEntry 10 }

fpPAGEZcbreak OBJECT-TYPE
   SYNTAX INTEGER
   ACCESS read-only
   STATUS mandatory
   DESCRIPTION
          "Page Zbreak."
   ::= { fpPageEntry 11 }

fpPAGEOutscan OBJECT-TYPE
   SYNTAX INTEGER
   ACCESS read-only
   STATUS mandatory
   DESCRIPTION
          "Page out scan."
   ::= { fpPageEntry 12 }


fpPAGEOutputpage OBJECT-TYPE
   SYNTAX INTEGER
   ACCESS read-only
   STATUS mandatory
   DESCRIPTION
          "Output Page."
   ::= { fpPageEntry 13 }

fpPAGEFsflushscan OBJECT-TYPE
   SYNTAX INTEGER
   ACCESS read-only
   STATUS mandatory
   DESCRIPTION
          "Flush scan."
   ::= { fpPageEntry 14 }

fpPAGEFsflushputpage OBJECT-TYPE
   SYNTAX INTEGER
   ACCESS read-only
   STATUS mandatory
   DESCRIPTION
          "Flush output page."
   ::= { fpPageEntry 15 }

fpPAGEOutcnt OBJECT-TYPE
   SYNTAX INTEGER
   ACCESS read-only
   STATUS mandatory
   DESCRIPTION
          "Page out count."
   ::= { fpPageEntry 16 }


  --
  -- fpBufferUIO table
  --
  --

fpBufferStatTable OBJECT-TYPE
   SYNTAX SEQUENCE OF FPBufferEntry
   ACCESS not-accessible
   STATUS mandatory
   DESCRIPTION
          "BufferIO is one of the modules present in StackOS. 
	   This table displays the bufferIO statistics for all FSPs."
   ::= { fpHTFS 3 }

fpBufferEntry OBJECT-TYPE
   SYNTAX FPBufferEntry
   ACCESS not-accessible
   STATUS mandatory
   DESCRIPTION
          "Each entry in the table for a single FSP."
   INDEX { fspIndex }
   ::= { fpBufferStatTable 1 }

FPBufferEntry ::= SEQUENCE {
        fpBUFLreads     INTEGER,
        fpBUFBreads     INTEGER,
        fpBUFLwrites    INTEGER,
        fpBUFBwrites    INTEGER,
        fpBUFIOwaits    INTEGER,
        fpBUFResid      INTEGER,
        fpBUFBufsize    INTEGER,
        fpBUFBcount     INTEGER
}


fpBUFLreads OBJECT-TYPE
   SYNTAX INTEGER
   ACCESS read-only
   STATUS mandatory
   DESCRIPTION
          "Number of buffered reads."
   ::= { fpBufferEntry 1 }

fpBUFBreads OBJECT-TYPE
   SYNTAX INTEGER
   ACCESS read-only
   STATUS mandatory
   DESCRIPTION
          "Number of breads doing sp-read."
   ::= { fpBufferEntry 2 }

fpBUFLwrites OBJECT-TYPE
   SYNTAX INTEGER
   ACCESS read-only
   STATUS mandatory
   DESCRIPTION
          "Number of buffered writes (incl. delayed)."
   ::= { fpBufferEntry 3 }

fpBUFBwrites OBJECT-TYPE
   SYNTAX INTEGER
   ACCESS read-only
   STATUS mandatory
   DESCRIPTION
          "Number of bwrites doing sp-write."
   ::= { fpBufferEntry 4 }

fpBUFIOwaits OBJECT-TYPE
   SYNTAX INTEGER
   ACCESS read-only
   STATUS mandatory
   DESCRIPTION
          "Number of processes blocked in biowait."
   ::= { fpBufferEntry 5 }

fpBUFResid OBJECT-TYPE
   SYNTAX INTEGER
   ACCESS read-only
   STATUS mandatory
   DESCRIPTION
          "Running total of unused buf memory."
   ::= { fpBufferEntry 6 }

fpBUFBufsize OBJECT-TYPE
   SYNTAX INTEGER
   ACCESS read-only
   STATUS mandatory
   DESCRIPTION
          "Running total of memory on free list."
   ::= { fpBufferEntry 7 }

fpBUFBcount OBJECT-TYPE
   SYNTAX INTEGER
   ACCESS read-only
   STATUS mandatory
   DESCRIPTION
          "Running total of memory on hash lists."
   ::= { fpBufferEntry 8 }



  --
  --
  --fpInodeStatTable
  --
  --

fpInodeTable OBJECT-TYPE
   SYNTAX SEQUENCE OF FPInodeEntry
   ACCESS not-accessible
   STATUS mandatory
   DESCRIPTION
          "Inode table displays the Inode Statistics for all FSPs. 
	   Inode is part of StackOS module."
   ::= { fpHTFS 4 }

fpInodeEntry OBJECT-TYPE
   SYNTAX FPInodeEntry
   ACCESS not-accessible
   STATUS mandatory
   DESCRIPTION
          "Each entry in the table displays Inode Statistics for a FSP."
   INDEX { fspIndex }
   ::= { fpInodeTable 1 }

FPInodeEntry ::= SEQUENCE {
        fpINODEIgetcalls         INTEGER,
        fpFoundinodes            INTEGER,
        fpTotalinodes            INTEGER,
        fpGoneinodes             INTEGER,
        fpFreeinodes             INTEGER,
        fpCacheinodes            INTEGER,
        fpSyncinodes             INTEGER
}


fpINODEIgetcalls OBJECT-TYPE
   SYNTAX INTEGER
   ACCESS read-only
   STATUS mandatory
   DESCRIPTION
          "Number of calls to htfs-iget."
   ::= { fpInodeEntry 1 }

fpFoundinodes OBJECT-TYPE
   SYNTAX INTEGER
   ACCESS read-only
   STATUS mandatory
   DESCRIPTION
          "Inode cache hits."
   ::= { fpInodeEntry 2 }

fpTotalinodes OBJECT-TYPE
   SYNTAX INTEGER
   ACCESS read-only
   STATUS mandatory
   DESCRIPTION
          "Total number of inodes in memory."
   ::= { fpInodeEntry 3 }

fpGoneinodes OBJECT-TYPE
   SYNTAX INTEGER
   ACCESS read-only
   STATUS mandatory
   DESCRIPTION
          "Number of inodes on gone list."
   ::= { fpInodeEntry 4 }

fpFreeinodes OBJECT-TYPE
   SYNTAX INTEGER
   ACCESS read-only
   STATUS mandatory
   DESCRIPTION
          "Number of inodes on free list."
   ::= { fpInodeEntry 5 }

fpCacheinodes OBJECT-TYPE
   SYNTAX INTEGER
   ACCESS read-only
   STATUS mandatory
   DESCRIPTION
          "Number of inodes on cache list."
   ::= { fpInodeEntry 6 }

fpSyncinodes OBJECT-TYPE
   SYNTAX INTEGER
   ACCESS read-only
   STATUS mandatory
   DESCRIPTION
          "Number of inodes on sync list."
   ::= { fpInodeEntry 7 }


  --
  -- axSP Group
  -- 
  --


-- ----------------------------------------------------------------------
---
-- textual conventions for enterprise-standard enumerated types
-- ----------------------------------------------------------------------
---

RaidLevel ::= TEXTUAL-CONVENTION
        STATUS  current
        DESCRIPTION
                 "Defines the type of Raid Level present in the system"
        SYNTAX  INTEGER {
                raid0(0),
                raid1(1),
                raid3(3),
                raid5(5),
                raid6(6),
                raid7(7)
        }


RebuildFlag ::= TEXTUAL-CONVENTION
        STATUS  current
        DESCRIPTION
                 "Defines the Rebuild Flag type."
        SYNTAX  INTEGER {
                none(0),
                autorebuild(1),
                manualrebuild(2),
                check(3),
                expandcapacity(4),
                phydevfailed(240),
                logdevfailed(241),
                justfailed(242),
                canceled(243),
                expandcapacityfailed(244),
                autorebuildfailed(255)
        }


BusType ::= TEXTUAL-CONVENTION
        STATUS  current
        DESCRIPTION
                 "Defines Bus type."
        SYNTAX  INTEGER {
                eisa(1),
                mca(2),
                pci(3),
                vesa(4),
                isa(5),
                scsi(6)
        }



ControllerType ::= TEXTUAL-CONVENTION
        STATUS  current
        DESCRIPTION
                 "This textual Convention defines the type of Controller."
        SYNTAX  INTEGER {
                dac960E(1),
                dac960M(8),
                dac960PD(16),
                dac960PL(17),
                dac960PDU(18),
                dac960PE(19),
                dac960PG(20),
                dac960PJ(21),
                dac960PTL(22),
                dac960PR(23),
                dac960PRL(24),
                dac960PT(25),
                dac1164P(26),
                dacI20(80),
                dac960S(96),
                dac960SU(97),
                dac960SX(98),
                dac960SF(99),
                dac960FL(100),
                hba440(129),
                hba440C(130),
                hba445(131),
                hba445C(132),
                hba440xC(133),
                hba445S(134),
                hba640(136),
                hba640A(137),
                hba446(138),
                hba446D(139),
                hba446S(140),
                hba742(144),
                hba742A(145),
                hba747(146),
                hba747D(147),
                hba747S(148),
                hba74xC(149),
                hba757(150),
                hba757D(151),
                hba757S(152),
                hba757CD(153),
                hba75xC(154),
                hba747C(155),
                hba757C(156),
                hba540(160),
                hba540C(161),
                hba542(162),
                hba542B(163),
                hba542C(164),
                hba542D(165),
                hba545(166),
                hba545C(167),
                hba545S(168),
                hba54xC(169),
                hba946(176),
                hba946C(177),
                hba948(178),
                hba948C(179),
                hba956(180),
                hba956C(181),
                hba958(182),
                hba958C(183),
                hba958D(184),
                hba956CD(185),
                hba958CD(186),
                hba930(192),
                hba932(193),
                hba950(194),
                hba952(195)
        }


VendorName ::= TEXTUAL-CONVENTION
        STATUS  current
        DESCRIPTION
                 "Name of the Vendors"
        SYNTAX  INTEGER {
                mylex(0),
                ibm(1),
                hp(2),
                dec(3),
                att(4),
                dell(5),
                nec(6),
                sni(7),
                ncr(8)
        }

U08Bits ::= TEXTUAL-CONVENTION
        STATUS  current
        DESCRIPTION
                 "Integer type of range 0..255"
        SYNTAX  INTEGER (0..255)

U16Bits ::= TEXTUAL-CONVENTION
        STATUS  current
        DESCRIPTION
                 "Integer type of range 0..65535"
        SYNTAX  INTEGER (0..65535)       
        
-- The JNI adapter logical statistics table

fabLogDevTable OBJECT-TYPE
       SYNTAX SEQUENCE OF FABLogDevEntry
       ACCESS not-accessible
       STATUS mandatory
       DESCRIPTION
                "This table contains information for logical devices."
       ::= { fabRaid 1 }
     
fabLogDevEntry OBJECT-TYPE
       SYNTAX FABLogDevEntry         
       ACCESS not-accessible
       STATUS mandatory 
       DESCRIPTION
       			"Entry for each logical device"
       INDEX { fspIndex, ldIndex }
       	::= { fabLogDevTable 1 }
       	
FABLogDevEntry ::= SEQUENCE {
		ldIndex 		INTEGER,
		ldSectorReads 	U16Bits,
		ldWBufReads		U16Bits,
		ldSectorWrites	U16Bits,
		ldReadIO		U16Bits,
		ldWriteIO		U16Bits,
		ldMediaErrors	U16Bits,
		ldDriveErrors	U16Bits,
		ldTotalTime		U16Bits
		}

ldIndex OBJECT-TYPE
       SYNTAX INTEGER 
       ACCESS read-only
       STATUS mandatory
       DESCRIPTION
       		" Index of the logical device" 
       	::= {fabLogDevEntry 1} 			

ldSectorReads OBJECT-TYPE
       SYNTAX INTEGER 
       ACCESS read-only
       STATUS mandatory
       DESCRIPTION
       		" Number of sectors read " 
       	::= {fabLogDevEntry 2}	

ldWBufReads OBJECT-TYPE
       SYNTAX INTEGER 
       ACCESS read-only
       STATUS mandatory
       DESCRIPTION           
       		" Number of sectors read from WBUF " 
       	::= {fabLogDevEntry 3}
       	
ldSectorWrites OBJECT-TYPE
       SYNTAX INTEGER 
       ACCESS read-only
       STATUS mandatory
       DESCRIPTION
       		"Number of sector writes " 
       	::= {fabLogDevEntry 4}

ldReadIO OBJECT-TYPE
       SYNTAX INTEGER 
       ACCESS read-only
       STATUS mandatory
       DESCRIPTION
       		"Number of read IO's " 
       	::= {fabLogDevEntry 5}

ldWriteIO OBJECT-TYPE
       SYNTAX INTEGER 
       ACCESS read-only
       STATUS mandatory
       DESCRIPTION
       		"Number of write IO's " 
       	::= {fabLogDevEntry 6}

ldMediaErrors OBJECT-TYPE
       SYNTAX INTEGER 
       ACCESS read-only
       STATUS mandatory
       DESCRIPTION
       		"Number of media errors " 
       	::= {fabLogDevEntry 7}

ldDriveErrors OBJECT-TYPE
       SYNTAX INTEGER 
       ACCESS read-only
       STATUS mandatory
       DESCRIPTION
       		"Number of drive errors " 
       	::= {fabLogDevEntry 8}

ldTotalTime OBJECT-TYPE
       SYNTAX INTEGER 
       ACCESS read-only
       STATUS mandatory
       DESCRIPTION
       		"Total time for the logical device"
	   ::= {fabLogDevEntry 9}	
		
       



-- The fabric adapter table --
   
fabAdptTable OBJECT-TYPE
       SYNTAX SEQUENCE OF FABAdptEntry
       ACCESS not-accessible
       STATUS mandatory
       DESCRIPTION
                "Table containing information for all fibre channel adapters 
                information on the Auspex IO node"
       ::= { axFab 1 }
       
fabAdptEntry OBJECT-TYPE 
       SYNTAX FABAdptEntry
       ACCESS not-accessible
       STATUS mandatory
       DESCRIPTION
       			"Entry for each fibre channel adapter"
       INDEX { fspIndex, fabIndex }
       ::= { fabAdptTable 1 }
       
FABAdptEntry ::=  SEQUENCE {
		fabIndex		INTEGER,  
		fabPCIBusNum		U16Bits,
		fabSlotNum      	U16Bits,
		fabIntLine		U16Bits,
		fabIntPin		U16Bits,
		fabType			U16Bits,
		fabVendorId		U16Bits,
		fabDeviceId		U16Bits,
		fabRevisionId		U16Bits,
		fabWWN			DisplayString,
		fabNumOfTargets 	U16Bits,
		fabAdptNumber		U08Bits
		}

fabIndex OBJECT-TYPE
       SYNTAX INTEGER 
       ACCESS read-only
       STATUS mandatory
       DESCRIPTION 
		"Fabric adapter index"
       ::= { fabAdptEntry 1 }
 
fabPCIBusNum OBJECT-TYPE
       SYNTAX U16Bits 
       ACCESS read-only
       STATUS mandatory
       DESCRIPTION 
		"Fabric adapter PCI BUS number"
       ::= { fabAdptEntry 2 }
       
fabSlotNum OBJECT-TYPE
       SYNTAX U16Bits 
       ACCESS read-only
       STATUS mandatory
       DESCRIPTION 
		"Fabric adapter Slot number"
       ::= { fabAdptEntry 3 }

fabIntLine OBJECT-TYPE
       SYNTAX U16Bits 
       ACCESS read-only
       STATUS mandatory
       DESCRIPTION 
		"Fabric adapter Interrupt line"
       ::= { fabAdptEntry 4 }
       
fabIntPin OBJECT-TYPE
       SYNTAX U16Bits 
       ACCESS read-only
       STATUS mandatory
       DESCRIPTION 
		"Fabric adapter Interrupt pin"
       ::= { fabAdptEntry 5 }
       
fabType OBJECT-TYPE
       SYNTAX U16Bits 
       ACCESS read-only
       STATUS mandatory
       DESCRIPTION 
		"Fabric adapter Type"
       ::= { fabAdptEntry 6 }
      
fabVendorId OBJECT-TYPE
       SYNTAX U16Bits 
       ACCESS read-only
       STATUS mandatory
       DESCRIPTION 
		"Fabric adapter Vendor ID"
       ::= { fabAdptEntry 7 }

fabDeviceId OBJECT-TYPE
       SYNTAX U16Bits
       ACCESS read-only
       STATUS mandatory
       DESCRIPTION 
		"Fabric adapter Device ID"
       ::= { fabAdptEntry 8 }
       
fabRevisionId OBJECT-TYPE
       SYNTAX U16Bits
       ACCESS read-only
       STATUS mandatory
       DESCRIPTION 
		"Fabric adapter Revision ID"
       ::= { fabAdptEntry 9 }   
    
fabWWN OBJECT-TYPE
       SYNTAX DisplayString 
       ACCESS read-only
       STATUS mandatory
       DESCRIPTION 
		"Fabric adapter World Wide Number"
       ::= { fabAdptEntry 10 }   

fabNumOfTargets OBJECT-TYPE
       SYNTAX U16Bits 
       ACCESS read-only
       STATUS mandatory
       DESCRIPTION 
		"Number of targets found for the adapter"
       ::= { fabAdptEntry 11 }   
       
fabAdptNumber OBJECT-TYPE
       SYNTAX U08Bits 
       ACCESS read-only
       STATUS mandatory
       DESCRIPTION 
		"Fabric adapter Number"
       ::= { fabAdptEntry 12 }   

fabTargetTable OBJECT-TYPE
       SYNTAX SEQUENCE OF FABTargetEntry
       ACCESS not-accessible
       STATUS mandatory
       DESCRIPTION
                "Table containing information for all fibre channel adapters 
                information on the Auspex IO node"
       ::= { axFab 2 }
       
fabTargetEntry OBJECT-TYPE 
       SYNTAX FABTargetEntry
       ACCESS not-accessible
       STATUS mandatory
       DESCRIPTION
       			"Entry for each fibre channel adapter"
       INDEX { fspIndex, fabTargetIndex }
       ::= { fabTargetTable 1 }
       
FABTargetEntry ::=  SEQUENCE {                                                
		fabTargetIndex		INTEGER,
		fabTargetAdapterNum	U08Bits,
		fabTargetNumber		U16Bits,		-- Target number starts from 0
		fabTargetWWN		DisplayString,
		fabTargetPortWWN	DisplayString,
		fabTargetAliasName	DisplayString,
		fabTargetType		U08Bits,
		fabTargetNumOfLuns	U16Bits
		}
                                    
fabTargetIndex OBJECT-TYPE
	SYNTAX INTEGER
	ACCESS read-only
	STATUS mandatory
	DESCRIPTION
			"The Fabric target adapter index "
	::= { fabTargetEntry 1 }                                    
	
fabTargetAdapterNum OBJECT-TYPE
	SYNTAX U08Bits
	ACCESS read-only
	STATUS mandatory
	DESCRIPTION 
			"The fabric target Adapter number"
	::= { fabTargetEntry 2 }
	
fabTargetNumber OBJECT-TYPE
	SYNTAX U16Bits
	ACCESS read-only
	STATUS mandatory
	DESCRIPTION 
			"The fabric target number"
	::= { fabTargetEntry 3 }    
	
fabTargetWWN OBJECT-TYPE
	SYNTAX DisplayString
	ACCESS read-only
	STATUS mandatory
	DESCRIPTION 
			"The fabric target WWN number"
	::= { fabTargetEntry 4 }
 
fabTargetPortWWN OBJECT-TYPE
	SYNTAX DisplayString
	ACCESS read-only
	STATUS mandatory
	DESCRIPTION 
			"The fabric target Port WWN number"
	::= { fabTargetEntry 5 }
	
fabTargetAliasName OBJECT-TYPE
	SYNTAX DisplayString
	ACCESS read-only
	STATUS mandatory
	DESCRIPTION 
			"The fabric target Alias Name"
	::= { fabTargetEntry 6 }
	
fabTargetType OBJECT-TYPE
	SYNTAX INTEGER      
		   {
		   		disk (1),
		   		other (2)
		   	}
	ACCESS read-only
	STATUS mandatory
	DESCRIPTION 
			"The fabric target Type disk - other "
	::= { fabTargetEntry 7 }

fabTargetNumOfLuns OBJECT-TYPE
	SYNTAX U16Bits
	ACCESS read-only
	STATUS mandatory
	DESCRIPTION 
			"The number of luns on the target"
	::= { fabTargetEntry 8 }
	

fabLunTable OBJECT-TYPE
       SYNTAX SEQUENCE OF FABLunEntry
       ACCESS not-accessible
       STATUS mandatory
       DESCRIPTION
                "Table containing information for all Luns "
       ::= { axFab 3 }
       
fabLunEntry OBJECT-TYPE 
       SYNTAX FABLunEntry
       ACCESS not-accessible
       STATUS mandatory
       DESCRIPTION
       			"Entry for each Lun"
       INDEX { fspIndex, fabLunIndex }
       ::= { fabLunTable 1 }
       
FABLunEntry ::=  SEQUENCE {                                                
		fabLunIndex			INTEGER,
		fabLunNumber		U16Bits,
		fabLunAdptNumber	U08Bits,
		fabLunTarNumber		U16Bits,
		fabLunWWN			DisplayString,
		fabLunType			U08Bits,
		fabLunSize			INTEGER,
		fabLunMap			U08Bits		
		}

fabLunIndex OBJECT-TYPE
	SYNTAX INTEGER
	ACCESS read-only
	STATUS mandatory
	DESCRIPTION 
			"Unique Lun identifier"
	::= { fabLunEntry 1 }
	

fabLunNumber OBJECT-TYPE
	SYNTAX U16Bits
	ACCESS read-only
	STATUS mandatory
	DESCRIPTION 
			" Lun Number "
	::= { fabLunEntry 2 }


fabLunAdptNumber OBJECT-TYPE
	SYNTAX U08Bits
	ACCESS read-only
	STATUS mandatory
	DESCRIPTION 
			"The adapter number for the lun"
	::= { fabLunEntry 3 }                  
	

fabLunTarNumber OBJECT-TYPE
	SYNTAX U16Bits
	ACCESS read-only
	STATUS mandatory
	DESCRIPTION 
			"The Target number for the lun"
	::= { fabLunEntry 4 }


fabLunWWN OBJECT-TYPE
	SYNTAX DisplayString
	ACCESS read-only
	STATUS mandatory
	DESCRIPTION 
			"The worldwide number for the lun"
	::= { fabLunEntry 5 }
	

fabLunType OBJECT-TYPE
	SYNTAX U08Bits
	ACCESS read-only
	STATUS mandatory
	DESCRIPTION 
			"The type of the lun"
	::= { fabLunEntry 6 }
	

fabLunSize OBJECT-TYPE
	SYNTAX INTEGER
	ACCESS read-only
	STATUS mandatory
	DESCRIPTION 
			"The size of the lun"
	::= { fabLunEntry 7 }
	

fabLunMap OBJECT-TYPE
	SYNTAX INTEGER
		   {
		   		unmapped (0),
		   		mapped (1)
		   }
	ACCESS read-only
	STATUS mandatory
	DESCRIPTION 
			"Identifier for the lun mapping"
	::= { fabLunEntry 8 }          

fabLunMapTable OBJECT-TYPE
       SYNTAX SEQUENCE OF FABLunMapEntry
       ACCESS not-accessible
       STATUS mandatory
       DESCRIPTION
                "Table containing mapping information for all Luns "
       ::= { axFab 4 }
       
fabLunMapEntry OBJECT-TYPE 
       SYNTAX FABLunMapEntry
       ACCESS not-accessible
       STATUS mandatory
       DESCRIPTION
       			"Entry for each mapped Lun"
       INDEX { fspIndex, fabLunMapIndex }
       ::= { fabLunMapTable 1 }
       
FABLunMapEntry ::=  SEQUENCE {                                                
		fabLunMapIndex		INTEGER,
		fabLunMNumber		U16Bits,
		fabLunAlias			DisplayString,
		fabLunMapWWN		DisplayString,
		fabLunLabel			U08Bits
		}

fabLunMapIndex OBJECT-TYPE
	SYNTAX INTEGER
	ACCESS read-only
	STATUS mandatory
	DESCRIPTION 
			"Unique Mapped Lun identifier"
	::= { fabLunMapEntry 1 }
	

fabLunMNumber OBJECT-TYPE
	SYNTAX U16Bits
	ACCESS read-only
	STATUS mandatory
	DESCRIPTION 
			" Mapped Lun Number "
	::= { fabLunMapEntry 2 }


fabLunAlias OBJECT-TYPE
	SYNTAX DisplayString
	ACCESS read-only
	STATUS mandatory
	DESCRIPTION 
			"The Alias name associated with the lun"
	::= { fabLunMapEntry 3 }                  
	

fabLunMapWWN OBJECT-TYPE
	SYNTAX DisplayString
	ACCESS read-only
	STATUS mandatory
	DESCRIPTION 
			"The WWN associated with the lun"
	::= { fabLunMapEntry 4 }


fabLunLabel OBJECT-TYPE
	SYNTAX INTEGER 
			{ unlabelled (0),
			  labelled (1),
			  labelledactive (2)
			}
	ACCESS read-only
	STATUS mandatory
	DESCRIPTION 
			"The label of the lun"
	::= { fabLunMapEntry 5 }


trapFSFull        	OBJECT IDENTIFIER ::= { axTrapData 1 }
trapFSDegradation   	OBJECT IDENTIFIER ::= { axTrapData 2 }
trapDiskUpdation  	OBJECT IDENTIFIER ::= { axTrapData 3 }
trapFCAdptLinkFailure	OBJECT IDENTIFIER ::= {axTrapData 4 }
trapFCAdptLinkUp		OBJECT IDENTIFIER ::= {axTrapData 5 }
trapFCLossOfLinkFailure	OBJECT IDENTIFIER ::= {axTrapData 6 }
trapLunDisappear		OBJECT IDENTIFIER ::= {axTrapData 7 }
trapLunSizeChange		OBJECT IDENTIFIER ::= {axTrapData 8 }

         
trapFSFullMsg OBJECT-TYPE
       SYNTAX DisplayString
       ACCESS read-only
       STATUS mandatory
       DESCRIPTION
                "Name of the file system which got full and 
		 for which fileSystemFull trap has to be sent."
       ::= { trapFSFull 1 }

trapFSFullTimeStamp OBJECT-TYPE
       SYNTAX TimeTicks
       ACCESS read-only
       STATUS mandatory
       DESCRIPTION
                "Time at which file system identified by trapFSFullMsg got full."
       ::= { trapFSFull 2 }


trapFSDegradationMsg OBJECT-TYPE
       SYNTAX DisplayString
       ACCESS read-only
       STATUS mandatory
       DESCRIPTION
                "Name of the file system which got degraded and 
		 for which fileSystemDegradation trap has to be sent."
       ::= { trapFSDegradation 1 }

trapFSDegradationTimeStamp OBJECT-TYPE
       SYNTAX TimeTicks
       ACCESS read-only
       STATUS mandatory
       DESCRIPTION
                "Time at which file system identified by 
		 trapFSDegradationMsg got degraded."
       ::= { trapFSDegradation 2 }


trapDiskMsg OBJECT-TYPE
       SYNTAX DisplayString
       ACCESS read-only
       STATUS mandatory
       DESCRIPTION
                "Name of the disk which got removed from the system and 
		 for which diskStackUpdation trap has to be sent."
       ::= { trapDiskUpdation 1 }

trapDiskTimeStamp OBJECT-TYPE
       SYNTAX TimeTicks
       ACCESS read-only
       STATUS mandatory
       DESCRIPTION
                "Time at which disk identified by trapDiskIndex 
		 was added/removed."
       ::= { trapDiskUpdation 2 }

trapFCAdptLinkFailureMsg OBJECT-TYPE
       SYNTAX DisplayString
       ACCESS read-only
       STATUS mandatory
       DESCRIPTION
                "Name of the fibre channel adapter on which link
                failure occured."
       ::= { trapFCAdptLinkFailure 1 }

trapFCAdptLinkFailureTimeStamp OBJECT-TYPE
       SYNTAX TimeTicks
       ACCESS read-only
       STATUS mandatory
       DESCRIPTION
                "Time at which the fibre channel adapter link failure occured."
       ::= { trapFCAdptLinkFailure 2 }
   
trapFCAdptLinkUpMsg OBJECT-TYPE
       SYNTAX DisplayString
       ACCESS read-only
       STATUS mandatory
       DESCRIPTION
                "Name of the fibre channel adapter on which link
                up occured."
       ::= { trapFCAdptLinkUp 1 }

trapFCAdptLinkUpTimeStamp OBJECT-TYPE
       SYNTAX TimeTicks
       ACCESS read-only
       STATUS mandatory
       DESCRIPTION
                "Time at which the fibre channel adapter link up occured."
       ::= { trapFCAdptLinkUp 2 }
      

trapFCLossOfLinkFailureMsg OBJECT-TYPE
       SYNTAX DisplayString
       ACCESS read-only
       STATUS mandatory
       DESCRIPTION
                "Name of the SD device which had complete loss of link."
       ::= { trapFCLossOfLinkFailure 1 }

trapFCLossOfLinkFailureTimeStamp OBJECT-TYPE
       SYNTAX TimeTicks
       ACCESS read-only
       STATUS mandatory
       DESCRIPTION
                "Time at which complete loss of link occured."
       ::= { trapFCLossOfLinkFailure 2 }
 
trapLunDisappearMsg OBJECT-TYPE
       SYNTAX DisplayString
       ACCESS read-only
       STATUS mandatory
       DESCRIPTION
                "Mapped lun which disappeared"
       ::= { trapLunDisappear 1 }

trapLunDisappearTimeStamp OBJECT-TYPE
       SYNTAX TimeTicks
       ACCESS read-only
       STATUS mandatory
       DESCRIPTION
                "Time at which mapped lun disappeared"
       ::= { trapLunDisappear 2 }

trapLunSizeChangeMsg OBJECT-TYPE
       SYNTAX DisplayString
       ACCESS read-only
       STATUS mandatory
       DESCRIPTION
                "Mapped lun whose lun size changed"
       ::= { trapLunSizeChange 1 }

trapLunSizeChangeTimeStamp OBJECT-TYPE
       SYNTAX TimeTicks
       ACCESS read-only
       STATUS mandatory
       DESCRIPTION
                "Time at which mapped lun size changed"
       ::= { trapLunSizeChange 2 }                                                                             
   
-- TRAPS

   fileSystemFullTrap TRAP-TYPE
       ENTERPRISE  auspex
       VARIABLES   { trapFSFullMsg, trapFSFullTimeStamp }
       DESCRIPTION
                "Trap indicating that a file system got full."
       REFERENCE
               "None"
       ::= 1

   fileSystemDegradationTrap TRAP-TYPE
       ENTERPRISE  auspex
       VARIABLES   { trapFSDegradationMsg, trapFSDegradationTimeStamp }
       DESCRIPTION
                "Trap indicating that a file system got degradated."
       REFERENCE
               "None"
       ::= 2 

   diskStackUpdationTrap TRAP-TYPE
       ENTERPRISE  auspex
       VARIABLES   { trapDiskMsg, trapDiskTimeStamp }
       DESCRIPTION
                "Trap indicating that a disk was removed."
       REFERENCE
               "None"
       ::= 3 
    
   fcLinkFailureTrap TRAP-TYPE
       ENTERPRISE  auspex
       VARIABLES   { trapFCAdptLinkFailureMsg, trapFCAdptLinkFailureTimeStamp }
       DESCRIPTION
                "Trap indicating that a adapter link failure occured."
       REFERENCE
               "None"
       ::= 4
    
   fcLinkUpTrap TRAP-TYPE
       ENTERPRISE  auspex
       VARIABLES   { trapFCAdptLinkUpMsg , trapFCAdptLinkUpTimeStamp }
       DESCRIPTION
                "Trap indicating that a adapter link up occured."
       REFERENCE
               "None"
       ::= 5
       
    fcCompleteLossTrap TRAP-TYPE
       ENTERPRISE  auspex
       VARIABLES   { trapFCLossOfLinkFailureMsg, trapFCLossOfLinkFailureTimeStamp }
       DESCRIPTION
                "Trap indicating that complete loss of link occured."
       REFERENCE
               "None"
       ::= 6
       
    lunDisappearTrap TRAP-TYPE
       ENTERPRISE  auspex
       VARIABLES   { trapLunDisappearMsg, trapLunDisappearTimeStamp }
       DESCRIPTION
                "Trap indicating that a mapped lun disappeared."
       REFERENCE
               "None"
       ::= 7
       
    lunSizeChangeTrap TRAP-TYPE
       ENTERPRISE  auspex
       VARIABLES   { trapLunSizeChangeMsg, trapLunSizeChangeTimeStamp }
       DESCRIPTION
                "Trap indicating that lun size change occured on a mapped lun."
       REFERENCE
               "None"
       ::= 8


   host     OBJECT IDENTIFIER ::= { mib-2 25 }

   hrSystem        OBJECT IDENTIFIER ::= { host 1 }
   hrStorage       OBJECT IDENTIFIER ::= { host 2 }
   hrDevice        OBJECT IDENTIFIER ::= { host 3 }


   -- textual conventions

   -- a truth value
   Boolean ::=   INTEGER { true(1), false(2) }


   -- memory size, expressed in units of 1024bytes
   KBytes ::=    INTEGER (0..2147483647)

   -- This textual convention is intended to identify the manufacturer,
   -- model, and version of a specific hardware or software product.
   -- It is suggested that these OBJECT IDENTIFIERs are allocated such
   -- that all products from a particular manufacturer are registered
   -- under a subtree distinct to that manufacturer.  In addition, all




   -- versions of a product should be registered under a subtree
   -- distinct to that product.  With this strategy, a management
   -- station may uniquely determine the manufacturer and/or model of a
   -- product whose productID is unknown to the management station.
   -- Objects of this type may be useful for inventory purposes or for
   -- automatically detecting incompatibilities or version mismatches
   -- between various hardware and software components on a system.
   ProductID ::= OBJECT IDENTIFIER
   -- unknownProduct will be used for any unknown ProductID
   -- unknownProduct OBJECT IDENTIFIER ::= { 0 0 }

   -- For example, the product ID for the ACME 4860 66MHz clock doubled
   -- processor might be:
   -- enterprises.acme.acmeProcessors.a4860DX2.MHz66
   -- A software product might be registered as:
   -- enterprises.acme.acmeOperatingSystems.acmeDOS.six(6).one(1)


   DateAndTime ::= OCTET STRING (SIZE (8 | 11))
   --        A date-time specification for the local time of day.
   --        This data type is intended to provide a consistent
   --        method of reporting date information.
   --
   --            field  octets  contents                  range
   --            =====  ======  =========                 =====
   --              1      1-2   year                      0..65536
   --                           (in network byte order)
   --              2       3    month                     1..12
   --              3       4    day                       1..31
   --              4       5    hour                      0..23
   --              5       6    minutes                   0..59
   --              6       7    seconds                   0..60
   --                           (use 60 for leap-second)
   --              7       8    deci-seconds              0..9
   --              8       9    direction from UTC        "+" / "-"
   --                           (in ascii notation)
   --              9      10    hours from UTC            0..11
   --             10      11    minutes from UTC          0..59
   --
   --            Note that if only local time is known, then
   --            timezone information (fields 8-10) is not present.

   InternationalDisplayString ::= OCTET STRING
   --  This data type is used to model textual information in some
   --  character set.  A network management station should use a local
   --  algorithm to determine which character set is in use and how it
   --  should be displayed.  Note that this character set may be encoded
   --  with more than one octet per symbol, but will most often be NVT




   --  ASCII.


   -- The Host Resources System Group
   --
   -- Implementation of this group is mandatory for all host systems.
   hrSystemUptime OBJECT-TYPE
       SYNTAX TimeTicks
       ACCESS read-only
       STATUS mandatory
       DESCRIPTION
              "The amount of time since this host was last
              initialized.  Note that this is different from
              sysUpTime in MIB-II [3] because sysUpTime is the
              uptime of the network management portion of the
              system."
       ::= { hrSystem 1 }

   hrSystemDate OBJECT-TYPE
       SYNTAX DateAndTime
       ACCESS read-write
       STATUS mandatory
       DESCRIPTION
              "The host's notion of the local date and time of
              day."
       ::= { hrSystem 2 }

   hrSystemInitialLoadDevice OBJECT-TYPE
       SYNTAX INTEGER (1..2147483647)
       ACCESS read-write
       STATUS mandatory
       DESCRIPTION
              "The index of the hrDeviceEntry for the device from
              which this host is configured to load its initial
              operating system configuration."
       ::= { hrSystem 3 }

   hrSystemInitialLoadParameters OBJECT-TYPE
       SYNTAX InternationalDisplayString (SIZE (0..128))
       ACCESS read-write
       STATUS mandatory
       DESCRIPTION
              "This object contains the parameters (e.g. a
              pathname and parameter) supplied to the load device
              when requesting the initial operating system
              configuration from that device."
       ::= { hrSystem 4 }





   hrSystemNumUsers OBJECT-TYPE
       SYNTAX Gauge
       ACCESS read-only
       STATUS mandatory
       DESCRIPTION
              "The number of user sessions for which this host is
              storing state information.  A session is a
              collection of processes requiring a single act of
              user authentication and possibly subject to
              collective job control."
       ::= { hrSystem 5 }

   hrSystemProcesses OBJECT-TYPE
       SYNTAX Gauge
       ACCESS read-only
       STATUS mandatory
       DESCRIPTION
              "The number of process contexts currently loaded or
              running on this system."
       ::= { hrSystem 6 }

   hrSystemMaxProcesses OBJECT-TYPE
       SYNTAX INTEGER (0..2147483647)
       ACCESS read-only
       STATUS mandatory
       DESCRIPTION
              "The maximum number of process contexts this system
              can support.  If there is no fixed maximum, the
              value should be zero.  On systems that have a fixed
              maximum, this object can help diagnose failures
              that occur when this maximum is reached."
       ::= { hrSystem 7 }


   -- The Host Resources Storage Group
   --
   -- Implementation of this group is mandatory for all host systems.

   -- Registration for some storage types, for use with hrStorageType
   hrStorageTypes          OBJECT IDENTIFIER ::= { hrStorage 1 }
   hrStorageOther          OBJECT IDENTIFIER ::= { hrStorageTypes 1 }
   hrStorageRam            OBJECT IDENTIFIER ::= { hrStorageTypes 2 }
   -- hrStorageVirtualMemory is temporary storage of swapped
   -- or paged memory
   hrStorageVirtualMemory  OBJECT IDENTIFIER ::= { hrStorageTypes 3 }
   hrStorageFixedDisk      OBJECT IDENTIFIER ::= { hrStorageTypes 4 }
   hrStorageRemovableDisk  OBJECT IDENTIFIER ::= { hrStorageTypes 5 }
   hrStorageFloppyDisk     OBJECT IDENTIFIER ::= { hrStorageTypes 6 }




   hrStorageCompactDisc    OBJECT IDENTIFIER ::= { hrStorageTypes 7 }
   hrStorageRamDisk        OBJECT IDENTIFIER ::= { hrStorageTypes 8 }

   hrMemorySize OBJECT-TYPE
       SYNTAX KBytes
       ACCESS read-only
       STATUS mandatory
       DESCRIPTION
              "The amount of physical main memory contained by
              the host."
       ::= { hrStorage 2 }


   hrStorageTable OBJECT-TYPE
       SYNTAX SEQUENCE OF HrStorageEntry
       ACCESS not-accessible
       STATUS mandatory
       DESCRIPTION
              "The (conceptual) table of logical storage areas on
              the host.

              An entry shall be placed in the storage table for
              each logical area of storage that is allocated and
              has fixed resource limits.  The amount of storage
              represented in an entity is the amount actually
              usable by the requesting entity, and excludes loss
              due to formatting or file system reference
              information.

              These entries are associated with logical storage
              areas, as might be seen by an application, rather
              than physical storage entities which are typically
              seen by an operating system.  Storage such as tapes
              and floppies without file systems on them are
              typically not allocated in chunks by the operating
              system to requesting applications, and therefore
              shouldn't appear in this table.  Examples of valid
              storage for this table include disk partitions,
              file systems, ram (for some architectures this is
              further segmented into regular memory, extended
              memory, and so on), backing store for virtual
              memory (`swap space').

              This table is intended to be a useful diagnostic
              for `out of memory' and `out of buffers' types of
              failures.  In addition, it can be a useful
              performance monitoring tool for tracking memory,
              disk, or buffer usage."




       ::= { hrStorage 3 }

   hrStorageEntry OBJECT-TYPE
       SYNTAX HrStorageEntry
       ACCESS not-accessible
       STATUS mandatory
       DESCRIPTION
              "A (conceptual) entry for one logical storage area
              on the host.  As an example, an instance of the
              hrStorageType object might be named
              hrStorageType.3"
       INDEX { hrStorageIndex }
       ::= { hrStorageTable 1 }

   HrStorageEntry ::= SEQUENCE {
           hrStorageIndex               INTEGER,
           hrStorageType                OBJECT IDENTIFIER,
           hrStorageDescr               DisplayString,
           hrStorageAllocationUnits     INTEGER,
           hrStorageSize                INTEGER,
           hrStorageUsed                INTEGER,
           hrStorageAllocationFailures  Counter
       }

   hrStorageIndex OBJECT-TYPE
       SYNTAX INTEGER (1..2147483647)
       ACCESS read-only
       STATUS mandatory
       DESCRIPTION
              "A unique value for each logical storage area
              contained by the host."
       ::= { hrStorageEntry 1 }

   hrStorageType OBJECT-TYPE
       SYNTAX OBJECT IDENTIFIER
       ACCESS read-only
       STATUS mandatory
       DESCRIPTION
              "The type of storage represented by this entry."
       ::= { hrStorageEntry 2 }

   hrStorageDescr OBJECT-TYPE
       SYNTAX DisplayString
       ACCESS read-only
       STATUS mandatory
       DESCRIPTION
              "A description of the type and instance of the
              storage described by this entry."




       ::= { hrStorageEntry 3 }

   hrStorageAllocationUnits OBJECT-TYPE
       SYNTAX      INTEGER (1..2147483647)
       ACCESS      read-only
       STATUS      mandatory
       DESCRIPTION
               "The size, in bytes, of the data objects allocated
               from this pool.  If this entry is monitoring
               sectors, blocks, buffers, or packets, for example,
               this number will commonly be greater than one.
               Otherwise this number will typically be one."
       ::= { hrStorageEntry 4 }

   hrStorageSize OBJECT-TYPE
       SYNTAX INTEGER (0..2147483647)
       ACCESS read-write
       STATUS mandatory
       DESCRIPTION
              "The size of the storage represented by this entry,
              in units of hrStorageAllocationUnits."
       ::= { hrStorageEntry 5 }

   hrStorageUsed OBJECT-TYPE
       SYNTAX INTEGER (0..2147483647)
       ACCESS read-only
       STATUS mandatory
       DESCRIPTION
              "The amount of the storage represented by this
              entry that is allocated, in units of
              hrStorageAllocationUnits."
       ::= { hrStorageEntry 6 }

   hrStorageAllocationFailures OBJECT-TYPE
       SYNTAX Counter
       ACCESS read-only
       STATUS mandatory
       DESCRIPTION
              "The number of requests for storage represented by
              this entry that could not be honored due to not
              enough storage.  It should be noted that as this
              object has a SYNTAX of Counter, that it does not
              have a defined initial value.  However, it is
              recommended that this object be initialized to
              zero."
       ::= { hrStorageEntry 7 }






   -- The Host Resources Device Group
   --
   -- Implementation of this group is mandatory for all host systems.
   --
   -- The device group is useful for identifying and diagnosing the
   -- devices on a system.  The hrDeviceTable contains common
   -- information for any type of device.  In addition, some devices
   -- have device-specific tables for more detailed information.  More
   -- such tables may be defined in the future for other device types.

   -- Registration for some device types, for use with hrDeviceType
   hrDeviceTypes             OBJECT IDENTIFIER ::= { hrDevice 1 }

   hrDeviceOther             OBJECT IDENTIFIER ::= { hrDeviceTypes 1 }
   hrDeviceUnknown           OBJECT IDENTIFIER ::= { hrDeviceTypes 2 }
   hrDeviceProcessor         OBJECT IDENTIFIER ::= { hrDeviceTypes 3 }
   hrDeviceNetwork           OBJECT IDENTIFIER ::= { hrDeviceTypes 4 }
   hrDevicePrinter           OBJECT IDENTIFIER ::= { hrDeviceTypes 5 }
   hrDeviceDiskStorage       OBJECT IDENTIFIER ::= { hrDeviceTypes 6 }
   hrDeviceVideo             OBJECT IDENTIFIER ::= { hrDeviceTypes 10 }
   hrDeviceAudio             OBJECT IDENTIFIER ::= { hrDeviceTypes 11 }
   hrDeviceCoprocessor       OBJECT IDENTIFIER ::= { hrDeviceTypes 12 }
   hrDeviceKeyboard          OBJECT IDENTIFIER ::= { hrDeviceTypes 13 }
   hrDeviceModem             OBJECT IDENTIFIER ::= { hrDeviceTypes 14 }
   hrDeviceParallelPort      OBJECT IDENTIFIER ::= { hrDeviceTypes 15 }
   hrDevicePointing          OBJECT IDENTIFIER ::= { hrDeviceTypes 16 }
   hrDeviceSerialPort        OBJECT IDENTIFIER ::= { hrDeviceTypes 17 }
   hrDeviceTape              OBJECT IDENTIFIER ::= { hrDeviceTypes 18 }
   hrDeviceClock             OBJECT IDENTIFIER ::= { hrDeviceTypes 19 }
   hrDeviceVolatileMemory    OBJECT IDENTIFIER ::= { hrDeviceTypes 20 }
   hrDeviceNonVolatileMemory OBJECT IDENTIFIER ::= { hrDeviceTypes 21 }


   hrDeviceTable OBJECT-TYPE
       SYNTAX SEQUENCE OF HrDeviceEntry
       ACCESS not-accessible
       STATUS mandatory
       DESCRIPTION
              "The (conceptual) table of devices contained by the
              host."
       ::= { hrDevice 2 }

   hrDeviceEntry OBJECT-TYPE
       SYNTAX HrDeviceEntry
       ACCESS not-accessible
       STATUS mandatory
       DESCRIPTION
              "A (conceptual) entry for one device contained by




              the host.  As an example, an instance of the
              hrDeviceType object might be named hrDeviceType.3"
       INDEX { hrDeviceIndex }
       ::= { hrDeviceTable 1 }

   HrDeviceEntry ::= SEQUENCE {
           hrDeviceIndex           INTEGER,
           hrDeviceType            OBJECT IDENTIFIER,
           hrDeviceDescr           DisplayString,
           hrDeviceID              ProductID,
           hrDeviceStatus          INTEGER,
           hrDeviceErrors          Counter
       }

   hrDeviceIndex OBJECT-TYPE
       SYNTAX INTEGER (1..2147483647)
       ACCESS read-only
       STATUS mandatory
       DESCRIPTION
              "A unique value for each device contained by the
              host.  The value for each device must remain
              constant at least from one re-initialization of the
              agent to the next re-initialization."
       ::= { hrDeviceEntry 1 }

   hrDeviceType OBJECT-TYPE
       SYNTAX OBJECT IDENTIFIER
       ACCESS read-only
       STATUS mandatory
       DESCRIPTION
              "An indication of the type of device.

              If this value is `hrDeviceProcessor { hrDeviceTypes
              3 }' then an entry exists in the hrProcessorTable
              which corresponds to this device.

              If this value is `hrDeviceNetwork { hrDeviceTypes 4
              }', then an entry exists in the hrNetworkTable
              which corresponds to this device.

              If this value is `hrDevicePrinter { hrDeviceTypes 5
              }', then an entry exists in the hrPrinterTable
              which corresponds to this device.

              If this value is `hrDeviceDiskStorage {
              hrDeviceTypes 6 }', then an entry exists in the
              hrDiskStorageTable which corresponds to this
              device."




       ::= { hrDeviceEntry 2 }

   hrDeviceDescr OBJECT-TYPE
       SYNTAX DisplayString (SIZE (0..64))
       ACCESS read-only
       STATUS mandatory
       DESCRIPTION
              "A textual description of this device, including
              the device's manufacturer and revision, and
              optionally, its serial number."
       ::= { hrDeviceEntry 3 }

   hrDeviceID OBJECT-TYPE
       SYNTAX ProductID
       ACCESS read-only
       STATUS mandatory
       DESCRIPTION
              "The product ID for this device."
       ::= { hrDeviceEntry 4 }

   hrDeviceStatus OBJECT-TYPE
        SYNTAX  INTEGER {
             unknown(1),
             running(2),
             warning(3),
             testing(4),
             down(5)
        }
        ACCESS  read-only
        STATUS  mandatory
        DESCRIPTION
              "The current operational state of the device
              described by this row of the table.  A value
              unknown(1) indicates that the current state of the
              device is unknown.  running(2) indicates that the
              device is up and running and that no unusual error
              conditions are known.  The warning(3) state
              indicates that agent has been informed of an
              unusual error condition by the operational software
              (e.g., a disk device driver) but that the device is
              still 'operational'.  An example would be high
              number of soft errors on a disk.  A value of
              testing(4), indicates that the device is not
              available for use because it is in the testing
              state.  The state of down(5) is used only when the
              agent has been informed that the device is not
              available for any use."
        ::= { hrDeviceEntry 5 }




   hrDeviceErrors OBJECT-TYPE
       SYNTAX Counter
       ACCESS read-only
       STATUS mandatory
       DESCRIPTION
               "The number of errors detected on this device.  It
               should be noted that as this object has a SYNTAX
               of Counter, that it does not have a defined
               initial value.  However, it is recommended that
               this object be initialized to zero."
       ::= { hrDeviceEntry 6 }

   hrProcessorTable OBJECT-TYPE
       SYNTAX SEQUENCE OF HrProcessorEntry
       ACCESS not-accessible
       STATUS mandatory
       DESCRIPTION
              "The (conceptual) table of processors contained by
              the host.

              Note that this table is potentially sparse: a
              (conceptual) entry exists only if the correspondent
              value of the hrDeviceType object is
              `hrDeviceProcessor'."
       ::= { hrDevice 3 }

   hrProcessorEntry OBJECT-TYPE
       SYNTAX HrProcessorEntry
       ACCESS not-accessible
       STATUS mandatory
       DESCRIPTION
              "A (conceptual) entry for one processor contained
              by the host.  The hrDeviceIndex in the index
              represents the entry in the hrDeviceTable that
              corresponds to the hrProcessorEntry.

              As an example of how objects in this table are
              named, an instance of the hrProcessorFrwID object
              might be named hrProcessorFrwID.3"
       INDEX { hrDeviceIndex }
       ::= { hrProcessorTable 1 }

   HrProcessorEntry ::= SEQUENCE {
           hrProcessorFrwID            ProductID,
           hrProcessorLoad             INTEGER
       }

   hrProcessorFrwID OBJECT-TYPE




       SYNTAX ProductID
       ACCESS read-only
       STATUS mandatory
       DESCRIPTION
              "The product ID of the firmware associated with the
              processor."
       ::= { hrProcessorEntry 1 }

   hrProcessorLoad OBJECT-TYPE
       SYNTAX INTEGER (0..100)
       ACCESS read-only
       STATUS mandatory
       DESCRIPTION
              "The average, over the last minute, of the
              percentage of time that this processor was not
              idle."
       ::= { hrProcessorEntry 2 }

   hrNetworkTable OBJECT-TYPE
       SYNTAX SEQUENCE OF HrNetworkEntry
       ACCESS not-accessible
       STATUS mandatory
       DESCRIPTION
              "The (conceptual) table of network devices
              contained by the host.

              Note that this table is potentially sparse: a
              (conceptual) entry exists only if the correspondent
              value of the hrDeviceType object is
              `hrDeviceNetwork'."
       ::= { hrDevice 4 }

   hrNetworkEntry OBJECT-TYPE
       SYNTAX HrNetworkEntry
       ACCESS not-accessible
       STATUS mandatory
       DESCRIPTION
              "A (conceptual) entry for one network device
              contained by the host.  The hrDeviceIndex in the
              index represents the entry in the hrDeviceTable
              that corresponds to the hrNetworkEntry.

              As an example of how objects in this table are
              named, an instance of the hrNetworkIfIndex object
              might be named hrNetworkIfIndex.3"
       INDEX { hrDeviceIndex }
       ::= { hrNetworkTable 1 }





   HrNetworkEntry ::= SEQUENCE {
           hrNetworkIfIndex    INTEGER
       }

   hrNetworkIfIndex OBJECT-TYPE
       SYNTAX INTEGER
       ACCESS read-only
       STATUS mandatory
       DESCRIPTION
              "The value of ifIndex which corresponds to this
              network device."
       ::= { hrNetworkEntry 1 }

   hrPrinterTable OBJECT-TYPE
       SYNTAX SEQUENCE OF HrPrinterEntry
       ACCESS not-accessible
       STATUS mandatory
       DESCRIPTION
              "The (conceptual) table of printers local to the
              host.

              Note that this table is potentially sparse: a
              (conceptual) entry exists only if the correspondent
              value of the hrDeviceType object is
              `hrDevicePrinter'."
       ::= { hrDevice 5 }

   hrPrinterEntry OBJECT-TYPE
       SYNTAX HrPrinterEntry
       ACCESS not-accessible
       STATUS mandatory
       DESCRIPTION
              "A (conceptual) entry for one printer local to the
              host.  The hrDeviceIndex in the index represents
              the entry in the hrDeviceTable that corresponds to
              the hrPrinterEntry.

              As an example of how objects in this table are
              named, an instance of the hrPrinterStatus object
              might be named hrPrinterStatus.3"
       INDEX { hrDeviceIndex }
       ::= { hrPrinterTable 1 }

   HrPrinterEntry ::= SEQUENCE {
           hrPrinterStatus             INTEGER,
           hrPrinterDetectedErrorState OCTET STRING
       }





   hrPrinterStatus OBJECT-TYPE
       SYNTAX INTEGER {
           other(1),
           unknown(2),
           idle(3),
           printing(4),
           warmup(5)
       }
       ACCESS read-only
       STATUS mandatory
       DESCRIPTION
               "The current status of this printer device.  When
               in the idle(1), printing(2), or warmup(3) state,
               the corresponding hrDeviceStatus should be
               running(2) or warning(3).  When in the unknown
               state, the corresponding hrDeviceStatus should be
               unknown(1)."
       ::= { hrPrinterEntry 1 }

   hrPrinterDetectedErrorState OBJECT-TYPE
       SYNTAX OCTET STRING
       ACCESS read-only
       STATUS mandatory
       DESCRIPTION
               "This object represents any error conditions
               detected by the printer.  The error conditions are
               encoded as bits in an octet string, with the
               following definitions:

                    Condition         Bit #    hrDeviceStatus

                    lowPaper          0        warning(3)
                    noPaper           1        down(5)
                    lowToner          2        warning(3)
                    noToner           3        down(5)
                    doorOpen          4        down(5)
                    jammed            5        down(5)
                    offline           6        down(5)
                    serviceRequested  7        warning(3)

               If multiple conditions are currently detected and
               the hrDeviceStatus would not otherwise be
               unknown(1) or testing(4), the hrDeviceStatus shall
               correspond to the worst state of those indicated,
               where down(5) is worse than warning(3) which is
               worse than running(2).

               Bits are numbered starting with the most




               significant bit of the first byte being bit 0, the
               least significant bit of the first byte being bit
               7, the most significant bit of the second byte
               being bit 8, and so on.  A one bit encodes that
               the condition was detected, while a zero bit
               encodes that the condition was not detected.

               This object is useful for alerting an operator to
               specific warning or error conditions that may
               occur, especially those requiring human
               intervention."
       ::= { hrPrinterEntry 2 }

   hrDiskStorageTable OBJECT-TYPE
       SYNTAX SEQUENCE OF HrDiskStorageEntry
       ACCESS not-accessible
       STATUS mandatory
       DESCRIPTION
              "The (conceptual) table of long-term storage
              devices contained by the host.  In particular, disk
              devices accessed remotely over a network are not
              included here.

              Note that this table is potentially sparse: a
              (conceptual) entry exists only if the correspondent
              value of the hrDeviceType object is
              `hrDeviceDiskStorage'."
       ::= { hrDevice 6 }

   hrDiskStorageEntry OBJECT-TYPE
       SYNTAX HrDiskStorageEntry
       ACCESS not-accessible
       STATUS mandatory
       DESCRIPTION
              "A (conceptual) entry for one long-term storage
              device contained by the host.  The hrDeviceIndex in
              the index represents the entry in the hrDeviceTable
              that corresponds to the hrDiskStorageEntry. As an
              example, an instance of the hrDiskStorageCapacity
              object might be named hrDiskStorageCapacity.3"
       INDEX { hrDeviceIndex }
       ::= { hrDiskStorageTable 1 }

   HrDiskStorageEntry ::= SEQUENCE {
           hrDiskStorageAccess         INTEGER,
           hrDiskStorageMedia          INTEGER,
           hrDiskStorageRemoveble      Boolean,
           hrDiskStorageCapacity       KBytes




       }

   hrDiskStorageAccess OBJECT-TYPE
       SYNTAX INTEGER {
                       readWrite(1),
                       readOnly(2)
               }
       ACCESS read-only
       STATUS mandatory
       DESCRIPTION
              "An indication if this long-term storage device is
              readable and writable or only readable.  This
              should reflect the media type, any write-protect
              mechanism, and any device configuration that
              affects the entire device."
       ::= { hrDiskStorageEntry 1 }

   hrDiskStorageMedia OBJECT-TYPE
       SYNTAX INTEGER {
                   other(1),
                   unknown(2),
                   hardDisk(3),
                   floppyDisk(4),
                   opticalDiskROM(5),
                   opticalDiskWORM(6),     -- Write Once Read Many
                   opticalDiskRW(7),
                   ramDisk(8)
               }
       ACCESS read-only
       STATUS mandatory
       DESCRIPTION
              "An indication of the type of media used in this
              long-term storage device."
       ::= { hrDiskStorageEntry 2 }

   hrDiskStorageRemoveble OBJECT-TYPE
       SYNTAX Boolean
       ACCESS read-only
       STATUS mandatory
       DESCRIPTION
               "Denotes whether or not the disk media may be
               removed from the drive."
       ::= { hrDiskStorageEntry 3 }

   hrDiskStorageCapacity OBJECT-TYPE
       SYNTAX KBytes
       ACCESS read-only
       STATUS mandatory




       DESCRIPTION
              "The total size for this long-term storage device."
       ::= { hrDiskStorageEntry 4 }

   hrPartitionTable OBJECT-TYPE
       SYNTAX SEQUENCE OF HrPartitionEntry
       ACCESS not-accessible
       STATUS mandatory
       DESCRIPTION
              "The (conceptual) table of partitions for long-term
              storage devices contained by the host.  In
              particular, partitions accessed remotely over a
              network are not included here."
       ::= { hrDevice 7 }

   hrPartitionEntry OBJECT-TYPE
       SYNTAX HrPartitionEntry
       ACCESS not-accessible
       STATUS mandatory
       DESCRIPTION
              "A (conceptual) entry for one partition.  The
              hrDeviceIndex in the index represents the entry in
              the hrDeviceTable that corresponds to the
              hrPartitionEntry.

              As an example of how objects in this table are
              named, an instance of the hrPartitionSize object
              might be named hrPartitionSize.3.1"
       INDEX { hrDeviceIndex, hrPartitionIndex }
       ::= { hrPartitionTable 1 }

   HrPartitionEntry ::= SEQUENCE {
           hrPartitionIndex                INTEGER,
           hrPartitionLabel                InternationalDisplayString,
           hrPartitionID                   OCTET STRING,
           hrPartitionSize                 KBytes,
           hrPartitionFSIndex              INTEGER
       }

   hrPartitionIndex OBJECT-TYPE
       SYNTAX INTEGER (1..2147483647)
       ACCESS read-only
       STATUS mandatory
       DESCRIPTION
              "A unique value for each partition on this long-
              term storage device.  The value for each long-term
              storage device must remain constant at least from
              one re-initialization of the agent to the next re-




              initialization."
       ::= { hrPartitionEntry 1 }

   hrPartitionLabel OBJECT-TYPE
       SYNTAX InternationalDisplayString (SIZE (0..128))
       ACCESS read-only
       STATUS mandatory
       DESCRIPTION
              "A textual description of this partition."
       ::= { hrPartitionEntry 2 }

   hrPartitionID OBJECT-TYPE
       SYNTAX OCTET STRING
       ACCESS read-only
       STATUS mandatory
       DESCRIPTION
              "A descriptor which uniquely represents this
              partition to the responsible operating system.  On
              some systems, this might take on a binary
              representation."
       ::= { hrPartitionEntry 3 }

   hrPartitionSize OBJECT-TYPE
       SYNTAX KBytes
       ACCESS read-only
       STATUS mandatory
       DESCRIPTION
               "The size of this partition."
       ::= { hrPartitionEntry 4 }

   hrPartitionFSIndex OBJECT-TYPE
       SYNTAX INTEGER (0..2147483647)
       ACCESS read-only
       STATUS mandatory
       DESCRIPTION
               "The index of the file system mounted on this
               partition.  If no file system is mounted on this
               partition, then this value shall be zero.  Note
               that multiple partitions may point to one file
               system, denoting that that file system resides on
               those partitions.  Multiple file systems may not
               reside on one partition."
       ::= { hrPartitionEntry 5 }


   -- The File System Table
   hrFSTable OBJECT-TYPE
       SYNTAX SEQUENCE OF HrFSEntry




       ACCESS not-accessible
       STATUS mandatory
       DESCRIPTION
               "The (conceptual) table of file systems local to
               this host or remotely mounted from a file server.
               File systems that are in only one user's
               environment on a multi-user system will not be
               included in this table."
       ::= { hrDevice 8 }

   hrFSEntry OBJECT-TYPE
       SYNTAX HrFSEntry
       ACCESS not-accessible
       STATUS mandatory
       DESCRIPTION
               "A (conceptual) entry for one file system local to
               this host or remotely mounted from a file server.
               File systems that are in only one user's
               environment on a multi-user system will not be
               included in this table.

               As an example of how objects in this table are
               named, an instance of the hrFSMountPoint object
               might be named hrFSMountPoint.3"
       INDEX { hrFSIndex }
       ::= { hrFSTable 1 }

   -- Registration for some popular File System types,
   -- for use with hrFSType.

   hrFSTypes               OBJECT IDENTIFIER ::= { hrDevice 9 }

   hrFSOther               OBJECT IDENTIFIER ::= { hrFSTypes 1 }
   hrFSUnknown             OBJECT IDENTIFIER ::= { hrFSTypes 2 }
   hrFSBerkeleyFFS         OBJECT IDENTIFIER ::= { hrFSTypes 3 }
   hrFSSys5FS              OBJECT IDENTIFIER ::= { hrFSTypes 4 }
   -- DOS
   hrFSFat                 OBJECT IDENTIFIER ::= { hrFSTypes 5 }
   -- OS/2 High Performance File System
   hrFSHPFS                OBJECT IDENTIFIER ::= { hrFSTypes 6 }
   --  Macintosh Hierarchical File System
   hrFSHFS                 OBJECT IDENTIFIER ::= { hrFSTypes 7 }


   -- Macintosh File System
   hrFSMFS                 OBJECT IDENTIFIER ::= { hrFSTypes 8 }
   -- Windows NT
   hrFSNTFS                OBJECT IDENTIFIER ::= { hrFSTypes 9 }




   hrFSVNode               OBJECT IDENTIFIER ::= { hrFSTypes 10 }
   hrFSJournaled           OBJECT IDENTIFIER ::= { hrFSTypes 11 }
   -- CD File systems
   hrFSiso9660             OBJECT IDENTIFIER ::= { hrFSTypes 12 }
   hrFSRockRidge           OBJECT IDENTIFIER ::= { hrFSTypes 13 }

   hrFSNFS                 OBJECT IDENTIFIER ::= { hrFSTypes 14 }
   hrFSNetware             OBJECT IDENTIFIER ::= { hrFSTypes 15 }
   -- Andrew File System
   hrFSAFS                 OBJECT IDENTIFIER ::= { hrFSTypes 16 }
   -- OSF DCE Distributed File System
   hrFSDFS                 OBJECT IDENTIFIER ::= { hrFSTypes 17 }
   hrFSAppleshare          OBJECT IDENTIFIER ::= { hrFSTypes 18 }
   hrFSRFS                 OBJECT IDENTIFIER ::= { hrFSTypes 19 }
   -- Data General
   hrFSDGCFS               OBJECT IDENTIFIER ::= { hrFSTypes 20 }
   -- SVR4 Boot File System
   hrFSBFS                 OBJECT IDENTIFIER ::= { hrFSTypes 21 }



   HrFSEntry ::= SEQUENCE {
           hrFSIndex                   INTEGER,
           hrFSMountPoint              InternationalDisplayString,
           hrFSRemoteMountPoint        InternationalDisplayString,
           hrFSType                    OBJECT IDENTIFIER,
           hrFSAccess                  INTEGER,
           hrFSBootable                Boolean,
           hrFSStorageIndex            INTEGER,
           hrFSLastFullBackupDate      DateAndTime,
           hrFSLastPartialBackupDate   DateAndTime
       }

   hrFSIndex OBJECT-TYPE
       SYNTAX INTEGER (1..2147483647)
       ACCESS read-only
       STATUS mandatory
       DESCRIPTION
               "A unique value for each file system local to this
               host.  The value for each file system must remain
               constant at least from one re-initialization of
               the agent to the next re-initialization."
       ::= { hrFSEntry 1 }

   hrFSMountPoint OBJECT-TYPE
       SYNTAX InternationalDisplayString (SIZE(0..128))
       ACCESS read-only
       STATUS mandatory




       DESCRIPTION
               "The path name of the root of this file system."
       ::= { hrFSEntry 2 }

   hrFSRemoteMountPoint OBJECT-TYPE
       SYNTAX InternationalDisplayString (SIZE(0..128))
       ACCESS read-only
       STATUS mandatory
       DESCRIPTION
               "A description of the name and/or address of the
               server that this file system is mounted from.
               This may also include parameters such as the mount
               point on the remote file system.  If this is not a
               remote file system, this string should have a
               length of zero."
       ::= { hrFSEntry 3 }

   hrFSType OBJECT-TYPE
       SYNTAX OBJECT IDENTIFIER
       ACCESS read-only
       STATUS mandatory
       DESCRIPTION
              "The value of this object identifies the type of
              this file system."
       ::= { hrFSEntry 4 }

   hrFSAccess OBJECT-TYPE
       SYNTAX INTEGER {
               readWrite(1),
               readOnly(2)
           }
       ACCESS read-only
       STATUS mandatory
       DESCRIPTION
              "An indication if this file system is logically
              configured by the operating system to be readable
              and writable or only readable.  This does not
              represent any local access-control policy, except
              one that is applied to the file system as a whole."
       ::= { hrFSEntry 5 }

   hrFSBootable OBJECT-TYPE
       SYNTAX Boolean
       ACCESS read-only
       STATUS mandatory
       DESCRIPTION
              "A flag indicating whether this file system is
              bootable."




       ::= { hrFSEntry 6 }

   hrFSStorageIndex OBJECT-TYPE
       SYNTAX INTEGER (0..2147483647)
       ACCESS read-only
       STATUS mandatory
       DESCRIPTION
               "The index of the hrStorageEntry that represents
               information about this file system.  If there is
               no such information available, then this value
               shall be zero.  The relevant storage entry will be
               useful in tracking the percent usage of this file
               system and diagnosing errors that may occur when
               it runs out of space."
       ::= { hrFSEntry 7 }

   hrFSLastFullBackupDate OBJECT-TYPE
       SYNTAX DateAndTime
       ACCESS read-write
       STATUS mandatory
       DESCRIPTION
              "The last date at which this complete file system
              was copied to another storage device for backup.
              This information is useful for ensuring that
              backups are being performed regularly.

              If this information is not known, then this
              variable shall have the value corresponding to
              January 1, year 0000, 00:00:00.0, which is encoded
              as (hex)'00 00 01 01 00 00 00 00'."
       ::= { hrFSEntry 8 }

   hrFSLastPartialBackupDate OBJECT-TYPE
       SYNTAX DateAndTime
       ACCESS read-write
       STATUS mandatory
       DESCRIPTION
              "The last date at which a portion of this file
              system was copied to another storage device for
              backup.  This information is useful for ensuring
              that backups are being performed regularly.

              If this information is not known, then this
              variable shall have the value corresponding to
              January 1, year 0000, 00:00:00.0, which is encoded
              as (hex)'00 00 01 01 00 00 00 00'."
       ::= { hrFSEntry 9 }


END
