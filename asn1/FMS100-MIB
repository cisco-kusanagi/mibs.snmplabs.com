-- **********************************************************************
--
-- Product:		XXXXXXX
-- MIB Version:		XXXXXXX
-- Comments:		xxxxxxxxxxxxxxxxxxxxxxxxxxxxxxxxxxxxxxxxx
--			xxxxxxxxxxxxxxxxxxxxxxxxxxxxxxxxxxxxxxxxx
-- History:		Date			Reason For Change
--			====			=================
--			December 22, 1993	Initial Version.
--
-- **********************************************************************
--	Copyright 3Com Technologies Limited (1993)
-- **********************************************************************



-- --------------------------------------------------------------------
-- ************ THE STARTING POINT FOR ALL MIB DEFINITIONS ************
-- --------------------------------------------------------------------

          FMS100-MIB DEFINITIONS ::= BEGIN

--
-- 22 Jun 95	David Chuang & Srinath Candadai, Added NAD products -
--				      FMS100 management only system
--
-- **********************************************************************
--      Copyright 3Com Technologies Limited. (1991-1995)
-- **********************************************************************

IMPORTS enterprises, OBJECT-TYPE, Counter
			FROM RFC1155-SMI
		;

--
-- This MIB contains 3com product OIDs (used in sysObjectID)
--

a3Com                   OBJECT IDENTIFIER ::= { enterprises 43 }
products                OBJECT IDENTIFIER ::= { a3Com 1 }
hub                     OBJECT IDENTIFIER ::= { products 8 }  
cards                   OBJECT IDENTIFIER ::= { products 9 }       
linkBuilderFMS100-mib   OBJECT IDENTIFIER ::= { a3Com 19 }
linkBuilderFMS100       OBJECT IDENTIFIER ::= { hub 20 }

--
-- the following identifiers are assigned to 3com modules and cards
--
linkBuilderFMS100-cards           OBJECT IDENTIFIER ::= { cards 10 } 

--
-- the following identifiers are assigned to 3com modules and cards
--
linkBuilderFMS100-cards-12utp     OBJECT IDENTIFIER ::= { linkBuilderFMS100-cards 1 }  -- this is Ethernet 100BaseTX repeater card



-- 3COM FMS100 Hub specific MIB

hubEnviroObject   OBJECT IDENTIFIER ::= { linkBuilderFMS100-mib 2 }

hubEnviroGroupTable	OBJECT-TYPE
			SYNTAX		SEQUENCE OF HubEnviroGroupEntry
			ACCESS		not-accessible
			STATUS		mandatory
			DESCRIPTION
			"Table of Environment information about the group."
			::= { hubEnviroObject 1 }

hubEnviroGroupEntry	OBJECT-TYPE
			SYNTAX		HubEnviroGroupEntry
			ACCESS		not-accessible
			STATUS		mandatory
			DESCRIPTION
			"An Entry in the table, containing information about
			 a single group."
			INDEX		{ hubServiceId, hubGroupIndex }
			::= { hubEnviroGroupTable 1 }

			HubEnviroGroupEntry ::= SEQUENCE {
				hubServiceId	INTEGER,
				hubGroupIndex	INTEGER,
				hubHighTemp	INTEGER,
				hubFanFailed	INTEGER
			}

	  hubServiceId	OBJECT-TYPE
			SYNTAX			INTEGER
			ACCESS			read-only
			STATUS			mandatory
			DESCRIPTION
			"This object identifies the repeater which this
			entry contains information. For FMS100, this is
			a constant 1."
			::= {hubEnviroGroupEntry  1}

	  hubGroupIndex OBJECT-TYPE
	      SYNTAX INTEGER (1..1024)
	      ACCESS read-only
	      STATUS mandatory
	      DESCRIPTION
	      "This object identifies the group within the repeater for which
	       this entry contains information. This number is never greater
	       than paRptrGroupCapacity."
	      ::= { hubEnviroGroupEntry 2 }

	  hubHighTemp OBJECT-TYPE
	      SYNTAX INTEGER { true(1), false(2) }
	      ACCESS read-only
	      STATUS mandatory
	      DESCRIPTION
			" This variable shows the current temperature status
			of the hub.
			If the variable changed from false to true, The
			enterprise-specific trap(a3comHighTemp) will be
			sent to the configured SNMP manager stations."
	      ::= { hubEnviroGroupEntry 3 }

	  hubFanFailed OBJECT-TYPE
	      SYNTAX INTEGER { true(1), false(2) }
	      ACCESS read-only
	      STATUS mandatory
	      DESCRIPTION
			" This variable shows the current Fan Fail status
			of the hub.
			If the variable changed from false to true, The
			enterprise-specific trap(a3comFanFailed) will be
			sent to the configured SNMP manager stations."
	      ::= { hubEnviroGroupEntry 4 }


-- 100Mb Ethernet Hub Specific MIB
-- These MIBs are defined in 802.3 Standards. However, since IETF has not
-- assigned the Object Identifier for these MIBs, we registered them in
-- FMS100 MIB branch.

pa100RptrSpecific	OBJECT IDENTIFIER ::= { linkBuilderFMS100-mib 3 }

pa100RptrInfo		OBJECT IDENTIFIER ::= { pa100RptrSpecific 1 }
pa100GroupInfo		OBJECT IDENTIFIER ::= { pa100RptrSpecific 2 }
pa100PortInfo		OBJECT IDENTIFIER ::= { pa100RptrSpecific 3 }

pa100RptrTable		OBJECT-TYPE
	SYNTAX			SEQUENCE OF Pa100RptrEntry
	ACCESS			not-accessible
	STATUS			mandatory
	DESCRIPTION
	"Table of descriptive and STATUS information about
	the 100Mb Ethernet Hub"
	::= { pa100RptrInfo 1 }

pa100RptrEntry OBJECT-TYPE
	SYNTAX			Pa100RptrEntry
	ACCESS			not-accessible
	STATUS			mandatory
	DESCRIPTION
	"An entry in the table, containing information
	about the repeater."
	INDEX			{ pa100RptrServiceId }
	::= { pa100RptrTable 1 }

	Pa100RptrEntry ::= SEQUENCE {
			 pa100RptrServiceId	       INTEGER,
			 pa100RptrClass 	       INTEGER,
			 pa100RptrStackCardTypeInfo        OCTET STRING
	}

pa100RptrServiceId  OBJECT-TYPE
	SYNTAX			INTEGER
	ACCESS			read-only
	STATUS			mandatory
	DESCRIPTION
	"This object identifies the repeater which this
	entry contains information."
	::= { pa100RptrEntry 1 }

pa100RptrClass OBJECT-TYPE
	SYNTAX			INTEGER {
					classI(1),	-- Class I Repeater
					classII(2),	-- Class II Repeater
					unknown(3)
	}
	ACCESS			read-only
	STATUS			mandatory
	DESCRIPTION
	"The pa100RptrClass is the repeater class as defined in
	802.3 standard.

	Class I: A type of repeater set specified such that in
	a maximum length segment topology, only one such
	repeater set may exist between any two DTEs within a
	single collision domain.

	Class II: A type of repeater set specified such that in
	a maximum length segment topology, only two such
	repeater set may exist between any two DTEs within a
	single collision domain."
	::= { pa100RptrEntry 2 }

pa100RptrStackCardTypeInfo OBJECT-TYPE
	SYNTAX			OCTET STRING (SIZE(1..8))
	ACCESS			read-only
	STATUS			mandatory
	DESCRIPTION
				"Supplies the information about the type of
				 Cards in the repeater stack.
				There is one octet for each unit in the stack. Each
				octet can have the following values:

					0 : undetected(power off or non-exist)
					1 : repeater card
					2 : management unit
					3 : bridge/management card
					4 : backup management(/bridge) card
					5 : powered off
					6 : unknown
				Value 0 indicates either the powered off card's
				cardindex is higher than all of the powered on cards
				or the card is non-existant.
				Value 5 indicates that the card is powered off
				and there are powered on card(s) with higher index
				number.

				Octet offset(started 0) N indicates N+1 th card information.
				I.e. The first octet indicates card 1's information."
	::= { pa100RptrEntry 3 }

--
-- The Basic Port Table
--

pa100PortTable		OBJECT-TYPE
	SYNTAX			SEQUENCE OF Pa100PortEntry
	ACCESS			not-accessible
	STATUS			mandatory
	DESCRIPTION
	"Table of descriptive and STATUS information about
	the ports that is specific to 100Mb Ethernet Hub"
	::= { pa100PortInfo 1 }

pa100PortEntry OBJECT-TYPE
	SYNTAX			Pa100PortEntry
	ACCESS			not-accessible
	STATUS			mandatory
	DESCRIPTION
	"An entry in the table, containing information
	about a single port."
	INDEX			{pa100PortServiceId, pa100PortGroupIndex,pa100PortIndex}
	::= { pa100PortTable 1 }

	Pa100PortEntry ::= SEQUENCE {
			 pa100PortServiceId			       INTEGER,
			 pa100PortGroupIndex			       INTEGER,
			 pa100PortIndex 			       INTEGER,
			 pa100PortIsolate			       INTEGER,
			 pa100PortSymbolErrorDuringPacket	       INTEGER
	}

pa100PortServiceId  OBJECT-TYPE
	SYNTAX			INTEGER
	ACCESS			read-only
	STATUS			mandatory
	DESCRIPTION
	"This object identifies the repeater which this
	entry contains information."
	::= { pa100PortEntry 1 }

pa100PortGroupIndex OBJECT-TYPE
	SYNTAX			INTEGER (1..1024)
	ACCESS			read-only
	STATUS			mandatory
	DESCRIPTION
	"This object identifies the group containing the
	port for which this entry contains information."
	::= { pa100PortEntry 2 }

pa100PortIndex OBJECT-TYPE
	SYNTAX			INTEGER (1..1024)
	ACCESS			read-only
	STATUS			mandatory
	DESCRIPTION
	"This object identifies the port within the group
	for which this entry contains information.  This
	value can never be greater than
	paRptrGroupPortCapacity for the associated group."
	::= { pa100PortEntry 3 }

pa100PortIsolate OBJECT-TYPE
	SYNTAX			Counter
	ACCESS			read-only
	STATUS			mandatory
	DESCRIPTION
	"Increment counter by each time that the repeater
	port automatically isolates as a consequence of false
	carrier events. The conditions which cause a port to
	automatically isolate are as defined by the transition
	from the False Carrier state to the Link Unstable state
	of the carrier integrity state diagram.(802.3 std)"
	::= { pa100PortEntry 4 }

pa100PortSymbolErrorDuringPacket OBJECT-TYPE
	SYNTAX			Counter
	ACCESS			read-only
	STATUS			mandatory
	DESCRIPTION
	"A count of the number of times when valid length
	packet was received at the port and there was at least
	one occurrence of an invalid symbol. This can increment
	only once per valid carrier event. A collision presence
	at any port of the repeater containing port N, will not
	cause this attribute to increment. "
	::= { pa100PortEntry 5 }

       END
