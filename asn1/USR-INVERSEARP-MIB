USR-INVERSEARP-MIB DEFINITIONS ::= BEGIN
	IMPORTS
	  RowStatus
                FROM SNMPv2-TC
          IpAddress
                FROM RFC1155-SMI
          OBJECT-TYPE,  MODULE-IDENTITY, Integer32
                FROM SNMPv2-SMI
          PhysAddress, common
                FROM USR-DEFINITIONS-MIB;
        usrInverseARP    MODULE-IDENTITY
         LAST-UPDATED "0001141020Z" -- Friday, January 14, 10:20, 2000
         ORGANIZATION "3Com Corporation, Carrier Division"
         CONTACT-INFO "Customer Support"
         DESCRIPTION
                 "The proprietary object definitions for Inverse ARP."
         ::= { common 73 }
   -- Begin managed object definitions here...
   -- The Inverse ARP Table contains the mapping of IP Address(network address)
   -- to dlci-interface pair for IP networks over Frame Relay PTP connections.
usrInverseARPTable OBJECT-TYPE
	SYNTAX SEQUENCE OF UsrInverseARPEntry
	MAX-ACCESS not-accessible
	STATUS current 
	DESCRIPTION
		"The Inverse ARP cache for Frame Relay Networks"
::= { usrInverseARP 1 }
usrInverseARPEntry OBJECT-TYPE
	SYNTAX UsrInverseARPEntry
	MAX-ACCESS not-accessible
	STATUS current
	DESCRIPTION
		"An Inverse ARP cache entry"
	INDEX { usrInverseARPIfIndex, usrInverseARPNetAddress }
::= { usrInverseARPTable 1 }
UsrInverseARPEntry ::= SEQUENCE {
        usrInverseARPIfIndex     Integer32,
        usrInverseARPPhysAddress PhysAddress,
        usrInverseARPNetAddress  IpAddress,
        usrInverseARPType        INTEGER,
        usrInverseARPAge         Integer32,
	usrInverseARPStatus      RowStatus
        }
usrInverseARPIfIndex OBJECT-TYPE
        SYNTAX  Integer32
        MAX-ACCESS  read-write
        STATUS  current
        DESCRIPTION
                "The interface on which this entry's equivalence
                is effective.  The interface identified by a
                particular value of this index is the same
                interface as identified by the same value of
                ifIndex."
        --CONFIGURABLE
::= { usrInverseARPEntry 1 }
usrInverseARPPhysAddress OBJECT-TYPE
        SYNTAX  PhysAddress
        MAX-ACCESS  read-write
        STATUS  current
        DESCRIPTION
                "The media-dependent `physical' address. For Frame Relay PTMP network,
                it's six byte long; 4 byte DLCI followed by 2byte interface(physical) index"
        --CONFIGURABLE
::= { usrInverseARPEntry 2 }
usrInverseARPNetAddress OBJECT-TYPE
        SYNTAX  IpAddress
        MAX-ACCESS  read-write
        STATUS  current
        DESCRIPTION
                "The IpAddress corresponding to the media-
                dependent `physical' address."
        --CONFIGURABLE
::= { usrInverseARPEntry 3 }
usrInverseARPType OBJECT-TYPE
        SYNTAX  INTEGER {
                    other(0),        -- none of the following
                    invalid(1),      -- an invalidated mapping
                    dynamic(2),
                    static(3)
                }
        MAX-ACCESS  read-write
        STATUS  current
        DESCRIPTION
                "The type of mapping"
        --CONFIGURABLE
::= { usrInverseARPEntry 4 }
usrInverseARPAge OBJECT-TYPE
        SYNTAX  Integer32
        MAX-ACCESS  read-write
        STATUS  current
        DESCRIPTION
                "The current timeout age of an entry"
        --CONFIGURABLE
::= { usrInverseARPEntry 5 }
usrInverseARPStatus OBJECT-TYPE
	SYNTAX  RowStatus
	MAX-ACCESS    read-write
	STATUS  current
	DESCRIPTION
		"The status of this row of the Inverse ARP Table. "
	--CONFIGURABLE
::= { usrInverseARPEntry 6 }
usrInverseARPConfigGroup OBJECT IDENTIFIER ::= { usrInverseARP 2 }
usrInverseARPTxInterval OBJECT-TYPE
        SYNTAX  Integer32
        MAX-ACCESS  read-write
        STATUS  current
        DESCRIPTION
                "The Inverse ARP transmit frequency in secs"
	--CONFIGURABLE
::= { usrInverseARPConfigGroup 1 }
usrInverseARPMaxAge OBJECT-TYPE
        SYNTAX  Integer32
        MAX-ACCESS  read-write
        STATUS  current
        DESCRIPTION
                "The Maximum age count of an entry before it is deleted from the cache. 
                 One count corresponds to one Inverse ARP transmit frequency period."
	--CONFIGURABLE
::= { usrInverseARPConfigGroup 2 }
usrInverseARPCacheClear OBJECT-TYPE
        SYNTAX  Integer32
        MAX-ACCESS  read-write
        STATUS  current
        DESCRIPTION
                "This object is used to clear the entire Inverse ARP cache."
::= { usrInverseARP 3 }
END         -- End USR-INVERSEARP-MIB definitions
--
-- ************************************************************************
--
--    usr_ip_routing.mib
--
-- Author:         han-son on
--
