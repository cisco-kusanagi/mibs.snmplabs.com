CXCAS-MIB DEFINITIONS ::= BEGIN

IMPORTS
   	OBJECT-TYPE   FROM RFC-1212

--  Proprietary Imports
    cxCAS		  FROM CXProduct-SMI;


--  The ABCD Transmit Signaling bits Table

dsx1ExtAbcdTxSignalingTable OBJECT-TYPE
   SYNTAX  SEQUENCE OF Dsx1ExtAbcdTxSignalingEntry
   ACCESS  not-accessible
   STATUS  mandatory
   DESCRIPTION
"ABCD bits pattern table for T1/E1 transmit signaling protocols"
   ::= { cxCAS 10 }

dsx1ExtAbcdTxSignalingEntry OBJECT-TYPE
   SYNTAX  Dsx1ExtAbcdTxSignalingEntry
   ACCESS  not-accessible
   STATUS  mandatory
   DESCRIPTION
"ABCD transmit signaling bits row definition."
   INDEX { dsx1ExtAbcdTxSignalingTypeIndex }
   ::= { dsx1ExtAbcdTxSignalingTable 1 }

Dsx1ExtAbcdTxSignalingEntry ::=
   SEQUENCE {
-- Parameters 
      dsx1ExtAbcdTxSignalingTypeIndex	INTEGER,
      dsx1ExtAbcdEmOnHook			   INTEGER,
      dsx1ExtAbcdEmOffHook	   	   INTEGER,
      dsx1ExtAbcdEmSeizeAck  	      INTEGER,
      dsx1ExtAbcdEmClearForward     INTEGER,
      dsx1ExtAbcdEmClearBackward    INTEGER,
      dsx1ExtAbcdFxLo			      INTEGER,
      dsx1ExtAbcdFxLc			      INTEGER,
      dsx1ExtAbcdFxRingingOn		   INTEGER,
      dsx1ExtAbcdFxLcf			      INTEGER,
      dsx1ExtAbcdFxLcfo			      INTEGER,
      dsx1ExtAbcdFxRingingOff		   INTEGER,
      dsx1ExtAbcdAnswer			      INTEGER,
      dsx1ExtAbcdBusyOut			   INTEGER,
      dsx1ExtAbcdFaultyLink			INTEGER
}

dsx1ExtAbcdTxSignalingTypeIndex  OBJECT-TYPE
     SYNTAX INTEGER (1..3)
     ACCESS  read-only
     STATUS  mandatory
     DESCRIPTION
"The index of the emulated interface type: 1=E&M, 2=FXS, 3=FXO"
     ::= { dsx1ExtAbcdTxSignalingEntry 1 }

dsx1ExtAbcdEmOnHook  OBJECT-TYPE
     SYNTAX INTEGER (0..15)
     ACCESS  read-write
     STATUS  mandatory
     DESCRIPTION
"ABCD bits pattern to signal the 'on-hook' state of an emulated E&M interface type.
Range of Values: 0 to 15"
     ::= { dsx1ExtAbcdTxSignalingEntry 10 }

dsx1ExtAbcdEmOffHook  OBJECT-TYPE
     SYNTAX INTEGER (0..15)
     ACCESS  read-write
     STATUS  mandatory
     DESCRIPTION
"ABCD bits pattern to signal the 'off-hook' state of an emulated E&M interface type.
Range of Values: 0 to 15"
     ::= { dsx1ExtAbcdTxSignalingEntry 11 }

dsx1ExtAbcdEmSeizeAck  OBJECT-TYPE
     SYNTAX INTEGER (0..15)
     ACCESS  read-write
     STATUS  mandatory
     DESCRIPTION
"ABCD bits pattern to signal the 'seizure acknowledge' state of an emulated R2 signaling line."
     ::= { dsx1ExtAbcdTxSignalingEntry 12 }

dsx1ExtAbcdEmClearForward  OBJECT-TYPE
     SYNTAX INTEGER (0..15)
     ACCESS  read-write
     STATUS  mandatory
     DESCRIPTION
"ABCD bits pattern to signal the 'clear forward' state of an emulated R2 signaling line."
     ::= { dsx1ExtAbcdTxSignalingEntry 13 }

dsx1ExtAbcdEmClearBackward  OBJECT-TYPE
     SYNTAX INTEGER (0..15)
     ACCESS  read-write
     STATUS  mandatory
     DESCRIPTION
"ABCD bits pattern to signal the 'clear backward' state of an emulated R2 signaling line."
     ::= { dsx1ExtAbcdTxSignalingEntry 14 }

dsx1ExtAbcdFxLo  OBJECT-TYPE
     SYNTAX INTEGER (0..15)
     ACCESS  read-write
     STATUS  mandatory
     DESCRIPTION
"ABCD bits pattern to signal the 'loop open' state of an emulated FXS or FXO interface type.
Range of Values: 0 to 15"
     ::= { dsx1ExtAbcdTxSignalingEntry 15 }

dsx1ExtAbcdFxLc  OBJECT-TYPE
     SYNTAX INTEGER (0..15)
     ACCESS  read-write
     STATUS  mandatory
     DESCRIPTION
"ABCD bits pattern to signal the 'loop closed' state of an emulated FXS or FXO interface type.
Range of Values: 0 to 15"
     ::= { dsx1ExtAbcdTxSignalingEntry 16 }

dsx1ExtAbcdFxRingingOn  OBJECT-TYPE
     SYNTAX INTEGER (0..15)
     ACCESS  read-write
     STATUS  mandatory
     DESCRIPTION
"ABCD bits pattern to signal the 'ringing' state of an emulated FXS or FXO interface type.
Range of Values: 0 to 15"
     ::= { dsx1ExtAbcdTxSignalingEntry 17 }

dsx1ExtAbcdFxLcf  OBJECT-TYPE
     SYNTAX INTEGER (0..15)
     ACCESS  read-write
     STATUS  mandatory
     DESCRIPTION
"ABCD bits pattern to signal the 'loop current feed' state of an emulated FXS or FXO interface type.
Range of Values: 0 to 15 "
     ::= { dsx1ExtAbcdTxSignalingEntry 18 }

dsx1ExtAbcdFxLcfo  OBJECT-TYPE
     SYNTAX INTEGER (0..15)
     ACCESS  read-write
     STATUS  mandatory
     DESCRIPTION
"ABCD bits pattern to signal the 'loop current feed open' state of an emulated FXS or FXO interface type.
Range of Values: 0 to 15"
     ::= { dsx1ExtAbcdTxSignalingEntry 19 }

dsx1ExtAbcdFxRingingOff  OBJECT-TYPE
     SYNTAX INTEGER (0..15)
     ACCESS  read-write
     STATUS  mandatory
     DESCRIPTION
"ABCD bits pattern to signal the 'ringing off' state of an emulated FXO interface type, only if E1 CAS is used.
Range of Values: 0 to 15"
     ::= { dsx1ExtAbcdTxSignalingEntry 20 }

dsx1ExtAbcdAnswer  OBJECT-TYPE
     SYNTAX INTEGER (0..15)
     ACCESS  read-write
     STATUS  mandatory
     DESCRIPTION
"ABCD bits pattern to signal the 'answer' state of an emulated interface type (FXS, FXO or E&M), only if E1 CAS is used.
Range of Values: 0 to 15"
     ::= { dsx1ExtAbcdTxSignalingEntry 21 }

dsx1ExtAbcdBusyOut  OBJECT-TYPE
     SYNTAX INTEGER (0..15)
     ACCESS  read-write
     STATUS  mandatory
     DESCRIPTION
"ABCD bits pattern to signal a disabled channel.
Range of Values: 0 to 15"
     ::= { dsx1ExtAbcdTxSignalingEntry 22 }

dsx1ExtAbcdFaultyLink  OBJECT-TYPE
     SYNTAX INTEGER (0..15)
     ACCESS  read-write
     STATUS  mandatory
     DESCRIPTION
"ABCD bits pattern to signal a faulty link (line).
Range of Values: 0 to 15"
     ::= { dsx1ExtAbcdTxSignalingEntry 23 }



--  The ABCD Receive Signaling bits Table

dsx1ExtAbcdRxSignalingTable OBJECT-TYPE
   SYNTAX  SEQUENCE OF Dsx1ExtAbcdRxSignalingEntry
   ACCESS  not-accessible
   STATUS  mandatory
   DESCRIPTION
"ABCD bits pattern table for T1/E1 receive signaling protocols"
   ::= { cxCAS 20 }

dsx1ExtAbcdRxSignalingEntry OBJECT-TYPE
   SYNTAX  Dsx1ExtAbcdRxSignalingEntry
   ACCESS  not-accessible
   STATUS  mandatory
   DESCRIPTION
"ABCD receive signaling bits row definition."
   INDEX { dsx1ExtAbcdRxSignalingTypeIndex,
           dsx1ExtAbcdRxSignalingAbcdValue }
   ::= { dsx1ExtAbcdRxSignalingTable 1 }

Dsx1ExtAbcdRxSignalingEntry ::=
   SEQUENCE {
-- Parameters 
      dsx1ExtAbcdRxSignalingTypeIndex	INTEGER,
      dsx1ExtAbcdRxSignalingAbcdValue	INTEGER,

      dsx1ExtAbcdValue			         INTEGER
}

dsx1ExtAbcdRxSignalingTypeIndex  OBJECT-TYPE
     SYNTAX INTEGER (1..3)
     ACCESS  read-only
     STATUS  mandatory
     DESCRIPTION
"The index of the emulated interface type: 1=E&M, 2=FXS, 3=FXO"
     ::= { dsx1ExtAbcdRxSignalingEntry 1 }

dsx1ExtAbcdRxSignalingAbcdValue  OBJECT-TYPE
     SYNTAX INTEGER (1..16)
     ACCESS  read-only
     STATUS  mandatory
     DESCRIPTION
"The index for all four ABCD bits patterns."
     ::= { dsx1ExtAbcdRxSignalingEntry 2 }

dsx1ExtAbcdValue  OBJECT-TYPE
     SYNTAX INTEGER {   
            on-hook (1),
            off-hook (2),
            ring-on (3),
            lcf (4),
            lcfo (5),
            answer (6),
            ring-off (7),
            busy-out (8),
            faulty-link (9),
            seize (10),
            proceed (11)
            }
     ACCESS  read-write
     STATUS  mandatory
     DESCRIPTION
"Signaling value assigned to selected ABCD bits pattern.
Range of Values: 1 to 11"
     ::= { dsx1ExtAbcdRxSignalingEntry 10 }
     
END
