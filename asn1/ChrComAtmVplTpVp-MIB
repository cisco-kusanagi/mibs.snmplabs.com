ChrComAtmVplTpVp-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComAtmVpl				FROM  Chromatis-MIB
	TruthValue				FROM  ChrTyp-MIB
	OperStatus				FROM  CISCO-RHINO-MIB;

-- chrComAtmVplTpVp Table

chrComAtmVplTpVpTable		OBJECT-TYPE
	SYNTAX		SEQUENCE OF ChrComAtmVplTpVpEntry
	MAX-ACCESS	not-accessible
	STATUS		current
	DESCRIPTION
	"Private table. This table does not augment the VPL table, since it contains entries only for VPC TPs."
	::= { chrComAtmVpl 2}

chrComAtmVplTpVpEntry		OBJECT-TYPE
	SYNTAX		ChrComAtmVplTpVpEntry
	MAX-ACCESS	not-accessible
	STATUS		current
	DESCRIPTION
	""
	INDEX  {  chrComAtmVplifIndex, chrComAtmVplAtmVplVpi }

--DEFAULT  get-function-async  MNIL_GetRoutine
--DEFAULT  set-function-async  MNIL_SetRoutine
--DEFAULT  next-function-async MNIL_NextRoutine
--DEFAULT  test-function-async MNIL_TestRoutine
--DEFAULT  cookie "TpVp"
	::= { chrComAtmVplTpVpTable  1 }

ChrComAtmVplTpVpEntry  ::=
	SEQUENCE  {
	chrComAtmVplifIndex			Unsigned32	(0..4294967295),
	chrComAtmVplAtmVplVpi		Unsigned32	(0..4294967295),
	chrComAtmVplCCSource		TruthValue,
	chrComAtmVplCCSink			TruthValue,
	chrComAtmVplTPOperStatus		OperStatus,
	chrComAtmVplAlarmVector		Integer32	(0..65535),
	chrComAtmVplAlarmSeverityProfileIndex Unsigned32	(0..4294967295)
}

chrComAtmVplifIndex 	OBJECT-TYPE
	SYNTAX		Unsigned32	(0..4294967295)
	MAX-ACCESS 	read-write
	STATUS 		current
	DESCRIPTION
	"Index of entry in the interface table"
	::= { chrComAtmVplTpVpEntry  1 }

chrComAtmVplAtmVplVpi 	OBJECT-TYPE
	SYNTAX		Unsigned32	(0..4294967295)
	MAX-ACCESS 	read-write
	STATUS 		current
	DESCRIPTION
	"The VPI value of the VPL"
	::= { chrComAtmVplTpVpEntry  2 }

chrComAtmVplCCSource 	OBJECT-TYPE
	SYNTAX		TruthValue
	MAX-ACCESS 	read-write
	STATUS 		current
	DESCRIPTION
	"A boolean indication whether this TP implements CC source finctionality."
	::= { chrComAtmVplTpVpEntry  3 }

chrComAtmVplCCSink 	OBJECT-TYPE
	SYNTAX		TruthValue
	MAX-ACCESS 	read-write
	STATUS 		current
	DESCRIPTION
	"A boolean indication whether this TP implements CC sink finctionality"
	::= { chrComAtmVplTpVpEntry  4 }


chrComAtmVplTPOperStatus 	OBJECT-TYPE
	SYNTAX		OperStatus
	MAX-ACCESS 	read-only
	STATUS 		current
	DESCRIPTION
	"This object indicates the current operational status of the TP. The up and down states indicate that the TP is currently operational, or not operational, respectively. The unknown state indicates that the status of this TP cannot be determined. "
	::= { chrComAtmVplTpVpEntry  5 }

chrComAtmVplAlarmVector 	OBJECT-TYPE
	SYNTAX		Integer32	(0..65535)
	MAX-ACCESS 	read-only
	STATUS 		current
	DESCRIPTION
	"16 bit field. The following are bits relative positions (0=LSB), and the trap ID associated to each alarm state. 
0. VPC-AIS  atmfM4VpcTpAisAlarm
8. VPC-RDI  atmfM4VpcTpRdiAlarm
"
	::= { chrComAtmVplTpVpEntry  6 }

chrComAtmVplAlarmSeverityProfileIndex 	OBJECT-TYPE
	SYNTAX		Unsigned32	(0..4294967295)
	MAX-ACCESS 	read-write
	STATUS 		current
	DESCRIPTION
	""
	::= { chrComAtmVplTpVpEntry  7 }


END
