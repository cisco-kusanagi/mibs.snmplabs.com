Wellfleet-FR2-MIB DEFINITIONS ::= BEGIN

-- Created by mdl2asn version 3.1
-- Creation date: Wed Aug 30 16:41:14 EDT 1995
-- Modifications:
--
-- 25-Oct-95  Additions for FR/ISDN backup
-- 04-Dec-07  Additions for BCC

    IMPORTS

      Counter, TimeTicks, Gauge
        FROM RFC1155-SMI
      OBJECT-TYPE
        FROM RFC-1212
      DisplayString
        FROM RFC1213-MIB
      wfFrameRelay2Group
        FROM Wellfleet-COMMON-MIB;


    wfFrIfDlcmiTable OBJECT-TYPE
        SYNTAX	SEQUENCE OF WfFrIfDlcmiEntry
        ACCESS	not-accessible
        STATUS	mandatory
        DESCRIPTION
                "The Parameters for the Data Link Connection Management Interface"
        ::= { wfFrameRelay2Group 1 }

    wfFrIfDlcmiEntry OBJECT-TYPE
        SYNTAX	WfFrIfDlcmiEntry
        ACCESS	not-accessible
        STATUS	mandatory
        DESCRIPTION
                "The parameters for a particular Data Link Connection Management Interface"
        INDEX	{ wfFrDlcmiLineNumber,
    		  wfFrDlcmiLLIndex }
        ::= { wfFrIfDlcmiTable 1 }

    WfFrIfDlcmiEntry ::= SEQUENCE {
    	    wfFrDlcmiDelete
    		INTEGER,
    	    wfFrDlcmiDisable
    		INTEGER,
    	    wfFrDlcmiLineNumber
    		INTEGER,
    	    wfFrDlcmiLLIndex
    		INTEGER,
    	    wfFrDlcmiCircuit
    		INTEGER,
    	    wfFrDlcmiManagementType
    		INTEGER,
    	    wfFrDlcmiStatus
    		INTEGER,
    	    wfFrDlcmiAddress
    		INTEGER,
    	    wfFrDlcmiAddressLen
    		INTEGER,
    	    wfFrDlcmiPollingInterval
    		INTEGER,
    	    wfFrDlcmiFullEnquiryInterval
    		INTEGER,
    	    wfFrDlcmiErrorThreshold
    		INTEGER,
    	    wfFrDlcmiMonitoredEvents
    		INTEGER,
    	    wfFrDlcmiMaxSupportedVCs
    		INTEGER,
    	    wfFrDlcmiVCsConfigured
    		INTEGER,
    	    wfFrDlcmiMulticast
    		INTEGER,
    	    wfFrDlcmiSeqCount
    		INTEGER,
    	    wfFrDlcmiLastReceived
    		INTEGER,
    	    wfFrDlcmiPassiveSeqCount
    		INTEGER,
    	    wfFrDlcmiPassiveReceived
    		INTEGER,
    	    wfFrDlcmiPolls
    		INTEGER,
    	    wfFrDlcmiCongestionDisable
    		INTEGER,
    	    wfFrDlcmiCongestionTmr
    		INTEGER,
    	    wfFrDlcmiCongestionCtr
    		INTEGER,
    	    wfFrErrType
    		INTEGER,
    	    wfFrErrData
    		OCTET STRING,
    	    wfFrErrTime
    		TimeTicks,
    	    wfFrErrDiscards
    		Counter,
    	    wfFrErrDrops
    		Counter,
    	    wfFrErrFaults
    		Counter,
    	    wfFrErrFaultTime
    		TimeTicks,
	    wfFrDlcmiDialFailureDisable
		INTEGER,
	    wfFrDlcmiInterfaceType
		INTEGER,
	    wfFrDlcmiBackupFilterCct
		INTEGER,
            wfFrDlcmiDebugLevel
                INTEGER,
            wfFrDlcmiTraceLevel
                INTEGER,
            wfFrDlcmiCongestionMethod
                INTEGER,
            wfFrDlcmiShapingTmr
                INTEGER,
            wfFrDlcmiShapingHiQueueLimit
                INTEGER,
            wfFrDlcmiShapingNormalQueueLimit
                INTEGER,
            wfFrDlcmiShapingLoQueueLimit
                INTEGER,
	    wfFrDlcmiXoffDisable
                INTEGER,
            wfFrDlcmiMissingPolls
                Counter,
            wfFrDlcmiName
                DisplayString,
            wfFrDlcmiEnableSinglePVCUpdate
                INTEGER,
            wfFrDlcmiAnnexSwEnq
                INTEGER,
            wfFrDlcmiAnnexSwEnqTmr
                INTEGER,
            wfFrDlcmiExtraStatusInfoEnable
                INTEGER
        }

    wfFrDlcmiDelete OBJECT-TYPE
        SYNTAX	INTEGER {
    		    created(1),
    		    deleted(2)
    		}
        ACCESS	read-write
        STATUS	mandatory
        DESCRIPTION
                "Indication to delete this frame relay interface"
        DEFVAL	{ created }
        ::= { wfFrIfDlcmiEntry 1 }

    wfFrDlcmiDisable OBJECT-TYPE
        SYNTAX	INTEGER {
    		    enabled(1),
    		    disabled(2)
    		}
        ACCESS	read-write
        STATUS	mandatory
        DESCRIPTION
                "Indicates when a dlcmi entry is to be enabled or disabled."
        DEFVAL	{ enabled }
        ::= { wfFrIfDlcmiEntry 2 }

    wfFrDlcmiLineNumber OBJECT-TYPE
        SYNTAX	INTEGER
        ACCESS	read-only
        STATUS	mandatory
        DESCRIPTION
                "The line number on which this frame relay interface resides.
                This is the first of two instance identifiers."
        ::= { wfFrIfDlcmiEntry 3 }

    wfFrDlcmiLLIndex OBJECT-TYPE
        SYNTAX	INTEGER
        ACCESS	read-only
        STATUS	mandatory
        DESCRIPTION
                "The Lower layer index uniquely identifies the lower layer in
                cases where the lower layer may be something other than the
                physical layer.  For example if Frame Relay is running over
                an ATM VC, the LLIndex identifies the ATM VC."
        ::= { wfFrIfDlcmiEntry 4 }

    wfFrDlcmiCircuit OBJECT-TYPE
        SYNTAX	INTEGER
        ACCESS	read-only
        STATUS	mandatory
        DESCRIPTION
                "The circuit number of this entry"
        ::= { wfFrIfDlcmiEntry 5 }

    wfFrDlcmiManagementType OBJECT-TYPE
        SYNTAX	INTEGER {
    		    none(1),
    		    lmi(2),
    		    t1617d(3),
    		    t1617b(4),
    		    annexa(5),
    		    lmiswitch(6),
    		    annexdswitch(7),
    		    annexaswitch(8)
    		}
        ACCESS	read-write
        STATUS	mandatory
        DESCRIPTION
                "This variable indicates which Data Link Connection Management
                scheme is active (and by implication, what DLCI it uses)."
        DEFVAL	{ t1617d }
        ::= { wfFrIfDlcmiEntry 6 }

    wfFrDlcmiStatus OBJECT-TYPE
        SYNTAX	INTEGER {
    		    running(1),
    		    fault(2),
    		    init(3),
    		    notpresent(4)
    		}
        ACCESS	read-only
        STATUS	mandatory
        DESCRIPTION
                "Indicates the state of the interface. It is called status
                because this is what it was called in the rfc.
                 FR_STATUS_RUNNING is the sate after the circuit is up (either LMI
                  successful or there is no DLCMI and the system just comes up).
                 FR_STATUS_FAULT is a transient state indicating that errors have
                  caused the circuit to be disabled until DLCMI recovery.
                 FR_STATUS_INITIALIZING is a transient state indicating that
                  the interface is trying to come up.
                 FR_STATUS_NOTPRESENT indicates that the interface is not present.
                  Likely this will never be seen except upon initial
                  configuration."
        DEFVAL	{ notpresent }
        ::= { wfFrIfDlcmiEntry 7 }

    wfFrDlcmiAddress OBJECT-TYPE
        SYNTAX	INTEGER {
    		    q921(1),
    		    q922march90(2),
    		    q922november90(3),
    		    q922(4)
    		}
        ACCESS	read-write
        STATUS	mandatory
        DESCRIPTION
                "This states which address format is in use on the FR interface.
                The default is Q922"
        DEFVAL	{ q922 }
        ::= { wfFrIfDlcmiEntry 8 }

    wfFrDlcmiAddressLen OBJECT-TYPE
        SYNTAX	INTEGER {
    		    twobyte(2),
    		    threebyte(3),
    		    fourbyte(4)
    		}
        ACCESS	read-write
        STATUS	mandatory
        DESCRIPTION
                "This variable states the address length in octets. In the case
                of Q922 format, the length indicates the entire length of the
                address includeding the control portion."
        DEFVAL	{ twobyte }
        ::= { wfFrIfDlcmiEntry 9 }

    wfFrDlcmiPollingInterval OBJECT-TYPE
        SYNTAX	INTEGER(5..30)
        ACCESS	read-write
        STATUS	mandatory
        DESCRIPTION
                "The number of seconds between successive status enquiry messages"
        DEFVAL	{ 10 }
        ::= { wfFrIfDlcmiEntry 10 }

    wfFrDlcmiFullEnquiryInterval OBJECT-TYPE
        SYNTAX	INTEGER(1..255)
        ACCESS	read-write
        STATUS	mandatory
        DESCRIPTION
                "The number of status enquiry intervals that pass before issuance
                of a full status enquiry message."
        DEFVAL	{ 6 }
        ::= { wfFrIfDlcmiEntry 11 }

    wfFrDlcmiErrorThreshold OBJECT-TYPE
        SYNTAX	INTEGER (1..5000)
        ACCESS	read-write
        STATUS	mandatory
        DESCRIPTION
                "This is the maximum number of unanswered Status Enquiries the
                equipment shall accept before declaring the interface down."
        DEFVAL	{ 3 }
        ::= { wfFrIfDlcmiEntry 12 }

    wfFrDlcmiMonitoredEvents OBJECT-TYPE
        SYNTAX	INTEGER (1..5000)
        ACCESS	read-write
        STATUS	mandatory
        DESCRIPTION
                "This is the number of status polling intervals over
                which the error threshold is counted.  For example, if
                within 'MonitoredEvents' number of events the station
                receives 'ErrorThreshold' number of errors, the
                interface is marked as down."
        DEFVAL	{ 4 }
        ::= { wfFrIfDlcmiEntry 13 }

    wfFrDlcmiMaxSupportedVCs OBJECT-TYPE
        SYNTAX	INTEGER
        ACCESS	read-only
        STATUS	mandatory
        DESCRIPTION
                "The maximum number of Virtual Circuits allowed for
                this interface.  Usually dictated by the Frame Relay
                network. The system sets this initially."
        ::= { wfFrIfDlcmiEntry 14 }

    wfFrDlcmiVCsConfigured OBJECT-TYPE
        SYNTAX	INTEGER
        ACCESS	read-only
        STATUS	mandatory
        DESCRIPTION
                "The number of VCs that are presently configured on the
                interface."
        ::= { wfFrIfDlcmiEntry 15 }

    wfFrDlcmiMulticast OBJECT-TYPE
        SYNTAX	INTEGER {
    		    enabled(1),
    		    disabled(2)
    		}
        ACCESS	read-write
        STATUS	mandatory
        DESCRIPTION
                "This indicates whether the frame relay provider offers a multicast"
        DEFVAL	{ disabled }
        ::= { wfFrIfDlcmiEntry 16 }

    wfFrDlcmiSeqCount OBJECT-TYPE
        SYNTAX	INTEGER(1..255)
        ACCESS	read-only
        STATUS	mandatory
        DESCRIPTION
                "This station's sequence counter. It represents the next
                value to send."
        DEFVAL	{ 1 }
        ::= { wfFrIfDlcmiEntry 17 }

    wfFrDlcmiLastReceived OBJECT-TYPE
        SYNTAX	INTEGER(1..255)
        ACCESS	read-only
        STATUS	mandatory
        DESCRIPTION
                "The sequence number just received from the switch."
        DEFVAL	{ 1 }
        ::= { wfFrIfDlcmiEntry 18 }

    wfFrDlcmiPassiveSeqCount OBJECT-TYPE
        SYNTAX	INTEGER(1..255)
        ACCESS	read-only
        STATUS	mandatory
        DESCRIPTION
                "This station's sequence counter for answering status enquiry."
        DEFVAL	{ 1 }
        ::= { wfFrIfDlcmiEntry 19 }

    wfFrDlcmiPassiveReceived OBJECT-TYPE
        SYNTAX	INTEGER(1..255)
        ACCESS	read-only
        STATUS	mandatory
        DESCRIPTION
                "The sequence number just received from the enquring station."
        DEFVAL	{ 1 }
        ::= { wfFrIfDlcmiEntry 20 }

    wfFrDlcmiPolls OBJECT-TYPE
        SYNTAX	INTEGER
        ACCESS	read-only
        STATUS	mandatory
        DESCRIPTION
                "This is the counter of where we are in the polling cycle."
        ::= { wfFrIfDlcmiEntry 21 }

    wfFrDlcmiCongestionDisable OBJECT-TYPE
        SYNTAX	INTEGER {
    		    enabled(1),
    		    disabled(2)
    		}
        ACCESS	read-write
        STATUS	mandatory
        DESCRIPTION
                "This indicates whether the VCs should use the congestion algorithm or
                not.  Each VC may be configured to run the algorithm to override this
                setting.  Those VCs which are configured via the DLCMI interface, will
                use this setting as their default."
        DEFVAL	{ disabled }
        ::= { wfFrIfDlcmiEntry 22 }

    wfFrDlcmiCongestionTmr OBJECT-TYPE
        SYNTAX	INTEGER {
    		    half(1),
    		    one(2),
    		    oneandhalf(3),
    		    two(4),
    		    twoandhalf(5),
    		    three(6),
    		    threeandhalf(7),
    		    four(8),
    		    fourandhalf(9),
    		    five(10)
    		}
        ACCESS	read-write
        STATUS	mandatory
        DESCRIPTION
                "This is the time period over which congestion notifications are counted.
                It is also the period during which the VC will cease sending information
                before resuming transmission if no congestion notifications are received.
                The timer is kept in 1/2 second intervals."
        DEFVAL	{ one }
        ::= { wfFrIfDlcmiEntry 23 }

    wfFrDlcmiCongestionCtr OBJECT-TYPE
        SYNTAX	INTEGER(1..500)
        ACCESS	read-write
        STATUS	mandatory
        DESCRIPTION
                "This represents the number of congestion notifications, when received
                within wfFrDlcmiCongestionTmr time, will result in the VC ceasing
                transmissions."
        DEFVAL	{ 20 }
        ::= { wfFrIfDlcmiEntry 24 }

    wfFrErrType OBJECT-TYPE
        SYNTAX	INTEGER {
    		    unknown(1),
    		    short(2),
    		    long(3),
    		    illegaldlci(4),
    		    unknowndlci(5),
    		    protoerr(6),
    		    unknownie(7),
    		    sequenceerr(8),
    		    unknownrpt(9),
    		    reset(10),
    		    cntrl(11)
    		}
        ACCESS	read-only
        STATUS	mandatory
        DESCRIPTION
                "Indicate the type of the last specific monitored error."
        ::= { wfFrIfDlcmiEntry 25 }

    wfFrErrData OBJECT-TYPE
        SYNTAX	OCTET STRING
        ACCESS	read-only
        STATUS	mandatory
        DESCRIPTION
                "Contains as much of the error packet as possible."
        ::= { wfFrIfDlcmiEntry 26 }

    wfFrErrTime OBJECT-TYPE
        SYNTAX	TimeTicks
        ACCESS	read-only
        STATUS	mandatory
        DESCRIPTION
                "The time the last error occurred."
        ::= { wfFrIfDlcmiEntry 27 }

    wfFrErrDiscards OBJECT-TYPE
        SYNTAX	Counter
        ACCESS	read-only
        STATUS	mandatory
        DESCRIPTION
                "The number of inbound frames dropped because of format or other
                errors or because the VC was not known."
        ::= { wfFrIfDlcmiEntry 28 }

    wfFrErrDrops OBJECT-TYPE
        SYNTAX	Counter
        ACCESS	read-only
        STATUS	mandatory
        DESCRIPTION
                "The number of outbound frames dropped. Usually this is due the
                specified DLCI being unknown or a broadcast packet is too long"
        ::= { wfFrIfDlcmiEntry 29 }

    wfFrErrFaults OBJECT-TYPE
        SYNTAX	Counter
        ACCESS	read-only
        STATUS	mandatory
        DESCRIPTION
                "The number of times that the Interface has come down due
                to errors since the system started.  The value is reset when
                a restart parameter is modified."
        ::= { wfFrIfDlcmiEntry 30 }

    wfFrErrFaultTime OBJECT-TYPE
        SYNTAX	TimeTicks
        ACCESS	read-only
        STATUS	mandatory
        DESCRIPTION
                "The time at which the interface last went down."
        ::= { wfFrIfDlcmiEntry 31 }

    wfFrDlcmiDialFailureDisable OBJECT-TYPE
	SYNTAX	INTEGER {
		    enabled (1),
		    disabled (2)
		}
	ACCESS	read-write
	STATUS	mandatory
	DESCRIPTION
		"On a dial interface, this indicates whether to time-out if
		 a full status message is not received. A timeout will cause
		 the connection to terminate."
	DEFVAL { disabled }
	::= { wfFrIfDlcmiEntry 32 }

    wfFrDlcmiInterfaceType OBJECT-TYPE
	SYNTAX	INTEGER {
		    normal (1),
		    primary (2),
		    backup (3),
		    backupDup (4),
                    demand (5)
		}
	ACCESS  read-write
	STATUS  mandatory
	DESCRIPTION
		"Indicates the type of interface this is. A normal interface
		 is not backed up, a primary interface is backed up, and
		 a backup interface is used for backup. backupDup is a
		 cue for SiteManager."
	DEFVAL  { normal }
	::= { wfFrIfDlcmiEntry 33 }

    wfFrDlcmiBackupFilterCct OBJECT-TYPE
	SYNTAX	INTEGER
	ACCESS	read-write
	STATUS	mandatory
	DESCRIPTION
		"The circuit number which defines the ppq filters that
                 the backup interface will use. If 0, the filters
                 defined for the default/main circuit will be used."
	DEFVAL  { 0 }
	::= { wfFrIfDlcmiEntry 34 }

    wfFrDlcmiDebugLevel OBJECT-TYPE
        SYNTAX  INTEGER
        ACCESS  read-write
        STATUS  mandatory
        DESCRIPTION
                "For Bay Networks internal use only."
        DEFVAL  { 0 }
        ::= { wfFrIfDlcmiEntry 35 }

    wfFrDlcmiTraceLevel OBJECT-TYPE
        SYNTAX  INTEGER
        ACCESS  read-write
        STATUS  mandatory
        DESCRIPTION
                "For Bay Networks internal use only."
        DEFVAL  { 0 }
        ::= { wfFrIfDlcmiEntry 36 }

    wfFrDlcmiCongestionMethod OBJECT-TYPE
        SYNTAX  INTEGER {
                    shutdown(1),
                    throttle(2),
                    throttleThenShutdown(3)
                }
        ACCESS  read-write
        STATUS  mandatory
        DESCRIPTION
                "Default congestion control method to use for all VCs
                 on this interface."
        DEFVAL { shutdown }
        ::= { wfFrIfDlcmiEntry 37 }

    wfFrDlcmiShapingTmr OBJECT-TYPE
        SYNTAX  INTEGER(0..8196)
        ACCESS  read-write
        STATUS  mandatory
        DESCRIPTION
                "The interval, in ticks (1/1024th of a second), that VCs
                 are processed for traffic shaping."
        DEFVAL { 128 }
        ::= { wfFrIfDlcmiEntry 38 }

    wfFrDlcmiShapingHiQueueLimit OBJECT-TYPE
        SYNTAX  INTEGER(0..5000)
        ACCESS  read-write
        STATUS  mandatory
        DESCRIPTION
                "The total number of buffers that the interface will
                 allow VCs to queue into the Hi queue. Divided by the
                 number of traffic shaped VCs to get the number of
                 buffers allowed per-VC."
        DEFVAL { 30 }
        ::= { wfFrIfDlcmiEntry 39 }

    wfFrDlcmiShapingNormalQueueLimit OBJECT-TYPE
        SYNTAX  INTEGER(0..5000)
        ACCESS  read-write
        STATUS  mandatory
        DESCRIPTION
                "The total number of buffers that the interface will
                 allow VCs to queue into the Normal queue. Divided by 
                 the number of traffic shaped VCs to get the number of
                 buffers allowed per-VC."
        DEFVAL { 200 }
        ::= { wfFrIfDlcmiEntry 40 }

    wfFrDlcmiShapingLoQueueLimit OBJECT-TYPE
        SYNTAX  INTEGER(0..5000)
        ACCESS  read-write
        STATUS  mandatory
        DESCRIPTION
                "The total number of buffers that the interface will
                 allow VCs to queue into the Lo queue. Divided by the
                 number of traffic shaped VCs to get the number of
                 buffers allowed per-VC."
        DEFVAL { 30 }
        ::= { wfFrIfDlcmiEntry 41 }

    wfFrDlcmiXoffDisable OBJECT-TYPE
        SYNTAX  INTEGER {
                    enabled(1),
                    disabled(2)
                }
        ACCESS  read-write
        STATUS  mandatory
        DESCRIPTION
                "Indicates whether to listen(enabled) or ignore(disabled)
                 XOFF (R-bit) notification"
        DEFVAL  { enabled }
        ::= { wfFrIfDlcmiEntry 42 }

    wfFrDlcmiMissingPolls OBJECT-TYPE
        SYNTAX  Counter
        ACCESS  read-only
        STATUS  mandatory
        DESCRIPTION
                "Number of times there was no status enquiry response
                 to a status enquiry"
        ::= { wfFrIfDlcmiEntry 43 }

    wfFrDlcmiName OBJECT-TYPE
        SYNTAX	DisplayString
        ACCESS	read-write
        STATUS	mandatory
        DESCRIPTION
                "User name for this interface, used by BCC"
        ::= { wfFrIfDlcmiEntry 44 }

    wfFrDlcmiEnableSinglePVCUpdate OBJECT-TYPE
        SYNTAX  INTEGER {
                    enabled(1),
                    disabled(2)
                }
        ACCESS  read-write
        STATUS  mandatory
        DESCRIPTION
                "Enables or disables the processing of Single Async PVC status messages that some 
                switches use. If disabled, Single Async PVC status messages are ignored. All 
                status changes in the FR circuit are based on the processing of full status enquiry 
                response messages. "
        DEFVAL  { enabled }
        ::= { wfFrIfDlcmiEntry 45 }

    wfFrDlcmiAnnexSwEnq OBJECT-TYPE
        SYNTAX  INTEGER {
                    enabled(1),
                    disabled(2)
                }
        ACCESS  read-write
        STATUS  mandatory
        DESCRIPTION
                "Enables or disables the processing of status enquiry
                 on annexdswitch(7) and annexaswitch(8).
                 If it is enabled and the status enquiry is not received
                 from the DTE within wfFrDlcmiAnnexSwEnqTmr,
                 the internal counter will be incremented.
                 If internal counter exceeds wfFrDlcmiErrorThreshold,
                 the circuit will be brought down."
        DEFVAL  { disabled }
        ::= { wfFrIfDlcmiEntry 46 }

    wfFrDlcmiAnnexSwEnqTmr OBJECT-TYPE
        SYNTAX  INTEGER(1..500)
        ACCESS  read-write
        STATUS  mandatory
        DESCRIPTION
                "Specify the timeout value in seconds for the status
                 inquiry on annexdswitch(7) and annexaswitch(8).
                 It is defaulted to 10 seconds."
        DEFVAL  { 10 }
        ::= { wfFrIfDlcmiEntry 47 }

    wfFrDlcmiExtraStatusInfoEnable OBJECT-TYPE
        SYNTAX	INTEGER {
    		    enabled(1),
    		    disabled(2)
    		}
        ACCESS	read-write
        STATUS	mandatory
        DESCRIPTION
                "Indicates whether or not to process extra lmi ies that may received from the switch"
        DEFVAL	{ disabled }
        ::= { wfFrIfDlcmiEntry 48 }

    wfFrVCircuitTable OBJECT-TYPE
        SYNTAX	SEQUENCE OF WfFrVCircuitEntry
        ACCESS	not-accessible
        STATUS	mandatory
        DESCRIPTION
                "Frame Relay Circuit table gives information about a virtual circuits."
        ::= { wfFrameRelay2Group 2 }

    wfFrVCircuitEntry OBJECT-TYPE
        SYNTAX	WfFrVCircuitEntry
        ACCESS	not-accessible
        STATUS	mandatory
        DESCRIPTION
                "An entry in the Frame Relay Circuit table."
        INDEX	{ wfFrCircuitLineNumber,
    		  wfFrCircuitLLIndex,
    		  wfFrCircuitDlci }
        ::= { wfFrVCircuitTable 1 }

    WfFrVCircuitEntry ::= SEQUENCE {
    	    wfFrCircuitDelete
    		INTEGER,
    	    wfFrCircuitLineNumber
    		INTEGER,
    	    wfFrCircuitLLIndex
    		INTEGER,
    	    wfFrCircuitNumber
    		INTEGER,
    	    wfFrCircuitDlci
    		INTEGER,
    	    wfFrCircuitState
    		INTEGER,
    	    wfFrCircuitStateSet
    		INTEGER,
    	    wfFrCircuitReceivedFECNs
    		Counter,
    	    wfFrCircuitReceivedBECNs
    		Counter,
    	    wfFrCircuitSentFrames
    		Counter,
    	    wfFrCircuitSentOctets
    		Counter,
    	    wfFrCircuitReceivedFrames
    		Counter,
    	    wfFrCircuitReceivedOctets
    		Counter,
    	    wfFrCircuitCreationTime
    		TimeTicks,
    	    wfFrCircuitLastTimeChange
    		TimeTicks,
    	    wfFrCircuitCommittedBurst
    		INTEGER,
    	    wfFrCircuitExcessBurst
    		INTEGER,
    	    wfFrCircuitThroughput
    		INTEGER,
    	    wfFrCircuitMulticast
    		INTEGER,
    	    wfFrCircuitType
    		INTEGER,
    	    wfFrCircuitDiscards
    		Counter,
    	    wfFrCircuitDrops
    		Counter,
    	    wfFrCircuitSubCct
    		INTEGER,
    	    wfFrCircuitMode
    		INTEGER,
    	    wfFrCircuitCongestionDisable
    		INTEGER,
    	    wfFrCircuitCongestionState
    		INTEGER,
    	    wfFrCircuitCongestionTmr
    		INTEGER,
    	    wfFrCircuitCongestionCtr
    		INTEGER,
            wfFrCircuitWcpEnable
                INTEGER,
            wfFrCircuitPrimaryHoldTmr
                INTEGER,
            wfFrCircuitInactivityTimer
                INTEGER,
            wfFrCircuitInactivityMode
                INTEGER,
            wfFrCircuitCongestionMethod
                INTEGER,
            wfFrCircuitShapedHiXmits
                Counter,
            wfFrCircuitShapedNormalXmits
                Counter,
            wfFrCircuitShapedLoXmits
                Counter,
            wfFrCircuitShapedHiClippedPkts
                Counter,
            wfFrCircuitShapedNormalClippedPkts
                Counter,
            wfFrCircuitShapedLoClippedPkts
                Counter,
            wfFrCircuitShapedHiQHighWaterPkts
                Gauge,
            wfFrCircuitShapedNormalQHighWaterPkts
                Gauge,
            wfFrCircuitShapedLoQHighWaterPkts
                Gauge,
            wfFrCircuitShapedDroppedPkts
                Counter,
            wfFrCircuitShapedLargePkts
                Counter,
            wfFrCircuitShapedHiTotalOctets
                Counter,
            wfFrCircuitShapedNormalTotalOctets
                Counter,
            wfFrCircuitShapedLoTotalOctets
                Counter,
            wfFrCircuitShapedPktsNotQueued
                Counter,
            wfFrCircuitShapedHighWaterPktsClear
                INTEGER,
            wfFrCircuitShapedHiQueueLimit
                INTEGER,
            wfFrCircuitShapedNormalQueueLimit
                INTEGER,
            wfFrCircuitShapedLoQueueLimit
                INTEGER,
            wfFrCircuitStartupDelay
                INTEGER,
            wfFrCircuitCurHiQueueLimit
                Gauge,
            wfFrCircuitCurNormalQueueLimit
                Gauge,
            wfFrCircuitCurLoQueueLimit
                Gauge,
            wfFrCircuitShapingState
                INTEGER,
            wfFrCircuitBwThreshold
                INTEGER,
            wfFrCircuitReceivedDEs
                Counter,
            wfFrCircuitSentDEs
                Counter
        }

    wfFrCircuitDelete OBJECT-TYPE
        SYNTAX	INTEGER {
    		    created(1),
    		    deleted(2)
    		}
        ACCESS	read-write
        STATUS	mandatory
        DESCRIPTION
                "Indication to delete this frame relay interface."
        DEFVAL	{ created }
        ::= { wfFrVCircuitEntry 1 }

    wfFrCircuitLineNumber OBJECT-TYPE
        SYNTAX	INTEGER
        ACCESS	read-only
        STATUS	mandatory
        DESCRIPTION
                "Instance identifier. This is the line number on which the associated Frame
                Relay interface resides."
        ::= { wfFrVCircuitEntry 2 }

    wfFrCircuitLLIndex OBJECT-TYPE
        SYNTAX	INTEGER
        ACCESS	read-only
        STATUS	mandatory
        DESCRIPTION
                "The Lower layer index uniquely identifies the lower layer in
                cases where the lower layer may be something other than the
                physical layer.  For example if Frame Relay is running over
                an ATM VC, the LLIndex identifies the ATM VC."
        ::= { wfFrVCircuitEntry 3 }

    wfFrCircuitNumber OBJECT-TYPE
        SYNTAX	INTEGER
        ACCESS	read-write
        STATUS	mandatory
        DESCRIPTION
                "The circuit number of this interface."
        ::= { wfFrVCircuitEntry 4 }

    wfFrCircuitDlci OBJECT-TYPE
        SYNTAX	INTEGER {
    		    twobyteminimum(16),
    		    twobytemaximum(1007),
    		    threebyteminimum(1024),
    		    threebytemaximum(64511),
    		    fourbyteminimum(131072),
    		    fourbytemaximum(8257535)
    		}
        ACCESS	read-only
        STATUS	mandatory
        DESCRIPTION
                "One of three instance identifier. This is the Frame Relay 'address'
                of the virtual circuit."
        ::= { wfFrVCircuitEntry 5 }

    wfFrCircuitState OBJECT-TYPE
        SYNTAX	INTEGER {
    		    invalid(1),
    		    active(2),
    		    inactive(3),
    		    xoff(4),
    		    control(5),
                    starting(6),
                    disabled(7)
    		}
        ACCESS	read-only
        STATUS	mandatory
        DESCRIPTION
                "Indicates the state of the particular virtual circuit."
        DEFVAL	{ invalid }
        ::= { wfFrVCircuitEntry 6 }

    wfFrCircuitStateSet OBJECT-TYPE
        SYNTAX	INTEGER {
    		    invalid(1),
    		    active(2),
    		    inactive(3),
    		    disabled(7)
    		}
        ACCESS	read-write
        STATUS	mandatory
        DESCRIPTION
                "User access for setting the state of a virtual circuit"
        DEFVAL	{ invalid }
        ::= { wfFrVCircuitEntry 7 }

    wfFrCircuitReceivedFECNs OBJECT-TYPE
        SYNTAX	Counter
        ACCESS	read-only
        STATUS	mandatory
        DESCRIPTION
                "Number of frames received indicating forward congestion."
        ::= { wfFrVCircuitEntry 8 }

    wfFrCircuitReceivedBECNs OBJECT-TYPE
        SYNTAX	Counter
        ACCESS	read-only
        STATUS	mandatory
        DESCRIPTION
                "Number of frames received indicating backward congestion."
        ::= { wfFrVCircuitEntry 9 }

    wfFrCircuitSentFrames OBJECT-TYPE
        SYNTAX	Counter
        ACCESS	read-only
        STATUS	mandatory
        DESCRIPTION
                "The number of frames sent from this virtual circuit."
        ::= { wfFrVCircuitEntry 10 }

    wfFrCircuitSentOctets OBJECT-TYPE
        SYNTAX	Counter
        ACCESS	read-only
        STATUS	mandatory
        DESCRIPTION
                "The number of octets sent from this virtual circuit."
        ::= { wfFrVCircuitEntry 11 }

    wfFrCircuitReceivedFrames OBJECT-TYPE
        SYNTAX	Counter
        ACCESS	read-only
        STATUS	mandatory
        DESCRIPTION
                "The number of frames received from this virtual circuit."
        ::= { wfFrVCircuitEntry 12 }

    wfFrCircuitReceivedOctets OBJECT-TYPE
        SYNTAX	Counter
        ACCESS	read-only
        STATUS	mandatory
        DESCRIPTION
                "The number of octets received from this virtual circuit."
        ::= { wfFrVCircuitEntry 13 }

    wfFrCircuitCreationTime OBJECT-TYPE
        SYNTAX	TimeTicks
        ACCESS	read-only
        STATUS	mandatory
        DESCRIPTION
                "The value of sysUpTime when the vc was created."
        ::= { wfFrVCircuitEntry 14 }

    wfFrCircuitLastTimeChange OBJECT-TYPE
        SYNTAX	TimeTicks
        ACCESS	read-only
        STATUS	mandatory
        DESCRIPTION
                "The value of sysUpTime when last there was a change in vc state."
        ::= { wfFrVCircuitEntry 15 }

    wfFrCircuitCommittedBurst OBJECT-TYPE
        SYNTAX	INTEGER
        ACCESS	read-write
        STATUS	mandatory
        DESCRIPTION
                "Indicates the maximum amount of data, in bits, that the network
                agrees to transfer under normal conditions, during the measurement
                interval."
        ::= { wfFrVCircuitEntry 16 }

    wfFrCircuitExcessBurst OBJECT-TYPE
        SYNTAX	INTEGER
        ACCESS	read-write
        STATUS	mandatory
        DESCRIPTION
                "Indicates teh maximum amount of uncommitted data bits that the network
                will attempt to deliver over the measurement interval."
        ::= { wfFrVCircuitEntry 17 }

    wfFrCircuitThroughput OBJECT-TYPE
        SYNTAX	INTEGER
        ACCESS	read-write
        STATUS	mandatory
        DESCRIPTION
                "This is the average number of 'Frame Relay Information Field'
                bits transferred per second across a user network interface in one
                direction, measured over the measurement interval."
        ::= { wfFrVCircuitEntry 18 }

    wfFrCircuitMulticast OBJECT-TYPE
        SYNTAX	INTEGER {
    		    unicast(1),
    		    multicast(2)
    		}
        ACCESS	read-write
        STATUS	mandatory
        DESCRIPTION
                "Indicates whether this DLCI is used for multicast or single destination."
        DEFVAL	{ unicast }
        ::= { wfFrVCircuitEntry 19 }

    wfFrCircuitType OBJECT-TYPE
        SYNTAX	INTEGER {
    		    static(1),
    		    dynamic(2),
                    dynamicsvc(3)
    		}
        ACCESS	read-only
        STATUS	mandatory
        DESCRIPTION
                "Indication of whether the VC was manually created (static),
                or dynamically created (dynamic) via the data link control
                management interface."
        DEFVAL	{ static }
        ::= { wfFrVCircuitEntry 20 }

    wfFrCircuitDiscards OBJECT-TYPE
        SYNTAX	Counter
        ACCESS	read-only
        STATUS	mandatory
        DESCRIPTION
                "The number of inbound frames discarded because of format errors,
                because the VC is inactive or because the protocol was not registered
                for this circuit."
        ::= { wfFrVCircuitEntry 21 }

    wfFrCircuitDrops OBJECT-TYPE
        SYNTAX	Counter
        ACCESS	read-only
        STATUS	mandatory
        DESCRIPTION
                "Indicates how many outbound frames were dropped. Usually these are
                dropped because the VC is not active."
        ::= { wfFrVCircuitEntry 22 }

    wfFrCircuitSubCct OBJECT-TYPE
        SYNTAX	INTEGER
        ACCESS	read-write
        STATUS	mandatory
        DESCRIPTION
                "Circuit number to use for this VC when configured in hybrid
                (for bridging) or direct access (VC as a circuit) mode."
        ::= { wfFrVCircuitEntry 23 }

    wfFrCircuitMode OBJECT-TYPE
        SYNTAX	INTEGER {
    		    group(1),
    		    hybrid(2),
    		    direct(3)
    		}
        ACCESS	read-write
        STATUS	mandatory
        DESCRIPTION
                "The mode of the given VC.
                GROUP - treats the VC as one of many vc's on a circuit.
                HYBRID - treats the VC as one of many vc's on a circuit for
                  protocol traffic, but as a separate circuit for bridging.
                DIRECT - treats the VC as a separate circuit for all applications."
        DEFVAL	{ group }
        ::= { wfFrVCircuitEntry 24 }

    wfFrCircuitCongestionDisable OBJECT-TYPE
        SYNTAX	INTEGER {
    		    enabled(1),
    		    disabled(2),
    		    inherit(3)
    		}
        ACCESS	read-write
        STATUS	mandatory
        DESCRIPTION
                "This indicates whether the congestion algorithm should be used
                for this VC.  If this is not set, the value is inherited from the
                DLCMI record."
        DEFVAL	{ inherit }
        ::= { wfFrVCircuitEntry 25 }

    wfFrCircuitCongestionState OBJECT-TYPE
        SYNTAX	INTEGER {
    		    forwarding(1),
    		    congested(2),
                    throttling(3)
    		}
        ACCESS	read-only
        STATUS	mandatory
        DESCRIPTION
                "This is used to indicate whether or not the VC is in a congested
                state.  If it is, no traffic will be sent on this VC."
        DEFVAL	{ forwarding }
        ::= { wfFrVCircuitEntry 26 }

    wfFrCircuitCongestionTmr OBJECT-TYPE
        SYNTAX	INTEGER {
    		    half(1),
    		    one(2),
    		    oneandhalf(3),
    		    two(4),
    		    twoandhalf(5),
    		    three(6),
    		    threeandhalf(7),
    		    four(8),
    		    fourandhalf(9),
    		    five(10)
    		}
        ACCESS	read-write
        STATUS	mandatory
        DESCRIPTION
                "This is the time period over which congestion notifications are
                counted.  It is also the period during which the VC will cease
                sending information before resuming transmission if no
                congestion notifications are received."
        DEFVAL	{ one }
        ::= { wfFrVCircuitEntry 27 }

    wfFrCircuitCongestionCtr OBJECT-TYPE
        SYNTAX	INTEGER(1..500)
        ACCESS	read-write
        STATUS	mandatory
        DESCRIPTION
                "This represents the number of congestion notifications, when
                received within wfFrCircuitCongestionTmr time, that will result
                in the VC ceasing transmissions."
        DEFVAL	{ 20 }
        ::= { wfFrVCircuitEntry 28 }

    wfFrCircuitWcpEnable OBJECT-TYPE
        SYNTAX	INTEGER {
                    enabled(1),
                    disabled(2)
                }
        ACCESS	read-write
        STATUS	mandatory
        DESCRIPTION
                "Enable Compression"
        DEFVAL	{ enabled }
        ::= { wfFrVCircuitEntry 29 }

    wfFrCircuitPrimaryHoldTmr OBJECT-TYPE
        SYNTAX  INTEGER
        ACCESS  read-write
        STATUS  mandatory
        DESCRIPTION
                "The maximum number of seconds that a Frame Relay PVC
                 Primary will be kept inactive, ignoring status
                 messages, when it is terminated because the backup has
                 started."
        DEFVAL   { 30 }
        ::= { wfFrVCircuitEntry 30 }
        
    wfFrCircuitInactivityTimer OBJECT-TYPE
        SYNTAX  INTEGER
        ACCESS  read-only
        STATUS  mandatory
        DESCRIPTION
                "Inactivity Timer for SVCs. Zero disables timer."
        DEFVAL   { 0 }
        ::= { wfFrVCircuitEntry 31 }

    wfFrCircuitInactivityMode OBJECT-TYPE
        SYNTAX	INTEGER {
    		    bothdirections(1),
    		    transmitonly(2),
    		    receiveonly(3),
    		    eitherdirection(4)
    		}
        ACCESS  read-only
        STATUS  mandatory
        DESCRIPTION
                "Specifies which packets will reset the SVC inactivity timer."
        DEFVAL   { bothdirections }
        ::= { wfFrVCircuitEntry 32 }

    wfFrCircuitCongestionMethod OBJECT-TYPE
        SYNTAX  INTEGER {
                    shutdown(1),
                    throttle(2),
                    throttleThenShutdown(3),
                    inherit(4)
                }
        ACCESS  read-write
        STATUS  mandatory
        DESCRIPTION
                "The congestion method to use on this VC."
        DEFVAL  { inherit }
        ::= { wfFrVCircuitEntry 33 }

    wfFrCircuitShapedHiXmits OBJECT-TYPE
        SYNTAX  Counter
        ACCESS  read-only
        STATUS  mandatory
        DESCRIPTION
                "Same as wfCctOptsEntry.wfCctOptsHiXmits for this VC"
        ::= { wfFrVCircuitEntry 34 }

    wfFrCircuitShapedNormalXmits OBJECT-TYPE
        SYNTAX  Counter
        ACCESS  read-only
        STATUS  mandatory
        DESCRIPTION
                "Same as wfCctOptsEntry.wfCctOptsNormalXmits for this
                 VC"
        ::= { wfFrVCircuitEntry 35 }

    wfFrCircuitShapedLoXmits OBJECT-TYPE
        SYNTAX  Counter
        ACCESS  read-only
        STATUS  mandatory
        DESCRIPTION
                "Same as wfCctOptsEntry.wfCctOptsLoXmits for this VC"
        ::= { wfFrVCircuitEntry 36 }

    wfFrCircuitShapedHiClippedPkts OBJECT-TYPE
        SYNTAX  Counter
        ACCESS  read-only
        STATUS  mandatory
        DESCRIPTION
                "Same as wfCctOptsEntry.wfCctOptsHiClippedPkts for
                 this VC"
        ::= { wfFrVCircuitEntry 37 }

    wfFrCircuitShapedNormalClippedPkts OBJECT-TYPE
        SYNTAX  Counter
        ACCESS  read-only
        STATUS  mandatory
        DESCRIPTION
                "Same as wfCctOptsEntry.wfCctOptsNormalClippedPkts for
                 this VC"
        ::= { wfFrVCircuitEntry 38 }

    wfFrCircuitShapedLoClippedPkts OBJECT-TYPE
        SYNTAX  Counter
        ACCESS  read-only
        STATUS  mandatory
        DESCRIPTION
                "Same as wfCctOptsEntry.wfCctOptsLoClippedPkts for
                 this VC"
        ::= { wfFrVCircuitEntry 39 }

    wfFrCircuitShapedHiQHighWaterPkts OBJECT-TYPE
        SYNTAX  Gauge
        ACCESS  read-only
        STATUS  mandatory
        DESCRIPTION
                "Same as wfCctOptsEntry.wfCctOptsHiQHighWaterPkts for
                 this VC"
        ::= { wfFrVCircuitEntry 40 }

    wfFrCircuitShapedNormalQHighWaterPkts OBJECT-TYPE
        SYNTAX  Gauge
        ACCESS  read-only
        STATUS  mandatory
        DESCRIPTION
                "Same as wfCctOptsEntry.wfCctOptsNormalQHighWaterPkts
                 for this VC"
        ::= { wfFrVCircuitEntry 41 }

    wfFrCircuitShapedLoQHighWaterPkts OBJECT-TYPE
        SYNTAX  Gauge
        ACCESS  read-only
        STATUS  mandatory
        DESCRIPTION
                "Same as wfCctOptsEntry.wfCctOptsLoQHighWaterPkts for
                 this VC"
        ::= { wfFrVCircuitEntry 42 }

    wfFrCircuitShapedDroppedPkts OBJECT-TYPE
        SYNTAX  Counter
        ACCESS  read-only
        STATUS  mandatory
        DESCRIPTION
                "Same as wfCctOptsEntry.wfCctOptsDroppedPkts for this
                 VC"
        ::= { wfFrVCircuitEntry 43 }

    wfFrCircuitShapedLargePkts OBJECT-TYPE
        SYNTAX  Counter
        ACCESS  read-only
        STATUS  mandatory
        DESCRIPTION
                "Same as wfCctOptsEntry.wfCctOptsLargePkts for this
                 VC"
        ::= { wfFrVCircuitEntry 44 }

    wfFrCircuitShapedHiTotalOctets OBJECT-TYPE
        SYNTAX  Counter
        ACCESS  read-only
        STATUS  mandatory
        DESCRIPTION
                "Same as wfCctOptsEntry.wfCctOptsHiTotalOctets for
                 this VC"
        ::= { wfFrVCircuitEntry 45 }

    wfFrCircuitShapedNormalTotalOctets OBJECT-TYPE
        SYNTAX  Counter
        ACCESS  read-only
        STATUS  mandatory
        DESCRIPTION
                "Same as wfCctOptsEntry.wfCctOptsNormalTotalOctets for
                 this VC"
        ::= { wfFrVCircuitEntry 46 }

    wfFrCircuitShapedLoTotalOctets OBJECT-TYPE
        SYNTAX  Counter
        ACCESS  read-only
        STATUS  mandatory
        DESCRIPTION
                "Same as wfCctOptsEntry.wfCctOptsLoTotalOctets for
                 this VC"
        ::= { wfFrVCircuitEntry 47 }

    wfFrCircuitShapedPktsNotQueued OBJECT-TYPE
        SYNTAX  Counter
        ACCESS  read-only
        STATUS  mandatory
        DESCRIPTION
                "Same as wfCctOptsEntry.wfCctOptsPktsNotQueued for
                 this VC"
        ::= { wfFrVCircuitEntry 48 }

    wfFrCircuitShapedHighWaterPktsClear OBJECT-TYPE
        SYNTAX  INTEGER
        ACCESS  read-write
        STATUS  mandatory
        DESCRIPTION
                "Same as wfCctOptsEntry.wfCctOptsHighWaterPktsClear
                 for this VC"
        DEFVAL  { 0 }
        ::= { wfFrVCircuitEntry 49 }

    wfFrCircuitShapedHiQueueLimit OBJECT-TYPE
        SYNTAX  INTEGER(0..5000) 
        ACCESS  read-write
        STATUS  mandatory
        DESCRIPTION
                "Same as wfCctOptsEntry.wfCctOptsHighPriorityQueueLimit
                 for this VC. If set to inherit (0), then the VC uses 
                 part of the global allocation of buffers in the DLCMI
                 entry."
        DEFVAL  { 0 }
        ::= { wfFrVCircuitEntry 50 }

    wfFrCircuitShapedNormalQueueLimit OBJECT-TYPE
        SYNTAX  INTEGER(0..5000)
        ACCESS  read-write
        STATUS  mandatory
        DESCRIPTION
                "Same as wfCctOptsEntry.wfCctOptsNormalPriorityQueueLimit
                 for this VC. If set to inherit (0), then the VC uses
                 part of the global allocation of buffers in the DLCMI
                 entry."
        DEFVAL  { 0 }
        ::= { wfFrVCircuitEntry 51 }

    wfFrCircuitShapedLoQueueLimit OBJECT-TYPE
        SYNTAX  INTEGER(0..5000)
        ACCESS  read-write
        STATUS  mandatory
        DESCRIPTION
                "Same as wfCctOptsEntry.wfCctOptsLowPriorityQueueLimit
                 for this VC. If set to inherit (0), then the VC uses
                 part of the global allocation of buffers in the DLCMI
                 entry."
        DEFVAL  { 0 }
        ::= { wfFrVCircuitEntry 52 }

    wfFrCircuitStartupDelay OBJECT-TYPE
        SYNTAX  INTEGER
        ACCESS  read-write
        STATUS  mandatory
        DESCRIPTION
                "Number of seconds the VC should wait before creating
                 the circuit or doing a dp_vc_line."
        DEFVAL  { 0 }
        ::= { wfFrVCircuitEntry 53 }

    wfFrCircuitCurHiQueueLimit OBJECT-TYPE
        SYNTAX  Gauge
        ACCESS  read-only
        STATUS  mandatory
        DESCRIPTION
                "This is the current high queue limit, based on the
                 VC and DLCMI configuration."
        DEFVAL  { 0 }
        ::= { wfFrVCircuitEntry 54 }

    wfFrCircuitCurNormalQueueLimit OBJECT-TYPE
        SYNTAX  Gauge
        ACCESS  read-only
        STATUS  mandatory
        DESCRIPTION
                "This is the current normal queue limit, based on the
                 VC and DLCMI configuration."
        DEFVAL  { 0 }
        ::= { wfFrVCircuitEntry 55 }

    wfFrCircuitCurLoQueueLimit OBJECT-TYPE
        SYNTAX  Gauge
        ACCESS  read-only
        STATUS  mandatory
        DESCRIPTION
                "This is the current low  queue limit, based on the
                 VC and DLCMI configuration."
        DEFVAL  { 0 }
        ::= { wfFrVCircuitEntry 56 }
        
    wfFrCircuitShapingState OBJECT-TYPE
        SYNTAX  INTEGER {
                    disabled(1),
                    invalid(2),
                    committed-shaping(3),
                    excess-shaping(4),
                    zero-cir(5)
                }
        ACCESS  read-only
        STATUS  mandatory
        DESCRIPTION
                "Indicates current state of a VCs traffic shaping
                 configuration" 
        DEFVAL  { disabled }
        ::= { wfFrVCircuitEntry 57 }

    wfFrCircuitBwThreshold OBJECT-TYPE
        SYNTAX  INTEGER
        ACCESS  read-write
        STATUS  mandatory
        DESCRIPTION
                "Set 3 to 10 times of the CIR configured with this PVC.
                 The threshold value for starting to send Normal and
                 Low Priority traffic is calculated based on physical
                 line speed. Setting this object to 3 to 10 times of CIR
                 value will provide more chance to the Normal and Low
                 Priority traffic so that it will help the Normal and Low
                 Priority traffic of low speed links over high speed
                 physical line from starvation such as 56Kbps and 65Kbps
                 lines over HSSI."
        DEFVAL  { 0 }
        ::= { wfFrVCircuitEntry 58 }

    wfFrCircuitReceivedDEs OBJECT-TYPE
        SYNTAX  Counter
        ACCESS  read-only
        STATUS  mandatory
        DESCRIPTION
                "Number of frames received from the network indicating
                 that they were eligible for discard since the virtual
                 circuit was created. This occurs when the remote DTE 
                 sets the DE flag, or when in remote DTE's switch detects
                 that the frame was received as Excess Burst data." 
        ::= { wfFrVCircuitEntry 59 }

    wfFrCircuitSentDEs OBJECT-TYPE
        SYNTAX  Counter
        ACCESS  read-only
        STATUS  mandatory
        DESCRIPTION
                "Number of frames sent from the network indicating
                 that they were eligible for discard since the virtual
                 circuit was created. This occurs when the local DTE 
                 sets the DE flag, indicating that during Network congestion
                 situations those frames should be discarded in preference
                 of ther frames sent without the DE bit set." 
        ::= { wfFrVCircuitEntry 60 }

    wfFrCctErrorTable OBJECT-TYPE
        SYNTAX	SEQUENCE OF WfFrCctErrorEntry
        ACCESS	not-accessible
        STATUS	mandatory
        DESCRIPTION
                "The Frame Relay Circuit Error Table."
        ::= { wfFrameRelay2Group 4 }

    wfFrCctErrorEntry OBJECT-TYPE
        SYNTAX	WfFrCctErrorEntry
        ACCESS	not-accessible
        STATUS	mandatory
        DESCRIPTION
                "An entry in the Frame Relay Circuit Error table."
        INDEX	{ wfFrCctErrorCct }
        ::= { wfFrCctErrorTable 1 }

    WfFrCctErrorEntry ::= SEQUENCE {
    	    wfFrCctErrorCct
    		INTEGER,
    	    wfFrCctErrorDrops
    		Counter,
    	    wfFrCctErrorDiscards
    		Counter
        }

    wfFrCctErrorCct OBJECT-TYPE
        SYNTAX	INTEGER
        ACCESS	read-only
        STATUS	mandatory
        DESCRIPTION
                "Instance Identifier - indicates the frame relay circuit number"
        ::= { wfFrCctErrorEntry 1 }

    wfFrCctErrorDrops OBJECT-TYPE
        SYNTAX	Counter
        ACCESS	read-only
        STATUS	mandatory
        DESCRIPTION
                "Indicates the number of frames that were dropped at the
                circuit level.  Generally this is because the particular
                protocol (within the inbound frame) was not registered
                for this circuit."
        ::= { wfFrCctErrorEntry 2 }

    wfFrCctErrorDiscards OBJECT-TYPE
        SYNTAX	Counter
        ACCESS	read-only
        STATUS	mandatory
        DESCRIPTION
                "Indicates the number of frames that were discarded at the
                circuit level.  Generally this is because the outbound
                frame was too long, or too short."
        ::= { wfFrCctErrorEntry 3 }

    wfFrServiceRecordTable OBJECT-TYPE
        SYNTAX	SEQUENCE OF WfFrServiceRecordEntry
        ACCESS	not-accessible
        STATUS	mandatory
        DESCRIPTION
                "Frame Relay service records group virtual circuits together."
        ::= { wfFrameRelay2Group 5 }

    wfFrServiceRecordEntry OBJECT-TYPE
        SYNTAX	WfFrServiceRecordEntry
        ACCESS	not-accessible
        STATUS	mandatory
        DESCRIPTION
                "An entry in the Frame Relay Service Record table."
        INDEX	{ wfFrServiceRecordLineNumber,
    		  wfFrServiceRecordLLIndex,
    		  wfFrServiceRecordCircuitNumber }
        ::= { wfFrServiceRecordTable 1 }

    WfFrServiceRecordEntry ::= SEQUENCE {
    	    wfFrServiceRecordDelete
    		INTEGER,
    	    wfFrServiceRecordLineNumber
    		INTEGER,
    	    wfFrServiceRecordLLIndex
    		INTEGER,
    	    wfFrServiceRecordCircuitNumber
    		INTEGER,
    	    wfFrServiceRecordDefaultFlag
    		INTEGER,
    	    wfFrServiceRecordNumberVCs
    		INTEGER,
    	    wfFrServiceRecordName
    		DisplayString,
    	    wfFrServiceRecordState
    		INTEGER,
    	    wfFrServiceRecordPreMultiCircuit
		INTEGER,
	    wfFrServiceRecordBackupFilterCct
		INTEGER,
	    wfFrServiceRecordBackupLineNumber
		INTEGER,
	    wfFrServiceRecordBackupLLIndex
		INTEGER,
            wfFrServiceRecordBackupMainCct
                INTEGER,
            wfFrServiceRecordPrimaryLineNumber
                INTEGER,
            wfFrServiceRecordPrimaryLLIndex
                INTEGER,
            wfFrServiceRecordPrimaryMainCct
                INTEGER,
	    wfFrServiceRecordSVCDisable
                INTEGER,
	    wfFrServiceRecordSVCLocNum
		DisplayString,
	    wfFrServiceRecordSVCLocSubAdr
		DisplayString,
	    wfFrServiceRecordSVCLocPlan
                INTEGER,
	    wfFrServiceRecordSVCLocTypeNum
                INTEGER,
	    wfFrServiceRecordSVCCallBlock		
                INTEGER,
	    wfFrServiceRecordSVCInScrnDisable
                INTEGER,
	    wfFrServiceRecordSVCInScrnUsage 
                INTEGER,
	    wfFrServiceRecordSVCInactTimer
                INTEGER,
	    wfFrServiceRecordSVCInactMode
                INTEGER,
    	    wfFrServiceRecordNumberStaticVCs
    		INTEGER,
    	    wfFrServiceRecordNumberDynamicVCs
    		INTEGER,
    	    wfFrServiceRecordNumberSVCs
    		INTEGER,
    	    wfFrServiceRecordNumberActiveVCs
    		INTEGER,
            wfFrServiceRecordifLastChange
                TimeTicks,
            wfFrServiceRecordifInOctets
                Counter,
            wfFrServiceRecordifInDiscards
                Counter,
            wfFrServiceRecordifOutOctets
                Counter,
            wfFrServiceRecordifOutDiscards
                Counter,
            wfFrServiceRecordifOutCtrlPkts
                Counter,
            wfFrServiceRecordifInCtrlPkts
                Counter
        }

    wfFrServiceRecordDelete OBJECT-TYPE
        SYNTAX	INTEGER {
    		    created(1),
    		    deleted(2)
    		}
        ACCESS	read-write
        STATUS	mandatory
        DESCRIPTION
                "Indication to delete this frame relay service record."
        DEFVAL	{ created }
        ::= { wfFrServiceRecordEntry 1 }

    wfFrServiceRecordLineNumber OBJECT-TYPE
        SYNTAX	INTEGER
        ACCESS	read-only
        STATUS	mandatory
        DESCRIPTION
                "Instance identifier. This is the line number on which the associated Frame
                Relay interface resides."
        ::= { wfFrServiceRecordEntry 2 }

    wfFrServiceRecordLLIndex OBJECT-TYPE
        SYNTAX	INTEGER
        ACCESS	read-only
        STATUS	mandatory
        DESCRIPTION
                "The Lower layer index uniquely identifies the lower layer in
                cases where the lower layer may be something other than the
                physical layer.  For example if Frame Relay is running over
                an ATM VC, the LLIndex identifies the ATM VC."
        ::= { wfFrServiceRecordEntry 3 }

    wfFrServiceRecordCircuitNumber OBJECT-TYPE
        SYNTAX	INTEGER
        ACCESS	read-only
        STATUS	mandatory
        DESCRIPTION
                "The circuit number of this interface."
        ::= { wfFrServiceRecordEntry 4 }

    wfFrServiceRecordDefaultFlag OBJECT-TYPE
        SYNTAX	INTEGER {
    		    true(1),
    		    false(2)
    		}
        ACCESS	read-write
        STATUS	mandatory
        DESCRIPTION
                "Identifies default service record for VCs added via the
                frame relay switch."
        DEFVAL	{ false }
        ::= { wfFrServiceRecordEntry 5 }

    wfFrServiceRecordNumberVCs OBJECT-TYPE
        SYNTAX	INTEGER
        ACCESS	read-write
        STATUS	mandatory
        DESCRIPTION
                "Number of virtual circuit associated with a service record."
        ::= { wfFrServiceRecordEntry 6 }

    wfFrServiceRecordName OBJECT-TYPE
        SYNTAX	DisplayString
        ACCESS	read-write
        STATUS	mandatory
        DESCRIPTION
                "User name for circuit"
        ::= { wfFrServiceRecordEntry 7 }

    wfFrServiceRecordState OBJECT-TYPE
        SYNTAX	INTEGER {
    		    inactive(1),
    		    active(2),
    		    invalid(3)
    		}
        ACCESS	read-only
        STATUS	mandatory
        DESCRIPTION
                "Used to identify new service record instances"
        DEFVAL	{ inactive }
        ::= { wfFrServiceRecordEntry 8 }

     wfFrServiceRecordPreMultiCircuit OBJECT-TYPE
        SYNTAX	INTEGER
        ACCESS	read-write
        STATUS	mandatory
        DESCRIPTION
                "circuit number prior to enabling multiline, allows
		 restoration of pre-multiline circuit"
        DEFVAL  { 0 }
        ::= { wfFrServiceRecordEntry 9 }

     wfFrServiceRecordBackupFilterCct OBJECT-TYPE
	SYNTAX	INTEGER
	ACCESS	read-write
	STATUS	mandatory
	DESCRIPTION
		"The circuit number used by the backup interface
		 to store/define the ppq filter configuration."
	DEFVAL  { 0 }
	::= { wfFrServiceRecordEntry 10 }

     wfFrServiceRecordBackupLineNumber OBJECT-TYPE
	SYNTAX	INTEGER
	ACCESS	read-write
	STATUS	mandatory
	DESCRIPTION
		"Indicates one of the backup interfaces for this primary
		 interface. The circuit on this service record should be
                 shared onto that backup interface."
	DEFVAL  { 0 }
	::= { wfFrServiceRecordEntry 11 }

     wfFrServiceRecordBackupLLIndex OBJECT-TYPE
	SYNTAX	INTEGER
	ACCESS	read-write
	STATUS	mandatory
	DESCRIPTION
		"Indicates one of the backup interfaces for this primary
                 interface. The circuit on this service record should be
                 shared onto that backup interface." 
	DEFVAL  { 0 }
	::= { wfFrServiceRecordEntry 12 }

     wfFrServiceRecordBackupMainCct OBJECT-TYPE
	SYNTAX	INTEGER
	ACCESS	read-write
	STATUS	mandatory
	DESCRIPTION
		"Indicates the main circuit of one of the backup interfaces 
                 for this primary interface. The circuit on this service 
                 record should be shared onto that backup interface."
	DEFVAL  { 0 }
	::= { wfFrServiceRecordEntry 13 }

     wfFrServiceRecordPrimaryLineNumber OBJECT-TYPE
	SYNTAX	INTEGER
	ACCESS	read-write
	STATUS	mandatory
	DESCRIPTION
		"Indicates the primary interface for this backup interface
		 This should be set only in the Default Service Record."
	DEFVAL  { 0 }
	::= { wfFrServiceRecordEntry 14 }

     wfFrServiceRecordPrimaryLLIndex OBJECT-TYPE
	SYNTAX	INTEGER
	ACCESS	read-write
	STATUS	mandatory
	DESCRIPTION
		"Indicates the primary interface for this backup interface. 
                 This should be set only in the Default Service Record."
	DEFVAL  { 0 }
	::= { wfFrServiceRecordEntry 15 }

     wfFrServiceRecordPrimaryMainCct OBJECT-TYPE
	SYNTAX	INTEGER
	ACCESS	read-write
	STATUS	mandatory
	DESCRIPTION
		"Indicates the main circuit on the primary interface for this 
                 backup interface. This should be set only in the Default 
                 Service Record."
	DEFVAL  { 0 }
	::= { wfFrServiceRecordEntry 16 }

    wfFrServiceRecordSVCDisable OBJECT-TYPE
	SYNTAX	INTEGER {
		enabled(1),
		disabled(2)
	}
	ACCESS	read-write
	STATUS	mandatory
	DESCRIPTION
		" Allow SVCs on this service record. "
	DEFVAL	{ disabled }
	::= { wfFrServiceRecordEntry 17 }

    wfFrServiceRecordSVCLocNum OBJECT-TYPE
	SYNTAX	DisplayString
	ACCESS	read-write
	STATUS	mandatory
	DESCRIPTION
		" Number associated with this service record. "
	::= { wfFrServiceRecordEntry 18 }

    wfFrServiceRecordSVCLocSubAdr OBJECT-TYPE
	SYNTAX	DisplayString
	ACCESS	read-write
	STATUS	mandatory
	DESCRIPTION
		" Subaddress of type NSAP (Q.931) further qualifies number "
	::= { wfFrServiceRecordEntry 19 }

    wfFrServiceRecordSVCLocPlan OBJECT-TYPE
	SYNTAX  INTEGER {
		e164(1),
		x121(3)
        }
	ACCESS	read-write
	STATUS	mandatory
	DESCRIPTION
		" Supported Q.931 4.3.8/4.3.10 numbering plans. Each
		  plan is represented by the 4 least significant bits
		  to align with the values stated in Q.931. "
	DEFVAL	{ x121 }
	::= { wfFrServiceRecordEntry 20 }

    wfFrServiceRecordSVCLocTypeNum OBJECT-TYPE
	SYNTAX  INTEGER {
                unknown(1),
		international(2)
        }
	ACCESS	read-write
	STATUS	mandatory
	DESCRIPTION
		" Supported Q.931 4.3.8/4.3.10 types of number. Each
		  type is represented by a value one greater than 
		  the values stated in Q.931. "
	DEFVAL	{ international }
	::= { wfFrServiceRecordEntry 21 }

    wfFrServiceRecordSVCCallBlock OBJECT-TYPE
        SYNTAX  INTEGER {
		none(1),
		inbound(2),
		outbound(3),
		all(4)
	}
        ACCESS  read-write
        STATUS  mandatory
        DESCRIPTION
                "Allow all calls, block inbound, block outbound, block 
		 all calls. "
        DEFVAL   { none }
	::= { wfFrServiceRecordEntry 22 }

    wfFrServiceRecordSVCInScrnDisable OBJECT-TYPE
	SYNTAX	INTEGER {
		enabled(1),
		disabled(2)
	}
        ACCESS  read-write
        STATUS  mandatory
        DESCRIPTION
                " Enable SVC call screening. "
        DEFVAL   { disabled }
	::= { wfFrServiceRecordEntry 23 }

    wfFrServiceRecordSVCInScrnUsage OBJECT-TYPE
	SYNTAX	INTEGER {
		include(1),
		exclude(2)
	}
        ACCESS  read-write
        STATUS  mandatory
        DESCRIPTION
                " Type of SVC call screening. "
        DEFVAL   { include }
	::= { wfFrServiceRecordEntry 24 }

    wfFrServiceRecordSVCInactTimer OBJECT-TYPE
        SYNTAX  INTEGER(0..2147483647)
        ACCESS  read-write
        STATUS  mandatory
        DESCRIPTION
                "Inactivity Timer for SVCs. Zero disables timer."
        DEFVAL   { 60 }
	::= { wfFrServiceRecordEntry 25 }

    wfFrServiceRecordSVCInactMode OBJECT-TYPE
        SYNTAX	INTEGER {
    		    bothdirections(1),
    		    transmitonly(2),
    		    receiveonly(3),
    		    eitherdirection(4)
    		}
        ACCESS  read-write
        STATUS  mandatory
        DESCRIPTION
                "Inactivity check mode"
        DEFVAL   { bothdirections }
	::= { wfFrServiceRecordEntry 26 }

    wfFrServiceRecordNumberStaticVCs OBJECT-TYPE
        SYNTAX	INTEGER
        ACCESS	read-only
        STATUS	mandatory
        DESCRIPTION
                "Number of static vcs associated with a service record."
        ::= { wfFrServiceRecordEntry 27 }

    wfFrServiceRecordNumberDynamicVCs OBJECT-TYPE
        SYNTAX	INTEGER
        ACCESS	read-only
        STATUS	mandatory
        DESCRIPTION
                "Number of dynamic vcs associated with a service record."
        ::= { wfFrServiceRecordEntry 28 }

    wfFrServiceRecordNumberSVCs OBJECT-TYPE
        SYNTAX	INTEGER
        ACCESS	read-only
        STATUS	mandatory
        DESCRIPTION
                "Number of svcs associated with a service record."
        ::= { wfFrServiceRecordEntry 29 }

    wfFrServiceRecordNumberActiveVCs OBJECT-TYPE
        SYNTAX	INTEGER
        ACCESS	read-only
        STATUS	mandatory
        DESCRIPTION
                "Number of active vcs associated with a service record."
        ::= { wfFrServiceRecordEntry 30 }

    wfFrServiceRecordifLastChange OBJECT-TYPE
        SYNTAX	TimeTicks
        ACCESS	read-only
        STATUS	mandatory
        DESCRIPTION
                "The value of sysUpTime when last there was a
                 change in a vc state."
        ::= { wfFrServiceRecordEntry 31 }

     wfFrServiceRecordifInOctets OBJECT-TYPE
        SYNTAX	Counter
        ACCESS	read-only
        STATUS	mandatory
        DESCRIPTION
                "The number of octets received from virtual circuits."
        ::= { wfFrServiceRecordEntry 32 }

    wfFrServiceRecordifInDiscards OBJECT-TYPE
        SYNTAX	Counter
        ACCESS	read-only
        STATUS	mandatory
        DESCRIPTION
                "The number of inbound frames discarded because of
                 format errors, because a VC is inactive or because
                 the protocol was not registered for this circuit."
        ::= { wfFrServiceRecordEntry 33 }

    wfFrServiceRecordifOutOctets OBJECT-TYPE
        SYNTAX	Counter
        ACCESS	read-only
        STATUS	mandatory
        DESCRIPTION
                "The number of octets sent from virtual circuits."
        ::= { wfFrServiceRecordEntry 34 }

    wfFrServiceRecordifOutDiscards OBJECT-TYPE
        SYNTAX	Counter
        ACCESS	read-only
        STATUS	mandatory
        DESCRIPTION
                "Indicates how many outbound frames were dropped.
                 Usually these are dropped because a VC is not active."
        ::= { wfFrServiceRecordEntry 35 }

    wfFrServiceRecordifOutCtrlPkts OBJECT-TYPE
        SYNTAX	Counter
        ACCESS	read-only
        STATUS	mandatory
        DESCRIPTION
                "The number of dlcmi frames sent."
        ::= { wfFrServiceRecordEntry 36 }

    wfFrServiceRecordifInCtrlPkts OBJECT-TYPE
        SYNTAX	Counter
        ACCESS	read-only
        STATUS	mandatory
        DESCRIPTION
                "The number of dlcmi frames received."
        ::= { wfFrServiceRecordEntry 37 }

    wfFrSigTable OBJECT-TYPE
	SYNTAX	SEQUENCE OF WfFrSigEntry
	ACCESS	not-accessible
	STATUS	mandatory
	DESCRIPTION
		" The MIB Table for Frame Relay Signalling "
	::= { wfFrameRelay2Group 6 }

    wfFrSigEntry OBJECT-TYPE
	SYNTAX	WfFrSigEntry
	ACCESS	not-accessible
	STATUS	mandatory
	DESCRIPTION
		" The entry of FR Signalling MIB table "
	INDEX	{ wfFrSigLineNumber,
		wfFrSigLLIndex }
	::= { wfFrSigTable 1 }

    WfFrSigEntry ::= SEQUENCE {
	wfFrSigDelete
		INTEGER,
	wfFrSigDisable
		INTEGER,
	wfFrSigLineNumber
		INTEGER,
	wfFrSigLLIndex
		INTEGER,
	wfFrSigStatus
		INTEGER,
	wfFrSigCircuit
		INTEGER,
	wfFrSigConformance
		INTEGER,
	wfFrSigSvcIdleTimer
		INTEGER,
	wfFrSigMaxSvcs
		INTEGER,
	wfFrSigSvcDeletePolicy
		INTEGER,
	wfFrSigSvcReplacePolicy
		INTEGER,
	wfFrSigT303
		INTEGER,
	wfFrSigT305
		INTEGER,
	wfFrSigT308
		INTEGER,
	wfFrSigT310
		INTEGER,
	wfFrSigT322
		INTEGER,
	wfFrSigN322
		INTEGER,
	wfFrSigNumMaxSVCs
		INTEGER,
	wfFrSigNumConnRej
		Counter,
	wfFrSigNumSvcRej
		Counter,
	wfFrSigNumSvcFailed
		Counter
    }

    wfFrSigDelete OBJECT-TYPE
	SYNTAX	INTEGER {
		created(1),
		deleted(2)
	}
	ACCESS	read-write
	STATUS	mandatory
	DESCRIPTION
		" Delete FR Signalling on this interface "
	DEFVAL	{ created }
	::= { wfFrSigEntry 1 }

    wfFrSigDisable OBJECT-TYPE
	SYNTAX	INTEGER {
		enabled(1),
		disabled(2)
	}
	ACCESS	read-write
	STATUS	mandatory
	DESCRIPTION
		" Disable FR Sig on this interface "
	DEFVAL	{ enabled }
	::= { wfFrSigEntry 2 }

    wfFrSigLineNumber OBJECT-TYPE
	SYNTAX	INTEGER
	ACCESS	read-only
	STATUS	mandatory
	DESCRIPTION
		" Logical Line number.  This attribute is Instance Id 1 "
	::= { wfFrSigEntry 3 }

    wfFrSigLLIndex OBJECT-TYPE
	SYNTAX	INTEGER
	ACCESS	read-only
	STATUS	mandatory
	DESCRIPTION
		" Lower Layer Index.  This attribute is Instance Id 2 "
	::= { wfFrSigEntry 4 }

    wfFrSigStatus OBJECT-TYPE
	SYNTAX	INTEGER {
		running(1),
		fault(2),
		init(3),
		notpresent(4)
	}
	ACCESS	read-only
	STATUS	mandatory
	DESCRIPTION
		" Frame Relay Signalling Status
		  This is also Q.933 Layer Status.
		 
		  STATUS_RUNNING FR Signalling state machine is ready.
		  STATUS_FAULT FR Signalling is in a non-operative state.
		  STATUS_INIT FR Signalling is initializing.
		  STATUS_NOTPRESENT FR Signalling is not started yet. This value 
		       is not likely except upon initial configuration.
		 "
	DEFVAL	{ notpresent }
	::= { wfFrSigEntry 5 }

    wfFrSigCircuit OBJECT-TYPE
	SYNTAX	INTEGER
	ACCESS	read-write
	STATUS	mandatory
	DESCRIPTION
		" Circuit number of the FR Signaling Stack (needed?) "
	::= { wfFrSigEntry 6 }

    wfFrSigConformance OBJECT-TYPE
	SYNTAX	INTEGER {
		frf4(1),
		priority(2),
		q933(3),
		t1617(4)
	}
	ACCESS	read-write
	STATUS	mandatory
	DESCRIPTION
		" Q.933 Standard Conformance Selection
		 
		  FRF4       Frame Relay Forum Implementation Agreement FRF.4
		  FRF4_PRIORITY FRF.4 plus support of X.213 Priority
		  Q933       ITU Q.933, 03/1993 - currently not implemented
		  ANSI_T1617    ANSI T1.617 - currently not implemented
		 "
	DEFVAL	{ frf4 }
	::= { wfFrSigEntry 7 }

    wfFrSigSvcIdleTimer OBJECT-TYPE
	SYNTAX	INTEGER {
		min(10),
		default(360),
		max(14400)
	}
	ACCESS	read-write
	STATUS	mandatory
	DESCRIPTION
		" SVC Idle timeout value
		  Number of seconds in which SVCs are not passing data 
		  before considered 'idle'.
		 "
	DEFVAL	{ default }
	::= { wfFrSigEntry 8 }

    wfFrSigMaxSvcs OBJECT-TYPE
	SYNTAX	INTEGER {
		min(1),
		default(16),
		max(1024)
	}
	ACCESS	read-write
	STATUS	mandatory
	DESCRIPTION
		" Max number of SVC allowed on this interface "
	DEFVAL	{ default }
	::= { wfFrSigEntry 9 }

    wfFrSigSvcDeletePolicy OBJECT-TYPE
	SYNTAX	INTEGER {
		always(1),
		use(2),
		never(3)
	}
	ACCESS	read-write
	STATUS	mandatory
	DESCRIPTION
		" SVC Deletion Policy
		   ALWAYS always delete idle SVCs
		   HEAVY_USE delete idle SVCs when 85% of Max SVCs are open
		   NEVER never delete idle SVCs
		 "
	DEFVAL	{ always }
	::= { wfFrSigEntry 10 }

    wfFrSigSvcReplacePolicy OBJECT-TYPE
	SYNTAX	INTEGER {
		always(1),
		idle(2),
		never(3)
	}
	ACCESS	read-write
	STATUS	mandatory
	DESCRIPTION
		" SVC Replacement Policy
		   ALWAYS replace an SVC of an equal or lower priority
		   IDLE replace an SVC of an equal or lower priority only if it
		       is idle
		   NEVER never replace an SVC
		 "
	DEFVAL	{ always }
	::= { wfFrSigEntry 11 }

    wfFrSigT303 OBJECT-TYPE
	SYNTAX	INTEGER {
		min(1),
		default(4),
		max(120)
	}
	ACCESS	read-write
	STATUS	mandatory
	DESCRIPTION
		" T303 - SETUP msg timer value in seconds
		 "
	DEFVAL	{ default }
	::= { wfFrSigEntry 12 }

    wfFrSigT305 OBJECT-TYPE
	SYNTAX	INTEGER {
		min(1),
		default(30),
		max(120)
	}
	ACCESS	read-write
	STATUS	mandatory
	DESCRIPTION
		" T305 - DISCONNECT timer value "
	DEFVAL	{ default }
	::= { wfFrSigEntry 13 }

    wfFrSigT308 OBJECT-TYPE
	SYNTAX	INTEGER {
		min(1),
		default(4),
		max(120)
	}
	ACCESS	read-write
	STATUS	mandatory
	DESCRIPTION
		" T308 - RELEASE timer value "
	DEFVAL	{ default }
	::= { wfFrSigEntry 14 }

    wfFrSigT310 OBJECT-TYPE
	SYNTAX	INTEGER {
		min(1),
		default(30),
		max(120)
	}
	ACCESS	read-write
	STATUS	mandatory
	DESCRIPTION
		" T310 - CALL PROCEEDING timer value
		  Q.931 specifies a default of 30-120 seconds for this timer.
		 "
	DEFVAL	{ default }
	::= { wfFrSigEntry 15 }

    wfFrSigT322 OBJECT-TYPE
	SYNTAX	INTEGER {
		min(1),
		default(4),
		max(120)
	}
	ACCESS	read-write
	STATUS	mandatory
	DESCRIPTION
		" T322 - STATUS ENQUIRY timer value "
	DEFVAL	{ default }
	::= { wfFrSigEntry 16 }

    wfFrSigN322 OBJECT-TYPE
	SYNTAX	INTEGER {
		min(1),
		max(100)
	}
	ACCESS	read-write
	STATUS	mandatory
	DESCRIPTION
		" Number of times STATUS ENQUIRY is retransmitted "
	DEFVAL	{ min }
	::= { wfFrSigEntry 17 }

    wfFrSigNumMaxSVCs OBJECT-TYPE
	SYNTAX	INTEGER
	ACCESS	read-only
	STATUS	mandatory
	DESCRIPTION
		" Maximum number of SVCs currently in active state "
	::= { wfFrSigEntry 18 }

    wfFrSigNumConnRej OBJECT-TYPE
	SYNTAX	Counter
	ACCESS	read-only
	STATUS	mandatory
	DESCRIPTION
		" Number of SVC creation attempts which were rejected by Switch "
	::= { wfFrSigEntry 19 }

    wfFrSigNumSvcRej OBJECT-TYPE
	SYNTAX	Counter
	ACCESS	read-only
	STATUS	mandatory
	DESCRIPTION
		" Number of SVC setup attempts which were rejected by this router "
	::= { wfFrSigEntry 20 }

    wfFrSigNumSvcFailed OBJECT-TYPE
	SYNTAX	Counter
	ACCESS	read-only
	STATUS	mandatory
	DESCRIPTION
		" Number of SVC setup attempts which failed due to errors "
	::= { wfFrSigEntry 21 }

    wfFrLapfTable OBJECT-TYPE
	SYNTAX	SEQUENCE OF WfFrLapfEntry
	ACCESS	not-accessible
	STATUS	mandatory
	DESCRIPTION
		" The MIB Table for Frame Relay LAPF "
	::= { wfFrameRelay2Group 7 }

    wfFrLapfEntry OBJECT-TYPE
	SYNTAX	WfFrLapfEntry
	ACCESS	not-accessible
	STATUS	mandatory
	DESCRIPTION
		" The entry of FR LAPF MIB table "
	INDEX	{ wfLapfLineNumber,
		wfLapfLLIndex }
	::= { wfFrLapfTable 1 }

    WfFrLapfEntry ::= SEQUENCE {
	wfLapfDelete
		INTEGER,
	wfLapfDisable
		INTEGER,
	wfLapfLineNumber
		INTEGER,
	wfLapfLLIndex
		INTEGER,
	wfLapfStatus
		INTEGER,
	wfLapfStationType
		INTEGER,
	wfLapfActionInitiate
		INTEGER,
	wfLapfT200
		INTEGER,
	wfLapfT203
		INTEGER,
	wfLapfN200
		INTEGER,
	wfLapfN201
		INTEGER,
	wfLapfK
		INTEGER,
	wfLapfRxWin
		INTEGER,
	wfLapfTxWin
		INTEGER,
	wfLapfSABMESent
		Counter,
	wfLapfSABMERcvd
		Counter,
	wfLapfUASent
		Counter,
	wfLapfUARcvd
		Counter,
	wfLapfDISCSent
		Counter,
	wfLapfDISCRcvd
		Counter,
	wfLapfDMSent
		Counter,
	wfLapfDMRcvd
		Counter,
	wfLapfFRMRSent
		Counter,
	wfLapfFRMRRcvd
		Counter,
	wfLapfRNRsSent
		Counter,
	wfLapfRNRsRcvd
		Counter,
	wfLapfREJsSent
		Counter,
	wfLapfREJsRcvd
		Counter,
	wfLapfIFramesSent
		Counter,
	wfLapfIFramesRcvd
		Counter,
	wfLapfUISent
		Counter,
	wfLapfUIRcvd
		Counter,
	wfLapfRRsSent
		Counter,
	wfLapfRRsRcvd
		Counter,
	wfLapfXIDSent
		Counter,
	wfLapfXIDRcvd
		Counter,
	wfLapfT200Timeouts
		Counter,
	wfLapfT203Timeouts
		Counter,
	wfLapfN200Exceeded
		Counter,
	wfLapfN201Error
		Counter
    }

    wfLapfDelete OBJECT-TYPE
	SYNTAX	INTEGER {
		created(1),
		deleted(2)
	}
	ACCESS	read-write
	STATUS	mandatory
	DESCRIPTION
		" Delete LAPF on this interface "
	DEFVAL	{ created }
	::= { wfFrLapfEntry 1 }

    wfLapfDisable OBJECT-TYPE
	SYNTAX	INTEGER {
		enabled(1),
		disabled(2)
	}
	ACCESS	read-write
	STATUS	mandatory
	DESCRIPTION
		" Disable Lapf on this interface "
	DEFVAL	{ enabled }
	::= { wfFrLapfEntry 2 }

    wfLapfLineNumber OBJECT-TYPE
	SYNTAX	INTEGER
	ACCESS	read-only
	STATUS	mandatory
	DESCRIPTION
		" Logical Line number.  This attribute is Instance Id 1 "
	::= { wfFrLapfEntry 3 }

    wfLapfLLIndex OBJECT-TYPE
	SYNTAX	INTEGER
	ACCESS	read-only
	STATUS	mandatory
	DESCRIPTION
		" Lower Layer Index.  This attribute is Instance Id 2 "
	::= { wfFrLapfEntry 4 }

    wfLapfStatus OBJECT-TYPE
	SYNTAX	INTEGER {
		running(1),
		fault(2),
		init(3),
		notpresent(4)
	}
	ACCESS	read-only
	STATUS	mandatory
	DESCRIPTION
		" Status of LAPF Data Link Control
		  
		  STATUS_RUNNING LAPF layer is ready and responsive.
		  STATUS_FAULT LAPF layer is in a non-operative state.
		  STATUS_INIT LAPF layer is initializing.
		  STATUS_NOTPRESENT LAPF layer is not started yet. This value 
		       is not likely except upon initial configuration.
		 "
	DEFVAL	{ notpresent }
	::= { wfFrLapfEntry 5 }

    wfLapfStationType OBJECT-TYPE
	SYNTAX	INTEGER {
		networkside(1),
		userside(2)
	}
	ACCESS	read-write
	STATUS	mandatory
	DESCRIPTION
		" Identifies the desired station type of this interface.
		  LAPF_USERSIDE     LAPF acts as the User-side (DTE) 
		  LAPF_NETWORKSIDE    LAPF acts as the Network-side (DCE)
		 "
	DEFVAL	{ networkside }
	::= { wfFrLapfEntry 6 }

    wfLapfActionInitiate OBJECT-TYPE
	SYNTAX	INTEGER {
		active(1),
		passive(2)
	}
	ACCESS	read-write
	STATUS	mandatory
	DESCRIPTION
		" This identifies the action LAPF will take to initiate link set-up. "
	DEFVAL	{ active }
	::= { wfFrLapfEntry 7 }

    wfLapfT200 OBJECT-TYPE
	SYNTAX	INTEGER(1..1200)
	ACCESS	read-write
	STATUS	mandatory
	DESCRIPTION
		" T200 - LAPF Base timer value, in tenths of a second "
	DEFVAL	{ 15 }
	::= { wfFrLapfEntry 8 }

    wfLapfT203 OBJECT-TYPE
	SYNTAX	INTEGER(1..120)
	ACCESS	read-write
	STATUS	mandatory
	DESCRIPTION
		" T203 - LAPF idle timer value, in seconds "
	DEFVAL	{ 30 }
	::= { wfFrLapfEntry 9 }

    wfLapfN200 OBJECT-TYPE
	SYNTAX	INTEGER(1..20)
	ACCESS	read-write
	STATUS	mandatory
	DESCRIPTION
		" N200 - Max number of LAPF retransmissions "
	DEFVAL	{ 3 }
	::= { wfFrLapfEntry 10 }

    wfLapfN201 OBJECT-TYPE
	SYNTAX	INTEGER(260..2052)
	ACCESS	read-write
	STATUS	mandatory
	DESCRIPTION
		" N201 - Max number of octets in LAPF Information field "
	DEFVAL	{ 260 }
	::= { wfFrLapfEntry 11 }

    wfLapfK OBJECT-TYPE
	SYNTAX	INTEGER(1..127)
	ACCESS	read-write
	STATUS	mandatory
	DESCRIPTION
		" k - Max number of outstanding I-frames "
	DEFVAL	{ 7 }
	::= { wfFrLapfEntry 12 }

    wfLapfRxWin OBJECT-TYPE
	SYNTAX	INTEGER
	ACCESS	read-only
	STATUS	mandatory
	DESCRIPTION
		" Current receive window size "
	::= { wfFrLapfEntry 13 }

    wfLapfTxWin OBJECT-TYPE
	SYNTAX	INTEGER
	ACCESS	read-only
	STATUS	mandatory
	DESCRIPTION
		" Current transmit window size "
	::= { wfFrLapfEntry 14 }

    wfLapfSABMESent OBJECT-TYPE
	SYNTAX	Counter
	ACCESS	read-only
	STATUS	mandatory
	DESCRIPTION
		" number of SABME sent "
	::= { wfFrLapfEntry 15 }

    wfLapfSABMERcvd OBJECT-TYPE
	SYNTAX	Counter
	ACCESS	read-only
	STATUS	mandatory
	DESCRIPTION
		" number of SABME received "
	::= { wfFrLapfEntry 16 }

    wfLapfUASent OBJECT-TYPE
	SYNTAX	Counter
	ACCESS	read-only
	STATUS	mandatory
	DESCRIPTION
		" number of UA sent "
	::= { wfFrLapfEntry 17 }

    wfLapfUARcvd OBJECT-TYPE
	SYNTAX	Counter
	ACCESS	read-only
	STATUS	mandatory
	DESCRIPTION
		" number of UA received "
	::= { wfFrLapfEntry 18 }

    wfLapfDISCSent OBJECT-TYPE
	SYNTAX	Counter
	ACCESS	read-only
	STATUS	mandatory
	DESCRIPTION
		" number of DISC sent "
	::= { wfFrLapfEntry 19 }

    wfLapfDISCRcvd OBJECT-TYPE
	SYNTAX	Counter
	ACCESS	read-only
	STATUS	mandatory
	DESCRIPTION
		" number of DISC received "
	::= { wfFrLapfEntry 20 }

    wfLapfDMSent OBJECT-TYPE
	SYNTAX	Counter
	ACCESS	read-only
	STATUS	mandatory
	DESCRIPTION
		" number of DM sent "
	::= { wfFrLapfEntry 21 }

    wfLapfDMRcvd OBJECT-TYPE
	SYNTAX	Counter
	ACCESS	read-only
	STATUS	mandatory
	DESCRIPTION
		" number of DM received "
	::= { wfFrLapfEntry 22 }

    wfLapfFRMRSent OBJECT-TYPE
	SYNTAX	Counter
	ACCESS	read-only
	STATUS	mandatory
	DESCRIPTION
		" number of FRMR sent "
	::= { wfFrLapfEntry 23 }

    wfLapfFRMRRcvd OBJECT-TYPE
	SYNTAX	Counter
	ACCESS	read-only
	STATUS	mandatory
	DESCRIPTION
		" number of FRMR received "
	::= { wfFrLapfEntry 24 }

    wfLapfRNRsSent OBJECT-TYPE
	SYNTAX	Counter
	ACCESS	read-only
	STATUS	mandatory
	DESCRIPTION
		" number of RNR frames received since link is up "
	::= { wfFrLapfEntry 25 }

    wfLapfRNRsRcvd OBJECT-TYPE
	SYNTAX	Counter
	ACCESS	read-only
	STATUS	mandatory
	DESCRIPTION
		" number of RNR frames sent since link is up "
	::= { wfFrLapfEntry 26 }

    wfLapfREJsSent OBJECT-TYPE
	SYNTAX	Counter
	ACCESS	read-only
	STATUS	mandatory
	DESCRIPTION
		" number of REJ frames received since link is up "
	::= { wfFrLapfEntry 27 }

    wfLapfREJsRcvd OBJECT-TYPE
	SYNTAX	Counter
	ACCESS	read-only
	STATUS	mandatory
	DESCRIPTION
		" number of REJ frames sent since link is up "
	::= { wfFrLapfEntry 28 }

    wfLapfIFramesSent OBJECT-TYPE
	SYNTAX	Counter
	ACCESS	read-only
	STATUS	mandatory
	DESCRIPTION
		" number of I-frames received since last link establishment "
	::= { wfFrLapfEntry 29 }

    wfLapfIFramesRcvd OBJECT-TYPE
	SYNTAX	Counter
	ACCESS	read-only
	STATUS	mandatory
	DESCRIPTION
		" number of I-frames sent since last link establishment "
	::= { wfFrLapfEntry 30 }

    wfLapfUISent OBJECT-TYPE
	SYNTAX	Counter
	ACCESS	read-only
	STATUS	mandatory
	DESCRIPTION
		" number of un-numbered I-frames received since last link establishment "
	::= { wfFrLapfEntry 31 }

    wfLapfUIRcvd OBJECT-TYPE
	SYNTAX	Counter
	ACCESS	read-only
	STATUS	mandatory
	DESCRIPTION
		" number of un-numbered I-frames sent since last link establishment "
	::= { wfFrLapfEntry 32 }

    wfLapfRRsSent OBJECT-TYPE
	SYNTAX	Counter
	ACCESS	read-only
	STATUS	mandatory
	DESCRIPTION
		" number of RR frames sent since link is up "
	::= { wfFrLapfEntry 33 }

    wfLapfRRsRcvd OBJECT-TYPE
	SYNTAX	Counter
	ACCESS	read-only
	STATUS	mandatory
	DESCRIPTION
		" number of RR frames received since link is up "
	::= { wfFrLapfEntry 34 }

    wfLapfXIDSent OBJECT-TYPE
	SYNTAX	Counter
	ACCESS	read-only
	STATUS	mandatory
	DESCRIPTION
		" number of XID sent  "
	::= { wfFrLapfEntry 35 }

    wfLapfXIDRcvd OBJECT-TYPE
	SYNTAX	Counter
	ACCESS	read-only
	STATUS	mandatory
	DESCRIPTION
		" number of XID  received "
	::= { wfFrLapfEntry 36 }

    wfLapfT200Timeouts OBJECT-TYPE
	SYNTAX	Counter
	ACCESS	read-only
	STATUS	mandatory
	DESCRIPTION
		" number of T200 Time-out that occured. "
	::= { wfFrLapfEntry 37 }

    wfLapfT203Timeouts OBJECT-TYPE
	SYNTAX	Counter
	ACCESS	read-only
	STATUS	mandatory
	DESCRIPTION
		" number of T203 time-out that occured. "
	::= { wfFrLapfEntry 38 }

    wfLapfN200Exceeded OBJECT-TYPE
	SYNTAX	Counter
	ACCESS	read-only
	STATUS	mandatory
	DESCRIPTION
		" number of N200 being exceeded. "
	::= { wfFrLapfEntry 39 }

    wfLapfN201Error OBJECT-TYPE
	SYNTAX	Counter
	ACCESS	read-only
	STATUS	mandatory
	DESCRIPTION
		" number of N201 error occured. "
	::= { wfFrLapfEntry 40 }


    wfFrFRF4SigTable OBJECT-TYPE
	SYNTAX	SEQUENCE OF WfFrFRF4SigEntry
	ACCESS	not-accessible
	STATUS	mandatory
	DESCRIPTION
		" The MIB Table for FRF4 SVC Signalling "
	::= { wfFrameRelay2Group 9 }

    wfFrFRF4SigEntry OBJECT-TYPE
	SYNTAX	WfFrFRF4SigEntry
	ACCESS	not-accessible
	STATUS	mandatory
	DESCRIPTION
		" The entry of FRF4 SVC Signalling MIB table "
	INDEX	{ wfFrFRF4SigLineNumber,
		wfFrFRF4SigLLIndex }
	::= { wfFrFRF4SigTable 1 }

    WfFrFRF4SigEntry ::= SEQUENCE {
	wfFrFRF4SigDelete
		INTEGER,
	wfFrFRF4SigDisable
		INTEGER,
	wfFrFRF4SigLineNumber
		INTEGER,
	wfFrFRF4SigLLIndex
		INTEGER,
	wfFrFRF4SigMaxSvcs
		INTEGER,
	wfFrFRF4SigT303
		INTEGER,
	wfFrFRF4SigT305
		INTEGER,
	wfFrFRF4SigT308
		INTEGER,
	wfFrFRF4SigT310
		INTEGER,
	wfFrFRF4SigT322
		INTEGER,
	wfFrFRF4SigN322
		INTEGER,
	wfFrFRF4SigFramesSent
		Counter,
	wfFrFRF4SigOctetsSent
		Counter,
	wfFrFRF4SigFramesReceived
		Counter,
	wfFrFRF4SigOctetsReceived
		Counter,
	wfFrFRF4SigFramesDropped
		Counter,
	wfFrFRF4SigFramesDiscarded
		Counter,
        wfFrFRF4SigSetupRx
                Counter,
        wfFrFRF4SigCallProcRx
                Counter,
        wfFrFRF4SigConnectRx
                Counter,
        wfFrFRF4SigDisconnectRx
                Counter,
        wfFrFRF4SigReleaseRx
                Counter,
        wfFrFRF4SigReleaseCompleteRx
                Counter,
        wfFrFRF4SigStatusRx
                Counter,
        wfFrFRF4SigStatusEnquiryRx
                Counter,
        wfFrFRF4SigSetupTx
                Counter,
        wfFrFRF4SigCallProcTx
                Counter,
        wfFrFRF4SigConnectTx
                Counter,
        wfFrFRF4SigDisconnectTx
                Counter,
        wfFrFRF4SigReleaseTx
                Counter,
        wfFrFRF4SigReleaseCompleteTx
                Counter,
        wfFrFRF4SigStatusTx
                Counter,
        wfFrFRF4SigStatusEnquiryTx
                Counter
    }

    wfFrFRF4SigDelete OBJECT-TYPE
	SYNTAX	INTEGER {
		created(1),
		deleted(2)
	}
	ACCESS	read-write
	STATUS	mandatory
	DESCRIPTION
		" Delete FRF4 SVC Signalling on this interface "
	DEFVAL	{ created }
	::= { wfFrFRF4SigEntry 1 }

    wfFrFRF4SigDisable OBJECT-TYPE
	SYNTAX	INTEGER {
		enabled(1),
		disabled(2)
	}
	ACCESS	read-write
	STATUS	mandatory
	DESCRIPTION
		" Disable FRF4 SVC Signalling on this interface "
	DEFVAL	{ enabled }
	::= { wfFrFRF4SigEntry 2 }

    wfFrFRF4SigLineNumber OBJECT-TYPE
	SYNTAX	INTEGER
	ACCESS	read-only
	STATUS	mandatory
	DESCRIPTION
		" Logical Line number.  This attribute is Instance Id 1 "
	::= { wfFrFRF4SigEntry 3 }

    wfFrFRF4SigLLIndex OBJECT-TYPE
	SYNTAX	INTEGER
	ACCESS	read-only
	STATUS	mandatory
	DESCRIPTION
		" Lower Layer Index.  This attribute is Instance Id 2 "
	::= { wfFrFRF4SigEntry 4 }

    wfFrFRF4SigMaxSvcs OBJECT-TYPE
	SYNTAX	INTEGER(1..2147483647)
	ACCESS	read-write
	STATUS	mandatory
	DESCRIPTION
		" Maximum number of SVCs for this interface "
        DEFVAL  { 100 }
	::= { wfFrFRF4SigEntry 5 }

    wfFrFRF4SigT303 OBJECT-TYPE
        SYNTAX  INTEGER (2..90)
        ACCESS  read-write
        STATUS  mandatory
        DESCRIPTION
                "  Timer number:         T303
                   default time-out:     4 s
                   state of call:        call present
                   cause for start:      outgoing setup
                   normal stop:          incoming connect/call-proceeding/
                                         release-complete
                   at the first expiry:  retransmit setup, restart T303
                   at the second expiry: clear call "
        DEFVAL  { 4 }
	::= { wfFrFRF4SigEntry 6 }

    wfFrFRF4SigT305 OBJECT-TYPE
	SYNTAX	INTEGER (20..90)
	ACCESS	read-write
	STATUS	mandatory
	DESCRIPTION
		"  Timer number:         T305
		   default time-out:     30 s
		   state of call:        disconnect ind
		   cause for start:      outgoing disconnect
		   normal stop:          incoming release/disconnect
		   at the first expiry:  outgoing release
		   at the second expiry: timer not restarted "
	DEFVAL	{ 30 }
	::= { wfFrFRF4SigEntry 7 }

    wfFrFRF4SigT308 OBJECT-TYPE
	SYNTAX	INTEGER (2..90)
	ACCESS	read-write
	STATUS	mandatory
	DESCRIPTION
		"  Timer number:         T308
		   default time-out:     4 s
		   state of call:        release req
		   cause for start:      outgoing release
		   normal stop:          incoming release/release-complete
		   at the first expiry:  retransmit release, restart T308
		   at the second expiry: place access channel in maintenance "
	DEFVAL	{ 4 }
	::= { wfFrFRF4SigEntry 8 }

    wfFrFRF4SigT310 OBJECT-TYPE
	SYNTAX	INTEGER (2..90)
	ACCESS	read-write
	STATUS	mandatory
	DESCRIPTION
		"  Timer number:         T310
		   default time-out:     10 s
		   state of call:        incoming call proceeding
		   cause for start:      incoming call proceeding
		   normal stop:          incoming connect/disconnect
		   at the first expiry:  clear call
		   at the second expiry: timer not restarted "
	DEFVAL	{ 10 }
	::= { wfFrFRF4SigEntry 9 }

    wfFrFRF4SigT322 OBJECT-TYPE
	SYNTAX	INTEGER (2..90)
	ACCESS	read-write
	STATUS	mandatory
	DESCRIPTION
		"  Timer number:         T322
		   default time-out:     4 s
		   state of call:        any call state
		   cause for start:      outgoing status enquiry
		   normal stop:          incoming status/disconnect/
		                         release/release-complete
		   at the first expiry:  resend status-enq, restart T322
		   at the next expiry:   if (--N322 > 0), resend status enq
					 and restart T322 "
	DEFVAL	{ 4 }
	::= { wfFrFRF4SigEntry 10 }

    wfFrFRF4SigN322 OBJECT-TYPE
	SYNTAX	INTEGER (1..20)
	ACCESS	read-write
	STATUS	mandatory
	DESCRIPTION
		" Number of times STATUS ENQUIRY is retransmitted "
	DEFVAL	{ 4 }
	::= { wfFrFRF4SigEntry 11 }


    wfFrFRF4SigFramesSent OBJECT-TYPE
	SYNTAX	Counter
	ACCESS	read-only
	STATUS	mandatory
	DESCRIPTION
		" Number of frames transmitted. "
	::= { wfFrFRF4SigEntry 12 }

    wfFrFRF4SigOctetsSent OBJECT-TYPE
	SYNTAX	Counter
	ACCESS	read-only
	STATUS	mandatory
	DESCRIPTION
		" Number of octets transmitted. "
	::= { wfFrFRF4SigEntry 13 }

    wfFrFRF4SigFramesReceived OBJECT-TYPE
	SYNTAX	Counter
	ACCESS	read-only
	STATUS	mandatory
	DESCRIPTION
		" Number of frames received. "
	::= { wfFrFRF4SigEntry 14 }

    wfFrFRF4SigOctetsReceived OBJECT-TYPE
	SYNTAX	Counter
	ACCESS	read-only
	STATUS	mandatory
	DESCRIPTION
		" Number of octets received. "
	::= { wfFrFRF4SigEntry 15 }

    wfFrFRF4SigFramesDropped OBJECT-TYPE
	SYNTAX	Counter
	ACCESS	read-only
	STATUS	mandatory
	DESCRIPTION
		" Number of frames dropped. "
	::= { wfFrFRF4SigEntry 16 }

    wfFrFRF4SigFramesDiscarded OBJECT-TYPE
	SYNTAX	Counter
	ACCESS	read-only
	STATUS	mandatory
	DESCRIPTION
		" Number of frames discarded. "
	::= { wfFrFRF4SigEntry 17 }

    wfFrFRF4SigSetupRx OBJECT-TYPE
        SYNTAX  Counter
        ACCESS  read-only
        STATUS  mandatory
        DESCRIPTION
                "Number of SETUP frames received."
        ::= { wfFrFRF4SigEntry 18 }

    wfFrFRF4SigCallProcRx OBJECT-TYPE
        SYNTAX  Counter
        ACCESS  read-only
        STATUS  mandatory
        DESCRIPTION
                "Number of CALL PROCEEDING frames received."
        ::= { wfFrFRF4SigEntry 19 }

    wfFrFRF4SigConnectRx OBJECT-TYPE
        SYNTAX  Counter
        ACCESS  read-only
        STATUS  mandatory
        DESCRIPTION
                "Number of CONNECT frames received."
        ::= { wfFrFRF4SigEntry 20 }

    wfFrFRF4SigDisconnectRx OBJECT-TYPE
        SYNTAX  Counter
        ACCESS  read-only
        STATUS  mandatory
        DESCRIPTION
                "Number of DISCONNECT frames received."
        ::= { wfFrFRF4SigEntry 21 }

    wfFrFRF4SigReleaseRx OBJECT-TYPE
        SYNTAX  Counter
        ACCESS  read-only
        STATUS  mandatory
        DESCRIPTION
                "Number of RELEASE frames received."
        ::= { wfFrFRF4SigEntry 22 }

    wfFrFRF4SigReleaseCompleteRx OBJECT-TYPE
        SYNTAX  Counter
        ACCESS  read-only
        STATUS  mandatory
        DESCRIPTION
                "Number of RELEASE COMPLETE frames received."
        ::= { wfFrFRF4SigEntry 23 }

    wfFrFRF4SigStatusRx OBJECT-TYPE
        SYNTAX  Counter
        ACCESS  read-only
        STATUS  mandatory
        DESCRIPTION
                "Number of STATUS frames received."
        ::= { wfFrFRF4SigEntry 24 }

    wfFrFRF4SigStatusEnquiryRx OBJECT-TYPE
        SYNTAX  Counter
        ACCESS  read-only
        STATUS  mandatory
        DESCRIPTION
                "Number of STATUS ENQUIRY frames received."
        ::= { wfFrFRF4SigEntry 25 }

    wfFrFRF4SigSetupTx OBJECT-TYPE
        SYNTAX  Counter
        ACCESS  read-only
        STATUS  mandatory
        DESCRIPTION
                "Number of SETUP frames transmitted."
        ::= { wfFrFRF4SigEntry 26 }

    wfFrFRF4SigCallProcTx OBJECT-TYPE
        SYNTAX  Counter
        ACCESS  read-only
        STATUS  mandatory
        DESCRIPTION
                "Number of CALL PROCEEDING frames transmitted."
        ::= { wfFrFRF4SigEntry 27 }

    wfFrFRF4SigConnectTx OBJECT-TYPE
        SYNTAX  Counter
        ACCESS  read-only
        STATUS  mandatory
        DESCRIPTION
                "Number of CONNECT frames transmitted."
        ::= { wfFrFRF4SigEntry 28 }

    wfFrFRF4SigDisconnectTx OBJECT-TYPE
        SYNTAX  Counter
        ACCESS  read-only
        STATUS  mandatory
        DESCRIPTION
                "Number of DISCONNECT frames transmitted."
        ::= { wfFrFRF4SigEntry 29 }

    wfFrFRF4SigReleaseTx OBJECT-TYPE
        SYNTAX  Counter
        ACCESS  read-only
        STATUS  mandatory
        DESCRIPTION
                "Number of RELEASE frames transmitted."
        ::= { wfFrFRF4SigEntry 30 }

    wfFrFRF4SigReleaseCompleteTx OBJECT-TYPE
        SYNTAX  Counter
        ACCESS  read-only
        STATUS  mandatory
        DESCRIPTION
                "Number of RELEASE COMPLETE frames transmitted."
        ::= { wfFrFRF4SigEntry 31 }

    wfFrFRF4SigStatusTx OBJECT-TYPE
        SYNTAX  Counter
        ACCESS  read-only
        STATUS  mandatory
        DESCRIPTION
                "Number of STATUS frames transmitted."
        ::= { wfFrFRF4SigEntry 32 }

    wfFrFRF4SigStatusEnquiryTx OBJECT-TYPE
        SYNTAX  Counter
        ACCESS  read-only
        STATUS  mandatory
        DESCRIPTION
                "Number of STATUS ENQUIRY frames transmitted."
        ::= { wfFrFRF4SigEntry 33 }

    wfFrSVCOptionsTable OBJECT-TYPE
	SYNTAX	SEQUENCE OF WfFrSVCOptionsEntry
	ACCESS	not-accessible
	STATUS	mandatory
	DESCRIPTION
		" The MIB Table for FRF4 SVC Signalling options "
	::= { wfFrameRelay2Group 10 }

    wfFrSVCOptionsEntry OBJECT-TYPE
	SYNTAX	WfFrSVCOptionsEntry
	ACCESS	not-accessible
	STATUS	mandatory
	DESCRIPTION
		" The entry of FRF4 SVC Signalling options MIB table "
	INDEX	{ wfFrSVCOptionsLineNumber,
		wfFrSVCOptionsLLIndex,
		wfFrSVCOptionsCircuitNumber,
		wfFrSVCOptionsInstanceIndex }
	::= { wfFrSVCOptionsTable 1 }

    WfFrSVCOptionsEntry ::= SEQUENCE {
	wfFrSVCOptionsDelete
		INTEGER,
	wfFrSVCOptionsDisable
		INTEGER,
	wfFrSVCOptionsLineNumber
		INTEGER,
	wfFrSVCOptionsLLIndex
		INTEGER,
	wfFrSVCOptionsCircuitNumber
		INTEGER,
	wfFrSVCOptionsInstanceIndex
		INTEGER,
	wfFrSVCOptionsRemNum
		DisplayString,
	wfFrSVCOptionsRemSubAdr
		DisplayString,
	wfFrSVCOptionsRemPlan
		INTEGER,
	wfFrSVCOptionsRemTypeNum
		INTEGER,
	wfFrSVCOptionsBroadcastDisable
		INTEGER,
	wfFrSVCOptionsInactTimer
		INTEGER,
	wfFrSVCOptionsInactMode
		INTEGER,
	wfFrSVCOptionsX213DataPriority
		INTEGER,
	wfFrSVCOptionsX213DataLQAPriority
		INTEGER,
	wfFrSVCOptionsX213GainPriority
		INTEGER,
	wfFrSVCOptionsX213GainLQAPriority
		INTEGER,
	wfFrSVCOptionsX213KeepPriority
		INTEGER,
	wfFrSVCOptionsX213KeepLQAPriority
		INTEGER,
	wfFrSVCOptionsLLCoreOutThroughput
		INTEGER,
	wfFrSVCOptionsLLCoreInThroughput
		INTEGER,
	wfFrSVCOptionsLLCoreMinOutThroughput
		INTEGER,
	wfFrSVCOptionsLLCoreMinInThroughput
		INTEGER,
	wfFrSVCOptionsLLCoreOutBc
		INTEGER,
	wfFrSVCOptionsLLCoreInBc
		INTEGER,
	wfFrSVCOptionsLLCoreOutBe
		INTEGER,
	wfFrSVCOptionsLLCoreInBe
		INTEGER,
	wfFrSVCOptionsCongestionDisable
		INTEGER,
	wfFrSVCOptionsCongestionTmr
		INTEGER,
	wfFrSVCOptionsCongestionCtr
		INTEGER,
	wfFrSVCOptionsCongestionMethod
		INTEGER,
	wfFrSVCOptionsTrafficShapingDisable
		INTEGER,
	wfFrSVCOptionsWcpEnable
		INTEGER,
    	wfFrSVCOptionsName
    		DisplayString
    }

    wfFrSVCOptionsDelete OBJECT-TYPE
	SYNTAX	INTEGER {
		created(1),
		deleted(2)
	}
	ACCESS	read-write
	STATUS	mandatory
	DESCRIPTION
		" Delete SVC options record "
	DEFVAL	{ created }
	::= { wfFrSVCOptionsEntry 1 }

    wfFrSVCOptionsDisable OBJECT-TYPE
	SYNTAX	INTEGER {
		enabled(1),
		disabled(2)
	}
	ACCESS	read-write
	STATUS	mandatory
	DESCRIPTION
		" Disable use of SVC options record "
	DEFVAL	{ enabled }
	::= { wfFrSVCOptionsEntry 2 }

    wfFrSVCOptionsLineNumber OBJECT-TYPE
	SYNTAX	INTEGER
	ACCESS	read-only
	STATUS	mandatory
	DESCRIPTION
		" Logical Line number.  This attribute is Instance Id 1 "
	::= { wfFrSVCOptionsEntry 3 }

    wfFrSVCOptionsLLIndex OBJECT-TYPE
	SYNTAX	INTEGER
	ACCESS	read-only
	STATUS	mandatory
	DESCRIPTION
		" Lower Layer Index.  This attribute is Instance Id 2 "
	::= { wfFrSVCOptionsEntry 4 }

    wfFrSVCOptionsCircuitNumber OBJECT-TYPE
	SYNTAX	INTEGER
	ACCESS	read-only
	STATUS	mandatory
	DESCRIPTION
		" Circuit number.  This attribute is Instance Id 3 "
	::= { wfFrSVCOptionsEntry 5 }

    wfFrSVCOptionsInstanceIndex OBJECT-TYPE
	SYNTAX	INTEGER
	ACCESS	read-only
	STATUS	mandatory
	DESCRIPTION
		" Instance index assigned by Site Manager.  This attribute
		  is Instance Id 4 "
	::= { wfFrSVCOptionsEntry 6 }

    wfFrSVCOptionsRemNum OBJECT-TYPE
	SYNTAX	DisplayString
	ACCESS	read-write
	STATUS	mandatory
	DESCRIPTION
		" Configured options apply to this number "
	::= { wfFrSVCOptionsEntry 7 }

    wfFrSVCOptionsRemSubAdr OBJECT-TYPE
	SYNTAX	DisplayString
	ACCESS	read-write
	STATUS	mandatory
	DESCRIPTION
		" Subaddress of type NSAP (Q.931) further qualifies number "
	::= { wfFrSVCOptionsEntry 8 }

    wfFrSVCOptionsRemPlan OBJECT-TYPE
	SYNTAX  INTEGER {
		e164(1),
		x121(3)
        }
	ACCESS	read-write
	STATUS	mandatory
	DESCRIPTION
		" Supported Q.931 4.3.8/4.3.10 numbering plans. Each
		  plan is represented by the 4 least significant bits
		  to align with the values stated in Q.931. "
	DEFVAL	{ x121 }
	::= { wfFrSVCOptionsEntry 9 }

    wfFrSVCOptionsRemTypeNum OBJECT-TYPE
	SYNTAX  INTEGER {
                unknown(1),
		international(2)
        }
	ACCESS	read-write
	STATUS	mandatory
	DESCRIPTION
		" Supported Q.931 4.3.8/4.3.10 types of number. Each
		  type is represented by a value one greater than 
		  the values stated in Q.931. "
		  
	DEFVAL	{ international }
	::= { wfFrSVCOptionsEntry 10 }

    wfFrSVCOptionsBroadcastDisable OBJECT-TYPE
	SYNTAX	INTEGER {
		enabled(1),
		disabled(2)
	}
	ACCESS	read-write
	STATUS	mandatory
	DESCRIPTION
		" Add this number to the SVC broadcast domain "
	DEFVAL	{ enabled }
	::= { wfFrSVCOptionsEntry 11 }

    wfFrSVCOptionsInactTimer OBJECT-TYPE
	SYNTAX	INTEGER(0..2147483647)
	ACCESS	read-write
	STATUS	mandatory
	DESCRIPTION
		" Amount of time (in seconds) to wait for packets before
		  disconnecting the SVC "
        DEFVAL  { 60 }
	::= { wfFrSVCOptionsEntry 12 }

    wfFrSVCOptionsInactMode OBJECT-TYPE
	SYNTAX  INTEGER {
    	        bothdirections(1),
                transmitonly(2),
    	        receiveonly(3),
                eitherdirection(4)
        }
	ACCESS	read-write
	STATUS	mandatory
	DESCRIPTION
		"Inactivity check mode"
	DEFVAL	{ bothdirections }
	::= { wfFrSVCOptionsEntry 13 }

    wfFrSVCOptionsX213DataPriority OBJECT-TYPE
	SYNTAX	INTEGER (0..15)
	ACCESS	read-write
	STATUS	mandatory
	DESCRIPTION
		" The priority of data on the network connection
		  as defined in Q.933 and X.213. Each priority is
		  the numerical value associated with said priority
		  in Q.933 "
	DEFVAL	{ 15 }
	::= { wfFrSVCOptionsEntry 14 }

    wfFrSVCOptionsX213DataLQAPriority OBJECT-TYPE
	SYNTAX	INTEGER (0..15)
	ACCESS	read-write
	STATUS	mandatory
	DESCRIPTION
		" The lowest quality acceptable (LQA) priority of
		  data on the network connection as defined in Q.933
		  and X.213. Each priority is the numerical value associated
		  with said priority in Q.933 "
	DEFVAL	{ 15 }
	::= { wfFrSVCOptionsEntry 15 }

    wfFrSVCOptionsX213GainPriority OBJECT-TYPE
	SYNTAX	INTEGER (0..15)
	ACCESS	read-write
	STATUS	mandatory
	DESCRIPTION
		" The priority to gain a network connection
		  as defined in Q.933 and X.213. Each priority is
		  the numerical value associated with said priority
		  in Q.933 "
	DEFVAL	{ 15 }
	::= { wfFrSVCOptionsEntry 16 }

    wfFrSVCOptionsX213GainLQAPriority OBJECT-TYPE
	SYNTAX	INTEGER (0..15)
	ACCESS	read-write
	STATUS	mandatory
	DESCRIPTION
		" The lowest quality acceptable (LQA) priority to
		  gain a network connection as defined in Q.933
		  and X.213. Each priority is the numerical value associated
		  with said priority in Q.933 "
	DEFVAL	{ 15 }
	::= { wfFrSVCOptionsEntry 17 }

    wfFrSVCOptionsX213KeepPriority OBJECT-TYPE
	SYNTAX	INTEGER (0..15)
	ACCESS	read-write
	STATUS	mandatory
	DESCRIPTION
		" The priority to keep a network connection
		  as defined in Q.933 and X.213. Each priority is
		  the numerical value associated with said priority
		  in Q.933 "
	DEFVAL	{ 15 }
	::= { wfFrSVCOptionsEntry 18 }

    wfFrSVCOptionsX213KeepLQAPriority OBJECT-TYPE
	SYNTAX	INTEGER (0..15)
	ACCESS	read-write
	STATUS	mandatory
	DESCRIPTION
		" The lowest quality acceptable (LQA) priority to
		  keep a network connection as defined in Q.933
		  and X.213. Each priority is the numerical value associated
		  with said priority in Q.933 "
	DEFVAL	{ 15 }
	::= { wfFrSVCOptionsEntry 19 }


    wfFrSVCOptionsLLCoreOutThroughput OBJECT-TYPE
	SYNTAX	INTEGER (0..2147483647)
	ACCESS	read-write
	STATUS	mandatory
	DESCRIPTION
		" Requested outgoing throughput.
		  Q.933:Throughput is the average number of frame mode 
		  information field bits transferred per second across a
		  user-network interface in one direction, measured over
		  an interval of duration T."
	DEFVAL	{ 0 }
	::= { wfFrSVCOptionsEntry 20 }

    wfFrSVCOptionsLLCoreInThroughput OBJECT-TYPE
	SYNTAX	INTEGER (0..2147483647)
	ACCESS	read-write
	STATUS	mandatory
	DESCRIPTION
		" Requested incoming throughput.
		  Q.933:Throughput is the average number of frame mode 
		  information field bits transferred per second across a
		  user-network interface in one direction, measured over
		  an interval of duration T."
	DEFVAL	{ 0 }
	::= { wfFrSVCOptionsEntry 21 }

    wfFrSVCOptionsLLCoreMinOutThroughput OBJECT-TYPE
	SYNTAX	INTEGER (0..2147483647)
	ACCESS	read-write
	STATUS	mandatory
	DESCRIPTION
		" Minimum acceptable outgoing throughput.
		  Q.933:Throughput is the average number of frame mode 
		  information field bits transferred per second across a
		  user-network interface in one direction, measured over
		  an interval of duration T."
	DEFVAL	{ 0 }
	::= { wfFrSVCOptionsEntry 22 }

    wfFrSVCOptionsLLCoreMinInThroughput OBJECT-TYPE
	SYNTAX	INTEGER (0..2147483647)
	ACCESS	read-write
	STATUS	mandatory
	DESCRIPTION
		" Minimum acceptable incoming throughput.
		  Q.933:Throughput is the average number of frame mode 
		  information field bits transferred per second across a
		  user-network interface in one direction, measured over
		  an interval of duration T."
	DEFVAL	{ 0 }
	::= { wfFrSVCOptionsEntry 23 }

    wfFrSVCOptionsLLCoreOutBc OBJECT-TYPE
	SYNTAX	INTEGER (0..2147483647)
	ACCESS	read-write
	STATUS	mandatory
	DESCRIPTION
		" Outgoing committed burst size in bytes.
		  Q.933:Committed burst is the maximum amount of data
		  (in bits) that the network agrees to transfer, under
		  normal conditions, over a measurement interval T.
		  information field bits transferred per second across a
		  user-network interface in one direction, measured over
		  an interval of duration T."
	DEFVAL	{ 0 }
	::= { wfFrSVCOptionsEntry 24 }

    wfFrSVCOptionsLLCoreInBc OBJECT-TYPE
	SYNTAX	INTEGER (0..2147483647)
	ACCESS	read-write
	STATUS	mandatory
	DESCRIPTION
		" Incoming committed burst size in bytes.
		  Q.933:Committed burst is the maximum amount of data
		  (in bits) that the network agrees to transfer, under
		  normal conditions, over a measurement interval T.
		  information field bits transferred per second across a
		  user-network interface in one direction, measured over
		  an interval of duration T."
	DEFVAL	{ 0 }
	::= { wfFrSVCOptionsEntry 25 }

    wfFrSVCOptionsLLCoreOutBe OBJECT-TYPE
	SYNTAX	INTEGER (0..2147483647)
	ACCESS	read-write
	STATUS	mandatory
	DESCRIPTION
		" Outgoing excess burst size in bytes.
		  Q.933:Excess burst is the maximum amount of
		  uncommitted data (in bits) that the network
		  will attempt to deliver over a measurement
		  interval T. "
	DEFVAL	{ 0 }
	::= { wfFrSVCOptionsEntry 26 }

    wfFrSVCOptionsLLCoreInBe OBJECT-TYPE
	SYNTAX	INTEGER (0..2147483647)
	ACCESS	read-write
	STATUS	mandatory
	DESCRIPTION
		" Incoming excess burst size in bytes.
		  Q.933:Excess burst is the maximum amount of
		  uncommitted data (in bits) that the network
		  will attempt to deliver over a measurement
		  interval T. "
	DEFVAL	{ 0 }
	::= { wfFrSVCOptionsEntry 27 }

    wfFrSVCOptionsCongestionDisable OBJECT-TYPE
        SYNTAX	INTEGER {
    		    enabled(1),
    		    disabled(2),
    		    inherit(3)
    		}
        ACCESS	read-write
        STATUS	mandatory
        DESCRIPTION
                "This indicates whether the congestion algorithm
		 should be used for this VC.  If this is not set,
		 the value is inherited from the DLCMI record."
        DEFVAL	{ inherit }
	::= { wfFrSVCOptionsEntry 28 }

    wfFrSVCOptionsCongestionTmr OBJECT-TYPE
        SYNTAX	INTEGER {
    		    half(1),
    		    one(2),
    		    oneandhalf(3),
    		    two(4),
    		    twoandhalf(5),
    		    three(6),
    		    threeandhalf(7),
    		    four(8),
    		    fourandhalf(9),
    		    five(10)
    		}
        ACCESS	read-write
        STATUS	mandatory
        DESCRIPTION
                "This is the time period over which congestion
		 notifications are counted.  It is also the
		 period during which the VC will cease sending
		 information before resuming transmission if no
		 congestion notifications are received."
        DEFVAL	{ one }
	::= { wfFrSVCOptionsEntry 29 }

    wfFrSVCOptionsCongestionCtr OBJECT-TYPE
        SYNTAX	INTEGER(1..500)
        ACCESS	read-write
        STATUS	mandatory
        DESCRIPTION
                "This represents the number of congestion
		 notifications, when received within
	         wfFrSVCOptionsCongestionTmr time, that will result
                 in the VC ceasing transmissions."
        DEFVAL	{ 20 }
	::= { wfFrSVCOptionsEntry 30 }

    wfFrSVCOptionsCongestionMethod OBJECT-TYPE
        SYNTAX	INTEGER {
                    shutdown(1),
                    throttle(2),
                    throttlethenshutdown(3),
                    inherit(4)
                }
        ACCESS	read-write
        STATUS	mandatory
        DESCRIPTION
                "Action when VC congestion occurs"
        DEFVAL	{ inherit }
	::= { wfFrSVCOptionsEntry 31 }

    wfFrSVCOptionsTrafficShapingDisable OBJECT-TYPE
        SYNTAX	INTEGER {
                    enabled(1),
                    disabled(2)
                }
        ACCESS	read-write
        STATUS	mandatory
        DESCRIPTION
                "Enable VC traffic shaping"
        DEFVAL	{ disabled }
	::= { wfFrSVCOptionsEntry 32 }

    wfFrSVCOptionsWcpEnable OBJECT-TYPE
        SYNTAX	INTEGER {
                    enabled(1),
                    disabled(2)
                }
        ACCESS	read-write
        STATUS	mandatory
        DESCRIPTION
                "Enable Compression"
        DEFVAL	{ enabled }
	::= { wfFrSVCOptionsEntry 33 }

    wfFrSVCOptionsName OBJECT-TYPE
        SYNTAX	DisplayString
        ACCESS	read-write
        STATUS	mandatory
        DESCRIPTION
                "User name for SVC options"
	::= { wfFrSVCOptionsEntry 34 }



    wfFrSVCActiveCallTable OBJECT-TYPE
	SYNTAX	SEQUENCE OF WfFrSVCActiveCallEntry
	ACCESS	not-accessible
	STATUS	mandatory
	DESCRIPTION
		" The MIB Table for the FRF.4 signalling parameters
		  in use for a sucessfully signalled SVC "
	::= { wfFrameRelay2Group 11 }

    wfFrSVCActiveCallEntry OBJECT-TYPE
	SYNTAX	WfFrSVCActiveCallEntry
	ACCESS	not-accessible
	STATUS	mandatory
	DESCRIPTION
		" The entry of FRF4 SVC active call MIB table "
	INDEX	{ wfFrSVCActiveCallLineNumber,
		wfFrSVCActiveCallLLIndex,
		wfFrSVCActiveCallDLCI }
	::= { wfFrSVCActiveCallTable 1 }

    WfFrSVCActiveCallEntry ::= SEQUENCE {
	wfFrSVCActiveCallDelete
		INTEGER,
	wfFrSVCActiveCallLineNumber
		INTEGER,
	wfFrSVCActiveCallLLIndex
		INTEGER,
	wfFrSVCActiveCallDLCI
		INTEGER,
	wfFrSVCActiveCallDirection
		INTEGER,
	wfFrSVCActiveCallCircuitNumber
		INTEGER,
	wfFrSVCActiveCallCalledNum
		DisplayString,
	wfFrSVCActiveCallCalledSubAdr
		DisplayString,
	wfFrSVCActiveCallCalledPlan
		INTEGER,
	wfFrSVCActiveCallCalledTypeNum
		INTEGER,
	wfFrSVCActiveCallCallingNum
		DisplayString,
	wfFrSVCActiveCallCallingSubAdr
		DisplayString,
	wfFrSVCActiveCallCallingPlan
		INTEGER,
	wfFrSVCActiveCallCallingTypeNum
		INTEGER,
	wfFrSVCActiveCallX213DataPriority
		INTEGER,
	wfFrSVCActiveCallX213DataLQAPriority
		INTEGER,
	wfFrSVCActiveCallX213GainPriority
		INTEGER,
	wfFrSVCActiveCallX213GainLQAPriority
		INTEGER,
	wfFrSVCActiveCallX213KeepPriority
		INTEGER,
	wfFrSVCActiveCallX213KeepLQAPriority
		INTEGER,
	wfFrSVCActiveCallLLCoreOutThroughput
		INTEGER,
	wfFrSVCActiveCallLLCoreInThroughput
		INTEGER,
	wfFrSVCActiveCallLLCoreMinOutThroughput
		INTEGER,
	wfFrSVCActiveCallLLCoreMinInThroughput
		INTEGER,
	wfFrSVCActiveCallLLCoreOutBc
		INTEGER,
	wfFrSVCActiveCallLLCoreInBc
		INTEGER,
	wfFrSVCActiveCallLLCoreOutBe
		INTEGER,
	wfFrSVCActiveCallLLCoreInBe
		INTEGER,
	wfFrSVCActiveCallConnectTime
		INTEGER
    }

    wfFrSVCActiveCallDelete OBJECT-TYPE
	SYNTAX	INTEGER {
		created(1),
		deleted(2)
	}
	ACCESS	read-write
	STATUS	mandatory
	DESCRIPTION
		" Delete SVC active call record "
	DEFVAL	{ created }
	::= { wfFrSVCActiveCallEntry 1 }

    wfFrSVCActiveCallLineNumber OBJECT-TYPE
	SYNTAX	INTEGER
	ACCESS	read-only
	STATUS	mandatory
	DESCRIPTION
		" Logical Line number.  This attribute is Instance Id 1 "
	::= { wfFrSVCActiveCallEntry 2 }

    wfFrSVCActiveCallLLIndex OBJECT-TYPE
	SYNTAX	INTEGER
	ACCESS	read-only
	STATUS	mandatory
	DESCRIPTION
		" Lower Layer Index.  This attribute is Instance Id 2 "
	::= { wfFrSVCActiveCallEntry 3 }

    wfFrSVCActiveCallDLCI OBJECT-TYPE
	SYNTAX	INTEGER
	ACCESS	read-only
	STATUS	mandatory
	DESCRIPTION
		" DCLI number.  This attribute is Instance Id 3 "
	::= { wfFrSVCActiveCallEntry 4 }

    wfFrSVCActiveCallDirection OBJECT-TYPE
	SYNTAX	INTEGER {
		inbound(1),
		outbound(2)
	}
	ACCESS	read-only
	STATUS	mandatory
	DESCRIPTION
		" Direction of call relative to router "
	::= { wfFrSVCActiveCallEntry 5 }

    wfFrSVCActiveCallCircuitNumber OBJECT-TYPE
	SYNTAX	INTEGER
	ACCESS	read-only
	STATUS	mandatory
	DESCRIPTION
		" Circuit number associated with this call "
	DEFVAL	{ 0 }
	::= { wfFrSVCActiveCallEntry 6 }

    wfFrSVCActiveCallCalledNum OBJECT-TYPE
	SYNTAX	DisplayString
	ACCESS	read-only
	STATUS	mandatory
	DESCRIPTION
		" Number from called party number information element "
	::= { wfFrSVCActiveCallEntry 7 }

    wfFrSVCActiveCallCalledSubAdr OBJECT-TYPE
	SYNTAX	DisplayString
	ACCESS	read-only
	STATUS	mandatory
	DESCRIPTION
		" Subaddress from called party subaddress information
		  element "
	::= { wfFrSVCActiveCallEntry 8 }

    wfFrSVCActiveCallCalledPlan OBJECT-TYPE
	SYNTAX  INTEGER 
	ACCESS	read-only
	STATUS	mandatory
	DESCRIPTION
		" Numbering plan from called party number
		  information element "
	DEFVAL	{ 0 }
	::= { wfFrSVCActiveCallEntry 9 }

    wfFrSVCActiveCallCalledTypeNum OBJECT-TYPE
	SYNTAX  INTEGER
	ACCESS	read-only
	STATUS	mandatory
	DESCRIPTION
		" Type of number from called party number
		  information element "
	DEFVAL	{ 0 }
	::= { wfFrSVCActiveCallEntry 10 }

    wfFrSVCActiveCallCallingNum OBJECT-TYPE
	SYNTAX	DisplayString
	ACCESS	read-only
	STATUS	mandatory
	DESCRIPTION
		" Number from calling party number information element "
	::= { wfFrSVCActiveCallEntry 11 }

    wfFrSVCActiveCallCallingSubAdr OBJECT-TYPE
	SYNTAX	DisplayString
	ACCESS	read-only
	STATUS	mandatory
	DESCRIPTION
		" Subaddress from calling party subaddress information
		  element "
	::= { wfFrSVCActiveCallEntry 12 }

    wfFrSVCActiveCallCallingPlan OBJECT-TYPE
	SYNTAX  INTEGER 
	ACCESS	read-only
	STATUS	mandatory
	DESCRIPTION
		" Numbering plan from calling party number
		  information element "
	DEFVAL	{ 0 }
	::= { wfFrSVCActiveCallEntry 13 }

    wfFrSVCActiveCallCallingTypeNum OBJECT-TYPE
	SYNTAX  INTEGER
	ACCESS	read-only
	STATUS	mandatory
	DESCRIPTION
		" Type of number from calling party number
		  information element "
	DEFVAL	{ 0 }
	::= { wfFrSVCActiveCallEntry 14 }

    wfFrSVCActiveCallX213DataPriority OBJECT-TYPE
	SYNTAX	INTEGER 
	ACCESS	read-only
	STATUS	mandatory
	DESCRIPTION
		" The priority of data on the network connection,
		  from the X.213 information element. "
	DEFVAL	{ 0 }
	::= { wfFrSVCActiveCallEntry 15 }

    wfFrSVCActiveCallX213DataLQAPriority OBJECT-TYPE
	SYNTAX	INTEGER
	ACCESS	read-only
	STATUS	mandatory
	DESCRIPTION
		" The lowest quality acceptable (LQA) priority of
		  data on the network connection, from the X.213
		  information element. "
	DEFVAL	{ 0 }
	::= { wfFrSVCActiveCallEntry 16 }

    wfFrSVCActiveCallX213GainPriority OBJECT-TYPE
	SYNTAX	INTEGER
	ACCESS	read-only
	STATUS	mandatory
	DESCRIPTION
		" The priority to gain a network connection,
		  from the X.213 information element. "
	DEFVAL	{ 0 }
	::= { wfFrSVCActiveCallEntry 17 }

    wfFrSVCActiveCallX213GainLQAPriority OBJECT-TYPE
	SYNTAX	INTEGER
	ACCESS	read-only
	STATUS	mandatory
	DESCRIPTION
		" The lowest quality acceptable (LQA) priority to
		  gain a network connection, from the X.213
		  information element. "
	DEFVAL	{ 0 }
	::= { wfFrSVCActiveCallEntry 18 }

    wfFrSVCActiveCallX213KeepPriority OBJECT-TYPE
	SYNTAX	INTEGER
	ACCESS	read-only
	STATUS	mandatory
	DESCRIPTION
		" The priority to keep a network connection,
		  from the X.213 information element. "
	DEFVAL	{ 0 }
	::= { wfFrSVCActiveCallEntry 19 }

    wfFrSVCActiveCallX213KeepLQAPriority OBJECT-TYPE
	SYNTAX	INTEGER
	ACCESS	read-only
	STATUS	mandatory
	DESCRIPTION
		" The lowest quality acceptable (LQA) priority to
		  keep a network connection, from the X.213
		  information element. "
	DEFVAL	{ 0 }
	::= { wfFrSVCActiveCallEntry 20 }


    wfFrSVCActiveCallLLCoreOutThroughput OBJECT-TYPE
	SYNTAX	INTEGER
	ACCESS	read-only
	STATUS	mandatory
	DESCRIPTION
		" Requested outgoing throughput, from the link layer
		  core information element. "
	DEFVAL	{ 0 }
	::= { wfFrSVCActiveCallEntry 21 }

    wfFrSVCActiveCallLLCoreInThroughput OBJECT-TYPE
	SYNTAX	INTEGER
	ACCESS	read-only
	STATUS	mandatory
	DESCRIPTION
		" Requested incoming throughput, from the link layer
		  core information element. "
	DEFVAL	{ 0 }
	::= { wfFrSVCActiveCallEntry 22 }

    wfFrSVCActiveCallLLCoreMinOutThroughput OBJECT-TYPE
	SYNTAX	INTEGER
	ACCESS	read-only
	STATUS	mandatory
	DESCRIPTION
		" Minimum acceptable outgoing throughput, from the 
		  link layer core information element. "
	DEFVAL	{ 0 }
	::= { wfFrSVCActiveCallEntry 23 }

    wfFrSVCActiveCallLLCoreMinInThroughput OBJECT-TYPE
	SYNTAX	INTEGER
	ACCESS	read-only
	STATUS	mandatory
	DESCRIPTION
		" Minimum acceptable incoming throughput, from the 
		  link layer core information element. "
	DEFVAL	{ 0 }
	::= { wfFrSVCActiveCallEntry 24 }

    wfFrSVCActiveCallLLCoreOutBc OBJECT-TYPE
	SYNTAX	INTEGER
	ACCESS	read-only
	STATUS	mandatory
	DESCRIPTION
		" Outgoing committed burst size in bytes, from the 
		  link layer core information element. "
	DEFVAL	{ 0 }
	::= { wfFrSVCActiveCallEntry 25 }

    wfFrSVCActiveCallLLCoreInBc OBJECT-TYPE
	SYNTAX	INTEGER
	ACCESS	read-only
	STATUS	mandatory
	DESCRIPTION
		" Incoming committed burst size in bytes, from the 
		  link layer core information element. "
	DEFVAL	{ 0 }
	::= { wfFrSVCActiveCallEntry 26 }

    wfFrSVCActiveCallLLCoreOutBe OBJECT-TYPE
	SYNTAX	INTEGER
	ACCESS	read-only
	STATUS	mandatory
	DESCRIPTION
		" Outgoing excess burst size in bytes, from the 
		  link layer core information element. "
	DEFVAL	{ 0 }
	::= { wfFrSVCActiveCallEntry 27 }

    wfFrSVCActiveCallLLCoreInBe OBJECT-TYPE
	SYNTAX	INTEGER 
	ACCESS	read-only
	STATUS	mandatory
	DESCRIPTION
		" Incoming excess burst size in bytes, from the 
		  link layer core information element. "
	DEFVAL	{ 0 }
	::= { wfFrSVCActiveCallEntry 28 }

    wfFrSVCActiveCallConnectTime OBJECT-TYPE
        SYNTAX	INTEGER 
        ACCESS	read-only
        STATUS	mandatory
        DESCRIPTION
                "Time connect message was sent or received. "
        DEFVAL	{ 0 }
	::= { wfFrSVCActiveCallEntry 29 }

    wfFrPtIntfTable OBJECT-TYPE
        SYNTAX	SEQUENCE OF WfFrPtIntfEntry
        ACCESS	not-accessible
        STATUS	mandatory
        DESCRIPTION
                "The PVC Passthru interface table contains the list of
                interface circuits.  There will be one entry for each
                direct mode PVC configured for PVC Passthru."
        ::= { wfFrameRelay2Group 12 }

    wfFrPtIntfEntry OBJECT-TYPE
        SYNTAX	WfFrPtIntfEntry
        ACCESS	not-accessible
        STATUS	mandatory
        DESCRIPTION
                "A PVC Passthru interface."
        INDEX	{ wfFrPtIntfCct,
                  wfFrPtIntfDlci }
        ::= { wfFrPtIntfTable 1 }

    WfFrPtIntfEntry ::= SEQUENCE {
    	    wfFrPtIntfDelete
    		INTEGER,
    	    wfFrPtIntfDisable
    		INTEGER,
    	    wfFrPtIntfCct
    		INTEGER,
    	    wfFrPtIntfDlci
    		INTEGER,
    	    wfFrPtIntfState
    		INTEGER,
    	    wfFrPtIntfRxFrames
    		Counter,
    	    wfFrPtIntfTxFrames
    		Counter,
    	    wfFrPtIntfDiscards
    		Counter,
    	    wfFrPtIntfDrops
    		Counter
        }

    wfFrPtIntfDelete OBJECT-TYPE
        SYNTAX	INTEGER {
    		    created(1),
    		    deleted(2)
    		}
        ACCESS	read-write
        STATUS	mandatory
        DESCRIPTION
                "Create/delete indicator for the PVC Passthru Interface entry."
        DEFVAL	{ created }
        ::= { wfFrPtIntfEntry 1 }

    wfFrPtIntfDisable OBJECT-TYPE
        SYNTAX	INTEGER {
    		    enabled(1),
    		    disabled(2)
    		}
        ACCESS	read-write
        STATUS	mandatory
        DESCRIPTION
                "Enable/disable indicator for the PVC Passthru Interface entry."
        DEFVAL	{ enabled }
        ::= { wfFrPtIntfEntry 2 }

    wfFrPtIntfCct OBJECT-TYPE
        SYNTAX	INTEGER
        ACCESS	read-only
        STATUS	mandatory
        DESCRIPTION
                "The DP circuit on which this interface resides. This
                attribute is the first component of the Instance ID 
                for this object."
        ::= { wfFrPtIntfEntry 3 }

    wfFrPtIntfDlci OBJECT-TYPE
        SYNTAX	INTEGER
        ACCESS	read-only
        STATUS	mandatory
        DESCRIPTION
                "The dlci associated with this circuit. This attribute
                is the second component of the Instance ID for this object."
        ::= { wfFrPtIntfEntry 4 }

    wfFrPtIntfState OBJECT-TYPE
        SYNTAX	INTEGER {
    		    active(1),
    		    inactive(2),
    		    invalid(3),
    		    notpresent(4)
                }
        ACCESS	read-only
        STATUS	mandatory
        DESCRIPTION
                "Interface state indicator. The state is active if the circuit
                is up."
        DEFVAL	{ notpresent }
        ::= { wfFrPtIntfEntry 5 }

    wfFrPtIntfRxFrames OBJECT-TYPE
        SYNTAX	Counter
        ACCESS	read-only
        STATUS	mandatory
        DESCRIPTION
                "The number of frames received on this interface."
        ::= { wfFrPtIntfEntry 6 }

    wfFrPtIntfTxFrames OBJECT-TYPE
        SYNTAX	Counter
        ACCESS	read-only
        STATUS	mandatory
        DESCRIPTION
                "The number of frames transmitted on this interface."
        ::= { wfFrPtIntfEntry 7 }

    wfFrPtIntfDiscards OBJECT-TYPE
        SYNTAX	Counter
        ACCESS	read-only
        STATUS	mandatory
        DESCRIPTION
                "The number of inbound frames discarded, either because
                this passthru interface is disabled or it has no partner."
        ::= { wfFrPtIntfEntry 8 }

    wfFrPtIntfDrops OBJECT-TYPE
        SYNTAX	Counter
        ACCESS	read-only
        STATUS	mandatory
        DESCRIPTION
                "The number of outbound frames dropped, because this
                passthru interface is disabled or inactive."
        ::= { wfFrPtIntfEntry 9 }

    wfFrPtMappingTable OBJECT-TYPE
        SYNTAX	SEQUENCE OF WfFrPtMappingEntry
        ACCESS	not-accessible
        STATUS	mandatory
        DESCRIPTION
                "The PVC Passthru mapping table contains the static routes
                between PVCs."
        ::= { wfFrameRelay2Group 13 }

    wfFrPtMappingEntry OBJECT-TYPE
        SYNTAX	WfFrPtMappingEntry
        ACCESS	not-accessible
        STATUS	mandatory
        DESCRIPTION
                "A PVC Passthru mapping."
        INDEX	{ wfFrPtMappingCctA,
                  wfFrPtMappingDlciA,
    		  wfFrPtMappingCctB,
                  wfFrPtMappingDlciB }
        ::= { wfFrPtMappingTable 1 }

    WfFrPtMappingEntry ::= SEQUENCE {
    	    wfFrPtMappingDelete
    		INTEGER,
    	    wfFrPtMappingDisable
    		INTEGER,
    	    wfFrPtMappingCctA
    		INTEGER,
    	    wfFrPtMappingDlciA
    		INTEGER,
    	    wfFrPtMappingCctB
    		INTEGER,
    	    wfFrPtMappingDlciB
    		INTEGER,
    	    wfFrPtMappingState
    		INTEGER
        }

    wfFrPtMappingDelete OBJECT-TYPE
        SYNTAX	INTEGER {
    		    created(1),
    		    deleted(2)
    		}
        ACCESS	read-write
        STATUS	mandatory
        DESCRIPTION
                "Create/delete indicator for the PVC Passthru Mapping entry."
        DEFVAL	{ created }
        ::= { wfFrPtMappingEntry 1 }

    wfFrPtMappingDisable OBJECT-TYPE
        SYNTAX	INTEGER {
    		    enabled(1),
    		    disabled(2)
    		}
        ACCESS	read-write
        STATUS	mandatory
        DESCRIPTION
                "Enable/disable indicator for the PVC Passthru Mapping entry."
        DEFVAL	{ enabled }
        ::= { wfFrPtMappingEntry 2 }

    wfFrPtMappingCctA OBJECT-TYPE
        SYNTAX	INTEGER
        ACCESS	read-only
        STATUS	mandatory
        DESCRIPTION
                "The first circuit (i.e., hybrid mode PVC) for this mapping.
                All data received on this circuit is delivered to circuit B.
                This attribute is the 1st of 2 components of the Instance ID 
                for this object."
        ::= { wfFrPtMappingEntry 3 }

    wfFrPtMappingDlciA OBJECT-TYPE
        SYNTAX	INTEGER
        ACCESS	read-only
        STATUS	mandatory
        DESCRIPTION
                "The dlci associated with circuit A."
        ::= { wfFrPtMappingEntry 4 }

    wfFrPtMappingCctB OBJECT-TYPE
        SYNTAX	INTEGER
        ACCESS	read-only
        STATUS	mandatory
        DESCRIPTION
                "The second circuit (i.e., hybrid mode PVC) for this mapping.
                All data received on this circuit is delivered to circuit A.
                This attribute is the 2nd of 2 components of the Instance ID 
                for this object."
        ::= { wfFrPtMappingEntry 5 }

    wfFrPtMappingDlciB OBJECT-TYPE
        SYNTAX	INTEGER
        ACCESS	read-only
        STATUS	mandatory
        DESCRIPTION
                "The dlci associated with circuit B."
        ::= { wfFrPtMappingEntry 6 }

    wfFrPtMappingState OBJECT-TYPE
        SYNTAX	INTEGER {
    		    active(1),
    		    inactive(2),
    		    invalid(3),
    		    notpresent(4)
                }
        ACCESS	read-only
        STATUS	mandatory
        DESCRIPTION
                "Mapping state indicator. The state is active if both circuits
                are up, inactive if one or both are down. The state is invalid
                if this mapping conflicts with another, or is misconfigured."
        DEFVAL	{ notpresent }
        ::= { wfFrPtMappingEntry 7 }


    wfFrMlTable OBJECT-TYPE
        SYNTAX	SEQUENCE OF WfFrMlEntry
        ACCESS	not-accessible
        STATUS	mandatory
        DESCRIPTION
                "The Multilink Frame Relay Table, containing information 
                and statistics for each Multilink Circuit"
        ::= { wfFrameRelay2Group 14 }

    wfFrMlEntry OBJECT-TYPE
        SYNTAX	WfFrMlEntry
        ACCESS	not-accessible
        STATUS	mandatory
        DESCRIPTION
                "per bundle Multilink Frame Relay information and counters"
        INDEX	{ wfFrMlCircuitNumber }
        ::= { wfFrMlTable 1 }

    WfFrMlEntry ::= SEQUENCE {
    	    wfFrMlDelete
    		INTEGER,
    	    wfFrMlCircuitNumber
    		INTEGER,
    	    wfFrMlMode
    		INTEGER,
    	    wfFrMlFragPermEnable
    		INTEGER,
    	    wfFrMlCircuitMaxBuffers
    		INTEGER,
    	    wfFrMlFragTriggerSize
    		INTEGER,
    	    wfFrMlFragStrict
    		INTEGER,
    	    wfFrMlAggVCStatusMode
    		INTEGER,
    	    wfFrMlCompressionEnable
    		INTEGER,
    	    wfFrMlHomeSlot
    		INTEGER,
    	    wfFrMlStatsLineCnt
    		Gauge,
    	    wfFrMlStatsBundleSpd
    		Gauge,
    	    wfFrMlStatsTxOctets
    		Counter,
    	    wfFrMlStatsTxPkts
    		Counter,
    	    wfFrMlStatsAvgTxListLen
    		Gauge,
    	    wfFrMlStatsRxOctets
    		Counter,
    	    wfFrMlStatsRxPkts
    		Counter,
    	    wfFrMlStatsReasmFails
    		Counter,
    	    wfFrMlStatsSeqNumberLost
    		Counter,
    	    wfFrMlStatsSeqNumberArrivedLate
    		Counter,
    	    wfFrMlStatsReSeqBufferCnt
    		Gauge,
    	    wfFrMlStatsReSeqBufferMax
    		Counter,
    	    wfFrMlStatsExceededBufferMax
    		Counter,
    	    wfFrMlStatsLinkIdleEvents
    		Counter,
	    wfFrMlStatsCalcPercent
		INTEGER,
	    wfFrMlStatsDebug
		INTEGER,
            wfFrMlStatsReassmBufferCnt
                Gauge,
            wfFrMlStatsReassmBufferMax
    		Counter,
            wfFrMlStatsNumPktsFragmented
    		Counter,
    	    wfFrMlStatsPQHiXmits
    		Counter,
    	    wfFrMlStatsPQNormalXmits
    		Counter,
    	    wfFrMlStatsPQLoXmits
    		Counter,
    	    wfFrMlStatsPQHiClippedPkts
    		Counter,
    	    wfFrMlStatsPQNormalClippedPkts
    		Counter,
    	    wfFrMlStatsPQLoClippedPkts
    		Counter,
    	    wfFrMlStatsPQIntrQHighWaterPkts
    		Gauge,
    	    wfFrMlStatsPQHiQHighWaterPkts
    		Gauge,
    	    wfFrMlStatsPQNormalQHighWaterPkts
    		Gauge,
    	    wfFrMlStatsPQLoQHighWaterPkts
    		Gauge,
    	    wfFrMlStatsPQHighWaterPktsClear
    		INTEGER,
    	    wfFrMlStatsPQDroppedPkts
    		Counter,
    	    wfFrMlStatsPQLargePkts
    		Counter,
    	    wfFrMlStatsPQHiTotalOctets
    		Counter,
    	    wfFrMlStatsPQNormalTotalOctets
    		Counter,
    	    wfFrMlStatsPQLoTotalOctets
    		Counter,
    	    wfFrMlStatsPQPktsNotQueued
    		Counter
        }

    wfFrMlDelete OBJECT-TYPE
        SYNTAX	INTEGER {
    		    created(1),
    		    deleted(2)
    		}
        ACCESS	read-write
        STATUS	mandatory
        DESCRIPTION
                "Create/Delete parameter"
        DEFVAL	{ created }
        ::= { wfFrMlEntry 1 }

    wfFrMlCircuitNumber OBJECT-TYPE
        SYNTAX	INTEGER(1..1023)
        ACCESS	read-only
        STATUS	mandatory
        DESCRIPTION
                "cct number for this instance"
        ::= { wfFrMlEntry 2 }

    wfFrMlMode OBJECT-TYPE
        SYNTAX	INTEGER {
    		    dtedte(1),
    		    uni(2)
    		}
        ACCESS	read-write
        STATUS	mandatory
        DESCRIPTION
                "Multilink frame relay mode"
        DEFVAL	{ dtedte }
        ::= { wfFrMlEntry 3 }

    wfFrMlFragPermEnable OBJECT-TYPE
        SYNTAX	INTEGER {
    		    enabled(1),
    		    disabled(2)
    		}
        ACCESS	read-write
        STATUS	mandatory
        DESCRIPTION
                "Bundle level enable/disable for fragmenting packets
                 regardless of trigger size."
        DEFVAL	{ disabled }
        ::= { wfFrMlEntry 4 }

    wfFrMlCircuitMaxBuffers OBJECT-TYPE
        SYNTAX  INTEGER(10..60)
        ACCESS  read-write
        STATUS  mandatory
        DESCRIPTION
                "This is the maximum number of stored buffers allowed in the
                 Multilink Receive logic for this circuit at any one time."
        DEFVAL  { 30 }
        ::= { wfFrMlEntry 5 }

    wfFrMlFragTriggerSize OBJECT-TYPE
        SYNTAX	INTEGER
        ACCESS	read-write
        STATUS	mandatory
        DESCRIPTION
                "This is the minimum size of a packet of which Multilink
                will fragment."
        DEFVAL	{ 256 }
        ::= { wfFrMlEntry 6 }

    wfFrMlFragStrict OBJECT-TYPE
        SYNTAX	INTEGER {
    		    enabled(1),
    		    disabled(2)
    		}
        ACCESS	read-write
        STATUS	mandatory
        DESCRIPTION
               "enable/disable strict fragmentation algorithm i.e. fragmenting
                a packet when its size exceeds the threshold regardless of what
                the average packet size is"
        DEFVAL	{ disabled }
        ::= { wfFrMlEntry 7 }

    wfFrMlAggVCStatusMode OBJECT-TYPE
        SYNTAX	INTEGER {
    		    anyactive(1),
    		    allactive(2),
                    other(3)    
    		}
        ACCESS	read-write
        STATUS	mandatory
        DESCRIPTION
                "FRF.13 defined mode of status aggregation."
        DEFVAL	{ anyactive }
        ::= { wfFrMlEntry 8 }

    wfFrMlCompressionEnable OBJECT-TYPE
        SYNTAX	INTEGER {
                    enabled(1),
                    disabled(2)
                }
        ACCESS	read-write
        STATUS	mandatory
        DESCRIPTION
                "Enable compression for all PVCs in the bundle."
        DEFVAL	{ disabled }
        ::= { wfFrMlEntry 9 }

    wfFrMlHomeSlot OBJECT-TYPE
        SYNTAX	INTEGER
        ACCESS	read-only
        STATUS	mandatory
        DESCRIPTION
                "Slot on which this Multilink Control Subsystem exists"
        ::= { wfFrMlEntry 10 }

    wfFrMlStatsLineCnt OBJECT-TYPE
        SYNTAX	Gauge
        ACCESS	read-only
        STATUS	mandatory
        DESCRIPTION
                "Current count of lines in Multilink bundle"
        ::= { wfFrMlEntry 11 }

    wfFrMlStatsBundleSpd OBJECT-TYPE
        SYNTAX	Gauge
        ACCESS	read-only
        STATUS	mandatory
        DESCRIPTION
                "Current total bandwidth of Multilink bundle"
        ::= { wfFrMlEntry 12 }

    wfFrMlStatsTxOctets OBJECT-TYPE
        SYNTAX	Counter
        ACCESS	read-only
        STATUS	mandatory
        DESCRIPTION
                "Number of octets transmitted by Multilink"
        ::= { wfFrMlEntry 13 }

    wfFrMlStatsTxPkts OBJECT-TYPE
        SYNTAX	Counter
        ACCESS	read-only
        STATUS	mandatory
        DESCRIPTION
                "Number of packets transmitted by Multilink"
        ::= { wfFrMlEntry 14 }

    wfFrMlStatsAvgTxListLen OBJECT-TYPE
        SYNTAX	Gauge
        ACCESS	read-only
        STATUS	mandatory
        DESCRIPTION
                "Average number of packets received in the transient
                list by the Multilink Transmit gate."
        ::= { wfFrMlEntry 15 }

    wfFrMlStatsRxOctets OBJECT-TYPE
        SYNTAX	Counter
        ACCESS	read-only
        STATUS	mandatory
        DESCRIPTION
                "Number of octets received without error"
        ::= { wfFrMlEntry 16 }

    wfFrMlStatsRxPkts OBJECT-TYPE
        SYNTAX	Counter
        ACCESS	read-only
        STATUS	mandatory
        DESCRIPTION
                "Number of packets received by Multilink"
        ::= { wfFrMlEntry 17 }

    wfFrMlStatsReasmFails OBJECT-TYPE
        SYNTAX	Counter
        ACCESS	read-only
        STATUS	mandatory
        DESCRIPTION
                "Number of packet reassembly failures"
        ::= { wfFrMlEntry 18 }

    wfFrMlStatsSeqNumberLost OBJECT-TYPE
        SYNTAX	Counter
        ACCESS	read-only
        STATUS	mandatory
        DESCRIPTION
                "Number of Multilink packets considered to be lost on
                the wire"
        ::= { wfFrMlEntry 19 }

    wfFrMlStatsSeqNumberArrivedLate OBJECT-TYPE
        SYNTAX	Counter
        ACCESS	read-only
        STATUS	mandatory
        DESCRIPTION
                "Number of Multilink packets which arrive
                containing an old Sequence Number. IE: packets
                with a more current Sequence Number have already
                been sent up to NCP"
        ::= { wfFrMlEntry 20 }

    wfFrMlStatsReSeqBufferCnt OBJECT-TYPE
        SYNTAX	Gauge
        ACCESS	read-only
        STATUS	mandatory
        DESCRIPTION
                "Number of Multilink packets currently stored
                in the ReSequencing buffer pool."
        ::= { wfFrMlEntry 21 }

    wfFrMlStatsReSeqBufferMax OBJECT-TYPE
        SYNTAX	Counter
        ACCESS	read-only
        STATUS	mandatory
        DESCRIPTION
                "The Maximum Number of Multilink packets stored
                in the ReSequencing buffer pool."
        ::= { wfFrMlEntry 22 }

    wfFrMlStatsExceededBufferMax OBJECT-TYPE
        SYNTAX	Counter
        ACCESS	read-only
        STATUS	mandatory
        DESCRIPTION
                "The number of times a buffer needed to be stored by the 
                 Multilink Receive logic when the count of buffers stored,
                 wfFrMlStatsReSeqBufferMax,was equal to the maximum allowable
                 for this circuit, wfFrMlCircuitMaxBuffers."
        ::= { wfFrMlEntry 23 }

    wfFrMlStatsLinkIdleEvents OBJECT-TYPE
        SYNTAX  Counter
        ACCESS  read-only
        STATUS  mandatory
        DESCRIPTION
                "The number of times the Multilink Receive logic detected a
                 stored buffer received on a line which has been declared idle."
        ::= { wfFrMlEntry 24 }

    wfFrMlStatsCalcPercent OBJECT-TYPE
        SYNTAX	INTEGER {
    		    enabled(1),
    		    disabled(2)
    		}
        ACCESS	read-write
        STATUS	mandatory
        DESCRIPTION
                "enable/disable collection of Rx percentage line usage"
        DEFVAL	{ disabled }
        ::= { wfFrMlEntry 25 }

    wfFrMlStatsDebug OBJECT-TYPE
        SYNTAX	INTEGER
        ACCESS	read-write
        STATUS	mandatory
        DESCRIPTION
                "DEBUG parameter - this is used to control debug code
                 for the Multilink subsystem"
        ::= { wfFrMlEntry 26 }

    wfFrMlStatsReassmBufferCnt OBJECT-TYPE
        SYNTAX  Gauge
        ACCESS  read-only
        STATUS  mandatory
        DESCRIPTION
                "Number of Multilink packets currently stored
                in the Reassembling buffer pools."
        ::= { wfFrMlEntry 27 }

    wfFrMlStatsReassmBufferMax OBJECT-TYPE
        SYNTAX  Counter
        ACCESS  read-only
        STATUS  mandatory
        DESCRIPTION
                "The Maximum Number of Multilink packets stored
                in the Reassembling buffer pools."
        ::= { wfFrMlEntry 28 }

    wfFrMlStatsNumPktsFragmented OBJECT-TYPE
        SYNTAX  Counter
        ACCESS  read-only
        STATUS  mandatory
        DESCRIPTION
                "The Number of Multilink packets that were 
	         fragmented."
        ::= { wfFrMlEntry 29 }

    wfFrMlStatsPQHiXmits OBJECT-TYPE
        SYNTAX  Counter
        ACCESS  read-only
        STATUS  mandatory
        DESCRIPTION
                "High priority transmit count."
        ::= { wfFrMlEntry 30 }

    wfFrMlStatsPQNormalXmits OBJECT-TYPE
        SYNTAX  Counter
        ACCESS  read-only
        STATUS  mandatory
        DESCRIPTION
                "Normal priority transmit count."
        ::= { wfFrMlEntry 31 }

    wfFrMlStatsPQLoXmits OBJECT-TYPE
        SYNTAX	Counter
        ACCESS	read-only
        STATUS	mandatory
        DESCRIPTION
                "Low priority transmit count"
        ::= { wfFrMlEntry 32 }

    wfFrMlStatsPQHiClippedPkts OBJECT-TYPE
        SYNTAX	Counter
        ACCESS	read-only
        STATUS	mandatory
        DESCRIPTION
                "High priority transmit clip Count"
        ::= { wfFrMlEntry 33 }

    wfFrMlStatsPQNormalClippedPkts OBJECT-TYPE
        SYNTAX	Counter
        ACCESS	read-only
        STATUS	mandatory
        DESCRIPTION
                "Normal priority transmit clip Count"
        ::= { wfFrMlEntry 34 }

    wfFrMlStatsPQLoClippedPkts OBJECT-TYPE
        SYNTAX	Counter
        ACCESS	read-only
        STATUS	mandatory
        DESCRIPTION
                "Low priority transmit clip Count"
        ::= { wfFrMlEntry 35 }

    wfFrMlStatsPQIntrQHighWaterPkts OBJECT-TYPE
        SYNTAX	Gauge
        ACCESS	read-only
        STATUS	mandatory
        DESCRIPTION
                "Interrupt-priority Queue high-water mark"
        ::= { wfFrMlEntry 36 }

    wfFrMlStatsPQHiQHighWaterPkts OBJECT-TYPE
        SYNTAX	Gauge
        ACCESS	read-only
        STATUS	mandatory
        DESCRIPTION
                "High-priority Queue high-water mark"
        ::= { wfFrMlEntry 37 }

    wfFrMlStatsPQNormalQHighWaterPkts OBJECT-TYPE
        SYNTAX	Gauge
        ACCESS	read-only
        STATUS	mandatory
        DESCRIPTION
                "Normal-priority Queue high-water mark"
        ::= { wfFrMlEntry 38 }

    wfFrMlStatsPQLoQHighWaterPkts OBJECT-TYPE
        SYNTAX	Gauge
        ACCESS	read-only
        STATUS	mandatory
        DESCRIPTION
                "Low-priority Queue high-water mark"
        ::= { wfFrMlEntry 39 }

    wfFrMlStatsPQHighWaterPktsClear OBJECT-TYPE
        SYNTAX	INTEGER
        ACCESS	read-write
        STATUS	mandatory
        DESCRIPTION
                "Attribute to clear the high-water marks. When the MIB
                changes, Priority Queueing (if ENABLED) checks to see
                if HighWaterPktsClear is different than the last time the MIB
                was modified in any way.  If it is different,
                all the high water marks (see above) are set to zero."
        ::= { wfFrMlEntry 40 }

    wfFrMlStatsPQDroppedPkts OBJECT-TYPE
        SYNTAX	Counter
        ACCESS	read-only
        STATUS	mandatory
        DESCRIPTION
                "Packets which were filtered in Priority Queueing"
        ::= { wfFrMlEntry 41 }

    wfFrMlStatsPQLargePkts OBJECT-TYPE
        SYNTAX	Counter
        ACCESS	read-only
        STATUS	mandatory
        DESCRIPTION
                "Large Packets which became an exception to latency rules"
        ::= { wfFrMlEntry 42 }

    wfFrMlStatsPQHiTotalOctets OBJECT-TYPE
        SYNTAX	Counter
        ACCESS	read-only
        STATUS	mandatory
        DESCRIPTION
                "Running total of High Octets transmitted when
                using Bandwidth Allocation dequeueing algorithm"
        ::= { wfFrMlEntry 43 }

    wfFrMlStatsPQNormalTotalOctets OBJECT-TYPE
        SYNTAX	Counter
        ACCESS	read-only
        STATUS	mandatory
        DESCRIPTION
                "Running total of Normal Octets transmitted when
                using Bandwidth Allocation dequeueing algorithm"
        ::= { wfFrMlEntry 44 }

    wfFrMlStatsPQLoTotalOctets OBJECT-TYPE
        SYNTAX	Counter
        ACCESS	read-only
        STATUS	mandatory
        DESCRIPTION
                "Running total of Low Octets transmitted when
                using Bandwidth Allocation dequeueing algorithm"
        ::= { wfFrMlEntry 45 }

    wfFrMlStatsPQPktsNotQueued OBJECT-TYPE
        SYNTAX Counter
        ACCESS read-only
        STATUS mandatory
        DESCRIPTION
                "Packets that were not Queued or Dropped by  
                 Priority Queuing "
        ::= { wfFrMlEntry 46 }

    wfFrMlVCTable OBJECT-TYPE
        SYNTAX	SEQUENCE OF WfFrMlVCEntry
        ACCESS	not-accessible
        STATUS	mandatory
        DESCRIPTION
                "The Multilink Frame Relay VC Table, containing information 
                and statistics for each multilink aggregated VC"
        ::= { wfFrameRelay2Group 15 }

    wfFrMlVCEntry OBJECT-TYPE
        SYNTAX	WfFrMlVCEntry
        ACCESS	not-accessible
        STATUS	mandatory
        DESCRIPTION
                "Multilink Frame Relay VC information and counters"
        INDEX	{ wfFrMlVCCircuitNumber,
                  wfFrMlVCDlci }
        ::= { wfFrMlVCTable 1 }

    WfFrMlVCEntry ::= SEQUENCE {
    	    wfFrMlVCDelete
    		INTEGER,
    	    wfFrMlVCCircuitNumber
    		INTEGER,
    	    wfFrMlVCDlci
    		INTEGER,
    	    wfFrMlVCAggState
    		INTEGER,
    	    wfFrMlVCAggNumberVCs
    		INTEGER,
    	    wfFrMlVCAggNumberVCsActive
    		INTEGER,
    	    wfFrMlVCStatsLineCnt
    		Gauge,
    	    wfFrMlVCStatsBundleSpd
    		Gauge,
    	    wfFrMlVCStatsTxOctets
    		Counter,
    	    wfFrMlVCStatsTxPkts
    		Counter,
    	    wfFrMlVCStatsAvgTxListLen
    		Gauge,
    	    wfFrMlVCStatsRxOctets
    		Counter,
    	    wfFrMlVCStatsRxPkts
    		Counter,
    	    wfFrMlVCStatsReasmFails
    		Counter,
    	    wfFrMlVCStatsSeqNumberLost
    		Counter,
    	    wfFrMlVCStatsSeqNumberArrivedLate
    		Counter,
    	    wfFrMlVCStatsReSeqBufferCnt
    		Gauge,
    	    wfFrMlVCStatsReSeqBufferMax
    		Counter,
    	    wfFrMlVCStatsExceededBufferMax
    		Counter,
    	    wfFrMlVCStatsLinkIdleEvents
    		Counter,
	    wfFrMlVCStatsCalcPercent
		INTEGER,
	    wfFrMlVCStatsDebug
		INTEGER,
            wfFrMlVCStatsReassmBufferCnt
                Gauge,
            wfFrMlVCStatsReassmBufferMax
    		Counter,
            wfFrMlVCStatsNumPktsFragmented
    		Counter
        }

    wfFrMlVCDelete OBJECT-TYPE
        SYNTAX	INTEGER {
    		    created(1),
    		    deleted(2)
    		}
        ACCESS	read-write
        STATUS	mandatory
        DESCRIPTION
                "Create/Delete parameter"
        DEFVAL	{ created }
        ::= { wfFrMlVCEntry 1 }

    wfFrMlVCCircuitNumber OBJECT-TYPE
        SYNTAX	INTEGER(1..1023)
        ACCESS	read-only
        STATUS	mandatory
        DESCRIPTION
                "cct number for this instance"
        ::= { wfFrMlVCEntry 2 }

    wfFrMlVCDlci OBJECT-TYPE
	SYNTAX	INTEGER
	ACCESS	read-only
	STATUS	mandatory
	DESCRIPTION
		" DCLI number. "
        ::= { wfFrMlVCEntry 3 }

    wfFrMlVCAggState OBJECT-TYPE
        SYNTAX	INTEGER {
    		    active(1),
    		    inactive(2)
    		}
        ACCESS	read-write
        STATUS	mandatory
        DESCRIPTION
                "Vc is active or inactive according to rules of
                 wfFrMlAggVCStatusMode."
        DEFVAL	{ active }
        ::= { wfFrMlVCEntry 4 }

    wfFrMlVCAggNumberVCs OBJECT-TYPE
        SYNTAX	INTEGER
        ACCESS	read-write
        STATUS	mandatory
        DESCRIPTION
                "Number of VCs comprising this aggregated VC."
        ::= { wfFrMlVCEntry 5 }

    wfFrMlVCAggNumberVCsActive OBJECT-TYPE
        SYNTAX	INTEGER
        ACCESS	read-write
        STATUS	mandatory
        DESCRIPTION
                "Number of VCs comprising this aggregated VC that are active."
        ::= { wfFrMlVCEntry 6 }

    wfFrMlVCStatsLineCnt OBJECT-TYPE
        SYNTAX	Gauge
        ACCESS	read-only
        STATUS	mandatory
        DESCRIPTION
                "Current count of lines in this aggregated VC that are active"
        ::= { wfFrMlVCEntry 7 }

    wfFrMlVCStatsBundleSpd OBJECT-TYPE
        SYNTAX	Gauge
        ACCESS	read-only
        STATUS	mandatory
        DESCRIPTION
                "Current total bandwidth of lines used by this vc"
        ::= { wfFrMlVCEntry 8 }

    wfFrMlVCStatsTxOctets OBJECT-TYPE
        SYNTAX	Counter
        ACCESS	read-only
        STATUS	mandatory
        DESCRIPTION
                "Number of octets transmitted by Multilink"
        ::= { wfFrMlVCEntry 9 }

    wfFrMlVCStatsTxPkts OBJECT-TYPE
        SYNTAX	Counter
        ACCESS	read-only
        STATUS	mandatory
        DESCRIPTION
                "Number of packets transmitted by Multilink"
        ::= { wfFrMlVCEntry 10 }

    wfFrMlVCStatsAvgTxListLen OBJECT-TYPE
        SYNTAX	Gauge
        ACCESS	read-only
        STATUS	mandatory
        DESCRIPTION
                "Average number of packets received in the transient
                list by the Multilink Transmit gate."
        ::= { wfFrMlVCEntry 11 }

    wfFrMlVCStatsRxOctets OBJECT-TYPE
        SYNTAX	Counter
        ACCESS	read-only
        STATUS	mandatory
        DESCRIPTION
                "Number of octets received without error"
        ::= { wfFrMlVCEntry 12 }

    wfFrMlVCStatsRxPkts OBJECT-TYPE
        SYNTAX	Counter
        ACCESS	read-only
        STATUS	mandatory
        DESCRIPTION
                "Number of packets received by Multilink"
        ::= { wfFrMlVCEntry 13 }

    wfFrMlVCStatsReasmFails OBJECT-TYPE
        SYNTAX	Counter
        ACCESS	read-only
        STATUS	mandatory
        DESCRIPTION
                "Number of packet reassembly failures"
        ::= { wfFrMlVCEntry 14 }

    wfFrMlVCStatsSeqNumberLost OBJECT-TYPE
        SYNTAX	Counter
        ACCESS	read-only
        STATUS	mandatory
        DESCRIPTION
                "Number of Multilink packets considered to be lost on
                the wire"
        ::= { wfFrMlVCEntry 15 }

    wfFrMlVCStatsSeqNumberArrivedLate OBJECT-TYPE
        SYNTAX	Counter
        ACCESS	read-only
        STATUS	mandatory
        DESCRIPTION
                "Number of Multilink packets which arrive
                containing an old Sequence Number. IE: packets
                with a more current Sequence Number have already
                been sent up to NCP"
        ::= { wfFrMlVCEntry 16 }

    wfFrMlVCStatsReSeqBufferCnt OBJECT-TYPE
        SYNTAX	Gauge
        ACCESS	read-only
        STATUS	mandatory
        DESCRIPTION
                "Number of Multilink packets currently stored
                in the ReSequencing buffer pool."
        ::= { wfFrMlVCEntry 17 }

    wfFrMlVCStatsReSeqBufferMax OBJECT-TYPE
        SYNTAX	Counter
        ACCESS	read-only
        STATUS	mandatory
        DESCRIPTION
                "The Maximum Number of Multilink packets stored
                in the ReSequencing buffer pool."
        ::= { wfFrMlVCEntry 18 }

    wfFrMlVCStatsExceededBufferMax OBJECT-TYPE
        SYNTAX	Counter
        ACCESS	read-only
        STATUS	mandatory
        DESCRIPTION
                "The number of times a buffer needed to be stored by the 
                 Multilink Receive logic when the count of buffers stored,
                 wfFrMlVCStatsReSeqBufferMax,was equal to the maximum allowable
                 for this circuit, wfFrMlVCCircuitMaxBuffers."
        ::= { wfFrMlVCEntry 19 }

    wfFrMlVCStatsLinkIdleEvents OBJECT-TYPE
        SYNTAX  Counter
        ACCESS  read-only
        STATUS  mandatory
        DESCRIPTION
                "The number of times the Multilink Receive logic detected a
                 stored buffer received on a line which has been declared idle."
        ::= { wfFrMlVCEntry 20 }

    wfFrMlVCStatsCalcPercent OBJECT-TYPE
        SYNTAX	INTEGER {
    		    enabled(1),
    		    disabled(2)
    		}
        ACCESS	read-write
        STATUS	mandatory
        DESCRIPTION
                "enable/disable collection of Rx percentage line usage"
        DEFVAL	{ disabled }
        ::= { wfFrMlVCEntry 21 }

    wfFrMlVCStatsDebug OBJECT-TYPE
        SYNTAX	INTEGER
        ACCESS	read-write
        STATUS	mandatory
        DESCRIPTION
                "DEBUG parameter - this is used to control debug code
                 for the Multilink subsystem"
        ::= { wfFrMlVCEntry 22 }

    wfFrMlVCStatsReassmBufferCnt OBJECT-TYPE
        SYNTAX  Gauge
        ACCESS  read-only
        STATUS  mandatory
        DESCRIPTION
                "Number of Multilink packets currently stored
                in the Reassembling buffer pools."
        ::= { wfFrMlVCEntry 23 }

    wfFrMlVCStatsReassmBufferMax OBJECT-TYPE
        SYNTAX  Counter
        ACCESS  read-only
        STATUS  mandatory
        DESCRIPTION
                "The Maximum Number of Multilink packets stored
                in the Reassembling buffer pools."
        ::= { wfFrMlVCEntry 24 }

    wfFrMlVCStatsNumPktsFragmented OBJECT-TYPE
        SYNTAX  Counter
        ACCESS  read-only
        STATUS  mandatory
        DESCRIPTION
                "The Number of Multilink packets that were 
	         fragmented."
        ::= { wfFrMlVCEntry 25 }

     --
     --      the range of a Data Link Connection Identifier
     --

     wfFrMapDlcmiTable OBJECT-TYPE
         SYNTAX   SEQUENCE OF WfFrMapDlcmiEntry
         ACCESS   not-accessible
         STATUS   mandatory
         DESCRIPTION
            "The Parameters for the Data Link Connection Management
            Interface for the frame relay service on this
            interface."
         REFERENCE
            "American National Standard T1.617-1991, Annex D"
         ::= { wfFrameRelay2Group 16 }

     wfFrMapDlcmiEntry OBJECT-TYPE
         SYNTAX   WfFrMapDlcmiEntry
         ACCESS   not-accessible
         STATUS   mandatory
         DESCRIPTION
            "The Parameters for a particular Data Link Connection
            Management Interface."
         INDEX { wfFrMapDlcmiIfIndex }
         ::= { wfFrMapDlcmiTable 1 }



     WfFrMapDlcmiEntry ::=
         SEQUENCE {
             wfFrMapDlcmiIfIndex         
                 INTEGER,
             wfFrMapDlcmiState      
                 INTEGER,
             wfFrMapDlcmiAddress   
                 INTEGER,
             wfFrMapDlcmiAddressLen     
                 INTEGER,
             wfFrMapDlcmiPollingInterval  
                 INTEGER,
             wfFrMapDlcmiFullEnquiryInterval 
                 INTEGER,
             wfFrMapDlcmiErrorThreshold    
                 INTEGER,
             wfFrMapDlcmiMonitoredEvents  
                 INTEGER,
             wfFrMapDlcmiMaxSupportedVCs 
                 INTEGER,
             wfFrMapDlcmiMulticast      
                 INTEGER,
             wfFrMapDlcmiStatus
                 INTEGER,
             wfFrMapDlcmiRowStatus     
                 INTEGER,
             wfFrMapDlcmiLineNumber
                 INTEGER,
             wfFrMapDlcmiLLIndex
                 INTEGER
     }


     wfFrMapDlcmiIfIndex OBJECT-TYPE
         SYNTAX   INTEGER (1..2147483647)
         ACCESS   read-only
         STATUS   mandatory
         DESCRIPTION
            "The ifIndex value of the corresponding ifEntry."
         ::= { wfFrMapDlcmiEntry 1 }


     wfFrMapDlcmiState OBJECT-TYPE
         SYNTAX INTEGER      {
             noLmiConfigured (1),
             lmiRev1         (2),
             ansiT1617D      (3),  -- ANSI T1.617 Annex D
             ansiT1617B      (4),  -- ANSI T1.617 Annex B
             itut933A        (5),  -- CCITT Q933 Annex A
             ansiT1617D1994  (6)   -- ANSI T1.617a-1994 Annex D
         }
         ACCESS   read-only
         STATUS   mandatory
         DESCRIPTION
            "This variable states which Data Link Connection
            Management scheme is active (and by implication, what
            DLCI it uses) on the Frame Relay interface."
         REFERENCE
            "American National Standard T1.617-1991, American
            National Standard T1.617a-1994, ITU-T Recommendation
            Q.933 (03/93)."

         ::= { wfFrMapDlcmiEntry 2 }


     wfFrMapDlcmiAddress OBJECT-TYPE
         SYNTAX      INTEGER {
                     q921           (1),  -- 13 bit DLCI
                     q922March90    (2),  -- 11 bit DLCI
                     q922November90 (3),  -- 10 bit DLCI
                     q922           (4)   -- Final Standard
         }
         ACCESS  read-only
         STATUS  mandatory
         DESCRIPTION
            "This variable states which address format is in use on
            the Frame Relay interface."
         ::= { wfFrMapDlcmiEntry 3 }


     wfFrMapDlcmiAddressLen OBJECT-TYPE
         SYNTAX  INTEGER     {
                 twoOctets (2),
                 threeOctets (3),
                 fourOctets (4)
         }
         ACCESS  read-only
         STATUS  mandatory
         DESCRIPTION
            "This variable states the address length in octets.  In
            the case of Q922 format, the length indicates the
            entire length of the address including the control
            portion."
         ::= { wfFrMapDlcmiEntry 4 }


     wfFrMapDlcmiPollingInterval OBJECT-TYPE
         SYNTAX   INTEGER (5..30)
         ACCESS   read-only
         STATUS   mandatory
         DESCRIPTION
            "This is the number of seconds between successive
            status enquiry messages."
         REFERENCE
            "American National Standard T1.617-1991, Section D.7
            Timer T391."
         DEFVAL { 10 }
         ::= { wfFrMapDlcmiEntry 5 }


     wfFrMapDlcmiFullEnquiryInterval OBJECT-TYPE
         SYNTAX   INTEGER (1..255)
         ACCESS   read-only
         STATUS   mandatory
         DESCRIPTION
            "Number of status enquiry intervals that pass before
            issuance of a full status enquiry message."
         REFERENCE
            "American National Standard T1.617-1991, Section D.7
            Counter N391."
         DEFVAL { 6 }
         ::= { wfFrMapDlcmiEntry 6 }


     wfFrMapDlcmiErrorThreshold OBJECT-TYPE
         SYNTAX   INTEGER (1..10)
         ACCESS   read-only
         STATUS   mandatory
         DESCRIPTION
            "This is the maximum number of unanswered Status
            Enquiries the equipment shall accept before declaring
            the interface down."
         REFERENCE
            "American National Standard T1.617-1991, Section D.5.1
            Counter N392."
         DEFVAL { 3 }
         ::= { wfFrMapDlcmiEntry 7 }


     wfFrMapDlcmiMonitoredEvents OBJECT-TYPE
         SYNTAX   INTEGER (1..10)
         ACCESS   read-only
         STATUS   mandatory
         DESCRIPTION
            "This is the number of status polling intervals over
            which the error threshold is counted.  For example, if
            within 'MonitoredEvents' number of events the station
            receives 'ErrorThreshold' number of errors, the
            interface is marked as down."
         REFERENCE
            "American National Standard T1.617-1991, Section D.5.2
            Counter N393."
         DEFVAL { 4 }
         ::= { wfFrMapDlcmiEntry 8 }

     wfFrMapDlcmiMaxSupportedVCs OBJECT-TYPE
         SYNTAX   INTEGER
         ACCESS   read-only
         STATUS   mandatory
         DESCRIPTION
            "The maximum number of Virtual Circuits allowed for
            this interface.  Usually dictated by the Frame Relay
            network.

            In response to a SET, if a value less than zero or
            higher than the agent's maximal capability is
            configured, the agent should respond badValue"
         ::= { wfFrMapDlcmiEntry 9 }

     wfFrMapDlcmiMulticast OBJECT-TYPE
         SYNTAX   INTEGER    {
                     nonBroadcast (1),
                     broadcast (2)
                     }
         ACCESS   read-only
         STATUS   mandatory
         DESCRIPTION
            "This indicates whether the Frame Relay interface is
            using a multicast service."
         ::= { wfFrMapDlcmiEntry 10 }



     wfFrMapDlcmiStatus OBJECT-TYPE
         SYNTAX   INTEGER    {
                     running      (1),    -- init complete, system running
                     fault        (2),    -- error threshold exceeded
                     initializing (3)     -- system start up
                     }
         ACCESS   read-only
         STATUS   mandatory
         DESCRIPTION
            "This indicates the status of the Frame Relay interface
            as determined by the performance of the dlcmi.  If no
            dlcmi is running, the Frame Relay interface will stay
            in the running state indefinitely."
         ::= { wfFrMapDlcmiEntry 11 }

     wfFrMapDlcmiRowStatus OBJECT-TYPE
         SYNTAX   INTEGER
         ACCESS   read-only
         STATUS   mandatory
         DESCRIPTION
            "SNMP Version 2 Row Status Variable.  Writable objects
            in the table may be written in any RowStatus state."
         ::= { wfFrMapDlcmiEntry 12 }

     wfFrMapDlcmiLineNumber OBJECT-TYPE
        SYNTAX  INTEGER
        ACCESS  read-only
        STATUS  mandatory
        DESCRIPTION
                "Instance identifier. This is the line number on which the
                 associated Frame Relay interface resides."
        ::= { wfFrMapDlcmiEntry 13 }

     wfFrMapDlcmiLLIndex OBJECT-TYPE
        SYNTAX  INTEGER
        ACCESS  read-only
        STATUS  mandatory
        DESCRIPTION
                "The Lower layer index uniquely identifies the lower layer in
                cases where the lower layer may be something other than the
                physical layer.  For example if Frame Relay is running over
                an ATM VC, the LLIndex identifies the ATM VC."
        ::= { wfFrMapDlcmiEntry 14 }



    wfFrMapCircuitTable OBJECT-TYPE
        SYNTAX  SEQUENCE OF WfFrMapCircuitEntry
        ACCESS  not-accessible
        STATUS  mandatory
        DESCRIPTION
                "The  Frame Relay VC Table to support RFC2115 , containing 
                 information and statistics for frCircuitEntry"
        ::= {wfFrameRelay2Group 17 }

    wfFrMapCircuitEntry OBJECT-TYPE
        SYNTAX  WfFrMapCircuitEntry
        ACCESS  not-accessible
        STATUS  mandatory
        DESCRIPTION
                "Frame Relay VC information mapped to frCircuitEntry"
        INDEX   { wfFrMapCircuitIfIndex,
                  wfFrMapCircuitDlci }
        ::= { wfFrMapCircuitTable 1 }

    WfFrMapCircuitEntry ::= SEQUENCE {
             wfFrMapCircuitIfIndex      
                  INTEGER,
             wfFrMapCircuitDlci
                  INTEGER,
             wfFrMapCircuitState
                  INTEGER,
             wfFrMapCircuitReceivedFECNs
                  Counter,
             wfFrMapCircuitReceivedBECNs
                  Counter,
             wfFrMapCircuitSentFrames
                  Counter,
             wfFrMapCircuitSentOctets
                  Counter,
             wfFrMapCircuitReceivedFrames
                 Counter,
             wfFrMapCircuitReceivedOctets
                 Counter,
             wfFrMapCircuitCreationTime
                 TimeTicks,
             wfFrMapCircuitLastTimeChange
                 TimeTicks,
             wfFrMapCircuitCommittedBurst
                 INTEGER,
             wfFrMapCircuitExcessBurst
                 INTEGER,
             wfFrMapCircuitThroughput
                 INTEGER,
             wfFrMapCircuitMulticast
                 INTEGER,
             wfFrMapCircuitType
                 INTEGER,
             wfFrMapCircuitDiscards
                 Counter,
             wfFrMapCircuitReceivedDEs
                 Counter,
             wfFrMapCircuitSentDEs
                 Counter,
             wfFrMapCircuitLogicalIfIndex
                 INTEGER,
             wfFrMapCircuitRowStatus
                 INTEGER,
             wfFrMapCircuitLineNumber
                 INTEGER,
             wfFrMapCircuitLLIndex
                 INTEGER
        }


     wfFrMapCircuitIfIndex OBJECT-TYPE
        SYNTAX  INTEGER (1..2147483647)
        ACCESS  read-only
        STATUS  mandatory
        DESCRIPTION
                "The ifIndex Value of the ifEntry this virtual circuit
                 is layered onto."
         ::= { wfFrMapCircuitEntry 1 }

    wfFrMapCircuitDlci OBJECT-TYPE
        SYNTAX  INTEGER
        ACCESS  read-only
        STATUS  mandatory
        DESCRIPTION
                "The Data Link Connection Identifier for this virtual
                 circuit."
        ::= { wfFrMapCircuitEntry 2 }

    wfFrMapCircuitState OBJECT-TYPE
        SYNTAX  INTEGER {
                    invalid (1),
                    active (2),
                    inactive (3)
                }
        ACCESS  read-only
        STATUS  mandatory
        DESCRIPTION
                "Indicates whether the particular virtual circuit is
                operational.  In the absence of a Data Link Connection
                 Management Interface, virtual circuit entries (rows)
                may be created by setting virtual circuit state to
                'active', or deleted by changing Circuit state to
                'invalid'.

                 Whether or not the row actually disappears is left to
                the implementation, so this object may actually read as
                 'invalid' for some arbitrary length of time.  It is
                 also legal to set the state of a virtual circuit to
                 'inactive' to temporarily disable a given circuit.

                 The use of 'invalid' is deprecated in this SNMP Version
                 2 MIB, in favor of frCircuitRowStatus."
        ::= { wfFrMapCircuitEntry 3 }

    wfFrMapCircuitReceivedFECNs OBJECT-TYPE
        SYNTAX  Counter 
        ACCESS  read-only
        STATUS  mandatory
        DESCRIPTION
                "Number of frames received from the network indicating
                forward congestion since the virtual circuit was
                created.  This occurs when the remote DTE sets the FECN
                flag, or when a switch in the network enqueues the
                frame to a trunk whose transmission queue is
                congested."
         ::= { wfFrMapCircuitEntry 4 }

    wfFrMapCircuitReceivedBECNs OBJECT-TYPE
        SYNTAX  Counter
        ACCESS  read-only
        STATUS  mandatory
        DESCRIPTION
                "Number of frames received from the network indicating
                backward congestion since the virtual circuit was
                created.  This occurs when the remote DTE sets the BECN
                flag, or when a switch in the network receives the
                frame from a trunk whose transmission queue is
                 congested"
        ::= { wfFrMapCircuitEntry 5 }

    wfFrMapCircuitSentFrames OBJECT-TYPE
        SYNTAX  Counter
        ACCESS  read-only
        STATUS  mandatory
        DESCRIPTION
                "The number of frames sent from this virtual circuit
                since it was created.  Octets counted are the full
                frame relay header and the payload, but do not include
                the flag characters or CRC."
         ::= { wfFrMapCircuitEntry 6 }

    wfFrMapCircuitSentOctets OBJECT-TYPE
        SYNTAX  Counter
        ACCESS  read-only
        STATUS  mandatory
        DESCRIPTION
                "The number of octets sent from this virtual circuit
                since it was created.  Octets counted are the full
                frame relay header and the payload, but do not include
                the flag characters or CRC."
        ::= { wfFrMapCircuitEntry 7 }

    wfFrMapCircuitReceivedFrames OBJECT-TYPE
        SYNTAX  Counter
        ACCESS  read-only
        STATUS  mandatory
        DESCRIPTION
                "Number of frames received over this virtual circuit
                 since it was created."
        ::= { wfFrMapCircuitEntry 8 }

    wfFrMapCircuitReceivedOctets OBJECT-TYPE
        SYNTAX  Counter
        ACCESS  read-only
        STATUS  mandatory
        DESCRIPTION
                "Number of octets received over this virtual circuit
                since it was created.  Octets counted include the full
                frame relay header, but do not include the flag
                characters or the CRC."
       ::= { wfFrMapCircuitEntry 9 }

    wfFrMapCircuitCreationTime OBJECT-TYPE
        SYNTAX  TimeTicks
        ACCESS  read-only
        STATUS  mandatory
        DESCRIPTION
                "The value of sysUpTime when the virtual circuit was
                created, whether by the Data Link Connection Management
                Interface or by a SetRequest."
        ::= { wfFrMapCircuitEntry 10 }

    wfFrMapCircuitLastTimeChange OBJECT-TYPE
        SYNTAX  TimeTicks
        ACCESS  read-only
        STATUS  mandatory
        DESCRIPTION
                "The value of sysUpTime when last there was a change in
                the virtual circuit state"
        ::= { wfFrMapCircuitEntry 11 }

    wfFrMapCircuitCommittedBurst OBJECT-TYPE
        SYNTAX  INTEGER(0..2147483647)
        ACCESS  read-only
        STATUS  mandatory
        DESCRIPTION
                "This variable indicates the maximum amount of data, in
                bits, that the network agrees to transfer under normal
                conditions, during the measurement interval."
        ::= { wfFrMapCircuitEntry 12 }

    wfFrMapCircuitExcessBurst OBJECT-TYPE
        SYNTAX  INTEGER(0..2147483647)
        ACCESS  read-only
        STATUS  mandatory
        DESCRIPTION
                "This variable indicates the maximum amount of
                uncommitted data bits that the network will attempt to
                deliver over the measurement interval.

                By default, if not configured when creating the entry,
                the Excess Information Burst Size is set to the value
                of ifSpeed."
        ::= { wfFrMapCircuitEntry 13 }

    wfFrMapCircuitThroughput OBJECT-TYPE
        SYNTAX  INTEGER(0..2147483647)
        ACCESS  read-only
        STATUS  mandatory
        DESCRIPTION
                "Throughput is the average number of 'Frame Relay
                Information Field' bits transferred per second across a
                user network interface in one direction, measured over
                the measurement interval.

                If the configured committed burst rate and throughput
                are both non-zero, the measurement interval, T, is
                T=frCircuitCommittedBurst/frCircuitThroughput.

                If the configured committed burst rate and throughput
                are both zero, the measurement interval, T, is
                       T=frCircuitExcessBurst/ifSpeed."
        ::= { wfFrMapCircuitEntry 14 }

    wfFrMapCircuitMulticast OBJECT-TYPE
        SYNTAX  INTEGER    {
                     unicast   (1),
                     oneWay    (2),
                     twoWay    (3),
                     nWay      (4)
                     }
        ACCESS  read-only
        STATUS  mandatory
        DESCRIPTION
                "This indicates whether this VC is used as a unicast VC
                (i.e. not multicast) or the type of multicast service
                subscribed to"
        ::= { wfFrMapCircuitEntry 15 }

    wfFrMapCircuitType OBJECT-TYPE
        SYNTAX  INTEGER    {
                     static  (1),
                     dynamic (2)
                  }
        ACCESS  read-only
        STATUS  mandatory
        DESCRIPTION
                "Indication of whether the VC was manually created
            (static), or dynamically created (dynamic) via the data
            link control management interface."
        ::= { wfFrMapCircuitEntry 16 }

    wfFrMapCircuitDiscards OBJECT-TYPE
        SYNTAX  Counter
        ACCESS  read-only
        STATUS  mandatory
        DESCRIPTION
                "The number of inbound frames dropped because of format
                errors, or because the VC is inactive."
        ::= { wfFrMapCircuitEntry 17 }

    wfFrMapCircuitReceivedDEs OBJECT-TYPE
        SYNTAX  Counter
        ACCESS  read-only
        STATUS  mandatory
        DESCRIPTION
                "Number of frames received from the network indicating
                that they were eligible for discard since the virtual
                circuit was created.  This occurs when the remote DTE
                sets the DE flag, or when in remote DTE's switch
                detects that the frame was received as Excess Burst
                data."
        ::= { wfFrMapCircuitEntry 18 }

    wfFrMapCircuitSentDEs OBJECT-TYPE
        SYNTAX  Counter
        ACCESS  read-only
        STATUS  mandatory
        DESCRIPTION
                "TNumber of frames sent to the network indicating that
                they were eligible for discard since the virtual
                circuit was created.   This occurs when the local DTE
                sets the DE flag, indicating that during Network
                congestion situations those frames should be discarded
                in preference of other frames sent without the DE bit
                set."
        ::= { wfFrMapCircuitEntry 19 }

     wfFrMapCircuitLogicalIfIndex OBJECT-TYPE
        SYNTAX  INTEGER (1..2147483647)
        ACCESS  read-only
        STATUS  mandatory
        DESCRIPTION
                "The number of times a buffer needed to be stored by the 
                 Multilink Receive logic when the count of buffers stored,
                 wfFrMlVCStatsReSeqBufferMax,was equal to the maximum allowable
                 for this circuit, wfFrMlVCCircuitMaxBuffers."
        ::= { wfFrMapCircuitEntry 20 }

     wfFrMapCircuitRowStatus OBJECT-TYPE
        SYNTAX  INTEGER 
        ACCESS  read-only
        STATUS  mandatory
        DESCRIPTION
                "This object is used to create a new row or modify or
                destroy an existing row in the manner described in the
                definition of the RowStatus textual convention.
                Writable objects in the table may be written in any
                RowStatus state."
        ::= {  wfFrMapCircuitEntry 21 }

     wfFrMapCircuitLineNumber OBJECT-TYPE
        SYNTAX  INTEGER
        ACCESS  read-only
        STATUS  mandatory
        DESCRIPTION
                "Instance identifier. This is the line number on which the
                 associated Frame Relay interface resides."
        ::= { wfFrMapCircuitEntry 22 }

     wfFrMapCircuitLLIndex OBJECT-TYPE
        SYNTAX  INTEGER
        ACCESS  read-only
        STATUS  mandatory
        DESCRIPTION
                "The Lower layer index uniquely identifies the lower layer in
                cases where the lower layer may be something other than the
                physical layer.  For example if Frame Relay is running over
                an ATM VC, the LLIndex identifies the ATM VC."
        ::= { wfFrMapCircuitEntry 23 }
     --
     --  Error Table

     -- The table describing errors encountered on each Frame
     -- Relay Interface.

     wfFrMapErrTable OBJECT-TYPE
         SYNTAX   SEQUENCE OF WfFrMapErrEntry
         ACCESS   not-accessible
         STATUS   mandatory
         DESCRIPTION
            "A table containing information about Errors on the
            Frame Relay interface.  Discontinuities in the counters
            contained in this table are the same as apply to the
            ifEntry associated with the Interface."
         ::= { wfFrameRelay2Group 18 }

     wfFrMapErrEntry OBJECT-TYPE
         SYNTAX   WfFrMapErrEntry
         ACCESS   not-accessible
         STATUS   mandatory
         DESCRIPTION
            "The error information for a single frame relay
            interface."
         INDEX { wfFrMapErrIfIndex }
         ::= { wfFrMapErrTable 1 }


     WfFrMapErrEntry ::=
         SEQUENCE {
             wfFrMapErrIfIndex            INTEGER,
             wfFrMapErrType               INTEGER,
             wfFrMapErrData               OCTET STRING,
             wfFrMapErrTime               TimeTicks,
             wfFrMapErrFaults             Counter,
             wfFrMapErrFaultTime          TimeTicks,
             wfFrMapErrLineNumber         INTEGER,
             wfFrMapErrLLIndex            INTEGER
     }


     wfFrMapErrIfIndex OBJECT-TYPE
         SYNTAX   INTEGER (1..2147483647)
         ACCESS   read-only
         STATUS   mandatory
         DESCRIPTION
            "The ifIndex Value of the corresponding ifEntry."
         ::= { wfFrMapErrEntry 1 }


         wfFrMapErrType OBJECT-TYPE
             SYNTAX   INTEGER    {
                         unknownError(1),
                         receiveShort(2),
                         receiveLong(3),
                         illegalAddress(4),
                         unknownAddress(5),
                         dlcmiProtoErr(6),
                         dlcmiUnknownIE(7),
                         dlcmiSequenceErr(8),
                         dlcmiUnknownRpt(9),
                         noErrorSinceReset(10)
                      }
         ACCESS   read-only
         STATUS   mandatory
         DESCRIPTION
            "The type of error that was last seen  on  this interface:
             receiveShort: frame was not long enough to allow
             demultiplexing - the address field was incomplete,
             or for virtual circuits using Multiprotocol over
             Frame Relay, the protocol identifier was missing
             or incomplete.

     receiveLong: frame exceeded maximum length configured for this
                  interface.

     illegalAddress: address field did not match configured format.

     unknownAddress: frame received on a virtual circuit which was not
                     active or administratively disabled.

     dlcmiProtoErr: unspecified error occurred when attempting to
                    interpret link maintenance frame.

     dlcmiUnknownIE: link maintenance frame contained an Information
                     Element type which is not valid for the
                     configured link maintenance protocol.

     dlcmiSequenceErr: link maintenance frame contained a sequence
                       number other than the expected value.

     dlcmiUnknownRpt: link maintenance frame contained a Report Type
                      Information Element whose value was not valid
                      for the configured link maintenance protocol.

     noErrorSinceReset: no errors have been detected since the last
                        cold start or warm start."
         ::= { wfFrMapErrEntry 2 }

     wfFrMapErrData OBJECT-TYPE
         SYNTAX   OCTET STRING (SIZE(1..1600))
         ACCESS   read-only
         STATUS   mandatory
         DESCRIPTION
            "An octet string containing as much of the error packet
            as possible.  As a minimum, it must contain the Q.922
            Address or as much as was delivered.  It is desirable
            to include all header and demultiplexing information."
         ::= { wfFrMapErrEntry 3 }

     wfFrMapErrTime OBJECT-TYPE
         SYNTAX   TimeTicks
         ACCESS   read-only
         STATUS   mandatory
         DESCRIPTION
            "The value of sysUpTime at which the error was
            detected."
         ::= { wfFrMapErrEntry 4 }

     wfFrMapErrFaults OBJECT-TYPE
         SYNTAX   Counter
         ACCESS   read-only
         STATUS   mandatory
         DESCRIPTION
            "The number of times the interface has gone down since
            it was initialized."
         ::= { wfFrMapErrEntry 5 }

     wfFrMapErrFaultTime OBJECT-TYPE
         SYNTAX   TimeTicks
         ACCESS   read-only
         STATUS   mandatory
         DESCRIPTION
            "The value of sysUpTime at the time when the interface
            was taken down due to excessive errors.  Excessive
            errors is defined as the time when a DLCMI exceeds the
            frDlcmiErrorThreshold number of errors within
            frDlcmiMonitoredEvents. See FrDlcmiEntry for further
            details."
         ::= { wfFrMapErrEntry 6 }

    wfFrMapErrLineNumber OBJECT-TYPE
        SYNTAX  INTEGER
        ACCESS  read-only
        STATUS  mandatory
        DESCRIPTION
                "Instance identifier. This is the line number on which the 
                 associated Frame Relay interface resides."
        ::= { wfFrMapErrEntry 7 }

    wfFrMapErrLLIndex OBJECT-TYPE
        SYNTAX  INTEGER
        ACCESS  read-only
        STATUS  mandatory
        DESCRIPTION
                "The Lower layer index uniquely identifies the lower layer in
                cases where the lower layer may be something other than the
                physical layer.  For example if Frame Relay is running over
                an ATM VC, the LLIndex identifies the ATM VC."
        ::= { wfFrMapErrEntry 8 }


    END  -- Wellfleet-FR2-MIB
