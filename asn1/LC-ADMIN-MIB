--  ==================================================================
--  LANCAST PROPRIETARY ADMIN MIB
--  ==================================================================

--  =================================================================
    LC-ADMIN-MIB
   
--  NOTES: 
--
--   1) The mib compiler renames a MIB Module name by adding
--       an extension of -A.  This results in the following error:
--         The module identity for "LC-ADMIN-MIB-A" conflicts with 
--         the one for "LC-ADMIN-MIB" which prevents the generation of
--         an output file.  
--
--       This is resolved by commenting out the following in the control file:
--       a) the IMPORT statement of MODULE-IDENTITY
--       b) the full MODULE-IDENTITY clause AND replacing it with:
--
--       admin OBJECT IDENTIFIER ::= { lancastMibModulesA 1 }  
--    
--       You will get the following warning but it can be ignored.
--         "Warning:  A MIB module must start with exactly one invocation of
--         the MODULE-IDENTITY macro immediately following an optional IMPORTS
--         clause."
--       
--


   DEFINITIONS ::= BEGIN

   IMPORTS

   MODULE-IDENTITY, OBJECT-TYPE, Integer32, IpAddress
        FROM SNMPv2-SMI
   DisplayString
        FROM SNMPv2-TC
   lancastMibModulesA
        FROM LANCAST-MIB;

 
-- ============================================================
-- MODULE IDENTITY & REVISION HISTORY
-- ============================================================
	  admin MODULE-IDENTITY
			LAST-UPDATED		"9903031200Z"
			ORGANIZATION		"Lancast Inc"
			CONTACT-INFO		"Contact:
											 Customer Service
											 Tel:	1-877-526-2278 ext 136
											 Fax:	1-603-594-2887
											 Web:	info@lancast.com"
			DESCRIPTION
							"This is the enterprise MIB definition file for the
             Admin Group of Lancast Managed products.
							
							Copyright 1999 Lancast Inc.	"
							
		  REVISION "9903031200Z"
		  				
		  DESCRIPTION	  				
		  				"REV 1.0  original Draft"
		  				
		  ::= { lancastMibModulesA 1 }		

--  ======================================================================
--  ADMIN BRANCH OID:  1.3.6.1.4.1.2745.1.1
--  =======================================================================
    adminS              OBJECT IDENTIFIER ::= { admin 1 }  
    adminT              OBJECT IDENTIFIER ::= { admin 2 }

--  ======================================================================
--  adminS: scalar group items  
--  =======================================================================
  curNumSysFiles OBJECT-TYPE
    SYNTAX  Integer32
    MAX-ACCESS  read-only
    STATUS  current
    DESCRIPTION
      "This object identifies the current number of read/write files
      contained in the sysFileTable."
    ::= { adminS 1 }
    
  primaryBootImage OBJECT-TYPE
    SYNTAX  DisplayString  (SIZE (1..64))
    MAX-ACCESS  read-write
    STATUS  current
    DESCRIPTION
      "The boot image to be loaded on start up."
    ::= { adminS 2 }
    
  primaryBootImageVersion OBJECT-TYPE
    SYNTAX  DisplayString  (SIZE (1..64))
    MAX-ACCESS  read-only
    STATUS  current
    DESCRIPTION
      "The version of the boot image to be loaded on start up."
    ::= { adminS 3 }
    
  primaryCoreImage OBJECT-TYPE
    SYNTAX  DisplayString  (SIZE (1..64))
    MAX-ACCESS  read-write
    STATUS  current
    DESCRIPTION
      "The core image to be loaded on start up."
    ::= { adminS 4 }
    
  primaryCoreImageVersion OBJECT-TYPE
    SYNTAX  DisplayString  (SIZE (1..64))
    MAX-ACCESS  read-only
    STATUS  current
    DESCRIPTION
      "The version of the core image to be loaded on start up."
    ::= { adminS 5 }
    
  primaryAppImage OBJECT-TYPE
    SYNTAX  DisplayString  (SIZE (1..64))
    MAX-ACCESS  read-write
    STATUS  current
    DESCRIPTION
      "The application(personality) image to be loaded on start up."
    ::= { adminS 6 }     
    
  primaryAppImageVersion OBJECT-TYPE
    SYNTAX  DisplayString  (SIZE (1..64))
    MAX-ACCESS  read-only
    STATUS  current
    DESCRIPTION
      "The version of the application(personality) image to be loaded
      on start up."
    ::= { adminS 7 }             
    
  curDateTime OBJECT-TYPE
    SYNTAX  DisplayString  (SIZE (1..32))
    MAX-ACCESS  read-write
    STATUS  current
    DESCRIPTION
      "A textual string of the current date and time of this system
      expressed as 
     .  Example: 12/01/1998 08:30:15."
        ::= { adminS 8 }

      fileTransferCapability OBJECT-TYPE
        SYNTAX  INTEGER { 
          none          (1),
          upLoadOnly    (2),
          downLoadOnly  (3),
          both          (4)
        }         
        MAX-ACCESS  read-write
        STATUS  current
        DESCRIPTION
          "This object specifies the overall ability of the device to perform
          transfering of files.  In some instances an organization may want to
          disable all downloads and or uploads to/from this system."
        ::= { adminS 9 }
        
      entityMibSupport  OBJECT-TYPE
        SYNTAX  INTEGER {
            localsubsetSNMPV1 (1),
            standardMibSNMPV2 (2)
        }
        MAX-ACCESS  read-only
        STATUS  current
        DESCRIPTION
          "This object indicates whether this product supports the 
          entity MIB under the Lancast Proprietary node or 
          the standard mgmnt.mib-2.47 node."
        ::= { adminS 10 }
        
      manufacturer  OBJECT-TYPE
        SYNTAX  DisplayString    (SIZE (1..128))
        MAX-ACCESS  read-only
        STATUS  current
        DESCRIPTION
          "The manufacturer of this product."
        ::= { adminS 11 }    

      communityStringRO OBJECT-TYPE
        SYNTAX  DisplayString    (SIZE (1..255))
        MAX-ACCESS  read-write
        STATUS  current
        DESCRIPTION
          "The community string required to authenticate a read access to all MIB
          objects except for the communityStringRW object."
        ::= { adminS 12 }    

      communityStringRW OBJECT-TYPE
        SYNTAX  DisplayString    (SIZE (1..255))
        MAX-ACCESS  read-write
        STATUS  current
        DESCRIPTION
          "The community string required to authenticate a read or write access
          to all MIB objects."
        ::= { adminS 13 }            

      snmpVersion OBJECT-TYPE
        SYNTAX  INTEGER {
            other           (1),
            v1              (2),
            v2              (3),
            v3              (4),
            biLingualV1V2   (5),
            bilingualV1V2c  (6)
        }
        MAX-ACCESS  read-only
        STATUS  current
        DESCRIPTION
          "The version of SNMP supported by this product."
        ::= { adminS 14 }      
        
      defaultGatewayAddress OBJECT-TYPE
        SYNTAX  IpAddress
        MAX-ACCESS  read-write
        STATUS  current
        DESCRIPTION
          "The default gateway address."
        ::= { adminS 15 }
        
      lastSystemResetReason OBJECT-TYPE
        SYNTAX  INTEGER {
          cold-start        (1),
          nms-sw-reset      (2),
          download-reset    (3),
          watch-dog-timeout (4)
        }
        MAX-ACCESS  read-only
        STATUS  current
        DESCRIPTION
          "This object specifies the reason the system was last reset."
        ::= { adminS 16 }
         
      lastSystemResetTime OBJECT-TYPE
        SYNTAX  DisplayString (SIZE (1..64))
        MAX-ACCESS  read-only
        STATUS  current
        DESCRIPTION
          "This object specifies the date and time the system was last reset ."
        ::= { adminS 17 }

        
    --  ======================================================================
    --  !!!!!!!!!!!!!!! adminT: Tables  !!!!!!!!!!!!!!!!!!!!!!!!!!!!!!!!!!!!!!
    --
    --    accessContolTable             adminT 1
    --    sysFileTable                  adminT 2
    --    xferFileTable                 adminT 3
    --    trapManagerTable              adminT 4
    --    trapControlTable              adminT 5
    --    interfaceAddressTable         adminT 6
    --
    -- =======================================================================    

      accessControlTable OBJECT-TYPE
        SYNTAX  SEQUENCE OF AccessControlTableEntry
        MAX-ACCESS  not-accessible
        STATUS  current
        DESCRIPTION
          "A table of information pertaining to management station addresses 
          that have authority to access this system."
        ::= { adminT 1  }

      accessControlTableEntry OBJECT-TYPE
        SYNTAX  AccessControlTableEntry
        MAX-ACCESS  not-accessible
        STATUS  current
        DESCRIPTION
          "An entry representing an authorized address."
        INDEX { accessControlIndex }
        ::= {accessControlTable 1 }

      AccessControlTableEntry ::= SEQUENCE {
        accessControlIndex          Integer32,
        accessControlAddress        IpAddress
        }

      accessControlIndex OBJECT-TYPE
        SYNTAX  Integer32
        MAX-ACCESS  read-only
        STATUS  current
        DESCRIPTION 
          "The index into the table of authorized managers of this system."
        ::= { accessControlTableEntry 1 }

      accessControlAddress OBJECT-TYPE
        SYNTAX  IpAddress
        MAX-ACCESS  read-write
        STATUS  current
        DESCRIPTION 
          "The address of a managment station which has authority to access
          this system."
        ::= { accessControlTableEntry 2 }

    --  ======================================================================
      sysFileTable OBJECT-TYPE
        SYNTAX  SEQUENCE OF SysFileTableEntry
        MAX-ACCESS  not-accessible
        STATUS  current
        DESCRIPTION
          "The table of information pertaining to files loaded on this system."
        ::= { adminT 2  }

      sysFileTableEntry OBJECT-TYPE
        SYNTAX  SysFileTableEntry
        MAX-ACCESS  not-accessible
        STATUS  current
        DESCRIPTION
          "An entry representing a file in this table."
        INDEX { sysFileTableIndex }
        ::= {sysFileTable 1 }

      SysFileTableEntry ::= SEQUENCE {
        sysFileTableIndex           Integer32,
        sysFileName                 DisplayString,
        sysFileSize                 Integer32,
        sysFileAttribute            INTEGER,
        sysFileDateTime             DisplayString
        }

      sysFileTableIndex OBJECT-TYPE
        SYNTAX  Integer32
        MAX-ACCESS  read-only
        STATUS  current
        DESCRIPTION 
          "The index into the table of files loaded on this system."
        ::= { sysFileTableEntry 1 }

      sysFileName OBJECT-TYPE
        SYNTAX  DisplayString (SIZE (1..128))
        MAX-ACCESS  read-write
        STATUS  current
        DESCRIPTION
          "The ascii name of a file."
        ::= { sysFileTableEntry 2 }
        
      sysFileSize OBJECT-TYPE
        SYNTAX  Integer32
        MAX-ACCESS  read-only
        STATUS  current
        DESCRIPTION
          "The file size measured in bytes."
        ::= {sysFileTableEntry 3 }

      sysFileAttribute OBJECT-TYPE
        SYNTAX  INTEGER {
          read           (1),
          write          (2),
          executable     (3)
          }
        MAX-ACCESS  read-only
        STATUS  current
        DESCRIPTION
          "This object indicates the attributes of each file loaded on this
          system."
        ::= { sysFileTableEntry 4 }
      
      sysFileDateTime OBJECT-TYPE
        SYNTAX  DisplayString  (SIZE (1..64))
        MAX-ACCESS  read-only
        STATUS  current
        DESCRIPTION
          "A textual string of the date and time this file was created on this
          system."
        ::= { sysFileTableEntry 5 }
        
    --  ======================================================================
      xferFileTable OBJECT-TYPE
        SYNTAX  SEQUENCE OF XferFileTableEntry
        MAX-ACCESS  not-accessible
        STATUS  current
        DESCRIPTION
          "The table of information pertaining to files that are transfered
          to/from this system."
        ::= { adminT 3  }

      xferFileTableEntry OBJECT-TYPE
        SYNTAX  XferFileTableEntry
        MAX-ACCESS  not-accessible
        STATUS  current
        DESCRIPTION
          "An entry representing a file in this table."
        INDEX { xferFileTableIndex }
        ::= {xferFileTable 1 }

      XferFileTableEntry ::= SEQUENCE 
        {
        xferFileTableIndex          Integer32,
        xferFileName                DisplayString,
        xferFileAddress             IpAddress,
        xferFileDirection           INTEGER,
        xferFileActivation          INTEGER,
        xferFileStatus              INTEGER,
        xferFileFailureCode         Integer32,
        xferFileProtocol            INTEGER
        }

      xferFileTableIndex OBJECT-TYPE
        SYNTAX  Integer32
        MAX-ACCESS  read-only   
        STATUS  current
        DESCRIPTION
          "The index into the table of file transfer information."
        ::= {xferFileTableEntry 1 }
        
      xferFileName  OBJECT-TYPE
        SYNTAX  DisplayString  (SIZE (1..128))
        MAX-ACCESS  read-write
        STATUS  current
        DESCRIPTION
          "The name of a file that is transferable on this system."
        ::= {xferFileTableEntry 2 }
        
      xferFileAddress OBJECT-TYPE
        SYNTAX  IpAddress
        MAX-ACCESS  read-write
        STATUS  current
        DESCRIPTION
          "The source IP address for a download or the desination IP address
          for an upload."
        ::= {xferFileTableEntry 3 }
        
      xferFileDirection OBJECT-TYPE
        SYNTAX  INTEGER   {
          upload   (1),
          download (2)
        }
        MAX-ACCESS  read-write
        STATUS  current
        DESCRIPTION
          "The direction to transfer a file.  
          Upload a file from this device  to the destination address 
            specified by xferFileAddress. 
          Download a file from the source address specified by xferFileAdress
            to this device."
        ::= {xferFileTableEntry  4 }     
        
      xferFileActivation  OBJECT-TYPE
        SYNTAX  INTEGER{
            transfer  (1),
            ready     (2)
        }
        MAX-ACCESS  read-write
        STATUS  current
        DESCRIPTION
          "Writing this object with the value of transfer(1) will invoke a file
          transfer to this system on a download or from this system on an upload.
          The value read back will always be ready(2).  Writing the value ready(2)
          will be ignored."
        ::= {xferFileTableEntry 5 } 
        
      xferFileStatus  OBJECT-TYPE
        SYNTAX  INTEGER {
            other             (1),
            waitingToXfer     (2),
            inProgress        (3),
            success           (4),
            failure           (5)
        }
        MAX-ACCESS  read-only   
        STATUS  current
        DESCRIPTION
          "This object reflect the status of the current or last file transfer."      
        ::= {xferFileTableEntry 6 }
        
      xferFileFailureCode  OBJECT-TYPE
        SYNTAX       Integer32
        MAX-ACCESS   read-only   
        STATUS  current
        DESCRIPTION
          "This object is the failure return code from a file transfer protocol
          such as TFTP and FTP.  Refer to the respective protocol for further
          information."
        ::= {xferFileTableEntry 7 }
                       
      xferFileProtocol  OBJECT-TYPE
        SYNTAX  INTEGER {
            other             (1),
            ftp               (2),
            tftp              (3)
        }
        MAX-ACCESS  read-write
        STATUS  current
        DESCRIPTION
          "This object selects the protocol to be used in a file transfer."
        ::= {xferFileTableEntry 8 }
       
    --  ======================================================================    
      trapManagerTable  OBJECT-TYPE
        SYNTAX  SEQUENCE OF TrapManagerTableEntry
        MAX-ACCESS  not-accessible
        STATUS  current
        DESCRIPTION
          "A table of Network Mangagement Applications to which traps
          will be sent."
        ::= { adminT 4 }
      
      trapManagerTableEntry OBJECT-TYPE
        SYNTAX  TrapManagerTableEntry
        MAX-ACCESS  not-accessible
        STATUS  current
        DESCRIPTION
          "An entry in the table of trap managers."
        INDEX   { trapManagerIndex }
        ::= {trapManagerTable 1}
        
      TrapManagerTableEntry ::= SEQUENCE {
          trapManagerIndex           Integer32,
          trapManagerIpAddress       IpAddress,
          trapManagerUdpPort         Integer32,
          trapManagerName            DisplayString,
          trapManagerControlStatus   INTEGER,
          trapManagerSnmpVersion     INTEGER
         }
          
      trapManagerIndex OBJECT-TYPE
        SYNTAX  Integer32
        MAX-ACCESS  read-only
        STATUS  current
        DESCRIPTION 
          "The index into the table of trap managers for this system."
        ::= { trapManagerTableEntry 1 }     
          
      trapManagerIpAddress  OBJECT-TYPE
        SYNTAX  IpAddress
        MAX-ACCESS  read-write
        STATUS  current
        DESCRIPTION 
          "This object identifies the IP address of a manager to which traps will
          be sent.  A valid address is any non zero value excluding the broadcast
          address 255.255.255.255.  Setting this to 0.0.0.0 disables this entry."
        ::= { trapManagerTableEntry 2 }

      trapManagerUdpPort OBJECT-TYPE
        SYNTAX       Integer32
        MAX-ACCESS   read-write
        STATUS  current
        DESCRIPTION 
          "This object specifies the UDP port at which a management application
          may receive traps.  The default value will be the standard UDP Trap 
          port of 162."
        DEFVAL  { 162 }
        ::= { trapManagerTableEntry 3 }

      trapManagerName OBJECT-TYPE
        SYNTAX  DisplayString    (SIZE (1..64))
        MAX-ACCESS  read-write
        STATUS  current
        DESCRIPTION 
          "A user defined name to identify this trap manager."
        ::= { trapManagerTableEntry 4 }

      trapManagerControlStatus OBJECT-TYPE
        SYNTAX  INTEGER {
           enabled   (1),
           disabled  (2)
        }        
        MAX-ACCESS  read-write
        STATUS  current
        DESCRIPTION 
          "This object is used to an enable or disable the sending of traps
          to a specific address.  Setting this to disable will prevent all
          traps from being sent to this entry's address."
        ::= { trapManagerTableEntry 5 }
           
      trapManagerSnmpVersion OBJECT-TYPE
        SYNTAX   INTEGER {
            other           (1),
            v1              (2),
            v2              (3),
            v3              (4),
            biLingualV1V2   (5),
            bilingualV1V2c  (6)
        }
        MAX-ACCESS   read-write
        STATUS       current
        DESCRIPTION 
          "This object specifies the SNMP version that this manager supports."
        ::= { trapManagerTableEntry 6 }

    --  ======================================================================    
      trapControlTable  OBJECT-TYPE
        SYNTAX  SEQUENCE OF TrapControlTableEntry
        MAX-ACCESS  not-accessible
        STATUS  current
        DESCRIPTION
           "A list identifying the enable/disable status of all traps that this
           system is capable of sending."
        ::= { adminT 5 }
      
      trapControlTableEntry OBJECT-TYPE
        SYNTAX  TrapControlTableEntry
        MAX-ACCESS  not-accessible
        STATUS  current
        DESCRIPTION
          "An entry in this table identifying the enable/disable status of a 
          particular trap."
        INDEX   { trapControlTableIndex }
        ::= {trapControlTable 1}
        
      TrapControlTableEntry ::= SEQUENCE {
          trapControlTableIndex    Integer32,
          trapControlName          DisplayString,
          trapControlV1TrapNumber  Integer32,
          trapControlStatus        INTEGER,
          trapControlV2TrapOid     OBJECT IDENTIFIER
          }
          
      trapControlTableIndex  OBJECT-TYPE
        SYNTAX  Integer32
        MAX-ACCESS  read-only
        STATUS  current
        DESCRIPTION 
          "The index into the table of trap control information."     
        ::= { trapControlTableEntry 1}

      trapControlName OBJECT-TYPE
        SYNTAX  DisplayString  (SIZE (1..64))
        MAX-ACCESS  read-only
        STATUS  current
        DESCRIPTION 
          "The name of the trap to which this entrys' trapControlStatus applies."
        ::= { trapControlTableEntry 2}
        
       trapControlV1TrapNumber OBJECT-TYPE
        SYNTAX       Integer32
        MAX-ACCESS   read-only
        STATUS  current
        DESCRIPTION 
          "The SNMP V1 number of the trap to which this entrys' trapControlStatus 
          applies."
        ::= { trapControlTableEntry 3}    

      trapControlStatus OBJECT-TYPE
        SYNTAX  INTEGER{
          enable    (1),
          disable   (2)
        }
        MAX-ACCESS  read-write
        STATUS  current
        DESCRIPTION 
          "The enable/disable status of this trap control.  When this object is
          set to enable, the corresponding trap will be generated to all trap
          managers listed and enabled in the trapManagerTable."
        ::= { trapControlTableEntry 4}    

      trapControlV2TrapOid OBJECT-TYPE
        SYNTAX         OBJECT IDENTIFIER
        MAX-ACCESS     read-only
        STATUS         current
        DESCRIPTION 
          "The object identifier used to identify a specific SNMP V2 trap.
          For example, the V2 Oid for COLD START is 1.3.6.1.6.3.1.1.5.1"
        ::= { trapControlTableEntry 5}   

     -- ===================================================================================
      interfaceAddressTable OBJECT-TYPE
        SYNTAX  SEQUENCE OF InterfaceAddressTableEntry
        MAX-ACCESS  not-accessible
        STATUS  current
        DESCRIPTION
          "A table of addresses associated with all mib-II interfaces in this
          system."
        ::= { adminT 6 }
      
      interfaceAddressTableEntry  OBJECT-TYPE
        SYNTAX  InterfaceAddressTableEntry
        MAX-ACCESS  not-accessible
        STATUS  current
        DESCRIPTION
          "An entry in the interface address table associated with a mib-II 
          interface."
        INDEX   { interfaceIfNum }
        ::= { interfaceAddressTable 1}
        
      InterfaceAddressTableEntry  ::= SEQUENCE {
          interfaceIfNum          Integer32,
          interfaceIpAddress      IpAddress,
          interfaceSubnetMask     IpAddress   
          }
        
      interfaceIfNum  OBJECT-TYPE
        SYNTAX       Integer32
        MAX-ACCESS   read-only
        STATUS  current
        DESCRIPTION 
          "The interface on which a module sends & receives protocol traffic.
          This value is the same value as ifIndex in MIB-II."
        ::= { interfaceAddressTableEntry 1 }        
        
      interfaceIpAddress  OBJECT-TYPE
        SYNTAX       IpAddress
        MAX-ACCESS   read-write
        STATUS  current
        DESCRIPTION 
          "This object identifies the address of the mib-II interface
          identified by interfaceIfNum."
        ::= { interfaceAddressTableEntry 2 }
        
      interfaceSubnetMask OBJECT-TYPE
        SYNTAX       IpAddress
        MAX-ACCESS   read-write
        STATUS  current
        DESCRIPTION 
          "The subnet mask associated with the adress of this entry.
          The value of the mask is an address with all the network bits
          set to 1 and all the host bits set to 0."
        ::= { interfaceAddressTableEntry 3 }



    END
