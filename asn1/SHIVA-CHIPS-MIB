--
-- 	Copyright 1992, 1993, 1995, 1996 Shiva Corporation
--

SHIVA-CHIPS-MIB DEFINITIONS ::= BEGIN

IMPORTS
    	tChipSets
    		FROM SHIVA-MIB;

-- tChipSets oids

--	Objects in this group are used for values of ifExtnsChipSets
--	for LocalTalk interfaces. They are here as "temporary" because
--	they really belong in an "llap" transmission MIB, but that
--	can't be created unless the MIB-II interfaces group is revised
--	to create a localtalk ifType value!

    -- chipZilog SCC (FP4 LocalTalk)
    chipZilogZ8530 OBJECT IDENTIFIER ::= { tChipSets 1 }

    -- chipZilog SAC (FP5 IOP)
    chipZilogZ181 OBJECT IDENTIFIER ::= { tChipSets 2 }

END
