-- This MIB was created by extracting information from 
-- Sun Mangement Center 3.5 for use in other applications
-- to help determine what is actually listed in the SMC snmp 
-- agent. Sun has/will not release their MIBS for this 
-- information, so I created them from all information that
-- they have released.
--
-- Most all the information should be correct, but
-- if you find a discrepency please let me know. I do not
-- have all available Sun hardware to test with, so not 
-- not all types of support hardware has been tested.
-- These MIBs have only been tested using the utilities
-- from net-snmp. They may or may not work with other
-- applications.
-- 
-- The MIBs are not detailed, they only are useful in 
-- mapping OIDs to names. At some point in time 
-- descriptions may be given.
--
-- Author: Brian T. O'Neill (btoneill@misplaced.net)
-- Date: 7-30-2003 
-- Version: 0.9
--
-- No guarantees are given regarding the accuracy of this
-- data.
--
-- Note: The naming was done in line with the published
-- MIBS from Sun Microsystems.
--
--
READER4UVH-SUNMANAGEMENTCENTER-MIB DEFINITIONS ::= BEGIN

  IMPORTS
        enterprises, NOTIFICATION-TYPE, OBJECT-TYPE, MODULE-IDENTITY
                FROM SNMPv2-SMI;

sun             OBJECT IDENTIFIER ::= { enterprises 42 }
prod            OBJECT IDENTIFIER ::= { sun 2 }
sunsymon        OBJECT IDENTIFIER ::= { prod 12 }
agent           OBJECT IDENTIFIER ::= { sunsymon 2 }
base            OBJECT IDENTIFIER ::= { agent 1 }
modules         OBJECT IDENTIFIER ::= { agent 2 }
hardware        OBJECT IDENTIFIER ::= { modules 1 }
--
--
config          OBJECT IDENTIFIER ::= { hardware 1 }
reader4u        OBJECT IDENTIFIER ::= { config 1 }
reader4udt      OBJECT IDENTIFIER ::= { config 2 }
reader4uwg      OBJECT IDENTIFIER ::= { config 3 }
reader4u1P      OBJECT IDENTIFIER ::= { config 4 }
reader4u1D      OBJECT IDENTIFIER ::= { config 5 }
reader4unt      OBJECT IDENTIFIER ::= { config 6 }
readerSerengeti OBJECT IDENTIFIER ::= { config 7 }
reader4uvh      OBJECT IDENTIFIER ::= { config 8 }
readerECP       OBJECT IDENTIFIER ::= { config 9 }
readerELP       OBJECT IDENTIFIER ::= { config 10 }


system		OBJECT IDENTIFIER ::= { reader4uvh 2 }

cpu-unit	OBJECT IDENTIFIER ::= { reader4uvh 15 }
cpu-mem-module	OBJECT IDENTIFIER ::= { reader4uvh 16 }
bank		OBJECT IDENTIFIER ::= { reader4uvh 18 }
dimm		OBJECT IDENTIFIER ::= { reader4uvh 19 }

power-supply 	OBJECT IDENTIFIER ::= { reader4uvh 22 }
--fru-device	OBJECT IDENTIFIER ::= { reader4uvh 23 }
seeprom		OBJECT IDENTIFIER ::= { reader4uvh 23 }
fans		OBJECT IDENTIFIER ::= { reader4uvh 24 }
keyswitch	OBJECT IDENTIFIER ::= { reader4uvh 30 }
running-led	OBJECT IDENTIFIER ::= { reader4uvh 31 }
-- not sure on controlled-led
controlled-led	OBJECT IDENTIFIER ::= { reader4uvh 32 }
system-status	OBJECT IDENTIFIER ::= { reader4uvh 37 }
-- not sure on system-status-panel
system-status-panel	OBJECT IDENTIFIER ::= { reader4uvh 38 }
service-led	OBJECT IDENTIFIER ::= { reader4uvh 43 }
removal-led	OBJECT IDENTIFIER ::= { reader4uvh 44 }
temperature-sensor	OBJECT IDENTIFIER ::= { reader4uvh 45 }
rsc		OBJECT IDENTIFIER ::= { reader4uvh 46 }
hardware-rules	OBJECT IDENTIFIER ::= { reader4uvh 47 }
io-controller	OBJECT IDENTIFIER ::= { reader4uvh 49 }
io-device	OBJECT IDENTIFIER ::= { reader4uvh 50 }
disk		OBJECT IDENTIFIER ::= { reader4uvh 51 }
tape		OBJECT IDENTIFIER ::= { reader4uvh 52 }
network		OBJECT IDENTIFIER ::= { reader4uvh 53 }
generic-device	OBJECT IDENTIFIER ::= { reader4uvh 55 }





sunSmTreeProp	OBJECT IDENTIFIER ::= { networkEntry 1 }
sunSmNodeName	OBJECT IDENTIFIER ::= { networkEntry 2 }
entry-no	OBJECT IDENTIFIER ::= { networkEntry 3 }
device-type	OBJECT IDENTIFIER ::= { networkEntry 4 }
fru	OBJECT IDENTIFIER ::= { networkEntry 5 }
ether	OBJECT IDENTIFIER ::= { networkEntry 6 }
inet	OBJECT IDENTIFIER ::= { networkEntry 7 }
interface-name	OBJECT IDENTIFIER ::= { networkEntry 8 }
node-hierarchy	OBJECT IDENTIFIER ::= { networkEntry 9 }
symbolic-name	OBJECT IDENTIFIER ::= { networkEntry 10 }
reg	OBJECT IDENTIFIER ::= { networkEntry 11 }
input-errors	OBJECT IDENTIFIER ::= { networkEntry 12 }
output-errors	OBJECT IDENTIFIER ::= { networkEntry 13 }
sunSmTreeProp	OBJECT IDENTIFIER ::= { running-led-entry 1 }
sunSmNodeName	OBJECT IDENTIFIER ::= { running-led-entry 2 }
entry-no	OBJECT IDENTIFIER ::= { running-led-entry 3 }
led-num	OBJECT IDENTIFIER ::= { running-led-entry 4 }
state	OBJECT IDENTIFIER ::= { running-led-entry 5 }
sunSmTreeProp	OBJECT IDENTIFIER ::= { system 1 }
sunSmNodeName	OBJECT IDENTIFIER ::= { system 2 }
os	OBJECT IDENTIFIER ::= { system 3 }
os-version	OBJECT IDENTIFIER ::= { system 4 }
system-clock-frequency	OBJECT IDENTIFIER ::= { system 5 }
architecture	OBJECT IDENTIFIER ::= { system 6 }
hostname	OBJECT IDENTIFIER ::= { system 7 }
machine	OBJECT IDENTIFIER ::= { system 8 }
platform	OBJECT IDENTIFIER ::= { system 9 }
sample	OBJECT IDENTIFIER ::= { system 10 }
serial-number	OBJECT IDENTIFIER ::= { system 11 }
timestamp	OBJECT IDENTIFIER ::= { system 12 }
timestamp-raw	OBJECT IDENTIFIER ::= { system 13 }
total-disks	OBJECT IDENTIFIER ::= { system 14 }
total-memory	OBJECT IDENTIFIER ::= { system 15 }
total-processors	OBJECT IDENTIFIER ::= { system 16 }
total-tape-devices	OBJECT IDENTIFIER ::= { system 17 }
total-model-changes	OBJECT IDENTIFIER ::= { system 18 }
total-config-changes	OBJECT IDENTIFIER ::= { system 19 }
cpu-unitTbl	OBJECT IDENTIFIER ::= { cpu-unit 1 }
removal-led-entry	OBJECT IDENTIFIER ::= { removal-ledTbl 1 }
power-supplyTbl	OBJECT IDENTIFIER ::= { power-supply 1 }
networkEntry	OBJECT IDENTIFIER ::= { networkTbl 1 }
temperature-sensor-entry	OBJECT IDENTIFIER ::= { temperature-sensorTbl 1 }
cpu-mem-moduleTbl	OBJECT IDENTIFIER ::= { cpu-mem-module 1 }
sunSmTreeProp	OBJECT IDENTIFIER ::= { power-supply-entry 1 }
sunSmNodeName	OBJECT IDENTIFIER ::= { power-supply-entry 2 }
entry-no	OBJECT IDENTIFIER ::= { power-supply-entry 3 }
fru	OBJECT IDENTIFIER ::= { power-supply-entry 4 }
state	OBJECT IDENTIFIER ::= { power-supply-entry 5 }
unix-Timestamp32	OBJECT IDENTIFIER ::= { power-supply-entry 6 }
fru-Description	OBJECT IDENTIFIER ::= { power-supply-entry 7 }
manufacture-Loc	OBJECT IDENTIFIER ::= { power-supply-entry 8 }
sun-Part-No	OBJECT IDENTIFIER ::= { power-supply-entry 9 }
sun-Serial-No	OBJECT IDENTIFIER ::= { power-supply-entry 10 }
vendor-Name	OBJECT IDENTIFIER ::= { power-supply-entry 11 }
initial-HW-Dash-Level	OBJECT IDENTIFIER ::= { power-supply-entry 12 }
initial-HW-Rev-Level	OBJECT IDENTIFIER ::= { power-supply-entry 13 }
fru-Shortname	OBJECT IDENTIFIER ::= { power-supply-entry 14 }
sunSmTreeProp	OBJECT IDENTIFIER ::= { rsc 1 }
sunSmNodeName	OBJECT IDENTIFIER ::= { rsc 2 }
device-type	OBJECT IDENTIFIER ::= { rsc 3 }
fru-device	OBJECT IDENTIFIER ::= { rsc 4 }
name	OBJECT IDENTIFIER ::= { rsc 5 }
unix-Timestamp32	OBJECT IDENTIFIER ::= { rsc 6 }
fru-Description	OBJECT IDENTIFIER ::= { rsc 7 }
manufacture-Loc	OBJECT IDENTIFIER ::= { rsc 8 }
sun-Part-No	OBJECT IDENTIFIER ::= { rsc 9 }
sun-Serial-No	OBJECT IDENTIFIER ::= { rsc 10 }
vendor-Name	OBJECT IDENTIFIER ::= { rsc 11 }
initial-HW-Dash-Level	OBJECT IDENTIFIER ::= { rsc 12 }
initial-HW-Rev-Level	OBJECT IDENTIFIER ::= { rsc 13 }
fru-Shortname	OBJECT IDENTIFIER ::= { rsc 14 }
rsc-hostname	OBJECT IDENTIFIER ::= { rsc 15 }
sunSmTreeProp	OBJECT IDENTIFIER ::= { io-deviceEntry 1 }
sunSmNodeName	OBJECT IDENTIFIER ::= { io-deviceEntry 2 }
entry-no	OBJECT IDENTIFIER ::= { io-deviceEntry 3 }
device-type	OBJECT IDENTIFIER ::= { io-deviceEntry 4 }
disk-count	OBJECT IDENTIFIER ::= { io-deviceEntry 5 }
instance	OBJECT IDENTIFIER ::= { io-deviceEntry 6 }
model	OBJECT IDENTIFIER ::= { io-deviceEntry 7 }
node-hierarchy	OBJECT IDENTIFIER ::= { io-deviceEntry 8 }
network-count	OBJECT IDENTIFIER ::= { io-deviceEntry 9 }
reg	OBJECT IDENTIFIER ::= { io-deviceEntry 10 }
tape-count	OBJECT IDENTIFIER ::= { io-deviceEntry 11 }
sunSmTreeProp	OBJECT IDENTIFIER ::= { cpu-unit-entry 1 }
sunSmNodeName	OBJECT IDENTIFIER ::= { cpu-unit-entry 2 }
entry-no	OBJECT IDENTIFIER ::= { cpu-unit-entry 3 }
clock-frequency	OBJECT IDENTIFIER ::= { cpu-unit-entry 4 }
cpu-type	OBJECT IDENTIFIER ::= { cpu-unit-entry 5 }
dcache-size	OBJECT IDENTIFIER ::= { cpu-unit-entry 6 }
device-type	OBJECT IDENTIFIER ::= { cpu-unit-entry 7 }
ecache-size	OBJECT IDENTIFIER ::= { cpu-unit-entry 8 }
fru	OBJECT IDENTIFIER ::= { cpu-unit-entry 9 }
icache-size	OBJECT IDENTIFIER ::= { cpu-unit-entry 10 }
model	OBJECT IDENTIFIER ::= { cpu-unit-entry 11 }
pathname-element	OBJECT IDENTIFIER ::= { cpu-unit-entry 12 }
processor-id	OBJECT IDENTIFIER ::= { cpu-unit-entry 13 }
status	OBJECT IDENTIFIER ::= { cpu-unit-entry 14 }
unit	OBJECT IDENTIFIER ::= { cpu-unit-entry 15 }
temperature	OBJECT IDENTIFIER ::= { cpu-unit-entry 16 }
upa-portid	OBJECT IDENTIFIER ::= { cpu-unit-entry 17 }
io-deviceTbl	OBJECT IDENTIFIER ::= { io-device 1 }
cpu-mem-module-entry	OBJECT IDENTIFIER ::= { cpu-mem-moduleTbl 1 }
power-supply-entry	OBJECT IDENTIFIER ::= { power-supplyTbl 1 }
io-controllerTbl	OBJECT IDENTIFIER ::= { io-controller 1 }
sunSmTreeProp	OBJECT IDENTIFIER ::= { tapeEntry 1 }
sunSmNodeName	OBJECT IDENTIFIER ::= { tapeEntry 2 }
entry-no	OBJECT IDENTIFIER ::= { tapeEntry 3 }
device-type	OBJECT IDENTIFIER ::= { tapeEntry 4 }
fru	OBJECT IDENTIFIER ::= { tapeEntry 5 }
instance	OBJECT IDENTIFIER ::= { tapeEntry 6 }
model	OBJECT IDENTIFIER ::= { tapeEntry 7 }
node-hierarchy	OBJECT IDENTIFIER ::= { tapeEntry 8 }
tape-name	OBJECT IDENTIFIER ::= { tapeEntry 9 }
status	OBJECT IDENTIFIER ::= { tapeEntry 10 }
target	OBJECT IDENTIFIER ::= { tapeEntry 11 }
soft-errors	OBJECT IDENTIFIER ::= { tapeEntry 12 }
hard-errors	OBJECT IDENTIFIER ::= { tapeEntry 13 }
transport-errors	OBJECT IDENTIFIER ::= { tapeEntry 14 }
temperature-sensorTbl	OBJECT IDENTIFIER ::= { temperature-sensor 1 }
generic-deviceTbl	OBJECT IDENTIFIER ::= { generic-device 1 }
sunSmTreeProp	OBJECT IDENTIFIER ::= { fan-entry 1 }
sunSmNodeName	OBJECT IDENTIFIER ::= { fan-entry 2 }
entry-no	OBJECT IDENTIFIER ::= { fan-entry 3 }
status	OBJECT IDENTIFIER ::= { fan-entry 4 }
speed	OBJECT IDENTIFIER ::= { fan-entry 5 }
sunSmTreeProp	OBJECT IDENTIFIER ::= { dimm-entry 1 }
sunSmNodeName	OBJECT IDENTIFIER ::= { dimm-entry 2 }
entry-no	OBJECT IDENTIFIER ::= { dimm-entry 3 }
device-type	OBJECT IDENTIFIER ::= { dimm-entry 4 }
fru	OBJECT IDENTIFIER ::= { dimm-entry 5 }
fru-device	OBJECT IDENTIFIER ::= { dimm-entry 6 }
module-size	OBJECT IDENTIFIER ::= { dimm-entry 7 }
socket-name	OBJECT IDENTIFIER ::= { dimm-entry 8 }
status	OBJECT IDENTIFIER ::= { dimm-entry 9 }
unix-Timestamp32	OBJECT IDENTIFIER ::= { dimm-entry 10 }
fru-Description	OBJECT IDENTIFIER ::= { dimm-entry 11 }
manufacture-Loc	OBJECT IDENTIFIER ::= { dimm-entry 12 }
sun-Part-No	OBJECT IDENTIFIER ::= { dimm-entry 13 }
sun-Serial-No	OBJECT IDENTIFIER ::= { dimm-entry 14 }
vendor-Name	OBJECT IDENTIFIER ::= { dimm-entry 15 }
initial-HW-Dash-Level	OBJECT IDENTIFIER ::= { dimm-entry 16 }
initial-HW-Rev-Level	OBJECT IDENTIFIER ::= { dimm-entry 17 }
fru-Shortname	OBJECT IDENTIFIER ::= { dimm-entry 18 }
service-led-entry	OBJECT IDENTIFIER ::= { service-ledTbl 1 }
sunSmTreeProp	OBJECT IDENTIFIER ::= { fru-device-entry 1 }
sunSmNodeName	OBJECT IDENTIFIER ::= { fru-device-entry 2 }
entry-no	OBJECT IDENTIFIER ::= { fru-device-entry 3 }
unix-Timestamp32	OBJECT IDENTIFIER ::= { fru-device-entry 4 }
fru-Description	OBJECT IDENTIFIER ::= { fru-device-entry 5 }
manufacture-Loc	OBJECT IDENTIFIER ::= { fru-device-entry 6 }
sun-Part-No	OBJECT IDENTIFIER ::= { fru-device-entry 7 }
sun-Serial-No	OBJECT IDENTIFIER ::= { fru-device-entry 8 }
vendor-Name	OBJECT IDENTIFIER ::= { fru-device-entry 9 }
initial-HW-Dash-Level	OBJECT IDENTIFIER ::= { fru-device-entry 10 }
initial-HW-Rev-Level	OBJECT IDENTIFIER ::= { fru-device-entry 11 }
fru-Shortname	OBJECT IDENTIFIER ::= { fru-device-entry 12 }
io-controllerTblEntry	OBJECT IDENTIFIER ::= { io-controllerTbl 1 }
generic-device-entry	OBJECT IDENTIFIER ::= { generic-deviceTbl 1 }
cpu-unit-entry	OBJECT IDENTIFIER ::= { cpu-unitTbl 1 }
tapeEntry	OBJECT IDENTIFIER ::= { tapeTbl 1 }
sunSmTreeProp	OBJECT IDENTIFIER ::= { diskEntry 1 }
sunSmNodeName	OBJECT IDENTIFIER ::= { diskEntry 2 }
entry-no	OBJECT IDENTIFIER ::= { diskEntry 3 }
device-type	OBJECT IDENTIFIER ::= { diskEntry 4 }
disk-name	OBJECT IDENTIFIER ::= { diskEntry 5 }
fru	OBJECT IDENTIFIER ::= { diskEntry 6 }
instance	OBJECT IDENTIFIER ::= { diskEntry 7 }
node-hierarchy	OBJECT IDENTIFIER ::= { diskEntry 8 }
target	OBJECT IDENTIFIER ::= { diskEntry 9 }
soft-errors	OBJECT IDENTIFIER ::= { diskEntry 10 }
hard-errors	OBJECT IDENTIFIER ::= { diskEntry 11 }
transport-errors	OBJECT IDENTIFIER ::= { diskEntry 12 }
sunSmTreeProp	OBJECT IDENTIFIER ::= { generic-device-entry 1 }
sunSmNodeName	OBJECT IDENTIFIER ::= { generic-device-entry 2 }
entry-no	OBJECT IDENTIFIER ::= { generic-device-entry 3 }
pathname-element	OBJECT IDENTIFIER ::= { generic-device-entry 4 }
sunSmTreeProp	OBJECT IDENTIFIER ::= { temperature-sensor-entry 1 }
sunSmNodeName	OBJECT IDENTIFIER ::= { temperature-sensor-entry 2 }
entry-no	OBJECT IDENTIFIER ::= { temperature-sensor-entry 3 }
temp	OBJECT IDENTIFIER ::= { temperature-sensor-entry 4 }
highwarn	OBJECT IDENTIFIER ::= { temperature-sensor-entry 5 }
lowwarn	OBJECT IDENTIFIER ::= { temperature-sensor-entry 6 }
highfail	OBJECT IDENTIFIER ::= { temperature-sensor-entry 7 }
lowfail	OBJECT IDENTIFIER ::= { temperature-sensor-entry 8 }
bankTbl	OBJECT IDENTIFIER ::= { bank 1 }
sunSmTreeProp	OBJECT IDENTIFIER ::= { controlled-led-entry 1 }
sunSmNodeName	OBJECT IDENTIFIER ::= { controlled-led-entry 2 }
entry-no	OBJECT IDENTIFIER ::= { controlled-led-entry 3 }
led-num	OBJECT IDENTIFIER ::= { controlled-led-entry 4 }
state	OBJECT IDENTIFIER ::= { controlled-led-entry 5 }
dimmTbl	OBJECT IDENTIFIER ::= { dimm 1 }
controlled-led-entry	OBJECT IDENTIFIER ::= { controlled-ledTbl 1 }
ssp-entry	OBJECT IDENTIFIER ::= { system-status-panel 1 }
fru-device-entry	OBJECT IDENTIFIER ::= { fru-deviceTbl 1 }
running-led-entry	OBJECT IDENTIFIER ::= { running-ledTbl 1 }
sunSmTreeProp	OBJECT IDENTIFIER ::= { io-controllerTblEntry 1 }
sunSmNodeName	OBJECT IDENTIFIER ::= { io-controllerTblEntry 2 }
entry-no	OBJECT IDENTIFIER ::= { io-controllerTblEntry 3 }
board-num	OBJECT IDENTIFIER ::= { io-controllerTblEntry 4 }
clock-frequency	OBJECT IDENTIFIER ::= { io-controllerTblEntry 5 }
device-type	OBJECT IDENTIFIER ::= { io-controllerTblEntry 6 }
instance	OBJECT IDENTIFIER ::= { io-controllerTblEntry 7 }
model	OBJECT IDENTIFIER ::= { io-controllerTblEntry 8 }
reg	OBJECT IDENTIFIER ::= { io-controllerTblEntry 9 }
upa-mid	OBJECT IDENTIFIER ::= { io-controllerTblEntry 10 }
upa-portid	OBJECT IDENTIFIER ::= { io-controllerTblEntry 11 }
version-no	OBJECT IDENTIFIER ::= { io-controllerTblEntry 12 }
controlled-ledTbl	OBJECT IDENTIFIER ::= { controlled-led 1 }
sunSmTreeProp	OBJECT IDENTIFIER ::= { service-led-entry 1 }
sunSmNodeName	OBJECT IDENTIFIER ::= { service-led-entry 2 }
entry-no	OBJECT IDENTIFIER ::= { service-led-entry 3 }
led-num	OBJECT IDENTIFIER ::= { service-led-entry 4 }
state	OBJECT IDENTIFIER ::= { service-led-entry 5 }
fan-entry	OBJECT IDENTIFIER ::= { fansTbl 1 }
sunSmTreeProp	OBJECT IDENTIFIER ::= { removal-led-entry 1 }
sunSmNodeName	OBJECT IDENTIFIER ::= { removal-led-entry 2 }
entry-no	OBJECT IDENTIFIER ::= { removal-led-entry 3 }
led-num	OBJECT IDENTIFIER ::= { removal-led-entry 4 }
state	OBJECT IDENTIFIER ::= { removal-led-entry 5 }
tapeTbl	OBJECT IDENTIFIER ::= { tape 1 }
running-ledTbl	OBJECT IDENTIFIER ::= { running-led 1 }
bank-entry	OBJECT IDENTIFIER ::= { bankTbl 1 }
service-ledTbl	OBJECT IDENTIFIER ::= { service-led 1 }
sunSmTreeProp	OBJECT IDENTIFIER ::= { ssp-entry 1 }
sunSmNodeName	OBJECT IDENTIFIER ::= { ssp-entry 2 }
entry-no	OBJECT IDENTIFIER ::= { ssp-entry 3 }
dimm-entry	OBJECT IDENTIFIER ::= { dimmTbl 1 }
diskTbl	OBJECT IDENTIFIER ::= { disk 1 }
removal-ledTbl	OBJECT IDENTIFIER ::= { removal-led 1 }
sunSmTreeProp	OBJECT IDENTIFIER ::= { keyswitch 1 }
sunSmNodeName	OBJECT IDENTIFIER ::= { keyswitch 2 }
position	OBJECT IDENTIFIER ::= { keyswitch 3 }
rcr4u291	OBJECT IDENTIFIER ::= { hardware-rules 1 }
fru-deviceTbl	OBJECT IDENTIFIER ::= { seeprom 1 }
sunSmTreeProp	OBJECT IDENTIFIER ::= { bank-entry 1 }
sunSmNodeName	OBJECT IDENTIFIER ::= { bank-entry 2 }
entry-no	OBJECT IDENTIFIER ::= { bank-entry 3 }
bank-size	OBJECT IDENTIFIER ::= { bank-entry 4 }
device-type	OBJECT IDENTIFIER ::= { bank-entry 5 }
fru-device	OBJECT IDENTIFIER ::= { bank-entry 6 }
status	OBJECT IDENTIFIER ::= { bank-entry 7 }
reader4uvh	OBJECT IDENTIFIER ::= { config 8 }
networkTbl	OBJECT IDENTIFIER ::= { network 1 }
fansTbl	OBJECT IDENTIFIER ::= { fans 1 }
io-deviceEntry	OBJECT IDENTIFIER ::= { io-deviceTbl 1 }
sunSmTreeProp	OBJECT IDENTIFIER ::= { cpu-mem-module-entry 1 }
sunSmNodeName	OBJECT IDENTIFIER ::= { cpu-mem-module-entry 2 }
entry-no	OBJECT IDENTIFIER ::= { cpu-mem-module-entry 3 }
num-cpus	OBJECT IDENTIFIER ::= { cpu-mem-module-entry 4 }
num-dimms	OBJECT IDENTIFIER ::= { cpu-mem-module-entry 5 }
status	OBJECT IDENTIFIER ::= { cpu-mem-module-entry 6 }
slot-name	OBJECT IDENTIFIER ::= { cpu-mem-module-entry 7 }
unix-Timestamp32	OBJECT IDENTIFIER ::= { cpu-mem-module-entry 8 }
fru-Description	OBJECT IDENTIFIER ::= { cpu-mem-module-entry 9 }
manufacture-Loc	OBJECT IDENTIFIER ::= { cpu-mem-module-entry 10 }
sun-Part-No	OBJECT IDENTIFIER ::= { cpu-mem-module-entry 11 }
sun-Serial-No	OBJECT IDENTIFIER ::= { cpu-mem-module-entry 12 }
vendor-Name	OBJECT IDENTIFIER ::= { cpu-mem-module-entry 13 }
initial-HW-Dash-Level	OBJECT IDENTIFIER ::= { cpu-mem-module-entry 14 }
initial-HW-Rev-Level	OBJECT IDENTIFIER ::= { cpu-mem-module-entry 15 }
fru-Shortname	OBJECT IDENTIFIER ::= { cpu-mem-module-entry 16 }
diskEntry	OBJECT IDENTIFIER ::= { diskTbl 1 }

END
