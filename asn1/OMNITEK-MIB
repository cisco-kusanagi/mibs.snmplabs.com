OMNITEK-MIB DEFINITIONS ::= BEGIN

	IMPORTS
		enterprises	FROM RFC1155-SMI
		OBJECT-TYPE	FROM RFC-1212
		DisplayString	FROM RFC1213-MIB
		TRAP-TYPE       FROM RFC-1215
		Integer32 FROM SNMPv2-SMI;

	AudioStatus ::= INTEGER 
		{ 
			missing (1),
			silent (2),
			active (3),
			peak (4)
		}

	omnitek         OBJECT IDENTIFIER ::= { enterprises 18458 }
	videostatus     OBJECT IDENTIFIER ::= { omnitek 1 }
	videoindex      OBJECT IDENTIFIER ::= { omnitek 2 }
	wss             OBJECT IDENTIFIER ::= { omnitek 3 }
	teletext        OBJECT IDENTIFIER ::= { omnitek 4 }
	closedcaptions  OBJECT IDENTIFIER ::= { omnitek 5 }
	errors          OBJECT IDENTIFIER ::= { omnitek 6 }
	timecode        OBJECT IDENTIFIER ::= { omnitek 7 }
	audio           OBJECT IDENTIFIER ::= { omnitek 8 }
	logging         OBJECT IDENTIFIER ::= { omnitek 9 }
	generator	OBJECT IDENTIFIER ::= { omnitek 10 }

-- videostatus MIB

	videoStandard OBJECT-TYPE
		SYNTAX INTEGER 
			{ 
				format486i59 (1),
				format486p59 (2),
				format576i50 (3),
				format576p50 (4),
				format720p59 (5),
				format720p60 (6),
				format1035i59 (7),
				format1035i60 (8),
				format1080sf23 (9),
				format1080p23 (10),
				format1080sf24 (11),
				format1080p24 (12),
				format1080i50 (13),
				format1080p25 (14),
				format1080i59 (15),
				format1080p29 (16),
				format1080i60 (17),
				format1080p30 (18),
				format720p23 (19),
				format720p24 (20),
				format720p25 (21),
				format720p29 (22),
				format720p30 (23),
				format720p50 (24),
				format1080sf23rgb444log (26),
				format1080sf23rgb444lin (27),
				format1080sf23yuv444 (28),
				format1080sf24rgb444log (29),
				format1080sf24rgb444lin (30),
				format1080sf24yuv444 (31)
			}
		ACCESS read-write
		STATUS mandatory
		DESCRIPTION 
			"The current video standard."
		::= { videostatus 1 }

	digitalInput OBJECT-TYPE
		SYNTAX INTEGER
			{
				missing (1),
				error (2),
				ok (3)
			}
		ACCESS read-only
		STATUS mandatory
		DESCRIPTION 
			"Digital input detect state."
		::= { videostatus 2 }

	digitalInputB OBJECT-TYPE
		SYNTAX INTEGER
			{
				missing (1),
				error (2),
				ok (3)
			}
		ACCESS read-only
		STATUS mandatory
		DESCRIPTION 
			"Digital input detect state for link B (dual-link cards only)."
		::= { videostatus 3 }

	motionContent OBJECT-TYPE
		SYNTAX INTEGER
			{
				frozen (1),
				active (2)
			}
		ACCESS read-only
		STATUS mandatory
		DESCRIPTION 
			"Motion content (frozen (false)/active (true))."
		::= { videostatus 4 }

	lumaContent OBJECT-TYPE
		SYNTAX INTEGER
			{
				black (1),
				active (2)
			}
		ACCESS read-only
		STATUS mandatory
		DESCRIPTION 
			"Set when the input to the analyzer has luminance."
		::= { videostatus 5 }

	chromaContent OBJECT-TYPE
		SYNTAX INTEGER
			{
				monochrome (1),
				active (2)
			}
		ACCESS read-only
		STATUS mandatory
		DESCRIPTION 
			"Set when the input to the analyzer has chrominance."
		::= { videostatus 6 }

	syncStatus OBJECT-TYPE
		SYNTAX INTEGER 
			{
				missing (1),
				error (2),
				ok (3)
			}
		ACCESS read-only
		STATUS mandatory
		DESCRIPTION 
			"Status of the external sync input."
		::= { videostatus 7 }

-- videoindex parameters

	activeFormat OBJECT-TYPE
		SYNTAX DisplayString
		ACCESS read-only
		STATUS mandatory
		DESCRIPTION 
			"A description of the Video Index active format (SD ONLY).  Can be one of the following:

			Not Present
			Active region is same as Coded Frame
			4:3
			16:9
			14:9
			Reserved (4)
			4:3 with shoot-and-protect 14:9 centre
			16:9 with shoot-and-protect 14:9 centre
			16:9 with shoot-and-protect 4:3 centre"
		::= { videoindex 1 }

	codedFrame OBJECT-TYPE
		SYNTAX DisplayString
		ACCESS read-only
		STATUS mandatory
		DESCRIPTION 
			"A description of the Video Index coded frame format (SD ONLY).  Can be one of the following:

			Not Present
			No Information
			525/59.94 - 4:3
			625/50 - 4:3
			Reserved (3)
			Reserved (4)
			525/59.94 - 16:9
			625/50 - 16:9
			Reserved (7)"
		::= { videoindex 2 }

	componentSet OBJECT-TYPE
		SYNTAX DisplayString
		ACCESS read-only
		STATUS mandatory
		DESCRIPTION 
			"A description of the Video Index component set (SD ONLY).  Can be one of the following:

			Not Present
			No Information
			RGB
			YCbCr
			YUV
			Monochrome
			NTSC
			PAL
			PAL-M
			SECAM
			Reserved (9)
			Reserved (10)
			Reserved (11)
			Reserved (12)
			Reserved (13)
			Reserved (14)
			Reserved (15)"
		::= { videoindex 3 }

	sampleStructure OBJECT-TYPE
		SYNTAX DisplayString
		ACCESS read-only
		STATUS mandatory
		DESCRIPTION 
			"Description of the Video Index sample structure (SD ONLY).  Can be one of the following:
			
			Not Present
			No Information
			4:0:0
			4:2:2
			4:2:2:4, Main
			4:2:2:4, Sub
			4:4:4, Main
			4:4:4, Sub
			4:4:4:4, Main
			4:4:4:4, Sub
			4:2:2 Progressive, Main
			4:2:2 Progressive, Sub
			4:2:0 Progressive
			8:4:4, Main
			8:4:4, Sub
			4:2:2:4, Single Link
			Reserved (15)"
		::= { videoindex 4 }

-- wss (Wide-Screen Signalling) parameters

	wssReadType OBJECT-TYPE
		SYNTAX INTEGER
			{
				en300294 (1),
				ardspec (2)
			}
		ACCESS read-write
		STATUS mandatory
		DESCRIPTION 
			"Read type of Wide-Screen Signalling information."
		::= { wss 1 }

	aspectRatioEN300294 OBJECT-TYPE
		SYNTAX DisplayString
		ACCESS read-only
		STATUS mandatory
		DESCRIPTION 
			"Description of Wide-Screen Signalling aspect ratio (EN300294).  Can be one of the following:
			
			Not Present
			4:3 Full Format
			14:9 Letterbox Center
			14:9 Letterbox Top
			16:9 Letterbox Center
			16:9 Letterbox Top
			> 16:9 Letterbox Center
			14:9 Full Format Center
			16:9 Full Format (Anamorphic)
			Unknown"
		::= { wss 2 }

	enhancedServicesEN300294 OBJECT-TYPE
		SYNTAX DisplayString
		ACCESS read-only
		STATUS mandatory
		DESCRIPTION 
			"Description of Wide-Screen Signalling enhanced services (EN300294).  Value returned will be 'Not Present' or a binary 
			string from '0000' to '1111'"
		::= { wss 3 }

	subtitlesEN300294 OBJECT-TYPE
		SYNTAX DisplayString
		ACCESS read-only
		STATUS mandatory
		DESCRIPTION 
			"Description of Wide-Screen Signalling subtitles (EN300294).  Value returned will be 'Not Present' or a binary 
			string from '000' to '111'"
		::= { wss 4 }

	othersEN300294 OBJECT-TYPE
		SYNTAX DisplayString
		ACCESS read-only
		STATUS mandatory
		DESCRIPTION 
			"Description of Wide-Screen Signalling others field (EN300294).  Value returned will be 'Not Present' or a binary 
			string from '000' to '111'"
		::= { wss 5 }

	aspectRatioARDSPEC OBJECT-TYPE
		SYNTAX DisplayString
		ACCESS read-only
		STATUS mandatory
		DESCRIPTION 
			"Description of Wide-Screen Signalling aspect ratio field (ARDSPEC).  Can be one of the following:

			Not Present
			No Information
			525/59.94 4x3
			625/50 4x3
			Reserved (3)
			Reserved (4)
			525/59.94 16x9
			625/50 16x9
			Reserved (7)"
		::= { wss 6 }

	activeFormatARDSPEC OBJECT-TYPE
		SYNTAX DisplayString
		ACCESS read-only
		STATUS mandatory
		DESCRIPTION 
			"Description of Wide-Screen Signalling active format field (ARDSPEC).  Can be one of the following:
			
			Not Present
			Active Picture Same As Coded Raster
			4x3
			16x9
			14x9
			Reserved (4)
			4x3 With Shoot-And-Protect 14x9 Centre
			16x9 With Shoot-And-Protect 14x9 Centre
			Reserved (7)"
		::= { wss 7 }

	parityBitsARDSPEC OBJECT-TYPE
		SYNTAX DisplayString
		ACCESS read-only
		STATUS mandatory
		DESCRIPTION 
			"Description of Wide-Screen Signalling parity bits field (ARDSPEC).  Value returned will be 'Not Present' or a binary 
			string from '00' to '11'"
		::= { wss 8 }

	enhancedServicesARDSPEC OBJECT-TYPE
		SYNTAX DisplayString
		ACCESS read-only
		STATUS mandatory
		DESCRIPTION 
			"Description of Wide-Screen Signalling enhanced services (ARDSPEC).  Value returned will be 'Not Present' or a binary 
			string from '0000' to '1111'"
		::= { wss 9 }

	reservedARDSPEC OBJECT-TYPE
		SYNTAX DisplayString
		ACCESS read-only
		STATUS mandatory
		DESCRIPTION 
			"Description of Wide-Screen Signalling reserved field (ARDSPEC).  Value returned will be 'Not Present' or a binary 
			string from '00' to '11'"
		::= { wss 10 }

-- teletext parameters

	present OBJECT-TYPE
		SYNTAX INTEGER 
			{
				missing (1),
				present (2)
			}
		ACCESS read-only
		STATUS mandatory
		DESCRIPTION 
			"Whether teletext is present on the input."
		::= { teletext 1 }

-- closed caption parameters

	closedCaptionAnc608 OBJECT-TYPE
		SYNTAX INTEGER 
			{
				missing (1),
				present (2)
			}
		ACCESS read-only
		STATUS mandatory
		DESCRIPTION 
			"Whether Closed Captioning is present on the input (ANC 608)."
		::= { closedcaptions 1 }

	closedCaptionAnc708 OBJECT-TYPE
		SYNTAX INTEGER 
			{
				missing (1),
				present (2)
			}
		ACCESS read-only
		STATUS mandatory
		DESCRIPTION 
			"Whether Closed Captioning is present on the input (ANC 708)."
		::= { closedcaptions 2 }

	closedCaptionLine21 OBJECT-TYPE
		SYNTAX INTEGER 
			{
				missing (1),
				present (2)
			}
		ACCESS read-only
		STATUS mandatory
		DESCRIPTION 
			"Whether Closed Captioning is present on the input (Line 21)."
		::= { closedcaptions 3 }

-- error parameters
	crcErrors OBJECT-TYPE
		SYNTAX Integer32
		ACCESS read-write
		STATUS mandatory
		DESCRIPTION 
			"Number of video CRC errors.  Set to 0 to reset counter (resets link b counter on dual-link cards also)."
		::= { errors 1 }

	crcBErrors OBJECT-TYPE
		SYNTAX Integer32
		ACCESS read-write
		STATUS mandatory
		DESCRIPTION 
			"Number of video CRC errors for link b (dual-link cards only).  Set to 0 to reset counter (resets link a counter also)"
		::= { errors 2 }

	rgbRangeErrors OBJECT-TYPE
		SYNTAX Integer32
		ACCESS read-write
		STATUS mandatory
		DESCRIPTION 
			"Number of video RGB range errors.  Set to 0 to reset counter."
		::= { errors 3 }

	rgbRangeMin OBJECT-TYPE
		SYNTAX Integer32
		ACCESS read-write
		STATUS mandatory
		DESCRIPTION 
			"The minimum value of the accepted RGB range."
		::= { errors 4 }

	rgbRangeMax OBJECT-TYPE
		SYNTAX Integer32
		ACCESS read-write
		STATUS mandatory
		DESCRIPTION 
			"The maximum value of the accepted RGB range."
		::= { errors 5 }

	ycbcrRangeErrors OBJECT-TYPE
		SYNTAX Integer32
		ACCESS read-write
		STATUS mandatory
		DESCRIPTION 
			"Number of video YCbCr range errors.  Set to 0 to reset counter"
		::= { errors 6 }

	yRangeMin OBJECT-TYPE
		SYNTAX Integer32
		ACCESS read-write
		STATUS mandatory
		DESCRIPTION 
			"The minimum value of the accepted video Y data before a YCbCr range error is flagged."
		::= { errors 7 }

	yRrangeMax OBJECT-TYPE
		SYNTAX Integer32
		ACCESS read-write
		STATUS mandatory
		DESCRIPTION 
			"The maximum value of the accepted video Y data before a YCbCr range error is flagged."
		::= { errors 8 }

	uRangeMin OBJECT-TYPE
		SYNTAX Integer32
		ACCESS read-write
		STATUS mandatory
		DESCRIPTION 
			"The minimum value of the accepted video U data before a YCbCr range error is flagged."
		::= { errors 9 }

	uRangeMax OBJECT-TYPE
		SYNTAX Integer32
		ACCESS read-write
		STATUS mandatory
		DESCRIPTION 
			"The maximum value of the accepted video U data before a YCbCr range error is flagged."
		::= { errors 10 }

	vRangeMin OBJECT-TYPE
		SYNTAX Integer32
		ACCESS read-write
		STATUS mandatory
		DESCRIPTION 
			"The minimum value of the accepted video V data before a YCbCr range error is flagged."
		::= { errors 11 }

	vRangeMax OBJECT-TYPE
		SYNTAX Integer32
		ACCESS read-write
		STATUS mandatory
		DESCRIPTION 
			"The maximum value of the accepted video V data before a YCbCr range error is flagged."
		::= { errors 12 }

	trsErrors OBJECT-TYPE
		SYNTAX Integer32
		ACCESS read-write
		STATUS mandatory
		DESCRIPTION 
			"Number of TRS errors.  Set to 0 to reset counter (resets link b counter on dual-link cards also)"
		::= { errors 13 }

	trsBErrors OBJECT-TYPE
		SYNTAX Integer32
		ACCESS read-write
		STATUS mandatory
		DESCRIPTION 
			"Number of TRS errors for link b (dual-link cards only).  Set to 0 to reset counter (resets link a counter also)"
		::= { errors 14 }

	ancErrors OBJECT-TYPE
		SYNTAX Integer32
		ACCESS read-write
		STATUS mandatory
		DESCRIPTION 
			"Number of ANC errors.  Set to 0 to reset counter (resets link b counter on dual-link cards also)"
		::= { errors 15 }

	ancBErrors OBJECT-TYPE
		SYNTAX Integer32
		ACCESS read-write
		STATUS mandatory
		DESCRIPTION 
			"Number of ANC errors for link b (dual-link cards only).  Set to 0 to reset counter (resets link a counter also)"
		::= { errors 16 }

	lineErrors OBJECT-TYPE
		SYNTAX Integer32
		ACCESS read-write
		STATUS mandatory
		DESCRIPTION 
			"Number of line number errors.  Set to 0 to reset counter (resets link b counter on dual-link cards also)"
		::= { errors 17 }

	lineBErrors OBJECT-TYPE
		SYNTAX Integer32
		ACCESS read-write
		STATUS mandatory
		DESCRIPTION 
			"Number of line number errors for link b (dual-link cards only).  Set to 0 to reset counter (resets link a counter also)"
		::= { errors 18 }

	frozenVITC OBJECT-TYPE
		SYNTAX Integer32
		ACCESS read-write
		STATUS mandatory
		DESCRIPTION 
			"Number of frozen VITC errors.  Set to 0 to reset counter.  NOT CURRENTLY IMPLEMENTED."
		::= { errors 19 }

	skippedVITC OBJECT-TYPE
		SYNTAX Integer32
		ACCESS read-write
		STATUS mandatory
		DESCRIPTION 
			"Number of skipped VITC errors.  Set to 0 to reset counter.  NOT CURRENTLY IMPLEMENTED."
		::= { errors 20 }

	frozenATC OBJECT-TYPE
		SYNTAX Integer32
		ACCESS read-write
		STATUS mandatory
		DESCRIPTION 
			"Number of frozen ATC errors.  Set to 0 to reset counter.  NOT CURRENTLY IMPLEMENTED."
		::= { errors 21 }

	skippedATC OBJECT-TYPE
		SYNTAX Integer32
		ACCESS read-write
		STATUS mandatory
		DESCRIPTION 
			"Number of skipped ATC errors.  Set to 0 to reset counter.  NOT CURRENTLY IMPLEMENTED."
		::= { errors 22 }

	compRangeErrors OBJECT-TYPE
		SYNTAX Integer32
		ACCESS read-write
		STATUS mandatory
		DESCRIPTION 
			"Number of Composite range errors.  Set to 0 to reset counter"
		::= { errors 23 }

	compRangeMin OBJECT-TYPE
		SYNTAX Integer32
		ACCESS read-write
		STATUS mandatory
		DESCRIPTION 
			""
		::= { errors 24 }

	compRangeMax OBJECT-TYPE
		SYNTAX Integer32
		ACCESS read-write
		STATUS mandatory
		DESCRIPTION 
			""
		::= { errors 25 }

	edhError OBJECT-TYPE
		SYNTAX Integer32
		ACCESS read-write
		STATUS mandatory
		DESCRIPTION 
			"Number of video EDH errors.  Set to 0 to reset counter."
		::= { errors 26 }

	edhInvalid OBJECT-TYPE
		SYNTAX Integer32
		ACCESS read-write
		STATUS mandatory
		DESCRIPTION 
			"Video EDH invalid counter.  Set to 0 to reset counter."
		::= { errors 27 }

-- timecode parameters

	vitc OBJECT-TYPE
		SYNTAX DisplayString
		ACCESS read-only
		STATUS mandatory
		DESCRIPTION 
			"VITC timecode of input (SD ONLY)."
		::= { timecode 1 }

	atc OBJECT-TYPE
		SYNTAX DisplayString
		ACCESS read-only
		STATUS mandatory
		DESCRIPTION 
			"ATC timecode of input."
		::= { timecode 2 }

-- audio parameters

	usageGroup1 OBJECT-TYPE
		SYNTAX DisplayString
		ACCESS read-only
		STATUS mandatory
		DESCRIPTION 
			"The audio usage string for audio group 1 .  NOT IMPLEMENTED YET"
		::= { audio 1 }

	usageGroup2 OBJECT-TYPE
		SYNTAX DisplayString
		ACCESS read-only
		STATUS mandatory
		DESCRIPTION 
			"The audio usage string for audio group 2 .  NOT IMPLEMENTED YET"
		::= { audio 2 }

	usageGroup3 OBJECT-TYPE
		SYNTAX DisplayString
		ACCESS read-only
		STATUS mandatory
		DESCRIPTION 
			"The audio usage string for audio group 3 .  NOT IMPLEMENTED YET"
		::= { audio 3 }

	usageGroup4 OBJECT-TYPE
		SYNTAX DisplayString
		ACCESS read-only
		STATUS mandatory
		DESCRIPTION 
			"The audio usage string for audio group 4 .  NOT IMPLEMENTED YET"
		::= { audio 4 }

	sampleGroup1 OBJECT-TYPE
		SYNTAX INTEGER 
			{
				audio (1),
				data (2)
			}
		ACCESS read-only
		STATUS mandatory
		DESCRIPTION 
			"Whether audio packets contain audio/data in group 1.  NOT IMPLEMENTED YET"
		::= { audio 5 }

	sampleGroup2 OBJECT-TYPE
		SYNTAX INTEGER 
			{
				audio (1),
				data (2)
			}
		ACCESS read-only
		STATUS mandatory
		DESCRIPTION 
			"Whether audio packets contain audio/data in group 2.  NOT IMPLEMENTED YET"
		::= { audio 6 }

	sampleGroup3 OBJECT-TYPE
		SYNTAX INTEGER 
			{
				audio (1),
				data (2)
			}
		ACCESS read-only
		STATUS mandatory
		DESCRIPTION 
			"Whether audio packets contain audio/data in group 3.  NOT IMPLEMENTED YET"
		::= { audio 7 }

	sampleGroup4 OBJECT-TYPE
		SYNTAX INTEGER 
			{
				audio (1),
				data (2)
			}
		ACCESS read-only
		STATUS mandatory
		DESCRIPTION 
			"Whether audio packets contain audio/data in group 4.  NOT IMPLEMENTED YET"
		::= { audio 8 }

	emphasisGroup1 OBJECT-TYPE
		SYNTAX INTEGER 
			{
				off (1),
				on (2)
			}
		ACCESS read-only
		STATUS mandatory
		DESCRIPTION 
			"Whether audio emphasis is present in audio group 1.  NOT IMPLEMENTED YET"
		::= { audio 9 }

	emphasisGroup2 OBJECT-TYPE
		SYNTAX INTEGER 
			{
				off (1),
				on (2)
			}
		ACCESS read-only
		STATUS mandatory
		DESCRIPTION 
			"Whether audio emphasis is present in audio group 2.  NOT IMPLEMENTED YET"
		::= { audio 10 }

	emphasisGroup3 OBJECT-TYPE
		SYNTAX INTEGER 
			{
				off (1),
				on (2)
			}
		ACCESS read-only
		STATUS mandatory
		DESCRIPTION 
			"Whether audio emphasis is present in audio group 3.  NOT IMPLEMENTED YET"
		::= { audio 11 }

	emphasisGroup4 OBJECT-TYPE
		SYNTAX INTEGER 
			{
				off (1),
				on (2)
			}
		ACCESS read-only
		STATUS mandatory
		DESCRIPTION 
			"Whether audio emphasis is present in audio group 4.  NOT IMPLEMENTED YET"
		::= { audio 12 }

	lockGroup1 OBJECT-TYPE
		SYNTAX INTEGER 
			{
				off (1),
				on (2)
			}
		ACCESS read-only
		STATUS mandatory
		DESCRIPTION 
			"Whether audio group 1 is locked.  NOT IMPLEMENTED YET"
		::= { audio 13 }

	lockGroup2 OBJECT-TYPE
		SYNTAX INTEGER 
			{
				off (1),
				on (2)
			}
		ACCESS read-only
		STATUS mandatory
		DESCRIPTION 
			"Whether audio group 2 is locked.  NOT IMPLEMENTED YET"
		::= { audio 14 }

	lockGroup3 OBJECT-TYPE
		SYNTAX INTEGER 
			{
				off (1),
				on (2)
			}
		ACCESS read-only
		STATUS mandatory
		DESCRIPTION 
			"Whether audio group 3 is locked.  NOT IMPLEMENTED YET"
		::= { audio 15 }

	lockGroup4 OBJECT-TYPE
		SYNTAX INTEGER 
			{
				off (1),
				on (2)
			}
		ACCESS read-only
		STATUS mandatory
		DESCRIPTION 
			"Whether audio group 4 is locked.  NOT IMPLEMENTED YET"
		::= { audio 16 }

	frequencyGroup1 OBJECT-TYPE
		SYNTAX INTEGER 
			{
				default48khz (1),
				manual48khz (2),
				freq441khz (3),
				freq32khz (4)
			}
		ACCESS read-only
		STATUS mandatory
		DESCRIPTION 
			"Sample frequency of audio in group 1.  NOT IMPLEMENTED YET"
		::= { audio 17 }

	frequencyGroup2 OBJECT-TYPE
		SYNTAX INTEGER 
			{
				default48khz (1),
				manual48khz (2),
				freq441khz (3),
				freq32khz (4)
			}
		ACCESS read-only
		STATUS mandatory
		DESCRIPTION 
			"Sample frequency of audio in group 2.  NOT IMPLEMENTED YET"
		::= { audio 18 }

	frequencyGroup3 OBJECT-TYPE
		SYNTAX INTEGER 
			{
				default48khz (1),
				manual48khz (2),
				freq441khz (3),
				freq32khz (4)
			}
		ACCESS read-only
		STATUS mandatory
		DESCRIPTION 
			"Sample frequency of audio in group 3.  NOT IMPLEMENTED YET"
		::= { audio 19 }

	frequencyGroup4 OBJECT-TYPE
		SYNTAX INTEGER 
			{
				default48khz (1),
				manual48khz (2),
				freq441khz (3),
				freq32khz (4)
			}
		ACCESS read-only
		STATUS mandatory
		DESCRIPTION 
			"Sample frequency of audio in group 4.  NOT IMPLEMENTED YET"
		::= { audio 20 }

	channelModeGroup1 OBJECT-TYPE
		SYNTAX INTEGER 
			{
				default (1),
				dual (2),
				single (3),
				primarysecondary (4),
				stereo (5)
			}
		ACCESS read-only
		STATUS mandatory
		DESCRIPTION 
			"Channel mode of audio group 1.  NOT IMPLEMENTED YET"
		::= { audio 21 }

	channelModeGroup2 OBJECT-TYPE
		SYNTAX INTEGER 
			{
				default (1),
				dual (2),
				single (3),
				primarysecondary (4),
				stereo (5)
			}
		ACCESS read-only
		STATUS mandatory
		DESCRIPTION 
			"Channel mode of audio group 2.  NOT IMPLEMENTED YET"
		::= { audio 22 }

	channelModeGroup3 OBJECT-TYPE
		SYNTAX INTEGER 
			{
				default (1),
				dual (2),
				single (3),
				primarysecondary (4),
				stereo (5)
			}
		ACCESS read-only
		STATUS mandatory
		DESCRIPTION 
			"Channel mode of audio group 3.  NOT IMPLEMENTED YET"
		::= { audio 23 }

	channelModeGroup4 OBJECT-TYPE
		SYNTAX INTEGER 
			{
				default (1),
				dual (2),
				single (3),
				primarysecondary (4),
				stereo (5)
			}
		ACCESS read-only
		STATUS mandatory
		DESCRIPTION 
			"Channel mode of audio group 4.  NOT IMPLEMENTED YET"
		::= { audio 24 }

	wordLengthGroup1 OBJECT-TYPE
		SYNTAX INTEGER 
			{
				default (1),
				bits16 (2),
				bits18 (3),
				bits19 (4),
				bits20 (5),
				bits22 (6),
				bits23 (7),
				bits24 (8),
				user (9)
			}
		ACCESS read-only
		STATUS mandatory
		DESCRIPTION 
			"Word length of data in audio group 1.  NOT IMPLEMENTED YET"
		::= { audio 25 }

	wordLengthGroup2 OBJECT-TYPE
		SYNTAX INTEGER 
			{
				default (1),
				bits16 (2),
				bits18 (3),
				bits19 (4),
				bits20 (5),
				bits22 (6),
				bits23 (7),
				bits24 (8),
				user (9)
			}
		ACCESS read-only
		STATUS mandatory
		DESCRIPTION 
			"Word length of data in audio group 2.  NOT IMPLEMENTED YET"
		::= { audio 26 }

	wordLengthGroup3 OBJECT-TYPE
		SYNTAX INTEGER 
			{
				default (1),
				bits16 (2),
				bits18 (3),
				bits19 (4),
				bits20 (5),
				bits22 (6),
				bits23 (7),
				bits24 (8),
				user (9)
			}
		ACCESS read-only
		STATUS mandatory
		DESCRIPTION 
			"Word length of data in audio group 3.  NOT IMPLEMENTED YET"
		::= { audio 27 }

	wordLengthGroup4 OBJECT-TYPE
		SYNTAX INTEGER 
			{
				default (1),
				bits16 (2),
				bits18 (3),
				bits19 (4),
				bits20 (5),
				bits22 (6),
				bits23 (7),
				bits24 (8),
				user (9)
			}
		ACCESS read-only
		STATUS mandatory
		DESCRIPTION 
			"Word length of data in audio group 4.  NOT IMPLEMENTED YET"
		::= { audio 28 }

	channelStatus1 OBJECT-TYPE
		SYNTAX AudioStatus
		ACCESS read-only
		STATUS mandatory
		DESCRIPTION 
			"Channel 1 audio status.  NOT IMPLEMENTED YET"
		::= { audio 29 }

	channelStatus2 OBJECT-TYPE
		SYNTAX AudioStatus
		ACCESS read-only
		STATUS mandatory
		DESCRIPTION 
			"Channel 2 audio status.  NOT IMPLEMENTED YET"
		::= { audio 30 }

	channelStatus3 OBJECT-TYPE
		SYNTAX AudioStatus
		ACCESS read-only
		STATUS mandatory
		DESCRIPTION 
			"Channel 3 audio status.  NOT IMPLEMENTED YET"
		::= { audio 31 }

	channelStatus4 OBJECT-TYPE
		SYNTAX AudioStatus
		ACCESS read-only
		STATUS mandatory
		DESCRIPTION 
			"Channel 4 audio status.  NOT IMPLEMENTED YET"
		::= { audio 32 }

	channelStatus5 OBJECT-TYPE
		SYNTAX AudioStatus
		ACCESS read-only
		STATUS mandatory
		DESCRIPTION 
			"Channel 5 audio status.  NOT IMPLEMENTED YET"
		::= { audio 33 }

	channelStatus6 OBJECT-TYPE
		SYNTAX AudioStatus
		ACCESS read-only
		STATUS mandatory
		DESCRIPTION 
			"Channel 6 audio status.  NOT IMPLEMENTED YET"
		::= { audio 34 }

	channelStatus7 OBJECT-TYPE
		SYNTAX AudioStatus
		ACCESS read-only
		STATUS mandatory
		DESCRIPTION 
			"Channel 7 audio status.  NOT IMPLEMENTED YET"
		::= { audio 35 }

	channelStatus8 OBJECT-TYPE
		SYNTAX AudioStatus
		ACCESS read-only
		STATUS mandatory
		DESCRIPTION 
			"Channel 8 audio status.  NOT IMPLEMENTED YET"
		::= { audio 36 }

	channelStatus9 OBJECT-TYPE
		SYNTAX AudioStatus
		ACCESS read-only
		STATUS mandatory
		DESCRIPTION 
			"Channel 9 audio status.  NOT IMPLEMENTED YET"
		::= { audio 37 }

	channelStatus10 OBJECT-TYPE
		SYNTAX AudioStatus
		ACCESS read-only
		STATUS mandatory
		DESCRIPTION 
			"Channel 10 audio status.  NOT IMPLEMENTED YET"
		::= { audio 38 }

	channelStatus11 OBJECT-TYPE
		SYNTAX AudioStatus
		ACCESS read-only
		STATUS mandatory
		DESCRIPTION 
			"Channel 11 audio status.  NOT IMPLEMENTED YET"
		::= { audio 39 }

	channelStatus12 OBJECT-TYPE
		SYNTAX AudioStatus
		ACCESS read-only
		STATUS mandatory
		DESCRIPTION 
			"Channel 12 audio status.  NOT IMPLEMENTED YET"
		::= { audio 40 }

	channelStatus13 OBJECT-TYPE
		SYNTAX AudioStatus
		ACCESS read-only
		STATUS mandatory
		DESCRIPTION 
			"Channel 13 audio status.  NOT IMPLEMENTED YET"
		::= { audio 41 }

	channelStatus14 OBJECT-TYPE
		SYNTAX AudioStatus
		ACCESS read-only
		STATUS mandatory
		DESCRIPTION 
			"Channel 14 audio status.  NOT IMPLEMENTED YET"
		::= { audio 42 }

	channelStatus15 OBJECT-TYPE
		SYNTAX AudioStatus
		ACCESS read-only
		STATUS mandatory
		DESCRIPTION 
			"Channel 15 audio status.  NOT IMPLEMENTED YET"
		::= { audio 43 }

	channelStatus16 OBJECT-TYPE
		SYNTAX AudioStatus
		ACCESS read-only
		STATUS mandatory
		DESCRIPTION 
			"Channel 16 audio status.  NOT IMPLEMENTED YET"
		::= { audio 44 }

	audioMin OBJECT-TYPE
		SYNTAX Integer32
		ACCESS read-only
		STATUS mandatory
		DESCRIPTION 
			"Audio level below which is deemed silence.  NOT IMPLEMENTED YET"
		::= { audio 45 }

	audioMax OBJECT-TYPE
		SYNTAX Integer32
		ACCESS read-only
		STATUS mandatory
		DESCRIPTION 
			"Audio level above which is deemed peak.  NOT IMPLEMENTED YET"
		::= { audio 46 }

-- logging parameters

	jobId OBJECT-TYPE
		SYNTAX DisplayString
		ACCESS read-write
		STATUS mandatory
		DESCRIPTION 
			"The current logging jobId - NULL if not logging.  NOT IMPLEMENTED YET"
		::= { logging 1 }

-- generator parameters

	indexPattern OBJECT-TYPE
		SYNTAX Integer32
		ACCESS write-only
		STATUS mandatory
		DESCRIPTION 
			"Go to a specific pattern in the 'palette'.  If the index is <= 1, the first pattern will be selected, if it is >= nPatterns, the last
			pattern will be selected"
		::= { generator 1 }

	nextPattern OBJECT-TYPE
		SYNTAX Integer32
		ACCESS write-only
		STATUS mandatory
		DESCRIPTION 
			"Go to next pattern in 'palette'.  If reached end of palette, go back to pattern 0.  Must be > 0"
		::= { generator 2 }

	prevPattern OBJECT-TYPE
		SYNTAX Integer32
		ACCESS write-only
		STATUS mandatory
		DESCRIPTION 
			"Go to previous pattern in 'palette'.  If reached pattern 0, go to last pattern in palette.  Must be > 0"
		::= { generator 3 }

	transportToStart OBJECT-TYPE
		SYNTAX Integer32
		ACCESS write-only
		STATUS mandatory
		DESCRIPTION
			"Set this object to anything other than 0 to go to first frame of currently selected sequence/playlist (this will have no effect if a
			non-sequence pattern is selected in the configuration)."
		::= { generator 4 }

	transportJogBack OBJECT-TYPE
		SYNTAX Integer32
		ACCESS write-only
		STATUS mandatory
		DESCRIPTION
			"Set this object to anything other than 0 to go to the previous frame of currently selected sequence/playlist (this will have no effect if a
			non-sequence pattern is selected in the configuration)."
		::= { generator 5 }

	transportPlayReverse OBJECT-TYPE
		SYNTAX Integer32
		ACCESS read-write
		STATUS mandatory
		DESCRIPTION
			"Determine whether the currently selected pattern/playlist is playing in reverse (if the currently selected pattern is not a sequence/playlist, 
			this value will return 0).  You can set this value to anything other than 0 to play the currently selected sequence/playlist in reverse (this 
			will have no effect if a non-sequence pattern is selected in the configuration)."
		::= { generator 6 }

	transportStop OBJECT-TYPE
		SYNTAX Integer32
		ACCESS read-write
		STATUS mandatory
		DESCRIPTION
			"Determine whether the currently selected pattern/playlist is stopped (if the currently selected pattern is not a sequence/playlist, 
			this value will return 0).  You can set this value to anything other than 0 to play the currently selected sequence/playlist in reverse 
			(this will have no effect if a non-sequence pattern is selected in the configuration)."
		::= { generator 7 }

	transportPlayForward OBJECT-TYPE
		SYNTAX Integer32
		ACCESS read-write
		STATUS mandatory
		DESCRIPTION
			"Determine whether the currently selected pattern/playlist is playing forward (if the currently selected pattern is not a sequence/playlist, 
			this value will return 0).  You can set this value to anything other than 0 to play the currently selected sequence/playlist forward (this 
			will have no effect if a non-sequence pattern is selected in the configuration)."
		::= { generator 8 }

	transportJogNext OBJECT-TYPE
		SYNTAX Integer32
		ACCESS write-only
		STATUS mandatory
		DESCRIPTION
			"Set this object to anything other than 0 to go to the next frame of currently selected sequence/playlist (this will have no effect if a
			non-sequence pattern is selected in the configuration)."
		::= { generator 9 }

	transportToEnd OBJECT-TYPE
		SYNTAX Integer32
		ACCESS write-only
		STATUS mandatory
		DESCRIPTION
			"Set this object to anything other than 0 to go to the last frame of currently selected sequence/playlist (this will have no effect if a
			non-sequence pattern is selected in the configuration)."
		::= { generator 10 }

	transportLoop OBJECT-TYPE
		SYNTAX Integer32
		ACCESS read-write
		STATUS mandatory
		DESCRIPTION
			"Determine whether the currently selected pattern/playlist is looped (if the currently selected pattern is not a sequence/playlist, 
			this value will return 0).  You can set this value to 0 to disable loop, or anything other than 0 to loop the currently selected 
			sequence/playlist (this will have no effect if a non-sequence pattern is selected in the configuration)."
		::= { generator 11 }

-- traps
	systemUpTRAP TRAP-TYPE
		ENTERPRISE omnitek
		DESCRIPTION 
			"This trap is generated when the Omnitek software connects to the SNMP service."
		::= 1

	systemDownTRAP TRAP-TYPE
		ENTERPRISE omnitek
		DESCRIPTION 
			"This trap is generated when the SNMP service loses contact with the Omnitek software."
		::= 2

	videoStandardChangedTRAP TRAP-TYPE
		ENTERPRISE videostatus
		VARIABLES { videoStandard }
		DESCRIPTION 
			"This trap is generated when the video standard is changed on the OmniTek card."
		::= 3

	digitalInputTRAP TRAP-TYPE
		ENTERPRISE videostatus
		VARIABLES { digitalInput }
		DESCRIPTION 
			"Digital input present (1) or not (0)."
		::= 4

	digitalInputBTRAP TRAP-TYPE
		ENTERPRISE videostatus
		VARIABLES { digitalInputB }
		DESCRIPTION 
			"Digital input link B present (1) or not (0)."
		::= 5

	motionContentTRAP TRAP-TYPE
		ENTERPRISE videostatus
		VARIABLES { motionContent }
		DESCRIPTION 
			"This trap is generated when the input video freezes."
		::= 6

	lumaContentTRAP TRAP-TYPE
		ENTERPRISE videostatus
		VARIABLES { lumaContent }
		DESCRIPTION 
			"This trap is generated when the input video loses its luminance component."
		::= 7

	chromaContentTRAP TRAP-TYPE
		ENTERPRISE videostatus
		VARIABLES { chromaContent }
		DESCRIPTION 
			"This trap is generated when the input video loses its chrominance component."
		::= 8

	syncStatusTRAP TRAP-TYPE
		ENTERPRISE videostatus
		VARIABLES { syncStatus }
		DESCRIPTION 
			"This trap is generated when the sync status changes."
		::= 9

	crcErrorsTRAP TRAP-TYPE
		ENTERPRISE errors
		VARIABLES { crcErrors }
		DESCRIPTION 
			"This trap is generated when a video CRC error is detected."
		::= 10

	crcBErrorsTRAP TRAP-TYPE
		ENTERPRISE errors
		VARIABLES { crcBErrors }
		DESCRIPTION 
			"This trap is generated when a video CRC error is detected."
		::= 11

	rgbRangeErrorsTRAP TRAP-TYPE
		ENTERPRISE errors
		VARIABLES { rgbRangeErrors }
		DESCRIPTION 
			"This trap is generated when a video RGB range error is detected."
		::= 12

	ycbcrRangeErrorsTRAP TRAP-TYPE
		ENTERPRISE errors
		VARIABLES { ycbcrRangeErrors }
		DESCRIPTION 
			"This trap is generated when a video YCbCr range error is detected."
		::= 13

	trsErrorsTRAP TRAP-TYPE
		ENTERPRISE errors
		VARIABLES { trsErrors }
		DESCRIPTION 
			"This trap is generated when a video TRS error is detected."
		::= 14

	trsBErrorsTRAP TRAP-TYPE
		ENTERPRISE errors
		VARIABLES { trsBErrors }
		DESCRIPTION 
			"This trap is generated when a video TRS error is detected."
		::= 15

	ancErrorsTRAP TRAP-TYPE
		ENTERPRISE errors
		VARIABLES { ancErrors }
		DESCRIPTION 
			"This trap is generated when a video ANC error is detected."
		::= 16

	ancBErrorsTRAP TRAP-TYPE
		ENTERPRISE errors
		VARIABLES { ancBErrors }
		DESCRIPTION 
			"This trap is generated when a video ANC error is detected."
		::= 17

	lineErrorsTRAP TRAP-TYPE
		ENTERPRISE errors
		VARIABLES { lineErrors }
		DESCRIPTION 
			"This trap is generated when a video line number error is detected."
		::= 18

	lineBErrorsTRAP TRAP-TYPE
		ENTERPRISE errors
		VARIABLES { lineBErrors }
		DESCRIPTION 
			"This trap is generated when a video line number error is detected."
		::= 19

	frozenVITCTRAP TRAP-TYPE
		ENTERPRISE errors
		VARIABLES { frozenVITC }
		DESCRIPTION 
			"This trap is generated when a VITC frozen error is detected.  THIS TRAP NOT CURRENTLY IMPLEMENTED"
		::= 20

	skippedVITCTRAP TRAP-TYPE
		ENTERPRISE errors
		VARIABLES { skippedVITC }
		DESCRIPTION 
			"This trap is generated when a VITC skipped error is detected.  THIS TRAP NOT CURRENTLY IMPLEMENTED"
		::= 21

	frozenATCTRAP TRAP-TYPE
		ENTERPRISE errors
		VARIABLES { frozenATC }
		DESCRIPTION 
			"This trap is generated when a ATC frozen error is detected.  THIS TRAP NOT CURRENTLY IMPLEMENTED"
		::= 22

	skippedATCTRAP TRAP-TYPE
		ENTERPRISE errors
		VARIABLES { skippedATC }
		DESCRIPTION 
			"This trap is generated when a ATC skipped error is detected.  THIS TRAP NOT CURRENTLY IMPLEMENTED"
		::= 23

	compRangeErrorsTRAP TRAP-TYPE
		ENTERPRISE errors
		VARIABLES { compRangeErrors }
		DESCRIPTION 
			"This trap is generated when a video Composite range error is detected."
		::= 24

	edhErrorTRAP TRAP-TYPE
		ENTERPRISE errors
		VARIABLES { edhError }
		DESCRIPTION 
			"This trap is generated when a video EDH error is detected."
		::= 25

	edhInvalidTRAP TRAP-TYPE
		ENTERPRISE errors
		VARIABLES { edhInvalid }
		DESCRIPTION 
			"This trap is generated when a video EDH invalid is detected."
		::= 26

END
