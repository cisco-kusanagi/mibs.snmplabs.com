--
-- Name:     Apollo SNMP MIB
-- Purpose:  MIB for the APSNMP.DLL Extension agent for Windows NT
-- File:     APSNMP.MIB
-- Revision: 1.0
-- Author:   Dean A. Gratton
-- Compile:  MIBCC SMI.MIB APSNMP.MIB
--
-- OIDS:
-- Brand Private Enterprise Number:		3716
--   Windows NT Operating System:		1
--     ApolloStatsForNT					1
--     apolloTrapsForNT					2
--   Unix Operating System:				2
--     ApolloStatsForUnix				1
--     apolloTrapsForUnix				2
--
-- Base OID for Brand WindowsNT:  1.3.6.1.4.1.3716.1.1
-- Base OID for Brand Unix:       1.3.6.1.4.1.3716.1.2
--
-- Revision History:
--     18-11-98		1.00    Initial Revision
--

    APSNMP-MIB DEFINITIONS ::= BEGIN
    IMPORTS
	TRAP-TYPE FROM RFC-1215
        enterprises
            FROM RFC1155-SMI
        OBJECT-TYPE
            FROM RFC-1212
        DisplayString
            FROM RFC1213-MIB;

    brand                      OBJECT IDENTIFIER ::= { enterprises 3716       }
    windowsNT                  OBJECT IDENTIFIER ::= { brand 1                }

    apolloStatsForNT           OBJECT IDENTIFIER ::= { windowsNT 1            }
    apolloThresholdForNT       OBJECT IDENTIFIER ::= { windowsNT 2            }
	apolloTrapsForNT           OBJECT IDENTIFIER ::= { windowsNT 3            }

	statsForPort               OBJECT IDENTIFIER ::= { apolloStatsForNT 1     }
	statsForCalls              OBJECT IDENTIFIER ::= { apolloStatsForNT 2     } 
	statsForSession            OBJECT IDENTIFIER ::= { apolloStatsForNT 3     }
	statsForData               OBJECT IDENTIFIER ::= { apolloStatsForNT 4     }
	statsForError              OBJECT IDENTIFIER ::= { apolloStatsForNT 5     }
	statsForDriver             OBJECT IDENTIFIER ::= { apolloStatsForNT 6     }
	statsForCompression        OBJECT IDENTIFIER ::= { apolloStatsForNT 7     }

	statsSessionForGeneral     OBJECT IDENTIFIER ::= { statsForSession  1     }
	statsSessionForApollo      OBJECT IDENTIFIER ::= { statsForSession  2     }
	statsSessionForPPP	       OBJECT IDENTIFIER ::= { statsForSession  3     }

	thresholdForPort           OBJECT IDENTIFIER ::= { apolloThresholdForNT 1 }
	thresholdForCalls          OBJECT IDENTIFIER ::= { apolloThresholdForNT 2 }
	thresholdForSession        OBJECT IDENTIFIER ::= { apolloThresholdForNT 3 }
	thresholdForData           OBJECT IDENTIFIER ::= { apolloThresholdForNT 4 }
	thresholdForError          OBJECT IDENTIFIER ::= { apolloThresholdForNT 5 }
	thresholdForDriver         OBJECT IDENTIFIER ::= { apolloThresholdForNT 6 }
	thresholdForCompression    OBJECT IDENTIFIER ::= { apolloThresholdForNT 7 }

	thresholdSessionForGeneral OBJECT IDENTIFIER ::= { thresholdForSession  1 }
	thresholdSessionForApollo  OBJECT IDENTIFIER ::= { thresholdForSession  2 }
	thresholdSessionForPPP	   OBJECT IDENTIFIER ::= { thresholdForSession  3 }

-- STATISTICS

-- PORT
  statsPortsInUse OBJECT-TYPE
    SYNTAX INTEGER (0..2147483647)
    ACCESS read-only
    STATUS mandatory
    DESCRIPTION
      "A read-only INTEGER variable."
    ::= { statsForPort 1 }

  statsMaxPortsUsed OBJECT-TYPE
    SYNTAX INTEGER (0..2147483647)
    ACCESS read-only
    STATUS mandatory
    DESCRIPTION
      "A read-only INTEGER variable."
    ::= { statsForPort 2 }

  statsPortsInUseIncoming OBJECT-TYPE
    SYNTAX INTEGER (0..2147483647)
    ACCESS read-only
    STATUS mandatory
    DESCRIPTION
      "A read-only INTEGER variable."
    ::= { statsForPort 3 }

  statsPortsInUseOutgoing OBJECT-TYPE
    SYNTAX INTEGER (0..2147483647)
    ACCESS read-only
    STATUS mandatory
    DESCRIPTION
      "A read-only INTEGER variable."
    ::= { statsForPort 4 }

  statsOverrallCompressionRatioOfAllPorts OBJECT-TYPE
    SYNTAX INTEGER (0..2147483647)
    ACCESS read-only
    STATUS mandatory
    DESCRIPTION
      "A read-only INTEGER variable."
    ::= { statsForPort 5 }

-- CALLS
  statsTotalCallsMade OBJECT-TYPE
    SYNTAX INTEGER (0..2147483647)
    ACCESS read-only
    STATUS mandatory
    DESCRIPTION
      "A read-only INTEGER variable."
    ::= { statsForCalls 1 }

  statsFailedOutgoingCalls OBJECT-TYPE
    SYNTAX INTEGER (0..2147483647)
    ACCESS read-only
    STATUS mandatory
    DESCRIPTION
      "A read-only INTEGER variable."
    ::= { statsForCalls 2 }

  statsTotalCallsReceivedPerMinute OBJECT-TYPE
    SYNTAX INTEGER (0..2147483647)
    ACCESS read-only
    STATUS mandatory
    DESCRIPTION
      "A read-only INTEGER variable."
    ::= { statsForCalls 3 }

  statsTotalCallsReceivedPerHour OBJECT-TYPE
    SYNTAX INTEGER (0..2147483647)
    ACCESS read-only
    STATUS mandatory
    DESCRIPTION
      "A read-only INTEGER variable."
    ::= { statsForCalls 4 }

  statsTotalCallsReceivedPerDay OBJECT-TYPE
    SYNTAX INTEGER (0..2147483647)
    ACCESS read-only
    STATUS mandatory
    DESCRIPTION
      "A read-only INTEGER variable."
    ::= { statsForCalls 5 }

  statsTotalCallsMadePerMinute OBJECT-TYPE
    SYNTAX INTEGER (0..2147483647)
    ACCESS read-only
    STATUS mandatory
    DESCRIPTION
      "A read-only INTEGER variable."
    ::= { statsForCalls 6 }

  statsTotalCallsMadePerHour OBJECT-TYPE
    SYNTAX INTEGER (0..2147483647)
    ACCESS read-only
    STATUS mandatory
    DESCRIPTION
      "A read-only INTEGER variable."
    ::= { statsForCalls 7 }

  statsTotalCallsMadePerDay OBJECT-TYPE
    SYNTAX INTEGER (0..2147483647)
    ACCESS read-only
    STATUS mandatory
    DESCRIPTION
      "A read-only INTEGER variable."
    ::= { statsForCalls 8 }

  statsTotalCallsReceived OBJECT-TYPE
    SYNTAX INTEGER (0..2147483647)
    ACCESS read-only
    STATUS mandatory
    DESCRIPTION
      "A read-only INTEGER variable."
    ::= { statsForCalls 9 }

-- SESSION - GENERAL
  statsMaxSessionsUsed OBJECT-TYPE
    SYNTAX INTEGER (0..2147483647)
    ACCESS read-only
    STATUS mandatory
    DESCRIPTION
      "A read-only INTEGER variable."
    ::= { statsSessionForGeneral 1 }

  statsTotalNumberUserSessionGranted OBJECT-TYPE
    SYNTAX INTEGER (0..2147483647)
    ACCESS read-only
    STATUS mandatory
    DESCRIPTION
      "A read-only INTEGER variable."
    ::= { statsSessionForGeneral 2 }

  statsTotalNumberUserSessionRefused OBJECT-TYPE
    SYNTAX INTEGER (0..2147483647)
    ACCESS read-only
    STATUS mandatory
    DESCRIPTION
      "A read-only INTEGER variable."
    ::= { statsSessionForGeneral 3 }

  statsTotalNumberUserSessionsGrantedPerMinute OBJECT-TYPE
    SYNTAX INTEGER (0..2147483647)
    ACCESS read-only
    STATUS mandatory
    DESCRIPTION
      "A read-only INTEGER variable."
    ::= { statsSessionForGeneral 4 }

  statsTotalNumberUserSessionGrantedPerHour OBJECT-TYPE
    SYNTAX INTEGER (0..2147483647)
    ACCESS read-only
    STATUS mandatory
    DESCRIPTION
      "A read-only INTEGER variable."
    ::= { statsSessionForGeneral 5 }

  statsTotalNumberUserSessionGrantedPerDay OBJECT-TYPE
    SYNTAX INTEGER (0..2147483647)
    ACCESS read-only
    STATUS mandatory
    DESCRIPTION
      "A read-only INTEGER variable."
    ::= { statsSessionForGeneral 6 }

  statsTotalNumberUserSessionRefusedPerMinute OBJECT-TYPE
    SYNTAX INTEGER (0..2147483647)
    ACCESS read-only
    STATUS mandatory
    DESCRIPTION
      "A read-only INTEGER variable."
    ::= { statsSessionForGeneral 7 }

  statsTotalNumberUserSessionRefusedPerHour OBJECT-TYPE
    SYNTAX INTEGER (0..2147483647)
    ACCESS read-only
    STATUS mandatory
    DESCRIPTION
      "A read-only INTEGER variable."
    ::= { statsSessionForGeneral 8 }

  statsTotalNumberUserSessionRefusedPerDay OBJECT-TYPE
    SYNTAX INTEGER (0..2147483647)
    ACCESS read-only
    STATUS mandatory
    DESCRIPTION
      "A read-only INTEGER variable."
    ::= { statsSessionForGeneral 9 }

  statsTotalActiveUserSession OBJECT-TYPE
    SYNTAX INTEGER (0..2147483647)
    ACCESS read-only
    STATUS mandatory
    DESCRIPTION
      "A read-only INTEGER variable."
    ::= { statsSessionForGeneral 10 }

-- SESSION - APOLLO
  statsApolloActiveUserSessions OBJECT-TYPE
    SYNTAX INTEGER (0..2147483647)
    ACCESS read-only
    STATUS mandatory
    DESCRIPTION
      "A read-only INTEGER variable."
    ::= { statsSessionForApollo 1 }

  statsApolloNumberUserSessionsGranted OBJECT-TYPE
    SYNTAX INTEGER (0..2147483647)
    ACCESS read-only
    STATUS mandatory
    DESCRIPTION
      "A read-only INTEGER variable."
    ::= { statsSessionForApollo 2 }

  statsApolloNumberUserSessionsrefused OBJECT-TYPE
    SYNTAX INTEGER (0..2147483647)
    ACCESS read-only
    STATUS mandatory
    DESCRIPTION
      "A read-only INTEGER variable."
    ::= { statsSessionForApollo 3 }

  statsApolloNumberUserSessionsGrantedPerMinute OBJECT-TYPE
    SYNTAX INTEGER (0..2147483647)
    ACCESS read-only
    STATUS mandatory
    DESCRIPTION
      "A read-only INTEGER variable."
    ::= { statsSessionForApollo 4 }

  statsApolloNumberUserSessionsGrantedPerHour OBJECT-TYPE
    SYNTAX INTEGER (0..2147483647)
    ACCESS read-only
    STATUS mandatory
    DESCRIPTION
      "A read-only INTEGER variable."
    ::= { statsSessionForApollo 5 }

  statsApolloNumberUserSessionsGrantedPerDay OBJECT-TYPE
    SYNTAX INTEGER (0..2147483647)
    ACCESS read-only
    STATUS mandatory
    DESCRIPTION
      "A read-only INTEGER variable."
    ::= { statsSessionForApollo 6 }

  statsApolloNumberUserSessionsRefusedPerMinute OBJECT-TYPE
    SYNTAX INTEGER (0..2147483647)
    ACCESS read-only
    STATUS mandatory
    DESCRIPTION
      "A read-only INTEGER variable."
    ::= { statsSessionForApollo 7 }

  statsApolloNumberUserSessionsRefusedPerHour OBJECT-TYPE
    SYNTAX INTEGER (0..2147483647)
    ACCESS read-only
    STATUS mandatory
    DESCRIPTION
      "A read-only INTEGER variable."
    ::= { statsSessionForApollo 8 }

  statsApolloNumberUserSessionsRefusedPerDay OBJECT-TYPE
    SYNTAX INTEGER (0..2147483647)
    ACCESS read-only
    STATUS mandatory
    DESCRIPTION
      "A read-only INTEGER variable."
    ::= { statsSessionForApollo 9 }

  statsApolloMaximumSessionsUsed OBJECT-TYPE
    SYNTAX INTEGER (0..2147483647)
    ACCESS read-only
    STATUS mandatory
    DESCRIPTION
      "A read-only INTEGER variable."
    ::= { statsSessionForApollo 10 }

-- SESSION - PPP
  statsPPPActiveUserSessions OBJECT-TYPE
    SYNTAX INTEGER (0..2147483647)
    ACCESS read-only
    STATUS mandatory
    DESCRIPTION
      "A read-only INTEGER variable."
    ::= { statsSessionForPPP 1 }

  statsPPPNumberUserSessionsGranted OBJECT-TYPE
    SYNTAX INTEGER (0..2147483647)
    ACCESS read-only
    STATUS mandatory
    DESCRIPTION
      "A read-only INTEGER variable."
    ::= { statsSessionForPPP 2 }

  statsPPPNumberUserSessionsRefused OBJECT-TYPE
    SYNTAX INTEGER (0..2147483647)
    ACCESS read-only
    STATUS mandatory
    DESCRIPTION
      "A read-only INTEGER variable."
    ::= { statsSessionForPPP 3 }

  statsPPPNumberUserSessionsGrantedPerMinute OBJECT-TYPE
    SYNTAX INTEGER (0..2147483647)
    ACCESS read-only
    STATUS mandatory
    DESCRIPTION
      "A read-only INTEGER variable."
    ::= { statsSessionForPPP 4 }

  statsPPPNumberUserSessionsGrantedPerHour OBJECT-TYPE
    SYNTAX INTEGER (0..2147483647)
    ACCESS read-only
    STATUS mandatory
    DESCRIPTION
      "A read-only INTEGER variable."
    ::= { statsSessionForPPP 5 }

  statsPPPNumberUserSessionsGrantedPerDay OBJECT-TYPE
    SYNTAX INTEGER (0..2147483647)
    ACCESS read-only
    STATUS mandatory
    DESCRIPTION
      "A read-only INTEGER variable."
    ::= { statsSessionForPPP 6 }

  statsPPPNumberUserSessionsRefusedPerMinute OBJECT-TYPE
    SYNTAX INTEGER (0..2147483647)
    ACCESS read-only
    STATUS mandatory
    DESCRIPTION
      "A read-only INTEGER variable."
    ::= { statsSessionForPPP 7 }

  statsPPPNumberUserSessionsRefusedPerHour OBJECT-TYPE
    SYNTAX INTEGER (0..2147483647)
    ACCESS read-only
    STATUS mandatory
    DESCRIPTION
      "A read-only INTEGER variable."
    ::= { statsSessionForPPP 8 }

  statsPPPNumberUserSessionsRefusedPerDay OBJECT-TYPE
    SYNTAX INTEGER (0..2147483647)
    ACCESS read-only
    STATUS mandatory
    DESCRIPTION
      "A read-only INTEGER variable."
    ::= { statsSessionForPPP 9 }

  statsPPPMaximumSessionsUsed OBJECT-TYPE
    SYNTAX INTEGER (0..2147483647)
    ACCESS read-only
    STATUS mandatory
    DESCRIPTION
      "A read-only INTEGER variable."
    ::= { statsSessionForPPP 10 }

-- DATA
  statsNumberBytesReceivedPerSecond OBJECT-TYPE
    SYNTAX INTEGER (0..2147483647)
    ACCESS read-only
    STATUS mandatory
    DESCRIPTION
      "A read-only INTEGER variable."
    ::= { statsForData 1 }

  statsNumberBytesReceivedPerMinute OBJECT-TYPE
    SYNTAX INTEGER (0..2147483647)
    ACCESS read-only
    STATUS mandatory
    DESCRIPTION
      "A read-only INTEGER variable."
    ::= { statsForData 2 }

  statsNumberBytesReceivedPerHour OBJECT-TYPE
    SYNTAX INTEGER (0..2147483647)
    ACCESS read-only
    STATUS mandatory
    DESCRIPTION
      "A read-only INTEGER variable."
    ::= { statsForData 3 }

  statsNumberBytesReceivedPerDay OBJECT-TYPE
    SYNTAX INTEGER (0..2147483647)
    ACCESS read-only
    STATUS mandatory
    DESCRIPTION
      "A read-only INTEGER variable."
    ::= { statsForData 4 }

  statsNumberBytesTransmittedPerSecond OBJECT-TYPE
    SYNTAX INTEGER (0..2147483647)
    ACCESS read-only
    STATUS mandatory
    DESCRIPTION
      "A read-only INTEGER variable."
    ::= { statsForData 5 }

  statsNumberBytesTransmittedPerMinute OBJECT-TYPE
    SYNTAX INTEGER (0..2147483647)
    ACCESS read-only
    STATUS mandatory
    DESCRIPTION
      "A read-only INTEGER variable."
    ::= { statsForData 6 }

  statsNumberBytesTransmittedPerHour OBJECT-TYPE
    SYNTAX INTEGER (0..2147483647)
    ACCESS read-only
    STATUS mandatory
    DESCRIPTION
      "A read-only INTEGER variable."
    ::= { statsForData 7 }

  statsNumberBytesTransmittedPerDay OBJECT-TYPE
    SYNTAX INTEGER (0..2147483647)
    ACCESS read-only
    STATUS mandatory
    DESCRIPTION
      "A read-only INTEGER variable."
    ::= { statsForData 8 }

  statsPacketsTransmittedPerMinute OBJECT-TYPE
    SYNTAX INTEGER (0..2147483647)
    ACCESS read-only
    STATUS mandatory
    DESCRIPTION
      "A read-only INTEGER variable."
    ::= { statsForData 9 }

  statsPacketsTransmittedPerHour OBJECT-TYPE
    SYNTAX INTEGER (0..2147483647)
    ACCESS read-only
    STATUS mandatory
    DESCRIPTION
      "A read-only INTEGER variable."
    ::= { statsForData 10 }

  statsPacketsTransmittedPerDay OBJECT-TYPE
    SYNTAX INTEGER (0..2147483647)
    ACCESS read-only
    STATUS mandatory
    DESCRIPTION
      "A read-only INTEGER variable."
    ::= { statsForData 11 }

  statsPacketsReceivedPerMinute OBJECT-TYPE
    SYNTAX INTEGER (0..2147483647)
    ACCESS read-only
    STATUS mandatory
    DESCRIPTION
      "A read-only INTEGER variable."
    ::= { statsForData 12 }

  statsPacketsReceivedPerHour OBJECT-TYPE
    SYNTAX INTEGER (0..2147483647)
    ACCESS read-only
    STATUS mandatory
    DESCRIPTION
      "A read-only INTEGER variable."
    ::= { statsForData 13 }

  statsPacketsReceivedPerDay OBJECT-TYPE
    SYNTAX INTEGER (0..2147483647)
    ACCESS read-only
    STATUS mandatory
    DESCRIPTION
      "A read-only INTEGER variable."
    ::= { statsForData 14 }

  statsPacketReceivedPerSecond OBJECT-TYPE
    SYNTAX INTEGER (0..2147483647)
    ACCESS read-only
    STATUS mandatory
    DESCRIPTION
      "A read-only INTEGER variable."
    ::= { statsForData 15 }

  statsPacketTransmittedPerSecond OBJECT-TYPE
    SYNTAX INTEGER (0..2147483647)
    ACCESS read-only
    STATUS mandatory
    DESCRIPTION
      "A read-only INTEGER variable."
    ::= { statsForData 16 }

  statsTotalPacketReceived OBJECT-TYPE
    SYNTAX INTEGER (0..2147483647)
    ACCESS read-only
    STATUS mandatory
    DESCRIPTION
      "A read-only INTEGER variable."
    ::= { statsForData 17 }

  statsTotalPacketTransmitted OBJECT-TYPE
    SYNTAX INTEGER (0..2147483647)
    ACCESS read-only
    STATUS mandatory
    DESCRIPTION
      "A read-only INTEGER variable."
    ::= { statsForData 18 }

  statsTotalNumberBytesTransmitted OBJECT-TYPE
    SYNTAX INTEGER (0..2147483647)
    ACCESS read-only
    STATUS mandatory
    DESCRIPTION
      "A read-only INTEGER variable."
    ::= { statsForData 19 }

  statsTotalNumberBytesReceived OBJECT-TYPE
    SYNTAX INTEGER (0..2147483647)
    ACCESS read-only
    STATUS mandatory
    DESCRIPTION
      "A read-only INTEGER variable."
    ::= { statsForData 20 }

-- ERROR
  statsTotalNumberReceivedErrors OBJECT-TYPE
    SYNTAX INTEGER (0..2147483647)
    ACCESS read-only
    STATUS mandatory
    DESCRIPTION
      "A read-only INTEGER variable."
    ::= { statsForError 1 }

  statsTotalNumberTransmitErrors OBJECT-TYPE
    SYNTAX INTEGER (0..2147483647)
    ACCESS read-only
    STATUS mandatory
    DESCRIPTION
      "A read-only INTEGER variable."
    ::= { statsForError 2 }

  statsTotalNumberReceivedErrorsPerMinute OBJECT-TYPE
    SYNTAX INTEGER (0..2147483647)
    ACCESS read-only
    STATUS mandatory
    DESCRIPTION
      "A read-only INTEGER variable."
    ::= { statsForError 3 }

  statsTotalNumberReceivedErrorsPerHour OBJECT-TYPE
    SYNTAX INTEGER (0..2147483647)
    ACCESS read-only
    STATUS mandatory
    DESCRIPTION
      "A read-only INTEGER variable."
    ::= { statsForError 4 }

  statsTotalNumberReceivedErrorsPerDay OBJECT-TYPE
    SYNTAX INTEGER (0..2147483647)
    ACCESS read-only
    STATUS mandatory
    DESCRIPTION
      "A read-only INTEGER variable."
    ::= { statsForError 5 }

  statsTotalNumberTransmitErrorsPerMinute OBJECT-TYPE
    SYNTAX INTEGER (0..2147483647)
    ACCESS read-only
    STATUS mandatory
    DESCRIPTION
      "A read-only INTEGER variable."
    ::= { statsForError 6 }

  statsTotalNumberTransmitErrorsPerHour OBJECT-TYPE
    SYNTAX INTEGER (0..2147483647)
    ACCESS read-only
    STATUS mandatory
    DESCRIPTION
      "A read-only INTEGER variable."
    ::= { statsForError 7 }

  statsTotalNumberTransmitErrorsPerDay OBJECT-TYPE
    SYNTAX INTEGER (0..2147483647)
    ACCESS read-only
    STATUS mandatory
    DESCRIPTION
      "A read-only INTEGER variable."
    ::= { statsForError 8 }

  statsMaximumErrorRatePerSecond OBJECT-TYPE
    SYNTAX INTEGER (0..2147483647)
    ACCESS read-only
    STATUS mandatory
    DESCRIPTION
      "A read-only INTEGER variable."
    ::= { statsForError 9 }

  statsTotalErrorRatePerSecond OBJECT-TYPE
    SYNTAX INTEGER (0..2147483647)
    ACCESS read-only
    STATUS mandatory
    DESCRIPTION
      "A read-only INTEGER variable."
    ::= { statsForError 10 }

-- DRIVER
  statsCurrentClock OBJECT-TYPE
    SYNTAX INTEGER (0..2147483647)
    ACCESS read-only
    STATUS mandatory
    DESCRIPTION
      "A read-only INTEGER variable."
    ::= { statsForDriver 1 }

  statsCurrentMemoryUsedByDriver OBJECT-TYPE
    SYNTAX INTEGER (0..2147483647)
    ACCESS read-only
    STATUS mandatory
    DESCRIPTION
      "A read-only INTEGER variable."
    ::= { statsForDriver 2 }

  statsMaximumMemoryUsedByDriver OBJECT-TYPE
    SYNTAX INTEGER (0..2147483647)
    ACCESS read-only
    STATUS mandatory
    DESCRIPTION
      "A read-only INTEGER variable."
    ::= { statsForDriver 3 }

  statsPercentCurrentMemoryUsedByDriver OBJECT-TYPE
    SYNTAX INTEGER (0..2147483647)
    ACCESS read-only
    STATUS mandatory
    DESCRIPTION
      "A read-only INTEGER variable."
    ::= { statsForDriver 4 }

  statsPercentMaximumMemoryUsedByDriver OBJECT-TYPE
    SYNTAX INTEGER (0..2147483647)
    ACCESS read-only
    STATUS mandatory
    DESCRIPTION
      "A read-only INTEGER variable."
    ::= { statsForDriver 5 }

  statsTotalMemoryAvailableToTheDriver OBJECT-TYPE
    SYNTAX INTEGER (0..2147483647)
    ACCESS read-only
    STATUS mandatory
    DESCRIPTION
      "A read-only INTEGER variable."
    ::= { statsForDriver 6 }


-- COMPRESSION
  statsBytesIntoCompression OBJECT-TYPE
    SYNTAX INTEGER (0..2147483647)
    ACCESS read-only
    STATUS mandatory
    DESCRIPTION
      "A read-only INTEGER variable."
    ::= { statsForCompression 1 }

  statsBytesOutCompression OBJECT-TYPE
    SYNTAX INTEGER (0..2147483647)
    ACCESS read-only
    STATUS mandatory
    DESCRIPTION
      "A read-only INTEGER variable."
    ::= { statsForCompression 2 }

  statsBytesIntoDecompression OBJECT-TYPE
    SYNTAX INTEGER (0..2147483647)
    ACCESS read-only
    STATUS mandatory
    DESCRIPTION
      "A read-only INTEGER variable."
    ::= { statsForCompression 3 }

  statsBytesOutDecompression OBJECT-TYPE
    SYNTAX INTEGER (0..2147483647)
    ACCESS read-only
    STATUS mandatory
    DESCRIPTION
      "A read-only INTEGER variable."
    ::= { statsForCompression 4 }

-- THRESHOLD

-- PORT
  thresholdPortsInUse OBJECT-TYPE
    SYNTAX INTEGER (0..2147483647)
    ACCESS read-write
    STATUS mandatory
    DESCRIPTION
      "A read-write INTEGER variable."
    ::= { thresholdForPort 1 }

  thresholdMaxPortsUsed OBJECT-TYPE
    SYNTAX INTEGER (0..2147483647)
    ACCESS read-write
    STATUS mandatory
    DESCRIPTION
      "A read-write INTEGER variable."
    ::= { thresholdForPort 2 }

  thresholdPortsInUseIncoming OBJECT-TYPE
    SYNTAX INTEGER (0..2147483647)
    ACCESS read-write
    STATUS mandatory
    DESCRIPTION
      "A read-write INTEGER variable."
    ::= { thresholdForPort 3 }

  thresholdPortsInUseOutgoing OBJECT-TYPE
    SYNTAX INTEGER (0..2147483647)
    ACCESS read-write
    STATUS mandatory
    DESCRIPTION
      "A read-write INTEGER variable."
    ::= { thresholdForPort 4 }

  thresholdOverrallCompressionRatioOfAllPorts OBJECT-TYPE
    SYNTAX INTEGER (0..2147483647)
    ACCESS read-write
    STATUS mandatory
    DESCRIPTION
      "A read-write INTEGER variable."
    ::= { thresholdForPort 5 }

-- CALLS
  thresholdTotalCallsMade OBJECT-TYPE
    SYNTAX INTEGER (0..2147483647)
    ACCESS read-write
    STATUS mandatory
    DESCRIPTION
      "A read-write INTEGER variable."
    ::= { thresholdForCalls 1 }

  thresholdFailedOutgoingCalls OBJECT-TYPE
    SYNTAX INTEGER (0..2147483647)
    ACCESS read-write
    STATUS mandatory
    DESCRIPTION
      "A read-write INTEGER variable."
    ::= { thresholdForCalls 2 }

  thresholdTotalCallsReceivedPerMinute OBJECT-TYPE
    SYNTAX INTEGER (0..2147483647)
    ACCESS read-write
    STATUS mandatory
    DESCRIPTION
      "A read-write INTEGER variable."
    ::= { thresholdForCalls 3 }

  thresholdTotalCallsReceivedPerHour OBJECT-TYPE
    SYNTAX INTEGER (0..2147483647)
    ACCESS read-write
    STATUS mandatory
    DESCRIPTION
      "A read-write INTEGER variable."
    ::= { thresholdForCalls 4 }

  thresholdTotalCallsReceivedPerDay OBJECT-TYPE
    SYNTAX INTEGER (0..2147483647)
    ACCESS read-write
    STATUS mandatory
    DESCRIPTION
      "A read-write INTEGER variable."
    ::= { thresholdForCalls 5 }

  thresholdTotalCallsMadePerMinute OBJECT-TYPE
    SYNTAX INTEGER (0..2147483647)
    ACCESS read-write
    STATUS mandatory
    DESCRIPTION
      "A read-write INTEGER variable."
    ::= { thresholdForCalls 6 }

  thresholdTotalCallsMadePerHour OBJECT-TYPE
    SYNTAX INTEGER (0..2147483647)
    ACCESS read-write
    STATUS mandatory
    DESCRIPTION
      "A read-write INTEGER variable."
    ::= { thresholdForCalls 7 }

  thresholdTotalCallsMadePerDay OBJECT-TYPE
    SYNTAX INTEGER (0..2147483647)
    ACCESS read-write
    STATUS mandatory
    DESCRIPTION
      "A read-write INTEGER variable."
    ::= { thresholdForCalls 8 }

  thresholdTotalCallsReceived OBJECT-TYPE
    SYNTAX INTEGER (0..2147483647)
    ACCESS read-write
    STATUS mandatory
    DESCRIPTION
      "A read-write INTEGER variable."
    ::= { thresholdForCalls 9 }

-- SESSION - GENERAL
  thresholdMaxSessionsUsed OBJECT-TYPE
    SYNTAX INTEGER (0..2147483647)
    ACCESS read-write
    STATUS mandatory
    DESCRIPTION
      "A read-write INTEGER variable."
    ::= { thresholdSessionForGeneral 1 }

  thresholdTotalNumberUserSessionGranted OBJECT-TYPE
    SYNTAX INTEGER (0..2147483647)
    ACCESS read-write
    STATUS mandatory
    DESCRIPTION
      "A read-write INTEGER variable."
    ::= { thresholdSessionForGeneral 2 }

  thresholdTotalNumberUserSessionRefused OBJECT-TYPE
    SYNTAX INTEGER (0..2147483647)
    ACCESS read-write
    STATUS mandatory
    DESCRIPTION
      "A read-write INTEGER variable."
    ::= { thresholdSessionForGeneral 3 }

  thresholdTotalNumberUserSessionsGrantedPerMinute OBJECT-TYPE
    SYNTAX INTEGER (0..2147483647)
    ACCESS read-write
    STATUS mandatory
    DESCRIPTION
      "A read-write INTEGER variable."
    ::= { thresholdSessionForGeneral 4 }

  thresholdTotalNumberUserSessionGrantedPerHour OBJECT-TYPE
    SYNTAX INTEGER (0..2147483647)
    ACCESS read-write
    STATUS mandatory
    DESCRIPTION
      "A read-write INTEGER variable."
    ::= { thresholdSessionForGeneral 5 }

  thresholdTotalNumberUserSessionGrantedPerDay OBJECT-TYPE
    SYNTAX INTEGER (0..2147483647)
    ACCESS read-write
    STATUS mandatory
    DESCRIPTION
      "A read-write INTEGER variable."
    ::= { thresholdSessionForGeneral 6 }

  thresholdTotalNumberUserSessionRefusedPerMinute OBJECT-TYPE
    SYNTAX INTEGER (0..2147483647)
    ACCESS read-write
    STATUS mandatory
    DESCRIPTION
      "A read-write INTEGER variable."
    ::= { thresholdSessionForGeneral 7 }

  thresholdTotalNumberUserSessionRefusedPerHour OBJECT-TYPE
    SYNTAX INTEGER (0..2147483647)
    ACCESS read-write
    STATUS mandatory
    DESCRIPTION
      "A read-write INTEGER variable."
    ::= { thresholdSessionForGeneral 8 }

  thresholdTotalNumberUserSessionRefusedPerDay OBJECT-TYPE
    SYNTAX INTEGER (0..2147483647)
    ACCESS read-write
    STATUS mandatory
    DESCRIPTION
      "A read-write INTEGER variable."
    ::= { thresholdSessionForGeneral 9 }

  thresholdTotalActiveUserSession OBJECT-TYPE
    SYNTAX INTEGER (0..2147483647)
    ACCESS read-write
    STATUS mandatory
    DESCRIPTION
      "A read-write INTEGER variable."
    ::= { thresholdSessionForGeneral 10 }

-- SESSION - APOLLO
  thresholdApolloActiveUserSessions OBJECT-TYPE
    SYNTAX INTEGER (0..2147483647)
    ACCESS read-write
    STATUS mandatory
    DESCRIPTION
      "A read-write INTEGER variable."
    ::= { thresholdSessionForApollo 1 }

  thresholdApolloNumberUserSessionsGranted OBJECT-TYPE
    SYNTAX INTEGER (0..2147483647)
    ACCESS read-write
    STATUS mandatory
    DESCRIPTION
      "A read-write INTEGER variable."
    ::= { thresholdSessionForApollo 2 }

  thresholdApolloNumberUserSessionsrefused OBJECT-TYPE
    SYNTAX INTEGER (0..2147483647)
    ACCESS read-write
    STATUS mandatory
    DESCRIPTION
      "A read-write INTEGER variable."
    ::= { thresholdSessionForApollo 3 }

  thresholdApolloNumberUserSessionsGrantedPerMinute OBJECT-TYPE
    SYNTAX INTEGER (0..2147483647)
    ACCESS read-write
    STATUS mandatory
    DESCRIPTION
      "A read-write INTEGER variable."
    ::= { thresholdSessionForApollo 4 }

  thresholdApolloNumberUserSessionsGrantedPerHour OBJECT-TYPE
    SYNTAX INTEGER (0..2147483647)
    ACCESS read-write
    STATUS mandatory
    DESCRIPTION
      "A read-write INTEGER variable."
    ::= { thresholdSessionForApollo 5 }

  thresholdApolloNumberUserSessionsGrantedPerDay OBJECT-TYPE
    SYNTAX INTEGER (0..2147483647)
    ACCESS read-write
    STATUS mandatory
    DESCRIPTION
      "A read-write INTEGER variable."
    ::= { thresholdSessionForApollo 6 }

  thresholdApolloNumberUserSessionsRefusedPerMinute OBJECT-TYPE
    SYNTAX INTEGER (0..2147483647)
    ACCESS read-write
    STATUS mandatory
    DESCRIPTION
      "A read-write INTEGER variable."
    ::= { thresholdSessionForApollo 7 }

  thresholdApolloNumberUserSessionsRefusedPerHour OBJECT-TYPE
    SYNTAX INTEGER (0..2147483647)
    ACCESS read-write
    STATUS mandatory
    DESCRIPTION
      "A read-write INTEGER variable."
    ::= { thresholdSessionForApollo 8 }

  thresholdApolloNumberUserSessionsRefusedPerDay OBJECT-TYPE
    SYNTAX INTEGER (0..2147483647)
    ACCESS read-write
    STATUS mandatory
    DESCRIPTION
      "A read-write INTEGER variable."
    ::= { thresholdSessionForApollo 9 }

  thresholdApolloMaximumSessionsUsed OBJECT-TYPE
    SYNTAX INTEGER (0..2147483647)
    ACCESS read-write
    STATUS mandatory
    DESCRIPTION
      "A read-write INTEGER variable."
    ::= { thresholdSessionForApollo 10 }

-- SESSION - PPP
  thresholdPPPActiveUserSessions OBJECT-TYPE
    SYNTAX INTEGER (0..2147483647)
    ACCESS read-write
    STATUS mandatory
    DESCRIPTION
      "A read-write INTEGER variable."
    ::= { thresholdSessionForPPP 1 }

  thresholdPPPNumberUserSessionsGranted OBJECT-TYPE
    SYNTAX INTEGER (0..2147483647)
    ACCESS read-write
    STATUS mandatory
    DESCRIPTION
      "A read-write INTEGER variable."
    ::= { thresholdSessionForPPP 2 }

  thresholdPPPNumberUserSessionsRefused OBJECT-TYPE
    SYNTAX INTEGER (0..2147483647)
    ACCESS read-write
    STATUS mandatory
    DESCRIPTION
      "A read-write INTEGER variable."
    ::= { thresholdSessionForPPP 3 }

  thresholdPPPNumberUserSessionsGrantedPerMinute OBJECT-TYPE
    SYNTAX INTEGER (0..2147483647)
    ACCESS read-write
    STATUS mandatory
    DESCRIPTION
      "A read-write INTEGER variable."
    ::= { thresholdSessionForPPP 4 }

  thresholdPPPNumberUserSessionsGrantedPerHour OBJECT-TYPE
    SYNTAX INTEGER (0..2147483647)
    ACCESS read-write
    STATUS mandatory
    DESCRIPTION
      "A read-write INTEGER variable."
    ::= { thresholdSessionForPPP 5 }

  thresholdPPPNumberUserSessionsGrantedPerDay OBJECT-TYPE
    SYNTAX INTEGER (0..2147483647)
    ACCESS read-write
    STATUS mandatory
    DESCRIPTION
      "A read-write INTEGER variable."
    ::= { thresholdSessionForPPP 6 }

  thresholdPPPNumberUserSessionsRefusedPerMinute OBJECT-TYPE
    SYNTAX INTEGER (0..2147483647)
    ACCESS read-write
    STATUS mandatory
    DESCRIPTION
      "A read-write INTEGER variable."
    ::= { thresholdSessionForPPP 7 }

  thresholdPPPNumberUserSessionsRefusedPerHour OBJECT-TYPE
    SYNTAX INTEGER (0..2147483647)
    ACCESS read-write
    STATUS mandatory
    DESCRIPTION
      "A read-write INTEGER variable."
    ::= { thresholdSessionForPPP 8 }

  thresholdPPPNumberUserSessionsRefusedPerDay OBJECT-TYPE
    SYNTAX INTEGER (0..2147483647)
    ACCESS read-write
    STATUS mandatory
    DESCRIPTION
      "A read-write INTEGER variable."
    ::= { thresholdSessionForPPP 9 }

  thresholdPPPMaximumSessionsUsed OBJECT-TYPE
    SYNTAX INTEGER (0..2147483647)
    ACCESS read-write
    STATUS mandatory
    DESCRIPTION
      "A read-write INTEGER variable."
    ::= { thresholdSessionForPPP 10 }

-- DATA
  thresholdNumberBytesReceivedPerSecond OBJECT-TYPE
    SYNTAX INTEGER (0..2147483647)
    ACCESS read-write
    STATUS mandatory
    DESCRIPTION
      "A read-write INTEGER variable."
    ::= { thresholdForData 1 }

  thresholdNumberBytesReceivedPerMinute OBJECT-TYPE
    SYNTAX INTEGER (0..2147483647)
    ACCESS read-write
    STATUS mandatory
    DESCRIPTION
      "A read-write INTEGER variable."
    ::= { thresholdForData 2 }

  thresholdNumberBytesReceivedPerHour OBJECT-TYPE
    SYNTAX INTEGER (0..2147483647)
    ACCESS read-write
    STATUS mandatory
    DESCRIPTION
      "A read-write INTEGER variable."
    ::= { thresholdForData 3 }

  thresholdNumberBytesReceivedPerDay OBJECT-TYPE
    SYNTAX INTEGER (0..2147483647)
    ACCESS read-write
    STATUS mandatory
    DESCRIPTION
      "A read-write INTEGER variable."
    ::= { thresholdForData 4 }

  thresholdNumberBytesTransmittedPerSecond OBJECT-TYPE
    SYNTAX INTEGER (0..2147483647)
    ACCESS read-write
    STATUS mandatory
    DESCRIPTION
      "A read-write INTEGER variable."
    ::= { thresholdForData 5 }

  thresholdNumberBytesTransmittedPerMinute OBJECT-TYPE
    SYNTAX INTEGER (0..2147483647)
    ACCESS read-write
    STATUS mandatory
    DESCRIPTION
      "A read-write INTEGER variable."
    ::= { thresholdForData 6 }

  thresholdNumberBytesTransmittedPerHour OBJECT-TYPE
    SYNTAX INTEGER (0..2147483647)
    ACCESS read-write
    STATUS mandatory
    DESCRIPTION
      "A read-write INTEGER variable."
    ::= { thresholdForData 7 }

  thresholdNumberBytesTransmittedPerDay OBJECT-TYPE
    SYNTAX INTEGER (0..2147483647)
    ACCESS read-write
    STATUS mandatory
    DESCRIPTION
      "A read-write INTEGER variable."
    ::= { thresholdForData 8 }

  thresholdPacketsTransmittedPerMinute OBJECT-TYPE
    SYNTAX INTEGER (0..2147483647)
    ACCESS read-write
    STATUS mandatory
    DESCRIPTION
      "A read-write INTEGER variable."
    ::= { thresholdForData 9 }

  thresholdPacketsTransmittedPerHour OBJECT-TYPE
    SYNTAX INTEGER (0..2147483647)
    ACCESS read-write
    STATUS mandatory
    DESCRIPTION
      "A read-write INTEGER variable."
    ::= { thresholdForData 10 }

  thresholdPacketsTransmittedPerDay OBJECT-TYPE
    SYNTAX INTEGER (0..2147483647)
    ACCESS read-write
    STATUS mandatory
    DESCRIPTION
      "A read-write INTEGER variable."
    ::= { thresholdForData 11 }

  thresholdPacketsReceivedPerMinute OBJECT-TYPE
    SYNTAX INTEGER (0..2147483647)
    ACCESS read-write
    STATUS mandatory
    DESCRIPTION
      "A read-write INTEGER variable."
    ::= { thresholdForData 12 }

  thresholdPacketsReceivedPerHour OBJECT-TYPE
    SYNTAX INTEGER (0..2147483647)
    ACCESS read-write
    STATUS mandatory
    DESCRIPTION
      "A read-write INTEGER variable."
    ::= { thresholdForData 13 }

  thresholdPacketsReceivedPerDay OBJECT-TYPE
    SYNTAX INTEGER (0..2147483647)
    ACCESS read-write
    STATUS mandatory
    DESCRIPTION
      "A read-write INTEGER variable."
    ::= { thresholdForData 14 }

  thresholdPacketReceivedPerSecond OBJECT-TYPE
    SYNTAX INTEGER (0..2147483647)
    ACCESS read-write
    STATUS mandatory
    DESCRIPTION
      "A read-write INTEGER variable."
    ::= { thresholdForData 15 }

  thresholdPacketTransmittedPerSecond OBJECT-TYPE
    SYNTAX INTEGER (0..2147483647)
    ACCESS read-write
    STATUS mandatory
    DESCRIPTION
      "A read-write INTEGER variable."
    ::= { thresholdForData 16 }

  thresholdTotalPacketReceived OBJECT-TYPE
    SYNTAX INTEGER (0..2147483647)
    ACCESS read-write
    STATUS mandatory
    DESCRIPTION
      "A read-write INTEGER variable."
    ::= { thresholdForData 17 }

  thresholdTotalPacketTransmitted OBJECT-TYPE
    SYNTAX INTEGER (0..2147483647)
    ACCESS read-write
    STATUS mandatory
    DESCRIPTION
      "A read-write INTEGER variable."
    ::= { thresholdForData 18 }

  thresholdTotalNumberBytesTransmitted OBJECT-TYPE
    SYNTAX INTEGER (0..2147483647)
    ACCESS read-write
    STATUS mandatory
    DESCRIPTION
      "A read-write INTEGER variable."
    ::= { thresholdForData 19 }

  thresholdTotalNumberBytesReceived OBJECT-TYPE
    SYNTAX INTEGER (0..2147483647)
    ACCESS read-write
    STATUS mandatory
    DESCRIPTION
      "A read-write INTEGER variable."
    ::= { thresholdForData 20 }

-- ERROR
  thresholdTotalNumberReceivedErrors OBJECT-TYPE
    SYNTAX INTEGER (0..2147483647)
    ACCESS read-write
    STATUS mandatory
    DESCRIPTION
      "A read-write INTEGER variable."
    ::= { thresholdForError 1 }

  thresholdTotalNumberTransmitErrors OBJECT-TYPE
    SYNTAX INTEGER (0..2147483647)
    ACCESS read-write
    STATUS mandatory
    DESCRIPTION
      "A read-write INTEGER variable."
    ::= { thresholdForError 2 }

  thresholdTotalNumberReceivedErrorsPerMinute OBJECT-TYPE
    SYNTAX INTEGER (0..2147483647)
    ACCESS read-write
    STATUS mandatory
    DESCRIPTION
      "A read-write INTEGER variable."
    ::= { thresholdForError 3 }

  thresholdTotalNumberReceivedErrorsPerHour OBJECT-TYPE
    SYNTAX INTEGER (0..2147483647)
    ACCESS read-write
    STATUS mandatory
    DESCRIPTION
      "A read-write INTEGER variable."
    ::= { thresholdForError 4 }

  thresholdTotalNumberReceivedErrorsPerDay OBJECT-TYPE
    SYNTAX INTEGER (0..2147483647)
    ACCESS read-write
    STATUS mandatory
    DESCRIPTION
      "A read-write INTEGER variable."
    ::= { thresholdForError 5 }

  thresholdTotalNumberTransmitErrorsPerMinute OBJECT-TYPE
    SYNTAX INTEGER (0..2147483647)
    ACCESS read-write
    STATUS mandatory
    DESCRIPTION
      "A read-write INTEGER variable."
    ::= { thresholdForError 6 }

  thresholdTotalNumberTransmitErrorsPerHour OBJECT-TYPE
    SYNTAX INTEGER (0..2147483647)
    ACCESS read-write
    STATUS mandatory
    DESCRIPTION
      "A read-write INTEGER variable."
    ::= { thresholdForError 7 }

  thresholdTotalNumberTransmitErrorsPerDay OBJECT-TYPE
    SYNTAX INTEGER (0..2147483647)
    ACCESS read-write
    STATUS mandatory
    DESCRIPTION
      "A read-write INTEGER variable."
    ::= { thresholdForError 8 }

  thresholdMaximumErrorRatePerSecond OBJECT-TYPE
    SYNTAX INTEGER (0..2147483647)
    ACCESS read-write
    STATUS mandatory
    DESCRIPTION
      "A read-write INTEGER variable."
    ::= { thresholdForError 9 }

  thresholdTotalErrorRatePerSecond OBJECT-TYPE
    SYNTAX INTEGER (0..2147483647)
    ACCESS read-write
    STATUS mandatory
    DESCRIPTION
      "A read-write INTEGER variable."
    ::= { thresholdForError 10 }

-- DRIVER
  thresholdCurrentClock OBJECT-TYPE
    SYNTAX INTEGER (0..2147483647)
    ACCESS read-write
    STATUS mandatory
    DESCRIPTION
      "A read-write INTEGER variable."
    ::= { thresholdForDriver 1 }

  thresholdCurrentMemoryUsedByDriver OBJECT-TYPE
    SYNTAX INTEGER (0..2147483647)
    ACCESS read-write
    STATUS mandatory
    DESCRIPTION
      "A read-write INTEGER variable."
    ::= { thresholdForDriver 2 }

  thresholdMaximumMemoryUsedByDriver OBJECT-TYPE
    SYNTAX INTEGER (0..2147483647)
    ACCESS read-write
    STATUS mandatory
    DESCRIPTION
      "A read-write INTEGER variable."
    ::= { thresholdForDriver 3 }

  thresholdPercentCurrentMemoryUsedByDriver OBJECT-TYPE
    SYNTAX INTEGER (0..2147483647)
    ACCESS read-write
    STATUS mandatory
    DESCRIPTION
      "A read-write INTEGER variable."
    ::= { thresholdForDriver 4 }

  thresholdPercentMaximumMemoryUsedByDriver OBJECT-TYPE
    SYNTAX INTEGER (0..2147483647)
    ACCESS read-write
    STATUS mandatory
    DESCRIPTION
      "A read-write INTEGER variable."
    ::= { thresholdForDriver 5 }

  thresholdTotalMemoryAvailableToTheDriver OBJECT-TYPE
    SYNTAX INTEGER (0..2147483647)
    ACCESS read-write
    STATUS mandatory
    DESCRIPTION
      "A read-write INTEGER variable."
    ::= { thresholdForDriver 6 }


-- COMPRESSION
  thresholdBytesIntoCompression OBJECT-TYPE
    SYNTAX INTEGER (0..2147483647)
    ACCESS read-write
    STATUS mandatory
    DESCRIPTION
      "A read-write INTEGER variable."
    ::= { thresholdForCompression 1 }

  thresholdBytesOutCompression OBJECT-TYPE
    SYNTAX INTEGER (0..2147483647)
    ACCESS read-write
    STATUS mandatory
    DESCRIPTION
      "A read-write INTEGER variable."
    ::= { thresholdForCompression 2 }

  thresholdBytesIntoDecompression OBJECT-TYPE
    SYNTAX INTEGER (0..2147483647)
    ACCESS read-write
    STATUS mandatory
    DESCRIPTION
      "A read-write INTEGER variable."
    ::= { thresholdForCompression 3 }

  thresholdBytesOutDecompression OBJECT-TYPE
    SYNTAX INTEGER (0..2147483647)
    ACCESS read-write
    STATUS mandatory
    DESCRIPTION
      "A read-write INTEGER variable."
    ::= { thresholdForCompression 4 }

-- TRAPS

-- PORT
  trapsPortsInUse TRAP-TYPE
    ENTERPRISE      apolloTrapsForNT
    DESCRIPTION
      "Trap"
    ::= 1

  trapsMaxPortsUsed TRAP-TYPE
    ENTERPRISE      apolloTrapsForNT
    DESCRIPTION
      "Trap"
    ::= 2

  trapsPortsInUseIncoming TRAP-TYPE
    ENTERPRISE      apolloTrapsForNT
    DESCRIPTION
      "Trap"
    ::= 3

  trapsPortsInUseOutgoing TRAP-TYPE
    ENTERPRISE      apolloTrapsForNT
    DESCRIPTION
      "Trap"
    ::= 4

  trapsOverrallCompressionRatioOfAllPorts TRAP-TYPE
    ENTERPRISE      apolloTrapsForNT
    DESCRIPTION
      "Trap"
    ::= 5

-- CALLS
  trapsTotalCallsMade TRAP-TYPE
    ENTERPRISE      apolloTrapsForNT
    DESCRIPTION
      "Trap"
    ::= 6

  trapsFailedOutgoingCalls TRAP-TYPE
    ENTERPRISE      apolloTrapsForNT
    DESCRIPTION
      "Trap"
    ::= 7

  trapsTotalCallsReceivedPerMinute TRAP-TYPE
    ENTERPRISE      apolloTrapsForNT
    DESCRIPTION
      "Trap"
    ::= 8

  trapsTotalCallsReceivedPerHour TRAP-TYPE
    ENTERPRISE      apolloTrapsForNT
    DESCRIPTION
      "Trap"
    ::= 9

  trapsTotalCallsReceivedPerDay TRAP-TYPE
    ENTERPRISE      apolloTrapsForNT
    DESCRIPTION
      "Trap"
    ::= 10

  trapsTotalCallsMadePerMinute TRAP-TYPE
    ENTERPRISE      apolloTrapsForNT
    DESCRIPTION
      "Trap"
    ::= 11

  trapsTotalCallsMadePerHour TRAP-TYPE
    ENTERPRISE      apolloTrapsForNT
    DESCRIPTION
      "Trap"
    ::= 12

  trapsTotalCallsMadePerDay TRAP-TYPE
    ENTERPRISE      apolloTrapsForNT
    DESCRIPTION
      "Trap"
    ::= 13

  trapsTotalCallsReceived TRAP-TYPE
    ENTERPRISE      apolloTrapsForNT
    DESCRIPTION
      "Trap"
    ::= 14

-- SESSION - GENERAL
  trapsMaxSessionsUsed TRAP-TYPE
    ENTERPRISE      apolloTrapsForNT
    DESCRIPTION
      "Trap"
    ::= 15

  trapsTotalNumberUserSessionGranted TRAP-TYPE
    ENTERPRISE      apolloTrapsForNT
    DESCRIPTION
      "Trap"
    ::= 16

  trapsTotalNumberUserSessionRefused TRAP-TYPE
    ENTERPRISE      apolloTrapsForNT
    DESCRIPTION
      "Trap"
    ::= 17

  trapsTotalNumberUserSessionsGrantedPerMinute TRAP-TYPE
    ENTERPRISE      apolloTrapsForNT
    DESCRIPTION
      "Trap"
    ::= 18

  trapsTotalNumberUserSessionGrantedPerHour TRAP-TYPE
    ENTERPRISE      apolloTrapsForNT
    DESCRIPTION
      "Trap"
    ::= 19

  trapsTotalNumberUserSessionGrantedPerDay TRAP-TYPE
    ENTERPRISE      apolloTrapsForNT
    DESCRIPTION
      "Trap"
    ::= 20

  trapsTotalNumberUserSessionRefusedPerMinute TRAP-TYPE
    ENTERPRISE      apolloTrapsForNT
    DESCRIPTION
      "Trap"
    ::= 21

  trapsTotalNumberUserSessionRefusedPerHour TRAP-TYPE
    ENTERPRISE      apolloTrapsForNT
    DESCRIPTION
      "Trap"
    ::= 22

  trapsTotalNumberUserSessionRefusedPerDay TRAP-TYPE
    ENTERPRISE      apolloTrapsForNT
    DESCRIPTION
      "Trap"
    ::= 23

  trapsTotalActiveUserSession TRAP-TYPE
    ENTERPRISE      apolloTrapsForNT
    DESCRIPTION
      "Trap"
    ::= 24

-- SESSION - APOLLO
  trapsApolloActiveUserSessions TRAP-TYPE
    ENTERPRISE      apolloTrapsForNT
    DESCRIPTION
      "Trap"
    ::= 25

  trapsApolloNumberUserSessionsGranted TRAP-TYPE
    ENTERPRISE      apolloTrapsForNT
    DESCRIPTION
      "Trap"
    ::= 26

  trapsApolloNumberUserSessionsrefused TRAP-TYPE
    ENTERPRISE      apolloTrapsForNT
    DESCRIPTION
      "Trap"
    ::= 27

  trapsApolloNumberUserSessionsGrantedPerMinute TRAP-TYPE
    ENTERPRISE      apolloTrapsForNT
    DESCRIPTION
      "Trap"
    ::= 28

  trapsApolloNumberUserSessionsGrantedPerHour TRAP-TYPE
    ENTERPRISE      apolloTrapsForNT
    DESCRIPTION
      "Trap"
    ::= 29

  trapsApolloNumberUserSessionsGrantedPerDay TRAP-TYPE
    ENTERPRISE      apolloTrapsForNT
    DESCRIPTION
      "Trap"
    ::= 30

  trapsApolloNumberUserSessionsRefusedPerMinute TRAP-TYPE
    ENTERPRISE      apolloTrapsForNT
    DESCRIPTION
      "Trap"
    ::= 31

  trapsApolloNumberUserSessionsRefusedPerHour TRAP-TYPE
    ENTERPRISE      apolloTrapsForNT
    DESCRIPTION
      "Trap"
    ::= 32

  trapsApolloNumberUserSessionsRefusedPerDay TRAP-TYPE
    ENTERPRISE      apolloTrapsForNT
    DESCRIPTION
      "Trap"
    ::= 33

  trapsApolloMaximumSessionsUsed TRAP-TYPE
    ENTERPRISE      apolloTrapsForNT
    DESCRIPTION
      "Trap"
    ::= 34

-- SESSION - PPP
  trapsPPPActiveUserSessions TRAP-TYPE
    ENTERPRISE      apolloTrapsForNT
    DESCRIPTION
      "Trap"
    ::= 35

  trapsPPPNumberUserSessionsGranted TRAP-TYPE
    ENTERPRISE      apolloTrapsForNT
    DESCRIPTION
      "Trap"
    ::= 36

  trapsPPPNumberUserSessionsRefused TRAP-TYPE
    ENTERPRISE      apolloTrapsForNT
    DESCRIPTION
      "Trap"
    ::= 37

  trapsPPPNumberUserSessionsGrantedPerMinute TRAP-TYPE
    ENTERPRISE      apolloTrapsForNT
    DESCRIPTION
      "Trap"
    ::= 38

  trapsPPPNumberUserSessionsGrantedPerHour TRAP-TYPE
    ENTERPRISE      apolloTrapsForNT
    DESCRIPTION
      "Trap"
    ::= 39

  trapsPPPNumberUserSessionsGrantedPerDay TRAP-TYPE
    ENTERPRISE      apolloTrapsForNT
    DESCRIPTION
      "Trap"
    ::= 40

  trapsPPPNumberUserSessionsRefusedPerMinute TRAP-TYPE
    ENTERPRISE      apolloTrapsForNT
    DESCRIPTION
      "Trap"
    ::= 41

  trapsPPPNumberUserSessionsRefusedPerHour TRAP-TYPE
    ENTERPRISE      apolloTrapsForNT
    DESCRIPTION
      "Trap"
    ::= 42

  trapsPPPNumberUserSessionsRefusedPerDay TRAP-TYPE
    ENTERPRISE      apolloTrapsForNT
    DESCRIPTION
      "Trap"
    ::= 43

  trapsPPPMaximumSessionsUsed TRAP-TYPE
    ENTERPRISE      apolloTrapsForNT
    DESCRIPTION
      "Trap"
    ::= 44

-- DATA
  trapsNumberBytesReceivedPerSecond TRAP-TYPE
    ENTERPRISE      apolloTrapsForNT
    DESCRIPTION
      "Trap"
    ::= 45

  trapsNumberBytesReceivedPerMinute TRAP-TYPE
    ENTERPRISE      apolloTrapsForNT
    DESCRIPTION
      "Trap"
    ::= 46

  trapsNumberBytesReceivedPerHour TRAP-TYPE
    ENTERPRISE      apolloTrapsForNT
    DESCRIPTION
      "Trap"
    ::= 47

  trapsNumberBytesReceivedPerDay TRAP-TYPE
    ENTERPRISE      apolloTrapsForNT
    DESCRIPTION
      "Trap"
    ::= 48

  trapsNumberBytesTransmittedPerSecond TRAP-TYPE
    ENTERPRISE      apolloTrapsForNT
    DESCRIPTION
      "Trap"
    ::= 49

  trapsNumberBytesTransmittedPerMinute TRAP-TYPE
    ENTERPRISE      apolloTrapsForNT
    DESCRIPTION
      "Trap"
    ::= 50

  trapsNumberBytesTransmittedPerHour TRAP-TYPE
    ENTERPRISE      apolloTrapsForNT
    DESCRIPTION
      "Trap"
    ::= 51

  trapsNumberBytesTransmittedPerDay TRAP-TYPE
    ENTERPRISE      apolloTrapsForNT
    DESCRIPTION
      "Trap"
    ::= 52

  trapsPacketsTransmittedPerMinute TRAP-TYPE
    ENTERPRISE      apolloTrapsForNT
    DESCRIPTION
      "Trap"
    ::= 53

  trapsPacketsTransmittedPerHour TRAP-TYPE
    ENTERPRISE      apolloTrapsForNT
    DESCRIPTION
      "Trap"
    ::= 54

  trapsPacketsTransmittedPerDay TRAP-TYPE
    ENTERPRISE      apolloTrapsForNT
    DESCRIPTION
      "Trap"
    ::= 55

  trapsPacketsReceivedPerMinute TRAP-TYPE
    ENTERPRISE      apolloTrapsForNT
    DESCRIPTION
      "Trap"
    ::= 56

  trapsPacketsReceivedPerHour TRAP-TYPE
    ENTERPRISE      apolloTrapsForNT
    DESCRIPTION
      "Trap"
    ::= 57

  trapsPacketsReceivedPerDay TRAP-TYPE
    ENTERPRISE      apolloTrapsForNT
    DESCRIPTION
      "Trap"
    ::= 58

  trapsPacketReceivedPerSecond TRAP-TYPE
    ENTERPRISE      apolloTrapsForNT
    DESCRIPTION
      "Trap"
    ::= 59

  trapsPacketTransmittedPerSecond TRAP-TYPE
    ENTERPRISE      apolloTrapsForNT
    DESCRIPTION
      "Trap"
    ::= 60

  trapsTotalPacketReceived TRAP-TYPE
    ENTERPRISE      apolloTrapsForNT
    DESCRIPTION
      "Trap"
    ::= 61

  trapsTotalPacketTransmitted TRAP-TYPE
    ENTERPRISE      apolloTrapsForNT
    DESCRIPTION
      "Trap"
    ::= 62

  trapsTotalNumberBytesTransmitted TRAP-TYPE
    ENTERPRISE      apolloTrapsForNT
    DESCRIPTION
      "Trap"
    ::= 63

  trapsTotalNumberBytesReceived TRAP-TYPE
    ENTERPRISE      apolloTrapsForNT
    DESCRIPTION
      "Trap"
    ::= 64

-- ERROR
  trapsTotalNumberReceivedErrors TRAP-TYPE
    ENTERPRISE      apolloTrapsForNT
    DESCRIPTION
      "Trap"
    ::= 65

  trapsTotalNumberTransmitErrors TRAP-TYPE
    ENTERPRISE      apolloTrapsForNT
    DESCRIPTION
      "Trap"
    ::= 66
  trapsTotalNumberReceivedErrorsPerMinute TRAP-TYPE
    ENTERPRISE      apolloTrapsForNT
    DESCRIPTION
      "Trap"
    ::= 67

  trapsTotalNumberReceivedErrorsPerHour TRAP-TYPE
    ENTERPRISE      apolloTrapsForNT
    DESCRIPTION
      "Trap"
    ::= 68

  trapsTotalNumberReceivedErrorsPerDay TRAP-TYPE
    ENTERPRISE      apolloTrapsForNT
    DESCRIPTION
      "Trap"
    ::= 69

  trapsTotalNumberTransmitErrorsPerMinute TRAP-TYPE
    ENTERPRISE      apolloTrapsForNT
    DESCRIPTION
      "Trap"
    ::= 70

  trapsTotalNumberTransmitErrorsPerHour TRAP-TYPE
    ENTERPRISE      apolloTrapsForNT
    DESCRIPTION
      "Trap"
    ::= 71

  trapsTotalNumberTransmitErrorsPerDay TRAP-TYPE
    ENTERPRISE      apolloTrapsForNT
    DESCRIPTION
      "Trap"
    ::= 72

  trapsMaximumErrorRatePerSecond TRAP-TYPE
    ENTERPRISE      apolloTrapsForNT
    DESCRIPTION
      "Trap"
    ::= 73

  trapsTotalErrorRatePerSecond TRAP-TYPE
    ENTERPRISE      apolloTrapsForNT
    DESCRIPTION
      "Trap"
    ::= 74

-- DRIVER
  trapsCurrentClock TRAP-TYPE
    ENTERPRISE      apolloTrapsForNT
    DESCRIPTION
      "Trap"
    ::= 75

  trapsCurrentMemoryUsedByDriver TRAP-TYPE
    ENTERPRISE      apolloTrapsForNT
    DESCRIPTION
      "Trap"
    ::= 76

  trapsMaximumMemoryUsedByDriver TRAP-TYPE
    ENTERPRISE      apolloTrapsForNT
    DESCRIPTION
      "Trap"
    ::= 77

  trapsPercentCurrentMemoryUsedByDriver TRAP-TYPE
    ENTERPRISE      apolloTrapsForNT
    DESCRIPTION
      "Trap"
    ::= 78

  trapsPercentMaximumMemoryUsedByDriver TRAP-TYPE
    ENTERPRISE      apolloTrapsForNT
    DESCRIPTION
      "Trap"
    ::= 79

  trapsTotalMemoryAvailableToTheDriver TRAP-TYPE
    ENTERPRISE      apolloTrapsForNT
    DESCRIPTION
      "Trap"
    ::= 80

-- COMPRESSION
  trapsBytesIntoCompression TRAP-TYPE
    ENTERPRISE      apolloTrapsForNT
    DESCRIPTION
      "Trap"
    ::= 81

  trapsBytesOutCompression TRAP-TYPE
    ENTERPRISE      apolloTrapsForNT
    DESCRIPTION
      "Trap"
    ::= 82

  trapsBytesIntoDecompression TRAP-TYPE
    ENTERPRISE      apolloTrapsForNT
    DESCRIPTION
      "Trap"
    ::= 83

  trapsBytesOutDecompression TRAP-TYPE
    ENTERPRISE      apolloTrapsForNT
    DESCRIPTION
      "Trap"
    ::= 84

    END
