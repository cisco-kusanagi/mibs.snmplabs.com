HHMSSMALL-MIB DEFINITIONS ::= BEGIN

IMPORTS
	OBJECT-TYPE
		FROM SNMPv2-SMI
	TRAP-TYPE
		FROM RFC-1215
;


            internet      OBJECT IDENTIFIER ::= { iso org(3) dod(6) 1 }
            directory     OBJECT IDENTIFIER ::= { internet 1 }
            mgmt          OBJECT IDENTIFIER ::= { internet 2 }
            experimental  OBJECT IDENTIFIER ::= { internet 3 }
            private       OBJECT IDENTIFIER ::= { internet 4 }
            enterprises   OBJECT IDENTIFIER ::= { private 1 }

            DisplayString ::= OCTET STRING


   akcp	OBJECT IDENTIFIER ::= { enterprises 3854 }
   hhmsagent	OBJECT IDENTIFIER ::= { akcp 1 }

      hhmsSensor OBJECT IDENTIFIER  ::=  {  hhmsagent 2 }

         hhmsSensorArray OBJECT IDENTIFIER  ::=  {  hhmsSensor 2 }
   
            hhmsSensorArrayEntry OBJECT IDENTIFIER  ::=  {  hhmsSensorArray 1 }

               hhmsSensorArrayTemp OBJECT IDENTIFIER  ::=  {  hhmsSensorArrayEntry 16 }

                  hhmsSensorArrayTempEntry OBJECT IDENTIFIER  ::=  {  hhmsSensorArrayTemp 1 }

                  hhmsSensorArrayTempDegree OBJECT-TYPE
                     SYNTAX  INTEGER
                     ACCESS  read-only
                     STATUS  mandatory
                     DESCRIPTION
                     "The degrees in this sensor"
                     ::=  {  hhmsSensorArrayTempEntry 3   }

                  hhmsSensorArrayTempStatus OBJECT-TYPE
                     SYNTAX  INTEGER {
		      	      noStatus(1),
			            normal(2),
			            highWarning(3),
			            highCritical(4),
   			         lowWarning(5),
   	   		      lowCritical(6),
	   	   	      sensorError(7)
                     }
                     ACCESS  read-only
                     STATUS  mandatory
                     DESCRIPTION
                     "The current status of this Sensor"
                     ::=  {  hhmsSensorArrayTempEntry 4   }
      

               hhmsSensorArrayHumidity OBJECT IDENTIFIER  ::=  {  hhmsSensorArrayEntry 17 }

                  hhmsSensorArrayHumidityEntry OBJECT IDENTIFIER  ::=  {  hhmsSensorArrayHumidity 1 }

                  hhmsSensorArrayHumidityPercent OBJECT-TYPE
                     SYNTAX  INTEGER
                     ACCESS  read-only
                     STATUS  mandatory
                     DESCRIPTION
                     "The relative humidity percentage measured by this sensor"
                     ::=  {  hhmsSensorArrayHumidityEntry 3   }

                  hhmsSensorArrayHumidityStatus OBJECT-TYPE
                     SYNTAX  INTEGER {
                     noStatus(1),
			            normal(2),
			            highWarning(3),
			            highCritical(4),
                     lowWarning(5),
                     lowCritical(6),
                     sensorError(7)
                     }
                     ACCESS  read-only
                     STATUS  mandatory
                     DESCRIPTION
                     "The current status of this Sensor"
                     ::=  {  hhmsSensorArrayHumidityEntry 4   }

               hhmsSensorArraySwitch OBJECT IDENTIFIER  ::=  {  hhmsSensorArrayEntry 18 }

                  hhmsSensorArraySwitchEntry OBJECT IDENTIFIER  ::=  {  hhmsSensorArraySwitch 1 }

                  hhmsSensorArraySwitchStatus OBJECT-TYPE
                     SYNTAX  INTEGER {
		      	      noStatus(1),
			            normal(2),
			            critical(4),
	   	   	      sensorError(7)
                     }
                     ACCESS  read-only
                     STATUS  mandatory
                     DESCRIPTION
                     "The current status of this Sensor, only input switches have a status"
                     ::=  {  hhmsSensorArraySwitchEntry 3  }

--
-- Varbinds used in TRAP Definitions
--

      hhmsAgentTraps      OBJECT IDENTIFIER  ::=  {  hhmsagent 7   }

      hhmsSensorStatus OBJECT-TYPE
            SYNTAX  INTEGER {
               noStatus(1),
               normal(2),
               highWarning(3),
               highCritical(4),
               lowWarning(5),
               lowCritical(6),
               sensorError(7)
				}
         ACCESS  read-only
         STATUS  mandatory
         DESCRIPTION
         "The current integer status of the sensor causing this trap to be sent"
         ::=  {  hhmsAgentTraps 1  }
      
      hhmsSensorValue OBJECT-TYPE
         SYNTAX  INTEGER
         ACCESS  read-only
         STATUS  mandatory
         DESCRIPTION
         "The current integer value of the sensor causing this trap to be sent"
         ::=  {  hhmsAgentTraps 2  }
      
      hhmsSensorLevelExceeded OBJECT-TYPE
         SYNTAX  INTEGER
         ACCESS  read-only
         STATUS  mandatory
         DESCRIPTION
         "The integer level that was exceeded causing this trap to be sent"
         ::=  {  hhmsAgentTraps 3  }
      

      hhmsSensorIndex OBJECT-TYPE
         SYNTAX  INTEGER
         ACCESS  read-only
         STATUS  mandatory
         DESCRIPTION
         "The integer index of the sensor causing this trap to be sent"
         ::=  {  hhmsAgentTraps 4  }
      

      hhmsSensorName OBJECT-TYPE
         SYNTAX  DisplayString
         ACCESS  read-only
         STATUS  mandatory
         DESCRIPTION
         "The name of the sensor causing this trap to be sent"
         ::=  {  hhmsAgentTraps 5  }
      
      hhmsSensorDescription OBJECT-TYPE
         SYNTAX  DisplayString
         ACCESS  read-only
         STATUS  mandatory
         DESCRIPTION
         "The description of the sensor causing this trap to be sent"
         ::=  {  hhmsAgentTraps 6  }
      

-- TRAP Definitions


	hhmsUnknownStatus TRAP-TYPE
		ENTERPRISE hhmsagent
		DESCRIPTION
			"hhmsagent status went to Unknown"
		::= 0

	hhmsNormalStatus TRAP-TYPE
		ENTERPRISE hhmsagent
		DESCRIPTION
			"hhmsagent status is Normal"
		::= 1

	hhmsWarningStatus TRAP-TYPE
		ENTERPRISE hhmsagent
		DESCRIPTION
			"hhmsagent status went to Warning"
		::= 2

	hhmsCriticalStatus TRAP-TYPE
		ENTERPRISE hhmsagent
		DESCRIPTION
			"hhmsagent status went to Critical"
		::= 3

	hhmsDownStatus TRAP-TYPE
		ENTERPRISE hhmsagent
		DESCRIPTION
			"hhmsagent status went to Disabled"
		::= 4

	hhmsTemperatureStatus TRAP-TYPE
		ENTERPRISE hhmsagent
		VARIABLES
			{ hhmsSensorStatus, hhmsSensorValue, hhmsSensorLevelExceeded, 
         hhmsSensorIndex, hhmsSensorName, hhmsSensorDescription }
		DESCRIPTION
			"Temperature sensor trap"
		::= 10

	hhmsHumidityStatus TRAP-TYPE
		ENTERPRISE hhmsagent
		VARIABLES
			{ hhmsSensorStatus, hhmsSensorValue, hhmsSensorLevelExceeded, 
         hhmsSensorIndex, hhmsSensorName, hhmsSensorDescription }
		DESCRIPTION
			"Humidity sensor trap"
		::= 20

	hhmsSwitchStatus TRAP-TYPE
		ENTERPRISE hhmsagent
		VARIABLES
			{ hhmsSensorStatus, hhmsSensorValue, hhmsSensorLevelExceeded, 
         hhmsSensorIndex, hhmsSensorName, hhmsSensorDescription }
		DESCRIPTION
			"Switch sensor trap"
		::= 30

END
