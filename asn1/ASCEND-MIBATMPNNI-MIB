--			Ascend mibatmpnni MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBATMPNNI-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibpnniSummaryAddrEntry  OBJECT IDENTIFIER ::= { configuration 44}
    mibpnniRouteTnsConfig  OBJECT IDENTIFIER ::= { configuration 50}
    mibpnniNodeConfig  OBJECT IDENTIFIER ::= { configuration 43}
    mibpnniDTLConfig  OBJECT IDENTIFIER ::= { configuration 48}
    mibpnniIfConfig  OBJECT IDENTIFIER ::= { configuration 45}
    mibpnniRouteNodeConfig  OBJECT IDENTIFIER ::= { configuration 47}
    mibpnniRouteAddrConfig  OBJECT IDENTIFIER ::= { configuration 49}
    mibpnniMetricsConfig  OBJECT IDENTIFIER ::= { configuration 46}

	-- The mibpnniSummaryAddrEntry table
	--
	-- This table contains parameters for the mibpnniSummaryAddrEntry profile
	--

    mibpnniSummaryAddrEntryTable	OBJECT-TYPE
	SYNTAX		SEQUENCE OF MibpnniSummaryAddrEntryEntry
	ACCESS		not-accessible
	STATUS		mandatory
	DESCRIPTION	"A list of mibpnniSummaryAddrEntry profile entries."
	::= { mibpnniSummaryAddrEntry 1 }

    mibpnniSummaryAddrEntryEntry	OBJECT-TYPE
	SYNTAX		MibpnniSummaryAddrEntryEntry
	ACCESS		not-accessible
	STATUS		mandatory
	DESCRIPTION	"A mibpnniSummaryAddrEntry entry containing objects that
			 maps to the parameters of mibpnniSummaryAddrEntry profile."
	INDEX		{ pnniSummaryAddrEntry-IndexName }
	::= { mibpnniSummaryAddrEntryTable 1 }

    MibpnniSummaryAddrEntryEntry ::=
	SEQUENCE {
	    pnniSummaryAddrEntry-IndexName
		DisplayString,
	    pnniSummaryAddrEntry-AddrIndex-NodeIndex
		INTEGER,
	    pnniSummaryAddrEntry-AddrIndex-Type
		INTEGER,
	    pnniSummaryAddrEntry-AddrIndex-Address
		DisplayString,
	    pnniSummaryAddrEntry-AddrIndex-PrefixLen
		INTEGER,
	    pnniSummaryAddrEntry-Suppress
		INTEGER,
	    pnniSummaryAddrEntry-State
		INTEGER,
	    pnniSummaryAddrEntry-Active
		INTEGER,
	    pnniSummaryAddrEntry-Action-o
		INTEGER
	}

    pnniSummaryAddrEntry-IndexName	OBJECT-TYPE
	SYNTAX	DisplayString
	ACCESS	read-only
	STATUS	mandatory
	DESCRIPTION	"The name of this profile which is corresponding to the value of the summary-addr-index."
	::= { mibpnniSummaryAddrEntryEntry 1 }

    pnniSummaryAddrEntry-AddrIndex-NodeIndex	OBJECT-TYPE
	SYNTAX	INTEGER
	ACCESS	read-write
	STATUS	mandatory
	DESCRIPTION	"The node index. "
	::= { mibpnniSummaryAddrEntryEntry 2 }

    pnniSummaryAddrEntry-AddrIndex-Type	OBJECT-TYPE
	SYNTAX	INTEGER {
		    internalSummary (2),
		    externalSummary (3)
		}
	ACCESS	read-write
	STATUS	mandatory
	DESCRIPTION	"The type (e.g. internal or exterior) of summary being described."
	::= { mibpnniSummaryAddrEntryEntry 3 }

    pnniSummaryAddrEntry-AddrIndex-Address	OBJECT-TYPE
	SYNTAX	DisplayString
	ACCESS	read-write
	STATUS	mandatory
	DESCRIPTION	"The ATM End System Address prefix for the summary."
	::= { mibpnniSummaryAddrEntryEntry 4 }

    pnniSummaryAddrEntry-AddrIndex-PrefixLen	OBJECT-TYPE
	SYNTAX	INTEGER
	ACCESS	read-write
	STATUS	mandatory
	DESCRIPTION	"The prefix length for the summary."
	::= { mibpnniSummaryAddrEntryEntry 5 }

    pnniSummaryAddrEntry-Suppress	OBJECT-TYPE
	SYNTAX	INTEGER {
		    true (2),
		    false (3)
		}
	ACCESS	read-write
	STATUS	mandatory
	DESCRIPTION	"Determines what is done with addresses that are being summarized by the instance. The default value (e.g. false) will indicate that the summary should propagate into the peer group. Network Management will be able to set the value of this attribute to `suppress' (e.g. true), which suppresses the summary and any reachable addresses it summarizes from being advertised into the peer group."
	::= { mibpnniSummaryAddrEntryEntry 6 }

    pnniSummaryAddrEntry-State	OBJECT-TYPE
	SYNTAX	INTEGER {
		    advertising (2),
		    suppressing (3),
		    inactive (4)
		}
	ACCESS	read-only
	STATUS	mandatory
	DESCRIPTION	"Indicates whether the summary is currently being advertised by the node within the local switching system into its peer group."
	::= { mibpnniSummaryAddrEntryEntry 7 }

    pnniSummaryAddrEntry-Active	OBJECT-TYPE
	SYNTAX	INTEGER {
		    no (1),
		    yes (2)
		}
	ACCESS	read-write
	STATUS	mandatory
	DESCRIPTION	"The state of this summary address entry."
	::= { mibpnniSummaryAddrEntryEntry 8 }

    pnniSummaryAddrEntry-Action-o	OBJECT-TYPE
	SYNTAX	INTEGER {
		    noAction (1),
		    createProfile (2),
		    deleteProfile (3)
		}
	ACCESS	read-write
	STATUS	mandatory
	DESCRIPTION	""
	::= { mibpnniSummaryAddrEntryEntry 9 }


	-- The mibpnniRouteTnsConfig table
	--
	-- This table contains parameters for the mibpnniRouteTnsConfig profile
	--

    mibpnniRouteTnsConfigTable	OBJECT-TYPE
	SYNTAX		SEQUENCE OF MibpnniRouteTnsConfigEntry
	ACCESS		not-accessible
	STATUS		mandatory
	DESCRIPTION	"A list of mibpnniRouteTnsConfig profile entries."
	::= { mibpnniRouteTnsConfig 1 }

    mibpnniRouteTnsConfigEntry	OBJECT-TYPE
	SYNTAX		MibpnniRouteTnsConfigEntry
	ACCESS		not-accessible
	STATUS		mandatory
	DESCRIPTION	"A mibpnniRouteTnsConfig entry containing objects that
			 maps to the parameters of mibpnniRouteTnsConfig profile."
	INDEX		{ pnniRouteTnsConfig-TnsIndex-NodeIndex, pnniRouteTnsConfig-TnsIndex-RouteTnsType, pnniRouteTnsConfig-TnsIndex-RouteTnsPlan, pnniRouteTnsConfig-TnsIndex-RouteTnsId, pnniRouteTnsConfig-TnsIndex-RouteTnsIndex }
	::= { mibpnniRouteTnsConfigTable 1 }

    MibpnniRouteTnsConfigEntry ::=
	SEQUENCE {
	    pnniRouteTnsConfig-TnsIndex-NodeIndex
		INTEGER,
	    pnniRouteTnsConfig-TnsIndex-RouteTnsType
		INTEGER,
	    pnniRouteTnsConfig-TnsIndex-RouteTnsPlan
		INTEGER,
	    pnniRouteTnsConfig-TnsIndex-RouteTnsId
		DisplayString,
	    pnniRouteTnsConfig-TnsIndex-RouteTnsIndex
		INTEGER,
	    pnniRouteTnsConfig-TnsIfIndex
		INTEGER,
	    pnniRouteTnsConfig-TnsAdvertisingNodeId
		DisplayString,
	    pnniRouteTnsConfig-TnsAdvertisedPortId
		INTEGER,
	    pnniRouteTnsConfig-TnsRouteType
		INTEGER,
	    pnniRouteTnsConfig-TnsPnniScope
		INTEGER,
	    pnniRouteTnsConfig-TnsVpCapability
		INTEGER,
	    pnniRouteTnsConfig-TnsMetricsTag
		INTEGER,
	    pnniRouteTnsConfig-TnsOriginateAdvertisement
		INTEGER,
	    pnniRouteTnsConfig-Active
		INTEGER,
	    pnniRouteTnsConfig-Action-o
		INTEGER
	}

    pnniRouteTnsConfig-TnsIndex-NodeIndex	OBJECT-TYPE
	SYNTAX	INTEGER
	ACCESS	read-only
	STATUS	mandatory
	DESCRIPTION	"Index that identifies a logical PNNI node."
	::= { mibpnniRouteTnsConfigEntry 1 }

    pnniRouteTnsConfig-TnsIndex-RouteTnsType	OBJECT-TYPE
	SYNTAX	INTEGER
	ACCESS	read-only
	STATUS	mandatory
	DESCRIPTION	"The type of network identification used for this transit network."
	::= { mibpnniRouteTnsConfigEntry 2 }

    pnniRouteTnsConfig-TnsIndex-RouteTnsPlan	OBJECT-TYPE
	SYNTAX	INTEGER
	ACCESS	read-only
	STATUS	mandatory
	DESCRIPTION	"The network identification plan according to which network id has been assigned."
	::= { mibpnniRouteTnsConfigEntry 3 }

    pnniRouteTnsConfig-TnsIndex-RouteTnsId	OBJECT-TYPE
	SYNTAX	DisplayString
	ACCESS	read-only
	STATUS	mandatory
	DESCRIPTION	"The value of the transit network identifier."
	::= { mibpnniRouteTnsConfigEntry 4 }

    pnniRouteTnsConfig-TnsIndex-RouteTnsIndex	OBJECT-TYPE
	SYNTAX	INTEGER
	ACCESS	read-only
	STATUS	mandatory
	DESCRIPTION	"An index into the set of listings of connectivity to a given transit network from a given local node."
	::= { mibpnniRouteTnsConfigEntry 5 }

    pnniRouteTnsConfig-TnsIfIndex	OBJECT-TYPE
	SYNTAX	INTEGER
	ACCESS	read-write
	STATUS	mandatory
	DESCRIPTION	"The local interface over which the transit network can be reached."
	::= { mibpnniRouteTnsConfigEntry 6 }

    pnniRouteTnsConfig-TnsAdvertisingNodeId	OBJECT-TYPE
	SYNTAX	DisplayString
	ACCESS	read-write
	STATUS	mandatory
	DESCRIPTION	"The node ID of a node advertising reachability to the transit network."
	::= { mibpnniRouteTnsConfigEntry 7 }

    pnniRouteTnsConfig-TnsAdvertisedPortId	OBJECT-TYPE
	SYNTAX	INTEGER
	ACCESS	read-write
	STATUS	mandatory
	DESCRIPTION	"The port identifier used from the advertising node to reach the given transit network."
	::= { mibpnniRouteTnsConfigEntry 8 }

    pnniRouteTnsConfig-TnsRouteType	OBJECT-TYPE
	SYNTAX	INTEGER {
		    other (2),
		    exterior (5)
		}
	ACCESS	read-write
	STATUS	mandatory
	DESCRIPTION	"The type (e.g. exterior or other) of reachability from the advertising node to the transit network."
	::= { mibpnniRouteTnsConfigEntry 9 }

    pnniRouteTnsConfig-TnsPnniScope	OBJECT-TYPE
	SYNTAX	INTEGER
	ACCESS	read-write
	STATUS	mandatory
	DESCRIPTION	"The PNNI scope of advertisement (i.e. level of PNNI hierarchy) of the reachability from the advertising node to the transit network."
	::= { mibpnniRouteTnsConfigEntry 10 }

    pnniRouteTnsConfig-TnsVpCapability	OBJECT-TYPE
	SYNTAX	INTEGER {
		    true (2),
		    false (3)
		}
	ACCESS	read-write
	STATUS	mandatory
	DESCRIPTION	"Indicates whether VPCs can be established from the advertising node to the reachable transit network."
	::= { mibpnniRouteTnsConfigEntry 11 }

    pnniRouteTnsConfig-TnsMetricsTag	OBJECT-TYPE
	SYNTAX	INTEGER
	ACCESS	read-write
	STATUS	mandatory
	DESCRIPTION	"The index into the pnniMetricsTable for the traffic parameter values that apply for the connectivity from the advertising node to the transit network."
	::= { mibpnniRouteTnsConfigEntry 12 }

    pnniRouteTnsConfig-TnsOriginateAdvertisement	OBJECT-TYPE
	SYNTAX	INTEGER {
		    true (2),
		    false (3)
		}
	ACCESS	read-write
	STATUS	mandatory
	DESCRIPTION	"Whether or not the transit network specified by this entry is to be advertised by the local node into its PNNI routing domain."
	::= { mibpnniRouteTnsConfigEntry 13 }

    pnniRouteTnsConfig-Active	OBJECT-TYPE
	SYNTAX	INTEGER {
		    no (1),
		    yes (2)
		}
	ACCESS	read-write
	STATUS	mandatory
	DESCRIPTION	"The current state of this route TNS entry."
	::= { mibpnniRouteTnsConfigEntry 14 }

    pnniRouteTnsConfig-Action-o	OBJECT-TYPE
	SYNTAX	INTEGER {
		    noAction (1),
		    createProfile (2),
		    deleteProfile (3)
		}
	ACCESS	read-write
	STATUS	mandatory
	DESCRIPTION	""
	::= { mibpnniRouteTnsConfigEntry 15 }


	-- The mibpnniNodeConfig table
	--
	-- This table contains parameters for the mibpnniNodeConfig profile
	--

    mibpnniNodeConfigTable	OBJECT-TYPE
	SYNTAX		SEQUENCE OF MibpnniNodeConfigEntry
	ACCESS		not-accessible
	STATUS		mandatory
	DESCRIPTION	"A list of mibpnniNodeConfig profile entries."
	::= { mibpnniNodeConfig 1 }

    mibpnniNodeConfigEntry	OBJECT-TYPE
	SYNTAX		MibpnniNodeConfigEntry
	ACCESS		not-accessible
	STATUS		mandatory
	DESCRIPTION	"A mibpnniNodeConfig entry containing objects that
			 maps to the parameters of mibpnniNodeConfig profile."
	INDEX		{ pnniNodeConfig-NodeIndex }
	::= { mibpnniNodeConfigTable 1 }

    MibpnniNodeConfigEntry ::=
	SEQUENCE {
	    pnniNodeConfig-NodeIndex
		INTEGER,
	    pnniNodeConfig-NodeLevel
		INTEGER,
	    pnniNodeConfig-NodeId
		DisplayString,
	    pnniNodeConfig-CurrNodeId
		DisplayString,
	    pnniNodeConfig-NodeLowest
		INTEGER,
	    pnniNodeConfig-NodeAdminStatus
		INTEGER,
	    pnniNodeConfig-NodeDomainName
		DisplayString,
	    pnniNodeConfig-NodeAtmAddress
		DisplayString,
	    pnniNodeConfig-NodePeerGroupId
		DisplayString,
	    pnniNodeConfig-CurrNodePeerGroupId
		DisplayString,
	    pnniNodeConfig-NodeRestrictedTransit
		INTEGER,
	    pnniNodeConfig-NodeComplexRep
		INTEGER,
	    pnniNodeConfig-NodePgl-LeadershipPriority
		INTEGER,
	    pnniNodeConfig-NodePgl-ParentNodeIndex
		INTEGER,
	    pnniNodeConfig-NodePgl-InitTime
		INTEGER,
	    pnniNodeConfig-NodePgl-OverrideDelay
		INTEGER,
	    pnniNodeConfig-NodePgl-ReelectTime
		INTEGER,
	    pnniNodeConfig-NodeTimer-PtseHolddown
		INTEGER,
	    pnniNodeConfig-NodeTimer-HelloHolddown
		INTEGER,
	    pnniNodeConfig-NodeTimer-HelloInterval
		INTEGER,
	    pnniNodeConfig-NodeTimer-HelloInactivityFactor
		INTEGER,
	    pnniNodeConfig-NodeTimer-HlinkInact
		INTEGER,
	    pnniNodeConfig-NodeTimer-PtseRefreshInterval
		INTEGER,
	    pnniNodeConfig-NodeTimer-PtseLifetimeFactor
		INTEGER,
	    pnniNodeConfig-NodeTimer-RxmtInterval
		INTEGER,
	    pnniNodeConfig-NodeTimer-PeerDelayedAckInterval
		INTEGER,
	    pnniNodeConfig-NodeTimer-AvcrPm
		INTEGER,
	    pnniNodeConfig-NodeTimer-AvcrMt
		INTEGER,
	    pnniNodeConfig-NodeTimer-CdvPm
		INTEGER,
	    pnniNodeConfig-NodeTimer-CtdPm
		INTEGER,
	    pnniNodeConfig-NodeSvccRcc-InitTime
		INTEGER,
	    pnniNodeConfig-NodeSvccRcc-RetryTime
		INTEGER,
	    pnniNodeConfig-NodeSvccRcc-CallingIntegrityTime
		INTEGER,
	    pnniNodeConfig-NodeSvccRcc-CalledIntegrityTime
		INTEGER,
	    pnniNodeConfig-NodeSvccRcc-TrafficDescrIndex
		INTEGER,
	    pnniNodeConfig-NodeScopeMapping-LocalNet
		INTEGER,
	    pnniNodeConfig-NodeScopeMapping-LocalNetPlus1
		INTEGER,
	    pnniNodeConfig-NodeScopeMapping-LocalNetPlus2
		INTEGER,
	    pnniNodeConfig-NodeScopeMapping-SiteMinus1
		INTEGER,
	    pnniNodeConfig-NodeScopeMapping-IntraSite
		INTEGER,
	    pnniNodeConfig-NodeScopeMapping-SitePlus1
		INTEGER,
	    pnniNodeConfig-NodeScopeMapping-OrganizationMinus1
		INTEGER,
	    pnniNodeConfig-NodeScopeMapping-IntraOrganization
		INTEGER,
	    pnniNodeConfig-NodeScopeMapping-OrganizationPlus1
		INTEGER,
	    pnniNodeConfig-NodeScopeMapping-CommunityMinus1
		INTEGER,
	    pnniNodeConfig-NodeScopeMapping-IntraCommunity
		INTEGER,
	    pnniNodeConfig-NodeScopeMapping-CommunityPlus1
		INTEGER,
	    pnniNodeConfig-NodeScopeMapping-Regional
		INTEGER,
	    pnniNodeConfig-NodeScopeMapping-InterRegional
		INTEGER,
	    pnniNodeConfig-NodeScopeMapping-Global
		INTEGER,
	    pnniNodeConfig-Action-o
		INTEGER
	}

    pnniNodeConfig-NodeIndex	OBJECT-TYPE
	SYNTAX	INTEGER
	ACCESS	read-only
	STATUS	mandatory
	DESCRIPTION	"A value assigned to a node in this switching system that uniquely identifies it in the MIB."
	::= { mibpnniNodeConfigEntry 1 }

    pnniNodeConfig-NodeLevel	OBJECT-TYPE
	SYNTAX	INTEGER
	ACCESS	read-write
	STATUS	mandatory
	DESCRIPTION	"The level of PNNI hierarchy at which this node exists. This attribute is used to determine the default node ID and the default peer group ID for this node. This object may only be written when pnniNodeAdminStatus has the value down."
	::= { mibpnniNodeConfigEntry 2 }

    pnniNodeConfig-NodeId	OBJECT-TYPE
	SYNTAX	DisplayString
	ACCESS	read-write
	STATUS	mandatory
	DESCRIPTION	"The value the switching system is using to represent itself as this node. If all the bytes of node-id are zero AND all the bytes of the node-peer-group-id are zero, then the value used for the node-id is derived from the node-level and node-atm-address. The derived value is that specified in the pnniNodeId object of the pnniNodeTable in the ATM Forum PNNI MIB."
	::= { mibpnniNodeConfigEntry 3 }

    pnniNodeConfig-CurrNodeId	OBJECT-TYPE
	SYNTAX	DisplayString
	ACCESS	read-only
	STATUS	mandatory
	DESCRIPTION	"The derived node-id value the switching system is using to represent itself as this node. This value is the value derived from the node-level and the node-atm-address."
	::= { mibpnniNodeConfigEntry 4 }

    pnniNodeConfig-NodeLowest	OBJECT-TYPE
	SYNTAX	INTEGER {
		    true (2),
		    false (3)
		}
	ACCESS	read-write
	STATUS	mandatory
	DESCRIPTION	"Indicates whether this node acts as a lowest level node or whether this node is a logical group node that becomes active when one of the other nodes in this switching system becomes a peer group leader."
	::= { mibpnniNodeConfigEntry 5 }

    pnniNodeConfig-NodeAdminStatus	OBJECT-TYPE
	SYNTAX	INTEGER {
		    up (2),
		    down (3)
		}
	ACCESS	read-write
	STATUS	mandatory
	DESCRIPTION	"Indicates whether the administrative status of the node is up (the node is allowed to become active) or down (the node is forced to be inactive)."
	::= { mibpnniNodeConfigEntry 6 }

    pnniNodeConfig-NodeDomainName	OBJECT-TYPE
	SYNTAX	DisplayString
	ACCESS	read-write
	STATUS	mandatory
	DESCRIPTION	"The name of the PNNI routing domain in which this node participates. All lowest-level PNNI nodes with the same pnniNodeDomainName are presumed to be connected."
	::= { mibpnniNodeConfigEntry 7 }

    pnniNodeConfig-NodeAtmAddress	OBJECT-TYPE
	SYNTAX	DisplayString
	ACCESS	read-write
	STATUS	mandatory
	DESCRIPTION	"This node's ATM End System Address. Remote systems wishing to exchange PNNI protocol packets with this node should direct packets or calls to this address."
	::= { mibpnniNodeConfigEntry 8 }

    pnniNodeConfig-NodePeerGroupId	OBJECT-TYPE
	SYNTAX	DisplayString
	ACCESS	read-write
	STATUS	mandatory
	DESCRIPTION	"The Peer Group Identifier of the peer group that the given node is to become a member of. If all the bytes of node-peer-group-id are zero AND all the bytes of the node-id are zero, then the value used for the node-peer-group-id is derived from the node-level and node-atm-address. The derived value is that specified in the pnniNodePeerGroupId object of the pnniNodeTable in the ATM Forum PNNI MIB."
	::= { mibpnniNodeConfigEntry 9 }

    pnniNodeConfig-CurrNodePeerGroupId	OBJECT-TYPE
	SYNTAX	DisplayString
	ACCESS	read-only
	STATUS	mandatory
	DESCRIPTION	"The derived value of the Peer Group Identifier of the peer group that the given node is to become a member of. The derived value is that specified in the pnniNodePeerGroupId object of the pnniNodeTable in the ATM Forum PNNI MIB."
	::= { mibpnniNodeConfigEntry 10 }

    pnniNodeConfig-NodeRestrictedTransit	OBJECT-TYPE
	SYNTAX	INTEGER {
		    true (2),
		    false (3)
		}
	ACCESS	read-write
	STATUS	mandatory
	DESCRIPTION	"Specifies whether the node is restricted to not allowing support of SVCs transiting this node. This attribute determines the setting of the restricted transit bit in the nodal information group originated by this node."
	::= { mibpnniNodeConfigEntry 11 }

    pnniNodeConfig-NodeComplexRep	OBJECT-TYPE
	SYNTAX	INTEGER {
		    true (2),
		    false (3)
		}
	ACCESS	read-write
	STATUS	mandatory
	DESCRIPTION	"Specifies whether this node uses the complex node representation. A value of `true' indicates that the complex node representation is used, whereas a value of `false' indicates that the simple node representation is used."
	::= { mibpnniNodeConfigEntry 12 }

    pnniNodeConfig-NodePgl-LeadershipPriority	OBJECT-TYPE
	SYNTAX	INTEGER
	ACCESS	read-write
	STATUS	mandatory
	DESCRIPTION	"The Leadership priority value this node should advertise in its nodal information group for the given peer group. Only the value zero can be used with nodes that are not PGL/LGN capable. As we cannot be a Peer Group Leader in this release, this value is always zero."
	::= { mibpnniNodeConfigEntry 13 }

    pnniNodeConfig-NodePgl-ParentNodeIndex	OBJECT-TYPE
	SYNTAX	INTEGER
	ACCESS	read-write
	STATUS	mandatory
	DESCRIPTION	"The local node index used to identify the node that will represent this peer group at the next higher level of hierarchy, if this node becomes peer group leader. The value 0 indicates that there is no parent node."
	::= { mibpnniNodeConfigEntry 14 }

    pnniNodeConfig-NodePgl-InitTime	OBJECT-TYPE
	SYNTAX	INTEGER
	ACCESS	read-write
	STATUS	mandatory
	DESCRIPTION	"The amount of time in seconds this node will delay advertising its choice of preferred PGL after having initialized operation and reached the full state with at least one neighbor in the peer group."
	::= { mibpnniNodeConfigEntry 15 }

    pnniNodeConfig-NodePgl-OverrideDelay	OBJECT-TYPE
	SYNTAX	INTEGER
	ACCESS	read-write
	STATUS	mandatory
	DESCRIPTION	"The amount of time in seconds a node will wait for itself to be declared the preferred PGL by unanimous agreement among its peers. In the absence of unanimous agreement this will be the amount of time that will pass before this node considers a two thirds majority as sufficient agreement to declare itself peer group leader, abandoning the attempt to get unanimous agreement."
	::= { mibpnniNodeConfigEntry 16 }

    pnniNodeConfig-NodePgl-ReelectTime	OBJECT-TYPE
	SYNTAX	INTEGER
	ACCESS	read-write
	STATUS	mandatory
	DESCRIPTION	"The amount of time in seconds after losing connectivity to the current peer group leader, that this node will wait before re-starting the process of electing a new peer group leader."
	::= { mibpnniNodeConfigEntry 17 }

    pnniNodeConfig-NodeTimer-PtseHolddown	OBJECT-TYPE
	SYNTAX	INTEGER
	ACCESS	read-write
	STATUS	mandatory
	DESCRIPTION	"The initial value for the PTSE hold down timer that will be used by the given node to limit the rate at which it can re-originate PTSEs. It must be a positive non-zero number."
	::= { mibpnniNodeConfigEntry 18 }

    pnniNodeConfig-NodeTimer-HelloHolddown	OBJECT-TYPE
	SYNTAX	INTEGER
	ACCESS	read-write
	STATUS	mandatory
	DESCRIPTION	"The initial value for the Hello hold down timer that will be used by the given node to limit the rate at which it sends Hellos. It must be a positive non-zero number."
	::= { mibpnniNodeConfigEntry 19 }

    pnniNodeConfig-NodeTimer-HelloInterval	OBJECT-TYPE
	SYNTAX	INTEGER
	ACCESS	read-write
	STATUS	mandatory
	DESCRIPTION	"The initial value for the Hello Timer. In the absence of triggered Hellos, this node will send one Hello packet on each of its ports on this interval."
	::= { mibpnniNodeConfigEntry 20 }

    pnniNodeConfig-NodeTimer-HelloInactivityFactor	OBJECT-TYPE
	SYNTAX	INTEGER
	ACCESS	read-write
	STATUS	mandatory
	DESCRIPTION	"The value for the Hello Inactivity factor that this node will use to determine when a neighbor has gone down."
	::= { mibpnniNodeConfigEntry 21 }

    pnniNodeConfig-NodeTimer-HlinkInact	OBJECT-TYPE
	SYNTAX	INTEGER
	ACCESS	read-write
	STATUS	mandatory
	DESCRIPTION	"The amount of time a node will continue to advertise a horizontal (logical) link for which it has not received and processed a LGN Horizontal Link information group."
	::= { mibpnniNodeConfigEntry 22 }

    pnniNodeConfig-NodeTimer-PtseRefreshInterval	OBJECT-TYPE
	SYNTAX	INTEGER
	ACCESS	read-write
	STATUS	mandatory
	DESCRIPTION	"The initial value for the Refresh timer that this node will use to drive (re-)origination of PTSEs in the absence of triggered updates."
	::= { mibpnniNodeConfigEntry 23 }

    pnniNodeConfig-NodeTimer-PtseLifetimeFactor	OBJECT-TYPE
	SYNTAX	INTEGER
	ACCESS	read-write
	STATUS	mandatory
	DESCRIPTION	"The value for the lifetime multiplier, expressed as a percentage. The result of multiplying the pnniNodePtseRefreshInterval attribute value by this attribute value is used as the initial lifetime that this node places into self-originated PTSEs."
	::= { mibpnniNodeConfigEntry 24 }

    pnniNodeConfig-NodeTimer-RxmtInterval	OBJECT-TYPE
	SYNTAX	INTEGER
	ACCESS	read-write
	STATUS	mandatory
	DESCRIPTION	"The period between retransmissions of unacknowledged Database Summary packets, PTSE Request packets, and PTSPs."
	::= { mibpnniNodeConfigEntry 25 }

    pnniNodeConfig-NodeTimer-PeerDelayedAckInterval	OBJECT-TYPE
	SYNTAX	INTEGER
	ACCESS	read-write
	STATUS	mandatory
	DESCRIPTION	"The minimum amount of time between transmissions of delayed PTSE acknowledgement packets."
	::= { mibpnniNodeConfigEntry 26 }

    pnniNodeConfig-NodeTimer-AvcrPm	OBJECT-TYPE
	SYNTAX	INTEGER
	ACCESS	read-write
	STATUS	mandatory
	DESCRIPTION	"The proportional multiplier used in the algorithms that determine significant change for AvCR parameters, expressed as a percentage."
	::= { mibpnniNodeConfigEntry 27 }

    pnniNodeConfig-NodeTimer-AvcrMt	OBJECT-TYPE
	SYNTAX	INTEGER
	ACCESS	read-write
	STATUS	mandatory
	DESCRIPTION	"The minimum threshold used in the algorithms that determine signif- icant change for AvCR parameters, expressed as a percentage."
	::= { mibpnniNodeConfigEntry 28 }

    pnniNodeConfig-NodeTimer-CdvPm	OBJECT-TYPE
	SYNTAX	INTEGER
	ACCESS	read-write
	STATUS	mandatory
	DESCRIPTION	"The proportional multiplier used in the algorithms that determine significant change for CDV metrics, expressed as a percentage."
	::= { mibpnniNodeConfigEntry 29 }

    pnniNodeConfig-NodeTimer-CtdPm	OBJECT-TYPE
	SYNTAX	INTEGER
	ACCESS	read-write
	STATUS	mandatory
	DESCRIPTION	"The proportional multiplier used in the algorithms that determine significant change for CTD metrics, expressed as a percentage."
	::= { mibpnniNodeConfigEntry 30 }

    pnniNodeConfig-NodeSvccRcc-InitTime	OBJECT-TYPE
	SYNTAX	INTEGER
	ACCESS	read-write
	STATUS	mandatory
	DESCRIPTION	"The amount of time this node will delay initiating establishment of an SVCC to a neighbor with a numerically lower ATM address, after determining that such an SVCC should be established."
	::= { mibpnniNodeConfigEntry 31 }

    pnniNodeConfig-NodeSvccRcc-RetryTime	OBJECT-TYPE
	SYNTAX	INTEGER
	ACCESS	read-write
	STATUS	mandatory
	DESCRIPTION	"The amount of time this node will delay after an apparently still necessary and viable SVCC-based RCC is unexpectedly torn down, before attempting to re-establish it."
	::= { mibpnniNodeConfigEntry 32 }

    pnniNodeConfig-NodeSvccRcc-CallingIntegrityTime	OBJECT-TYPE
	SYNTAX	INTEGER
	ACCESS	read-write
	STATUS	mandatory
	DESCRIPTION	"The amount of time this node will wait for an SVCC, which it has initiated establishment of as the calling party, to become fully established before giving up and tearing it down."
	::= { mibpnniNodeConfigEntry 33 }

    pnniNodeConfig-NodeSvccRcc-CalledIntegrityTime	OBJECT-TYPE
	SYNTAX	INTEGER
	ACCESS	read-write
	STATUS	mandatory
	DESCRIPTION	"The amount of time this node will wait for an SVCC, which it has decided to accept as the called party, to become fully established before giving up and tearing it down."
	::= { mibpnniNodeConfigEntry 34 }

    pnniNodeConfig-NodeSvccRcc-TrafficDescrIndex	OBJECT-TYPE
	SYNTAX	INTEGER
	ACCESS	read-write
	STATUS	mandatory
	DESCRIPTION	"An index into the atmTrafficDescrParamTable defined in RFC 1695. This traffic descriptor is used when establishing switched virtual channels for use as SVCC-based RCCs to/from PNNI logical group nodes."
	::= { mibpnniNodeConfigEntry 35 }

    pnniNodeConfig-NodeScopeMapping-LocalNet	OBJECT-TYPE
	SYNTAX	INTEGER
	ACCESS	read-write
	STATUS	mandatory
	DESCRIPTION	"The highest level of PNNI hierarchy (i.e. smallest PNNI routing level) that lies within the organizational scope value localNetwork(1)."
	::= { mibpnniNodeConfigEntry 36 }

    pnniNodeConfig-NodeScopeMapping-LocalNetPlus1	OBJECT-TYPE
	SYNTAX	INTEGER
	ACCESS	read-write
	STATUS	mandatory
	DESCRIPTION	"The highest level of PNNI hierarchy (i.e. smallest PNNI routing level) that lies within the organizational scope localNetworkPlusOne(2)."
	::= { mibpnniNodeConfigEntry 37 }

    pnniNodeConfig-NodeScopeMapping-LocalNetPlus2	OBJECT-TYPE
	SYNTAX	INTEGER
	ACCESS	read-write
	STATUS	mandatory
	DESCRIPTION	"The highest level of PNNI hierarchy (i.e. smallest PNNI routing level) that lies within the organizational scope localNetworkPlusTwo(3)."
	::= { mibpnniNodeConfigEntry 38 }

    pnniNodeConfig-NodeScopeMapping-SiteMinus1	OBJECT-TYPE
	SYNTAX	INTEGER
	ACCESS	read-write
	STATUS	mandatory
	DESCRIPTION	"The highest level of PNNI hierarchy (i.e. smallest PNNI routing level) that lies within the organizational scope value siteMinusOne(4)."
	::= { mibpnniNodeConfigEntry 39 }

    pnniNodeConfig-NodeScopeMapping-IntraSite	OBJECT-TYPE
	SYNTAX	INTEGER
	ACCESS	read-write
	STATUS	mandatory
	DESCRIPTION	"The highest level of PNNI hierarchy (i.e. smallest PNNI routing level) that lies within the organizational scope value intraSite(5)."
	::= { mibpnniNodeConfigEntry 40 }

    pnniNodeConfig-NodeScopeMapping-SitePlus1	OBJECT-TYPE
	SYNTAX	INTEGER
	ACCESS	read-write
	STATUS	mandatory
	DESCRIPTION	"The highest level of PNNI hierarchy (i.e. smallest PNNI routing level) that lies within the organizational scope value sitePlusOne(6)."
	::= { mibpnniNodeConfigEntry 41 }

    pnniNodeConfig-NodeScopeMapping-OrganizationMinus1	OBJECT-TYPE
	SYNTAX	INTEGER
	ACCESS	read-write
	STATUS	mandatory
	DESCRIPTION	"The highest level of PNNI hierarchy (i.e. smallest PNNI routing level) that lies within the organizational scope value organizationMinusOne(7)."
	::= { mibpnniNodeConfigEntry 42 }

    pnniNodeConfig-NodeScopeMapping-IntraOrganization	OBJECT-TYPE
	SYNTAX	INTEGER
	ACCESS	read-write
	STATUS	mandatory
	DESCRIPTION	"The highest level of PNNI hierarchy (i.e. smallest PNNI routing level) that lies within the organizational scope value intraOrganization(8)."
	::= { mibpnniNodeConfigEntry 43 }

    pnniNodeConfig-NodeScopeMapping-OrganizationPlus1	OBJECT-TYPE
	SYNTAX	INTEGER
	ACCESS	read-write
	STATUS	mandatory
	DESCRIPTION	"The highest level of PNNI hierarchy (i.e. smallest PNNI routing level) that lies within the organizational scope value organizationPlusOne(9)."
	::= { mibpnniNodeConfigEntry 44 }

    pnniNodeConfig-NodeScopeMapping-CommunityMinus1	OBJECT-TYPE
	SYNTAX	INTEGER
	ACCESS	read-write
	STATUS	mandatory
	DESCRIPTION	"The highest level of PNNI hierarchy (i.e. smallest PNNI routing level) that lies within the organizational scope value communityMinusOne(10)."
	::= { mibpnniNodeConfigEntry 45 }

    pnniNodeConfig-NodeScopeMapping-IntraCommunity	OBJECT-TYPE
	SYNTAX	INTEGER
	ACCESS	read-write
	STATUS	mandatory
	DESCRIPTION	"The highest level of PNNI hierarchy (i.e. smallest PNNI routing level) that lies within the organizational scope value intraCommunity(11)."
	::= { mibpnniNodeConfigEntry 46 }

    pnniNodeConfig-NodeScopeMapping-CommunityPlus1	OBJECT-TYPE
	SYNTAX	INTEGER
	ACCESS	read-write
	STATUS	mandatory
	DESCRIPTION	"The highest level of PNNI hierarchy (i.e. smallest PNNI routing level) that lies within the organizational scope value communityPlusOne(12)."
	::= { mibpnniNodeConfigEntry 47 }

    pnniNodeConfig-NodeScopeMapping-Regional	OBJECT-TYPE
	SYNTAX	INTEGER
	ACCESS	read-write
	STATUS	mandatory
	DESCRIPTION	"The highest level of PNNI hierarchy (i.e. smallest PNNI routing level) that lies within the organizational scope value regional(13)."
	::= { mibpnniNodeConfigEntry 48 }

    pnniNodeConfig-NodeScopeMapping-InterRegional	OBJECT-TYPE
	SYNTAX	INTEGER
	ACCESS	read-write
	STATUS	mandatory
	DESCRIPTION	"The highest level of PNNI hierarchy (i.e. smallest PNNI routing level) that lies within the organizational scope value interRegional(14)."
	::= { mibpnniNodeConfigEntry 49 }

    pnniNodeConfig-NodeScopeMapping-Global	OBJECT-TYPE
	SYNTAX	INTEGER
	ACCESS	read-write
	STATUS	mandatory
	DESCRIPTION	"The highest level of PNNI hierarchy (i.e. smallest PNNI routing level) that lies within the organizational scope value global(15)."
	::= { mibpnniNodeConfigEntry 50 }

    pnniNodeConfig-Action-o	OBJECT-TYPE
	SYNTAX	INTEGER {
		    noAction (1),
		    createProfile (2),
		    deleteProfile (3)
		}
	ACCESS	read-write
	STATUS	mandatory
	DESCRIPTION	""
	::= { mibpnniNodeConfigEntry 51 }


	-- The mibpnniDTLConfig table
	--
	-- This table contains parameters for the mibpnniDTLConfig profile
	--

    mibpnniDTLConfigTable	OBJECT-TYPE
	SYNTAX		SEQUENCE OF MibpnniDTLConfigEntry
	ACCESS		not-accessible
	STATUS		mandatory
	DESCRIPTION	"A list of mibpnniDTLConfig profile entries."
	::= { mibpnniDTLConfig 1 }

    mibpnniDTLConfigEntry	OBJECT-TYPE
	SYNTAX		MibpnniDTLConfigEntry
	ACCESS		not-accessible
	STATUS		mandatory
	DESCRIPTION	"A mibpnniDTLConfig entry containing objects that
			 maps to the parameters of mibpnniDTLConfig profile."
	INDEX		{ pnniDTLConfig-DtlIndex-NodeIndex, pnniDTLConfig-DtlIndex-DtlIndex, pnniDTLConfig-DtlIndex-DtlEntryIndex }
	::= { mibpnniDTLConfigTable 1 }

    MibpnniDTLConfigEntry ::=
	SEQUENCE {
	    pnniDTLConfig-DtlIndex-NodeIndex
		INTEGER,
	    pnniDTLConfig-DtlIndex-DtlIndex
		INTEGER,
	    pnniDTLConfig-DtlIndex-DtlEntryIndex
		INTEGER,
	    pnniDTLConfig-DtlNodeId
		DisplayString,
	    pnniDTLConfig-DtlPortId
		INTEGER,
	    pnniDTLConfig-DtlLinkType
		INTEGER,
	    pnniDTLConfig-Active
		INTEGER,
	    pnniDTLConfig-Action-o
		INTEGER
	}

    pnniDTLConfig-DtlIndex-NodeIndex	OBJECT-TYPE
	SYNTAX	INTEGER
	ACCESS	read-only
	STATUS	mandatory
	DESCRIPTION	"Index that identifies a logical PNNI node."
	::= { mibpnniDTLConfigEntry 1 }

    pnniDTLConfig-DtlIndex-DtlIndex	OBJECT-TYPE
	SYNTAX	INTEGER
	ACCESS	read-only
	STATUS	mandatory
	DESCRIPTION	"The index in the node's DTL table of this DTL stack."
	::= { mibpnniDTLConfigEntry 2 }

    pnniDTLConfig-DtlIndex-DtlEntryIndex	OBJECT-TYPE
	SYNTAX	INTEGER
	ACCESS	read-only
	STATUS	mandatory
	DESCRIPTION	"The index in the current DTL stack of this entry."
	::= { mibpnniDTLConfigEntry 3 }

    pnniDTLConfig-DtlNodeId	OBJECT-TYPE
	SYNTAX	DisplayString
	ACCESS	read-write
	STATUS	mandatory
	DESCRIPTION	"The node which is this hop in the DTL stack."
	::= { mibpnniDTLConfigEntry 4 }

    pnniDTLConfig-DtlPortId	OBJECT-TYPE
	SYNTAX	INTEGER
	ACCESS	read-write
	STATUS	mandatory
	DESCRIPTION	"The port from the pnniDTLNodeId to use as the exit.If the DTL stack does not care, this is coded as zero."
	::= { mibpnniDTLConfigEntry 5 }

    pnniDTLConfig-DtlLinkType	OBJECT-TYPE
	SYNTAX	INTEGER {
		    invalid (2),
		    horizontal (3),
		    uplink (4),
		    last (5)
		}
	ACCESS	read-write
	STATUS	mandatory
	DESCRIPTION	"The type of link out from this node (pnniDTLNodeId).This is well defined even if the specific port is not specified."
	::= { mibpnniDTLConfigEntry 6 }

    pnniDTLConfig-Active	OBJECT-TYPE
	SYNTAX	INTEGER {
		    no (1),
		    yes (2)
		}
	ACCESS	read-write
	STATUS	mandatory
	DESCRIPTION	"The current state of this DTL entry."
	::= { mibpnniDTLConfigEntry 7 }

    pnniDTLConfig-Action-o	OBJECT-TYPE
	SYNTAX	INTEGER {
		    noAction (1),
		    createProfile (2),
		    deleteProfile (3)
		}
	ACCESS	read-write
	STATUS	mandatory
	DESCRIPTION	""
	::= { mibpnniDTLConfigEntry 8 }


	-- The mibpnniIfConfig table
	--
	-- This table contains parameters for the mibpnniIfConfig profile
	--

    mibpnniIfConfigTable	OBJECT-TYPE
	SYNTAX		SEQUENCE OF MibpnniIfConfigEntry
	ACCESS		not-accessible
	STATUS		mandatory
	DESCRIPTION	"A list of mibpnniIfConfig profile entries."
	::= { mibpnniIfConfig 1 }

    mibpnniIfConfigEntry	OBJECT-TYPE
	SYNTAX		MibpnniIfConfigEntry
	ACCESS		not-accessible
	STATUS		mandatory
	DESCRIPTION	"A mibpnniIfConfig entry containing objects that
			 maps to the parameters of mibpnniIfConfig profile."
	INDEX		{ pnniIfConfig-Shelf-o, pnniIfConfig-Slot-o, pnniIfConfig-Item-o, pnniIfConfig-LogicalItem-o }
	::= { mibpnniIfConfigTable 1 }

    MibpnniIfConfigEntry ::=
	SEQUENCE {
	    pnniIfConfig-Shelf-o
		INTEGER,
	    pnniIfConfig-Slot-o
		INTEGER,
	    pnniIfConfig-Item-o
		INTEGER,
	    pnniIfConfig-LogicalItem-o
		INTEGER,
	    pnniIfConfig-Address-PhysicalAddress-Shelf
		INTEGER,
	    pnniIfConfig-Address-PhysicalAddress-Slot
		INTEGER,
	    pnniIfConfig-Address-PhysicalAddress-ItemNumber
		INTEGER,
	    pnniIfConfig-Address-LogicalItem
		INTEGER,
	    pnniIfConfig-IfNodeIndex
		INTEGER,
	    pnniIfConfig-IfAggrToken
		INTEGER,
	    pnniIfConfig-IfVpCapability
		INTEGER,
	    pnniIfConfig-IfAdmWeightCbr
		INTEGER,
	    pnniIfConfig-IfAdmWeightRtVbr
		INTEGER,
	    pnniIfConfig-IfAdmWeightNrtVbr
		INTEGER,
	    pnniIfConfig-IfAdmWeightAbr
		INTEGER,
	    pnniIfConfig-IfAdmWeightUbr
		INTEGER,
	    pnniIfConfig-IfRccServiceCategory
		INTEGER,
	    pnniIfConfig-IfRccQosName
		DisplayString,
	    pnniIfConfig-Action-o
		INTEGER
	}

    pnniIfConfig-Shelf-o	OBJECT-TYPE
	SYNTAX	INTEGER
	ACCESS	read-only
	STATUS	mandatory
	DESCRIPTION	""
	::= { mibpnniIfConfigEntry 1 }

    pnniIfConfig-Slot-o	OBJECT-TYPE
	SYNTAX	INTEGER
	ACCESS	read-only
	STATUS	mandatory
	DESCRIPTION	""
	::= { mibpnniIfConfigEntry 2 }

    pnniIfConfig-Item-o	OBJECT-TYPE
	SYNTAX	INTEGER
	ACCESS	read-only
	STATUS	mandatory
	DESCRIPTION	""
	::= { mibpnniIfConfigEntry 3 }

    pnniIfConfig-LogicalItem-o	OBJECT-TYPE
	SYNTAX	INTEGER
	ACCESS	read-only
	STATUS	mandatory
	DESCRIPTION	""
	::= { mibpnniIfConfigEntry 4 }

    pnniIfConfig-Address-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibpnniIfConfigEntry 5 }

    pnniIfConfig-Address-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibpnniIfConfigEntry 6 }

    pnniIfConfig-Address-PhysicalAddress-ItemNumber	OBJECT-TYPE
	SYNTAX	INTEGER
	ACCESS	read-write
	STATUS	mandatory
	DESCRIPTION	"A number that specifies an addressable entity within the context of shelf and slot."
	::= { mibpnniIfConfigEntry 7 }

    pnniIfConfig-Address-LogicalItem	OBJECT-TYPE
	SYNTAX	INTEGER
	ACCESS	read-write
	STATUS	mandatory
	DESCRIPTION	"A number that specifies an addressable logical entity within the context of a physical address."
	::= { mibpnniIfConfigEntry 8 }

    pnniIfConfig-IfNodeIndex	OBJECT-TYPE
	SYNTAX	INTEGER
	ACCESS	read-write
	STATUS	mandatory
	DESCRIPTION	"Identifies the node within the switching system that the interface is directly attached to. The value zero is not a valid value."
	::= { mibpnniIfConfigEntry 9 }

    pnniIfConfig-IfAggrToken	OBJECT-TYPE
	SYNTAX	INTEGER
	ACCESS	read-write
	STATUS	mandatory
	DESCRIPTION	"The configured aggregation token for this interface. The aggregation token controls what other links the link associated with this interface will be aggregated together with."
	::= { mibpnniIfConfigEntry 10 }

    pnniIfConfig-IfVpCapability	OBJECT-TYPE
	SYNTAX	INTEGER {
		    true (2),
		    false (3)
		}
	ACCESS	read-only
	STATUS	mandatory
	DESCRIPTION	"Indicates whether the interface is capable of having VPCs established within it or not."
	::= { mibpnniIfConfigEntry 11 }

    pnniIfConfig-IfAdmWeightCbr	OBJECT-TYPE
	SYNTAX	INTEGER
	ACCESS	read-write
	STATUS	mandatory
	DESCRIPTION	"The administrative weight of this interface for the constant bit rate service category."
	::= { mibpnniIfConfigEntry 12 }

    pnniIfConfig-IfAdmWeightRtVbr	OBJECT-TYPE
	SYNTAX	INTEGER
	ACCESS	read-write
	STATUS	mandatory
	DESCRIPTION	"The administrative weight of this interface for the real-time variable bit rate service category."
	::= { mibpnniIfConfigEntry 13 }

    pnniIfConfig-IfAdmWeightNrtVbr	OBJECT-TYPE
	SYNTAX	INTEGER
	ACCESS	read-write
	STATUS	mandatory
	DESCRIPTION	"The administrative weight of this interface for the non-real-time variable bit rate service category."
	::= { mibpnniIfConfigEntry 14 }

    pnniIfConfig-IfAdmWeightAbr	OBJECT-TYPE
	SYNTAX	INTEGER
	ACCESS	read-write
	STATUS	mandatory
	DESCRIPTION	"The administrative weight of this interface for the available bit rate service category."
	::= { mibpnniIfConfigEntry 15 }

    pnniIfConfig-IfAdmWeightUbr	OBJECT-TYPE
	SYNTAX	INTEGER
	ACCESS	read-write
	STATUS	mandatory
	DESCRIPTION	"The administrative weight of this interface for the unspecified bit rate service category."
	::= { mibpnniIfConfigEntry 16 }

    pnniIfConfig-IfRccServiceCategory	OBJECT-TYPE
	SYNTAX	INTEGER {
		    other (2),
		    cbr (3),
		    rtVbr (4),
		    nrtVbr (5),
		    abr (6),
		    ubr (7)
		}
	ACCESS	read-write
	STATUS	mandatory
	DESCRIPTION	"The service category used for the PNNI routing control channel (VCI=18) on this interface."
	::= { mibpnniIfConfigEntry 17 }

    pnniIfConfig-IfRccQosName	OBJECT-TYPE
	SYNTAX	DisplayString
	ACCESS	read-write
	STATUS	mandatory
	DESCRIPTION	"The QOS for the PNNI Routing control channel."
	::= { mibpnniIfConfigEntry 18 }

    pnniIfConfig-Action-o	OBJECT-TYPE
	SYNTAX	INTEGER {
		    noAction (1),
		    createProfile (2),
		    deleteProfile (3)
		}
	ACCESS	read-write
	STATUS	mandatory
	DESCRIPTION	""
	::= { mibpnniIfConfigEntry 19 }


	-- The mibpnniRouteNodeConfig table
	--
	-- This table contains parameters for the mibpnniRouteNodeConfig profile
	--

    mibpnniRouteNodeConfigTable	OBJECT-TYPE
	SYNTAX		SEQUENCE OF MibpnniRouteNodeConfigEntry
	ACCESS		not-accessible
	STATUS		mandatory
	DESCRIPTION	"A list of mibpnniRouteNodeConfig profile entries."
	::= { mibpnniRouteNodeConfig 1 }

    mibpnniRouteNodeConfigEntry	OBJECT-TYPE
	SYNTAX		MibpnniRouteNodeConfigEntry
	ACCESS		not-accessible
	STATUS		mandatory
	DESCRIPTION	"A mibpnniRouteNodeConfig entry containing objects that
			 maps to the parameters of mibpnniRouteNodeConfig profile."
	INDEX		{ pnniRouteNodeConfig-Index-NodeIndex, pnniRouteNodeConfig-Index-RouteNodeClass, pnniRouteNodeConfig-Index-RouteNodeDestNodeId, pnniRouteNodeConfig-Index-RouteNodeDtl }
	::= { mibpnniRouteNodeConfigTable 1 }

    MibpnniRouteNodeConfigEntry ::=
	SEQUENCE {
	    pnniRouteNodeConfig-Index-NodeIndex
		INTEGER,
	    pnniRouteNodeConfig-Index-RouteNodeClass
		INTEGER,
	    pnniRouteNodeConfig-Index-RouteNodeDestNodeId
		DisplayString,
	    pnniRouteNodeConfig-Index-RouteNodeDtl
		INTEGER,
	    pnniRouteNodeConfig-DestPortId
		INTEGER,
	    pnniRouteNodeConfig-Proto
		INTEGER,
	    pnniRouteNodeConfig-TimeStamp
		INTEGER,
	    pnniRouteNodeConfig-NodeInfo
		DisplayString,
	    pnniRouteNodeConfig-GcacClp
		INTEGER,
	    pnniRouteNodeConfig-FwdMetricAw
		INTEGER,
	    pnniRouteNodeConfig-FwdMetric1
		INTEGER,
	    pnniRouteNodeConfig-FwdMetric2
		INTEGER,
	    pnniRouteNodeConfig-FwdMetric3
		INTEGER,
	    pnniRouteNodeConfig-FwdMetric4
		INTEGER,
	    pnniRouteNodeConfig-FwdMetric5
		INTEGER,
	    pnniRouteNodeConfig-FwdMeteric6
		INTEGER,
	    pnniRouteNodeConfig-FwdMeteric7
		INTEGER,
	    pnniRouteNodeConfig-FwdMeteric8
		INTEGER,
	    pnniRouteNodeConfig-BwdMetricAw
		INTEGER,
	    pnniRouteNodeConfig-BwdMetric1
		INTEGER,
	    pnniRouteNodeConfig-BwdMetric2
		INTEGER,
	    pnniRouteNodeConfig-BwdMetric3
		INTEGER,
	    pnniRouteNodeConfig-BwdMetric4
		INTEGER,
	    pnniRouteNodeConfig-BwdMetric5
		INTEGER,
	    pnniRouteNodeConfig-BwdMetric6
		INTEGER,
	    pnniRouteNodeConfig-BwdMetric7
		INTEGER,
	    pnniRouteNodeConfig-BwdMetric8
		INTEGER,
	    pnniRouteNodeConfig-VpCapability
		INTEGER,
	    pnniRouteNodeConfig-Active
		INTEGER,
	    pnniRouteNodeConfig-Action-o
		INTEGER
	}

    pnniRouteNodeConfig-Index-NodeIndex	OBJECT-TYPE
	SYNTAX	INTEGER
	ACCESS	read-only
	STATUS	mandatory
	DESCRIPTION	"Index that identifies a logical PNNI node."
	::= { mibpnniRouteNodeConfigEntry 1 }

    pnniRouteNodeConfig-Index-RouteNodeClass	OBJECT-TYPE
	SYNTAX	INTEGER
	ACCESS	read-only
	STATUS	mandatory
	DESCRIPTION	"Indicates the service category with which this forwarding table entry is associated."
	::= { mibpnniRouteNodeConfigEntry 2 }

    pnniRouteNodeConfig-Index-RouteNodeDestNodeId	OBJECT-TYPE
	SYNTAX	DisplayString
	ACCESS	read-only
	STATUS	mandatory
	DESCRIPTION	"The node ID of the destination node to which this route proceeds, and at which the DTL stack for this route terminates."
	::= { mibpnniRouteNodeConfigEntry 3 }

    pnniRouteNodeConfig-Index-RouteNodeDtl	OBJECT-TYPE
	SYNTAX	INTEGER
	ACCESS	read-only
	STATUS	mandatory
	DESCRIPTION	"The index into the owning PNNI node's DTL table of the DTL stack that goes with this route."
	::= { mibpnniRouteNodeConfigEntry 4 }

    pnniRouteNodeConfig-DestPortId	OBJECT-TYPE
	SYNTAX	INTEGER
	ACCESS	read-write
	STATUS	mandatory
	DESCRIPTION	"The port ID of the destination node at which the route terminates.A port ID of zero indicates the node nucleus.When the destination node is represented by the simple node representation, this value should be set to zero."
	::= { mibpnniRouteNodeConfigEntry 5 }

    pnniRouteNodeConfig-Proto	OBJECT-TYPE
	SYNTAX	INTEGER {
		    other (2),
		    local (3),
		    mgmt (4),
		    pnni (5)
		}
	ACCESS	read-only
	STATUS	mandatory
	DESCRIPTION	"The routing mechanism via which this route was learned."
	::= { mibpnniRouteNodeConfigEntry 6 }

    pnniRouteNodeConfig-TimeStamp	OBJECT-TYPE
	SYNTAX	INTEGER
	ACCESS	read-only
	STATUS	mandatory
	DESCRIPTION	"The time at which this route was last updated or otherwise determined to be correct. Note that no semantics of `too old' can be implied except through knowledge of the routing protocol by which the route was learned."
	::= { mibpnniRouteNodeConfigEntry 7 }

    pnniRouteNodeConfig-NodeInfo	OBJECT-TYPE
	SYNTAX	DisplayString
	ACCESS	read-write
	STATUS	mandatory
	DESCRIPTION	"A reference to MIB definitions specific to the particular routing protocol which is responsible for this route,as determined by the value specified in the route's pnniRouteNodeProto value.Currently not supportted and is set to 0.0."
	::= { mibpnniRouteNodeConfigEntry 8 }

    pnniRouteNodeConfig-GcacClp	OBJECT-TYPE
	SYNTAX	INTEGER {
		    clpequal0 (2),
		    clpequal0or1 (3)
		}
	ACCESS	read-write
	STATUS	mandatory
	DESCRIPTION	"For PNNI, indicates whether any advertised GCAC parameters apply for CLP=0 traffic or for CLP=0+1 traffic."
	::= { mibpnniRouteNodeConfigEntry 9 }

    pnniRouteNodeConfig-FwdMetricAw	OBJECT-TYPE
	SYNTAX	INTEGER
	ACCESS	read-write
	STATUS	mandatory
	DESCRIPTION	"The cumulative administrative weight calculated for the forward direction of this route. 0xFFFFFFFF means the metric is not used."
	::= { mibpnniRouteNodeConfigEntry 10 }

    pnniRouteNodeConfig-FwdMetric1	OBJECT-TYPE
	SYNTAX	INTEGER
	ACCESS	read-write
	STATUS	mandatory
	DESCRIPTION	"An alternate routing parameter for the forward direction of this route. For information learned from PNNI nodes, this is the maximum possible cell rate (in cells per second) for the forward direction of the route. 0xFFFFFFFF means the metric is not used."
	::= { mibpnniRouteNodeConfigEntry 11 }

    pnniRouteNodeConfig-FwdMetric2	OBJECT-TYPE
	SYNTAX	INTEGER
	ACCESS	read-write
	STATUS	mandatory
	DESCRIPTION	"An alternate routing parameter for the forward direction of this route. For information learned from PNNI nodes, this is the Available cell rate (in cells per second) for the forward direction of the route. 0xFFFFFFFF means the metric is not used."
	::= { mibpnniRouteNodeConfigEntry 12 }

    pnniRouteNodeConfig-FwdMetric3	OBJECT-TYPE
	SYNTAX	INTEGER
	ACCESS	read-write
	STATUS	mandatory
	DESCRIPTION	"An alternate routing parameter for the forward direction of this route. For information learned from PNNI nodes, this is the cumulative Max. Cell Transfer Delay (in microseconds) for the forward direction of the route. 0xFFFFFFFF means the metric is not used."
	::= { mibpnniRouteNodeConfigEntry 13 }

    pnniRouteNodeConfig-FwdMetric4	OBJECT-TYPE
	SYNTAX	INTEGER
	ACCESS	read-write
	STATUS	mandatory
	DESCRIPTION	"An alternate routing parameter for the forward direction of this route. For information learned from PNNI nodes, this is the cumulative Cell Delay Variation (in microseconds)for forward direction of the route. 0xFFFFFFFF means the metric is not used."
	::= { mibpnniRouteNodeConfigEntry 14 }

    pnniRouteNodeConfig-FwdMetric5	OBJECT-TYPE
	SYNTAX	INTEGER
	ACCESS	read-write
	STATUS	mandatory
	DESCRIPTION	"An alternate routing parameter for the forward direction of this route. For information learned from PNNI nodes, this is the cumulative Cell Loss Ratio for CLP=0 traffic for the forward direction of the route. Cell loss ratio value is computed as 10**(-n) where 'n' is the value returned in this variable.0xFFFFFFFF means the metric is not used."
	::= { mibpnniRouteNodeConfigEntry 15 }

    pnniRouteNodeConfig-FwdMeteric6	OBJECT-TYPE
	SYNTAX	INTEGER
	ACCESS	read-write
	STATUS	mandatory
	DESCRIPTION	"An alternate routing parameter for the forward direction of this route. For information learned from PNNI nodes, this is the cumulative Cell Loss Ratio for CLP=0+1 traffic for the forward direction of the route. Cell loss ratio value is computed as 10**(-n) where 'n' is the returned in this variable.0xFFFFFFFF means the metric is not used."
	::= { mibpnniRouteNodeConfigEntry 16 }

    pnniRouteNodeConfig-FwdMeteric7	OBJECT-TYPE
	SYNTAX	INTEGER
	ACCESS	read-write
	STATUS	mandatory
	DESCRIPTION	"An alternate routing parameter for the forward direction of this route. For information learned from PNNI nodes, this is the Cell Rate Margin (in cells per second) for the forward direction of the route. 0xFFFFFFFF means the metric is not used."
	::= { mibpnniRouteNodeConfigEntry 17 }

    pnniRouteNodeConfig-FwdMeteric8	OBJECT-TYPE
	SYNTAX	INTEGER
	ACCESS	read-write
	STATUS	mandatory
	DESCRIPTION	"An alternate routing parameter for the forward direction of this route. For information learned from PNNI nodes, this is the Variance Factor (in units of 2**(-8)) for the forward direction of the route. 0xFFFFFFFF means the metric is not used."
	::= { mibpnniRouteNodeConfigEntry 18 }

    pnniRouteNodeConfig-BwdMetricAw	OBJECT-TYPE
	SYNTAX	INTEGER
	ACCESS	read-write
	STATUS	mandatory
	DESCRIPTION	"The administrative weight calculated for the backward direction of this route. 0xFFFFFFFF means the metric is not used."
	::= { mibpnniRouteNodeConfigEntry 19 }

    pnniRouteNodeConfig-BwdMetric1	OBJECT-TYPE
	SYNTAX	INTEGER
	ACCESS	read-write
	STATUS	mandatory
	DESCRIPTION	"Alternate routing parameter for the backward direction of this route. For information learned from PNNI nodes, this is the maximum possible cell rate(in cells per second)for the backward direction of the route. 0xFFFFFFFF means the metric is not used."
	::= { mibpnniRouteNodeConfigEntry 20 }

    pnniRouteNodeConfig-BwdMetric2	OBJECT-TYPE
	SYNTAX	INTEGER
	ACCESS	read-write
	STATUS	mandatory
	DESCRIPTION	"Alternate routing parameter for the backward direction of this route. For information learned from PNNI nodes, this is the Available cell rate (in cells per second) for the backward direction of the route. Further information on available bandwidth may be obtainable by reference to the nodal advertisements of the nodes in the path. 0xFFFFFFFF means the metric is not used."
	::= { mibpnniRouteNodeConfigEntry 21 }

    pnniRouteNodeConfig-BwdMetric3	OBJECT-TYPE
	SYNTAX	INTEGER
	ACCESS	read-write
	STATUS	mandatory
	DESCRIPTION	"Alternate routing parameter for the backward direction of this route. For information learned from PNNI nodes, this is the cumulative Max Cell Transfer Delay (in microseconds) for the backward direction of the route.0xFFFFFFFF means the metric is not used."
	::= { mibpnniRouteNodeConfigEntry 22 }

    pnniRouteNodeConfig-BwdMetric4	OBJECT-TYPE
	SYNTAX	INTEGER
	ACCESS	read-write
	STATUS	mandatory
	DESCRIPTION	"Alternate routing parameter for the backward direction of this route. For information learned from PNNI nodes, this is the cumulative Cell Delay Variation (in microseconds) for the backward direction of the route. 0xFFFFFFFF means the metric is not used."
	::= { mibpnniRouteNodeConfigEntry 23 }

    pnniRouteNodeConfig-BwdMetric5	OBJECT-TYPE
	SYNTAX	INTEGER
	ACCESS	read-write
	STATUS	mandatory
	DESCRIPTION	"Alternate routing parameter for the backward direction of this route. For information learned from PNNI nodes, this is the cumulative Cell Loss Ratio for CLP=0 traffic for the backward direction of the route. Cell loss ratio value is computed as 10**(-n) where 'n' is the value returned in this variable.0xFFFFFFFF means the metric isn't used."
	::= { mibpnniRouteNodeConfigEntry 24 }

    pnniRouteNodeConfig-BwdMetric6	OBJECT-TYPE
	SYNTAX	INTEGER
	ACCESS	read-write
	STATUS	mandatory
	DESCRIPTION	"Alternate routing parameter for the backward direction of this route. For information learned from PNNI nodes, this is the cumulative Cell Loss Ratio for CLP=0+1 traffic for the backward direction of the route Cell loss ratio value is computed as 10**(-n) where 'n' is the value returned in this variable.0xFFFFFFFF means the metric isn't used."
	::= { mibpnniRouteNodeConfigEntry 25 }

    pnniRouteNodeConfig-BwdMetric7	OBJECT-TYPE
	SYNTAX	INTEGER
	ACCESS	read-write
	STATUS	mandatory
	DESCRIPTION	"Alternate routing parameter for the backward direction of this route. For information learned from PNNI nodes, this is the Cell Rate Margin (in cells per second) for the backward direction of the route. 0xFFFFFFFF means the metric isn't used."
	::= { mibpnniRouteNodeConfigEntry 26 }

    pnniRouteNodeConfig-BwdMetric8	OBJECT-TYPE
	SYNTAX	INTEGER
	ACCESS	read-write
	STATUS	mandatory
	DESCRIPTION	"Alternate routing parameter for the backward direction of this route. For information learned from PNNI nodes, this is the Variance Factor (in units of 2**(-8)) for the backward direction of the route. 0xFFFFFFFF means the metric isn't used."
	::= { mibpnniRouteNodeConfigEntry 27 }

    pnniRouteNodeConfig-VpCapability	OBJECT-TYPE
	SYNTAX	INTEGER {
		    true (2),
		    false (3)
		}
	ACCESS	read-write
	STATUS	mandatory
	DESCRIPTION	"Attribute indicates whether a VPC setup on this route is possible."
	::= { mibpnniRouteNodeConfigEntry 28 }

    pnniRouteNodeConfig-Active	OBJECT-TYPE
	SYNTAX	INTEGER {
		    no (1),
		    yes (2)
		}
	ACCESS	read-write
	STATUS	mandatory
	DESCRIPTION	"The current state of this route node entry."
	::= { mibpnniRouteNodeConfigEntry 29 }

    pnniRouteNodeConfig-Action-o	OBJECT-TYPE
	SYNTAX	INTEGER {
		    noAction (1),
		    createProfile (2),
		    deleteProfile (3)
		}
	ACCESS	read-write
	STATUS	mandatory
	DESCRIPTION	""
	::= { mibpnniRouteNodeConfigEntry 30 }


	-- The mibpnniRouteAddrConfig table
	--
	-- This table contains parameters for the mibpnniRouteAddrConfig profile
	--

    mibpnniRouteAddrConfigTable	OBJECT-TYPE
	SYNTAX		SEQUENCE OF MibpnniRouteAddrConfigEntry
	ACCESS		not-accessible
	STATUS		mandatory
	DESCRIPTION	"A list of mibpnniRouteAddrConfig profile entries."
	::= { mibpnniRouteAddrConfig 1 }

    mibpnniRouteAddrConfigEntry	OBJECT-TYPE
	SYNTAX		MibpnniRouteAddrConfigEntry
	ACCESS		not-accessible
	STATUS		mandatory
	DESCRIPTION	"A mibpnniRouteAddrConfig entry containing objects that
			 maps to the parameters of mibpnniRouteAddrConfig profile."
	INDEX		{ pnniRouteAddrConfig-Name }
	::= { mibpnniRouteAddrConfigTable 1 }

    MibpnniRouteAddrConfigEntry ::=
	SEQUENCE {
	    pnniRouteAddrConfig-Name
		DisplayString,
	    pnniRouteAddrConfig-AddrIndex-NodeIndex
		INTEGER,
	    pnniRouteAddrConfig-AddrIndex-Address
		DisplayString,
	    pnniRouteAddrConfig-AddrIndex-PrefixLen
		INTEGER,
	    pnniRouteAddrConfig-AddrIndex-Index
		INTEGER,
	    pnniRouteAddrConfig-IfIndex
		INTEGER,
	    pnniRouteAddrConfig-AdvNodeId
		DisplayString,
	    pnniRouteAddrConfig-AdvPortId
		INTEGER,
	    pnniRouteAddrConfig-Type
		INTEGER,
	    pnniRouteAddrConfig-Proto
		INTEGER,
	    pnniRouteAddrConfig-PnniScope
		INTEGER,
	    pnniRouteAddrConfig-VpCapability
		INTEGER,
	    pnniRouteAddrConfig-MetricsTag
		INTEGER,
	    pnniRouteAddrConfig-PtseIdPtseId
		INTEGER,
	    pnniRouteAddrConfig-OriginateAdvert
		INTEGER,
	    pnniRouteAddrConfig-Info
		DisplayString,
	    pnniRouteAddrConfig-OperStatus
		INTEGER,
	    pnniRouteAddrConfig-TimeStamp
		INTEGER,
	    pnniRouteAddrConfig-Active
		INTEGER,
	    pnniRouteAddrConfig-Action-o
		INTEGER
	}

    pnniRouteAddrConfig-Name	OBJECT-TYPE
	SYNTAX	DisplayString
	ACCESS	read-only
	STATUS	mandatory
	DESCRIPTION	"The name of this profile which is corresponding to the value of the addr-index."
	::= { mibpnniRouteAddrConfigEntry 1 }

    pnniRouteAddrConfig-AddrIndex-NodeIndex	OBJECT-TYPE
	SYNTAX	INTEGER
	ACCESS	read-write
	STATUS	mandatory
	DESCRIPTION	"Index that identifies a logical PNNI node."
	::= { mibpnniRouteAddrConfigEntry 2 }

    pnniRouteAddrConfig-AddrIndex-Address	OBJECT-TYPE
	SYNTAX	DisplayString
	ACCESS	read-write
	STATUS	mandatory
	DESCRIPTION	"The value of the ATM End System Address prefix."
	::= { mibpnniRouteAddrConfigEntry 3 }

    pnniRouteAddrConfig-AddrIndex-PrefixLen	OBJECT-TYPE
	SYNTAX	INTEGER
	ACCESS	read-write
	STATUS	mandatory
	DESCRIPTION	"The prefix length to be applied to the ATM End System Address prefix."
	::= { mibpnniRouteAddrConfigEntry 4 }

    pnniRouteAddrConfig-AddrIndex-Index	OBJECT-TYPE
	SYNTAX	INTEGER
	ACCESS	read-write
	STATUS	mandatory
	DESCRIPTION	"An index into the set of listings of connectivity to a given address prefix from a given local node."
	::= { mibpnniRouteAddrConfigEntry 5 }

    pnniRouteAddrConfig-IfIndex	OBJECT-TYPE
	SYNTAX	INTEGER
	ACCESS	read-write
	STATUS	mandatory
	DESCRIPTION	"The local interface over which the reachable address can be reached. The value zero indicates an unknown interface or reachability through a remote node."
	::= { mibpnniRouteAddrConfigEntry 6 }

    pnniRouteAddrConfig-AdvNodeId	OBJECT-TYPE
	SYNTAX	DisplayString
	ACCESS	read-write
	STATUS	mandatory
	DESCRIPTION	"The node ID of a node advertising reachability to the address prefix. If the local node index is zero, then the advertising node ID must be set to all zeros."
	::= { mibpnniRouteAddrConfigEntry 7 }

    pnniRouteAddrConfig-AdvPortId	OBJECT-TYPE
	SYNTAX	INTEGER
	ACCESS	read-write
	STATUS	mandatory
	DESCRIPTION	"The port identifier used from the advertising node to reach the given address prefix."
	::= { mibpnniRouteAddrConfigEntry 8 }

    pnniRouteAddrConfig-Type	OBJECT-TYPE
	SYNTAX	INTEGER {
		    other (2),
		    reject (3),
		    internal (4),
		    exterior (5)
		}
	ACCESS	read-write
	STATUS	mandatory
	DESCRIPTION	"The type (e.g. internal or exterior) of reachability from the advertising node to the address prefix."
	::= { mibpnniRouteAddrConfigEntry 9 }

    pnniRouteAddrConfig-Proto	OBJECT-TYPE
	SYNTAX	INTEGER {
		    other (2),
		    local (3),
		    mgmt (4),
		    pnni (5)
		}
	ACCESS	read-only
	STATUS	mandatory
	DESCRIPTION	"The routing mechanism via which the connectivity from the advertising node to the reachable address prefix was learned."
	::= { mibpnniRouteAddrConfigEntry 10 }

    pnniRouteAddrConfig-PnniScope	OBJECT-TYPE
	SYNTAX	INTEGER
	ACCESS	read-write
	STATUS	mandatory
	DESCRIPTION	"The PNNI scope of advertisement (i.e. level of PNNI hierarchy) of the reachability from the advertising node to the address prefix."
	::= { mibpnniRouteAddrConfigEntry 11 }

    pnniRouteAddrConfig-VpCapability	OBJECT-TYPE
	SYNTAX	INTEGER {
		    true (2),
		    false (3)
		}
	ACCESS	read-write
	STATUS	mandatory
	DESCRIPTION	"Indicates whether VPCs can be established from the advertising node to the reachable address prefix."
	::= { mibpnniRouteAddrConfigEntry 12 }

    pnniRouteAddrConfig-MetricsTag	OBJECT-TYPE
	SYNTAX	INTEGER
	ACCESS	read-write
	STATUS	mandatory
	DESCRIPTION	"The index into the pnniMetricsTable for the traffic parameter values that apply for the connectivity from the advertising node to the reachable address prefix. There will be one or more entries in the pnniMetricsTable whose first instance identifier matches the value of this variable."
	::= { mibpnniRouteAddrConfigEntry 13 }

    pnniRouteAddrConfig-PtseIdPtseId	OBJECT-TYPE
	SYNTAX	INTEGER
	ACCESS	read-only
	STATUS	mandatory
	DESCRIPTION	"For reachable addresses learned via PNNI, this attribute contains the value of the PTSE Identifier for the PTSE being originated by the originating node which contains the information group(s) describing the reachable address. For reachable addresses learned by means other than PNNI, this attribute is set to zero."
	::= { mibpnniRouteAddrConfigEntry 14 }

    pnniRouteAddrConfig-OriginateAdvert	OBJECT-TYPE
	SYNTAX	INTEGER {
		    true (2),
		    false (3)
		}
	ACCESS	read-write
	STATUS	mandatory
	DESCRIPTION	"Whether or not the reachable address specified by this entry is to be advertised by the local node into its PNNI routing domain."
	::= { mibpnniRouteAddrConfigEntry 15 }

    pnniRouteAddrConfig-Info	OBJECT-TYPE
	SYNTAX	DisplayString
	ACCESS	read-only
	STATUS	mandatory
	DESCRIPTION	"A reference to MIB definitions specific to the particular routing protocol which is responsible for this reachable address prefix, as determined by the value specified in the route's pnniRouteAddrProto value. Currently not supportted and is set to 0.0."
	::= { mibpnniRouteAddrConfigEntry 16 }

    pnniRouteAddrConfig-OperStatus	OBJECT-TYPE
	SYNTAX	INTEGER {
		    inactive (2),
		    active (3),
		    advertised (4)
		}
	ACCESS	read-only
	STATUS	mandatory
	DESCRIPTION	"Indicates whether the reachable address prefix is operationally valid and whether it is being advertised by this node."
	::= { mibpnniRouteAddrConfigEntry 17 }

    pnniRouteAddrConfig-TimeStamp	OBJECT-TYPE
	SYNTAX	INTEGER
	ACCESS	read-only
	STATUS	mandatory
	DESCRIPTION	"Indicates when the connectivity from the advertising node to the reachable address prefix became known to the local node."
	::= { mibpnniRouteAddrConfigEntry 18 }

    pnniRouteAddrConfig-Active	OBJECT-TYPE
	SYNTAX	INTEGER {
		    no (1),
		    yes (2)
		}
	ACCESS	read-write
	STATUS	mandatory
	DESCRIPTION	"The current state of this route address entry."
	::= { mibpnniRouteAddrConfigEntry 19 }

    pnniRouteAddrConfig-Action-o	OBJECT-TYPE
	SYNTAX	INTEGER {
		    noAction (1),
		    createProfile (2),
		    deleteProfile (3)
		}
	ACCESS	read-write
	STATUS	mandatory
	DESCRIPTION	""
	::= { mibpnniRouteAddrConfigEntry 20 }


	-- The mibpnniMetricsConfig table
	--
	-- This table contains parameters for the mibpnniMetricsConfig profile
	--

    mibpnniMetricsConfigTable	OBJECT-TYPE
	SYNTAX		SEQUENCE OF MibpnniMetricsConfigEntry
	ACCESS		not-accessible
	STATUS		mandatory
	DESCRIPTION	"A list of mibpnniMetricsConfig profile entries."
	::= { mibpnniMetricsConfig 1 }

    mibpnniMetricsConfigEntry	OBJECT-TYPE
	SYNTAX		MibpnniMetricsConfigEntry
	ACCESS		not-accessible
	STATUS		mandatory
	DESCRIPTION	"A mibpnniMetricsConfig entry containing objects that
			 maps to the parameters of mibpnniMetricsConfig profile."
	INDEX		{ pnniMetricsConfig-MetricsIndex-NodeIndex, pnniMetricsConfig-MetricsIndex-MetricsTag, pnniMetricsConfig-MetricsIndex-MetricsDirection, pnniMetricsConfig-MetricsIndex-MetricsIndex }
	::= { mibpnniMetricsConfigTable 1 }

    MibpnniMetricsConfigEntry ::=
	SEQUENCE {
	    pnniMetricsConfig-MetricsIndex-NodeIndex
		INTEGER,
	    pnniMetricsConfig-MetricsIndex-MetricsTag
		INTEGER,
	    pnniMetricsConfig-MetricsIndex-MetricsDirection
		INTEGER,
	    pnniMetricsConfig-MetricsIndex-MetricsIndex
		INTEGER,
	    pnniMetricsConfig-MetricsClasses
		INTEGER,
	    pnniMetricsConfig-MetricsGcacClp
		INTEGER,
	    pnniMetricsConfig-MetricsAdminWeight
		INTEGER,
	    pnniMetricsConfig-Metrics1
		INTEGER,
	    pnniMetricsConfig-Metrics2
		INTEGER,
	    pnniMetricsConfig-Metrics3
		INTEGER,
	    pnniMetricsConfig-Metrics4
		INTEGER,
	    pnniMetricsConfig-Metrics5
		INTEGER,
	    pnniMetricsConfig-Metrics6
		INTEGER,
	    pnniMetricsConfig-Metrics7
		INTEGER,
	    pnniMetricsConfig-Metrics8
		INTEGER,
	    pnniMetricsConfig-Active
		INTEGER,
	    pnniMetricsConfig-Action-o
		INTEGER
	}

    pnniMetricsConfig-MetricsIndex-NodeIndex	OBJECT-TYPE
	SYNTAX	INTEGER
	ACCESS	read-only
	STATUS	mandatory
	DESCRIPTION	"Index that identifies a logical PNNI node."
	::= { mibpnniMetricsConfigEntry 1 }

    pnniMetricsConfig-MetricsIndex-MetricsTag	OBJECT-TYPE
	SYNTAX	INTEGER
	ACCESS	read-only
	STATUS	mandatory
	DESCRIPTION	"An arbitrary integer that is used to associate a set of traffic parameters that are always advertised together.Within this set, the parameters are distinguished by the service categories and direction to which a set of parameters apply."
	::= { mibpnniMetricsConfigEntry 2 }

    pnniMetricsConfig-MetricsIndex-MetricsDirection	OBJECT-TYPE
	SYNTAX	INTEGER
	ACCESS	read-only
	STATUS	mandatory
	DESCRIPTION	"The direction, with respect to the advertising node,in which the parameters in this entry apply."
	::= { mibpnniMetricsConfigEntry 3 }

    pnniMetricsConfig-MetricsIndex-MetricsIndex	OBJECT-TYPE
	SYNTAX	INTEGER
	ACCESS	read-only
	STATUS	mandatory
	DESCRIPTION	"An index into the set of parameters associated with the given tag and direction."
	::= { mibpnniMetricsConfigEntry 4 }

    pnniMetricsConfig-MetricsClasses	OBJECT-TYPE
	SYNTAX	INTEGER
	ACCESS	read-write
	STATUS	mandatory
	DESCRIPTION	"The service categories to which this set of parameters applies.This is an integer used as a bit mask with each bit that is set representing a single service category for which the resources indicated are avail- able.Bit 5 represents CBR, bit 4 represents real-time VBR, bit 3 represents non-real-time VBR, bit 2 represents ABR, and bit 1 (LSB) represents UBR."
	::= { mibpnniMetricsConfigEntry 5 }

    pnniMetricsConfig-MetricsGcacClp	OBJECT-TYPE
	SYNTAX	INTEGER {
		    clpequal0 (2),
		    clpequal0or1 (3)
		}
	ACCESS	read-write
	STATUS	mandatory
	DESCRIPTION	"Indicates whether the advertised GCAC parameters apply for CLP=0 traffic or for CLP=0+1 traffic."
	::= { mibpnniMetricsConfigEntry 6 }

    pnniMetricsConfig-MetricsAdminWeight	OBJECT-TYPE
	SYNTAX	INTEGER
	ACCESS	read-write
	STATUS	mandatory
	DESCRIPTION	"The administrative weight from the advertising node to the remote end of the PNNI entity or to the reachable address or transit network, for the specified service categories."
	::= { mibpnniMetricsConfigEntry 7 }

    pnniMetricsConfig-Metrics1	OBJECT-TYPE
	SYNTAX	INTEGER
	ACCESS	read-write
	STATUS	mandatory
	DESCRIPTION	"An alternate routing parameter from the advertising node to the remote end of the PNNI entity or to the reachable address or transit network, for the specified service categories."
	::= { mibpnniMetricsConfigEntry 8 }

    pnniMetricsConfig-Metrics2	OBJECT-TYPE
	SYNTAX	INTEGER
	ACCESS	read-write
	STATUS	mandatory
	DESCRIPTION	"An alternate routing parameter from the advertising node to the remote end of the PNNI entity or to the reachable address or transit network, for the specified service categories."
	::= { mibpnniMetricsConfigEntry 9 }

    pnniMetricsConfig-Metrics3	OBJECT-TYPE
	SYNTAX	INTEGER
	ACCESS	read-write
	STATUS	mandatory
	DESCRIPTION	"An alternate routing parameter from the advertising node to the remote end of the PNNI entity or to the reachable address or transit network, for the specified service categories."
	::= { mibpnniMetricsConfigEntry 10 }

    pnniMetricsConfig-Metrics4	OBJECT-TYPE
	SYNTAX	INTEGER
	ACCESS	read-write
	STATUS	mandatory
	DESCRIPTION	"An alternate routing parameter from the advertising node to the remote end of the PNNI entity or to the reachable address or transit network, for the specified service categories."
	::= { mibpnniMetricsConfigEntry 11 }

    pnniMetricsConfig-Metrics5	OBJECT-TYPE
	SYNTAX	INTEGER
	ACCESS	read-write
	STATUS	mandatory
	DESCRIPTION	"An alternate routing parameter from the advertising node to the remote end of the PNNI entity or to the reachable address or transit network, for the specified service categories."
	::= { mibpnniMetricsConfigEntry 12 }

    pnniMetricsConfig-Metrics6	OBJECT-TYPE
	SYNTAX	INTEGER
	ACCESS	read-write
	STATUS	mandatory
	DESCRIPTION	"An alternate routing parameter from the advertising node to the remote end of the PNNI entity or to the reachable address or transit network, for the specified service categories."
	::= { mibpnniMetricsConfigEntry 13 }

    pnniMetricsConfig-Metrics7	OBJECT-TYPE
	SYNTAX	INTEGER
	ACCESS	read-write
	STATUS	mandatory
	DESCRIPTION	"An alternate routing parameter from the advertising node to the remote end of the PNNI entity or to the reachable address or transit network, for the specified service categories."
	::= { mibpnniMetricsConfigEntry 14 }

    pnniMetricsConfig-Metrics8	OBJECT-TYPE
	SYNTAX	INTEGER
	ACCESS	read-write
	STATUS	mandatory
	DESCRIPTION	"An alternate routing parameter from the advertising node to the remote end of the PNNI entity or to the reachable address or transit network, for the specified service categories."
	::= { mibpnniMetricsConfigEntry 15 }

    pnniMetricsConfig-Active	OBJECT-TYPE
	SYNTAX	INTEGER {
		    no (1),
		    yes (2)
		}
	ACCESS	read-write
	STATUS	mandatory
	DESCRIPTION	"The current state of this metrics entry"
	::= { mibpnniMetricsConfigEntry 16 }

    pnniMetricsConfig-Action-o	OBJECT-TYPE
	SYNTAX	INTEGER {
		    noAction (1),
		    createProfile (2),
		    deleteProfile (3)
		}
	ACCESS	read-write
	STATUS	mandatory
	DESCRIPTION	""
	::= { mibpnniMetricsConfigEntry 17 }

END
