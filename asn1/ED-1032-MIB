--
-- FILE NAME = ED-1032.MIB ($Revision:   1.7  $)
-- CONTENTS  = MIB Definition for ED-1032 Fibre Channel Switch
--

ED-1032-MIB DEFINITIONS ::= BEGIN

   IMPORTS
      enterprises, Counter
         FROM RFC1155-SMI
      OBJECT-TYPE
         FROM RFC-1212
      TRAP-TYPE
         FROM RFC-1215;

   --
   -- Enterprise Specific Object Identifiers
   --

   mcData         OBJECT IDENTIFIER ::= { enterprises 289 }
   -- Product lines or generic product information
   -- common      OBJECT IDENTIFIER ::= { mcData 1 }
   commDev        OBJECT IDENTIFIER ::= { mcData 2 } -- communication devices

   -- Fibre Channel product lines
   fibreChannel   OBJECT IDENTIFIER ::= { commDev 1 }
   fcSwitch       OBJECT IDENTIFIER ::= { fibreChannel 1 }
   ed-1032        OBJECT IDENTIFIER ::= { fcSwitch 1 }

   -- textual conventions

   DisplayString ::= OCTET STRING

   Ed1032SysOperStatus  ::= INTEGER {
      operational       (1),
      redundant-failure (2),
      minor-failure     (3),
      major-failure     (4),
      not-operational   (5)
   }

   Ed1032SysState ::= INTEGER {
      online         (1),
      coming-online  (2),
      offline        (3),
      going-offline  (4)
   }

   Ed1032FruCode ::= INTEGER {
      fru-bkplane   (1) ,    -- Backplane
      fru-ctp       (2) ,    -- Control Processor card
      fru-mpc       (3) ,    -- Message Path Controller card
      fru-cmm       (4) ,    -- Central Memory Module card
      fru-fan       (5) ,    -- Fan module
      fru-power     (6) ,    -- Power supply module
      fru-panel     (7) ,    -- Operator panel
      fru-gsm       (8) ,    -- G_Port Module card: short wave, multimode (GSM)
      fru-gls       (9) ,    -- G_Port Module card: long wave, single-mode (GLS)
      fru-glx       (10),    -- G_Port Module card: long wave, mixed-mode (GLX)
      fru-lsm       (11),    -- L_Port Module card: short wave, multimode (LSM)
      fru-gxx       (12)     -- G_Port Module card: combo GSM/GLS (GXX)
   }

   Ed1032FruPosition ::= INTEGER (0..255)
   Ed1032FruStatus  ::= INTEGER {
      active      (1),
      backup      (2),
      update-busy (3),
      failed      (4)
   }

   Ed1032PortIndex ::= INTEGER (0..2048)

   Ed1032PortPhyState   ::= INTEGER {
        psNotInstalled  (1),
        psAvailable     (2),
        psBlocked       (3),
        psUnavailable   (4),
        psLinkFailure   (5),
        psLinkFailLOL   (6),
        psIntDiags      (7),
        psExtLoop       (8),
        psPortFail      (9),
        psSR            (10),
        psLR            (11)
   }

   Ed1032PortStatus ::= INTEGER {
                online  (1),
                offline (2),
                testing (3),
                faulty  (4)
   }

   Ed1032PortAdmStatus  ::= INTEGER {
      online   (1),
      offline  (2),
      testing  (3)
   }

   -- Groups in ED-1032 MIB

   ed1032Sys   OBJECT IDENTIFIER ::= { ed-1032 1 }

   ed1032Fru    OBJECT IDENTIFIER ::= { ed-1032 2 }

   ed1032Port    OBJECT IDENTIFIER ::= { ed-1032 3 }

   -- reserved    OBJECT IDENTIFIER ::= { ed-1032 4 }
   -- reserved    OBJECT IDENTIFIER ::= { ed-1032 5 }
   -- reserved    OBJECT IDENTIFIER ::= { ed-1032 6 }
   -- reserved    OBJECT IDENTIFIER ::= { ed-1032 7 }
   -- reserved    OBJECT IDENTIFIER ::= { ed-1032 8 }
   -- reserved    OBJECT IDENTIFIER ::= { ed-1032 9 }

   --
   -- the System Group
   --

   ed1032SysCurrentDate         OBJECT-TYPE
         SYNTAX         DisplayString (SIZE (64))
         ACCESS         read-only
         STATUS         mandatory
         DESCRIPTION    "The current date information."
   ::= { ed1032Sys 1 }

   ed1032SysBootDate            OBJECT-TYPE
         SYNTAX         DisplayString (SIZE (64))
         ACCESS         read-only
         STATUS         mandatory
         DESCRIPTION    "The date and time of the last IPL"
   ::= { ed1032Sys 2 }

   ed1032SysFirmwareVersion     OBJECT-TYPE
         SYNTAX         DisplayString (SIZE (24))
         ACCESS         read-only
         STATUS         mandatory
         DESCRIPTION    "The current version of the firmware."
   ::= { ed1032Sys 3 }

   ed1032SysTypeNum   OBJECT-TYPE
         SYNTAX         DisplayString (SIZE (64))
    ACCESS              read-only
         STATUS         mandatory
         DESCRIPTION    "This object identifies ASCII type
    number for the unit."
   ::= { ed1032Sys 4 }

   ed1032SysModelNum    OBJECT-TYPE
         SYNTAX      DisplayString (SIZE (64))
    ACCESS           read-only
         STATUS      mandatory
         DESCRIPTION    "This object identifies ASCII
    model number for the unit."
   ::= { ed1032Sys 5 }

   ed1032SysMfg         OBJECT-TYPE
         SYNTAX      DisplayString (SIZE (64))
    ACCESS           read-only
         STATUS      mandatory
         DESCRIPTION    "This object identifies ASCII
    manufacturer for the unit."
   ::= { ed1032Sys 6 }

   ed1032SysPlantOfMfg    OBJECT-TYPE
         SYNTAX      DisplayString (SIZE (64))
    ACCESS           read-only
         STATUS      mandatory
         DESCRIPTION    "This object identifies ASCII plant
    of manufacturer for the unit."
   ::= { ed1032Sys 7 }

   ed1032SysSeqNum    OBJECT-TYPE
         SYNTAX      DisplayString (SIZE (64))
    ACCESS           read-only
         STATUS      mandatory
         DESCRIPTION    "This object identifies ASCII
    sequence number for the unit."
   ::= { ed1032Sys 8 }

   ed1032SysEcLevel    OBJECT-TYPE
         SYNTAX      DisplayString (SIZE (64))
    ACCESS           read-only
         STATUS      mandatory
         DESCRIPTION    "This object identifies ASCII EC level
    ID for the unit."
   ::= { ed1032Sys 9 }

   ed1032SysOemSerialNum    OBJECT-TYPE
         SYNTAX      DisplayString (SIZE (64))
    ACCESS           read-only
         STATUS      mandatory
         DESCRIPTION    "This object identifies ASCII OEM
    serial number for the unit."
   ::= { ed1032Sys 10 }

   ed1032SysOperStatus          OBJECT-TYPE
         SYNTAX         Ed1032SysOperStatus
         ACCESS         read-only
         STATUS         mandatory
         DESCRIPTION    "The current operational status
    of the switch. The values are defined as follow:
    operational (1), redundant-failure (2), minor-failure (3),
    major-failure (4), not-operational (5)."
   ::= { ed1032Sys 11 }

   ed1032SysState               OBJECT-TYPE
         SYNTAX         Ed1032SysState
         ACCESS         read-only
         STATUS         mandatory
         DESCRIPTION    "If the edOperStatus of the switch is
    operational, the switch will be in one of the four states:
    online(1), coming-online(2), offline(3), and going-offline(4)."
   ::= { ed1032Sys 12 }

   ed1032SysAdmStatus           OBJECT-TYPE
    SYNTAX              INTEGER {
                                online  (1),
                                offline (2)
                        }
         ACCESS         read-write
         STATUS         mandatory
         DESCRIPTION    "The desired administrative status
    of the switch. A management station may place the switch
    in a desired state by setting this object accordingly.
    The desired administrative status are online(1) and offline(2).
    The online means setting the switch to be accessible by
    an external Fibre Channel port, and offline means setting
    the switch to be inaccessible."
   ::= { ed1032Sys 13 }

   --
   -- End of System Group
   --

   --
   -- Fibre Channel FRU Group
   -- This group contains FRU information of each Fibre Channel Module.
   --

   ed1032FruTable     OBJECT-TYPE
      SYNTAX         SEQUENCE OF Ed1032FruEntry
      ACCESS         not-accessible
      STATUS         mandatory
      DESCRIPTION    "A table that contains one entry for each module."
      ::= { ed1032Fru 1 }

   ed1032FruEntry     OBJECT-TYPE
      SYNTAX           Ed1032FruEntry
      ACCESS           not-accessible
      STATUS           mandatory
      DESCRIPTION      "An entry containing the service parameters of the module."
      INDEX   { ed1032FruCode,
                ed1032FruPosition }
      ::= { ed1032FruTable 1 }

   Ed1032FruEntry ::= SEQUENCE {
      ed1032FruCode         Ed1032FruCode,
      ed1032FruPosition     Ed1032FruPosition,
      ed1032FruStatus       Ed1032FruStatus,
      ed1032FruPartNumber   DisplayString (SIZE (64)),
      ed1032FruSerialNumber DisplayString (SIZE (64)),
      ed1032FruPowerOnHours Counter,
      ed1032FruTestDate     DisplayString (SIZE (64))
   }

   ed1032FruCode     OBJECT-TYPE
      SYNTAX         Ed1032FruCode
      ACCESS         read-only
      STATUS         mandatory
      DESCRIPTION    "Field Replaceable Unit.
      A hardware component of the product that is replaceable
      as an entire unit. Each module defined in this MIB has
      a fixed FRU code. The values are defined as follow:
      fru-none (0) , fru-bkplane  (1), fru-ctp  (2), fru-mpc (3),
      fru-cmm (4), fru-fan (5), fru-power (6), fru-panel (7),
      fru-gsm (8), fru-gls (9), fru-glx (10), fru-lsm (11), fru-gxx (12)."
      ::= { ed1032FruEntry 1 }

   ed1032FruPosition    OBJECT-TYPE
      SYNTAX             Ed1032FruPosition
      ACCESS             read-only
      STATUS             mandatory
      DESCRIPTION    "This object identifies the position
      of the module. Port cards start from 1 to 8.
      All other cards start from 1 to 1 or 2."
      ::= { ed1032FruEntry 2 }

   ed1032FruStatus    OBJECT-TYPE
      SYNTAX           Ed1032FruStatus
      ACCESS           read-only
      STATUS           mandatory
      DESCRIPTION    "This object identifies the operational
      status of the module. The active(1)
      state indicates that the current module is active.
      The backup(2) state indicates that the back up module is used.
      update-busy (3) state indicates that the module is
      in the updating process. The failed(4) state indicates
      that the current module is failed."
      ::= { ed1032FruEntry 3 }

   ed1032FruPartNumber   OBJECT-TYPE
      SYNTAX              DisplayString (SIZE (64))
      ACCESS              read-only
      STATUS              mandatory
      DESCRIPTION    "This object identifies the part number of the module."
      ::= { ed1032FruEntry 4 }

   ed1032FruSerialNumber    OBJECT-TYPE
      SYNTAX                 DisplayString (SIZE (64))
      ACCESS                 read-only
      STATUS                 mandatory
      DESCRIPTION    "This object identifies the serial number of the module."
      ::= { ed1032FruEntry 5 }

   ed1032FruPowerOnHours    OBJECT-TYPE
      SYNTAX                 Counter
      ACCESS                 read-only
      STATUS                 mandatory
      DESCRIPTION    "This object indicates the number of the hours that the
                      FRU has been in operation."
      ::= { ed1032FruEntry 6 }

   ed1032FruTestDate    OBJECT-TYPE
      SYNTAX             DisplayString (SIZE (64))
      ACCESS             read-only
      STATUS             mandatory
      DESCRIPTION    "This object indicates final test date of the module."
      ::= { ed1032FruEntry 7 }

   --
   -- End of Fibre Channel FRU Group
   --

   --
   -- Fibre Channel Port Group
   -- This group contains information about each Fibre Channel port.
   --

   ed1032PortTable     OBJECT-TYPE
      SYNTAX         SEQUENCE OF Ed1032PortEntry
      ACCESS         not-accessible
      STATUS         mandatory
      DESCRIPTION    "A table that contains one entry
      for each switch port (stitch only)."
      ::= { ed1032Port 1 }

   ed1032PortEntry     OBJECT-TYPE
      SYNTAX         Ed1032PortEntry
      ACCESS         not-accessible
      STATUS         mandatory
      DESCRIPTION    "An entry containing the information of the switch port."
      INDEX   { ed1032PortIndex }
      ::= { ed1032PortTable 1 }

   Ed1032PortEntry ::= SEQUENCE {
      ed1032PortIndex           Ed1032PortIndex,
      ed1032PortPhyState        Ed1032PortPhyState,
      ed1032PortOpStatus        Ed1032PortStatus,
           ed1032PortAdmStatus       Ed1032PortAdmStatus,

           -- the rest is mapped to gstat_t
           ed1032PortTxWords                 Counter,
           ed1032PortRxWords                 Counter,
           ed1032PortTxFrames        Counter,
           ed1032PortRxFrames        Counter,
           ed1032PortRxC2Frames      Counter,
           ed1032PortRxC3Frames      Counter,
           ed1032PortRxLCs                   Counter,
           ed1032PortRxMcasts        Counter,
           ed1032PortTooManyRdys          Counter,
           ed1032PortNoTxCredits          Counter,
           ed1032PortRxEncFrs        Counter,
           ed1032PortRxCrcs                  Counter,
           ed1032PortRxTruncs        Counter,
           ed1032PortRxTooLongs      Counter,
           ed1032PortRxBadEofs       Counter,
           ed1032PortRxBadOs                 Counter,
           ed1032PortC3Discards      Counter,
           ed1032PortMcastTimedOuts  Counter,
           ed1032PortTxMcasts        Counter,
      ed1032PortTxThroughput    Counter,
      ed1032PortRxThroughput    Counter
   }

   ed1032PortIndex     OBJECT-TYPE
      SYNTAX         Ed1032PortIndex
      ACCESS         read-only
      STATUS         mandatory
      DESCRIPTION    "This object identifies the switch port."
      ::= { ed1032PortEntry 1 }

   ed1032PortPhyState   OBJECT-TYPE
    SYNTAX              Ed1032PortPhyState
    ACCESS              read-only
         STATUS         mandatory
         DESCRIPTION    "This object identifies the physical state of the port."
   ::= { ed1032PortEntry 2 }

   ed1032PortOpStatus  OBJECT-TYPE
      SYNTAX         Ed1032PortStatus
      ACCESS         read-only
      STATUS         mandatory
      DESCRIPTION    "This object identifies the operational
      status of the port. The online state indicates that user frames
      can be passed."
      ::= { ed1032PortEntry 3 }

   ed1032PortAdmStatus  OBJECT-TYPE
         SYNTAX         Ed1032PortAdmStatus
         ACCESS         read-write
         STATUS         mandatory
         DESCRIPTION    "The desired state of the port.
    A management station may place the port in a desired
    state by setting this object accordingly. The testing(3)
    state indicates that no user frames can be passed.
    As the result of either explicit management action
    or per configuration information accessible by the switch,
    ed1032PortAdmStatus is then changed to either the online(1)
    or testing(3) states,       or remains in the offline state."
   ::= { ed1032PortEntry 4 }

   ed1032PortTxWords    OBJECT-TYPE
         SYNTAX         Counter
         ACCESS         read-only
         STATUS         mandatory
         DESCRIPTION    "This object counts the number of
    Fibre Channel words that the port has transmitted."
   ::= { ed1032PortEntry 11 }

   ed1032PortRxWords    OBJECT-TYPE
         SYNTAX         Counter
         ACCESS         read-only
         STATUS         mandatory
         DESCRIPTION    "This object counts the number of
    Fibre Channel words that the port has received."
   ::= { ed1032PortEntry 12 }
                -- does this include primitive signals, primitive sequence or
                -- just words within frames?

   ed1032PortTxFrames   OBJECT-TYPE
         SYNTAX         Counter
         ACCESS         read-only
         STATUS         mandatory
         DESCRIPTION    "This object counts the number of
    (Fibre Channel) frames that the port has transmitted."
   ::= { ed1032PortEntry 13 }

   ed1032PortRxFrames   OBJECT-TYPE
         SYNTAX         Counter
         ACCESS         read-only
         STATUS         mandatory
         DESCRIPTION    "This object counts the number of
    (Fibre Channel) frames that the port has received."
   ::= { ed1032PortEntry 14 }

   ed1032PortRxC2Frames OBJECT-TYPE
         SYNTAX         Counter
         ACCESS         read-only
         STATUS         mandatory
         DESCRIPTION    "This object counts the number of
    Class 2 frames that the port has received."
   ::= { ed1032PortEntry 15 }

   ed1032PortRxC3Frames OBJECT-TYPE
         SYNTAX         Counter
         ACCESS         read-only
         STATUS         mandatory
         DESCRIPTION    "This object counts the number of
    Class 3 frames that the port has received."
   ::= { ed1032PortEntry 16 }

   ed1032PortRxLCs              OBJECT-TYPE
    SYNTAX              Counter
         ACCESS         read-only
    STATUS              mandatory
    DESCRIPTION "This object counts the number of
    Link Control frames that the port has received."
   ::= { ed1032PortEntry 17 }

   ed1032PortRxMcasts   OBJECT-TYPE
         SYNTAX         Counter
    ACCESS              read-only
         STATUS         mandatory
         DESCRIPTION    "This object counts the number of
    Multicast frames that the port has received."
   ::= { ed1032PortEntry 18 }

   ed1032PortTooManyRdys        OBJECT-TYPE
    SYNTAX              Counter
         ACCESS         read-only
         STATUS         mandatory
         DESCRIPTION    "This object counts the number of
    times when RDYs exceeds the frames received."
   ::= { ed1032PortEntry 19 }

   ed1032PortNoTxCredits        OBJECT-TYPE
         SYNTAX         Counter
         ACCESS         read-only
    STATUS              mandatory
         DESCRIPTION    "This object counts the amount of time
    that frame transmission is blocked by a transmit credit of zero.
    This is sampled once every 120 53.125 MHZ clocks,
    and the counter is incremented by 1 if the condition is true."
   ::= { ed1032PortEntry 20 }

   ed1032PortRxEncFrs   OBJECT-TYPE
    SYNTAX              Counter
    ACCESS              read-only
    STATUS              mandatory
         DESCRIPTION    "This object counts the number of
    encoding error or disparity error inside or outside
    frames received."
   ::= { ed1032PortEntry 21 }

   ed1032PortRxCrcs             OBJECT-TYPE
         SYNTAX         Counter
         ACCESS         read-only
         STATUS         mandatory
         DESCRIPTION    "This object counts the number of
    CRC errors detected for frames received."
   ::= { ed1032PortEntry 22 }

   ed1032PortRxTruncs   OBJECT-TYPE
    SYNTAX              Counter
    ACCESS              read-only
    STATUS              mandatory
    DESCRIPTION "This object counts the number of
    truncated frames that the port has received."
   ::= { ed1032PortEntry 23 }

   ed1032PortRxTooLongs OBJECT-TYPE
         SYNTAX         Counter
    ACCESS              read-only
    STATUS              mandatory
         DESCRIPTION    "This object counts the number of
    received frames that are too long."
   ::= { ed1032PortEntry 24 }

   ed1032PortRxBadEofs  OBJECT-TYPE
         SYNTAX         Counter
         ACCESS         read-only
         STATUS         mandatory
         DESCRIPTION    "This object counts the number of
    received frames that have bad EOF delimiter."
   ::= { ed1032PortEntry 25 }

   ed1032PortRxBadOs            OBJECT-TYPE
    SYNTAX              Counter
         ACCESS         read-only
         STATUS         mandatory
         DESCRIPTION    "This object counts the number of
    invalid Ordered Sets received."
   ::= { ed1032PortEntry 26 }

   ed1032PortC3Discards OBJECT-TYPE
         SYNTAX         Counter
         ACCESS         read-only
         STATUS         mandatory
         DESCRIPTION    "This object counts the number of
    Class 3 frames that the port has discarded."
   ::= { ed1032PortEntry 27 }

   ed1032PortMcastTimedOuts     OBJECT-TYPE
    SYNTAX              Counter
         ACCESS         read-only
         STATUS         mandatory
         DESCRIPTION    "This object counts the number of
    Multicast frames that has been timed out."
   ::= { ed1032PortEntry 28 }

   ed1032PortTxMcasts   OBJECT-TYPE
         SYNTAX         Counter
         ACCESS         read-only
         STATUS         mandatory
         DESCRIPTION    "This object counts the number of
    Multicast frames that has been transmitted."
   ::= { ed1032PortEntry 29 }

   ed1032PortTxThroughput       OBJECT-TYPE
         SYNTAX         Counter
         ACCESS         read-only
         STATUS         mandatory
         DESCRIPTION    "This object presents the Bps transmission rate."
   ::= { ed1032PortEntry 30 }

   ed1032PortRxThroughput       OBJECT-TYPE
         SYNTAX         Counter
         ACCESS         read-only
         STATUS         mandatory
         DESCRIPTION    "This object presents the Bps reception rate."
   ::= { ed1032PortEntry 31 }

   --
   -- End of Fibre Channel Port Group
   --


   --
   -- ED-1032 Enterprise Specific Trap Definitions
   --

   ed1032PortScn       TRAP-TYPE
      ENTERPRISE     mcData
      VARIABLES      { ed1032PortOpStatus }
      DESCRIPTION    "An ed1032PortScn(1) is generated
      whenever a Fc_Port changes its operational state.
      For instance, the Fc_Port goes from on-line to offline."
      ::= 1

   ed1032FruScn       TRAP-TYPE
      ENTERPRISE     mcData
      VARIABLES      { ed1032FruStatus }
      DESCRIPTION    "An ed1032FruScn(2) is generated
      whenever a FRU status changes its operational state."
      ::= 2

END   -- ED-1032-MIB
