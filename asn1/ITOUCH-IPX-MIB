-- $Id: it-ipx-mib.mib,v 1.1 2000/07/25 14:32:09 sse Exp $
            ITOUCH-IPX-MIB DEFINITIONS ::= BEGIN

                    IMPORTS
                            Counter
                                    FROM RFC1155-SMI
                            DisplayString
                                    FROM RFC1213-MIB
                            iTouch
                                    FROM ITOUCH-MIB
                            OBJECT-TYPE
                                    FROM RFC-1212;

            xIpx            OBJECT IDENTIFIER ::= { iTouch 15 }

            -- ITouch IPX subgroups

            xIpxSystem      OBJECT IDENTIFIER ::= { xIpx 1 }
            xIpxIf          OBJECT IDENTIFIER ::= { xIpx 2 }
            xIpxNetbios     OBJECT IDENTIFIER ::= { xIpx 3 }
            xIpxRip         OBJECT IDENTIFIER ::= { xIpx 4 }
            xIpxSap         OBJECT IDENTIFIER ::= { xIpx 5 }
	    xIpxFilter      OBJECT IDENTIFIER ::= { xIpx 6 }
            -- number 7 reserved
            xIpxPrinter     OBJECT IDENTIFIER ::= { xIpx 8 }


            -- This is a MIB module for all iTouch Communications systems that
            -- implement IPX.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.


            -- the System group

            -- Implementation of this group is mandatory for all iTouch
            -- systems that implement IPX

            ipxRouting OBJECT-TYPE
                SYNTAX INTEGER { disabled(1), enabled(2) }
                ACCESS read-write
                STATUS mandatory
                DESCRIPTION
                    "Control for IPX routing services."
                ::= { xIpxSystem 1 }

            ipxInternalNetwork OBJECT-TYPE
                SYNTAX INTEGER (1..4294967294)
                ACCESS read-write
                STATUS mandatory
                DESCRIPTION
                    "The IPX Internal Network to use on the the IPX Router."
		DEFVAL { 1 }
                ::= { xIpxSystem 2 }

            -- the Interface group

            -- Implementation of this group is mandatory for all iTouch
            -- systems that implement IPX

            ipxIfTable OBJECT-TYPE
                SYNTAX SEQUENCE OF IpxIfEntry
                ACCESS not-accessible
                STATUS mandatory
                DESCRIPTION
                    "A list of IPX interface entries."
                ::= { xIpxIf 1 }

            ipxIfEntry OBJECT-TYPE
                SYNTAX IpxIfEntry
                ACCESS not-accessible
                STATUS mandatory
                DESCRIPTION
                    "IPX interface parameters and counters."
                INDEX { ipxIfIndex }
                ::= { ipxIfTable 1 }

            IpxIfEntry ::=
                SEQUENCE {
                    ipxIfIndex
                        INTEGER,
                    ipxIfState
                        INTEGER,
                    ipxIfNetwork
                        INTEGER,
                    ipxIfFrameStyle
                        INTEGER,
                    ipxIfFramesIn
                        Counter,
                    ipxIfFramesOut
                        Counter,
                    ipxIfErrors
                        Counter,
                    ipxIfTransitDelay
                        INTEGER,
                    ipxIfTransitDelayActual
                        INTEGER,
                    ipxIfProtocolPriority
                        INTEGER,
                    ipxIfWatchdogSpoof
                        INTEGER,
                    ipxIfStatusNetwork
                        INTEGER
                }

            ipxIfIndex OBJECT-TYPE
                SYNTAX INTEGER
                ACCESS read-only
                STATUS mandatory
                DESCRIPTION
                    "An index value that uniquely identifies an IPX 
                    interface.  The interface identified by a particular 
                    value of this index is the same interface as 
                    identified by the same value of ifIndex."
                ::= { ipxIfEntry 1 }

            ipxIfState OBJECT-TYPE
                SYNTAX INTEGER { disabled(1), enabled(2) }
                ACCESS read-write
                STATUS mandatory
                DESCRIPTION
                    "Control for IPX routing services for this 
                    interface."
                DEFVAL { enabled }
                ::= { ipxIfEntry 2 }

            ipxIfNetwork OBJECT-TYPE
                SYNTAX INTEGER
                ACCESS read-write
                STATUS mandatory
                DESCRIPTION
                    "The IPX network number of the network to which this 
                    interface is attached."
                DEFVAL { 0 }
                ::= { ipxIfEntry 3 }

            ipxIfFrameStyle OBJECT-TYPE
                SYNTAX INTEGER { ethernet(1), ieee8023(2), ieee8022(3), ieee802Snap(4) }
                ACCESS read-write
                STATUS mandatory
                DESCRIPTION
                    "Control for the CSMA/CD frame style to use on this 
                    interface."
                DEFVAL { ieee8023 }
                ::= { ipxIfEntry 4 }

            ipxIfFramesIn OBJECT-TYPE
                SYNTAX Counter
                ACCESS read-only
                STATUS mandatory
                DESCRIPTION
                    "The number of IPX frames received on this 
                    interface."
                ::= { ipxIfEntry 5 }

            ipxIfFramesOut OBJECT-TYPE
                SYNTAX Counter
                ACCESS read-only
                STATUS mandatory
                DESCRIPTION
                    "The number of IPX frames sent on this interface."
                ::= { ipxIfEntry 6 }

            ipxIfErrors OBJECT-TYPE
                SYNTAX Counter
                ACCESS read-only
                STATUS mandatory
                DESCRIPTION
                    "The number of IPX errors seen on this interface."
                ::= { ipxIfEntry 7 }

            ipxIfTransitDelay OBJECT-TYPE
                SYNTAX INTEGER
                ACCESS read-write
                STATUS mandatory
                DESCRIPTION
                    "The number of 55 millisecond ticks it takes for a 
                    packet to  travel from one destination to another on 
                    the interface.  A value of 0 means that the system 
                    will calculate this value based on the measured 
                    speed of the interface."
                ::= { ipxIfEntry 8 }

            ipxIfTransitDelayActual OBJECT-TYPE
                SYNTAX INTEGER     
                ACCESS read-only
                STATUS mandatory
                DESCRIPTION
                    "The number of 55 millisecond ticks it takes for a 
                    packet to travel from one destination to another on 
                    the interface."
                ::= { ipxIfEntry 9 }

            ipxIfProtocolPriority OBJECT-TYPE
                SYNTAX INTEGER { low(1), medium(3), high(5) }
                ACCESS read-write
                STATUS mandatory
                DESCRIPTION
                    "This value defines the priority at which all 
                    Internet Routed packets will be placed on the WAN 
                    output queue."
                DEFVAL { medium }
                ::= { ipxIfEntry 10 }

            ipxIfWatchdogSpoof OBJECT-TYPE
                SYNTAX INTEGER { disabled(1), enabled(2) }
                ACCESS read-write
                STATUS mandatory
                DESCRIPTION
                    "Control for whether or not this router
                    responds to IPX watchog requests on this
                    interface."
                DEFVAL { disabled }
                ::= { ipxIfEntry 11 }

            ipxIfStatusNetwork OBJECT-TYPE
               SYNTAX INTEGER
                ACCESS read-only
                STATUS mandatory
                DESCRIPTION
                    "The IPX network number that is actually in use on the 
                    attached interface.  This value may have been learned 
		     via listening to the attached network."
                DEFVAL { 0 }
                ::= { ipxIfEntry 12 }


            -- the Netbios group

            -- Implementation of this group is mandatory for all iTouch
            -- systems that implement IPX Netbios

            ipxNetbiosHopLimit OBJECT-TYPE
                SYNTAX INTEGER (0..255)
                ACCESS read-write
                STATUS mandatory
                DESCRIPTION
                    "Maximum number of hops that an IPX Netbios packet 
                    may make."
                ::= { xIpxNetbios 1 }

            ipxNetbiosIfTable OBJECT-TYPE
                SYNTAX SEQUENCE OF IpxNetbiosIfEntry
                ACCESS not-accessible
                STATUS mandatory
                DESCRIPTION
                    "A list of IPX interface entries."
                ::= { xIpxNetbios 2 }

            ipxNetbiosIfEntry OBJECT-TYPE
                SYNTAX IpxNetbiosIfEntry
                ACCESS not-accessible
                STATUS mandatory
                DESCRIPTION
                    "IPX interface parameters and counters."
                INDEX { ipxNetbiosIfIndex }
                ::= { ipxNetbiosIfTable 1 }

            IpxNetbiosIfEntry ::=
                SEQUENCE {
                    ipxNetbiosIfIndex
                        INTEGER,
                    ipxIfNetbiosForwarding
                        INTEGER,
                    ipxIfNetbiosIn
                        Counter,
                    ipxIfNetbiosOut
                        Counter
                }

            ipxNetbiosIfIndex OBJECT-TYPE
                SYNTAX INTEGER
                ACCESS read-only
                STATUS mandatory
                DESCRIPTION
                    "An index value that uniquely identifies an IPX 
                    interface.  The interface identified by a particular 
                    value of this index is the same interface as 
                    identified by the same value of ifIndex."
                ::= { ipxNetbiosIfEntry 1 }

            ipxIfNetbiosForwarding OBJECT-TYPE
                SYNTAX INTEGER { disabled(1), enabled(2) }
                ACCESS read-write
                STATUS mandatory
                DESCRIPTION
                    "Control whether Netbios packet will be forwarded in 
                    or out on this interface."
                DEFVAL { enabled }
                ::= { ipxNetbiosIfEntry 2 }

            ipxIfNetbiosIn OBJECT-TYPE
                SYNTAX Counter
                ACCESS read-only
                STATUS mandatory
                DESCRIPTION
                    "The number of IPX Netbios frames received on this 
                    interface."
                ::= { ipxNetbiosIfEntry 3 }

            ipxIfNetbiosOut OBJECT-TYPE
                SYNTAX Counter
                ACCESS read-only
                STATUS mandatory
                DESCRIPTION
                    "The number of IPX Netbios frames sent on this 
                    interface."
                ::= { ipxNetbiosIfEntry 4 }


            -- the RIP group

            -- Implementation of this group is mandatory for all iTouch
            -- systems that implement IPX RIP

            ipxRipIfTable OBJECT-TYPE
                SYNTAX SEQUENCE OF IpxRipIfEntry
                ACCESS not-accessible
                STATUS mandatory
                DESCRIPTION
                    "A list of IPX interface entries."
                ::= { xIpxRip 1 }

            ipxRipIfEntry OBJECT-TYPE
                SYNTAX IpxRipIfEntry
                ACCESS not-accessible
                STATUS mandatory
                DESCRIPTION
                    "IPX interface parameters and counters."
                INDEX { ipxRipIfIndex }
                ::= { ipxRipIfTable 1 }

            IpxRipIfEntry ::=
                SEQUENCE {
                    ipxRipIfIndex
                        INTEGER,
                    ipxIfRipBcst
                        INTEGER,
                    ipxIfRipBcstDiscardTimeout
                        INTEGER,
                    ipxIfRipBcstTimer
                        INTEGER,
                    ipxIfRipIn
                        Counter,
                    ipxIfRipOut
                        Counter,
                    ipxIfRipAgedOut
                        Counter
                }

            ipxRipIfIndex OBJECT-TYPE
                SYNTAX INTEGER
                ACCESS read-only
                STATUS mandatory
                DESCRIPTION
                    "An index value that uniquely identifies an IPX 
                    interface.  The interface identified by a particular 
                    value of this index is the same interface as 
                    identified by the same value of ifIndex."
                ::= { ipxRipIfEntry 1 }

            ipxIfRipBcst OBJECT-TYPE
                SYNTAX INTEGER { disabled(1), enabled(2), propUpdateOnly(3), demandCircuit(4) }
                ACCESS read-write
                STATUS mandatory
                DESCRIPTION
                    "Control whether RIP packets will be broadcasted out 
                    this interface."
                DEFVAL { enabled }
                ::= { ipxRipIfEntry 2 }

            ipxIfRipBcstDiscardTimeout OBJECT-TYPE
                SYNTAX INTEGER
                ACCESS read-write
                STATUS mandatory
                DESCRIPTION
                    "The number of seconds to wait before discarding 
                    information learned from a RIP broadcast."
                DEFVAL { 180 }
                ::= { ipxRipIfEntry 3 }

            ipxIfRipBcstTimer OBJECT-TYPE
                SYNTAX INTEGER
                ACCESS read-write
                STATUS mandatory
                DESCRIPTION
                    "The number of seconds to wait between sending out 
                    RIP broadcasts."
                DEFVAL { 60 }
                ::= { ipxRipIfEntry 4 }

            ipxIfRipIn OBJECT-TYPE
                SYNTAX Counter
                ACCESS read-only
                STATUS mandatory
                DESCRIPTION
                    "The number of RIP broadcasts received on this 
                    interface."
                ::= { ipxRipIfEntry 5 }

            ipxIfRipOut OBJECT-TYPE
                SYNTAX Counter
                ACCESS read-only
                STATUS mandatory
                DESCRIPTION
                    "The number of RIP broadcasts sent on this 
                    interface."
                ::= { ipxRipIfEntry 6 }

            ipxIfRipAgedOut OBJECT-TYPE
                SYNTAX Counter
                ACCESS read-only
                STATUS mandatory
                DESCRIPTION
                    "The number of entries timed out and discarded on 
                    this interface."
                ::= { ipxRipIfEntry 7 }

            ipxRipTable OBJECT-TYPE
                SYNTAX SEQUENCE OF IpxRipEntry
                ACCESS not-accessible
                STATUS mandatory
                DESCRIPTION
                    "A list of RIP entries."
                ::= { xIpxRip 2 }

            ipxRipEntry OBJECT-TYPE
                SYNTAX IpxRipEntry
                ACCESS not-accessible
                STATUS mandatory
                DESCRIPTION
                    "IPX interface parameters and counters."
                INDEX { ipxRipNetwork }
                ::= { ipxRipTable 1 }

            IpxRipEntry ::=
                SEQUENCE {
                    ipxRipNetwork
                        INTEGER,
                    ipxRipRouter
                        OCTET STRING,
                    ipxRipInterface
                        INTEGER,
                    ipxRipHops
                        INTEGER,
                    ipxRipTransTime
                        INTEGER,
                    ipxRipAge
                        INTEGER
                }

            ipxRipNetwork OBJECT-TYPE
                SYNTAX INTEGER
                ACCESS read-only
                STATUS mandatory
                DESCRIPTION
                    "An IPX network number to which this router knows a 
                    path."
                ::= { ipxRipEntry 1 }

            ipxRipRouter OBJECT-TYPE
                SYNTAX OCTET STRING ( SIZE(6) )
                ACCESS read-only
                STATUS mandatory
                DESCRIPTION
                    "The Ethernet address of an IPX router on this 
                    network."
                ::= { ipxRipEntry 2 }

            ipxRipInterface OBJECT-TYPE
                SYNTAX INTEGER
                ACCESS read-only
                STATUS mandatory
                DESCRIPTION
                    "The interface to reach the router.  A value of 
                    ifIndex."
                ::= { ipxRipEntry 3 }

            ipxRipHops OBJECT-TYPE
                SYNTAX INTEGER
                ACCESS read-only
                STATUS mandatory
                DESCRIPTION
                    "The number of hops to reach the router."
                ::= { ipxRipEntry 4 }

            ipxRipTransTime OBJECT-TYPE
                SYNTAX INTEGER
                ACCESS read-only
                STATUS mandatory
                DESCRIPTION
                    "The number of 55 millisecond ticks it takes for a 
                    packet to travel to the router."
                ::= { ipxRipEntry 5 }

            ipxRipAge OBJECT-TYPE
                SYNTAX INTEGER
                ACCESS read-only
                STATUS mandatory
                DESCRIPTION
                    "The age of the RIP entry in seconds."
                ::= { ipxRipEntry 6 }

            ipxRipRtTable OBJECT-TYPE
                SYNTAX SEQUENCE OF IpxRipRtEntry
                ACCESS not-accessible
                STATUS mandatory
                DESCRIPTION
                    "A list of RIP Routing entries."
                ::= { xIpxRip 3 }

            ipxRipRtEntry OBJECT-TYPE
                SYNTAX IpxRipRtEntry
                ACCESS not-accessible
                STATUS mandatory
                DESCRIPTION
                    "IPX Routing Entry information"
                INDEX { ipxRipRtNetwork, ipxRipRtInterface, ipxRipRtOrigin,
                         ipxRipRtRouter  }
                ::= { ipxRipRtTable 1 }

            IpxRipRtEntry ::=
                SEQUENCE {
                    ipxRipRtNetwork
                        INTEGER,
                    ipxRipRtRouter
                        OCTET STRING,
                    ipxRipRtInterface
                        INTEGER,
                    ipxRipRtHops
                        INTEGER,
                    ipxRipRtTransTime
                        INTEGER,
		     ipxRipRtOrigin
			INTEGER,
		     ipxRipRtRowStatus
			INTEGER
                }

            ipxRipRtNetwork OBJECT-TYPE
                SYNTAX INTEGER
                ACCESS read-only
                STATUS mandatory
                DESCRIPTION
                    "An IPX network number to which this router knows a 
                    path."
                ::= { ipxRipRtEntry 1 }

            ipxRipRtRouter OBJECT-TYPE
                SYNTAX OCTET STRING ( SIZE(6) )
                ACCESS read-only
                STATUS mandatory
                DESCRIPTION
                    "The Ethernet address of an IPX router on this 
                    network."
                ::= { ipxRipRtEntry 2 }

            ipxRipRtInterface OBJECT-TYPE
                SYNTAX INTEGER
                ACCESS read-only
                STATUS mandatory
                DESCRIPTION
                    "The interface to reach the router.  A value of 
                    ifIndex."
                ::= { ipxRipRtEntry 3 }

            ipxRipRtHops OBJECT-TYPE
                SYNTAX INTEGER (0..16)
                ACCESS read-write
                STATUS mandatory
                DESCRIPTION
                    "The number of hops to reach the router."
                ::= { ipxRipRtEntry 4 }

            ipxRipRtTransTime OBJECT-TYPE
                SYNTAX INTEGER (0..65535)
                ACCESS read-write
                STATUS mandatory
                DESCRIPTION
                    "The number of 55 millisecond ticks it takes for a 
                    packet to travel to the router."
                ::= { ipxRipRtEntry 5 }

            ipxRipRtOrigin OBJECT-TYPE
                SYNTAX INTEGER { ripLearned(1), static(2), nlspLearned(3) }
                ACCESS read-only
                STATUS mandatory
                DESCRIPTION
                    "The source of the RIP entry, either Learned via RIP or Static."
                ::= { ipxRipRtEntry 6 }


            ipxRipRtRowStatus OBJECT-TYPE
                SYNTAX INTEGER { invalid(1), valid(2) }
                ACCESS read-write
                STATUS mandatory
                DESCRIPTION
                    "Create or Delete RIP routing table entries."
                DEFVAL { valid }
                ::= { ipxRipRtEntry 7}


            -- the SAP group

            -- Implementation of this group is mandatory for all iTouch
            -- systems that implement IPX SAP

            ipxSapIfTable OBJECT-TYPE
                SYNTAX SEQUENCE OF IpxSapIfEntry
                ACCESS not-accessible
                STATUS mandatory
                DESCRIPTION
                    "A list of IPX interface entries."
                ::= { xIpxSap 1 }

            ipxSapIfEntry OBJECT-TYPE
                SYNTAX IpxSapIfEntry
                ACCESS not-accessible
                STATUS mandatory
                DESCRIPTION
                    "IPX interface parameters and counters."
                INDEX { ipxSapIfIndex }
                ::= { ipxSapIfTable 1 }

            IpxSapIfEntry ::=
                SEQUENCE {
                    ipxSapIfIndex
                        INTEGER,
                    ipxIfSapBcst
                        INTEGER,
                    ipxIfSapBcstDiscardTimeout
                        INTEGER,
                    ipxIfSapBcstTimer
                        INTEGER,
                    ipxIfSapIn
                        Counter,
                    ipxIfSapOut
                        Counter,
                    ipxIfSapAgedOut
                        Counter
                }

            ipxSapIfIndex OBJECT-TYPE
                SYNTAX INTEGER
                ACCESS read-only
                STATUS mandatory
                DESCRIPTION
                    "An index value that uniquely identifies an IPX 
                    interface.  The interface identified by a particular 
                    value of this index is the same interface as 
                    identified by the same value of ifIndex."
                ::= { ipxSapIfEntry 1 }

            ipxIfSapBcst OBJECT-TYPE
                SYNTAX INTEGER { disabled(1), enabled(2), propUpdateOnly(3), demandCircuit(4) }
                ACCESS read-write
                STATUS mandatory
                DESCRIPTION
                    "Control whether SAP packets will be broadcasted out 
                    this interface."
                DEFVAL { enabled }
                ::= { ipxSapIfEntry 2 }

            ipxIfSapBcstDiscardTimeout OBJECT-TYPE
                SYNTAX INTEGER
                ACCESS read-write
                STATUS mandatory
                DESCRIPTION
                    "The number of seconds to wait before discarding 
                    information learned from a SAP broadcast."
                DEFVAL { 180 }
                ::= { ipxSapIfEntry 3 }

            ipxIfSapBcstTimer OBJECT-TYPE
                SYNTAX INTEGER
                ACCESS read-write
                STATUS mandatory
                DESCRIPTION
                    "The number of seconds to wait between sending out 
                    SAP broadcasts."
                DEFVAL { 60 }
                ::= { ipxSapIfEntry 4 }

            ipxIfSapIn OBJECT-TYPE
                SYNTAX Counter
                ACCESS read-only
                STATUS mandatory
                DESCRIPTION
                    "The number SAP broadcasts received on this 
                    interface."
                ::= { ipxSapIfEntry 5 }

            ipxIfSapOut OBJECT-TYPE
                SYNTAX Counter
                ACCESS read-only
                STATUS mandatory
                DESCRIPTION
                    "The number SAP broadcasts sent on this interface."
                ::= { ipxSapIfEntry 6 }

            ipxIfSapAgedOut OBJECT-TYPE
                SYNTAX Counter
                ACCESS read-only
                STATUS mandatory
                DESCRIPTION
                    "The number entries for this interface discarded due 
                    to aging timeout."
                ::= { ipxSapIfEntry 7 }

            ipxSapTable OBJECT-TYPE
                SYNTAX SEQUENCE OF IpxSapEntry
                ACCESS not-accessible
                STATUS mandatory
                DESCRIPTION
                    "A list of SAP entries."
                ::= { xIpxSap 2 }

            ipxSapEntry OBJECT-TYPE
                SYNTAX IpxSapEntry
                ACCESS not-accessible
                STATUS mandatory
                DESCRIPTION
                    "IPX interface parameters and counters."
                INDEX { ipxSapName, ipxSapType }
                ::= { ipxSapTable 1 }

            IpxSapEntry ::=
                SEQUENCE {
                    ipxSapName
                        DisplayString,
                    ipxSapNetwork
                        INTEGER,
                    ipxSapHost
                        OCTET STRING,
                    ipxSapSocket
                        INTEGER,
                    ipxSapInterface
                        INTEGER,
                    ipxSapType
                        INTEGER,
                    ipxSapAge
                        INTEGER
                }

            ipxSapName OBJECT-TYPE
                SYNTAX DisplayString (SIZE (48))
                ACCESS read-only
                STATUS mandatory
                DESCRIPTION
                    "The name of the service, null filled."
                ::= { ipxSapEntry 1 }

            ipxSapNetwork OBJECT-TYPE
                SYNTAX INTEGER
                ACCESS read-only
                STATUS mandatory
                DESCRIPTION
                    "The IPX network number on which the service's host 
                    resides."
                ::= { ipxSapEntry 2 }

            ipxSapHost OBJECT-TYPE
                SYNTAX OCTET STRING ( SIZE(6))
                ACCESS read-only
                STATUS mandatory
                DESCRIPTION
                    "The Ethernet address of the IPX host of the 
                    service."
                ::= { ipxSapEntry 3 }

            ipxSapSocket OBJECT-TYPE
                SYNTAX INTEGER
                ACCESS read-only
                STATUS mandatory
                DESCRIPTION
                    "The socket number of the service on the host."
                ::= { ipxSapEntry 4 }

            ipxSapInterface OBJECT-TYPE
                SYNTAX INTEGER
                ACCESS read-only
                STATUS mandatory
                DESCRIPTION
                    "The interface of the router in the direction of the 
                    service.  A value of ifIndex."
                ::= { ipxSapEntry 5 }

            ipxSapType OBJECT-TYPE
                SYNTAX INTEGER {
                            user(1),
                            userGroup(2),
                            printQueue(3),
                            novellFileServer(4),
                            jobServer(5),
                            gateway1(6),
                            printServer(7),
                            archiveQueue(8),
                            archiveServer(9),
                            jobQueue(10),
                            administration(11)
                        }
                ACCESS read-only
                STATUS mandatory
                DESCRIPTION
                    "The type of the service.  The enumeration is an 
					incomplete set of all possible values."
                ::= { ipxSapEntry 6 }

            ipxSapAge OBJECT-TYPE
                SYNTAX INTEGER
                ACCESS read-only
                STATUS mandatory
                DESCRIPTION
                    "The age of the Sap entry in seconds."
                ::= { ipxSapEntry 7 }

            ipxSapSvTable OBJECT-TYPE
                SYNTAX SEQUENCE OF IpxSapSvEntry
                ACCESS not-accessible
                STATUS mandatory
                DESCRIPTION
                    "A list of SAP entries."
                ::= { xIpxSap 3 }

            ipxSapSvEntry OBJECT-TYPE
                SYNTAX IpxSapSvEntry
                ACCESS not-accessible
                STATUS mandatory
                DESCRIPTION
                    "IPX interface parameters and counters."
                INDEX { ipxSapSvName, ipxSapSvType, ipxSapSvOrigin,
	                ipxSapSvNetwork, ipxSapSvSocket, ipxSapSvHost  }
                ::= { ipxSapSvTable 1 }

            IpxSapSvEntry ::=
                SEQUENCE {
                    ipxSapSvName
                        DisplayString,
                    ipxSapSvNetwork
                        INTEGER,
                    ipxSapSvHost
                        OCTET STRING,
                    ipxSapSvSocket
                        INTEGER,
                    ipxSapSvInterface
                        INTEGER,
                    ipxSapSvOrigin
                        INTEGER,
                    ipxSapSvType
                        INTEGER,
		     ipxSapSvHops
			INTEGER,
		     ipxSapSvRowStatus
			INTEGER,
		     ipxSapSvAge
			INTEGER
                }

            ipxSapSvName OBJECT-TYPE
                SYNTAX DisplayString (SIZE (0..48))
                ACCESS read-only
                STATUS mandatory
                DESCRIPTION
                    "The name of the service."
                ::= { ipxSapSvEntry 1 }

            ipxSapSvNetwork OBJECT-TYPE
                SYNTAX INTEGER
                ACCESS read-only
                STATUS mandatory
                DESCRIPTION
                    "The IPX network number on which the service's host 
                    resides."
                ::= { ipxSapSvEntry 2 }

            ipxSapSvHost OBJECT-TYPE
                SYNTAX OCTET STRING ( SIZE(6))
                ACCESS read-only
                STATUS mandatory
                DESCRIPTION
                    "The Ethernet address of the IPX host of the 
                    service."
                ::= { ipxSapSvEntry 3 }

            ipxSapSvSocket OBJECT-TYPE
                SYNTAX INTEGER (0..65535)
                ACCESS read-only
                STATUS mandatory
                DESCRIPTION
                    "The socket number of the service on the host."
                ::= { ipxSapSvEntry 4 }

            ipxSapSvInterface OBJECT-TYPE
                SYNTAX INTEGER
                ACCESS read-only
                STATUS mandatory
                DESCRIPTION
                    "The interface of the router in the direction of the 
                    service.  A value of ifIndex."
                ::= { ipxSapSvEntry 5 }

            ipxSapSvOrigin OBJECT-TYPE
                SYNTAX INTEGER {
                            ipxSapLearned(1),
                            ipxStatic(2)
                       }
                ACCESS read-only
                STATUS mandatory
                DESCRIPTION
                    "The source of the RIP entry, either Learned via RIP or Static."
                ::= { ipxSapSvEntry 6 }

            ipxSapSvType OBJECT-TYPE
                SYNTAX INTEGER {
                            user(1),
                            userGroup(2),
                            printQueue(3),
                            novellFileServer(4),
                            jobServer(5),
                            gateway1(6),
                            printServer(7),
                            archiveQueue(8),
                            archiveServer(9),
                            jobQueue(10),
                            administration(11)
                        }
                ACCESS read-only
                STATUS mandatory
                DESCRIPTION
                    "The type of the service.  The enumeration is an 
					incomplete set of all possible values."
                ::= { ipxSapSvEntry 7 }

            ipxSapSvHops OBJECT-TYPE
                SYNTAX INTEGER (0..16)
                ACCESS read-write
                STATUS mandatory
                DESCRIPTION
                    "The number of hops to the Service."
                ::= { ipxSapSvEntry 8 }

            ipxSapSvRowStatus OBJECT-TYPE
                SYNTAX INTEGER { disabled(1), enabled(2) }
                ACCESS read-write
                STATUS mandatory
                DESCRIPTION
                    "Create or Delete SAP Service table entries."
                DEFVAL { enabled }
                ::= { ipxSapSvEntry 9}

            ipxSapSvAge OBJECT-TYPE
                SYNTAX INTEGER
                ACCESS read-only
                STATUS mandatory
                DESCRIPTION
                    "The age of the Sap entry in seconds."
                ::= { ipxSapSvEntry 10 }

            -- the IPX Filter group

            -- Implementation of this group is mandatory for all iTouch
            -- systems that implement IPX Filtering

            ipxIfFilterTable OBJECT-TYPE
                SYNTAX SEQUENCE OF IpxIfFilterEntry
                ACCESS not-accessible
                STATUS mandatory
                DESCRIPTION
                    "A list of IPX interface Source and Destination
                     address Filter entries."
                ::= { xIpxFilter 1 }

            ipxIfFilterEntry OBJECT-TYPE
                SYNTAX IpxIfFilterEntry
                ACCESS not-accessible
                STATUS mandatory
                DESCRIPTION
                    "IPX Source and Destination interface Filters."
                INDEX { ipxIfIndex, ipxIfFilterDestNetwork, ipxIfFilterDestNode,
                        ipxIfFilterSourceNetwork, ipxIfFilterSourceNode, 
                        ipxIfFilterPacketType, ipxIfFilterStatusDestNetworkAll,
			ipxIfFilterStatusDestNodeAll,ipxIfFilterStatusSourceNetworkAll,
			ipxIfFilterStatusSourceNodeAll,ipxIfFilterStatusPacketTypeAll  }
                ::= { ipxIfFilterTable 1 }

            IpxIfFilterEntry ::=
                SEQUENCE {
                    ipxIfFilterIndex
                        INTEGER,
                    ipxIfFilterDestNetwork
                        INTEGER,
                    ipxIfFilterDestNode
                        OCTET STRING,
                    ipxIfFilterSourceNetwork
                        INTEGER,
                    ipxIfFilterSourceNode
                        OCTET STRING,
                    ipxIfFilterPacketType
                        INTEGER,
                    ipxIfFilterAction
                        INTEGER,
                    ipxIfFilterRowStatus
                        INTEGER,
                    ipxIfFilterStatusDestNetworkAll
                        INTEGER,
                    ipxIfFilterStatusDestNodeAll
                        INTEGER,
                    ipxIfFilterStatusSourceNetworkAll
                        INTEGER,
                    ipxIfFilterStatusSourceNodeAll
                        INTEGER,
                    ipxIfFilterStatusPacketTypeAll
                        INTEGER
                }

            ipxIfFilterIndex OBJECT-TYPE
                SYNTAX INTEGER
                ACCESS read-only
                STATUS mandatory
                DESCRIPTION
                    "The interface to which this IPX Address filter applies.
                     A value of ifIndex."
                ::= { ipxIfFilterEntry 1 }

            ipxIfFilterDestNetwork OBJECT-TYPE
                SYNTAX INTEGER
                ACCESS read-only
                STATUS mandatory
                DESCRIPTION
                    "The destination IPX network to be filtered."
                ::= { ipxIfFilterEntry 2 }

            ipxIfFilterDestNode OBJECT-TYPE
                SYNTAX OCTET STRING ( SIZE(6))
                ACCESS read-only
                STATUS mandatory
                DESCRIPTION
                    "The destination IPX node to be filtered."
                ::= { ipxIfFilterEntry 3 }

            ipxIfFilterSourceNetwork OBJECT-TYPE
                SYNTAX INTEGER
                ACCESS read-only
                STATUS mandatory
                DESCRIPTION
                    "The destination IPX network to be filtered."
                ::= { ipxIfFilterEntry 4 }

            ipxIfFilterSourceNode OBJECT-TYPE
                SYNTAX OCTET STRING ( SIZE(6))
                ACCESS read-only
                STATUS mandatory
                DESCRIPTION
                    "The destination IPX node to be filtered."
                ::= { ipxIfFilterEntry 5 }

            ipxIfFilterPacketType OBJECT-TYPE
                SYNTAX INTEGER (0..255) 
                ACCESS read-only
                STATUS mandatory
                DESCRIPTION
                    "The IPX packet type to be filtered."
                ::= { ipxIfFilterEntry 6 }

            ipxIfFilterAction OBJECT-TYPE
                SYNTAX INTEGER {
                           forward(1),
                           discard(2)
                       }
                ACCESS read-write
                STATUS mandatory
                DESCRIPTION
                    "The IPX filter action to be taken, either Forward or Discard."
                ::= { ipxIfFilterEntry 7 }

            ipxIfFilterRowStatus OBJECT-TYPE
                SYNTAX INTEGER {
                           invalid(1),
                           valid(2)
                       }
                ACCESS read-write
                STATUS mandatory
                DESCRIPTION
                    "The IPX Filter create or delete function."
                ::= { ipxIfFilterEntry 8 }

            ipxIfFilterStatusDestNetworkAll OBJECT-TYPE
                SYNTAX INTEGER {
                           disabled(1),
                           enabled(2)
                       }
                ACCESS read-only
                STATUS mandatory
                DESCRIPTION
                    "The IPX Filter flag meaning ALL destination networks."
                ::= { ipxIfFilterEntry 9 }

            ipxIfFilterStatusDestNodeAll OBJECT-TYPE
                SYNTAX INTEGER {
                           disabled(1),
                           enabled(2)
                       }
                ACCESS read-only
                STATUS mandatory
                DESCRIPTION
                    "The IPX Filter flag meaning ALL destination nodes."
                ::= { ipxIfFilterEntry 10 }

            ipxIfFilterStatusSourceNetworkAll OBJECT-TYPE
                SYNTAX INTEGER {
                           disabled(1),
                           enabled(2)
                       }
                ACCESS read-only
                STATUS mandatory
                DESCRIPTION
                    "The IPX Filter flag meaning ALL source networks."
                ::= { ipxIfFilterEntry 11 }

            ipxIfFilterStatusSourceNodeAll OBJECT-TYPE
                SYNTAX INTEGER {
                           disabled(1),
                           enabled(2)
                       }
                ACCESS read-only
                STATUS mandatory
                DESCRIPTION
                    "The IPX Filter flag meaning ALL source nodes."
                ::= { ipxIfFilterEntry 12 }

            ipxIfFilterStatusPacketTypeAll OBJECT-TYPE
                SYNTAX INTEGER {
                           disabled(1),
                           enabled(2)
                       }
                ACCESS read-only
                STATUS mandatory
                DESCRIPTION
                    "The IPX Filter flag meaning ALL packet types."
                ::= { ipxIfFilterEntry 13 }


            ipxIfRipFilterTable OBJECT-TYPE
                SYNTAX SEQUENCE OF IpxIfRipFilterEntry
                ACCESS not-accessible
                STATUS mandatory
                DESCRIPTION
                    "A list of IPX interface RIP Filter entries."
                ::= { xIpxFilter 2 }

            ipxIfRipFilterEntry OBJECT-TYPE
                SYNTAX IpxIfRipFilterEntry
                ACCESS not-accessible
                STATUS mandatory
                DESCRIPTION
                    "IPX RIP interface Filters."
                INDEX { ipxIfIndex, ipxIfRipFilterType, ipxIfRipFilterNetwork, ipxIfRipFilterNetworkAll, 
			ipxIfRipFilterHost }
                ::= { ipxIfRipFilterTable 1 }

            IpxIfRipFilterEntry ::=
                SEQUENCE {
                    ipxIfRipFilterNetwork
                        INTEGER,
                    ipxIfRipFilterType
                        INTEGER,
                    ipxIfRipFilterAction
                        INTEGER,
                    ipxIfRipFilterRowStatus
                        INTEGER,
                    ipxIfRipFilterNetworkAll
                        INTEGER,
                    ipxIfRipFilterHost
			OCTET STRING
                }

            ipxIfRipFilterNetwork OBJECT-TYPE
                SYNTAX INTEGER
                ACCESS read-only
                STATUS mandatory
                DESCRIPTION
                    "The IPX RIP network to be filtered."
                ::= { ipxIfRipFilterEntry 1 }

            ipxIfRipFilterType OBJECT-TYPE
                SYNTAX INTEGER {
                           import(1),
                           export(2)
                       }
                ACCESS read-only
                STATUS mandatory
                DESCRIPTION
                    "The IPX RIP filter type, either IMPORT or EXPORT."
                ::= { ipxIfRipFilterEntry 2 }

            ipxIfRipFilterAction OBJECT-TYPE	
                SYNTAX INTEGER {
                           allow(1),
                           deny(2)
                       }
                ACCESS read-write	
                STATUS mandatory	
                DESCRIPTION	
                    "The IPX RIP filter action to be taken, either ALLOW or DENY."
                ::= { ipxIfRipFilterEntry 3 }

            ipxIfRipFilterRowStatus OBJECT-TYPE
                SYNTAX INTEGER {
                           invalid(1),
                           valid(2)
                       }
                ACCESS read-write
                STATUS mandatory
                DESCRIPTION
                    "The IPX RIP Filter create or delete function."
                ::= { ipxIfRipFilterEntry 4 }

            ipxIfRipFilterNetworkAll OBJECT-TYPE
                SYNTAX INTEGER {
                           disabled(1),
                           enabled(2)
                       }
                ACCESS read-only
                STATUS mandatory
                DESCRIPTION
                    "The IPX RIP Filter flag meaning filter ALL networks."
                ::= { ipxIfRipFilterEntry 5 }


            ipxIfRipFilterHost OBJECT-TYPE
                SYNTAX OCTET STRING (SIZE (6))
                ACCESS read-only
                STATUS mandatory
                DESCRIPTION
                    "The RIP Filter IPX Host Address from which RIP will ALLOW/DENY IMPORT of routes."
                ::= { ipxIfRipFilterEntry 6 }


            ipxIfSapFilterTable OBJECT-TYPE
                SYNTAX SEQUENCE OF IpxIfSapFilterEntry
                ACCESS not-accessible
                STATUS mandatory
                DESCRIPTION
                    "A list of IPX interface SAP Filter entries."
                ::= { xIpxFilter 3 }

            ipxIfSapFilterEntry OBJECT-TYPE
                SYNTAX IpxIfSapFilterEntry
                ACCESS not-accessible
                STATUS mandatory
                DESCRIPTION
                    "IPX SAP interface Filters."
                INDEX { ipxIfIndex, ipxIfSapFilterType, ipxIfSapFilterName, ipxIfSapFilterServiceType, 
                        ipxIfSapFilterServiceTypeAll, ipxIfSapFilterNetwork, ipxIfSapFilterNetworkAll, 
			ipxIfSapFilterHost }
                ::= { ipxIfSapFilterTable 1 }

            IpxIfSapFilterEntry ::=
                SEQUENCE {
                    ipxIfSapFilterNetwork
                        INTEGER,
                    ipxIfSapFilterType
                        INTEGER,
                    ipxIfSapFilterServiceType
                        INTEGER,
                    ipxIfSapFilterAction
                        INTEGER,
                    ipxIfSapFilterRowStatus
                        INTEGER,
                    ipxIfSapFilterNetworkAll
                        INTEGER,
                    ipxIfSapFilterServiceTypeAll
                        INTEGER,
                    ipxIfSapFilterName
                        DisplayString,
                    ipxIfSapFilterHost
                        OCTET STRING
                }

            ipxIfSapFilterNetwork OBJECT-TYPE
                SYNTAX INTEGER
                ACCESS read-only
                STATUS mandatory
                DESCRIPTION
                    "The IPX SAP network to be filtered."
                ::= { ipxIfSapFilterEntry 1 }

            ipxIfSapFilterType OBJECT-TYPE
                SYNTAX INTEGER {
                           import(1),
                           export(2)
                       }
                ACCESS read-only
                STATUS mandatory
                DESCRIPTION
                    "The IPX SAP filter type, either IMPORT or EXPORT."
                ::= { ipxIfSapFilterEntry 2 }

            ipxIfSapFilterServiceType OBJECT-TYPE
                SYNTAX INTEGER (0..65535)
                ACCESS read-only
                STATUS mandatory
                DESCRIPTION
                    "The IPX SAP service type to which this filter applies."
                ::= { ipxIfSapFilterEntry 3 }

            ipxIfSapFilterAction OBJECT-TYPE	
                SYNTAX INTEGER {
                           allow(1),
                           deny(2)
                       }
                ACCESS read-write	
                STATUS mandatory	
                DESCRIPTION	
                    "The IPX SAP filter action to be taken, either ALLOW or DENY."
                ::= { ipxIfSapFilterEntry 4 }

            ipxIfSapFilterRowStatus OBJECT-TYPE
                SYNTAX INTEGER {
                           invalid(1),
                           valid(2)
                       }
                ACCESS read-write
                STATUS mandatory
                DESCRIPTION
                    "The IPX SAP Filter create or delete function."
                ::= { ipxIfSapFilterEntry 5 }

            ipxIfSapFilterNetworkAll OBJECT-TYPE
                SYNTAX INTEGER {
                           disabled(1),
                           enabled(2)
                       }
                ACCESS read-only
                STATUS mandatory
                DESCRIPTION
                    "The IPX SAP Filter flag meaning filter ALL networks."
                ::= { ipxIfSapFilterEntry 6 }

            ipxIfSapFilterServiceTypeAll OBJECT-TYPE
                SYNTAX INTEGER {
                           disabled(1),
                           enabled(2)
                       }
                ACCESS read-only
                STATUS mandatory
                DESCRIPTION
                    "The IPX SAP Filter flag meaning filter ALL service types."
                ::= { ipxIfSapFilterEntry 7 }

            ipxIfSapFilterName OBJECT-TYPE
                SYNTAX DisplayString (SIZE (0..48))
                ACCESS read-only
                STATUS mandatory
                DESCRIPTION
                    "The name of the service to be filtered."
                ::= { ipxIfSapFilterEntry 8 }

            ipxIfSapFilterHost OBJECT-TYPE
                SYNTAX OCTET STRING (SIZE (6))
                ACCESS read-only
                STATUS mandatory
                DESCRIPTION
                    "The IPX Host address from which SAP will ALLOW/DENY IMPORT of services ."
                ::= { ipxIfSapFilterEntry 9 }

            -- the Printer group

            -- Implementation of this group is mandatory for all iTouch
            -- systems that implement IPX printers

            -- Additional single-instance values follow the Port table

            -- the Printer Port table

            ipxPrinterPortTable OBJECT-TYPE
                SYNTAX SEQUENCE OF IpxPrinterPortEntry
                ACCESS not-accessible
                STATUS mandatory
                DESCRIPTION
                    "A list of IPX printer character port entries."
                ::= { xIpxPrinter 1 }

            ipxPrinterPortEntry OBJECT-TYPE
                SYNTAX IpxPrinterPortEntry
                ACCESS not-accessible
                STATUS mandatory
                DESCRIPTION
                    "IPX printer parameter values for a character 
                    port."
                INDEX { ipxPrinterPortIndex }
                ::= { ipxPrinterPortTable 1 }

            IpxPrinterPortEntry ::=
                SEQUENCE {
                    ipxPrinterPortIndex
                        INTEGER,
                    ipxPrinterPortStatus
                        INTEGER,
                    ipxPrinterPortServer
                        DisplayString,
                    ipxPrinterPortPrinter
                        INTEGER,
                    ipxTimeout
                        INTEGER
                }

            ipxPrinterPortIndex OBJECT-TYPE
                SYNTAX INTEGER
                ACCESS read-only
                STATUS mandatory
                DESCRIPTION
                    "An index value that uniquely identifies a port.  
                    The port identified by a particular value of this 
                    index is the same port as identified by 
                    charPortIndex in the Proposed Standard Internet 
                    Character MIB."
                ::= { ipxPrinterPortEntry 1 }

            ipxPrinterPortStatus OBJECT-TYPE
                SYNTAX INTEGER { invalid(1), valid(2) }
                ACCESS read-write
                STATUS mandatory
                DESCRIPTION
                    "Status of this entry.  Setting the value to 
                    'invalid' invalidates the entry.  It is an 
                    implementation-specific matter as to whether the 
                    agent removes an invalidated entry from the table."
                DEFVAL { valid }
                ::= { ipxPrinterPortEntry 2 }

            ipxPrinterPortServer OBJECT-TYPE
                SYNTAX DisplayString (SIZE (0..48))
                ACCESS read-write
                STATUS mandatory
                DESCRIPTION
                    "The name of an active print server on the 
                    network."
                ::= { ipxPrinterPortEntry 3 }

            ipxPrinterPortPrinter OBJECT-TYPE
                SYNTAX INTEGER (0..255)
                ACCESS read-write
                STATUS mandatory
                DESCRIPTION
                    "An available remote printer on 
                    ixpPrinterPortServer."
                ::= { ipxPrinterPortEntry 4 }

             ipxTimeout OBJECT-TYPE
                SYNTAX INTEGER (15..300)
                ACCESS read-write
                STATUS mandatory
                DESCRIPTION
                    "A control to set the the time at which a print job from a
                     print server will be timed out and the port freed."
                DEFVAL { 15 }
                ::= { ipxPrinterPortEntry 5 }

            -- The following are additional single-instance values, 
            -- not part of the Port table.

            ipxPrinterEthernet OBJECT-TYPE
                SYNTAX INTEGER { disabled(1), enabled(2) }
                ACCESS read-write
                STATUS mandatory
                DESCRIPTION
                    "Control for use of Ethernet-style message framing, 
                    with the IPX protocol type.  Mutually exclusive with 
                    ipxPrinterMac, ipxPrinterMac802_2_Snap, and ipxPrinterMac802_2."
                ::= { xIpxPrinter 2 }

            ipxPrinterMac OBJECT-TYPE
                SYNTAX INTEGER { disabled(1), enabled(2) }
                ACCESS read-write
                STATUS mandatory
                DESCRIPTION
                    "Control for use of MAC-only message framing, with 
                    no protocol type.  Mutually exclusive with 
                    ipxPrinterEthernet, ipxPrinterMac802_2_Snap, and ipxPrinterMac802_2."
                ::= { xIpxPrinter 3 }

            ipxPrinterMac802-2 OBJECT-TYPE
                SYNTAX INTEGER { disabled(1), enabled(2) }
                ACCESS read-write
                STATUS mandatory
                DESCRIPTION
                    "Control for use of MAC message framing with 
                    802.2 framing.  Mutually exclusive with 
                    ipxPrinterEthernet, ipxPrinterMac, and ipxPrinterMac802_2_Snap."
                ::= { xIpxPrinter 4 }

            ipxPrinterMac802-2-Snap OBJECT-TYPE
                SYNTAX INTEGER { disabled(1), enabled(2) }
                ACCESS read-write
                STATUS mandatory
                DESCRIPTION
                    "Control for use of MAC-only message framing with 
                    802 Snap framing.  Mutually exclusive with 
                    ipxPrinterEthernet, ipxPrinterMac, and ipxPrinterMac802_2."
                ::= { xIpxPrinter 5 }


END
