-- extracted from draft-ietf-ops-vlanid-tc-mib-01.txt
-- at Sat Oct  2 06:23:23 2004

   VLAN-ID-MIB DEFINITIONS ::= BEGIN

   IMPORTS

       MODULE-IDENTITY, mib-2, Integer32           FROM SNMPv2-SMI
       TEXTUAL-CONVENTION                          FROM SNMPv2-TC;

   vlanIdMIB   MODULE-IDENTITY

       LAST-UPDATED  "200409270000Z"  -- 27 September 2004
       ORGANIZATION  "IETF Operations and Management Area"
       CONTACT-INFO  "Bert Wijnen (Editor)
                      Lucent Technologies
                      Schagen 33
                      3461 GL Linschoten
                      Netherlands

                      Phone: +31 348-407-775
                      EMail: bwijnen@lucent.com

                      Send comments to <mibs@ops.ietf.org>.
                     "
       DESCRIPTION   "This MIB module provides commonly used textual
                      conventions for VLAN Identifiers.

                      Copyright (C) The Internet Society (2004). This
                      version of this MIB module is part of RFC XXXX,
                      see the RFC itself for full legal notices.
                     "
                     -- RFC-Editor: assign XXXX above
                     --             then remove this note

       -- Revision History

       REVISION      "200409270000Z"  -- 27 September 2004
       DESCRIPTION   "Initial version, published as RFC XXXX."
                     -- RFC-Editor: assign XXXX above,
                     --             then remove this note

       ::= { mib-2 nnn } -- To be assigned by IANA

   VlanIdentifier        ::= TEXTUAL-CONVENTION
       DISPLAY-HINT     "d"
       STATUS            current
       DESCRIPTION      "The VLAN ID that uniquely identifies a VLAN.  It
                         is the 12-bit VLAN ID used in the VLAN Tag header.
                         The range is defined by the REFERENCEd specification.
                        "
       REFERENCE        "IEEE Std 802.1Q 2003 Edition, Virtual Bridged
                         Local Area Networks.
                        "
       SYNTAX            Integer32 (1..4094)

   VlanIdentifierOrAny   ::= TEXTUAL-CONVENTION
       DISPLAY-HINT     "d"
       STATUS            current
       DESCRIPTION      "The VLAN ID that uniquely identifies a VLAN.

                         The special value of 4095 is used to indicate a
                         wildcard, i.e. any value.
                        "
       SYNTAX            Integer32 (1..4094 | 4095)

   VlanIdentifierOrNone  ::= TEXTUAL-CONVENTION
       DISPLAY-HINT     "d"
       STATUS            current
       DESCRIPTION      "The VLAN ID that uniquely identifies a VLAN.

                         The special value of zero is used to indicate
                         that no VLAN ID is present or used.
                        "
       SYNTAX            Integer32 (0 | 1..4094)

   VlanIdentifierOrAnyOrNone  ::= TEXTUAL-CONVENTION
       DISPLAY-HINT     "d"
       STATUS            current
       DESCRIPTION      "The VLAN ID that uniquely identifies a VLAN.

                         The special value of zero is used to indicate
                         that no VLAN ID is present or used.

                         The special value of 4095 is used to indicate a
                         wildcard, i.e. any value.
                        "
       SYNTAX            Integer32 (0 | 1..4094 | 4095)

   END

-- 
--    Copyright (C) The Internet Society (2004).  This document is subject
--    to the rights, licenses and restrictions contained in BCP 78, and
--    except as set forth therein, the authors retain all their rights.
-- 
-- 
-- Acknowledgment
-- 
--    Funding for the RFC Editor function is currently provided by the
--    Internet Society.
