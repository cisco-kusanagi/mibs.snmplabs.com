-- $Id: flash.mib,v 29.3.38.2 1999/09/07 18:55:25 mbannach Exp $
--
-- Feb 21, 1998 klk Initial mib creation
-- Apr 21, 1998 AKQ Fixed syntax errors
-- May 20, 1998 AKQ Removed mount, unmount, encrpt upload from 
--              flashOperation command 
-- May 28, 1998 AKQ Added LoadType to flashOperation 
-- June 2, 1988 AKQ Added other type to DeviceFormatStatus
-- Oct. 5, 1998 MB Droped flashOperation load type and controller 
--              info/refined description, flashOperationStatus now read-only
-- Mar 10, 1999 MK Corrected spelling errors in the Description 
--              of flashDeviceMaster and flashDeviceController.
-- Sep  3, 1999 MB Added tftpPort configuration item and cleand up MIB

ASCEND-FLASH-MIB DEFINITIONS ::= BEGIN

      IMPORTS
         IpAddress      FROM RFC1155-SMI
         flashGroup     FROM ASCEND-MIB
         DisplayString  FROM RFC1213-MIB
         OBJECT-TYPE    FROM RFC-1212;

flashDevice OBJECT IDENTIFIER ::= { flashGroup 1 }

-- General information for using this MIB : 
--
-- The FLASH MIB provides an interface to the external FLASH memory on the 
-- Lucent Access platforms. It allows the user to look up the current status
-- of the FLASH and perform operations.
-- The term 'socket' is consistently used to describe a physical flash card
-- slot. The term slot was avoided to distinguish the flash card slot from 
-- the 'slots' of extension modules for the modular access devices like the
-- MAX TNT / Stinger / APX 8000.
-- Note : 'flashDeviceSocket', 'flashFileSocket', 'flashOperationSocket' always
--        refer to the same physical flash card as long as no new flash card is
--        inserted or a present card is removed.
-- 
-- TAOS 8.0 supports the MAX TNT, APEX and STINGER platforms.

--  Boolean Values
TruthValue ::= INTEGER { true (1), false (2) }

flashDevices OBJECT-TYPE
        SYNTAX  INTEGER
        ACCESS  read-only
        STATUS  mandatory
        DESCRIPTION
          "The maximum number of flash devices that are presented in the 
           flashDeviceTable. The maximum flashDeviceSocket. A value of 0
           indicates that the agent does not support any flashDevices"
       ::= { flashDevice 1 }

flashDeviceTable OBJECT-TYPE
        SYNTAX  SEQUENCE OF FlashDeviceEntry
        ACCESS  not-accessible
        STATUS  mandatory
        DESCRIPTION
          "This table contains one entry for each flash socket being mangaged via
           SNMP agent in this system."
       ::= { flashDevice 2 }

flashDeviceEntry OBJECT-TYPE
     SYNTAX  FlashDeviceEntry
     ACCESS  not-accessible
     STATUS  mandatory
     DESCRIPTION
        "An entry in the flashDeviceTable.  For each managed flashDevice there is 
         one entry present. It provides information for a single flashDevice as 
         indexed via the flashDeviceSocket."
     INDEX   { flashDeviceSocket }
    ::= { flashDeviceTable 1 }

    FlashDeviceEntry ::=
        SEQUENCE {
         flashDeviceSocket             INTEGER,
         flashDeviceController         INTEGER,
         flashDeviceControllerSocket   INTEGER,
         flashDeviceSize               INTEGER,
         flashDeviceUsed               INTEGER,
         flashDeviceState              INTEGER,
         flashDeviceMaster             TruthValue,
         flashDeviceFormatStatus       INTEGER,
         flashDeviceDescription        DisplayString
    }

flashDeviceSocket OBJECT-TYPE
     SYNTAX INTEGER
     ACCESS read-only
     STATUS mandatory
     DESCRIPTION
          "A value that uniquely identifies a single entry in the 
           flashDeviceTable."
     ::= { flashDeviceEntry 1 }

flashDeviceController OBJECT-TYPE
     SYNTAX INTEGER
     ACCESS read-only
     STATUS mandatory
     DESCRIPTION
          "Uniquely identifies the controller that manages this flash device.
           One or more devices can be managed by a single controller. The 
           devices managed by this agent might have one or more controllers 
           associated to them."
     ::= { flashDeviceEntry 2 }

flashDeviceControllerSocket OBJECT-TYPE
     SYNTAX INTEGER
     ACCESS read-only
     STATUS mandatory
     DESCRIPTION
          "Identifies the socket of the flashDeviceController for this 
           flashDeviceSocket. One or more sockets can be managed by the 
           controller identified via flashDeviceController. Each socket
           of a given controller has a unique flashDeviceControllerSocket."
     ::= { flashDeviceEntry 3 }

flashDeviceSize OBJECT-TYPE
     SYNTAX INTEGER
     ACCESS read-only
     STATUS mandatory
     DESCRIPTION
          "The maximum number of bytes this flashDevice can store."
     ::= { flashDeviceEntry 4 }

flashDeviceUsed OBJECT-TYPE
     SYNTAX INTEGER
     ACCESS read-only
     STATUS mandatory
     DESCRIPTION
          "The Total number of bytes currently stored in this flashDevice."
     ::= { flashDeviceEntry 5 }

flashDeviceState OBJECT-TYPE
     SYNTAX INTEGER {
          inserted(1),
          removed(2)
     }
     ACCESS read-only
     STATUS mandatory
     DESCRIPTION
          "The current state of this given flashDevice."
     ::= { flashDeviceEntry 6 }

flashDeviceMaster OBJECT-TYPE
     SYNTAX TruthValue
     ACCESS read-only
     STATUS mandatory
     DESCRIPTION
          "Identifies if this entry is controlled by the master controller
           or a slave controller. flashDeviceMaster is true if this socket
           is managed by the master controller and false otherwise."
     ::= { flashDeviceEntry 7 }

flashDeviceFormatStatus OBJECT-TYPE
     SYNTAX INTEGER {
          format-v1(1),
          format-v2(2),
          format-v3(3),
          format-other(99),
          unformatted(100)
     }
     ACCESS read-only
     STATUS mandatory
     DESCRIPTION
          "The format present on the flashDevice."
     ::= { flashDeviceEntry 8 }

flashDeviceDescription OBJECT-TYPE
     SYNTAX DisplayString
     ACCESS read-only
     STATUS mandatory
     DESCRIPTION
          "Textual description of the flashDevice."
     ::= { flashDeviceEntry 9 }

--             
-- FLASH FILE INFORMATION
--
-- These mib objects provide information about the files that are present 
-- on a given the flashDevice. 

flashFileTable OBJECT-TYPE
     SYNTAX  SEQUENCE OF FlashFileEntry
     ACCESS  not-accessible
     STATUS  mandatory
     DESCRIPTION
        "Contains information about all files that are managed via the
         agent on this system."
     ::= { flashGroup 2 }

flashFileEntry OBJECT-TYPE
     SYNTAX FlashFileEntry
     ACCESS  not-accessible
     STATUS  mandatory
     DESCRIPTION
        "Information about a single file on a given socket. A socket is
         a single access entity."
     INDEX   { flashFileSocket, flashFileIndex }
     ::= { flashFileTable 1 }

    FlashFileEntry ::=
        SEQUENCE {
         flashFileIndex                INTEGER,
         flashFileSocket               INTEGER,
         flashFileSize                 INTEGER,
         flashFileStatus               INTEGER,
         flashFileName                 DisplayString,
         flashFileChecksum             INTEGER,
         flashFileVersion              DisplayString,
         flashFileAccess               INTEGER,
         flashFileDateTimeStamp        DisplayString
    }

flashFileIndex OBJECT-TYPE
     SYNTAX  INTEGER
     ACCESS  read-only
     STATUS  mandatory
     DESCRIPTION
          "The unique index for a given socket that identifies this file."
     ::= { flashFileEntry 1 }

flashFileSocket OBJECT-TYPE
     SYNTAX  INTEGER
     ACCESS  read-only
     STATUS  mandatory
     DESCRIPTION
          "The socket on which the file resides."
     ::= { flashFileEntry 3 }

flashFileSize OBJECT-TYPE
     SYNTAX  INTEGER
     ACCESS  read-only
     STATUS  mandatory
     DESCRIPTION
          "The size of the file in bytes."
     ::= { flashFileEntry 4 }

flashFileStatus OBJECT-TYPE
     SYNTAX  INTEGER {
          valid(1),
          invalid(2),
          open-read(3),
          open-write(4)
     }
     ACCESS  read-only
     STATUS  mandatory
     DESCRIPTION
          "The current status of the file."
     ::= { flashFileEntry 5 }

flashFileName OBJECT-TYPE
     SYNTAX  DisplayString
     ACCESS  read-only
     STATUS  mandatory
     DESCRIPTION
          "The name used by the system to idenfity the file"
     ::= { flashFileEntry 6 }

flashFileChecksum OBJECT-TYPE
     SYNTAX  INTEGER
     ACCESS  read-only
     STATUS  mandatory
     DESCRIPTION
          "The checksum for this file."
     ::= { flashFileEntry 7 }

flashFileVersion OBJECT-TYPE
     SYNTAX  DisplayString
     ACCESS  read-only
     STATUS  mandatory
     DESCRIPTION
          "The version of the file"
     ::= { flashFileEntry 8 }

flashFileAccess OBJECT-TYPE
     SYNTAX  INTEGER {
          readOnly(1),
          readWrite(2)
     }
     ACCESS  read-only
     STATUS  mandatory
     DESCRIPTION
          "Access flags for the file."
     ::= { flashFileEntry 9 }

flashFileDateTimeStamp OBJECT-TYPE
     SYNTAX  DisplayString
     ACCESS  read-only
     STATUS  mandatory
     DESCRIPTION
          "The timestamp of the file when it was written to the flash"
     ::= { flashFileEntry 10 }

flashOperation OBJECT IDENTIFIER ::= { flashGroup 3 }

flashOperationStatus OBJECT-TYPE
     SYNTAX INTEGER {
          idle(1),
          activeFormating(2),
          activeFileUpload(3),
          activeConfigUpload(4),
          activeConfigDownload(5),
          activeInProgress(6),
          
          success(50),
          errorGeneric(51),
          errorFilenameNotValid(52),
          
          -- tftp operation related error codes.
          errorTftpEnotFound(101),
          errorTftpEaccess(102),
          errorTftpEnoSpace(103),
          errorTftpEbadOp(104),
          errorTftpEbadTid(105),
          errorTftpEexists(106),
          errorTftpEnouser(107),
          errorTftpEparm(108),
          errorTftpEbusy(109),
          errorTftpEresource(110),
          errorTftpEtimeout(111),
          errorTftpEuerror(112),
          errorTftpEretries(113),
          errorTftpCreateFile(114),
          errorTftpOpenFile(115),
          errorTftpReadData(116),
          errorTftpWriteData(117),
          
          -- flash operation related error codes.
          errorFlashResultBadParam(151),
          errorFlashResultNotFound(152),
          errorFlashResultTooManyOpen(153),
          errorFlashResultAlreadyOpen(154),
          errorFlashResultNullFile(155),
          errorFlashResultNoCard(156),
          errorFlashResultNoFormat(157),
          errorFlashResultOldFormat(158),
          errorFlashResultReadOnly(159),
          errorFlashResultNoSpace(160),
          errorFlashResultUnavail(161),
          errorFlashResultInternalError(162)
     }
     ACCESS  read-only 
     STATUS  mandatory
     DESCRIPTION
        "Status of the current operation in progress or the appropiate error 
         indication for the last operation performed. If the operation was 
         performed successfully 'no-operation-in-progress' is returned."
     ::= { flashOperation 1 }


flashOperationCommand OBJECT-TYPE
     SYNTAX INTEGER {
          format-card(1),
          tftp-upload(2),
          no-command(3),
          load-config(4),
          save-config(5)
     }
     ACCESS  read-write
     STATUS  mandatory
     DESCRIPTION
          "The object indicates the current operation. A set to the object 
           triggers the operation to be performed. If an operation is 
           in progress a set operation to this object causes a generic 
           error. format-card formats the card in the given socket.
           tftp-upload describes the upload of a file from a TFTP host 
           to the system. load-config reads the file described in 
           flashOperationSrcFileName into the system. save-config sends the 
           config to the TFTP host. Note that the TFTP host must allow write
           operations to take advantage of this feature."
     ::= { flashOperation 2 }

flashOperationHost OBJECT-TYPE
     SYNTAX IpAddress
     ACCESS  read-write
     STATUS  mandatory
     DESCRIPTION
          "Ip address of the TFTP host associated with an operation. If an 
           operation is in progress a set operation to this object causes a 
           generic error. For save operation this host must allow TFTP write 
           operation."
     ::= { flashOperation 3 }

flashOperationDestFileName OBJECT-TYPE
     SYNTAX DisplayString
     ACCESS  read-write
     STATUS  mandatory
     DESCRIPTION
          "Destination filename for operations. For a save operation this is
           the filename to be written to on the TFTP host. For load 
           operations this is the filename on the system. If an operation is 
           in progress a set operation to this object causes a generic 
           error."
     ::= { flashOperation 4 }

flashOperationSrcFileName OBJECT-TYPE
     SYNTAX DisplayString
     ACCESS  read-write
     STATUS  mandatory
     DESCRIPTION
          "Source filename for operations. For a save operation this is
           the filename on the system. For load operations this is the 
           filename to be read from to on the TFTP host. If an operation is 
           in progress a set operation to this object causes a generic 
           error."
     ::= { flashOperation 5 }

flashOperationSocket OBJECT-TYPE
     SYNTAX INTEGER
     ACCESS  read-write
     STATUS  mandatory
     DESCRIPTION
          "The flash socket to operate on. If an operation is 
           in progress a set operation to this object causes a generic 
           error."
     ::= { flashOperation 7 }

-- flashOperationTftpPort was introduced in TAOS 7.2
flashOperationTftpPort OBJECT-TYPE
     SYNTAX  INTEGER
     ACCESS  read-write
     STATUS  mandatory
     DESCRIPTION
        "This object defines the port # to use on the remote system when
         starting a TFTP operation using a flashOperationCommand. The default
         port is 69/(tcp/udp) Trivial File Transfer. The port numbers allowed 
         for configuration range from 1..65535"
     ::= { flashOperation 8 }

END
