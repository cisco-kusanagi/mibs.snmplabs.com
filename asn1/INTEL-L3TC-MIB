INTEL-L3TC-MIB DEFINITIONS ::= BEGIN

-- Copyright (C) 1999 Intel Corporation. All rights reserved.
--
-- Layer 3 transparant caching (L3TC) MIB, 22-04-1999
--
-- Proprietary MIB containing information about L3TC
--
-- Build 1
--

	IMPORTS
		IpAddress	FROM RFC1155-SMI
		DisplayString   FROM RFC1213-MIB
		OBJECT-TYPE	FROM RFC-1212
		mib2ext		FROM INTEL-GEN-MIB;

--
-- L3TC top-level definitions:
--

l3tcache	OBJECT IDENTIFIER ::= { mib2ext 37 }

l3tcFrontPorts	OBJECT IDENTIFIER ::= { l3tcache 1 }

l3tcServers	OBJECT IDENTIFIER ::= { l3tcache 2 }

l3tcTcpPorts	OBJECT IDENTIFIER ::= { l3tcache 3 }

l3tcStaticIPs	OBJECT IDENTIFIER ::= { l3tcache 4 }

l3tcSingleAttrs	OBJECT IDENTIFIER ::= { l3tcache 5 }

--
-- Front Ports:
--
l3tcFrontPortsTable OBJECT-TYPE
    SYNTAX SEQUENCE OF L3tcFrontPortsEntry
    ACCESS not-accessible
    STATUS mandatory
    DESCRIPTION "Numbers and Cache-modes of front ports"
    ::= { l3tcFrontPorts 1 }

l3tcFrontPortsEntry OBJECT-TYPE
    SYNTAX L3tcFrontPortsEntry
    ACCESS not-accessible
    STATUS mandatory
    DESCRIPTION ""
    INDEX { l3tcFrontPortsNumber }
    ::= { l3tcFrontPortsTable 1 }

L3tcFrontPortsEntry ::= SEQUENCE {
                        l3tcFrontPortsNumber
                           INTEGER,
                        l3tcFrontPortsMode
                           INTEGER
                        }

l3tcFrontPortsNumber OBJECT-TYPE
    SYNTAX INTEGER
    ACCESS read-only
    STATUS mandatory
    DESCRIPTION "Front Port number 1..24 identifying subject front port"
    ::= { l3tcFrontPortsEntry 1 }

l3tcFrontPortsMode OBJECT-TYPE
    SYNTAX INTEGER { normal(1), client(2), server(3) }
    ACCESS read-write
    STATUS mandatory
    DESCRIPTION "Tells the mode (normal/client/server) of the port"
    ::= { l3tcFrontPortsEntry 2 }

--
-- Cache servers:
--
l3tcServersTable OBJECT-TYPE
    SYNTAX SEQUENCE OF L3tcServersEntry
    ACCESS not-accessible
    STATUS mandatory
    DESCRIPTION "UserGroup membership for prefices of IP-addresses"
    ::= { l3tcServers 1 }

l3tcServersEntry OBJECT-TYPE
    SYNTAX L3tcServersEntry
    ACCESS not-accessible
    STATUS mandatory
    DESCRIPTION ""
    INDEX { l3tcServersIndex }
    ::= { l3tcServersTable 1 }

L3tcServersEntry ::= SEQUENCE {
                        l3tcServersIndex
                           INTEGER,
                        l3tcServersIpAddress
                           IpAddress,
                        l3tcServersDeleteEntry
                           INTEGER,
                        l3tcServersPortNumber
                           INTEGER,
                        l3tcServersHeartBeatUrl
                           DisplayString (SIZE(80)),
                        l3tcServersName
                           DisplayString (SIZE(20)),
			l3tcServersHeartBeatStatus
			   INTEGER
                        }

l3tcServersIndex OBJECT-TYPE
    SYNTAX INTEGER
    ACCESS read-only
    STATUS mandatory
    DESCRIPTION "Box-wide uniquely identifying number of subject cache server"
    ::= { l3tcServersEntry 1 }

l3tcServersIpAddress OBJECT-TYPE
    SYNTAX IpAddress
    ACCESS read-write
    STATUS mandatory
    DESCRIPTION "IpAddress of subject cache server"
    ::= { l3tcServersEntry 2 }

l3tcServersDeleteEntry OBJECT-TYPE
    SYNTAX INTEGER
    ACCESS read-write
    STATUS mandatory
    DESCRIPTION "Write 1 to this attribute to delete entire entry.
	Write 2 to a non-existing row creates a new row."
    ::= { l3tcServersEntry 3 }

l3tcServersPortNumber OBJECT-TYPE
    SYNTAX INTEGER
    ACCESS read-write
    STATUS mandatory
    DESCRIPTION "Identifies the Front Port to which this server is attached"
    ::= { l3tcServersEntry 4 }

l3tcServersHeartBeatUrl OBJECT-TYPE
    SYNTAX DisplayString (SIZE(80))
    ACCESS read-write
    STATUS mandatory
    DESCRIPTION "The URL to request when performing heart-beat checking"
    ::= { l3tcServersEntry 5 }

l3tcServersName OBJECT-TYPE
    SYNTAX DisplayString (SIZE(20))
    ACCESS read-write
    STATUS mandatory
    DESCRIPTION "The name for identification of the server presented
	to the operator"
    ::= { l3tcServersEntry 6 }

l3tcServersHeartBeatStatus OBJECT-TYPE
    SYNTAX INTEGER { ok(1), retrying(2), noResponse(3) }
    ACCESS read-only
    STATUS mandatory
    DESCRIPTION "Actual status of heart-beat monitoring of server"
    ::= { l3tcServersEntry 7 }

--
-- TCP Port numbers subject to l3tc-routing"
--
l3tcTcpPortsTable OBJECT-TYPE
    SYNTAX SEQUENCE OF L3tcTcpPortsEntry
    ACCESS not-accessible
    STATUS mandatory
    DESCRIPTION "List of Tcp Port Numbers subject to l3tc-routing"
    ::= { l3tcTcpPorts 1 }

l3tcTcpPortsEntry OBJECT-TYPE
    SYNTAX L3tcTcpPortsEntry
    ACCESS not-accessible
    STATUS mandatory
    DESCRIPTION ""
    INDEX { l3tcTcpPortsNumber }
    ::= { l3tcTcpPortsTable 1 }

L3tcTcpPortsEntry ::= SEQUENCE {
                        l3tcTcpPortsNumber
                           INTEGER,
                        l3tcTcpPortsDeleteEntry
                           INTEGER
                        }

l3tcTcpPortsNumber OBJECT-TYPE
    SYNTAX INTEGER
    ACCESS read-only
    STATUS mandatory
    DESCRIPTION "This TCP Port Number is subject to t-cache-forwarding"
    ::= { l3tcTcpPortsEntry 1 }

l3tcTcpPortsDeleteEntry OBJECT-TYPE
    SYNTAX INTEGER
    ACCESS read-write
    STATUS mandatory
    DESCRIPTION "Write 1 to this attribute to delete entire entry.
	Write 2 to a non-existing row creates a new row."
    ::= { l3tcTcpPortsEntry 2 }


--
-- Static sites:
--
l3tcStaticIPsTable OBJECT-TYPE
    SYNTAX SEQUENCE OF L3tcStaticIPsEntry
    ACCESS not-accessible
    STATUS mandatory
    DESCRIPTION "Operator-assigned servers for particular IP sites"
    ::= { l3tcStaticIPs 1 }

l3tcStaticIPsEntry OBJECT-TYPE
    SYNTAX L3tcStaticIPsEntry
    ACCESS not-accessible
    STATUS mandatory
    DESCRIPTION ""
    INDEX { l3tcStaticIPsPacketDestIP }
    ::= { l3tcStaticIPsTable 1 }

L3tcStaticIPsEntry ::= SEQUENCE {
                        l3tcStaticIPsPacketDestIP
                           IpAddress,
                        l3tcStaticIPsDeleteEntry
                           INTEGER,
                        l3tcStaticIPsServerIndex
                           INTEGER
                        }

l3tcStaticIPsPacketDestIP OBJECT-TYPE
    SYNTAX IpAddress
    ACCESS read-only
    STATUS mandatory
    DESCRIPTION "IP Address of subject IP site"
    ::= { l3tcStaticIPsEntry 1 }

l3tcStaticIPsDeleteEntry OBJECT-TYPE
    SYNTAX INTEGER
    ACCESS read-write
    STATUS mandatory
    DESCRIPTION "Write 1 to this attribute to delete entire entry.
	Write 2 to a non-existing row creates a new row."
    ::= { l3tcStaticIPsEntry 2 }

l3tcStaticIPsServerIndex OBJECT-TYPE
    SYNTAX INTEGER
    ACCESS read-write
    STATUS mandatory
    DESCRIPTION "Index value of cache server assigned to subject IP site"
    ::= { l3tcStaticIPsEntry 3 }



l3tcPollingInterval OBJECT-TYPE
    SYNTAX INTEGER
    ACCESS read-write
    STATUS mandatory
    DESCRIPTION "Interval in seconds between successive heart-beat-polls"
    ::= { l3tcSingleAttrs 1 }

l3tcEnabled OBJECT-TYPE
    SYNTAX INTEGER { on(1), off(2) }
    ACCESS read-write
    STATUS mandatory
    DESCRIPTION "Whether or not the TC routing is enabled"
    ::= { l3tcSingleAttrs 2 }

l3tcRevertToDefaults OBJECT-TYPE
    SYNTAX INTEGER
    ACCESS read-write
    STATUS mandatory
    DESCRIPTION "This is a bit mask setting selected parts of the configuration
	to factory defaults.

	value & 1: causes all front ports to revert to normal mode. All
		servers referring to a leaving-server-mode frontport are
		deleted too and all static sites reffering to deleted servers
		are deleted too.

	value & 2: removes all servers and all static sites

	value & 4: removes all TCP-protocols

	value & 8: removes all static sites

	value & 16: sets polling interval to 30 seconds and switches off
		the entire transparent caching facility

	As an example setting this attribute to the value 31 completely
	restores factory defaults."
    ::= { l3tcSingleAttrs 3 }


END
