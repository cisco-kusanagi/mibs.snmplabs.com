-- 
-- Copyright 1999 by Fore Systems, Inc. 
-- Converted to SMIv2 rfc 2578,2579,2580 - STD 58
--
-- Copyright 1997 by Fore Systems, Inc.
--
-- This file contains definitions for management information for Fore Systems
-- physical assemblies.  It is general in nature in order to accomodate all
-- of the current hardware products as well as any future products in the
-- forseeable future, or until an industry standard MIB is adopted.
------------------------------------------------------------------------------

Fore-If-MIB DEFINITIONS ::= BEGIN

  IMPORTS
     Integer32,
     OBJECT-TYPE,
     MODULE-IDENTITY                   FROM SNMPv2-SMI
     ifIndex			       FROM IF-MIB
     foreIfExtension 		       FROM Fore-Common-MIB;

foreIfModule MODULE-IDENTITY
     LAST-UPDATED    "9709081030-0400"
     ORGANIZATION    "FORE"
     CONTACT-INFO    "
             Postal: FORE Systems Inc.
                     1000 FORE Drive
                     Warrendale, PA 15086-7502
             Tel:    +1 724 742 6900
             Email:  nm_mibs@fore.com
             Web:    http://www.fore.com"
     DESCRIPTION
             "This MIB module defines the FORE Systems interface 
	      table. This table contains information necessary to 
	      configure the MTU size of an interface."
	::= { foreIfExtension 1 }

------------------------------------------------------------------------------
-- The foreIfGroup

foreIfGroup OBJECT IDENTIFIER ::= { foreIfExtension 2 }

foreIfTable OBJECT-TYPE
        SYNTAX  SEQUENCE OF ForeIfEntry
        MAX-ACCESS  not-accessible
        STATUS  current
        DESCRIPTION
                "A table of information per interface. This is
                 an extension of the standard ifTable"
        ::= { foreIfGroup 1 }

foreIfEntry OBJECT-TYPE
        SYNTAX  ForeIfEntry
        MAX-ACCESS  not-accessible
        STATUS  current
        DESCRIPTION
                "A table of information per interface"
        INDEX { ifIndex }
        ::= { foreIfTable 1 }

ForeIfEntry ::=
        SEQUENCE {
              foreIfMtu       Integer32
        }

foreIfMtu OBJECT-TYPE
	SYNTAX  Integer32
	MAX-ACCESS  read-write
	STATUS  current
	DESCRIPTION
        	"The size of the largest datagram which can be
                 sent/received on the interface, specified in
                 octets.  For interfaces that are used for
                 transmitting network datagrams, this is the size
                 of the largest network datagram that can be sent
                 on the interface. Currently this variable can be
		 set for qaaX interfaces only."
       ::= { foreIfEntry 1 }

END
