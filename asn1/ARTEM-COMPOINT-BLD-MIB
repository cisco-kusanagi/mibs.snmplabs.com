-- **********************************************************************
-- * Artem private BLD Management Information Base
-- **********************************************************************
ARTEM-COMPOINT-BLD-MIB DEFINITIONS ::= BEGIN

	IMPORTS
		ifIndex
			FROM RFC1213-MIB
		OBJECT-GROUP, NOTIFICATION-GROUP
			FROM SNMPv2-CONF
		enterprises, IpAddress, Integer32, OBJECT-TYPE, MODULE-IDENTITY, 
		OBJECT-IDENTITY, NOTIFICATION-TYPE
			FROM SNMPv2-SMI
		TruthValue, MacAddress, RowStatus, TEXTUAL-CONVENTION
			FROM SNMPv2-TC;
			
-- **********************************************************************
-- *  MODULE IDENTITY
-- **********************************************************************
	artem MODULE-IDENTITY
		LAST-UPDATED "200506101217Z"
		ORGANIZATION
			"Funkwerk Enterprise Communications."
		CONTACT-INFO
			"juergen.lachmann@funkwerk-ec.com."
		DESCRIPTION
			"Funkwerk Enterprise Communications MIB file that provides 
			 additional attributes not covered by standard MIBs 
			 for Broken Link Detection in artem products."

		REVISION "200506101217Z"
		DESCRIPTION
			"Updated Revision and last-updated."

		REVISION "200505241324Z"
		DESCRIPTION
			"Removed artemBLDIfTableIndex and artemBLDIfIndex from 
			 artemBLDIfTable. Index is now ifIndex."
			
		REVISION "200504291205Z"
		DESCRIPTION
			"Initial version."
		::= { enterprises 4280 }
		
-- **********************************************************************
-- *   Node definitions
-- **********************************************************************

-- **********************************************************************
-- *   artemBLD
-- **********************************************************************
	artemBLD OBJECT-IDENTITY
		STATUS current
		DESCRIPTION
			"Definitions and attributes for Broken Link Detection."
		::= { artem 6 }

	artemBLDAdminStatus OBJECT-TYPE
		SYNTAX TruthValue
		MAX-ACCESS read-write
		STATUS current
		DESCRIPTION
			"This attribute selects whether periodic 
			 BLD link checking is administratively enabled."
		DEFVAL { false }
		::= { artemBLD 1 }

	artemBLDLinkState OBJECT-TYPE
		SYNTAX TruthValue
		MAX-ACCESS read-only
		STATUS current
		DESCRIPTION
			"This attribute indicates whether the IP target 
			 monitored by BLD is currently reachable."
		::= { artemBLD 2 }

	artemBLDTargetAddress OBJECT-TYPE
		SYNTAX IpAddress
		MAX-ACCESS read-write
		STATUS current
		DESCRIPTION
			"This attribute holds the IP address of the 
			 connection target which is periodically checked by BLD."
		DEFVAL { '00000000'H } -- 0.0.0.0
		::= { artemBLD 3 }

	artemBLDTargetIf OBJECT-TYPE
		SYNTAX INTEGER (0..2147483647)
		MAX-ACCESS read-only
		STATUS current
		DESCRIPTION
			"This attribute hold the ifIndex of the interface that 
			 received the most recent reply from the BLD target.
			 The value 0 indicates that no reply has been received."
		::= { artemBLD 4 }

	artemBLDCheckInterval OBJECT-TYPE
		SYNTAX INTEGER (1..3600)
   		UNITS "seconds"
		MAX-ACCESS read-write
		STATUS current
		DESCRIPTION
			"This is the interval between successive 
			 checks whether the BLD target is reachable."
        DEFVAL { 300 }
		::= { artemBLD 5 }

	artemBLDTimeout OBJECT-TYPE
		SYNTAX INTEGER (1..300)
   		UNITS "seconds"
		MAX-ACCESS read-write
		STATUS current
		DESCRIPTION
			"This attribute defines the timeout for 
			 replies from the BLD target."
        DEFVAL { 1 }
		::= { artemBLD 6 }

	artemBLDRetries OBJECT-TYPE
		SYNTAX INTEGER (0..99)
		MAX-ACCESS read-write
		STATUS current
		DESCRIPTION
			"This attribute defines the number of timer BLD 
			 retries to reach the target after an initial failed 
			 attempt until the connection is considered broken."
        DEFVAL { 5 }
		::= { artemBLD 7 }

-- **********************************************************************
-- *    artemBLDIfTable  TABLE
-- **********************************************************************
	artemBLDIfTable OBJECT-TYPE
		SYNTAX SEQUENCE OF ArtemBLDIfEntry
		MAX-ACCESS not-accessible
		STATUS current
		DESCRIPTION
			"This is table of all interfaces which will be modified 
			 when BLD detects that its target is unreachable.
			 AP type interfaces are temporarily closed and will 
			 	not allow any client to associate.
			 Bridge type interfaces are unlocked if their operational 
			 	status is disabled(2)."
		::= {  artemBLD 8 }
		
	artemBLDIfEntry OBJECT-TYPE
		SYNTAX ArtemBLDIfEntry
		MAX-ACCESS not-accessible
		STATUS current
		DESCRIPTION
			"An entry in artemBLDIfTable."
		INDEX { ifIndex }
		::= { artemBLDIfTable 1 }

	ArtemBLDIfEntry ::=
		SEQUENCE {
			artemBLDIfRowStatus		RowStatus
		}

	artemBLDIfRowStatus OBJECT-TYPE
        SYNTAX RowStatus
        MAX-ACCESS read-create
        STATUS current
        DESCRIPTION
            "Auxiliary variable for creation of new object instances 
             and/or the deletion of existing object instances."
    	::= { artemBLDIfEntry 1 }
    	
-- **********************************************************************
-- *    End of artemBLDIfTable  TABLE
-- **********************************************************************

-- **********************************************************************
-- *    BLD notification Objects
-- **********************************************************************
    artemBLDNotification OBJECT IDENTIFIER 
    	::= { artemBLD 9 }

	artemBLDConnection NOTIFICATION-TYPE
		OBJECTS {
	        	ifIndex, 
	        	artemBLDLinkState 
	        	}
	    STATUS current
	    DESCRIPTION
	        "This notification is triggered for every interface in 
	         artemBLDIfTable whenever BLD detects a change in target 
	         link state."
		::= { artemBLDNotification 1 }

-- **********************************************************************
-- *    End of BLD notification Objects
-- **********************************************************************

-- ********************************************************************
-- * Groups 
-- ********************************************************************
	artemBLDGroup OBJECT-GROUP
		OBJECTS {
				artemBLDAdminStatus, 
				artemBLDLinkState, 
				artemBLDTargetAddress, 
				artemBLDTargetIf, 
				artemBLDCheckInterval, 
				artemBLDTimeout, 
				artemBLDRetries, 
				artemBLDIfRowStatus
				}
		STATUS current
		DESCRIPTION
			"Attributes for artem Broken Link Detection (BLD)."
		::= { artemBLD 10 }

	artemBLDNotificationGroup NOTIFICATION-GROUP
		NOTIFICATIONS {
				artemBLDConnection
				}
		STATUS current
		DESCRIPTION
			"Notifications for BLD events"
		::= { artemBLD 11 }
		
-- ********************************************************************
-- * End of Groups 
-- ********************************************************************

-- **********************************************************************
-- *   End of artemBLD
-- **********************************************************************

END
