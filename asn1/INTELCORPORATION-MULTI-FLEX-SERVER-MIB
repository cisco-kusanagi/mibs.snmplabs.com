-- INTEL CONFIDENTIAL
-- Copyright 2006, 2007
-- Intel Corporation All Rights Reserved.
--
-- The source code contained or described herein and all documents related to
-- the source code ("Material") are owned by Intel Corporation or its
-- suppliers and licensors. Title to the Material remains with Intel
-- Corporation or its suppliers and licensors. The Material contains trade
-- secrets and proprietary and confidential information of Intel or its
-- suppliers and licensors. The Material is protected by worldwide copyright
-- and trade secret laws and treaty provisions. No part of the Material may be
-- used, copied, reproduced, modified, published, uploaded, posted,
-- transmitted, distributed, or disclosed in any way without Intel's prior
-- express written permission.
--
-- Unless otherwise expressly permitted by Intel in a separate license
-- agreement, use of the Material is subject to the copyright notices,
-- trademarks, warranty, use, and disclosure restrictions reflected on the
-- outside of the media, in the documents themselves, and in the "About" or
-- "Read Me" or similar file contained within this source code. Unless
-- otherwise expressly agreed by Intel in writing, you may not remove
-- or alter such notices in any way.
--

    INTELCORPORATION-MULTI-FLEX-SERVER-MIB DEFINITIONS ::= BEGIN

        IMPORTS
            MODULE-IDENTITY, OBJECT-IDENTITY, OBJECT-TYPE, Integer32,
            Unsigned32, NOTIFICATION-TYPE
                FROM SNMPv2-SMI

            DisplayString
                FROM SNMPv2-TC

            OBJECT-GROUP, NOTIFICATION-GROUP
                FROM SNMPv2-CONF

            Power, IdromBinary16 
                FROM INTELCORPORATION-MULTI-FLEX-SERVER-TC

            regModule, components, groups, notifications, component,
            severity, eventType, user, instanceId, detail, eventId
                FROM INTELCORPORATION-MULTI-FLEX-SERVER-REG;


            multiFlexServerMibModule MODULE-IDENTITY
                LAST-UPDATED "200708211700Z"        -- August 21, 2007 at 17:00 GMT
                ORGANIZATION
                    "Intel Corporation"
                CONTACT-INFO
                    "Brian Kurle
                    Intel Corporation
                    JF5-2-C3
                    Tel: 503-712-5032
                    E-Mail: brianx.j.kurle@intel.com"
                DESCRIPTION
                    "Managment access to Multi-Flex Server chassis.
                    There is still some question where under the products tree this
                    belongs the chassisManagement tree would be logical *if* there
                    is possibility of either the Multi-Flex Server chassis will be allowed
                    a 3rd party CMM, or if the CMM may be put in a 3rd party
                    chassis.   It appears that initially that neither is the case
                    and that Multi-Flex Server will remain solely an SMB unit.  Thus, it
                    may be placed by itself under the smb tree"
                REVISION "200708211700Z"        -- August 21, 2007 at 17:00 GMT
                DESCRIPTION
                    "Renamed eventPolicyId to eventId"
                REVISION "200708161330Z"        -- August 16, 2007 at 13:30 GMT
                DESCRIPTION
                    "Reordered Revision to reverse chronological as some
                    browsers choke, cleaned up some other simple nit-picky
                    errors
                    
                    Added eventPolicyId to the notification group
                    "
                REVISION "200707161130Z"        -- July 16, 2007 at 11:30 GMT
                DESCRIPTION
                    "Dropped chassisBmcFirmwareVersion as it is really the
                    same information as the the CMM, which manages the
                    chassis."
                REVISION "200706072030Z"        -- June 07, 2007 at 20:30 GMT
                DESCRIPTION
                    "Added the IdromBinary16 to represent the asset tag,
                    part number, and serial number fields within the IDROM
                    fields."
                REVISION "200706071330Z"        -- June 07, 2007 at 13:30 GMT
                DESCRIPTION
                    "Corrected maximum/nominal IDROM parameters and comments"
                REVISION "200705301330Z"        -- May 30, 2007 at 13:30 GMT
                DESCRIPTION
                    "Fixed location of the chassisNotificationGroup
                    (previously typo'd to the wrong tree)"
                REVISION "200705301030Z"        -- May 30, 2007 at 10:30 GMT
                DESCRIPTION
                    "Added initial generic notification/trap type"
                REVISION "200704091030Z"        -- April 09, 2007 at 10:30 GMT
                DESCRIPTION
                    "Added overlooked BMC Version information"
                REVISION "200703121830Z"        -- March 12, 2007 at 18:30 GMT
                DESCRIPTION
                    "Moved FirmwareBundleId from chassis to CMM Tree.
                    Data now complies with IDROM (DID/DSD) information.

                    Renumbered / reorganized accordingly"
                REVISION "200703061030Z"        -- March 06, 2007 at 10:30 GMT
                DESCRIPTION
                    "Removed chassisVersion & chassisUpgradeFirmware at
                    architects' request

                    Renumbered/resequenced entries accordingly"
                REVISION "200702221700Z"        -- February 22, 2007 at 17:00 GMT
                DESCRIPTION
                    "Renamed MIB file and updated internal relevance to
                    formal product name Multi-Flex Server"
                REVISION "200611011000Z"        -- November 01, 2006 at 10:00 GMT
                DESCRIPTION
                    "Changed 'theChassis' to 'chassis'"
                REVISION "200609291529Z"        -- September 29, 2006 at 15:29 GMT
                DESCRIPTION
                    "Rearranged the Promise MIB information and morphed it into our format.
                    Removed either superfluous or undesired objects."
                REVISION "200609281732Z"        -- September 28, 2006 at 17:32 GMT
                DESCRIPTION
                    "Removed codename references and 'global prefixing.'
                    Created and moved Textual Conventions to own module."
                REVISION "200609010624Z"        -- September 01, 2006 at 06:24 GMT
                DESCRIPTION
                    "Parceled out the sub components to their own modules."
                ::= { regModule 10 }


--
-- The definition of Multi-Flex Server-specific traps are located at the end of
-- each group.
-- Main components of the chassis
--

        chassis OBJECT-IDENTITY
            STATUS current
            DESCRIPTION
                "chassis for the Multi-Flex Server product.
                Container for chassis specific information as well as all
                components logically contained within."
            ::= { components 10 }


--
-- ----------------------------------------------------------------------------
--
-- Chassis group.
--
-- This group contains information about the chassis.
--
-- ----------------------------------------------------------------------------
--
-- chassis tree

--
-- IDROM (Midplane)
--

        chassisVendor OBJECT-TYPE
            SYNTAX DisplayString
            MAX-ACCESS read-only
            STATUS current
            DESCRIPTION
                "Device manufacturer"
            ::= { chassis 1 }

        chassisMfgDate OBJECT-TYPE
            SYNTAX DisplayString
            MAX-ACCESS read-only
            STATUS current
            DESCRIPTION
                "Manufacture date/time"
            ::= { chassis 2 }

        chassisDeviceName OBJECT-TYPE
            SYNTAX DisplayString
            MAX-ACCESS read-only
            STATUS current
            DESCRIPTION
                "Device Name"
            ::= { chassis 3 }

        chassisPart OBJECT-TYPE
            SYNTAX IdromBinary16
            MAX-ACCESS read-only
            STATUS current
            DESCRIPTION
                "Device Part Number"
            ::= { chassis 4 }

        chassisSerialNo OBJECT-TYPE
            SYNTAX IdromBinary16
            MAX-ACCESS read-only
            STATUS current
            DESCRIPTION
                "Device Serial Number"
            ::= { chassis 5 }

        chassisMaximumPower OBJECT-TYPE
            SYNTAX Power
            MAX-ACCESS read-only
            STATUS current
            DESCRIPTION
                "Static maximum power generation / consumption (in watts):

                <0      - Negative numbers indicate device consumes power (in watts)
                >0      - Positive numbers indicate device generates power (in watts)
                0       - Device is passive (does not not consume or generate power)
                -1      - Maximum power generation/consumption not known or specified"
            ::= { chassis 6 }

        chassisNominalPower OBJECT-TYPE
            SYNTAX Power
            MAX-ACCESS read-only
            STATUS current
            DESCRIPTION
                "Static Nominal power generation / consumption (in watts):

                <0      - Negative numbers indicate device consumes power (in watts)
                >0      - Positive numbers indicate device generates power (in watts)
                0       - Device is passive (does not not consume or generate power)
                -1      - Nominal power generation/consumption not known or specified"
            ::= { chassis 7 }

        chassisAssetTag OBJECT-TYPE
            SYNTAX IdromBinary16
            MAX-ACCESS read-only
            STATUS current
            DESCRIPTION
                "Asset Tag # of device"
            ::= { chassis 8 }

--
-- All relevant Chassis components
--

        chassisGroup OBJECT-GROUP
            OBJECTS {

                chassisVendor,
                chassisMfgDate,
                chassisDeviceName,
                chassisPart,
                chassisSerialNo,
                chassisMaximumPower,
                chassisNominalPower,
                chassisAssetTag

            }
            STATUS current
            DESCRIPTION
                "Root level objects for the chassis."
            ::= { groups 10 }

--
-- Chassis related notifications
--
        genericChassisEvent NOTIFICATION-TYPE
            OBJECTS {

                component,
                severity,
                eventType,
                user,
                instanceId,
                detail,
                eventId
                
            }
            STATUS current
            DESCRIPTION
                "Generic event reporting"
            ::= { notifications 10 }

        chassisNotificationGroup NOTIFICATION-GROUP
            NOTIFICATIONS {

                genericChassisEvent

            }
            STATUS current
            DESCRIPTION
                "Chassis Related Events"
            ::= { groups 110 }


    END

--  vim:ts=4:ai:nohls:nowrap:expandtab
