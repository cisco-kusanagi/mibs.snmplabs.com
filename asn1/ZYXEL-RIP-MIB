-- ZyXEL Communications Corporation
-- Private Enterprise MIB definition 
  
-- This file describes the ZyXEL Communications Corporation Enterprise MIB.
-- It contains ZyXEL products OIDs, and common managed objects.

-- $Log: ZYXEL-RIP-MIB.mib $ 
-- Revision 1.5  2013/12/06 07:08:37  ccho 
-- remove uncessary imports 
-- Revision 1.4  2012/09/19 07:46:09  Kevin 
-- if it's leaf node, revise the vender name from zyxel to zy 
-- Revision 1.3  2012/08/22 09:48:36  Kevin 
-- Revise reference entry name 
-- Revision 1.2  2012/07/05 06:24:35  Kevin 
-- 1. upgrade from SNMP to SNMPv2  
-- 2. clean warning 
-- Revision 1.1  2012/05/30 07:50:31  Kevin 
-- Initial revision 

ZYXEL-RIP-MIB DEFINITIONS ::= BEGIN

	 IMPORTS
	OBJECT-TYPE
		FROM SNMPv2-SMI			-- RFC2578	
		
	MODULE-IDENTITY
		FROM SNMPv2-SMI
	
	EnabledStatus
		FROM  P-BRIDGE-MIB

	zyRouteDomainIpAddress, zyRouteDomainIpMaskBits		
		FROM ZYXEL-IP-FORWARD-MIB
	
	esMgmt			
		FROM ZYXEL-ES-SMI;

	zyxelRip MODULE-IDENTITY
		LAST-UPDATED	"201207010000Z"    
		ORGANIZATION "Enterprise Solution ZyXEL"     
		CONTACT-INFO
			""	   
		DESCRIPTION
			"The subtree for Routing Information Protocol (RIP)"
		::= { esMgmt 74 }
		
	zyxelRipSetup     		OBJECT IDENTIFIER ::= { zyxelRip 1 }


  
-- *******************************************************************
-- *
-- * zyxelRipSetup
-- *
-- *******************************************************************

-- zyxelRipState
		zyRipState OBJECT-TYPE
        SYNTAX  EnabledStatus
        MAX-ACCESS  read-write
        STATUS  current
        DESCRIPTION
                    "Enabled/Disabled RIP on the Switch."
        ::= { zyxelRipSetup 1 }

-- zyxelRipDistance
		zyRipDistance OBJECT-TYPE
        SYNTAX  INTEGER
        MAX-ACCESS  read-write
        STATUS  current
        DESCRIPTION
                    "The administrative distance of RIP routes."
        ::= { zyxelRipSetup 2 }
		
-- zyxelRipRouteDomainTable
		zyxelRipRouteDomainTable OBJECT-TYPE
        SYNTAX	SEQUENCE OF ZyxelRipRouteDomainEntry
        MAX-ACCESS  not-accessible
        STATUS  current
        DESCRIPTION
					"The table contains RIP route domain configuration."
        ::= { zyxelRipSetup 3 }

		zyxelRipRouteDomainEntry OBJECT-TYPE
        SYNTAX	ZyxelRipRouteDomainEntry
        MAX-ACCESS	not-accessible
        STATUS	current
        DESCRIPTION    	
					"An entry contains RIP route domain configuration."
        INDEX          	{ zyRouteDomainIpAddress, zyRouteDomainIpMaskBits }
        ::= { zyxelRipRouteDomainTable 1 }
		
		
        ZyxelRipRouteDomainEntry ::=
		SEQUENCE {
        	zyRipRouteDomainDirection	INTEGER,
        	zyRipRouteDomainVersion		INTEGER      	
        }

        zyRipRouteDomainDirection OBJECT-TYPE
        SYNTAX  INTEGER {
        	none(0),
        	outgoing(1),
        	incoming(2),
        	both(3)
        }
        MAX-ACCESS  read-write
        STATUS  current
        DESCRIPTION
			"RIP direction which controls the sending and receiving of RIP packet."
        ::= { zyxelRipRouteDomainEntry 1 }
		
	    zyRipRouteDomainVersion OBJECT-TYPE
        SYNTAX  INTEGER {
        	v1(0),
        	v2b(1),
        	v2m(2)
        }        
        MAX-ACCESS  read-write
        STATUS  current
        DESCRIPTION
			"RIP version which controls the format and the broadcasting method of the RIP packets that the switch sends."
        ::= { zyxelRipRouteDomainEntry 2 }

END
