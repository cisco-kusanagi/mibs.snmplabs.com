-- *****************************************************************
-- REDSTONE-IP-TEMPLATE-MIB
--
-- Redstone Communications Inc. Enterprise MIB
-- IP Template MIB
--
-- Copyright 1999 Unisphere Solutions Inc.
-- All Rights Reserved.
-- *****************************************************************

REDSTONE-IP-TEMPLATE-MIB DEFINITIONS ::= BEGIN

IMPORTS
    MODULE-IDENTITY, 
    OBJECT-TYPE,
    Integer32,
    Unsigned32,
    IpAddress
        FROM SNMPv2-SMI

    DisplayString,
    RowStatus
        FROM SNMPv2-TC

    MODULE-COMPLIANCE, 
    OBJECT-GROUP  
        FROM SNMPv2-CONF

    InterfaceIndexOrZero
        FROM IF-MIB

    rsMgmt
		FROM REDSTONE-SMI

    RsEnable,
    RsName
        FROM REDSTONE-TC;


rsIpTemplateMIB MODULE-IDENTITY
    LAST-UPDATED "9908250000Z"
    ORGANIZATION "Redstone Communications Inc."
	CONTACT-INFO
        "
        Redstone Communications, Inc.
		5 Carlisle Road
        Westford MA 01886
        USA
        Tel:    +1-978-692-1999
		Email:  mib@redstonecom.com
        "
	DESCRIPTION
		"The IP Template MIB for the
		Redstone Communications Inc. enterprise."
	REVISION      "9908250000Z"
	DESCRIPTION
		"Initial version of this MIB module."
    ::= { rsMgmt 26 }


-- ++++++++++++++++++++++++++++++++++++++++++++++++++++++++++++++++++++++
-- Textual conventions
-- ++++++++++++++++++++++++++++++++++++++++++++++++++++++++++++++++++++++

-- No textual conventions are currently defined.


-- ++++++++++++++++++++++++++++++++++++++++++++++++++++++++++++++++++++++
-- Managed object groups
-- ++++++++++++++++++++++++++++++++++++++++++++++++++++++++++++++++++++++

rsIpTemplateObjects              OBJECT IDENTIFIER ::= {rsIpTemplateMIB 1}

rsIpTemplate                     OBJECT IDENTIFIER ::= {rsIpTemplateObjects 1 }

-- ++++++++++++++++++++++++++++++++++++++++++++++++++++++++++++++++++++++
-- Managed objects for IP Templates
-- ++++++++++++++++++++++++++++++++++++++++++++++++++++++++++++++++++++++

rsIpTemplateTable OBJECT-TYPE
    SYNTAX      SEQUENCE OF RsIpTemplateEntry
    MAX-ACCESS  not-accessible
    STATUS      current
    DESCRIPTION
        "The entries in this table describe templates for configuring 
        IP interfaces."
    ::= { rsIpTemplate 1 }

rsIpTemplateEntry OBJECT-TYPE
    SYNTAX      RsIpTemplateEntry
    MAX-ACCESS  not-accessible
    STATUS      current
    DESCRIPTION
        "A template describing configuration of an IP interface."
    INDEX { rsIpTemplateId }
    ::= { rsIpTemplateTable 1 }

RsIpTemplateEntry ::= SEQUENCE {
    rsIpTemplateId                  Unsigned32,
    rsIpTemplateRowStatus           RowStatus,
    rsIpTemplateRouterName          RsName,
    rsIpTemplateIpAddr              IpAddress,
    rsIpTemplateIpMask              IpAddress,
    rsIpTemplateDirectedBcastEnable RsEnable,
    rsIpTemplateIcmpRedirectEnable  RsEnable,
    rsIpTemplateAccessRoute         RsEnable,
    rsIpTemplateMtu                 Integer32,
    rsIpTemplateLoopbackIfIndex     InterfaceIndexOrZero
}

rsIpTemplateId OBJECT-TYPE
    SYNTAX      Unsigned32
    MAX-ACCESS  not-accessible
    STATUS      current
    DESCRIPTION
        "The integer identifier associated with this template.
        A value for this identifier is determined by locating or creating
        a template name in the rsTemplateNameTable."
    ::= { rsIpTemplateEntry 1 }

rsIpTemplateRowStatus OBJECT-TYPE
    SYNTAX      RowStatus
    MAX-ACCESS  read-create
    STATUS      current
    DESCRIPTION
        "Controls creation/deletion of entries in this table.
        Only the values 'createAndGo' and 'destroy' may be SET.
        
        The value of rsIpTemplateId must match that of a template
        name configured in rsTemplateNameTable."
    ::= { rsIpTemplateEntry 2 }

rsIpTemplateRouterName OBJECT-TYPE
    SYNTAX      RsName
    MAX-ACCESS  read-create
    STATUS      current
    DESCRIPTION
        "The virtual router to which an IP interface configured by this 
        template will be assigned, if other mechanisms do not otherwise
        specify a virtual router assignment."
    DEFVAL { ''H }
    ::= { rsIpTemplateEntry 3 }

rsIpTemplateIpAddr OBJECT-TYPE
    SYNTAX      IpAddress
    MAX-ACCESS  read-create
    STATUS      current
    DESCRIPTION
        "An IP address to be used by an IP interface configured by this
        template. This object will have a value of 0.0.0.0 for an unnumbered
        interface."
    DEFVAL { 0 }
    ::= { rsIpTemplateEntry 4 }

rsIpTemplateIpMask OBJECT-TYPE
    SYNTAX      IpAddress
    MAX-ACCESS  read-create
    STATUS      current
    DESCRIPTION
        "An IP address mask to be used by an IP interface configured by this
        template. This object will have a value of 0.0.0.0 for an unnumbered
        interface."
    DEFVAL { 0 }
    ::= { rsIpTemplateEntry 5 }

rsIpTemplateDirectedBcastEnable OBJECT-TYPE
    SYNTAX      RsEnable
    MAX-ACCESS  read-create
    STATUS      current
    DESCRIPTION
        "Enable/disable forwarding of directed broadcasts on this 
        IP network interface."
    DEFVAL { disable }
    ::= { rsIpTemplateEntry 6 }

rsIpTemplateIcmpRedirectEnable OBJECT-TYPE
    SYNTAX      RsEnable
    MAX-ACCESS  read-create
    STATUS      current
    DESCRIPTION
        "Enable/disable transmission of ICMP Redirect messages on this
        IP network interface."
    DEFVAL { disable }
    ::= { rsIpTemplateEntry 7 }

rsIpTemplateAccessRoute OBJECT-TYPE
    SYNTAX      RsEnable
    MAX-ACCESS  read-create
    STATUS      current
    DESCRIPTION
        "Enable/disable whether a host route is automatically created
        for a remote host attached to an IP interface that is configured
        using this template."
    DEFVAL { enable }
    ::= { rsIpTemplateEntry 8 }

rsIpTemplateMtu OBJECT-TYPE
    SYNTAX      Integer32(0 | 512..10240)
    MAX-ACCESS  read-create
    STATUS      current
    DESCRIPTION
        "The configured MTU size for this IP network interface. If set to
        zero, the default MTU size, as determined by the underlying 
        network media, is used."
    DEFVAL { 0 } 
    ::= { rsIpTemplateEntry 9 }

rsIpTemplateLoopbackIfIndex OBJECT-TYPE
    SYNTAX      InterfaceIndexOrZero
    MAX-ACCESS  read-create
    STATUS      current
    DESCRIPTION
        "For unnumbered interfaces, the IfIndex of the IP loopback interface 
        whose IP address is used as the source address for transmitted IP packets.
        A value of zero means the loopback interface is unspecified (e.g., when
        the interface is numbered)."
    DEFVAL { 0 }
    ::= { rsIpTemplateEntry 10 }



-- ++++++++++++++++++++++++++++++++++++++++++++++++++++++++++++++++++++++
-- Notification control objects
-- ++++++++++++++++++++++++++++++++++++++++++++++++++++++++++++++++++++++

-- No notifications are defined in this MIB. Placeholder follows.

-- rsIpTemplateTrapControl      OBJECT IDENTIFIER ::= { rsIpTemplateMIB 2 }



-- ++++++++++++++++++++++++++++++++++++++++++++++++++++++++++++++++++++++
-- Notifications
-- ++++++++++++++++++++++++++++++++++++++++++++++++++++++++++++++++++++++

-- No notifications are defined in this MIB. Placeholder follows.

-- The following two OBJECT IDENTIFIERS are used to define SNMPv2 
-- Notifications that are easily translated into SNMPv1 Traps.

-- rsIpTemplateTraps            OBJECT IDENTIFIER ::= { rsIpTemplateMIB 3 }
-- rsIpTemplateTrapPrefix       OBJECT IDENTIFIER ::= { rsIpTemplateTraps 0 }



-- ++++++++++++++++++++++++++++++++++++++++++++++++++++++++++++++++++++++
-- Conformance information
-- ++++++++++++++++++++++++++++++++++++++++++++++++++++++++++++++++++++++

rsIpTemplateMIBConformance
             OBJECT IDENTIFIER ::= { rsIpTemplateMIB 4 }
rsIpTemplateMIBCompliances
             OBJECT IDENTIFIER ::= { rsIpTemplateMIBConformance 1 }
rsIpTemplateMIBGroups
             OBJECT IDENTIFIER ::= { rsIpTemplateMIBConformance 2 }


-- compliance statements

rsIpTemplateCompliance MODULE-COMPLIANCE
    STATUS      current
    DESCRIPTION
        "The compliance statement for systems supporting IP
        configuration templates."
    MODULE  -- this module
    MANDATORY-GROUPS { rsIpTemplateGroup }
    ::= { rsIpTemplateMIBCompliances 1 }


-- units of conformance

rsIpTemplateGroup OBJECT-GROUP
    OBJECTS {
        rsIpTemplateRowStatus,
        rsIpTemplateRouterName,
        rsIpTemplateIpAddr,
        rsIpTemplateIpMask,
        rsIpTemplateDirectedBcastEnable,
        rsIpTemplateIcmpRedirectEnable,
        rsIpTemplateAccessRoute,
        rsIpTemplateMtu,
        rsIpTemplateLoopbackIfIndex
    }
    STATUS      current
    DESCRIPTION
        "The basic collection of objects providing management
        of IP Template functionality in a Redstone product."
    ::= { rsIpTemplateMIBGroups 1 }

END
