-- 
-- Copyright 1999 by Fore Systems, Inc. 
-- Converted to SMIv2 rfc 2578,2579,2580 - STD 58
--
-- Copyright 1999 by Fore Systems, Inc.
-- All Rights Reserved
--
-- This mib implements management information for
-- the PLCP convergence layer in an atm interface.
-- Typically PLCP framing is used to encapsulate
-- ATM cells for transmission over a DS3/E3 link.

Fore-PLCP-MIB DEFINITIONS ::= BEGIN

IMPORTS
         Counter32,
	 OBJECT-TYPE,
	 MODULE-IDENTITY,
	 Integer32, NOTIFICATION-TYPE	FROM	SNMPv2-SMI
	 asx		      	FROM	Fore-Common-MIB
	 ifIndex,ifName       	FROM	IF-MIB
	 trapLogIndex		FROM	Fore-TrapLog-MIB;

forePlcpMib            MODULE-IDENTITY
          LAST-UPDATED         "9911050000Z"
          ORGANIZATION         "FORE"
          CONTACT-INFO         
               "      Postal:   FORE Systems Inc.
                                 1000 FORE Drive
                                 Warrendale, PA 15086-7502
                       Tel:      +1 724 742 6900
                       Email:    nm_mibs@fore.com
                       Web:      http://www.fore.com"
          DESCRIPTION "
	      This mib implements management information for
	      the PLCP convergence layer in an atm interface.
	      Typically PLCP framing is used to encapsulate
	      ATM cells for transmission over a DS3/E3 link."
    ::= { asx 13 }

forePlcpConfigTable OBJECT-TYPE
	SYNTAX	SEQUENCE OF ForePlcpConfigEntry
	MAX-ACCESS	not-accessible
	STATUS	current
	DESCRIPTION
		"A table of PLCP convergence layer information
		 configuration parameters."
	::= { forePlcpMib 1 }

forePlcpConfigEntry OBJECT-TYPE
	SYNTAX	ForePlcpConfigEntry
	MAX-ACCESS	not-accessible
	STATUS	current
	DESCRIPTION
		"A table entry containing PLCP convergence layer
		 configuration information for each 
		 atm interface using PLCP."
	INDEX  { ifIndex }
	::= { forePlcpConfigTable 1 }

ForePlcpConfigEntry ::=
	SEQUENCE {
		forePlcpConfigFrameFormat	   INTEGER
	}

forePlcpConfigFrameFormat OBJECT-TYPE
	SYNTAX		INTEGER {
				forePlcpFrameFormatDs1(1),
				forePlcpFrameFormatE1(2),
				forePlcpFrameFormatDs3(3),
				forePlcpFrameFormatE3(4)
			}
	MAX-ACCESS		read-write
	STATUS		current
	DESCRIPTION
		"This variable controls the PLCP framing format used
		 to carry ATM cells over this interface.  Note that
		 some interfaces may not support all formats and that
		 this variable may be read-only for some interfaces."
	::= { forePlcpConfigEntry 1 }


forePlcpTotalTable OBJECT-TYPE
	SYNTAX	SEQUENCE OF ForePlcpTotalEntry
	MAX-ACCESS	not-accessible
	STATUS	current
	DESCRIPTION
		"A table of PLCP convergence layer information
		 and parameters."
	::= { forePlcpMib 2 }

forePlcpTotalEntry OBJECT-TYPE
	SYNTAX	ForePlcpTotalEntry
	MAX-ACCESS	not-accessible
	STATUS	current
	DESCRIPTION
		"A table entry containing PLCP convergence layer
		 information for each atm interface using PLCP."
	INDEX  { ifIndex }
	::= { forePlcpTotalTable 1 }

ForePlcpTotalEntry ::=
	SEQUENCE {
		forePlcpTotalFerrCount	    Counter32,
		forePlcpTotalLofSeconds	   Counter32,
		forePlcpTotalBip8Count	    Counter32,
		forePlcpTotalFebeCount	    Counter32,
		forePlcpTotalYellowAlarmSeconds   Counter32
	}

forePlcpTotalFerrCount OBJECT-TYPE
	SYNTAX		Counter32
	MAX-ACCESS	read-only
	STATUS	current
	DESCRIPTION
		"The number of framing errors detected since the interface
		 was reset.  A framing error is determined by errors in
		 the A1 and A2 bytes of the PLCP frame." 
	::= { forePlcpTotalEntry 1 }

forePlcpTotalLofSeconds OBJECT-TYPE
	SYNTAX		Counter32
	MAX-ACCESS	read-only
	STATUS	current
	DESCRIPTION
		"The number of seconds an out of frame condition persisted."
	::= { forePlcpTotalEntry 2 }

forePlcpTotalBip8Count OBJECT-TYPE
	SYNTAX		Counter32
	MAX-ACCESS	read-only
	STATUS	current
	DESCRIPTION
		"The number of Bit Interleaved Parity errors detected since
		 the interface was reset.  A BIP error is determined by using
		 the parity carried in the B1 byte of the PLCP frame."
	::= { forePlcpTotalEntry 3 }

forePlcpTotalFebeCount OBJECT-TYPE
	SYNTAX		Counter32
	MAX-ACCESS	read-only
	STATUS	current
	DESCRIPTION
		"The number of Far End BIP Errors detected.  This information
		 is determined by examination of the G1 byte in the PLCP frame."
	::= { forePlcpTotalEntry 4 }

forePlcpTotalYellowAlarmSeconds OBJECT-TYPE
	SYNTAX	  Counter32
	MAX-ACCESS	read-only
	STATUS	current
	DESCRIPTION
		"The number of seconds that a far end yellow alarm condition has
		 persisted.  This information is determined by examiniation of
		 the G1 byte of the PLCP frame."
	::= { forePlcpTotalEntry 5 }

-- Current table	

forePlcpCurrentTable OBJECT-TYPE
	SYNTAX	SEQUENCE OF ForePlcpCurrentEntry
	MAX-ACCESS	not-accessible
	STATUS	current
	DESCRIPTION
		"A table of PLCP convergence layer information
		 and parameters."
	::= { forePlcpMib 3 }

forePlcpCurrentEntry OBJECT-TYPE
	SYNTAX	ForePlcpCurrentEntry
	MAX-ACCESS	not-accessible
	STATUS	current
	DESCRIPTION
		"A table entry containing PLCP convergence layer
		 current statistics for each atm interface using PLCP."
	INDEX  { ifIndex }
	::= { forePlcpCurrentTable 1 }

ForePlcpCurrentEntry ::=
	SEQUENCE {
		forePlcpCurrentFerrCount	    Counter32,
		forePlcpCurrentBip8Count	    Counter32,
		forePlcpCurrentFebeCount	    Counter32,
                forePlcpCurrentErrSeconds           Counter32,
                forePlcpCurrentSevErrSeconds        Counter32,
                forePlcpCurrentUnavailSeconds       Counter32
	}

forePlcpCurrentFerrCount OBJECT-TYPE
        SYNTAX          Counter32
        MAX-ACCESS      read-only
        STATUS  current
        DESCRIPTION
                "The number of framing errors detected in current interval.
                 A framing error is determined by errors in
                 the A1 and A2 bytes of the PLCP frame."
        ::= { forePlcpCurrentEntry 1 }

forePlcpCurrentBip8Count OBJECT-TYPE
        SYNTAX          Counter32
        MAX-ACCESS      read-only
        STATUS  current
        DESCRIPTION
                "The number of Bit Interleaved Parity errors detected in
                 the current interval.  A BIP error is determined by using
                 the parity carried in the B1 byte of the PLCP frame."
        ::= { forePlcpCurrentEntry 2 }

forePlcpCurrentFebeCount OBJECT-TYPE
        SYNTAX          Counter32
        MAX-ACCESS      read-only
        STATUS  current
        DESCRIPTION
                "The number of Far End BIP Errors detected in the 
		 current interval.  This information is determined 
		 by examination of the G1 byte in the PLCP frame."
        ::= { forePlcpCurrentEntry 3 }

forePlcpCurrentErrSeconds OBJECT-TYPE
        SYNTAX          Counter32
        MAX-ACCESS          read-only
        STATUS          current
        DESCRIPTION
          "Number of Errored Seconds in current interval"
        ::= { forePlcpCurrentEntry 4 }

forePlcpCurrentSevErrSeconds OBJECT-TYPE
        SYNTAX          Counter32
        MAX-ACCESS      read-only
        STATUS          current
        DESCRIPTION
          "Number of Severely Errored Seconds in current interval"
        ::= { forePlcpCurrentEntry 5 }

forePlcpCurrentUnavailSeconds OBJECT-TYPE
        SYNTAX          Counter32
        MAX-ACCESS      read-only
        STATUS          current
        DESCRIPTION
          "Number of Unavailable Seconds in the current interval"
        ::= { forePlcpCurrentEntry 6 }

-- Interval table

forePlcpIntervalTable OBJECT-TYPE
        SYNTAX  SEQUENCE OF ForePlcpIntervalEntry
        MAX-ACCESS      not-accessible
        STATUS  current
        DESCRIPTION
                "Interval table of PLCP convergence layer information
                 and parameters."
        ::= { forePlcpMib 4 }

forePlcpIntervalEntry OBJECT-TYPE
        SYNTAX  ForePlcpIntervalEntry
        MAX-ACCESS      not-accessible
        STATUS  current
        DESCRIPTION
                "A table entry containing PLCP convergence layer
                 current statistics for each atm interface using PLCP."
        INDEX  { ifIndex, forePlcpInterval }
        ::= { forePlcpIntervalTable 1 }

ForePlcpIntervalEntry ::=
        SEQUENCE {
		forePlcpInterval                     Integer32,
                forePlcpIntervalFerrCount            Counter32,
                forePlcpIntervalBip8Count            Counter32,
                forePlcpIntervalFebeCount            Counter32,
                forePlcpIntervalErrSeconds           Counter32,
                forePlcpIntervalSevErrSeconds        Counter32,
                forePlcpIntervalUnavailSeconds       Counter32
        }

forePlcpInterval OBJECT-TYPE
        SYNTAX          Integer32
        MAX-ACCESS      read-only
        STATUS          current
        DESCRIPTION
          "Interval number"
        ::= { forePlcpIntervalEntry 1 }


forePlcpIntervalFerrCount OBJECT-TYPE
        SYNTAX          Counter32
        MAX-ACCESS      read-only
        STATUS  current
        DESCRIPTION
                "The number of framing errors detected in particular interval.
                 A framing error is determined by errors in
                 the A1 and A2 bytes of the PLCP frame."
        ::= { forePlcpIntervalEntry 2 }

forePlcpIntervalBip8Count OBJECT-TYPE
        SYNTAX          Counter32
        MAX-ACCESS      read-only
        STATUS  current
        DESCRIPTION
                "The number of Bit Interleaved Parity errors detected in
                 the particular interval.  A BIP error is determined by using
                 the parity carried in the B1 byte of the PLCP frame."
        ::= { forePlcpIntervalEntry 3 }

forePlcpIntervalFebeCount OBJECT-TYPE
        SYNTAX          Counter32
        MAX-ACCESS      read-only
        STATUS  current
        DESCRIPTION
                "The number of Far End BIP Errors detected in the 
                 particular interval.  This information is determined 
                 by examination of the G1 byte in the PLCP frame."
        ::= { forePlcpIntervalEntry 4 }

forePlcpIntervalErrSeconds OBJECT-TYPE
        SYNTAX          Counter32
        MAX-ACCESS          read-only
        STATUS          current
        DESCRIPTION
          "Number of Errored Seconds in particular interval"
        ::= { forePlcpIntervalEntry 5 }

forePlcpIntervalSevErrSeconds OBJECT-TYPE
        SYNTAX          Counter32
        MAX-ACCESS      read-only
        STATUS          current
        DESCRIPTION
          "Number of Severely Errored Seconds in particular interval"
        ::= { forePlcpIntervalEntry 6 }

forePlcpIntervalUnavailSeconds OBJECT-TYPE
        SYNTAX          Counter32
        MAX-ACCESS      read-only
        STATUS          current
        DESCRIPTION
          "Number of Unavailable Seconds in the particular interval"
        ::= { forePlcpIntervalEntry 7 }

-- Diagnostics Section

-- forePlcpDiagnosticsTable OBJECT-TYPE
--	SYNTAX	SEQUENCE OF ForePlcpDiagnosticsEntry
--	MAX-ACCESS	not-accessible
--	STATUS	current
--	DESCRIPTION
--		"A table of PLCP convergence layer information
--		 and parameters."
--	::= { forePlcpMib 3 }
--
-- The Diagnostics table is tentativly defined as below, however it
-- is subject to change
--
--
--forePlcpDiagnosticsEntry OBJECT-TYPE
--	SYNTAX	ForePlcpDiagnosticsEntry
--	ACCESS	not-accessible
--	STATUS	mandatory
--	DESCRIPTION
--		"A table entry containing PLCP convergence layer
--		 information for each atm interface using PLCP."
--	INDEX  { ifIndex }
--	::= { forePlcpDiagnosticsTable 1 }

--ForePlcpDiagnosticsEntry ::=
--	SEQUENCE {
--	}

-- Trap Section

forePlcpYellowDetected NOTIFICATION-TYPE
	OBJECTS { ifIndex, ifName, trapLogIndex }
	STATUS      current
	DESCRIPTION
		"This trap indicates that the specified DS3 port has
		detected incoming PLCP Yellow Alarm."
	::= { forePlcpMib 0 1 }

forePlcpYellowCleared NOTIFICATION-TYPE
	OBJECTS { ifIndex, ifName, trapLogIndex }
	STATUS      current
	DESCRIPTION
		"This trap indicates that the specified DS3 port has
		detected clearance of incoming PLCP Yellow Alarm."
	::= { forePlcpMib 0 2 }

forePlcpLOFDetected NOTIFICATION-TYPE
	OBJECTS { ifIndex, ifName, trapLogIndex }
	STATUS      current
	DESCRIPTION
		"This trap indicates that the specified DS3 port has
		detected incoming PLCP LOF Alarm."
	::= { forePlcpMib 0 3 }

forePlcpLOFCleared NOTIFICATION-TYPE
	OBJECTS { ifIndex, ifName, trapLogIndex }
	STATUS      current
	DESCRIPTION
		"This trap indicates that the specified DS3 port has
		detected clearance of incoming PLCP LOF Alarm."
	::= { forePlcpMib 0 4 }

END
