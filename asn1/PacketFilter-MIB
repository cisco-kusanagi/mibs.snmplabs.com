PacketFilter-MIB DEFINITIONS ::= BEGIN

        IMPORTS
                enterprises,
                OBJECT-TYPE,
                Counter
                        FROM RFC1155-SMI
                internetServer
                        FROM InternetServer-MIB;

--      microsoft       OBJECT IDENTIFIER ::= { enterprises 311 }
--      software        OBJECT IDENTIFIER ::= { microsoft 1 }
--      internetServer  OBJECT IDENTIFIER ::= { software 7 }
        packetFilter    OBJECT IDENTIFIER ::= { internetServer 13 }
        pfStatistics    OBJECT IDENTIFIER ::= { packetFilter 1 }

-- Packet Filter Driver Statistics
	totalDrops OBJECT-TYPE
		SYNTAX	Counter
		ACCESS	read-only
		STATUS	mandatory
		DESCRIPTION 
			"The total number of dropped or filtered packets."
		::= { pfStatistics 1 }

	totalBads OBJECT-TYPE
		SYNTAX	Counter
		ACCESS	read-only
		STATUS	mandatory
		DESCRIPTION 
			"The total number of packets dropped because dynamic packet filtering rejected the data."
		::= { pfStatistics 2 }

	totalViolations OBJECT-TYPE
		SYNTAX	Counter
		ACCESS	read-only
		STATUS	mandatory
		DESCRIPTION 
			"The total of the number of frames dropped because of a protocol irregularity."
		::= { pfStatistics 3 }

	totalSYNS OBJECT-TYPE
		SYNTAX	Counter
		ACCESS	read-only
		STATUS	mandatory
		DESCRIPTION 
			"The total number of connections made through the filtered interfaces."
		::= { pfStatistics 4 }

	lostFrames OBJECT-TYPE
		SYNTAX	Counter
		ACCESS	read-only
		STATUS	mandatory
		DESCRIPTION 
			"The total of the number of packets dropped that could not be logged."
		::= { pfStatistics 5 }


END
