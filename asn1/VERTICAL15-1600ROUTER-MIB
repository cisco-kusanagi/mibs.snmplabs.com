VERTICAL15-1600ROUTER-MIB DEFINITIONS ::= BEGIN

IMPORTS
		DisplayString FROM SNMPv2-TC
			enterprises FROM RFC1155-SMI
        OBJECT-TYPE
                     FROM RFC-1212
		TRAP-TYPE FROM RFC-1215;
             
vertical OBJECT IDENTIFIER ::= { enterprises 2338 }  

	--  Author  : Rajiv Anand
	--  Version : 1.0
	--  Date : April 12, 1999

	v1600Router	OBJECT IDENTIFIER ::= {vertical 15}

	v1600InstalledSlot OBJECT-TYPE
		SYNTAX INTEGER
		ACCESS read-only
		STATUS mandatory
		DESCRIPTION "The slot number in which the 1600-Router Card is installed."
		::= { v1600Router 1 }
	
	v1600Ser0ChannelWidth OBJECT-TYPE
		SYNTAX INTEGER
		ACCESS read-only
		STATUS mandatory
		DESCRIPTION "The number of channels used by the internal interface (S0) to connect to T1."
		::= { v1600Router 2 }
	
	v1600Ser0T1InterfaceSlot OBJECT-TYPE
		SYNTAX INTEGER
		ACCESS read-only
		STATUS mandatory
		DESCRIPTION "Slot number of T1 card configured for the WAN interface."
		::= { v1600Router 3 }

	v1600Ser0T1InterfacePort OBJECT-TYPE
		SYNTAX INTEGER (1..2)
		ACCESS read-only
		STATUS mandatory
		DESCRIPTION  "Port number of the T1 card configured for WAN interface."
		::= { v1600Router 4 }

	v1600Ser0T1InterfaceStartChan OBJECT-TYPE
		SYNTAX INTEGER (0..24)
		ACCESS read-only
		STATUS mandatory
		DESCRIPTION "Starting channel used by the internal interface (S0) to T1."
		::= { v1600Router 5 }

	v1600FlashCardReady OBJECT-TYPE
		SYNTAX INTEGER { ready(0), notReady(1) }
		ACCESS read-only
		STATUS mandatory
		DESCRIPTION "Ready = Flash card inserted , Not Ready = Flash card removed."
		::= { v1600Router 6 }

	-- ================= LED status ==================

	v1600CardReadyLED OBJECT-TYPE
		SYNTAX INTEGER { on(0), off(1) }
		ACCESS read-only
		STATUS mandatory
		DESCRIPTION "On= 1600-Router Card is fully operational, Off=1600-Router Card is not Ready." 
		::= { v1600Router 7 }

	v1600CardErrorLED OBJECT-TYPE
		SYNTAX INTEGER { on(0), off(1) }
		ACCESS read-only
		STATUS mandatory
		DESCRIPTION "On= 1600-Router Card is not ready, Off=1600-Router Card is Ready." 
		::= { v1600Router 8 }


	-- ================= 1600-Router Status=============

	v1600RouterOKLED OBJECT-TYPE
		SYNTAX INTEGER { on(0), off(1) }
		ACCESS read-only
		STATUS mandatory
		DESCRIPTION "Router OK LED Status. This variable is no longer used and will be
		deprecated in the next release."
		::= { v1600Router 9 }

	-- =================  5-in-1 Serial 1 Interface =============

	v1600ExtSerial1ConnOK OBJECT-TYPE
		SYNTAX INTEGER { on(1), off(0) }
		ACCESS read-only
		STATUS mandatory
		DESCRIPTION "Shows whether a cable is connected to the 5-in-1 External 
		Serial(S1) Connector. on=Connected , off=Not Connected"
		::= { v1600Router 10 }

	v1600ExtSerial1DCD OBJECT-TYPE
		SYNTAX INTEGER { on(0), off(1) }
		ACCESS read-only
		STATUS mandatory
		DESCRIPTION "Shows the status of 5-in-1 External Serial(S1) DCD LED.
		on=Link is up, off=Link is down" 
		::= { v1600Router 11 }
	
	-- ================= Switch Port information ==================

	v1600SwitchSlotNum OBJECT-TYPE
		SYNTAX INTEGER
		ACCESS read-only
		STATUS mandatory
		DESCRIPTION "Switch port Slot number. This variable is no longer used and will be 
		deprecated in the next release."
		::= { v1600Router 12 }

	v1600EthSwitchedPorts OBJECT-TYPE
		SYNTAX INTEGER
		ACCESS read-only
		STATUS mandatory
		DESCRIPTION "Number of Swithced Ethernet ports on 1600-Router Card."
		::= { v1600Router 13 }

	v1600SwitchStat OBJECT-TYPE
		SYNTAX DisplayString
		ACCESS read-only
		STATUS mandatory
		DESCRIPTION "More Information about Switch Port statistics. This variable is no
		longer used and will be deprecated in the next release."
		::= { v1600Router 14 }

	-- =================  Internal Serial 0 Interface =============

	v1600IntSerial0ConnOK OBJECT-TYPE
		SYNTAX INTEGER { on(0), off(1) }
		ACCESS read-only
		STATUS mandatory
		DESCRIPTION "Internal WAN interface (S0) connection to T1 LED status."
		::= { v1600Router 15 }

	v1600IntSerial0DCD OBJECT-TYPE
		SYNTAX INTEGER { on(0), off(1) }
		ACCESS read-only
		STATUS mandatory
		DESCRIPTION "Internal WAN interface (S0) Link LED status.
		on=Link is up, off=Link is down."
		::= { v1600Router 16 }
	
	-- =================  Internal Ethernet 0 Interface =============

	v1600RouterEthLinkOK OBJECT-TYPE
		SYNTAX INTEGER { on(0), off(1) }
		ACCESS read-only
		STATUS mandatory
		DESCRIPTION "Shows status of internal Ethernet Interface (E0) LED.
		on=Link is up , off=Link is down"
		::= { v1600Router 17 }

	-- ===============  TRAP definitions =================

	v1600CardNotReady TRAP-TYPE
		ENTERPRISE vertical
		VARIABLES { v1600InstalledSlot }
		DESCRIPTION
		"Notification sent when the 1600-Router card is not ready at boot time."
	::= 68 

	v1600FlashCardNotReady TRAP-TYPE
		ENTERPRISE vertical
		VARIABLES { v1600InstalledSlot }
		DESCRIPTION
		"The Flash card on the 1600-Router Card is either removed or not inserted properly.
		Please insert the Flash Card after you power down the system."
	::= 69
	
	v1600FlashCardReadyTrap TRAP-TYPE
		ENTERPRISE vertical
		VARIABLES { v1600InstalledSlot }
		DESCRIPTION
		"The Flash card on the 1600-Router Card has been re-inserted." 
	::= 76 

	v1600RouterReady TRAP-TYPE
		ENTERPRISE vertical
		VARIABLES { v1600InstalledSlot }
		DESCRIPTION
		"The Router is ready and has booted from the image on the Flash Card."
	::= 77 

	v1600RouterNotReady TRAP-TYPE
		ENTERPRISE vertical
		VARIABLES { v1600InstalledSlot }
		DESCRIPTION
		"The Router is has not booted from the image on the Flash Card or the system 
		is still booting. Please open the 1600-Router console and make sure that the 
		Router boots from the image on the Flash Card for normal operation of the system."
	::= 78 

END
