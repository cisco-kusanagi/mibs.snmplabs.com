CXV34-MIB DEFINITIONS ::= BEGIN


IMPORTS
   OBJECT-TYPE             FROM RFC-1212
   DisplayString           FROM RFC1213-MIB
   cxV34,
   SapIndex,
   Alias                   FROM CXProduct-SMI;


--  Configuration Table

--  The table describing:
--  parameters used to configure each V34 slot and its associated hardware 
--  port.


v34SlotTable OBJECT-TYPE
   SYNTAX  SEQUENCE OF V34SlotEntry
   ACCESS  not-accessible
   STATUS  mandatory
   DESCRIPTION
"Describes a table that contains configuration information about each V34 
modem and its associated hardware port."
   ::= { cxV34 1 }


   v34SlotEntry OBJECT-TYPE
      SYNTAX  V34SlotEntry
      ACCESS  not-accessible
      STATUS  mandatory
      DESCRIPTION
"Describes the configuration information applied to a specific V34 modem 
and its associated hardware port."
      INDEX { v34SlotNumber }
      ::= { v34SlotTable 1 }


   V34SlotEntry ::=
      SEQUENCE {
         v34SlotNumber                        SapIndex,
         v34SlotAlias                         Alias,
         v34SlotRowStatus                     INTEGER,
         v34SlotStatus                        INTEGER,
         v34SlotAnswerMode                    INTEGER,
         v34SlotModemString                   DisplayString(SIZE (0..32)),         
         v34SlotDialNumber                    DisplayString,
         v34SlotSpeedStatus                   INTEGER,
         v34SlotRetrainStatus                 INTEGER,
         v34SlotHookStatus                    INTEGER,
         v34SlotRingStatus                    INTEGER,
         v34SlotDsrStatus                     INTEGER,
         v34SlotDtrStatus                     INTEGER,
         v34SlotModel                         INTEGER,
         v34SlotRevision                      INTEGER,
         v34SlotEco                           INTEGER
         }


   v34SlotNumber OBJECT-TYPE
      SYNTAX  SapIndex
      ACCESS  read-only
      STATUS  mandatory
      DESCRIPTION
"Identifies a numerical value applied to the modem. Each device has a 
unique number."
      ::= { v34SlotEntry 1 }

   v34SlotAlias OBJECT-TYPE
      SYNTAX  Alias
      ACCESS  read-write
      STATUS  mandatory
      DESCRIPTION
"Assigns a name used for the alias. Each modem requires a unique name. You 
may not assign the same name twice.

Default Value: none

Range of Values: Up to twelve alphanumeric characters, the first character 
must be alphabetic.

Configuration Changed: operative"
      ::= { v34SlotEntry 2 }

   v34SlotRowStatus OBJECT-TYPE
      SYNTAX  INTEGER {
          invalid         (1),
          valid           (2)
          }
      ACCESS  read-write
      STATUS  mandatory
      DESCRIPTION
"Determines the status of the objects in in a table row.

Default Value: none

Options:

invalid (1): row is flagged, after next reset the values will be disabled 
and the row will be deleted from the table.

valid (2): values are enabled

 Configuration Changed: administrative"

      ::= { v34SlotEntry 3 }

   v34SlotStatus OBJECT-TYPE
      SYNTAX  INTEGER {
         v34-not-present         (1),
         v34-present             (2),
         v34-present-failed      (3)
          }
      ACCESS  read-only
      STATUS  mandatory
      DESCRIPTION
"Identifies the presence or absence of a V.34 modem in the slot and if 
present, whether it has failed initialization.

Default Value: none

Options:

v34-not-present (1)

v34-present (2) 

v34-present-failed (3)"
      ::= { v34SlotEntry 4 }

   v34SlotModemString OBJECT-TYPE
      SYNTAX  DisplayString (SIZE (0..32))
      ACCESS  read-write
      STATUS  mandatory
      DESCRIPTION
"Determines a string to be sent to the modem upon initialization.

Default Value: none

Range of Values: 0-32 alphanumberic  characters

Configuration Changed: administrative"
      ::= { v34SlotEntry 5 }

   v34SlotDialNumber OBJECT-TYPE
      SYNTAX  DisplayString (SIZE (1..20))
      ACCESS  read-write
      STATUS  mandatory
      DESCRIPTION
"Specifies the number used to dial the remote modem.

Default Value: none

Range of Values: An octet string of 12 numeric characters

Configuration Changed: administrative"


      ::= { v34SlotEntry 6 }

   v34SlotAnswerMode OBJECT-TYPE
      SYNTAX  INTEGER {
         answer-disabled         (1),
         answer-enabled          (2),
         test-mode               (3)

          }
      ACCESS  read-write
      STATUS  mandatory
      DESCRIPTION
"Determines whether the device will answer an incoming call.

Default Value: answer-enabled (2)

Options:

answer-disabled (1)

answer-enabled (2)

test-mode (3)

Configuration Changed: operative"
      DEFVAL { answer-enabled }
      ::= { v34SlotEntry 7 }

   v34SlotSpeedStatus OBJECT-TYPE
      SYNTAX  INTEGER {
         speed-0-300             (1),
         speed-600               (2),
         speed-1200              (3),
         speed-2400              (4),
         speed-4800              (5),
         speed-7200              (6),
         speed-9600              (7),
         speed-12000             (8),
         speed-14400             (9),
         speed-16800             (10),
         speed-19200             (11),
         speed-21600             (12),
         speed-24000             (13),
         speed-26400             (14),
         speed-28800             (15)
          }
      ACCESS  read-only
      STATUS  mandatory
      DESCRIPTION
"Identifies the connection rate operative during the current dial call 
only. 

Default Value: none

Options:

speed-0-300 (1)

speed-600 (2)

speed-1200 (3)

speed-2400 (4)

speed-4800 (5)

speed-7200 (6)

speed-9600 (7)

speed-12000 (8)

speed-14400 (9)

speed-16800 (10)

speed-19200 (11)

speed-21600 (12)

speed-24000 (13)

speed-26400 (14)

speed-28800 (15) "
      ::= { v34SlotEntry 8 }


   v34SlotRetrainStatus OBJECT-TYPE
      SYNTAX  INTEGER {
         no-retraining          (1),
         retraining             (2)
            }
      ACCESS  read-only
      STATUS  mandatory
      DESCRIPTION
"Identifies whether the modem is retraining or not. It is only applicable 
while the modem is on-line.

Default Value: none

Options:

no-retraining (1)

retraining (2)"

      ::= { v34SlotEntry 9 }

   v34SlotHookStatus OBJECT-TYPE
      SYNTAX  INTEGER {
         on-hook                 (1),
         off-hook                (2)
     }
      ACCESS  read-only
      STATUS  mandatory
      DESCRIPTION
"Identifies whether the modem is 'off-hook' (connected to the telephone 
line), or 'on-hook' (disconnected).

Default Value: none

Options:

on-hook (1)

off-hook (2)"
      ::= { v34SlotEntry 10 }

   v34SlotRingStatus OBJECT-TYPE
      SYNTAX  INTEGER {
         no-ring                 (1),
         ring                    (2)
    }
      ACCESS  read-only
      STATUS  mandatory
      DESCRIPTION
"Identifies when the modem detects a ring signal from the telephone line.

Default Value: none

Options:

no-ring (1)

ring (2)"
      ::= { v34SlotEntry 11 }

   v34SlotDsrStatus OBJECT-TYPE
      SYNTAX  INTEGER {
         dsr-deasserted          (1),
         dsr-asserted            (2)
    }
      ACCESS  read-only
      STATUS  mandatory
      DESCRIPTION
"Identifies the data transfer state of the modem by the status of the Data 
Set Ready (DSR) signal .

Default Value: none

Options

dsr-deasserted (1): data transfer inactive

dsr-asserted (2): data transfer active"

      ::= { v34SlotEntry 12 }

   v34SlotDtrStatus OBJECT-TYPE
      SYNTAX  INTEGER {
         dtr-deasserted          (1),
         dtr-asserted            (2)
          }
      ACCESS  read-only
      STATUS  mandatory
      DESCRIPTION
"Identifies the status of the Data Terminal Ready (DTR) signal that the 
motherboard uses to dial the pre-stored phone number (if in originate 
mode) or to enable auto answer (if in answer mode).

Default Value: none

Options:

dtr-deasserted (1)

dtr-asserted (2)"
      ::= { v34SlotEntry 13 }


   v34SlotModel OBJECT-TYPE
      SYNTAX  INTEGER (0..7)
      ACCESS  read-only
      STATUS  mandatory
      DESCRIPTION
"Identifies the model number of the Printed Circuit Board (PCB) as an 
integer value from 0 to 7.

Default Value: none

Range of Values: 0-7"
      ::= { v34SlotEntry 14 }

   v34SlotRevision OBJECT-TYPE
      SYNTAX  INTEGER (0..15)
      ACCESS  read-only
      STATUS  mandatory
      DESCRIPTION
"Identifies the revision number of the PCB as an integer value from 0 to 
15.

Default Value: none

Range of Values: 0-15"
      ::= { v34SlotEntry 15 }

   v34SlotEco OBJECT-TYPE
      SYNTAX  INTEGER (0..15)
      ACCESS  read-only
      STATUS  mandatory
      DESCRIPTION
"Identifies the Engineering Change Order (ECO) level of the PCB as an 
integer value from 0 to 15.

Default Value: none

Range of Values: 0-15"

      ::= { v34SlotEntry 16 }


END
