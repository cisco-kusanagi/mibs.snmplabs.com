-- LAN system configuration group for the IPX router.
-- This MIB contains basic configuration information about the IPX
-- interfaces and the binding of these interfaces to the real subnetworks
-- such as device drivers or convergence elements.

CXCFG-IPX-MIB DEFINITIONS ::= BEGIN    

--#CURRENT-VERSION 1

   IMPORTS
      OBJECT-TYPE                     
         FROM RFC-1212
      Alias, cxIpx
         FROM CXProduct-SMI;


     cxCfgIpx OBJECT IDENTIFIER 
    ::= { cxIpx 1 }                                -- is this OK ???

      -- Types
      
      NetNumber ::= OCTET STRING(SIZE(4))
      
      -- Gen config
      
      cxCfgIpxNumClockTicksPerSecond OBJECT-TYPE
   SYNTAX  INTEGER
   ACCESS  read-write
   STATUS  mandatory
   DESCRIPTION
"Identifies the  number of clock ticks per second. 

Range of Values: None 

Default Value: The value is always 1 "

             
   ::= { cxCfgIpx 1 }
 

      -- Config Table for each port

     cxCfgIpxPortTable OBJECT-TYPE
      SYNTAX  SEQUENCE OF CxCfgIpxPortEntry
      ACCESS  not-accessible
      STATUS  mandatory
      DESCRIPTION
"Provides configuration information for each IPX port.

The table contains three default entries (rows); each row corresponds 
to a particular IPX port.  Some of the  values in a row can be modified. If 
more than three IPX ports are required, additional entries can be added."

       ::= { cxCfgIpx 2 }


     cxCfgIpxPortEntry OBJECT-TYPE
         SYNTAX  CxCfgIpxPortEntry
         ACCESS  not-accessible
         STATUS  mandatory
         DESCRIPTION 
"Provides configuration information for a particular IPX port.  Some of the
parameters can be modified."

         INDEX   { cxCfgIpxPort }
         ::= { cxCfgIpxPortTable 1 }

     CxCfgIpxPortEntry ::=
         SEQUENCE {
        cxCfgIpxPort
            INTEGER,
        cxCfgIpxPortIfIndex
            INTEGER,
        cxCfgIpxPortSubnetworkSAPAlias 
            Alias,
        cxCfgIpxPortState 
            INTEGER,
        cxCfgIpxPortRowStatus
            INTEGER,

     cxCfgIpxPortTransportTime
         INTEGER,
     cxCfgIpxPortMaxHops
         INTEGER,
     cxCfgIpxPortIntNetNum
         NetNumber,
     cxCfgIpxPortPerSapBcast
         INTEGER,
     cxCfgIpxPortPerRipBcast
         INTEGER,
     cxCfgIpxPortSapBcast
         INTEGER,
     cxCfgIpxPortRipBcast
         INTEGER,                
     cxCfgIpxPortDiagPackets
         INTEGER,
     cxCfgIpxPortPerRipTxTimer
         INTEGER,
     cxCfgIpxPortPerSapTxTimer
         INTEGER,
     cxCfgIpxPortRipAgeTimer
         INTEGER,
     cxCfgIpxPortSapAgeTimer
         INTEGER,
     cxCfgIpxPortFrameType
         INTEGER,
     cxCfgIpxPortWatchSpoof
         INTEGER,
     cxCfgIpxPortSpxWatchSpoof
         INTEGER,
     cxCfgIpxPortSerialSpoof
         INTEGER,
     cxCfgIpxPortSRSupport
         INTEGER                              
         }


     cxCfgIpxPort OBJECT-TYPE
         SYNTAX  INTEGER (1..65535)
         ACCESS  read-only
         STATUS  mandatory
         DESCRIPTION
"Identifies the number of the IPX Port. The number is used as local
index for this and the ipxStatsTable.

Range of Values: From 1 to 32 

Default Value: None

Note: The system defines three default entries; their respective values are 1, 2, and 3."

         ::= { cxCfgIpxPortEntry 1 }

     cxCfgIpxPortIfIndex OBJECT-TYPE
         SYNTAX  INTEGER
         ACCESS  read-only
         STATUS  mandatory
         DESCRIPTION
"Identifies the table row that contains configuration or monitoring objects
for a specific type of physical interface.

Range of Values: From 1 to the number of entries in the  interface table.  

Default value: None "

         ::= { cxCfgIpxPortEntry 2 }

     cxCfgIpxPortSubnetworkSAPAlias OBJECT-TYPE
         SYNTAX  Alias
         ACCESS  read-write
         STATUS  mandatory
         DESCRIPTION 
"Determines the name which uniquely defines the cxCfgIpxPortSubnetworkSap.

Range of Values: 0 to 16 alphanumeric characters. The first character 
must be a letter, spaces are not allowed.

Default Values: None

Note: The system defines three default entries; their respective values 
are  LAN-PORT1, CNV-PORT1, and CNV-PORT2.

Related Parameter:
The object must be the same as cxLanIoPortAlias 
of the cxLanIoPortTable, and cxFwkDestAlias in cxFwkCircuitTable.

Configuration Changed: Administrative"

         ::= { cxCfgIpxPortEntry 3 }

     cxCfgIpxPortState OBJECT-TYPE
         SYNTAX  INTEGER {
                 on  (1),
                 off (2)
                 }
         ACCESS  read-write
         STATUS  mandatory
         DESCRIPTION
"Determines the initialization state of the IPX port. 

Options:
on (1): The port is active, transmission is possible.

off (2): The port is inactive, transmission is not possible.

Default Values:  (1) On. For LAN ports
                 (2) Off. For convergence ports

Configuration Changed:  Administrative"

        DEFVAL { off }
         ::= { cxCfgIpxPortEntry 4 }

      cxCfgIpxPortRowStatus  OBJECT-TYPE
          SYNTAX  INTEGER {
             invalid (1),
             valid   (2)
             }
          ACCESS  read-write
          STATUS  mandatory
          DESCRIPTION 
"Determines the status of the objects in a table row.

Options:
valid (1): Values are enabled.

invalid (2): Row is flagged, after next reset the values will be disabled 
and the row will be deleted from the table.

Default Value: (1) Valid. Values are enabled 

Configuration Changed: Administrative "

          DEFVAL { valid }
     ::= { cxCfgIpxPortEntry 5 }

      cxCfgIpxPortTransportTime OBJECT-TYPE
     SYNTAX  INTEGER (1..30)
     ACCESS  read-write
     STATUS  mandatory
     DESCRIPTION
"Determines the transport time, in clock ticks, for LAN or WAN links.
This value is set to 1 for LAN links.  WAN links may have a value of 1 or
higher.  One clock tick is 55 ms.

Range of Values: From 1 to 30

Default Value: 1

Configuration Changed:  Administrative"

        DEFVAL { 1 }
     ::= { cxCfgIpxPortEntry 6 }

      cxCfgIpxPortMaxHops OBJECT-TYPE
     SYNTAX  INTEGER (1..16)
     ACCESS  read-write
     STATUS  mandatory
     DESCRIPTION 
"Determines the maximum number of hops a packet may take before it is
discarded.

Range of Values: From 1 to 16

Default Value: 16

Configuration Changed: Administrative "

        DEFVAL { 16 }
     ::= { cxCfgIpxPortEntry 7 }

      cxCfgIpxPortIntNetNum OBJECT-TYPE
     SYNTAX  NetNumber
     ACCESS  read-write
     STATUS  mandatory
     DESCRIPTION
"Determines the IPX internal network number associated with the port.  The
number must be entered as 8 hexadecimal characters, for example 0xAB12CD34. 
The x must be lowercase; the others are not case sensitive.

Range of Values: 4 octets, each character ranging from 00 to FF

Default Value: None

Note: The system defines three default entries; their respective values are 
00 00 00 0xa2, 00 00 00 0xf1, and 00 00 00 0xf2.

Configuration Changed: Administrative "

     ::= { cxCfgIpxPortEntry 8 }

      cxCfgIpxPortPerSapBcast OBJECT-TYPE
     SYNTAX  INTEGER {
           on (1),
           off(2)
        }   
     ACCESS  read-write
     STATUS  mandatory
     DESCRIPTION
"Determines whether periodic SAP broadcasting is active.  

Options:
On (1): SAP broadcasting is active, and the router sends periodic SAP  
broadcasts to advertise its services to other locally attached networks.

Off (2): SAP broadcasting is inactive.

Default Value:  (1) 

Related parameter: The frequency of the broadcast is determined by 
cxCfgIpxPortPerSAPTxTimer.

Configuration Changed:  Administrative"

        DEFVAL { on }
     ::= { cxCfgIpxPortEntry 9 }

      cxCfgIpxPortPerRipBcast OBJECT-TYPE
     SYNTAX  INTEGER {
           on (1),
           off(2)
        }   
     ACCESS  read-write
     STATUS  mandatory
     DESCRIPTION
"Determines whether periodic RIP broadcasting is active.

Options:
on (1): RIP broadcasting is active, and the router sends periodic
RIP broadcasts to advertise its services to other locally attached networks.

off (2): RIP broadcasting is inactive.

Default Value:  on (1) 

Related Parameter: The frequency of the broadcast is determined by 
cxCfgIpxPortPerRipTxTimer.

Configuration Changed:  Administrative"

        DEFVAL { on }
     ::= { cxCfgIpxPortEntry 10 }

      cxCfgIpxPortSapBcast OBJECT-TYPE
     SYNTAX  INTEGER {
           on (1),
           off(2)
        }   
     ACCESS  read-write
     STATUS  mandatory
     DESCRIPTION 
"Determines whether the port sends a SAP broadcast in response to a SAP 
query sent by another router. 

Options:
on (1): The port will respond to SAP queries.

off (2): The port will not respond to SAP queries.

Default Value: on (1) 

Configuration Changed:  Administrative"

        DEFVAL { on }
     ::= { cxCfgIpxPortEntry 11 }

      cxCfgIpxPortRipBcast OBJECT-TYPE
     SYNTAX  INTEGER {
           on (1),
           off(2)
        }   
     ACCESS  read-write
     STATUS  mandatory
     DESCRIPTION 
"Determines whether the port sends a RIP broadcast in response to a RIP 
query sent by another router.  When the value is set to on, the port 
responds to RIP queries.

Options:
On (1): The port will respond to RIP queries.

Off (2): The port will not respond to RIP queries.

Default Value: on (1) 

Configuration Changed:  Administrative"

        DEFVAL { on }
     ::= { cxCfgIpxPortEntry 12 }

      cxCfgIpxPortDiagPackets OBJECT-TYPE
     SYNTAX  INTEGER {
           on (1),
           off(2)
        }   
     ACCESS  read-write
     STATUS  mandatory
     DESCRIPTION
"Determines whether the IPX port will respond to diagnostic packets. 

Options:
On (1): The port will respond, and will transmit a diagnostic response
packet.

Off (2): The port will not respond.

Default Value:  off (2) 

Configuration Changed:  Administrative. "

        DEFVAL { off }
     ::= { cxCfgIpxPortEntry 13 }

      cxCfgIpxPortPerRipTxTimer OBJECT-TYPE
     SYNTAX  INTEGER (1..3600)
     ACCESS  read-write
     STATUS  mandatory
     DESCRIPTION
"Determines the length of time, in seconds, between periodic RIP broadcasts.

Range of Values: From 1 to 3600

Default Value: 60

Configuration Changed: Administrative "

        DEFVAL { 60 }
     ::= { cxCfgIpxPortEntry 14 }

      cxCfgIpxPortPerSapTxTimer OBJECT-TYPE
     SYNTAX  INTEGER (1..3600)
     ACCESS  read-write
     STATUS  mandatory
     DESCRIPTION 
"Determines the length of time, in seconds, between periodic SAP broadcasts.

Range of Values: From 1 to 3600

Default Value: 60

Configuration Changed:  Administrative"

        DEFVAL { 60 }
     ::= { cxCfgIpxPortEntry 15 }

      cxCfgIpxPortRipAgeTimer OBJECT-TYPE
     SYNTAX  INTEGER (1..3600)
     ACCESS  read-write
     STATUS  mandatory
     DESCRIPTION
"Determines the length of time, in seconds, that an entry can remain in 
the IPX port's RIP table without being updated. When the value (number of
seconds) expires the entry in the RIP table is deleted.  A value of 0 means 
aging is not used.

Range of Values: From 1 to 3600

Default Value: 180

Configuration Changed: Administrative "

        DEFVAL { 180 }
     ::= { cxCfgIpxPortEntry 16 }

      cxCfgIpxPortSapAgeTimer OBJECT-TYPE
     SYNTAX  INTEGER (1..3600)
     ACCESS  read-write
     STATUS  mandatory
     DESCRIPTION
"Determines the length of time (aging), in seconds, that an entry can 
remain in the IPX port's SAP table without being updated. When the value
(number of seconds) expires the entry in the SAP table is deleted. A value 
of 0 means aging is not used.

Range of Values: From 1 to 3600

Default Value: 180

Configuration Changed: Administrative "

        DEFVAL { 180 }
     ::= { cxCfgIpxPortEntry 17 }

     
     cxCfgIpxPortFrameType OBJECT-TYPE
         SYNTAX  INTEGER {
                 raw-802-3(1),
                 ethernet-II(2),
                 llc-802-2(3),
                 snap(4)
                 }
         ACCESS  read-write
         STATUS  mandatory
         DESCRIPTION
"Determines which type of framing is used for IPX header information. 
Framing refers to the way the header information is formatted. The format
is determined by the destination IPX number. Upon receipt of data, the IPX 
router checks its address tables to determine which header format is 
used by the destination address. 

The first three options are used for LAN data; the fourth option is used 
for WAN (frame relay) destinations.

Options: 
raw- 802-3 (1): Used for LAN data.

ethernet-II (2): Used for LAN data. 

LLC-802-3 (3): Used for LAN data.  

snap (4): Used for WAN (frame relay).


Default Value: raw- 802-3 (1) 

Configuration Changed: Administrative"

        DEFVAL { raw-802-3 }
         ::= { cxCfgIpxPortEntry 18 }
     

     cxCfgIpxPortWatchSpoof OBJECT-TYPE
     SYNTAX  INTEGER {
           on (1),
           off(2)
        }   
     ACCESS  read-write
     STATUS  mandatory
     DESCRIPTION
"Determines whether IPX Watchdog Spoofing is enabled (on).  IPX Watchdog
Spoofing is a software technique that limits the number of IPX Watchdog 
frames that are sent over a WAN; the technique is intended to decrease the 
use of expensive WAN lines without disturbing overall network use.

If IPX Watchdog Spoofing is desired, the remote peer must also have this 
parameter enabled.

Options:
on (1): IPX Watchdog Spoofing is enabled.

off (2): IPX Watchdog Spoofing is disabled.

Default Value: off (2) 

Configuration Changed: Administrative "

        DEFVAL { off }
     ::= { cxCfgIpxPortEntry 19 }


     cxCfgIpxPortSpxWatchSpoof OBJECT-TYPE
     SYNTAX  INTEGER {
           on (1),
           off(2)
        }   
     ACCESS  read-write
     STATUS  mandatory
     DESCRIPTION
"Determines whether SPX Watchdog Spoofing is enabled (on). SPX Watchdog 
Spoofing is a software technique that limits the number of  SPX Watchdog 
frames that are sent over a WAN; the technique is intended to decrease the 
use of expensive WAN lines without disturbing overall network use.

If SPX Watchdog Spoofing is desired, the remote peer must also have this 
parameter on.

Options:
On (1): SPX Watchdog Spoofing is enabled. 

Off (2): SPX Watchdog Spoofing is disabled.

Default Value: off (2)

Configuration Changed:  Administrative"

        DEFVAL { off }
     ::= { cxCfgIpxPortEntry 20 }


     cxCfgIpxPortSerialSpoof OBJECT-TYPE
     SYNTAX  INTEGER {
           on (1),
           off(2)
        }   
     ACCESS  read-write
     STATUS  mandatory
     DESCRIPTION
"Determines whether Serialization Spoofing is (enabled) on. Serialization 
Spoofing is a software technique that limits the number of Serialization 
frames (they test the legal version of Novell software) that are sent over 
a WAN; the technique is intended to decrease the use of expensive WAN lines 
without disturbing overall network use.

Options:
on (1): Serialization Spoofing is enabled.

off (2): Serialization Spoofing is disabled.

Default Value: off (2)

Configuration Changed: Administrative "

        DEFVAL { off }
     ::= { cxCfgIpxPortEntry 21 }

     cxCfgIpxPortSRSupport OBJECT-TYPE
     SYNTAX  INTEGER {
               enabled  (1),
               disabled (2)
            }              
     ACCESS  read-write
     STATUS  mandatory

     DESCRIPTION
"Determines whether the port should support Source Routing
packet. If it is enabled, the physical infterface of the port
must be Token-Ring. If it is disabled, any Source Routing
packet will be discarded.

Default Value: disabled (2)

Configuration Changed:  administrative"
   DEFVAL { disabled }
   --#STARTING-VERSION 1
   ::= { cxCfgIpxPortEntry 22 }   
   
cxCfgIpxMibLevel OBJECT-TYPE
   SYNTAX   INTEGER
   ACCESS   read-only
   STATUS   mandatory
   DESCRIPTION
"Used to determine current MIB module release supported
by the agent. Object is in decimal."
   DEFVAL { 0 }
   --#STARTING-VERSION 1
   ::= {  cxCfgIpx 20 }

   

END
