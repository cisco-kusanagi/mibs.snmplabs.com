-- extracted from draft-zorn-dime-diameter-base-protocol-mib-02.txt
-- at Wed May 30 06:08:22 2007

   DIAMETER-BASE-PROTOCOL-MIB DEFINITIONS ::= BEGIN

   IMPORTS
         InetAddressType,
         InetAddress
               FROM INET-ADDRESS-MIB -- [RFC4001]

         MODULE-IDENTITY,
         OBJECT-TYPE,
         NOTIFICATION-TYPE,
         Counter32,
         Unsigned32,
         Gauge32,
         TimeTicks
               FROM SNMPv2-SMI -- [RFC2578]
         SnmpAdminString
               FROM SNMP-FRAMEWORK-MIB -- [RFC3411]
         NOTIFICATION-GROUP,
         MODULE-COMPLIANCE,
         OBJECT-GROUP
               FROM SNMPv2-CONF -- [RFC2580]
         RowStatus,
         TruthValue,
         StorageType
               FROM SNMPv2-TC; -- [RFC2579]


   DiameterBasePMIB MODULE-IDENTITY
         LAST-UPDATED "200701280000Z" -- 28 January 2007
         ORGANIZATION "IETF dime Working Group."
         CONTACT-INFO
             "Glen Zorn
              Cisco Systems, Inc.
              2901 Third Avenue, Suite 600
              SEA1/5/
              Seattle, WA 98121
              USA
              Phone: +1 (425) 344 8113
              Email: gwz@cisco.com"
          DESCRIPTION
              "The MIB module for entities implementing the
              Diameter Base Protocol.

              Copyright (C) The Internet Society (2007).  This initial
              version of this MIB module was published in RFC yyyy;
              for full legal notices see the RFC itself.  Supplementary
              information may be available on
              http://www.ietf.org/copyrights/ianamib.html."

   -- RFC Ed.: replace yyyy with actual RFC number and remove this note

         REVISION "200703030000Z" -- 13 June 2006
         DESCRIPTION "Initial version as published in RFC yyyy"
   -- RFC Ed.: replace yyyy with actual RFC number and remove this note
         ::= { mib-2 119 }  -- Experimental value assigned by IANA.

   -- Top-Level Components of this MIB.
   diameterBaseProtocolMIB    OBJECT::= { diameterMIB 1 }
   diameterBaseNotifications  OBJECT IDENTIFIER ::=
                                        { diameterBaseProtocolMIB 0 }
   diameterBaseObjects        OBJECT IDENTIFIER ::=
                                        { diameterBaseProtocolMIB 1 }
   diameterBaseConform        OBJECT IDENTIFIER ::=
                                        { diameterBaseProtocolMIB 2 }

   dbpLocalCfgs    OBJECT IDENTIFIER ::= { diameterBaseObjects 1 }
   dbpLocalStats   OBJECT IDENTIFIER ::= { diameterBaseObjects 2 }
   dbpPeerCfgs     OBJECT IDENTIFIER ::= { diameterBaseObjects 3 }
   dbpPeerStats    OBJECT IDENTIFIER ::= { diameterBaseObjects 4 }
   dbpRealmCfgs    OBJECT IDENTIFIER ::= { diameterBaseObjects 5 }
   dbpRealmStats   OBJECT IDENTIFIER ::= { diameterBaseObjects 6 }
   dbpNotifCfgs    OBJECT IDENTIFIER ::= { diameterBaseObjects 7 }


   -- Protocol Error Notifications

   dbpProtocolErrorNotifEnabled OBJECT-TYPE
          SYNTAX      TruthValue
          MAX-ACCESS  read-write
          STATUS      current
          DESCRIPTION
                "Setting the value of this object to True(1)
                 enables the dbpProtocolErrorNotif notification."
          DEFVAL      {false}
          ::= { dbpNotifCfgs 1 }

   dbpProtocolErrorNotif NOTIFICATION-TYPE
          OBJECTS {
                     dbpPeerId,
                     dbpPeerStatsProtocolErrors
                  }
          STATUS     current
          DESCRIPTION
                "An dbpProtocolError Notification is sent when both the
                 following conditions are true:
                 1) the value of dbpProtocolErrorNotifEnabled is True(1)
                 2) the value of dbpPerPeerStatsProtocolErrors changes
                 It can be utilized by an NMS to trigger
                 logical/physical entity table maintenance polls.
                 An agent must not generate more than one
                 dbpProtocolError 'notification event' in a five second
                 period, where a 'notification event' is the
                 transmission of a single Notification PDU to a list of
                 Notification destinations.
                 If additional premanent failures occur within the
                 five second 'throttling' period, then these
                 notification events should be suppressed by the agent.
                 An  NMS should periodically check the value of
                 dbpPerPeerStatsProtocolErrors to detect any missed
                 dbpProtocolError notification events, e.g. due to
                 throttling or transmission loss."
         ::= { diameterBaseNotifications 1 }


   -- Transient Error Notifications

   dbpTransientFailureNotifEnabled OBJECT-TYPE
          SYNTAX      TruthValue
          MAX-ACCESS  read-write
          STATUS      current
          DESCRIPTION
                "Setting the value of this object to True(1)
                 enables the dbpTransientFailure Notification."
          ::= { dbpNotifCfgs 2 }

   dbpTransientFailureNotif NOTIFICATION-TYPE
          OBJECTS  {
                      dbpPeerId,
                      dbpPeerStatsTransientFailures
                   }
          STATUS     current
          DESCRIPTION
                "An dbpTransientFailure Notification is sent when both
                 the following conditions are true:
                 1) the value of dbpTransientFailureNotifEnabled
                    is True(1)
                 2) the value of dbpPerPeerStatsTransientFailures
                    changes
                 It can be utilized by an NMS to trigger
                 logical/physical entity table maintenance polls.
                 An agent must not generate more than one
                 dbpTransientFailure 'notification event' in a five
                 second period, where a 'notification event' is the
                 transmission of a single notification PDU to a list
                 of notification destinations.
                 If additional transient failures occur
                 within the five second 'throttling' period, then
                 these notification events should be suppressed
                 by the agent.
                 An NMS should periodically check the value of
                 dbpPerPeerStatsTransientFailures to detect any
                 missed dbpTransientFailure notification events,
                 e.g. due to throttling or transmission loss."
         ::= { diameterBaseNotifications 2 }


   -- Permanent Failure Notifications

   dbpPermanentFailureNotifEnabled OBJECT-TYPE
          SYNTAX      TruthValue
          MAX-ACCESS  read-write
          STATUS      current
          DESCRIPTION
                "Setting the value of this object to True(1)
                 enables the dbpPermanentFailure notification."
          DEFVALUE    { false }
          ::= { dbpNotifCfgs 3 }

   dbpPermanentFailureNotif NOTIFICATION-TYPE
          OBJECTS  {
                      dbpPeerId,
                      dbpPeerStatsPermanentFailures
                   }
          STATUS     current
          DESCRIPTION
                "An dbpPermanentFailure notification is sent when
                 both the following conditions are true:
                 1) the value of dbpPermanentFailureNotifEnabled
                    is True(1)
                 2) the value of dbpPerPeerStatsPermanentFailures
                    changes
                 It can be utilized by an NMS to trigger
                 logical/physical entity table maintenance polls.
                 An agent must not generate more than one
                 dbpPermanentFailure 'notification event' in a five
                 second period, where a 'notification event' is the
                 transmission of a single notification PDU to a list
                 of notification destinations.
                 If additional premanent failures occur within the
                 five second 'throttling' period, then these
                 trap-events should be suppressed by the agent.
                 An NMS should periodically check the value of
                 dbpPerPeerStatsPermanentFailures to detect
                 any missed dbpPermanentFailure trap-events,
                 e.g. due to throttling or transmission loss."
         ::= { diameterBaseNotifications 3 }


   -- Connection Down Notifs
   dbpPeerConnectionDownNotifEnabled OBJECT-TYPE
          SYNTAX      TruthValue
          MAX-ACCESS  read-write
          STATUS      current
          DESCRIPTION
                "Setting the value of this object to True(1)
                 enables the dbpPeerConnectionDown notification."
          DEFVAL      { false }
          ::= { dbpNotifCfgs 4 }

   dbpPeerConnectionDownNotif NOTIFICATION-TYPE
          OBJECTS  {
                      dbpLocalId,
                      dbpPeerId
                   }
          STATUS     current
          DESCRIPTION
                "An dbpPeerConnectionDown notification is sent when
                 both the following conditions are true:
                 1) the value of dbpPeerConnectionDownNotifEnabled is
                    True(1)
                 2) dbpPerPeerStatsState changes to closed(1)
                 It can be utilized by an NMS to trigger
                 logical/physical
                 entity table maintenance polls.  An agent must not
                 generate more than one dbpPeerConnectionDown
                 'notification event' in a five second period, where a
                 'notification event' is the transmission of a single
                 notification PDU to a list of notification
                 destinations.
                 If additional 'transport down' events occur within the
                 five second 'throttling' period, then these trap-events
                 should be suppressed by the agent."
         ::= { diameterBaseNotifications 4 }


   -- Connection Up Notifications

   dbpPeerConnectionUpNotifEnabled OBJECT-TYPE
          SYNTAX      TruthValue
          MAX-ACCESS  read-write
          STATUS      current
          DESCRIPTION
                "Setting the value of this object to True(1)
                 enables the dbpPeerConnectionUp notification."
          DEFVAL      { false }
          ::= { dbpNotifCfgs 5 }

   dbpPeerConnectionUpNotif NOTIFICATION-TYPE
          OBJECTS  {
                      dbpLocalId,
                      dbpPeerId
                   }
          STATUS     current
          DESCRIPTION
                "An dbpPeerConnectionUp notification is sent
                 when both thefollowing conditions are true:
                 1) the value of dbpPeerConnectionUpNotifEnabled is
                    True(1)
                 2) the value of dbpPerPeerStatsState changes to
                    either rOpen(6)or iOpen(7)
                 It can be utilized by an NMS to trigger
                 logical/physical entity table maintenance polls.
                 An agent must not generate
                 more than one dbpPeerConnectionDown
                 'notification event' in a
                 five second period, where a 'notification event' is the
                 transmission of a single notification PDU to a
                 list of notification destinations.
                 If additional 'transport down' events
                 occur within the five second 'throttling' period,
                 then these trap-events should be suppressed by the
                 agent."
         ::= { diameterBaseNotifications 5 }


   -- Local Configs

   dbpLocalId OBJECT-TYPE
          SYNTAX     SnmpAdminString
          MAX-ACCESS read-only
          STATUS     current
          DESCRIPTION
                "The implementation-specific identification
                 string for the Diameter software in use on
                 the system; for example: 'diameterd'"
          ::= { dbpLocalCfgs 1 }

   dbpLocalIpAddrTable OBJECT-TYPE
       SYNTAX          SEQUENCE OF DbpLocalIpAddrEntry
       MAX-ACCESS      not-accessible
       STATUS          current
       DESCRIPTION
               "The table listing the Diameter
               local host's IP Addresses."
       ::= { dbpLocalCfgs 2 }

   dbpLocalIpAddrEntry OBJECT-TYPE
       SYNTAX          DbpLocalIpAddrEntry
       MAX-ACCESS      not-accessible
       STATUS          current
       DESCRIPTION
               "A row entry representing a Diameter
               local host IP Address."
       INDEX           { dbpLocalIpAddrIndex }
       ::= { dbpLocalIpAddrTable 1 }

   DbpLocalIpAddrEntry ::= SEQUENCE {
           dbpLocalIpAddrIndex Unsigned32,
           dbpLocalIpAddrType  InetAddressType,
           dbpLocalIpAddress   InetAddress
   }

   dbpLocalIpAddrIndex OBJECT-TYPE
       SYNTAX          Unsigned32 (1..4294967295 )
       MAX-ACCESS      not-accessible
       STATUS          current
       DESCRIPTION
               "A number uniquely identifying the number
               of IP Addresses supported by this Diameter
               host."
       ::= { dbpLocalIpAddrEntry 1 }

   dbpLocalIpAddrType OBJECT-TYPE
       SYNTAX          InetAddressType
       MAX-ACCESS      read-only
       STATUS          current
       DESCRIPTION
               "The type of internet address stored
               in dbpLocalIpAddress."
       ::= { dbpLocalIpAddrEntry 2 }

   dbpLocalIpAddress OBJECT-TYPE
       SYNTAX          InetAddress
       MAX-ACCESS      read-only
       STATUS          current
       DESCRIPTION
               "The IP-Address of the host, which is of the type
               specified in dbpLocalIpAddrType."
       ::= { dbpLocalIpAddrEntry 3 }

   dbpLocalTcpListenPort OBJECT-TYPE
          SYNTAX      Unsigned32 (1..65535)
          MAX-ACCESS  read-only
          STATUS      current
          DESCRIPTION
                "Diameter TCP 'listen' port."
          ::= { dbpLocalCfgs 3 }

   dbpLocalSctpListenPort OBJECT-TYPE
          SYNTAX      Unsigned32 (1..65535)
          MAX-ACCESS  read-only
          STATUS      current
          DESCRIPTION
                "Diameter SCTP 'listen' port."
          ::= { dbpLocalCfgs 4 }

   dbpLocalOriginHost OBJECT-TYPE
       SYNTAX          SnmpAdminString
       MAX-ACCESS      read-write
       STATUS          current
       DESCRIPTION     "This object represents the Local Origin Host."
       DEFVAL          { "" }
       ::= { dbpLocalCfgs 5 }

   dbpLocalRealm OBJECT-TYPE
       SYNTAX          SnmpAdminString
       MAX-ACCESS      read-only
       STATUS          current
       DESCRIPTION     "This object represents the Local Realm Name."
       DEFVAL          { "" }
       ::= { dbpLocalCfgs 6 }


   dbpLocalStatsTotalMessagesIn OBJECT-TYPE
          SYNTAX      Counter32
          MAX-ACCESS  read-only
          STATUS      current
          DESCRIPTION
                "The total number of Diameter Base Protocol
                 messages received."
          ::= { dbpLocalStats 1 }
   Base Protocol
   dbpLocalStatsTotalMessagesOut OBJECT-TYPE
          SYNTAX      Counter32
          MAX-ACCESS  read-only
          STATUS      current
          DESCRIPTION
                "The total number of Diameter Base Protocol
                 messages transmitted."
          ::= { dbpLocalStats 2 }

   dbpLocalStatsTotalUpTime OBJECT-TYPE
          SYNTAX     TimeTicks
          MAX-ACCESS read-only
          STATUS     current
          DESCRIPTION
                "This object represents the total time this Diameter
                 server has been up until now."
          ::= { dbpLocalStats 3 }

   dbpLocalResetTime OBJECT-TYPE
          SYNTAX     TimeTicks
          MAX-ACCESS read-only
          STATUS     current
          DESCRIPTION
                "If the server keeps persistent state (e.g., a process)
                 and supports a 'reset' operation (e.g., can be told to
                 re-read configuration files), this value will be the
                 time elapsed (in hundredths of a second) since the
                 server was 'reset'.  For software that does not
                 have persistence or does not support a 'reset'
                 operation, this value will be zero."
          ::= { dbpLocalStats 4 }

   dbpLocalConfigReset OBJECT-TYPE
          SYNTAX     INTEGER { other(1),
                               reset(2),
                               initializing(3),
                               running(4) }
          MAX-ACCESS read-write
          STATUS     current
          DESCRIPTION
                "Status/action object to reinitialize any persistent
                 server state.  When set to reset(2), any persistent
                 server state (such as a process) is reinitialized as
                 if the server had just been started.  This value will
                 never be returned by a read operation.  When read,
                 one of the following values will be returned:
                    other(1) - server in some unknown state;
                    reset(2) - command to reinitialize server state;
                    initializing(3) - server (re)initializing;
                    running(4) - server currently running."
          DEFVAL      { other }
          ::= { dbpLocalStats 5 }
   -- ***
   dbpLocalApplicationsTable OBJECT-TYPE
          SYNTAX     SEQUENCE OF DbpLocalApplicationsEntry
          MAX-ACCESS not-accessible
          STATUS     current
          DESCRIPTION
                "The table listing the Diameter applications
                 supported by this server."
          ::= { dbpLocalCfgs 7 }

   dbpLocalApplicationsEntry OBJECT-TYPE
          SYNTAX     DbpLocalApplicationsEntry
          MAX-ACCESS not-accessible
          STATUS     current
          DESCRIPTION
                "A row entry representing a Diameter
                 application on this server."
          INDEX      { dbpLocalApplicationsIndex }
          ::= { dbpLocalApplicationsTable 1 }

   DbpLocalApplicationsEntry ::= SEQUENCE {
          dbpLocalApplicationsIndex  Unsigned32,
          dbpLocalApplStorageType    StorageType,
          dbpLocalApplicationsStatus RowStatus
   }

   dbpLocalApplicationsIndex OBJECT-TYPE
          SYNTAX      Unsigned32 ( 1..4294967295 )
          MAX-ACCESS  not-accessible
          STATUS      current
          DESCRIPTION
                  "A number uniquely identifying a
                  supported Diameter application. Upon reload,
                  dbpLocalApplIndex values may be changed."
          ::= { dbpLocalApplicationsEntry 1 }

   dbpLocalApplStorageType OBJECT-TYPE
       SYNTAX          StorageType
       MAX-ACCESS      read-create
       STATUS          current
       DESCRIPTION
               "The storage type for this conceptual row. None of
               the columnar objects is writable when the conceptual
               row is permanent."
       REFERENCE       "Textual Conventions for SMIv2, Section 2."
       DEFVAL          { nonVolatile }
       ::= { dbpLocalApplEntry 2 }

   dbpLocalApplicationsStatus OBJECT-TYPE
          SYNTAX     RowStatus
          MAX-ACCESS read-create
          STATUS     current
          DESCRIPTION
               "The status of this conceptual row.
               To create a row in this table, a manager must
               set this object to either createAndGo(4) or
               createAndWait(5).

               Until instances of all corresponding columns are
               appropriately configured, the value of the
               corresponding instance of the cdsgStatus column is
               'notReady'.

               In particular, a newly created row cannot be made
               active until the corresponding dbpLocalApplIndex
               has been set.

               dbpLocalApplIndex may not be modified while the
               value of this object is active(1):
               An attempt to set these objects while the value of
               dbpLocalApplStatus is active(1) will result in
               an inconsistentValue error.

               Entries in this table with dbpLocalApplStatus equal to
               active(1) remain in the table until destroyed.

               Entries in this table with dbpLocalApplStatus equal to
               values other than active(1) will be destroyed after
               timeout (5 minutes)."
          ::= { dbpLocalApplicationsEntry 3 }
   -- ***
   dbpPeerTable OBJECT-TYPE
          SYNTAX     SEQUENCE OF DbpPeerEntry
          MAX-ACCESS not-accessible
          STATUS     current
          DESCRIPTION
                "The table listing information regarding
                 the discovered or configured Diameter
                 peer servers."
          ::= { dbpPeerCfgs 1 }

   dbpPeerEntry OBJECT-TYPE
          SYNTAX     DbpPeerEntry
          MAX-ACCESS not-accessible
          STATUS     current
          DESCRIPTION
                "A row entry representing a discovered
                 or configured Diameter peer server."
          INDEX      { dbpPeerIndex }
          ::= { dbpPeerTable 1 }

   DbpPeerEntry ::= SEQUENCE {
          dbpPeerIndex                         Unsigned32,
          dbpPeerId                       SnmpAdminString,
          dbpPeerPortConnect                   Unsigned32,
          dbpPeerPortListen                    Unsigned32,
          dbpPeerProtocol                         INTEGER,
          dbpPeerSecurity                         INTEGER,
          dbpPeerFirmwareRevision              Unsigned32,
          dbpPeerStorageType                  StorageType,
          dbpPeerStatus                         RowStatus }

   dbpPeerIndex OBJECT-TYPE
          SYNTAX     Unsigned32 (1..4294967295)
          MAX-ACCESS not-accessible
          STATUS     current
          DESCRIPTION
                "A number uniquely identifying each Diameter peer
                 with which the host server communicates.
                 Upon reload, dbpPeerIndex values may be changed."
          ::= { dbpPeerEntry  1 }

   dbpPeerId OBJECT-TYPE
          SYNTAX     SnmpAdminString
          MAX-ACCESS read-create
          STATUS     current
          DESCRIPTION
                "The server identifier for the Diameter peer.
                 It must be unique and non-empty."
          ::= { dbpPeerEntry  2 }

   dbpPeerPortConnect OBJECT-TYPE
          SYNTAX     Unsigned32 (1..65535)
          MAX-ACCESS read-only
          STATUS     current
          DESCRIPTION
                "The connection port this server used
                 to connect to the Diameter peer.
                 If there is no active connection, this
                 value will be zero(0)."
          ::= { dbpPeerEntry  3 }

   dbpPeerPortListen OBJECT-TYPE
          SYNTAX     Unsigned32 (1..65535)
          MAX-ACCESS read-only
          STATUS     current
          DESCRIPTION
                "The port the server is listening on."
          ::= { dbpPeerEntry  4 }

   dbpPeerProtocol OBJECT-TYPE
          SYNTAX     INTEGER { tcp(1),
                               sctp(2) }
          MAX-ACCESS read-only
          STATUS     current
          DESCRIPTION
                "The transport protocol (tcp/sctp) the
                 Diameter peer is using."
          ::= { dbpPeerEntry  5 }

   dbpPeerSecurity OBJECT-TYPE
          SYNTAX     INTEGER { other(1),
                               tls(2),
                               ipsec(3) }
          MAX-ACCESS read-only
          STATUS     current
          DESCRIPTION
                "The security the Diameter peer is using.

                 other(1) - Unknown Security Protocol
                 tls(2)   - Transport Layer Security Protocol
                 ipsec(3) - Internet Protocol Security"
          DEFVAL          { other }
          ::= { dbpPeerEntry  6 }

   dbpPeerFirmwareRevision OBJECT-TYPE
          SYNTAX     Unsigned32 (1..4294967295)
          MAX-ACCESS read-only
          STATUS     current
          DESCRIPTION
                "Firmware revision of peer.  If no firmware
                 revision, the revision of the Diameter software
                 module may be reported instead."
          ::= { dbpPeerEntry 7 }

   dbpPeerStorageType OBJECT-TYPE
       SYNTAX          StorageType
       MAX-ACCESS      read-create
       STATUS          current
       DESCRIPTION
               "The storage type for this conceptual row.
               Only the dbpPeerPortListen object is writable when
               the conceptual row is permanent."
       REFERENCE       "Textual Conventions for SMIv2, Section 2."
       DEFVAL          { nonVolatile }
       ::= { dbpPeerEntry 8 }

   dbpPeerStatus OBJECT-TYPE
          SYNTAX     RowStatus
          MAX-ACCESS read-create
          STATUS     current
          DESCRIPTION
                "Status of the peer entry: creating the entry
                 enables the peer, destroying the entry disables
                 the peer."
          ::= {dbpPeerEntry 9 }

   dbpPeerIpAddrTable OBJECT-TYPE
          SYNTAX     SEQUENCE OF DbpPeerIpAddrEntry
          MAX-ACCESS not-accessible
          STATUS     current
          DESCRIPTION
                "The table listing the Diameter
                 peer IP addresses."
          ::= { dbpPeerCfgs 2 }

   dbpPeerIpAddrEntry OBJECT-TYPE
          SYNTAX     DbpPeerIpAddrEntry
          MAX-ACCESS not-accessible
          STATUS     current
          DESCRIPTION
                "A row entry representing a
                 peer Diameter server."
          INDEX      {
                       dbpPeerIndex,
                       dbpPeerIpAddressIndex }
          ::= { dbpPeerIpAddrTable 1 }

   DbpPeerIpAddrEntry ::= SEQUENCE {
          dbpPeerIpAddressIndex Unsigned32,
          dbpPeerIpAddressType  InetAddressType,
          dbpPeerIpAddress      InetAddress }

   dbpPerrIpAddressIndex OBJECT-TYPE
          SYNTAX     Unsigned32 (1..4294967295)
          MAX-ACCESS not-accessible
          STATUS     current
          DESCRIPTION
                "A number uniquely identifying the number
                 of IP Addresses supported by all Diameter
                 peers."
          ::= { dbpPeerIpAddrEntry  1 }

   dbpPeerIpAddressType OBJECT-TYPE
          SYNTAX      InetAddressType
          MAX-ACCESS  read-only
          STATUS      current
          DESCRIPTION
                "The type of address stored in
                 diameterPeerIpAddress."
          ::= {dbpPeerIpAddrEntry 2}

   dbpPeerIpAddress OBJECT-TYPE
          SYNTAX      InetAddress
          MAX-ACCESS  read-only
          STATUS      current
          DESCRIPTION
                "The active IP Address(es) used for connections."
          ::= {dbpPeerIpAddrEntry 3}

   dbpAppAdvToPeerTable OBJECT-TYPE
          SYNTAX     SEQUENCE OF DbpAppAdvToPeerEntry
          MAX-ACCESS not-accessible
          STATUS     current
          DESCRIPTION
                "The table listing the applications advertised by
                 this host to each peer and the types of service
                 supported: accounting, authentication or both."
          ::= { dbpLocalCfgs 8 }

   dbpAppAdvToPeerEntry OBJECT-TYPE
          SYNTAX     DbpAppAdvToPeerEntry
          MAX-ACCESS not-accessible
          STATUS     current
          DESCRIPTION
                "A row entry representing a discovered or
                 configured Diameter peer server."
          INDEX      { dbpPeerIndex,
                       dbpAppAdvToPeerVendorId,
                       dbpAppAdvToPeerIndex }
          ::= { dbpAppAdvToPeerTable 1 }

   DbpAppAdvToPeerEntry ::= SEQUENCE {
          dbpAppAdvToPeerVendorId                 Unsigned32,
          dbpAppAdvToPeerIndex                    Unsigned32,
          dbpAppAdvToPeerServices                    INTEGER,
          dbpAppAppAdvToPeerStorageType           StorageType,
          dbpAppAdvToPeerStatus                    RowStatus }

   dbpAppAdvToPeerVendorId OBJECT-TYPE
          SYNTAX     Unsigned32 ( 1..4294967295 )
          MAX-ACCESS not-accessible
          STATUS     current
          DESCRIPTION
                "The IANA Enterprise Code value assigned to
                 the vendor of the Diameter device."
          ::= { dbpAppAdvToPeerEntry  1 }

   dbpAppAdvToPeerIndex OBJECT-TYPE
          SYNTAX     Unsigned32 ( 1..4294967295 )
          MAX-ACCESS not-accessible
          STATUS     current
          DESCRIPTION
                "A number uniquely identifying a Diameter
                 application advertised as supported by
                 this host to each peer.  Upon reload,
                 dbpAppAdvToPeerIndex values may be
                 changed"
          ::= { dbpAppAdvToPeerEntry  2 }

   dbpAppAdvToPeerServices OBJECT-TYPE
          SYNTAX     INTEGER { acct(1),
                               auth(2),
                               both(3) }
          MAX-ACCESS read-only
          STATUS     current
          DESCRIPTION
                "The type of services supported for each application,
                 accounting, authentication or both."
          ::= { dbpAppAdvToPeerEntry  3 }

   dbpAppAdvToPeerStorageType OBJECT-TYPE
       SYNTAX          StorageType
       MAX-ACCESS      read-create
       STATUS          current
       DESCRIPTION
               "The storage type for this conceptual row.
               None of the objects are writable when the
               conceptual row is permanent."
       REFERENCE       "Textual Conventions for SMIv2, Section 2."
       DEFVAL          { nonVolatile }
       ::= { dbpAppAdvToPeerEntry 4 }

   dbpAppAdvToPeerStatus OBJECT-TYPE
          SYNTAX     RowStatus
          MAX-ACCESS read-create
          STATUS     current
          DESCRIPTION
                "Status of the entry: creating the entry causes the
                 application to be advertised, destroying the entry
                 ceases advertisement."
          ::= { dbpAppAdvToPeerEntry  5 }

   -- Applications advertised BY peers

   dbpAppAdvFromPeerTable OBJECT-TYPE
       SYNTAX          SEQUENCE OF DbpAppAdvFromPeerEntry
       MAX-ACCESS      not-accessible
       STATUS          current
       DESCRIPTION
               "The table listing the applications advertised by
               each peer to this host and the types of service
               supported: accounting, authentication or both."
       ::= { dbpPeerCfgs 3 }

   dbpAppAdvFromPeerEntry OBJECT-TYPE
       SYNTAX          DbpAppAdvFromPeerEntry
       MAX-ACCESS      not-accessible
       STATUS          current
       DESCRIPTION
               "A row entry representing a discovered or
               configured Diameter peer server."
       INDEX           {
                           dbpPeerIndex,
                           dbpAppAdvFromPeerVendorId,
                           dbpAppAdvFromPeerIndex
                       }
       ::= { dbpAppAdvFromPeerTable 1 }

   DbpAppAdvFromPeerEntry ::= SEQUENCE {
           dbpAppAdvFromPeerVendorId Unsigned32,
           dbpAppAdvFromPeerIndex    Unsigned32,
           dbpAppAdvFromPeerType     INTEGER
   }

   dbpAppAdvFromPeerVendorId OBJECT-TYPE
       SYNTAX          Unsigned32 (1..4294967295 )
       MAX-ACCESS      not-accessible
       STATUS          current
       DESCRIPTION
               "The IANA Enterprise Code value assigned to
               the vendor of the Diameter application."
       ::= { dbpAppAdvFromPeerEntry 1 }

   dbpAppAdvFromPeerIndex OBJECT-TYPE
       SYNTAX          Unsigned32 (1..4294967295 )
       MAX-ACCESS      not-accessible
       STATUS          current
       DESCRIPTION
               "A number uniquely identifying the applications
               advertised as supported from each Diameter peer."
       ::= { dbpAppAdvFromPeerEntry 2 }

   dbpAppAdvFromPeerType OBJECT-TYPE
       SYNTAX          INTEGER  {
                           acct(1),
                           auth(2),
                           both(3)
                       }
       MAX-ACCESS      read-only
       STATUS          current
       DESCRIPTION
               "The type of services supported for each application,
               accounting, authentication or both.
                   acct(1)  -  accounting
                   auth(2)  -  authentication
                   both(3)  -  both accounting and authentication."
       ::= { dbpAppAdvFromPeerEntry 3 }

   -- table of vendor-IDs supported by each peer

   dbpPeerVendorTable OBJECT-TYPE
       SYNTAX          SEQUENCE OF DbpPeerVendorEntry
       MAX-ACCESS      not-accessible
       STATUS          current
       DESCRIPTION
               "The table listing the Vendor IDs
               supported by the peer."
       ::= { dbpPeerCfgs 4 }

   dbpPeerVendorEntry OBJECT-TYPE
       SYNTAX          DbpPeerVendorEntry
       MAX-ACCESS      not-accessible
       STATUS          current
       DESCRIPTION
               "A row entry representing a
               Vendor ID supported by the peer."
       INDEX           {
                           dbpPeerIndex,
                           dbpPeerVendorIndex
                       }
       ::= { dbpPeerVendorTable 1 }

   DbpPeerVendorEntry ::= SEQUENCE {
           dbpPeerVendorIndex       Unsigned32,
           dbpPeerVendorId          INTEGER ,
           dbpPeerVendorStorageType StorageType,
           dbpPeerVendorRowStatus   RowStatus
   }
   dbpPeerVendorIndex OBJECT-TYPE
       SYNTAX          Unsigned32 (1..4294967295 )
       MAX-ACCESS      not-accessible
       STATUS          current
       DESCRIPTION
               "A number uniquely identifying the Vendor
               ID supported by the peer. Upon reload,
               dbpPeerVendorIndex values may be changed."
       ::= { dbpPeerVendorEntry 1 }

   dbpPeerVendorId OBJECT-TYPE
       SYNTAX          INTEGER  {
                           diameterVendorIetf(0),
                           diameterVendorCisco(9),
                           diameterVendor3gpp(10415),
                           diameterVendorVodafone(12645)
                       }
       MAX-ACCESS      read-create
       STATUS          current
       DESCRIPTION
               "The active vendor ID used for peer connections.
               diameterVendorIetf(0)           -- IETF
               diameterVendor3gpp(10415)       -  3GPP
       DEFVAL          { diameterVendorIetf }
       ::= { dbpPeerVendorEntry 2 }

   dbpPeerVendorStorageType OBJECT-TYPE
       SYNTAX          StorageType
       MAX-ACCESS      read-create
       STATUS          current
       DESCRIPTION
               "The storage type for this conceptual row.
               None of the objects are writable when the
               conceptual row is permanent."
       REFERENCE       "Textual Conventions for SMIv2, Section 2."
       DEFVAL          { nonVolatile }
       ::= { dbpPeerVendorEntry 3 }

   dbpPeerVendorRowStatus OBJECT-TYPE
       SYNTAX          RowStatus
       MAX-ACCESS      read-create
       STATUS          current
       DESCRIPTION
               "The status of this conceptual row.

               To create a row in this table, a manager must
               set this object to either createAndGo(4) or
               createAndWait(5).
               Until instances of all corresponding columns are
               appropriately configured, the value of the
               corresponding instance of the dbpPeerVendorRowStatus
               column is 'notReady'.

               In particular, a newly created row cannot be made
               active until the corresponding dbpPeerVendorId has been
               set. Also, a newly created row cannot be made active
               until the corresponding 'dbpPeerIndex' has been set.

               dbpPeerVendorId may not be modified while the
               value of this object is active(1):
               An attempt to set these objects while the value of
               dbpPeerVendorRowStatus is active(1) will result in
               an inconsistentValue error.

               Entries in this table with dbpPeerVendorRowStatus equal
                to active(1) remain in the table until destroyed.

               Entries in this table with dbpPeerVendorRowStatus equal
               to values other than active(1) will be destroyed after
               timeout (5 minutes)."
       ::= { dbpPeerVendorEntry 4 }


   dbpPerPeerStatsTable OBJECT-TYPE
          SYNTAX     SEQUENCE OF DbpPerPeerStatsEntry
          MAX-ACCESS not-accessible
          STATUS     current
          DESCRIPTION
                "The table listing the Diameter peer statistics."
          ::= { dbpPeerStats 1 }

   dbpPerPeerStatsEntry OBJECT-TYPE
          SYNTAX     DbpPerPeerStatsEntry
          MAX-ACCESS not-accessible
          STATUS     current
          DESCRIPTION
                "A row entry representing a Diameter peer."
          INDEX     { dbpPeerIndex }
          ::= { dbpPerPeerStatsTable 1 }

   DbpPerPeerStatsEntry ::= SEQUENCE {
          dbpPerPeerStatsState               INTEGER,
          dbpPerPeerStatsStateDuration       TimeTicks,
          dbpPerPeerStatsLastDiscCause       INTEGER,
          dbpPerPeerStatsWhoInitDisconnect   INTEGER,
          dbpPerPeerStatsDWCurrentStatus     INTEGER,
          dbpPerPeerStatsTimeoutConnAtmpts   Counter32,
          dbpPerPeerStatsASRsIn              Counter32,
          dbpPerPeerStatsASRsOut             Counter32,
          dbpPerPeerStatsASAsIn              Counter32,
          dbpPerPeerStatsASAsOut             Counter32,
          dbpPerPeerStatsACRsIn              Counter32,
          dbpPerPeerStatsACRsOut             Counter32,
          dbpPerPeerStatsACAsIn              Counter32,
          dbpPerPeerStatsACAsOut             Counter32,
          dbpPerPeerStatsCERsIn              Counter32,
          dbpPerPeerStatsCERsOut             Counter32,
          dbpPerPeerStatsCEAsIn              Counter32,
          dbpPerPeerStatsCEAsOut             Counter32,
          dbpPerPeerStatsDWRsIn              Counter32,
          dbpPerPeerStatsDWRsOut             Counter32,
          dbpPerPeerStatsDWAsIn              Counter32,
          dbpPerPeerStatsDWAsOut             Counter32,
          dbpPerPeerStatsDPRsIn              Counter32,
          dbpPerPeerStatsDPRsOut             Counter32,
          dbpPerPeerStatsDPAsIn              Counter32,
          dbpPerPeerStatsDPAsOut             Counter32,
          dbpPerPeerStatsRARsIn              Counter32,
          dbpPerPeerStatsRARsOut             Counter32,
          dbpPerPeerStatsRAAsIn              Counter32,
          dbpPerPeerStatsRAAsOut             Counter32,
          dbpPerPeerStatsSTRsIn              Counter32,
          dbpPerPeerStatsSTRsOut             Counter32,
          dbpPerPeerStatsSTAsIn              Counter32,
          dbpPerPeerStatsSTAsOut             Counter32,
          dbpPerPeerStatsDWReqTimer          TimeTicks,
          dbpPerPeerStatsRedirectEvents      Counter32,
          dbpPerPeerStatsAccDupRequests      Counter32,
          dbpPerPeerStatsMalformedReqsts     Counter32,
          dbpPerPeerStatsAccsNotRecorded     Counter32,
          dbpPerPeerStatsAccRetrans          Counter32,
          dbpPerPeerStatsTotalRetrans        Counter32,
          dbpPerPeerStatsAccPendReqstsOut    Gauge32,
          dbpPerPeerStatsAccReqstsDropped    Counter32,
          dbpPerPeerStatsHByHDropMessages    Counter32,
          dbpPerPeerStatsEToEDupMessages     Counter32,
          dbpPerPeerStatsUnknownTypes        Counter32,
          dbpPerPeerStatsProtocolErrors      Counter32,
          dbpPerPeerStatsTransientFailures   Counter32,
          dbpPerPeerStatsPermanentFailures   Counter32,
          dbpPerPeerStatsTransportDown       Counter32 }

   dbpPerPeerStatsState OBJECT-TYPE
          SYNTAX     INTEGER { closed(1),
                               waitConnAck(2),
                               waitICea(3),
                               elect(4),
                               waitReturns(5),
                               rOpen(6),
                               iOpen(7),
                               closing(8) }
          MAX-ACCESS read-only
          STATUS     current
          DESCRIPTION
                "Connection state in the Peer State Machine of
                 the peer with which this Diameter server is
                 communicating.

                 closed      - Connection closed with this peer.
                 waitConnAck - Waiting for an acknowledgment
                               from this peer.
                 waitICea    - Waiting for a Capabilities-Exchange-
                               Answer from this peer.
                 elect       - When the peer and the server are both
                               trying to bring up a connection with
                               each other at the same time.  An
                               election process begins which
                               determines which socket remains open.
                 waitReturns - Waiting for election returns.
                 r-open      - Responder transport connection is
                               used for communication.
                 i-open      - Initiator transport connection is
                               used for communication.
                 closing     - Actively closing and doing cleanup."
          ::= { dbpPerPeerStatsEntry 1 }

   dbpPerPeerStatsStateDuration OBJECT-TYPE
          SYNTAX     TimeTicks
          MAX-ACCESS read-only
          STATUS     current
          DESCRIPTION
                "Peer state duration."
          ::= { dbpPerPeerStatsEntry 2 }

   dbpPerPeerStatsLastDiscCause OBJECT-TYPE
          SYNTAX     INTEGER { rebooting(1),
                               busy(2),
                               doNotWantToTalk(3),
                               election(4) }
          MAX-ACCESS read-only
          STATUS     current
          DESCRIPTION
                "The last cause for a peers disconnection.

                 rebooting       - A scheduled reboot is imminent.
                 busy            - The peer's internal resources are
                                   constrained, and it has determined
                                   that the transport connection needs
                                   to be shutdown.
                 doNotWantToTalk - The peer has determined that
                                   it does not see a need for the
                                   transport connection to exist,
                                   since it does not expect any
                                   messages to be exchanged in
                                   the foreseeable future.
                 electionLost    - The peer has determined that it
                                   has lost the election process
                                   and has therefore disconnected
                                   the transport connection."
          ::= { dbpPerPeerStatsEntry 3 }

   dbpPerPeerStatsWhoInitDisconnect OBJECT-TYPE
          SYNTAX     INTEGER { host(1),
                               peer(2) }
          MAX-ACCESS read-only
          STATUS     current
          DESCRIPTION
                "Did the host or peer initiate the disconnect?

                 host - If this server initiated the disconnect.
                 peer - If the peer with which this server was
                        connected initiated the disconnect."
          ::= { dbpPerPeerStatsEntry 4 }

   dbpPerPeerStatsDWCurrentStatus OBJECT-TYPE
          SYNTAX     INTEGER { okay(1),
                               suspect(2),
                               down(3),
                               reopen(4) }
          MAX-ACCESS read-only
          STATUS     current
          DESCRIPTION
                "okay    - Indicates the connection is presumed working.
                 suspect - Indicates the connection is possibly
                           congested or down.
                 down    - The peer is no longer reachable, causing
                           the transport connection to be shutdown.
                 reopen  - Three watchdog messages are exchanged with
                           accepted round trip times, and the connection
                           to the peer is considered stabilized."
          ::= { dbpPerPeerStatsEntry 5 }

   dbpPerPeerStatsTimeoutConnAtmpts OBJECT-TYPE
          SYNTAX     Counter32
          MAX-ACCESS read-only
          STATUS     current
          DESCRIPTION
                "If there is no transport connection with a peer,
                 this is the number of times the server attempts
                 to connect to that peer.  This is reset on
                 disconnection."
          ::= { dbpPerPeerStatsEntry 6 }

   dbpPerPeerStatsASRsIn OBJECT-TYPE
          SYNTAX     Counter32
          MAX-ACCESS read-only
          STATUS     current
          DESCRIPTION
                "Abort-Session-Request messages received
                 from the peer."
          ::= { dbpPerPeerStatsEntry 7 }

   dbpPerPeerStatsASRsOut OBJECT-TYPE
          SYNTAX     Counter32
          MAX-ACCESS read-only
          STATUS     current
          DESCRIPTION
                "Abort-Session-Request messages
                 sent to the peer."
          ::= { dbpPerPeerStatsEntry 8 }

   dbpPerPeerStatsASAsIn OBJECT-TYPE
          SYNTAX     Counter32
          MAX-ACCESS read-only
          STATUS     current
          DESCRIPTION
                "Number of Abort-Session-Answer
                 messages received from the peer."
          ::= { dbpPerPeerStatsEntry 9 }

   dbpPerPeerStatsASAsOut OBJECT-TYPE
          SYNTAX     Counter32
          MAX-ACCESS read-only
          STATUS     current
          DESCRIPTION
                "Number of Abort-Session-Answer
                 messages sent to the peer."
          ::= { dbpPerPeerStatsEntry 10 }

   dbpPerPeerStatsACRsIn OBJECT-TYPE
          SYNTAX     Counter32
          MAX-ACCESS read-only
          STATUS     current
          DESCRIPTION
                "Number of Accounting-Request messages
                 received from the peer."
          ::= { dbpPerPeerStatsEntry 11 }

   dbpPerPeerStatsACRsOut OBJECT-TYPE
          SYNTAX     Counter32
          MAX-ACCESS read-only
          STATUS     current
          DESCRIPTION
                "Number of Accounting-Request messages
                 sent to the peer."
          ::= { dbpPerPeerStatsEntry 12 }

   dbpPerPeerStatsACAsIn OBJECT-TYPE
          SYNTAX     Counter32
          MAX-ACCESS read-only
          STATUS     current
          DESCRIPTION
                "Number of Accounting-Answer messages
                 received from the peer."
          ::= { dbpPerPeerStatsEntry 13 }

   dbpPerPeerStatsACAsOut OBJECT-TYPE
          SYNTAX     Counter32
          MAX-ACCESS read-only
          STATUS     current
          DESCRIPTION
                "Number of Accounting-Answer messages
                 sent to the peer."
          ::= { dbpPerPeerStatsEntry 14 }

   dbpPerPeerStatsCERsIn OBJECT-TYPE
          SYNTAX     Counter32
          MAX-ACCESS read-only
          STATUS     current
          DESCRIPTION
                "Number of Capabilities-Exchange-Request
                 messages received from the peer."
          ::= { dbpPerPeerStatsEntry 15 }

   dbpPerPeerStatsCERsOut OBJECT-TYPE
          SYNTAX     Counter32
          MAX-ACCESS read-only
          STATUS     current
          DESCRIPTION
                "Number of Capabilities-Exchange-Request
                 messages sent to the peer."
          ::= { dbpPerPeerStatsEntry 16 }

   dbpPerPeerStatsCEAsIn OBJECT-TYPE
          SYNTAX     Counter32
          MAX-ACCESS read-only
          STATUS     current
          DESCRIPTION
                "Number of Capabilities-Exchange-Answer
                 messages received from the peer."
          ::= { dbpPerPeerStatsEntry 17 }

   dbpPerPeerStatsCEAsOut OBJECT-TYPE
          SYNTAX     Counter32
          MAX-ACCESS read-only
          STATUS     current
          DESCRIPTION
                "Number of Capabilities-Exchange-Answer
                 messages sent to the peer."
          ::= { dbpPerPeerStatsEntry 18 }

   dbpPerPeerStatsDWRsIn OBJECT-TYPE
          SYNTAX     Counter32
          MAX-ACCESS read-only
          STATUS     current
          DESCRIPTION
                "Number of Device-Watchdog-Request
                 messages received from the peer."
          ::= { dbpPerPeerStatsEntry 19 }

   dbpPerPeerStatsDWRsOut OBJECT-TYPE
          SYNTAX     Counter32
          MAX-ACCESS read-only
          STATUS     current
          DESCRIPTION
                "Number of Device-Watchdog-Request
                 messages sent to the peer."
          ::= { dbpPerPeerStatsEntry 20 }

   dbpPerPeerStatsDWAsIn OBJECT-TYPE
          SYNTAX     Counter32
          MAX-ACCESS read-only
          STATUS     current
          DESCRIPTION
                "Number of Device-Watchdog-Answer
                 messages received from the peer."
          ::= { dbpPerPeerStatsEntry 21 }

   dbpPerPeerStatsDWAsOut OBJECT-TYPE
          SYNTAX     Counter32
          MAX-ACCESS read-only
          STATUS     current
          DESCRIPTION
                "Number of Device-Watchdog-Answer
                 messages sent to the peer."
          ::= { dbpPerPeerStatsEntry 22 }

   dbpPerPeerStatsDPRsIn OBJECT-TYPE
          SYNTAX     Counter32
          MAX-ACCESS read-only
          STATUS     current
          DESCRIPTION
                "Number of Disconnect-Peer-Request messages
                 received."
          ::= { dbpPerPeerStatsEntry 23 }

   dbpPerPeerStatsDPRsOut OBJECT-TYPE
          SYNTAX     Counter32
          MAX-ACCESS read-only
          STATUS     current
          DESCRIPTION
                "Number of Disconnect-Peer-Request messages
                 sent."
          ::= { dbpPerPeerStatsEntry 24 }

   dbpPerPeerStatsDPAsIn OBJECT-TYPE
          SYNTAX     Counter32
          MAX-ACCESS read-only
          STATUS     current
          DESCRIPTION
                "Number of Disconnect-Peer-Answer messages
                 received."
          ::= { dbpPerPeerStatsEntry 25 }

   dbpPerPeerStatsDPAsOut OBJECT-TYPE
          SYNTAX     Counter32
          MAX-ACCESS read-only
          STATUS     current
          DESCRIPTION
                "Number of Disconnect-Peer-Answer messages
                 sent."
          ::= { dbpPerPeerStatsEntry 26 }

   dbpPerPeerStatsRARsIn  OBJECT-TYPE
          SYNTAX     Counter32
          MAX-ACCESS read-only
          STATUS     current
          DESCRIPTION
                "Number of Re-Auth-Request messages
                 received."
          ::= { dbpPerPeerStatsEntry 27 }

   dbpPerPeerStatsRARsOut OBJECT-TYPE
          SYNTAX     Counter32
          MAX-ACCESS read-only
          STATUS     current
          DESCRIPTION
                "Number of Re-Auth-Request messages
                 sent."
          ::= { dbpPerPeerStatsEntry 28 }

   dbpPerPeerStatsRAAsIn OBJECT-TYPE
          SYNTAX     Counter32
          MAX-ACCESS read-only
          STATUS     current
          DESCRIPTION
                "Number of Re-Auth-Answer messages
                 received."
          ::= { dbpPerPeerStatsEntry 29 }

   dbpPerPeerStatsRAAsOut OBJECT-TYPE
          SYNTAX     Counter32
          MAX-ACCESS read-only
          STATUS     current
          DESCRIPTION
                "Number of Re-Auth-Answer messages
                 sent."
          ::= { dbpPerPeerStatsEntry 30 }

   dbpPerPeerStatsSTRsIn OBJECT-TYPE
          SYNTAX     Counter32
          MAX-ACCESS read-only
          STATUS     current
          DESCRIPTION
                "Number of Session-Termination-Request
                 messages received from the peer."
          ::= { dbpPerPeerStatsEntry 31 }

   dbpPerPeerStatsSTRsOut OBJECT-TYPE
          SYNTAX     Counter32
          MAX-ACCESS read-only
          STATUS     current
          DESCRIPTION
                "Number of Session-Termination-Request
                 messages sent to the peer."
          ::= { dbpPerPeerStatsEntry 32 }

   dbpPerPeerStatsSTAsIn OBJECT-TYPE
          SYNTAX     Counter32
          MAX-ACCESS read-only
          STATUS     current
          DESCRIPTION
                "Number of Session-Termination-Answer
                 messages received from the peer."
          ::= { dbpPerPeerStatsEntry 33 }

   dbpPerPeerStatsSTAsOut OBJECT-TYPE
          SYNTAX     Counter32
          MAX-ACCESS read-only
          STATUS     current
          DESCRIPTION
                "Number of Session-Termination-Answer
                 messages sent to the peer."
          ::= { dbpPerPeerStatsEntry 34 }

   dbpPerPeerStatsDWReqTimer OBJECT-TYPE
          SYNTAX     TimeTicks
          MAX-ACCESS read-only
          STATUS     current
          DESCRIPTION
                "Device-Watchdog Request Timer, which
                 is the interval between packets sent to
                 peers."
          ::= { dbpPerPeerStatsEntry 35 }

   dbpPerPeerStatsRedirectEvents OBJECT-TYPE
          SYNTAX     Counter32
          MAX-ACCESS read-only
          STATUS     current
          DESCRIPTION
                "Redirect Event count, which is the number
                 of redirects sent from a peer."
          ::= { dbpPerPeerStatsEntry 36 }

   dbpPerPeerStatsAccDupRequests OBJECT-TYPE
          SYNTAX     Counter32
          MAX-ACCESS read-only
          STATUS     current
          DESCRIPTION
                "The number of duplicate Diameter Accounting-Request
                 packets received."
          ::= { dbpPerPeerStatsEntry 37 }

   dbpPerPeerStatsMalformedReqsts OBJECT-TYPE
          SYNTAX     Counter32
          MAX-ACCESS read-only
          STATUS     current
          DESCRIPTION
                "The number of malformed Diameter
                 packets received."
          ::= { dbpPerPeerStatsEntry 38 }

   dbpPerPeerStatsAccsNotRecorded OBJECT-TYPE
          SYNTAX     Counter32
          MAX-ACCESS read-only
          STATUS     current
          DESCRIPTION
                "The number of Diameter Accounting-Request packets
                 which were received and responded to but not
                 recorded."
          ::= { dbpPerPeerStatsEntry 39 }

   dbpPerPeerStatsAccRetrans OBJECT-TYPE
          SYNTAX     Counter32
          MAX-ACCESS read-only
          STATUS     current
          DESCRIPTION
                "The number of Diameter Accounting-Request packets
                 retransmitted to this Diameter server."
          ::= { dbpPerPeerStatsEntry 40 }

   dbpPerPeerStatsTotalRetrans OBJECT-TYPE
          SYNTAX     Counter32
          MAX-ACCESS read-only
          STATUS     current
          DESCRIPTION
                "The number of Diameter packets retransmitted
                 to this Diameter server, not to include Diameter
                 Accounting-Request packets retransmitted."
          ::= { dbpPerPeerStatsEntry 41 }

   dbpPerPeerStatsAccPendReqstsOut OBJECT-TYPE
          SYNTAX     Gauge32
          MAX-ACCESS read-only
          STATUS     current
          DESCRIPTION
             "The number of Diameter Accounting-Request packets
              sent to this peer that have not yet timed out or
              received a response. This variable is incremented when an
              Accounting-Request is sent to this server and decremented
              due to receipt of an Accounting-Response, a timeout or
              a retransmission."
          ::= { dbpPerPeerStatsEntry 42 }

   dbpPerPeerStatsAccReqstsDropped OBJECT-TYPE
          SYNTAX     Counter32
          MAX-ACCESS read-only
          STATUS     current
          DESCRIPTION
             "The number of Accounting-Requests to this server
              that have been dropped."
          ::= { dbpPerPeerStatsEntry 43 }

   dbpPerPeerStatsHByHDropMessages OBJECT-TYPE
          SYNTAX     Counter32
          MAX-ACCESS read-only
          STATUS     current
          DESCRIPTION
                "An answer message that is received with an unknown
                 Hop-by-Hop Identifier.  Does not include Accounting
                 Requests dropped."
          ::= { dbpPerPeerStatsEntry 44 }

   dbpPerPeerStatsEToEDupMessages OBJECT-TYPE
          SYNTAX     Counter32
          MAX-ACCESS read-only
          STATUS     current
          DESCRIPTION
                "Duplicate answer messages that are to be locally
                 consumed.  Does not include duplicate Accounting
                 Requests received."
          ::= { dbpPerPeerStatsEntry 45 }

   dbpPerPeerStatsUnknownTypes OBJECT-TYPE
          SYNTAX     Counter32
          MAX-ACCESS read-only
          STATUS     current
          DESCRIPTION
                "The number of Diameter packets of unknown type
                 which were received."
          ::= { dbpPerPeerStatsEntry 46 }

   dbpPerPeerStatsProtocolErrors OBJECT-TYPE
          SYNTAX     Counter32
          MAX-ACCESS read-only
          STATUS     current
          DESCRIPTION
                "Number of protocol errors returned to peer,
                 but not including redirects."
          ::= { dbpPerPeerStatsEntry 47 }

   dbpPerPeerStatsTransientFailures OBJECT-TYPE
          SYNTAX     Counter32
          MAX-ACCESS read-only
          STATUS     current
          DESCRIPTION
                "Transient Failure count."
          ::= { dbpPerPeerStatsEntry 48 }

   dbpPerPeerStatsPermanentFailures OBJECT-TYPE
          SYNTAX     Counter32
          MAX-ACCESS read-only
          STATUS     current
          DESCRIPTION
                "Number of permanent failures returned to peer."
          ::= { dbpPerPeerStatsEntry 49 }

   dbpPerPeerStatsTransportDown OBJECT-TYPE
          SYNTAX     Counter32
          MAX-ACCESS read-only
          STATUS     current
          DESCRIPTION
                "Number of unexpected transport failures."
          ::= { dbpPerPeerStatsEntry 50 }

   dbpRealmMessageRouteTable OBJECT-TYPE
          SYNTAX     SEQUENCE OF DbpRealmMessageRouteEntry
          MAX-ACCESS not-accessible
          STATUS     current
          DESCRIPTION
                "The table listing the Diameter
                 Realm-based Message Route information."
          ::= { dbpRealmStats 1 }

   dbpRealmMessageRouteEntry OBJECT-TYPE
          SYNTAX     DbpRealmMessageRouteEntry
          MAX-ACCESS not-accessible
          STATUS     current
          DESCRIPTION
                "A row entry representing a Diameter
                 Realm Based Message Route server."
          INDEX      { dbpRealmMessageRouteIndex }
          ::= { dbpRealmMessageRouteTable 1 }

   DbpRealmMessageRouteEntry ::= SEQUENCE {
          dbpRealmMessageRouteIndex              Unsigned32,
          dbpRealmMessageRouteRealm         SnmpAdminString,
          dbpRealmMessageRouteApp                Unsigned32,
          dbpRealmMessageRouteType                  INTEGER,
          dbpRealmMessageRouteAction                INTEGER,
          dbpRealmMessageRouteACRsIn              Counter32,
          dbpRealmMessageRouteACRsOut             Counter32,
          dbpRealmMessageRouteACAsIn              Counter32,
          dbpRealmMessageRouteACAsOut             Counter32,
          dbpRealmMessageRouteRARsIn              Counter32,
          dbpRealmMessageRouteRARsOut             Counter32,
          dbpRealmMessageRouteRAAsIn              Counter32,
          dbpRealmMessageRouteRAAsOut             Counter32,
          dbpRealmMessageRouteSTRsIn              Counter32,
          dbpRealmMessageRouteSTRsOut             Counter32,
          dbpRealmMessageRouteSTAsIn              Counter32,
          dbpRealmMessageRouteSTAsOut             Counter32,
          dbpRealmMessageRouteASRsIn              Counter32,
          dbpRealmMessageRouteASRsOut             Counter32,
          dbpRealmMessageRouteASAsIn              Counter32,
          dbpRealmMessageRouteASAsOut             Counter32,
          dbpRealmMessageRouteAccRetrans          Counter32,
          dbpRealmMessageRouteAccDupReqsts        Counter32,
          dbpRealmMessageRoutePendReqstsOut         Gauge32,
          dbpRealmMessageRouteReqstsDrop          Counter32 }

   dbpRealmMessageRouteIndex OBJECT-TYPE
          SYNTAX     Unsigned32 (1..4294967295)
          MAX-ACCESS not-accessible
          STATUS     current
          DESCRIPTION
                "A number uniquely identifying each Realm."
          ::= { dbpRealmMessageRouteEntry 1 }

   dbpRealmMessageRouteRealm OBJECT-TYPE
          SYNTAX     SnmpAdminString
          MAX-ACCESS read-only
          STATUS     current
          DESCRIPTION
                "Realm name"
          ::= { dbpRealmMessageRouteEntry 2 }

   dbpRealmMessageRouteApp OBJECT-TYPE
          SYNTAX     Unsigned32 (1..4294967295)
          MAX-ACCESS read-only
          STATUS     current
          DESCRIPTION
                "Application id used to route packets
                 to this realm."
          ::= { dbpRealmMessageRouteEntry 3 }

   dbpRealmMessageRouteType OBJECT-TYPE
          SYNTAX     INTEGER { acct(1),
                               auth(2),
                               both(3) }
          MAX-ACCESS read-only
          STATUS     current
          DESCRIPTION
                "The types of service supported for each
                 realm application: accounting,
                 authentication or both."
          ::= { dbpRealmMessageRouteEntry 4 }

   dbpRealmMessageRouteAction OBJECT-TYPE
          SYNTAX     INTEGER { local(1),
                               relay(2),
                               proxy(3),
                               redirect(4) }
          MAX-ACCESS read-only
          STATUS     current
          DESCRIPTION
                "The action is used to identify how a
                 message should be treated based on the realm,
                 application and type.
                 local    - Diameter messages that resolve to a
                            route entry with the Local Action set to
                            Local can be satisfied locally, and do
                            not need to be routed to another server.
                 relay    - All Diameter messages that fall within
                            this category MUST be routed to a
                            next-hop server, without modifying any
                            non-routing AVPs.
                 proxy    - All Diameter messages that fall within this
                            category MUST be routed to a next-hop
                            server.
                 redirect - Diameter messages that fall within this
                            category MUST have the identity of the home
                            Diameter server(s) appended, and returned
                            to the sender of the message."
          ::= { dbpRealmMessageRouteEntry 5 }

   dbpRealmMessageRouteACRsIn OBJECT-TYPE
          SYNTAX     Counter32
          MAX-ACCESS read-only
          STATUS     current
          DESCRIPTION
                "Number of Accounting-Request messages
                 received from the realm."
          ::= { dbpRealmMessageRouteEntry 6 }

   dbpRealmMessageRouteACRsOut OBJECT-TYPE
          SYNTAX     Counter32
          MAX-ACCESS read-only
          STATUS     current
          DESCRIPTION
                "Number of Accounting-Request messages
                 sent to the realm."
          ::= { dbpRealmMessageRouteEntry 7 }

   dbpRealmMessageRouteACAsIn OBJECT-TYPE
          SYNTAX     Counter32
          MAX-ACCESS read-only
          STATUS     current
          DESCRIPTION
                "Number of Accounting-Answer messages
                 received from the realm."
          ::= { dbpRealmMessageRouteEntry 8 }

   dbpRealmMessageRouteACAsOut OBJECT-TYPE
          SYNTAX     Counter32
          MAX-ACCESS read-only
          STATUS     current
          DESCRIPTION
                "Number of Accounting-Answer messages
                 sent to the realm."
          ::= { dbpRealmMessageRouteEntry 9 }

   dbpRealmMessageRouteRARsIn OBJECT-TYPE
          SYNTAX     Counter32
          MAX-ACCESS read-only
          STATUS     current
          DESCRIPTION
                "Number of Re-Auth-Request messages
                 received from the realm."
          ::= { dbpRealmMessageRouteEntry 10 }

   dbpRealmMessageRouteRARsOut OBJECT-TYPE
          SYNTAX     Counter32
          MAX-ACCESS read-only
          STATUS     current
          DESCRIPTION
                "Number of Re-Auth-Request messages
                 sent to the realm."
          ::= { dbpRealmMessageRouteEntry 11 }

   dbpRealmMessageRouteRAAsIn OBJECT-TYPE
          SYNTAX     Counter32
          MAX-ACCESS read-only
          STATUS     current
          DESCRIPTION
                "Number of Re-Auth-Answer messages
                 received from the realm."
          ::= { dbpRealmMessageRouteEntry 12 }

   dbpRealmMessageRouteRAAsOut OBJECT-TYPE
          SYNTAX     Counter32
          MAX-ACCESS read-only
          STATUS     current
          DESCRIPTION
                "Number of Re-Auth-Answer messages
                 sent to the realm."
          ::= { dbpRealmMessageRouteEntry 13 }

   dbpRealmMessageRouteSTRsIn OBJECT-TYPE
          SYNTAX     Counter32
          MAX-ACCESS read-only
          STATUS     current
          DESCRIPTION
                "Number of Session-Termination-Request messages
                 received from the realm."
          ::= { dbpRealmMessageRouteEntry 14 }

   dbpRealmMessageRouteSTRsOut OBJECT-TYPE
          SYNTAX     Counter32
          MAX-ACCESS read-only
          STATUS     current
          DESCRIPTION
                "Number of Session-Termination-Request messages
                 sent to the realm."
          ::= { dbpRealmMessageRouteEntry 15 }

   dbpRealmMessageRouteSTAsIn OBJECT-TYPE
          SYNTAX     Counter32
          MAX-ACCESS read-only
          STATUS     current
          DESCRIPTION
                "Number of Session-Termination-Answer messages
                 received from the realm."
          ::= { dbpRealmMessageRouteEntry 16 }

   dbpRealmMessageRouteSTAsOut OBJECT-TYPE
          SYNTAX     Counter32
          MAX-ACCESS read-only
          STATUS     current
          DESCRIPTION
                "Number of Session-Termination-Answer messages
                 sent to the realm."
          ::= { dbpRealmMessageRouteEntry 17 }

   dbpRealmMessageRouteASRsIn OBJECT-TYPE
          SYNTAX     Counter32
          MAX-ACCESS read-only
          STATUS     current
          DESCRIPTION
                "Number of Abort-Session-Request messages
                 received from the realm."
          ::= { dbpRealmMessageRouteEntry 18 }

   dbpRealmMessageRouteASRsOut OBJECT-TYPE
          SYNTAX     Counter32
          MAX-ACCESS read-only
          STATUS     current
          DESCRIPTION
                "Number of Abort-Session-Request messages
                 sent to the realm."
          ::= { dbpRealmMessageRouteEntry 19 }

   dbpRealmMessageRouteASAsIn OBJECT-TYPE
          SYNTAX     Counter32
          MAX-ACCESS read-only
          STATUS     current
          DESCRIPTION
                "Number of Abort-Session-Answer messages
                 received from the realm."
          ::= { dbpRealmMessageRouteEntry 20 }

   dbpRealmMessageRouteASAsOut OBJECT-TYPE
          SYNTAX     Counter32
          MAX-ACCESS read-only
          STATUS     current
          DESCRIPTION
                "Number of Abort-Session-Answer messages
                 sent to the realm."
          ::= { dbpRealmMessageRouteEntry 21 }

   dbpRealmMessageRouteAccRetrans OBJECT-TYPE
          SYNTAX     Counter32
          MAX-ACCESS read-only
          STATUS     current
          DESCRIPTION
                "The number of Diameter accounting packets
                 retransmitted to this realm."
          ::= { dbpRealmMessageRouteEntry 22 }

   dbpRealmMessageRouteAccDupReqsts OBJECT-TYPE
          SYNTAX     Counter32
          MAX-ACCESS read-only
          STATUS     current
          DESCRIPTION
                "The number of duplicate Diameter accounting
                 packets sent to this realm."
          ::= { dbpRealmMessageRouteEntry 23 }

   dbpRealmMessageRoutePendReqstsOut OBJECT-TYPE
          SYNTAX     Gauge32
          MAX-ACCESS read-only
          STATUS     current
          DESCRIPTION
             "The number of Diameter Accounting-Request packets
              sent to this peer that have not yet timed out or
              received a response. This variable is incremented when an
              Accounting-Request is sent to this server and decremented
              due to receipt of an Accounting-Response, a timeout or
              a retransmission."
          ::= { dbpRealmMessageRouteEntry 24 }

   dbpRealmMessageRouteReqstsDrop OBJECT-TYPE
          SYNTAX     Counter32
          MAX-ACCESS read-only
          STATUS     current
          DESCRIPTION
                "The number of requsts dropped by this realm."
          ::= { dbpRealmMessageRouteEntry 25 }

   dbpRealmKnownPeersTable OBJECT-TYPE
          SYNTAX     SEQUENCE OF DbpRealmKnownPeersEntry
          MAX-ACCESS not-accessible
          STATUS     current
          DESCRIPTION
                "The table listing the Diameter
                 Realms and known peers."
          ::= { dbpRealmCfgs 1 }

   dbpRealmKnownPeersEntry OBJECT-TYPE
          SYNTAX     DbpRealmKnownPeersEntry
          MAX-ACCESS not-accessible
          STATUS     current
          DESCRIPTION
                "A row entry representing a Diameter
                 Realm and known peers."
          INDEX      { dbpRealmMessageRouteIndex,
                       dbpRealmKnownPeersIndex }
          ::= { dbpRealmKnownPeersTable 1 }

   DbpRealmKnownPeersEntry ::= SEQUENCE {
          dbpRealmKnownPeersIndex                Unsigned32,
          dbpRealmKnownPeers                     Unsigned32,
          dbpRealmKnownPeersChosen                  INTEGER }

   dbpRealmKnownPeersIndex OBJECT-TYPE
          SYNTAX     Unsigned32 (1..4294967295)
          MAX-ACCESS not-accessible
          STATUS     current
          DESCRIPTION
                "A sequential identifier number."
          ::= { dbpRealmKnownPeersEntry 1 }

   dbpRealmKnownPeers OBJECT-TYPE
          SYNTAX     Unsigned32 (1..4294967295)
          MAX-ACCESS read-only
          STATUS     current
          DESCRIPTION
                "The index of the peer this realm knows about.
                 This is an ordered list, where the ordering
                 signifies the order in which the peers are
                 tried.  Same as the dbpPeerIndex"
          ::= { dbpRealmKnownPeersEntry 2 }

   dbpRealmKnownPeersChosen OBJECT-TYPE
          SYNTAX     INTEGER { roundRobin(1),
                               loadBalance(2),
                               firstPreferred(3),
                               mostRecentFirst(4),
                               other(5) }
          MAX-ACCESS read-only
          STATUS     current
          DESCRIPTION
                "How the realm chooses which peer to send
                 packets to.
                 roundRobin      - The peer used for each transaction
                                   is selected based on the order in
                                   which peers are configured.
                 loadBalance     - The peer used for each transaction
                                   is based on the load metric (maybe
                                   implementation dependent) of all
                                   peers defined for the realm, with
                                   the least loaded server selected
                                   first.
                 firstPreferred  - The first defined server is always
                                   used for transactions unless
                                   failover occurs.
                 mostRecentFirst - The most recently used server is
                                   used first for each transaction."
          ::= { dbpRealmKnownPeersEntry 3 }

   -- -- Conformance -- dbpMIBCompliances

   diameterBaseProtocolMIBCompliances
                       OBJECT IDENTIFIER ::= { diameterBaseConform 1 }

   diameterBaseProtocolMIBGroups
                       OBJECT IDENTIFIER ::= { diameterBaseConform 2 }

   -- -- Compliance Statements --

   diameterBaseProtocolCompliance MODULE-COMPLIANCE
          STATUS     current
          DESCRIPTION
               "The compliance statement for Diameter Base
                Protocol entities."
          MODULE -- this module
               MANDATORY-GROUPS { dbpLocalCfgGroup,
                                  dbpPeerCfgGroup,
                                  dbpPeerStatsGroup,
                                  dbpNotificationsGroup,
                                  dbpNotifCfgGroup }

               GROUP              dbpLocalCfgSkippedGroup
               DESCRIPTION
                  "This group is only mandatory for a system that
                   implements all the local config objects."

               GROUP              dbpLocalStatsSkippedGroup
               DESCRIPTION
                  "This group is only mandatory for a system that
                   implements all the local statistics objects."

               GROUP              dbpPeerCfgSkippedGroup
               DESCRIPTION
                  "This group is only mandatory for a system that
                   implements all the peer config objects."

               GROUP              dbpPeerStatsSkippedGroup
               DESCRIPTION
                  "This group is only mandatory for a system that
                   implements all the peer statistic objects."

               GROUP              dbpRealmCfgSkippedGroup
               DESCRIPTION
                  "This group is only mandatory for a system that
                   implementsall the realm config objects."

               GROUP              dbpPMIBRealmStatsSkippedGroup
               DESCRIPTION
                  "This group is only mandatory for a system that
                   implements all the realm statistic objects."

          ::= { diameterBaseProtocolCompliances 1 }

   -- -- Units of Conformance --

   dbpLocalCfgGroup OBJECT-GROUP
         OBJECTS {
                 dbpLocalRealm,
                 dbpLocalOriginHost,
                 dbpLocalVendorId,
                 dbpLocalVendorStorageType,
                 dbpLocalVendorRowStatus
         }
         STATUS  current
         DESCRIPTION
               "A collection of objects providing configuration common
                to the server."
         ::= { diameterBaseProtocolMIBGroups 1 }

   dbpPeerCfgGroup OBJECT-GROUP
       OBJECTS   {
                 dbpPeerId,
                 dbpPeerPortConnect,
                 dbpPeerPortListen,
                 dbpPeerProtocol,
                 dbpPeerSecurity,
                 dbpPeerFirmwareRevision,
                 dbpPeerStorageType,
                 dbpPeerRowStatus,
                 dbpPeerIpAddressType,
                 dbpPeerIpAddress,
                 dbpPeerVendorId,
                 dbpPeerVendorStorageType,
                 dbpPeerVendorRowStatus
       }
       STATUS          current
       DESCRIPTION
               "A collection of objects providing configuration
               of the Diameter peers."
       ::= { diameterBaseProtocolMIBGroups 2 }

   dbpPeerStatsGroup OBJECT-GROUP
       OBJECTS   {
                 dbpPeerStatsState,
                 dbpPeerStatsStateDuration,
                 dbpPeerStatsLastDiscCause,
                 dbpPeerStatsWhoInitDisconnect,
                 dbpPeerStatsDWCurrentStatus,
                 dbpPeerStatsTimeoutConnAtmpts,
                 dbpPeerStatsASRsIn,
                 dbpPeerStatsASRsOut,
                 dbpPeerStatsASAsIn,
                 dbpPeerStatsASAsOut,
                 dbpPeerStatsACRsIn,
                 dbpPeerStatsACRsOut,
                 dbpPeerStatsACAsIn,
                 dbpPeerStatsACAsOut,
                 dbpPeerStatsCERsIn,
                 dbpPeerStatsCERsOut,
                 dbpPeerStatsCEAsIn,
                 dbpPeerStatsCEAsOut,
                 dbpPeerStatsDWRsIn,
                 dbpPeerStatsDWRsOut,
                 dbpPeerStatsDWAsIn,
                 dbpPeerStatsDWAsOut,
                 dbpPeerStatsDPRsIn,
                 dbpPeerStatsDPRsOut,
                 dbpPeerStatsDPAsIn,
                 dbpPeerStatsDPAsOut,
                 dbpPeerStatsRARsIn,
                 dbpPeerStatsRARsOut,
                 dbpPeerStatsRAAsIn,
                 dbpPeerStatsRAAsOut,
                 dbpPeerStatsSTRsIn,
                 dbpPeerStatsSTRsOut,
                 dbpPeerStatsSTAsIn,
                 dbpPeerStatsSTAsOut,
                 dbpPeerStatsDWReqTimer,
                 dbpPeerStatsRedirectEvents,
                 dbpPeerStatsAccDupRequests,
                 dbpPeerStatsMalformedReqsts,
                 dbpPeerStatsAccsNotRecorded,
                 dbpPeerStatsAccRetrans,
                 dbpPeerStatsTotalRetrans,
                 dbpPeerStatsAccPendReqstsOut,
                 dbpPeerStatsAccReqstsDropped,
                 dbpPeerStatsHByHDropMessages,
                 dbpPeerStatsEToEDupMessages,
                 dbpPeerStatsUnknownTypes,
                 dbpPeerStatsProtocolErrors,
                 dbpPeerStatsTransientFailures,
                 dbpPeerStatsPermanentFailures,
                 dbpPeerStatsTransportDown
       }
       STATUS          current
       DESCRIPTION
               "A collection of objects providing statistics
                of the Diameter peers."
       ::= { diameterBaseProtocolMIBGroups 3 }

   dbpNotificationsGroup NOTIFICATION-GROUP
      NOTIFICATIONS    {
                       dbpProtocolErrorNotif,
                       dbpTransientFailureNotif,
                       dbpPermanentFailureNotif,
                       dbpPeerConnectionDownNotif,
                       dbpPeerConnectionUpNotif
                       }
       STATUS          current
       DESCRIPTION
               "The set of notifications which an agent is required
                to implement."
       ::= { diameterBaseProtocolMIBGroups 4 }

   dbpNotifCfgGroup OBJECT-GROUP
       OBJECTS         {
                       dbpProtocolErrorNotifEnabled,
                       dbpTransientFailureNotifEnabled,
                       dbpPermanentFailureNotifEnabled,
                       dbpPeerConnectionDownNotifEnabled,
                       dbpPeerConnectionUpNotifEnabled
                       }
       STATUS          current
       DESCRIPTION
               "A collection of objects providing configuration for
               base protocol notifications."
       ::= { diameterBaseProtocolMIBGroups 5 }

   dbpLocalCfgSkippedGroup OBJECT-GROUP
       OBJECTS         {
                       dbpLocalId,
                       dbpLocalIpAddrType,
                       dbpLocalIpAddress,
                       dbpLocalTcpListenPort,
                       dbpLocalSctpListenPort,
                       dbpLocalStatsTotalPacketsIn,
                       dbpLocalStatsTotalPacketsOut,
                       dbpLocalStatsTotalUpTime,
                       dbpLocalResetTime,
                       dbpLocalConfigReset,
                       dbpLocalApplStorageType,
                       dbpLocalApplRowStatus,
                       dbpAppAdvToPeerServices,
                       dbpAppAdvToPeerStorageType,
                       dbpAppAdvToPeerRowStatus
                       }
       STATUS          current
       DESCRIPTION
               "A collection of objects providing configuration common
               to the server."
       ::= { diameterBaseProtocolMIBGroups 6 }

   dbpLocalStatsSkippedGroup OBJECT-GROUP
       OBJECTS         {
                       dbpLocalStatsTotalPacketsIn,
                       dbpLocalStatsTotalPacketsOut,
                       dbpLocalStatsTotalUpTime,
                       dbpLocalResetTime,
                       dbpLocalConfigReset
                       }
       STATUS          current
       DESCRIPTION
               "A collection of objects providing statistics common
               to the server."
       ::= { diameterBaseProtocolMIBGroups 7 }

   dbpPeerCfgSkippedGroup OBJECT-GROUP
       OBJECTS         { cdbpAppAdvFromPeerType }
       STATUS          current
       DESCRIPTION
               "A collection of objects providing configuration for
               Diameter peers."
       ::= { diameterBaseProtocolMIBGroups 8 }

   dbpPeerStatsSkippedGroup OBJECT-GROUP
       OBJECTS         {
                       dbpPeerStatsDWCurrentStatus,
                       dbpPeerStatsDWReqTimer,
                       dbpPeerStatsRedirectEvents,
                       dbpPeerStatsAccDupRequests,
                       dbpPeerStatsEToEDupMessages
                       }
       STATUS          current
       DESCRIPTION
               "A collection of objects providing statistics
               of Diameter peers."
       ::= { diameterBaseProtocolMIBGroups 9 }

   dbpRealmCfgSkippedGroup OBJECT-GROUP
       OBJECTS         {
                       dbpRealmKnownPeers,
                       dbpRealmKnownPeersChosen
                       }
       STATUS          current
       DESCRIPTION
               "A collection of objects providing configuration for
               realm message routing."
       ::= { diameterBaseProtocolMIBGroups 10 }

   dbpRealmStatsSkippedGroup OBJECT-GROUP
       OBJECTS         {
                       dbpRealmMessageRouteRealm,
                       dbpRealmMessageRouteApp,
                       dbpRealmMessageRouteType,
                       dbpRealmMessageRouteAction,
                       dbpRealmMessageRouteACRsIn,
                       dbpRealmMessageRouteACRsOut,
                       dbpRealmMessageRouteACAsIn,
                       dbpRealmMessageRouteACAsOut,
                       dbpRealmMessageRouteRARsIn,
                       dbpRealmMessageRouteRARsOut,
                       dbpRealmMessageRouteRAAsIn,
                       dbpRealmMessageRouteRAAsOut,
                       dbpRealmMessageRouteSTRsIn,
                       dbpRealmMessageRouteSTRsOut,
                       dbpRealmMessageRouteSTAsIn,
                       dbpRealmMessageRouteSTAsOut,
                       dbpRealmMessageRouteASRsIn,
                       dbpRealmMessageRouteASRsOut,
                       dbpRealmMessageRouteASAsIn,
                       dbpRealmMessageRouteASAsOut,
                       dbpRealmMessageRouteAccRetrans,
                       dbpRealmMessageRouteAccDupReqsts,
                       dbpRealmMessageRoutePendReqstsOut,
                       dbpRealmMessageRouteReqstsDrop
                       }
       STATUS          current
       DESCRIPTION
               "A collection of objects providing statistics
               of realm message routing."
       ::= { diameterBaseProtocolMIBGroups 11 }

   END

-- 
--    Copyright (C) The IETF Trust (2007).
-- 
--    This document is subject to the rights, licenses and restrictions
--    contained in BCP 78, and except as set forth therein, the authors
--    retain all their rights.
-- 
--    This document and the information contained herein are provided on an
--    "AS IS" basis and THE CONTRIBUTOR, THE ORGANIZATION HE/SHE REPRESENTS
--    OR IS SPONSORED BY (IF ANY), THE INTERNET SOCIETY, THE IETF TRUST AND
--    THE INTERNET ENGINEERING TASK FORCE DISCLAIM ALL WARRANTIES, EXPRESS
--    OR IMPLIED, INCLUDING BUT NOT LIMITED TO ANY WARRANTY THAT THE USE OF
--    THE INFORMATION HEREIN WILL NOT INFRINGE ANY RIGHTS OR ANY IMPLIED
--    WARRANTIES OF MERCHANTABILITY OR FITNESS FOR A PARTICULAR PURPOSE.
-- 
-- 
-- Intellectual Property
-- 
--    The IETF takes no position regarding the validity or scope of any
--    Intellectual Property Rights or other rights that might be claimed to
--    pertain to the implementation or use of the technology described in
--    this document or the extent to which any license under such rights
--    might or might not be available; nor does it represent that it has
--    made any independent effort to identify any such rights.  Information
--    on the procedures with respect to rights in RFC documents can be
--    found in BCP 78 and BCP 79.
-- 
--    Copies of IPR disclosures made to the IETF Secretariat and any
--    assurances of licenses to be made available, or the result of an
--    attempt made to obtain a general license or permission for the use of
--    such proprietary rights by implementers or users of this
--    specification can be obtained from the IETF on-line IPR repository at
--    http://www.ietf.org/ipr.
-- 
--    The IETF invites any interested party to bring to its attention any
--    copyrights, patents or patent applications, or other proprietary
--    rights that may cover technology that may be required to implement
--    this standard.  Please address the information to the IETF at
--    ietf-ipr@ietf.org.
-- 
-- 
-- Acknowledgment
-- 
--    Funding for the RFC Editor function is provided by the IETF
--    Administrative Support Activity (IASA).
