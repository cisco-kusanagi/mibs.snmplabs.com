-- $Id: advanced.mib,v 29.6 1999/03/16 18:45:21 mkrasnic Exp $

--
-- Aug 29, 1997 rm   Initial creation (moved from wan.mib)
--                   This MIB is protected by hash-code bit "AdvancedAgent".
-- 02 Oct 97:   kn   EOI-12553: Back out the above change and rename wanInfo
--                   to advancedAgent
-- 12 Feb 98:   kn   EOI 17530 Added more variables to wanLineTable
--
-- 30 Sep 98	mb   EOI 250156 Added dtpt and net2net variables to
--		     wanLineTable and added wanLineChannelUsageTable.
-- 15 Mar 99	mk   Added a note to the DESCRIPTION of wanLineChannelTrunkGroup.

ASCEND-ADVANCED-AGENT-MIB DEFINITIONS ::= BEGIN

       IMPORTS
                advancedAgent
                        FROM ASCEND-MIB
                DisplayString
                        FROM ASCEND-MIB
                OBJECT-TYPE
                        FROM RFC-1212;

    wanUseTrunkGroups OBJECT-TYPE
        SYNTAX  INTEGER {
            do-not-use(1),
            use(2)
        }
        ACCESS  read-only
        STATUS  mandatory
        DESCRIPTION
           "System wide parameter dictating the use of trunk groups."
       ::= { advancedAgent 20 }

    wanLineTable OBJECT-TYPE
        SYNTAX  SEQUENCE OF WanLineEntry
        ACCESS  not-accessible
        STATUS  mandatory
        DESCRIPTION
           "The wan line table."
       ::= { advancedAgent 21 }

    wanLineEntry OBJECT-TYPE
        SYNTAX  WanLineEntry
        ACCESS  not-accessible
        STATUS  mandatory
        DESCRIPTION
           "An entry in the wan line table."
       INDEX   { wanLineIfIndex }
       ::= { wanLineTable 1 }

    WanLineEntry ::=
        SEQUENCE {
            wanLineIfIndex
                INTEGER,
            wanLineName
                DisplayString,
            wanLineType
                OBJECT IDENTIFIER,
            wanLineChannels
                INTEGER,
            wanLineState
                INTEGER,
            wanLineStateString
                DisplayString,
            wanLineActiveChannels
                INTEGER,
            wanLineUsage
                INTEGER,
            wanLineHuntGrpPhoneNumber1
                DisplayString,
            wanLineHuntGrpPhoneNumber2
                DisplayString,
            wanLineHuntGrpPhoneNumber3
                DisplayString,
            wanLineAvailableChannels
                INTEGER,
            wanLineSwitchedChannels
                INTEGER,
            wanLineDisabledChannels
                INTEGER,
	    wanLineNailedChannels
                INTEGER,
	    wanLineOutOfServiceChannels
                INTEGER,
	    wanLineNet2NetChannels
	    	INTEGER,
	    wanLineDtptChannels
	        INTEGER
    }

    wanLineIfIndex OBJECT-TYPE
        SYNTAX  INTEGER
        ACCESS  read-only
        STATUS  mandatory
        DESCRIPTION
           "This value for this object  is  equal  to  the
           value  of  ifIndex from the Interfaces table of
           MIB II (RFC 1213)."
       ::= { wanLineEntry 1 }

    wanLineName OBJECT-TYPE
        SYNTAX  DisplayString
        ACCESS  read-only
        STATUS  mandatory
        DESCRIPTION
          "A textual name of the wanLine as assigned through
          the menu sytem."
       ::= { wanLineEntry 2 }

     wanLineType OBJECT-TYPE
         SYNTAX  OBJECT IDENTIFIER
         ACCESS  read-only
         STATUS  mandatory
         DESCRIPTION
            "One of 'wanTypes'."
       ::= { wanLineEntry 3 }

    wanLineChannels OBJECT-TYPE
        SYNTAX  INTEGER
        ACCESS  read-only
        STATUS  mandatory
        DESCRIPTION
           "The number of ds0 channels supported."
       ::= { wanLineEntry 4 }

    wanLineState OBJECT-TYPE
        SYNTAX  INTEGER {
            ls-unknown(1),
            ls-does-not-exist(2),
            ls-disabled(3),
            ls-no-physical(4),
            ls-no-logical(5),
            ls-point-to-point(6),
            ls-multipoint-1(7),
            ls-multipoint-2(8),
            ls-loss-of-sync(9),
            ls-yellow-alarm(10),
            ls-ais-receive(11),
            ls-no-d-channel(12),
            ls-active(13),
            ls-maintenance(14)
        }
        ACCESS  read-only
        STATUS  mandatory
        DESCRIPTION
           "The state of the line."
       ::= { wanLineEntry 5 }

    wanLineStateString OBJECT-TYPE
        SYNTAX  DisplayString
        ACCESS  read-only
        STATUS  mandatory
        DESCRIPTION
          "A textual representation of the wanLineState
          as displayed by the menu sytem."
       ::= { wanLineEntry 6 }

    wanLineActiveChannels OBJECT-TYPE
        SYNTAX  INTEGER
        ACCESS  read-only
        STATUS  mandatory
        DESCRIPTION
          "The number of switched DS0 channels of the line.
	  This variable counts the number of wanLineChannels on an enabled
          line with the wanLineChannelUsage of ds0-switched-channel(3) and
          with any following wanLineChannelState bs-clear-pending(8),
          bs-dialing(9), bs-ringing(10),and bs-connected(11) for all the
          entries in its wanLineChannelEntry table." 
       ::= { wanLineEntry 7 }

    wanLineUsage OBJECT-TYPE
        SYNTAX  INTEGER {
            lu-unknown(1),
            lu-unavailable(2),
            lu-disabled(3),
            lu-enabled(4),
            lu-trunk(5),
            lu-quiesced(6),
            lu-drop-and-insert(7),
            lu-t-online-user(8),
            lu-t-online-zgr(9)
        }
        ACCESS  read-write
        STATUS  mandatory
        DESCRIPTION
          "The usage of the line. SETting values are supported only for T1/E1
           links. Only lu-disabled(3), lu-trunk(5), and lu-quiesced(6) for
           T1/PRI are currently supported for SETs."
       ::= { wanLineEntry 8 }

    wanLineHuntGrpPhoneNumber1 OBJECT-TYPE
        SYNTAX  DisplayString
        ACCESS  read-write
        STATUS  mandatory
        DESCRIPTION
          "The hunt group phone number associated with
          the line. This entry is manually entered in the line
          configurations options."
       ::= { wanLineEntry 9 }

    wanLineHuntGrpPhoneNumber2 OBJECT-TYPE
        SYNTAX  DisplayString
        ACCESS  read-write
        STATUS  mandatory
        DESCRIPTION
          "The hunt group phone number associated with
          the line. This entry is manually entered in the line
          configurations options."
       ::= { wanLineEntry 10 }

    wanLineHuntGrpPhoneNumber3 OBJECT-TYPE
        SYNTAX  DisplayString
        ACCESS  read-write
        STATUS  mandatory
        DESCRIPTION
          "The hunt group phone number associated with
          the line. This entry is manually entered in the line
          configurations options."
       ::= { wanLineEntry 11 }

    wanLineAvailableChannels OBJECT-TYPE
        SYNTAX  INTEGER
        ACCESS  read-only
        STATUS  mandatory
        DESCRIPTION
          "The number of DS0 channels of the line configured as Switched and
	  available for making or accepting calls. 
          This variable counts the number of wanLineChannels with the
          wanLineChannelState of bs-idle(7) for all the entries in its
          wanLineChannelEntry table."
       ::= { wanLineEntry 12 }

    wanLineSwitchedChannels OBJECT-TYPE
        SYNTAX  INTEGER
        ACCESS  read-only
        STATUS  mandatory
        DESCRIPTION
          "The number of DS0 channels of the line configured as switched.
          This variable counts the number of wanLineChannels on an enabled
          line with the wanLineChannelUsage of ds0-switched-channel(3) and
          with wanLineChannelState not bs-disabled(18) for all the entries
          in its wanLineChannelEntry table." 
       ::= { wanLineEntry 13 }

    wanLineDisabledChannels OBJECT-TYPE
        SYNTAX  INTEGER
        ACCESS  read-only
        STATUS  mandatory
        DESCRIPTION
          "The number of disabled DS0 channels of the line.
          This variable counts the number of wanLineChannels with the
          wanLineChannelState of bs-disabled(18) and with any
          wanLineChannelUsage for all the entries in its wanLineChannelEntry
          table."
       ::= { wanLineEntry 14 }

    wanLineNailedChannels OBJECT-TYPE
        SYNTAX  INTEGER
        ACCESS  read-only
        STATUS  mandatory
        DESCRIPTION
          "The number of DS0 channels of the line configured as nailed.
          This variable counts the number of wanLineChannels on an enabled
          line with the wanLineChannelUsage of ds0-clear-64(5) and with
          wanLineChannelState not bs-disabled(18) for all the entries in its
          wanLineChannelEntry table." 
       ::= { wanLineEntry 15 }

    wanLineOutOfServiceChannels OBJECT-TYPE
        SYNTAX  INTEGER
        ACCESS  read-only
        STATUS  mandatory
        DESCRIPTION
          "The number of out-of-service DS0 channels of the line.
          This variable counts the number of wanLineChannels on an enabled
          line with the wanLineChannelUsage of ds0-switched-channel and
          wanLineChannelState of bs-unavailable(2), bs-out-of-service(4),
          bs-maintenance(16) for all the entries in its wanLineChannelEntry
          table." 
       ::= { wanLineEntry 16 }

    wanLineNet2NetChannels OBJECT-TYPE
    	SYNTAX INTEGER
	ACCESS read-only
	STATUS mandatory
	DESCRIPTION
	  "The number of NET2NET DS0 channels of the line.
	  This variable counts the number of wanLineChannels on an enabled
	  line with the wanLineChannelUsage of ds0-switched-channel and
	  wanLineChannelState of bs-net2net-dialing, bs-net2net-ringing and
	  bs-net2net-connected for all the entries in its wanLineChannelEntry
	  table."
       ::= { wanLineEntry 17 }

    wanLineDtptChannels OBJECT-TYPE
    	SYNTAX INTEGER
	ACCESS read-only
	STATUS mandatory
	DESCRIPTION
	  "The number of DTPT DS0 channels of the line.
	  This variable counts the number of wanLineChannels on an enabled
	  line with the wanLineChannelUsage of ds0-switched-channel and
	  wanLineChannelState of bs-dtpt-dialing, bs-dtpt-ringing and
	  bs-dtpt-connected for all the entries in its wanLineChannelEntry
	  table."
       ::= { wanLineEntry 18 }

    wanLineChannelTable OBJECT-TYPE
        SYNTAX  SEQUENCE OF WanLineChannelEntry
        ACCESS  not-accessible
        STATUS  mandatory
        DESCRIPTION
           "The wan line table."
       ::= { advancedAgent 22 }

    wanLineChannelEntry OBJECT-TYPE
        SYNTAX  WanLineChannelEntry
        ACCESS  not-accessible
        STATUS  mandatory
        DESCRIPTION
           "An entry in the wan line table."
       INDEX   { wanLineChannelIfIndex, wanLineChannelIndex }
       ::= { wanLineChannelTable 1 }

    WanLineChannelEntry ::=
        SEQUENCE {
            wanLineChannelIfIndex
                INTEGER,
            wanLineChannelIndex
                INTEGER,
            wanLineChannelState
                INTEGER,
            wanLineChannelStateString
                DisplayString,
            wanLineChannelErrorCount
                INTEGER,
            wanLineChannelUsage
                INTEGER,
            wanLineChannelTrunkGroup
                INTEGER,
            wanLineChannelPhoneNumber
                DisplayString,
            wanLineChannelSlot
                INTEGER,
            wanLineChannelPort
                INTEGER,
            wanLineChannelNailedState
                INTEGER
        }

    wanLineChannelIfIndex OBJECT-TYPE
        SYNTAX  INTEGER
        ACCESS  read-only
        STATUS  mandatory
        DESCRIPTION
           "This value for this object  is  equal  to  the
           value  of  ifIndex from the Interfaces table of
           MIB II (RFC 1213)."
       ::= { wanLineChannelEntry 1 }

    wanLineChannelIndex OBJECT-TYPE
        SYNTAX  INTEGER
        ACCESS  read-only
        STATUS  mandatory
        DESCRIPTION
           "The ds0 channel number with the line."
       ::= { wanLineChannelEntry 2 }

    wanLineChannelState OBJECT-TYPE
        SYNTAX  INTEGER {
            bs-unknown(1),
            bs-unavailable(2),
            bs-unused(3),
            bs-out-of-service(4),
            bs-nailed-up(5),
            bs-held(6),
            bs-idle(7),
            bs-clear-pending(8),
            bs-dialing(9),
            bs-ringing(10),
            bs-connected(11),
            bs-signaling(12),
            bs-cut-through(13),
            bs-current-d(14),
            bs-backup-d(15),
            bs-maintenance(16),
            bs-spc-up(17),
            bs-disabled(18),
	    bs-dialing-net2net(19),
	    bs-ringing-net2net(20),
	    bs-connected-net2net(21),
	    bs-dialing-dtpt(22),
	    bs-ringing-dtpt(23),
	    bs-connected-dtpt(24)
        }
        ACCESS  read-only
        STATUS  mandatory
        DESCRIPTION
           "The state of the ds0 channel."
       ::= { wanLineChannelEntry 3 }

    wanLineChannelStateString OBJECT-TYPE
        SYNTAX  DisplayString
        ACCESS  read-only
        STATUS  mandatory
        DESCRIPTION
           "A textual representation of the wanLineChannelState
           as displayed by the menu sytem."
       ::= { wanLineChannelEntry 4 }

    wanLineChannelErrorCount OBJECT-TYPE
        SYNTAX  INTEGER
        ACCESS  read-only
        STATUS  mandatory
        DESCRIPTION
           "The error count encountered on the channel."
       ::= { wanLineChannelEntry 5 }

    wanLineChannelUsage OBJECT-TYPE
        SYNTAX  INTEGER {
            ds0-unknown-channel(1),
            ds0-unused-channel(2),
            ds0-switched-channel(3),
            ds0-cut-through(4),
            ds0-clear-64(5),
            ds0-pri-d-channel(6),
            ds0-nfas-prime-d(7),
            ds0-nfas-sec-d(8),
            ds0-cas-channel(9),
            ds0-spc-channel(10)
        }
        ACCESS  read-only
        STATUS  mandatory
        DESCRIPTION
           "The usage for this ds0 channel."
       ::= { wanLineChannelEntry 6 }

    wanLineChannelTrunkGroup OBJECT-TYPE
        SYNTAX INTEGER
        ACCESS  read-only
        STATUS  mandatory
        DESCRIPTION
           "The trunk group assigned to this channel.
	    Note: This attribute returns 0 if
	          wanUseTrunkGroup is set to do-not-use(1)."
       ::= { wanLineChannelEntry 7 }

    wanLineChannelPhoneNumber OBJECT-TYPE
        SYNTAX  DisplayString
        ACCESS  read-only
        STATUS  mandatory
        DESCRIPTION
           "The phone number of this channel.  This is the number
           sent to the far end in an inverse multiplexed call when
           instructing the far end to add more bandwidth.
           The number should contain the minimum number of digits
           to identify the channel.  If the channel is part
           of a hunt group, the phone number should be blank."
       ::= { wanLineChannelEntry 8 }

    wanLineChannelSlot OBJECT-TYPE
        SYNTAX INTEGER
        ACCESS  read-only
        STATUS  mandatory
        DESCRIPTION
           "A slot number for routing incoming
            calls associated with the channel. A slot-port number
            zero means calls arriving on this channel can be
            routed to any port."
        ::= { wanLineChannelEntry 9 }

    wanLineChannelPort OBJECT-TYPE
        SYNTAX INTEGER
        ACCESS  read-only
        STATUS  mandatory
        DESCRIPTION
           "A port number for routing incoming
            calls associated with the channel. A slot-port number
            zero means calls arriving on this channel can be
            routed to any port."
        ::= { wanLineChannelEntry 10 }

    wanLineChannelNailedState OBJECT-TYPE
        SYNTAX INTEGER {
            not-applicable(1),
            nailed-held(2),
            nailed-active(3)
        }
        ACCESS  read-only
        STATUS  mandatory
        DESCRIPTION
           "The nailed group associated with the channel."
        ::= { wanLineChannelEntry 11 }

    wanAvailableChannels OBJECT-TYPE
        SYNTAX  INTEGER
        ACCESS  read-only
        STATUS  mandatory
        DESCRIPTION
          "The sum of wanLineAvailableChannels for all lines."
       ::= { advancedAgent 23 }

    wanSwitchedChannels OBJECT-TYPE
        SYNTAX  INTEGER
        ACCESS  read-only
        STATUS  mandatory
        DESCRIPTION
          "The sum of wanLineSwitchedChannels for all lines."
       ::= { advancedAgent 24 }

    wanDisabledChannels OBJECT-TYPE
        SYNTAX  INTEGER
        ACCESS  read-only
        STATUS  mandatory
        DESCRIPTION
          "The sum of wanLineDisabledChannels for all lines."
       ::= { advancedAgent 25 }

    wanActiveChannels OBJECT-TYPE
        SYNTAX  INTEGER
        ACCESS  read-only
        STATUS  mandatory
        DESCRIPTION
          "The sum of wanLineActiveChannels for all lines."
       ::= { advancedAgent 26 }

    wanNailedChannels OBJECT-TYPE
        SYNTAX  INTEGER
        ACCESS  read-only
        STATUS  mandatory
        DESCRIPTION
          "The sum of wanLineNailedChannels for all lines."
       ::= { advancedAgent 27 }

    wanOutOfServiceChannels OBJECT-TYPE
        SYNTAX  INTEGER
        ACCESS  read-only
        STATUS  mandatory
        DESCRIPTION
          "The sum of wanLineOutOfChannels for all lines."
       ::= { advancedAgent 28 }

    --
    -- Channel state summaries per line type.
    --

    wanLineChannelUsageTable OBJECT-TYPE
    	SYNTAX	SEQUENCE OF WanLineChannelUsageEntry
	ACCESS	not-accessible
	STATUS	mandatory
	DESCRIPTION
	  "Table of channel state summaries per line type."
	::= { advancedAgent 29 }

    wanLineChannelUsageEntry OBJECT-TYPE
	SYNTAX	WanLineChannelUsageEntry
	ACCESS	not-accessible
	STATUS	mandatory
	DESCRIPTION
	  "An entry in the channel state summary table for the given
	  wanLineUsage and wanLineChannelState."
	INDEX	{ wanLineUsage, wanLineChannelState }
	::= { wanLineChannelUsageTable 1 }

    WanLineChannelUsageEntry ::=
	SEQUENCE {
	    wanLineChannelUsageCount		-- the actual count.
	     	INTEGER
	}

    wanLineChannelUsageCount OBJECT-TYPE
    	SYNTAX	INTEGER
	ACCESS	read-only
	STATUS	mandatory
	DESCRIPTION
        "The count of channels in the selected wanLineChannelState for the
	selected wanLineUsage."
      ::= { wanLineChannelUsageEntry 1 }

END
