--
--
-- NOTE:
--
--
-- This is the NPI TRAP MIB, modified for the DS24+ by XACT Inc.
--
--
--
-- February 9, 1998
--
--
--
-- ==================================================================
-- FILE : TRAP.MIB file, 1.00.00, 08/15/1997

-- --------------------------------------------------------------
-- Copyright (c) 1996, 1997 Network Peripherals Inc.
-- All rights reserved.

-- This SNMP Management Information Specification embodies
-- Network Peripherals Inc.'s (NPI) confidential and
-- proprietary intellectual property.  NPI retains all title
-- and ownership in the Specification, including any revisions.

-- This Specification is supplied "AS IS", and NPI
-- makes no warranty, either expressed or implied,
-- as to the use, operation, condition, or performance of the
-- Specification.

-- -----------------
-- Revised History :
-- -----------------
-- This MIB file is trap definition for NPI TidalWave
-- devices (FE-1200+/FE-1200TF+)
--
-- *** 01/31/1997, created by Andy Choi,
-- *** 07/18/1997, v 0.0.7 released by Andy Choi
-- *** 08/15/1997, v 1.00.00 released by Eric Weng
--
-- ==============================================================


-- ENTERPRISE
   -- FE_1200+ : switch_FE1200PLUS (current defined)
   -- FE_1200  : switch_FE1200
   -- FE_210   : switch_FE210
   -- FE_224   : switch_FE224

   -- Traps are defined using the conventions in RFC 1215 [6].

-- ==================================================================


TWTRAP-MIB DEFINITIONS ::= BEGIN

IMPORTS
     mgmt, NetworkAddress, IpAddress, Counter, Gauge, internet,
     TimeTicks                                         FROM RFC1155-SMI
     DisplayString                                     FROM RFC1213-MIB
     TRAP-TYPE                                         FROM RFC-1215
     OBJECT-TYPE                                       FROM RFC-1212;

mgmt         OBJECT IDENTIFIER ::= { iso org(3) dod(6) internet(1) mgmt(2) }
directory    OBJECT IDENTIFIER ::= { internet 1 }
experimental OBJECT IDENTIFIER ::= { internet 3 }
private      OBJECT IDENTIFIER ::= { internet 4 }
enterprises  OBJECT IDENTIFIER ::= { private  1 }
mib-2        OBJECT IDENTIFIER ::= { mgmt 1 }


MacAddress ::= OCTET STRING (SIZE (6))    -- a 6 octet address in
                                          -- the "canonical" order


-- (1.3.6.1.4.1.1101)
npi                          OBJECT IDENTIFIER ::= { enterprises 1101 }
common               		 OBJECT IDENTIFIER ::= { npi 1 }
npi-Switching-MIB            OBJECT IDENTIFIER ::= { npi 2 }

switch-Common-MIB            OBJECT IDENTIFIER ::= { npi-Switching-MIB 1 }
switchBasicHubInfo           OBJECT IDENTIFIER ::= { switch-Common-MIB 1 }
switchBasicPortInfo          OBJECT IDENTIFIER ::= { switch-Common-MIB 2 }

switch-DS24             	 OBJECT IDENTIFIER ::= { npi-Switching-MIB 13 }
switch-TidalWave             OBJECT IDENTIFIER ::= { npi-Switching-MIB 10 }
switch-FE1200PLUS            OBJECT IDENTIFIER ::= { switch-TidalWave 1 }
switch-FE1200                OBJECT IDENTIFIER ::= { npi-Switching-MIB 3 }
switch-Cascade-MIB           OBJECT IDENTIFIER ::= { npi-Switching-MIB 2 }
switchCmsBasicPackage        OBJECT IDENTIFIER ::= { switch-Cascade-MIB  1 }
switchCmsBasicClusterInfo    OBJECT IDENTIFIER ::= { switchCmsBasicPackage 1 }
switchCmsBasicUnitInfo       OBJECT IDENTIFIER ::= { switchCmsBasicPackage 2 }
switchCmsBasicPortInfo       OBJECT IDENTIFIER ::= { switchCmsBasicPackage 3 }
switchCmsAddrTrackPackage    OBJECT IDENTIFIER ::= { switch-Cascade-MIB 3 }
switchCmsAddrTrackPortInfo   OBJECT IDENTIFIER ::= { switchCmsAddrTrackPackage 3 }

---
dot1dBridge                  OBJECT IDENTIFIER ::= { mib-2 17 }
dot1dBase                    OBJECT IDENTIFIER ::= { dot1dBridge 1 }
dot1dStp                     OBJECT IDENTIFIER ::= { dot1dBridge 2 }
dot1dSr                      OBJECT IDENTIFIER ::= { dot1dBridge 3 }
dot1dTp                      OBJECT IDENTIFIER ::= { dot1dBridge 4 }
dot1dStatic                  OBJECT IDENTIFIER ::= { dot1dBridge 5 }

---
devDeviceInfo                OBJECT IDENTIFIER ::= { common 1 }
devMonitorInfo               OBJECT IDENTIFIER ::= { common 2 }
devActionInfo                OBJECT IDENTIFIER ::= { common 3 }
devMonTrapReportLevel        OBJECT IDENTIFIER ::= { devMonitorInfo 2 }

---
snmpDot3RptrMgt              OBJECT IDENTIFIER ::= { mib-2 22 }
rptrBasicPackage             OBJECT IDENTIFIER ::= { snmpDot3RptrMgt 1 }
rptrMonitorPackage           OBJECT IDENTIFIER ::= { snmpDot3RptrMgt 2 }
rptrAddrTrackPackage         OBJECT IDENTIFIER ::= { snmpDot3RptrMgt 3 }
rptrRptrInfo                 OBJECT IDENTIFIER ::= { rptrBasicPackage 1 }
rptrGroupInfo                OBJECT IDENTIFIER ::= { rptrBasicPackage 2 }
rptrPortInfo                 OBJECT IDENTIFIER ::= { rptrBasicPackage 3 }
rptrMonitorRptrInfo          OBJECT IDENTIFIER ::= { rptrMonitorPackage 1 }
rptrMonitorGroupInfo         OBJECT IDENTIFIER ::= { rptrMonitorPackage 2 }
rptrMonitorPortInfo          OBJECT IDENTIFIER ::= { rptrMonitorPackage 3 }
rptrAddrTrackRptrInfo        OBJECT IDENTIFIER ::= { rptrAddrTrackPackage 1 }
rptrAddrTrackGroupInfo       OBJECT IDENTIFIER ::= { rptrAddrTrackPackage 2 }
rptrAddrTrackPortInfo        OBJECT IDENTIFIER ::= { rptrAddrTrackPackage 3 }

rptrPortTable                OBJECT IDENTIFIER ::= { rptrPortInfo 1 }
rptrPortEntry                OBJECT IDENTIFIER ::= { rptrPortTable 1 }
rptrPortIndex                OBJECT IDENTIFIER ::= { rptrPortEntry 2 }

rptrPortGroupIndex           OBJECT IDENTIFIER ::= { rptrPortEntry 1 }

---
basicUnitTable               OBJECT IDENTIFIER ::= { switchCmsBasicUnitInfo 1 }
basicUnitEntry               OBJECT IDENTIFIER ::= { basicUnitTable 1 }
basicUnitIndex               OBJECT IDENTIFIER ::= { basicUnitEntry 1 }

basicPortTable               OBJECT IDENTIFIER ::= { switchCmsBasicPortInfo 1 }
basicPortEntry               OBJECT IDENTIFIER ::= { basicPortTable 1 }
basicPortUnitIndex           OBJECT IDENTIFIER ::= { basicPortEntry 1 }
basicPortIndex               OBJECT IDENTIFIER ::= { basicPortEntry 2 }

addrTrackPortTable           OBJECT IDENTIFIER ::= { switchCmsAddrTrackPortInfo  1 }
addrTrackPortEntry           OBJECT IDENTIFIER ::= { addrTrackPortTable  1 }
addrTrackPortUnitIndex       OBJECT IDENTIFIER ::= { addrTrackPortEntry 1 }
addrTrackPortPortIndex       OBJECT IDENTIFIER ::= { addrTrackPortEntry 2 }

---
basicSwitchPowerState        OBJECT IDENTIFIER ::= { switchBasicHubInfo 14 }

switchPortTable              OBJECT IDENTIFIER ::= { switchBasicPortInfo  1 }
switchPortEntry              OBJECT IDENTIFIER ::= { switchPortTable  1 }
switchPortIndex              OBJECT IDENTIFIER ::= { switchPortEntry 1 }
switchPortFullDuplex         OBJECT IDENTIFIER ::= { switchPortEntry 6 }
switchPortFlowControl        OBJECT IDENTIFIER ::= { switchPortEntry 7 }
switchPortSpeed              OBJECT IDENTIFIER ::= { switchPortEntry 13 }
-- switchPortSpeed              OBJECT IDENTIFIER ::= { switchPortEntry 8 }

switchAddrTrackInfo          OBJECT IDENTIFIER ::= { switch-Common-MIB 3 }
switchAddrPortInfo           OBJECT IDENTIFIER ::= { switchAddrTrackInfo 1 }
switchAddrPortTable          OBJECT IDENTIFIER ::= { switchAddrPortInfo  1 }
switchAddrPortEntry          OBJECT IDENTIFIER ::= { switchAddrPortTable  1 }
switchAddrPortIndex          OBJECT IDENTIFIER ::= { switchAddrPortEntry 1 }

switchPortMonitorInfo        OBJECT IDENTIFIER ::= { switch-DS24 7 }
switchPortMonitorTable       OBJECT IDENTIFIER ::= { switchPortMonitorInfo 4 }
switchPortMonitorEntry       OBJECT IDENTIFIER ::= { switchPortMonitorTable  1 }
switchPortMonitorIndex       OBJECT IDENTIFIER ::= { switchPortMonitorEntry 1 }
switchPortMonitorMessageStatus OBJECT IDENTIFIER ::= { switchPortMonitorEntry 3 }

switchAddrStaticInfo         OBJECT IDENTIFIER ::= { switch-Common-MIB 4 }
switchAddrPortPackMaxCount   OBJECT IDENTIFIER ::= { switchAddrPortEntry 6 }
switchAddrStaticPackMaxCount OBJECT IDENTIFIER ::= { switchAddrStaticInfo  4 }

switchAddrStaticTable        OBJECT IDENTIFIER ::= { switchAddrStaticInfo  6 }
switchAddrStaticEntry        OBJECT IDENTIFIER ::= { switchAddrStaticTable  1 }
switchAddrStaticIndex        OBJECT IDENTIFIER ::= { switchAddrStaticEntry 1 }
switchAddrStaticSetAddress   OBJECT IDENTIFIER ::= { switchAddrStaticEntry 2 }

switchThresholdInfo          OBJECT IDENTIFIER ::= { switch-Common-MIB 5 }
basicThresholdTable          OBJECT IDENTIFIER ::= { switchThresholdInfo 4 }
basicThresholdTableEntry     OBJECT IDENTIFIER ::= { basicThresholdTable 1 }

switchThresholdPort          OBJECT IDENTIFIER ::= { basicThresholdTableEntry 5}
switchThresholdType          OBJECT IDENTIFIER ::= { basicThresholdTableEntry 6}
switchThresholdUnit          OBJECT IDENTIFIER ::= { basicThresholdTableEntry 4}
switchThresholdCounter       OBJECT IDENTIFIER ::= { basicThresholdTableEntry 9}

switchSecureAddrInfo         OBJECT IDENTIFIER ::= { switch-DS24 6 }

switchAddrSecureTable        OBJECT IDENTIFIER ::= { switchSecureAddrInfo 4 }
switchAddrSecureEntry        OBJECT IDENTIFIER ::= { switchAddrSecureTable 1 }
switchAddrSecurePortIndex    OBJECT IDENTIFIER ::= { switchAddrSecureEntry 1 }
switchAddrSecureIndex        OBJECT IDENTIFIER ::= { switchAddrSecureEntry 2 }
switchAddrSecureAddress      OBJECT IDENTIFIER ::= { switchAddrSecureEntry 3 }

switchVirtualLanInfo         OBJECT IDENTIFIER ::= { switch-DS24 8 }
switchVirtualLanMessage      OBJECT IDENTIFIER ::= { switchVirtualLanInfo 5 }

switchPowerLinkInfo               OBJECT IDENTIFIER ::= { switch-Common-MIB 9 }
switchPowerLinkOperationMode      OBJECT IDENTIFIER ::= { switchPowerLinkInfo 2 }
switchPowerLinkUserSettingInfo    OBJECT IDENTIFIER ::= { switchPowerLinkInfo 5 }
switchPowerLinkUserOperationMode  OBJECT IDENTIFIER ::= { switchPowerLinkUserSettingInfo 1 }
switchPowerLinkUserRange          OBJECT IDENTIFIER ::= { switchPowerLinkUserSettingInfo 2 }
switchPowerLinkStatus             OBJECT IDENTIFIER ::= { switchPowerLinkInfo 7 }

switchTrapInfo                    OBJECT IDENTIFIER ::= { switch-DS24 13 }
switchTrapStaticCollisionAddress  OBJECT IDENTIFIER ::= { switchTrapInfo 1 }
switchTrapStaticCollisionAddress2 OBJECT IDENTIFIER ::= { switchTrapInfo 2 }
switchTrapFilterCollisionAddress  OBJECT IDENTIFIER ::= { switchTrapInfo 3 }

---
dot1dStpPortTable                 OBJECT IDENTIFIER ::= { dot1dStp 15 }
dot1dStpPortEntry                 OBJECT IDENTIFIER ::= { dot1dStpPortTable 1 }
dot1dStpPort                      OBJECT IDENTIFIER ::= { dot1dStpPortEntry 1 }


---
-- Traps defined by RFC1493
-- ==========================================================================

   newRoot         TRAP-TYPE
       ENTERPRISE  dot1dBridge
       VARIABLES   { devMonTrapReportLevel }     -- == 2
       DESCRIPTION
                   " Become the new root of the Spanning Tree."
       ::= 1

   topologyChange  TRAP-TYPE
       ENTERPRISE  dot1dBridge
       VARIABLES   { devMonTrapReportLevel }     -- == 2
       DESCRIPTION
                   " Spanning tree topology change."
       ::= 2

-- ==================================================================

   -- Traps for use by reset & test

   rptr-Reset      TRAP-TYPE
       ENTERPRISE  switch-FE1200PLUS
       VARIABLES   { devMonTrapReportLevel }     -- == 3
       DESCRIPTION
                   " Successfully reset the switching hub."
       ::= 256

   rptr-FReset1    TRAP-TYPE
       ENTERPRISE  switch-FE1200PLUS
       VARIABLES   { devMonTrapReportLevel }     -- == 3
       DESCRIPTION
                   " Fattory reset of the switching hub is successful."
       ::= 257

-- ==================================================================

   -- Traps for use by port status

   rptr-Port-Enabled  TRAP-TYPE
       ENTERPRISE  switch-FE1200PLUS
       VARIABLES   { devMonTrapReportLevel,      -- == 4
                     rptrPortGroupIndex,
                     rptrPortIndex }
       DESCRIPTION
                   " Enable a port."
       ::= 288

   rptr-Port-Disabled  TRAP-TYPE
       ENTERPRISE  switch-FE1200PLUS
       VARIABLES   { devMonTrapReportLevel,      -- == 4
                     rptrPortGroupIndex,
                     rptrPortIndex }
       DESCRIPTION
                   " Disable a port."
       ::= 289

-- ===============================

   -- Traps for use by port status

   rptr-Port-Link-Up  TRAP-TYPE
       ENTERPRISE  switch-FE1200PLUS
       VARIABLES   { devMonTrapReportLevel,      -- == 6
                     rptrPortGroupIndex,
                     rptrPortIndex }
       DESCRIPTION
                   " Link state of a port has been changed from down to up."
       ::= 292

   rptr-Port-Link-Down  TRAP-TYPE
       ENTERPRISE  switch-FE1200PLUS
       VARIABLES   { devMonTrapReportLevel,      -- == 6
                     rptrPortGroupIndex,
                     rptrPortIndex }
       DESCRIPTION
                   " Link state of a port has been changed from up to down."
       ::= 293

-- ===============================

   -- Traps for use by power supply change

   switch-Unit-Power-Status TRAP-TYPE
      ENTERPRISE switch-FE1200PLUS
      VARIABLES   { devMonTrapReportLevel,       -- == 2
                    basicSwitchPowerState
                  }
      DESCRIPTION
                  " The power supply of the switching hub is changed."
      ::= 512

-- ===============================

   -- Traps for use by spanning tree

   switch-Port-Monitor-Rx-CBPDU  TRAP-TYPE
       ENTERPRISE switch-FE1200PLUS
       VARIABLES   { devMonTrapReportLevel,      -- == 5
                     dot1dStpPort,
                     switchPortMonitorIndex
                   }
       DESCRIPTION
                   " The monitoring port received a configuration BPDU."
       ::= 514

-- =====================

  -- Traps for use by port status changed

   switch-Port-Duplex-Change TRAP-TYPE
      ENTERPRISE  switch-FE1200PLUS
      VARIABLES   { devMonTrapReportLevel,       -- == 3
                    switchPortIndex,
                    switchPortFullDuplex
                  }
      DESCRIPTION
                  " Duplex status of the switching port is changed."
      ::= 532

   switch-Port-Speed-Change TRAP-TYPE
      ENTERPRISE  switch-FE1200PLUS
      VARIABLES   { devMonTrapReportLevel,       -- == 3
                    switchPortIndex,
                    switchPortSpeed
                  }
      DESCRIPTION
                  " Speed of the switching port is changed."
      ::= 533

   switch-Port-FlowControl-Changed TRAP-TYPE
      ENTERPRISE  switch-FE1200PLUS
      VARIABLES   { devMonTrapReportLevel,       -- == 3
                    switchPortIndex,
                    switchPortFlowControl
                  }
      DESCRIPTION
                  " Flow Control status of the switching port is changed
                    due to auto-negotiate full duplex.
                  "
      ::= 534

-- ===============================
-- ===============================

   -- Traps for use by thread hold

   switch-Unit-Accumulate-reach  TRAP-TYPE
       ENTERPRISE  switch-FE1200PLUS
       VARIABLES   { devMonTrapReportLevel,      -- == 3
                     switchThresholdUnit,
                     switchThresholdType,
                     switchThresholdCounter
                   }
       DESCRIPTION
                   " "
       ::= 576

   switch-Unit-Rate-notification  TRAP-TYPE
       ENTERPRISE  switch-FE1200PLUS
       VARIABLES   { devMonTrapReportLevel,      -- == 3
                     switchThresholdUnit,
                     switchThresholdType,
                     switchThresholdCounter
                   }
       DESCRIPTION
                   " "
       ::= 577

   switch-Port-Accumulate-reach  TRAP-TYPE
       ENTERPRISE  switch-FE1200PLUS
       VARIABLES   { devMonTrapReportLevel,      -- == 3
                     switchThresholdUnit,
                     switchThresholdPort,
                     switchThresholdType,
                     switchThresholdCounter
                   }
       DESCRIPTION
                   " "
       ::= 579

   switch-Port-Rate-notification  TRAP-TYPE
       ENTERPRISE  switch-FE1200PLUS
       VARIABLES   { devMonTrapReportLevel,      -- == 3
                     switchThresholdUnit,
                     switchThresholdPort,
                     switchThresholdType,
                     switchThresholdCounter
                   }
       DESCRIPTION
                   " "
       ::= 580


-- ===============================

   -- Traps for use by address operation

   switch-Security-On  TRAP-TYPE
       ENTERPRISE  switch-FE1200PLUS
       VARIABLES   { devMonTrapReportLevel }     -- == 3
       DESCRIPTION
                   " Enable filter function."
       ::= 592

   switch-Security-Off  TRAP-TYPE
       ENTERPRISE  switch-FE1200PLUS
       VARIABLES   { devMonTrapReportLevel }     -- == 3
       DESCRIPTION
                   " Disable filter function."
       ::= 593

   switch-Security-Addr-Collision  TRAP-TYPE
       ENTERPRISE  switch-FE1200PLUS
       VARIABLES   { devMonTrapReportLevel,      -- == 3
                     switchTrapFilterCollisionAddress,  -- incoming address
                     switchAddrSecurePortIndex,         -- collision entry
                     switchAddrSecureIndex,
                     switchAddrSecureAddress
                   }
       DESCRIPTION
                   " Set a collision address in filter table."
       ::= 595

   switch-Security-Reserved-Addr-Collision  TRAP-TYPE
       ENTERPRISE  switch-FE1200PLUS
       VARIABLES   { devMonTrapReportLevel,      -- == 3
                     switchTrapFilterCollisionAddress,  -- incoming address
                     switchAddrStaticIndex,             -- collision entry
                     switchAddrStaticSetAddress
                   }
       DESCRIPTION
                   " Set an address collision with reserved address."
       ::= 596


-- ===============================

   -- Traps for use by port monitor

   switch-Port-Monitor-On  TRAP-TYPE
       ENTERPRISE  switch-FE1200PLUS
       VARIABLES   { devMonTrapReportLevel }     -- == 3
       DESCRIPTION
                   " Enable port monitor function."
       ::= 608

   switch-Port-Monitor-Off  TRAP-TYPE
       ENTERPRISE  switch-FE1200PLUS
       VARIABLES   { devMonTrapReportLevel }     -- == 3
       DESCRIPTION
                   " Disable port monitor function."
       ::= 609

   switch-Port-Monitor-Port-On  TRAP-TYPE
       ENTERPRISE  switch-FE1200PLUS
       VARIABLES   { devMonTrapReportLevel,      -- == 6
                     switchPortIndex
                   }
       DESCRIPTION
                   " Port monitor function is active on the specific port."
       ::= 610

   switch-Port-Monitor-Port-Off  TRAP-TYPE
       ENTERPRISE  switch-FE1200PLUS
       VARIABLES   { devMonTrapReportLevel,      -- == 6
                     switchPortIndex
                   }
       DESCRIPTION
                   " Port monitor function is removed from the specific port."
       ::= 611
--

   switch-Port-Monitor-Active  TRAP-TYPE
       ENTERPRISE  switch-FE1200PLUS
       VARIABLES   { devMonTrapReportLevel,      -- == 4
                     switchPortMonitorIndex
                   }
       DESCRIPTION
                   " Enable port monitor function of a monitor group."
       ::= 612

   switch-Port-Monitor-Removed  TRAP-TYPE
       ENTERPRISE  switch-FE1200PLUS
       VARIABLES   { devMonTrapReportLevel,      -- == 4
                     switchPortMonitorIndex
                   }
       DESCRIPTION
                   " Disable port monitor function of a monitor group."
       ::= 613

   switch-Port-Monitor-Error  TRAP-TYPE
       ENTERPRISE  switch-FE1200PLUS
       VARIABLES   { devMonTrapReportLevel,      -- == 5
                     switchPortMonitorIndex,
                     switchPortMonitorMessageStatus
                   }
       DESCRIPTION
                   " Operation error for port monitor function."
       ::= 614


-- ===============================

   -- Traps for use by virtual LAN

   switch-Virtual-LAN-On  TRAP-TYPE
       ENTERPRISE  switch-FE1200PLUS
       VARIABLES   { devMonTrapReportLevel }     -- == 3
       DESCRIPTION
                   " Enable Virtual LAN function."
       ::= 624

   switch-Virtual-LAN-Off  TRAP-TYPE
       ENTERPRISE  switch-FE1200PLUS
       VARIABLES   { devMonTrapReportLevel }     -- == 3
       DESCRIPTION
                   " Disable Virtual LAN function."
       ::= 625

   switch-VL-Port-On   TRAP-TYPE
       ENTERPRISE  switch-FE1200PLUS
       VARIABLES   { devMonTrapReportLevel,      -- == 6
                     switchPortIndex
                   }
       DESCRIPTION
                   " Virtual LAN function is active on the specific port."
       ::= 626

   switch-VL-Port-Off  TRAP-TYPE
       ENTERPRISE  switch-FE1200PLUS
       VARIABLES   { devMonTrapReportLevel,      -- == 6
                     switchPortIndex
                   }
       DESCRIPTION
                   " Virtual LAN function is removed from the specific port."
       ::= 627

-- ===============================
-- ==================================================================

END

-- EOF
