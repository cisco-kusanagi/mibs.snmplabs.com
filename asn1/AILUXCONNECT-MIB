AILUXCONNECT-MIB DEFINITIONS ::= BEGIN

IMPORTS
    MODULE-IDENTITY, NOTIFICATION-TYPE, OBJECT-TYPE,
    Integer32,
    enterprises
					FROM SNMPv2-SMI
    TruthValue
					FROM SNMPv2-TC
    InterfaceIndex
					FROM IF-MIB
    AIIConnType
					FROM AISYSTEM-MIB;

    aii OBJECT IDENTIFIER ::= {enterprises 539}

aiLuxConnect MODULE-IDENTITY
    LAST-UPDATED "200104301700Z"
    ORGANIZATION "Applied Innovation Inc."
    CONTACT-INFO
	"		Engineering MIB Administrator
		Postal: Applied Innovation Inc.
			5800 Innovation Drive
			Dublin, Ohio 43017-3271

		Tel:	614-798-2000
		Fax:	614-798-1770
		Email:	snmp@aiinet.com"
    DESCRIPTION "MIB module for the AI LuxConnect."
    REVISION "200104301700Z"
    DESCRIPTION "The initial revision of this module."
	::= { aii 33 }

-- Object definitions (Using "aiLC" prefix)


aiLCTrapInfo OBJECT IDENTIFIER ::= { aiLuxConnect 0 }

aiLCTrapGtranSwitch NOTIFICATION-TYPE
    OBJECTS	{ aiLCGtranActiveIndex,
		  aiLCGtranActiveSpan }
    STATUS      current
    DESCRIPTION
	"Trap sent when the GTRAN switches the fiber span utilized by
	the active laser."
    ::= { aiLCTrapInfo 1 }

aiLCTrapGbicInserted NOTIFICATION-TYPE
    OBJECTS	{ aiLCGbicIndex,
    		  aiLCGbicConnectorType }
    STATUS      current
    DESCRIPTION
	"Trap sent when a Gigabit Ethernet Interface Converter is inserted."
    ::= { aiLCTrapInfo 2 }

aiLCTrapGbicRemoved NOTIFICATION-TYPE
    OBJECTS	{ aiLCGbicIndex,
		  aiLCGbicConnectorType }
    STATUS      current
    DESCRIPTION
	"Trap sent when a Gigabit Ethernet Interface Converter is removed."
    ::= { aiLCTrapInfo 3 }

-- Information on the GTRAN 10G laser.

aiLCGtranActiveTable OBJECT-TYPE
    SYNTAX      SEQUENCE OF AiLCGtranActiveEntry
    MAX-ACCESS  not-accessible
    STATUS      current
    DESCRIPTION
	"Information on the active laser of the GTRAN module."
    ::= { aiLuxConnect 1 }

aiLCGtranActiveEntry OBJECT-TYPE
    SYNTAX      AiLCGtranActiveEntry
    MAX-ACCESS  not-accessible
    STATUS      current
    DESCRIPTION
	"Information on a given GTRAN active laser"
    INDEX { aiLCGtranActiveIndex }
    ::= { aiLCGtranActiveTable 1 }

AiLCGtranActiveEntry ::=
    SEQUENCE {
	aiLCGtranActiveIndex		InterfaceIndex,
	aiLCGtranActiveBackupIndex	InterfaceIndex,
	aiLCGtranActiveSpan		INTEGER,
	aiLCGtranActiveRxUtilization	Integer32,
	aiLCGtranActiveTxUtilization	Integer32,
	aiLCGtranActiveClockSlave	TruthValue,
	aiLCGtranActiveCoolerStatus	INTEGER,
	aiLCGtranActiveTemperature	INTEGER,
	aiLCGtranActiveRxPower		INTEGER,
	aiLCGtranActiveTxPower		INTEGER
    }


aiLCGtranActiveIndex OBJECT-TYPE
    SYNTAX	InterfaceIndex
    MAX-ACCESS	read-only
    STATUS	current
    DESCRIPTION
	"Index of this object in the current table.  Since this table
	entry is an extension of the ifTable, this should object
	should have the same value as the corresponding ifIndex."
    ::= { aiLCGtranActiveEntry 1 }

aiLCGtranActiveBackupIndex OBJECT-TYPE
    SYNTAX	InterfaceIndex
    MAX-ACCESS	read-only
    STATUS	current
    DESCRIPTION
	"Index of the corresponding backup laser."
    ::= { aiLCGtranActiveEntry 2 }

aiLCGtranActiveSpan OBJECT-TYPE
    SYNTAX	INTEGER { work(1), protect(2) }
    MAX-ACCESS	read-write
    STATUS	current
    DESCRIPTION
	"Indicates which fiber span is currently being utilized by the
	actvie laser"
    ::= { aiLCGtranActiveEntry 3 }

aiLCGtranActiveRxUtilization OBJECT-TYPE
    SYNTAX	Integer32 (0..100)
    MAX-ACCESS	read-only
    STATUS	current
    DESCRIPTION
	"Approximate percentage utilization of the fiber.  This only
	accounts for incoming (received) packets."
    ::= { aiLCGtranActiveEntry 4 }

aiLCGtranActiveTxUtilization OBJECT-TYPE
    SYNTAX	Integer32 (0..100)
    MAX-ACCESS	read-only
    STATUS	current
    DESCRIPTION
	"Approximate percentage utilization of the fiber.  This only
	accounts for outgoing (transmitted) packets."
    ::= { aiLCGtranActiveEntry 5 }

aiLCGtranActiveClockSlave OBJECT-TYPE
    SYNTAX	TruthValue
    MAX-ACCESS	read-write
    STATUS	current
    DESCRIPTION
	"True if this laser is the clock slave."
    ::= { aiLCGtranActiveEntry 6 }

aiLCGtranActiveCoolerStatus OBJECT-TYPE
    SYNTAX	INTEGER { up(1), down(2) }
    MAX-ACCESS	read-write
    STATUS	current
    DESCRIPTION
	"The state of the laser cooler.  While the cooler can be
	disabled, this will render the laser ineffective.  This object
	is primarily here for status purposes."
    ::= { aiLCGtranActiveEntry 7 }

aiLCGtranActiveTemperature OBJECT-TYPE
    SYNTAX	INTEGER { okay(1), trouble(2) }
    MAX-ACCESS	read-only
    STATUS	current
    DESCRIPTION
	"The GTRAN part is aware when it passes out of its operational
	temperature range.  This object turns to trouble(2) as soon as
	we get such a report from the GTRAN."
    ::= { aiLCGtranActiveEntry 8 }

aiLCGtranActiveRxPower OBJECT-TYPE
    SYNTAX	INTEGER { okay(1), under(2), over(3) }
    MAX-ACCESS	read-only
    STATUS	current
    DESCRIPTION
	"Input power level."
    ::= { aiLCGtranActiveEntry 9 }

aiLCGtranActiveTxPower OBJECT-TYPE
    SYNTAX	INTEGER { okay(1), under(2), over(3) }
    MAX-ACCESS	read-only
    STATUS	current
    DESCRIPTION
	"Output power level.  The GTRAN will report under(2) if its
	self monitoring indicates that the laser is not transmitting
	at full power.  over(3) is not currently used, but included
	for symmetry."
    ::= { aiLCGtranActiveEntry 10 }

aiLCGtranBackupTable OBJECT-TYPE
    SYNTAX      SEQUENCE OF AiLCGtranBackupEntry
    MAX-ACCESS  not-accessible
    STATUS      current
    DESCRIPTION
	""
    ::= { aiLuxConnect 2 }

aiLCGtranBackupEntry OBJECT-TYPE
    SYNTAX      AiLCGtranBackupEntry
    MAX-ACCESS  not-accessible
    STATUS      current
    DESCRIPTION
	""
    INDEX { aiLCGtranBackupIndex }
    ::= { aiLCGtranBackupTable 1 }

AiLCGtranBackupEntry ::=
    SEQUENCE {
	aiLCGtranBackupIndex		InterfaceIndex,
	aiLCGtranBackupActiveIndex	InterfaceIndex
    }

aiLCGtranBackupIndex OBJECT-TYPE
    SYNTAX	InterfaceIndex
    MAX-ACCESS	read-only
    STATUS	current
    DESCRIPTION
	"Index of this object in the current table.  Since this table
	entry is an extension of the ifTable, this should object
	should have the same value as the corresponding ifIndex."
    ::= { aiLCGtranBackupEntry 1 }

aiLCGtranBackupActiveIndex OBJECT-TYPE
    SYNTAX	InterfaceIndex
    MAX-ACCESS	read-only
    STATUS	current
    DESCRIPTION
	"Index of the corresponding active laser."
    ::= { aiLCGtranBackupEntry 2 }

-- Information on the 1G Ethernet Interfaces

aiLcGbicTable OBJECT-TYPE
    SYNTAX      SEQUENCE OF AiLCGbicEntry
    MAX-ACCESS  not-accessible
    STATUS      current
    DESCRIPTION
	"Information on the GBIC interfaces"
    ::= { aiLuxConnect 3 }

aiLCGbicEntry OBJECT-TYPE
    SYNTAX      AiLCGbicEntry
    MAX-ACCESS  not-accessible
    STATUS      current
    DESCRIPTION
	"Information on a given GBIC"
    INDEX { aiLCGbicIndex }
    ::= { aiLcGbicTable 1 }

AiLCGbicEntry ::=
    SEQUENCE {
	aiLCGbicIndex			InterfaceIndex,
	aiLCGbicConnectorType		AIIConnType,
	aiLCGbicTxMode			INTEGER,
	aiLCGbicRxUtilization		Integer32,
	aiLCGbicTxUtilization		Integer32
    }

aiLCGbicIndex OBJECT-TYPE
    SYNTAX	InterfaceIndex
    MAX-ACCESS	read-only
    STATUS	current
    DESCRIPTION
	"Index of this object in the current table.  Since this table
	entry is an extension of the ifTable, this should object
	should have the same value as the corresponding ifIndex."
    ::= { aiLCGbicEntry 1 }

aiLCGbicConnectorType OBJECT-TYPE
    SYNTAX      AIIConnType
    MAX-ACCESS  read-only
    STATUS      current
    DESCRIPTION
	"Type of connector in this GBIC slot."
    ::= { aiLCGbicEntry 2 }

aiLCGbicTxMode OBJECT-TYPE
    SYNTAX	INTEGER { down(1),
			  up(2),
			  gtran(3) }
    MAX-ACCESS	read-write
    STATUS	current
    DESCRIPTION
	"The true administrative state of this interface.  down(1) and
	up(2) carry the same semantics as ifAdminStatus.  gtran(3) is
	used when this interface should only be operational if the
	gtran device is capable of passing packets.  Note that the
	test status of the device is not truly orthogonal to this
	variable and is set separately.  However, setting that
	variable may effect the state of this one."
    ::= { aiLCGbicEntry 3 }

aiLCGbicRxUtilization OBJECT-TYPE
    SYNTAX	Integer32 (0..100)
    MAX-ACCESS	read-only
    STATUS	current
    DESCRIPTION
	"Approximate percentage utilization of the fiber.  This only
	accounts for incoming (received) packets."
    ::= { aiLCGbicEntry 4 }

aiLCGbicTxUtilization OBJECT-TYPE
    SYNTAX	Integer32 (0..100)
    MAX-ACCESS	read-only
    STATUS	current
    DESCRIPTION
	"Approximate percentage utilization of the fiber.  This only
	accounts for outgoing (transmitted) packets."
    ::= { aiLCGbicEntry 5 }

END
