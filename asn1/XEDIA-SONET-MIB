XEDIA-SONET-MIB DEFINITIONS ::= BEGIN

IMPORTS 
    MODULE-IDENTITY, OBJECT-TYPE
        FROM SNMPv2-SMI
    TEXTUAL-CONVENTION
        FROM SNMPv2-TC
    sonetMediumEntry, 
    sonetSectionCurrentEntry, sonetSectionIntervalEntry, 
    sonetLineCurrentEntry, sonetLineIntervalEntry,
    sonetPathCurrentEntry, sonetPathIntervalEntry
        FROM SONET-MIB 
    MODULE-COMPLIANCE, OBJECT-GROUP
        FROM SNMPv2-CONF
    xediaMibs
        FROM XEDIA-REG
    ;    

xediaSonetMIB MODULE-IDENTITY
    LAST-UPDATED "9810141434Z" -- October 14, 1998
    ORGANIZATION "Xedia Corp."
    CONTACT-INFO
        "support@xedia.com"
    DESCRIPTION
        "This module defines additional objects for management of SONET 
        links in Xedia devices, above and beyond what is defined in the
        standard SONET mib."
    ::= { xediaMibs 25 }

-- Top-level organization of the MIB

xSonetObjects          OBJECT IDENTIFIER ::= { xediaSonetMIB 1 }
xSonetTables           OBJECT IDENTIFIER ::= { xediaSonetMIB 2 }
xSonetConformance      OBJECT IDENTIFIER ::= { xediaSonetMIB 3 }

-- Textual Conventions

XSonetSectionStatus ::= TEXTUAL-CONVENTION
        STATUS  current
        DESCRIPTION
                "This type is a bit string representing a sum of section conditions, 
                 therefore, it can indicate multiple failures
                 simultaneously. The value sonetSectionNoDefect is set if and only if no
                 other flag is set."
        REFERENCE
                "SONET MIB sonetSectionCurrentStatus"
        SYNTAX  BIT STRING {
                    sonetSectionNoDefect(0),     -- No alarm present
                    sonetSectionLOS(1),          -- Loss of Signal failure state
                    sonetSectionLOF(2)           -- Loss of Framing failure state
                }

XSonetLineStatus ::= TEXTUAL-CONVENTION
        STATUS  current
        DESCRIPTION
                "This type is a bit string representing a sum of line conditions, 
                 therefore, it can indicate multiple failures
                 simultaneously. The value sonetNoAlarm is set if and only if no
                 other flag is set."
        REFERENCE
                "SONET MIB sonetLineCurrentStatus"
        SYNTAX  BIT STRING {
                    sonetLineNoDefect(0),     -- No alarm present
                    sonetLineAIS(1),          -- Receiving AIS failure state
                    sonetLineRDI(2)           -- Receiving RDI (remote defect indication)
                }

XSonetPathStatus ::= TEXTUAL-CONVENTION
        STATUS  current
        DESCRIPTION
                "This type is a bit string representing a sum of path conditions, 
                 therefore, it can indicate multiple failures
                 simultaneously. The value sonetNoAlarm is set if and only if no
                 other flag is set."
        REFERENCE
                "SONET MIB sonetPathCurrentStatus"
        SYNTAX  BIT STRING {
                    sonetPathNoDefect(0),     -- No alarm present
                    sonetPathSTSLOP(1),       -- Receiving Loss of Pointer failure state
                    sonetPathSTSAIS(2),       -- Receiving AIS failure state
                    sonetPathRDI(3),          -- Receiving RDI (remote defect indication)
                    sonetPathUnequipped(4),   -- Receiving UnEQ failure state
                    sonetPathSignalLabelMismatch(5) -- Receiving wrong signal label
                }


-- ***************************************
-- Extensions to the SONET 'Medium' Table
-- ***************************************

xSonetMediumTable        OBJECT-TYPE
    SYNTAX      SEQUENCE OF XSonetMediumEntry
    MAX-ACCESS  not-accessible
    STATUS      current
    DESCRIPTION
            "The Xedia SONET Medium table contains extensions to
             the SONET Medium table."
    ::= { xSonetTables 1 }

xSonetMediumEntry        OBJECT-TYPE
    SYNTAX      XSonetMediumEntry
    MAX-ACCESS  not-accessible
    STATUS      current
    DESCRIPTION
            "An entry in the Xedia SONET Medium table."
    AUGMENTS    { sonetMediumEntry }
    ::= { xSonetMediumTable 1 }

XSonetMediumEntry ::=
    SEQUENCE {
        xsonetTransmitClockSource INTEGER,
        xsonetLoopbackConfig     INTEGER,
        xsonetSectionStatus  XSonetSectionStatus,
        xsonetLineStatus  XSonetLineStatus,
        xsonetPathStatus  XSonetPathStatus
    }

     xsonetTransmitClockSource OBJECT-TYPE
          SYNTAX  INTEGER {
                     external(1),
                     internal(2)
                 }
          MAX-ACCESS  read-write
          STATUS  current
          DESCRIPTION
                 "The source of Transmit Clock.

                 external indicates that the recovered receive clock
                 is used as the transmit clock.

                 internal indicates that a local clock source is
                 used."
               DEFVAL { internal }
               ::= { xSonetMediumEntry 1 }

xsonetLoopbackConfig OBJECT-TYPE
    SYNTAX      INTEGER {  
                    sonetNoLoop(1),
                    sonetLineLoop(2),
                    sonetOtherLoop(3),
                    sonetInwardLoop(4),
                    sonetDualLoop(5)
            }
    MAX-ACCESS  read-write
    STATUS      current
    DESCRIPTION
        "The current loopback setting of the interface."
    ::= { xSonetMediumEntry 2 }


xsonetSectionStatus  OBJECT-TYPE
    SYNTAX      XSonetSectionStatus
    MAX-ACCESS  read-only
    STATUS      current
    DESCRIPTION
           "The current section status, a bitwise OR of current
            fault indications or NO_DEFECT if no fault is present."
    ::= { xSonetMediumEntry 3 }


xsonetLineStatus  OBJECT-TYPE
    SYNTAX      XSonetLineStatus
    MAX-ACCESS  read-only
    STATUS      current
    DESCRIPTION
           "The current line status, a bitwise OR of current
            fault indications or NO_DEFECT if no fault is present."
    ::= { xSonetMediumEntry 4 }


xsonetPathStatus  OBJECT-TYPE
    SYNTAX      XSonetPathStatus
    MAX-ACCESS  read-only
    STATUS      current
    DESCRIPTION
           "The current path status, a bitwise OR of current
            fault indications or NO_DEFECT if no fault is present."
    ::= { xSonetMediumEntry 5 }


-- ***********************************************
-- Extensions to the SONET 'Section Current' Table
-- ***********************************************

xSonetSectionCurrentTable        OBJECT-TYPE
    SYNTAX      SEQUENCE OF XSonetSectionCurrentEntry
    MAX-ACCESS  not-accessible
    STATUS      current
    DESCRIPTION
            "The Xedia SONET SectionCurrent table contains extensions to
             the SONET SectionCurrent table which includes statistics 
             being collected for the current 15 minute interval."
    ::= { xSonetTables 2 }
 
xSonetSectionCurrentEntry        OBJECT-TYPE
    SYNTAX      XSonetSectionCurrentEntry
    MAX-ACCESS  not-accessible
    STATUS      current
    DESCRIPTION
            "An entry in the Xedia SONET SectionCurrent table."
    AUGMENTS    { sonetSectionCurrentEntry}
    ::= { xSonetSectionCurrentTable 1 }

XSonetSectionCurrentEntry ::=
    SEQUENCE {
      xsonetSectionCurrentStatus  XSonetSectionStatus
    }

xsonetSectionCurrentStatus  OBJECT-TYPE
    SYNTAX      XSonetSectionStatus
    MAX-ACCESS  read-only
    STATUS      current
    DESCRIPTION
           "The bitwise ORing of the sonetSectionCurrentStatus values (local 
            section status) encountered during the current 15 
            minute interval. This object is useful in identifying 
            all xsonetSectionStatus conditions which occured during
            the interval including the NO_DEFECT condition."
    ::= { xSonetSectionCurrentEntry 1 }


-- ***********************************************
-- Extensions to the SONET 'Section Interval' Table
-- ***********************************************

xSonetSectionIntervalTable        OBJECT-TYPE
    SYNTAX      SEQUENCE OF XSonetSectionIntervalEntry
    MAX-ACCESS  not-accessible
    STATUS      current
    DESCRIPTION
            "The Xedia SONET SectionInterval Table contains extensions to 
             the SONET SectionInterval table which includes statistics 
             collected over the previous 24 hours of operation.
             The past 24 hours are broken into 96 completed 15 
             minute intervals."
    ::= { xSonetTables 3 }
 
xSonetSectionIntervalEntry        OBJECT-TYPE
    SYNTAX      XSonetSectionIntervalEntry
    MAX-ACCESS  not-accessible
    STATUS      current
    DESCRIPTION
            "An entry in the Xedia SONET Section Interval Table."
    AUGMENTS    { sonetSectionIntervalEntry}
    ::= { xSonetSectionIntervalTable 1 }

XSonetSectionIntervalEntry ::=
    SEQUENCE {
      xsonetSectionIntervalStatus  XSonetSectionStatus
    }

xsonetSectionIntervalStatus  OBJECT-TYPE
    SYNTAX      XSonetSectionStatus
    MAX-ACCESS  read-only
    STATUS      current
    DESCRIPTION
           "The bitwise ORing of the sonetSectionStatus values (local 
            section status) encountered during the interval."
    ::= { xSonetSectionIntervalEntry 1 }


-- ***********************************************
-- Extensions to the SONET 'Line Current' Table
-- ***********************************************

xSonetLineCurrentTable        OBJECT-TYPE
    SYNTAX      SEQUENCE OF XSonetLineCurrentEntry
    MAX-ACCESS  not-accessible
    STATUS      current
    DESCRIPTION
            "The Xedia SONET LineCurrent table contains extensions to
             the SONET LineCurrent table which includes statistics 
             being collected for the current 15 minute interval."
    ::= { xSonetTables 5 }
 
xSonetLineCurrentEntry        OBJECT-TYPE
    SYNTAX      XSonetLineCurrentEntry
    MAX-ACCESS  not-accessible
    STATUS      current
    DESCRIPTION
            "An entry in the Xedia SONET LineCurrent table."
    AUGMENTS    { sonetLineCurrentEntry}
    ::= { xSonetLineCurrentTable 1 }

XSonetLineCurrentEntry ::=
    SEQUENCE {
      xsonetLineCurrentStatus  XSonetLineStatus
    }

xsonetLineCurrentStatus  OBJECT-TYPE
    SYNTAX      XSonetLineStatus
    MAX-ACCESS  read-only
    STATUS      current
    DESCRIPTION
           "The bitwise ORing of the sonetLineCurrentStatus values (local 
            line status) encountered during the current 15 
            minute interval. This object is useful in identifying 
            all xsonetLineStatus conditions which occured during
            the interval including the NO_DEFECT condition."
    ::= { xSonetLineCurrentEntry 1 }


-- ***********************************************
-- Extensions to the SONET 'Line Interval' Table
-- ***********************************************

xSonetLineIntervalTable        OBJECT-TYPE
    SYNTAX      SEQUENCE OF XSonetLineIntervalEntry
    MAX-ACCESS  not-accessible
    STATUS      current
    DESCRIPTION
            "The Xedia SONET LineInterval Table contains extensions to 
             the SONET LineInterval table which includes statistics 
             collected over the previous 24 hours of operation.
             The past 24 hours are broken into 96 completed 15 
             minute intervals."
    ::= { xSonetTables 6 }
 
xSonetLineIntervalEntry        OBJECT-TYPE
    SYNTAX      XSonetLineIntervalEntry
    MAX-ACCESS  not-accessible
    STATUS      current
    DESCRIPTION
            "An entry in the Xedia SONET Line Interval Table."
    AUGMENTS    { sonetLineIntervalEntry}
    ::= { xSonetLineIntervalTable 1 }

XSonetLineIntervalEntry ::=
    SEQUENCE {
      xsonetLineIntervalStatus  XSonetLineStatus
    }

xsonetLineIntervalStatus  OBJECT-TYPE
    SYNTAX      XSonetLineStatus
    MAX-ACCESS  read-only
    STATUS      current
    DESCRIPTION
           "The bitwise ORing of the sonetLineStatus values (local 
            line status) encountered during the interval."
    ::= { xSonetLineIntervalEntry 1 }


-- ***********************************************
-- Extensions to the SONET 'Path Current' Table
-- ***********************************************

xSonetPathCurrentTable        OBJECT-TYPE
    SYNTAX      SEQUENCE OF XSonetPathCurrentEntry
    MAX-ACCESS  not-accessible
    STATUS      current
    DESCRIPTION
            "The Xedia SONET PathCurrent table contains extensions to
             the SONET PathCurrent table which includes statistics 
             being collected for the current 15 minute interval."
    ::= { xSonetTables 8 }
 
xSonetPathCurrentEntry        OBJECT-TYPE
    SYNTAX      XSonetPathCurrentEntry
    MAX-ACCESS  not-accessible
    STATUS      current
    DESCRIPTION
            "An entry in the Xedia SONET PathCurrent table."
    AUGMENTS    { sonetPathCurrentEntry}
    ::= { xSonetPathCurrentTable 1 }

XSonetPathCurrentEntry ::=
    SEQUENCE {
      xsonetPathCurrentStatus  XSonetPathStatus
    }

xsonetPathCurrentStatus  OBJECT-TYPE
    SYNTAX      XSonetPathStatus
    MAX-ACCESS  read-only
    STATUS      current
    DESCRIPTION
           "The bitwise ORing of the sonetPathCurrentStatus values (local 
            path status) encountered during the current 15 
            minute interval. This object is useful in identifying 
            all xsonetPathStatus conditions which occured during
            the interval including the NO_DEFECT condition."
    ::= { xSonetPathCurrentEntry 1 }


-- ***********************************************
-- Extensions to the SONET 'Path Interval' Table
-- ***********************************************

xSonetPathIntervalTable        OBJECT-TYPE
    SYNTAX      SEQUENCE OF XSonetPathIntervalEntry
    MAX-ACCESS  not-accessible
    STATUS      current
    DESCRIPTION
            "The Xedia SONET PathInterval Table contains extensions to 
             the SONET PathInterval table which includes statistics 
             collected over the previous 24 hours of operation.
             The past 24 hours are broken into 96 completed 15 
             minute intervals."
    ::= { xSonetTables 9 }
 
xSonetPathIntervalEntry        OBJECT-TYPE
    SYNTAX      XSonetPathIntervalEntry
    MAX-ACCESS  not-accessible
    STATUS      current
    DESCRIPTION
            "An entry in the Xedia SONET Path Interval Table."
    AUGMENTS    { sonetPathIntervalEntry}
    ::= { xSonetPathIntervalTable 1 }

XSonetPathIntervalEntry ::=
    SEQUENCE {
      xsonetPathIntervalStatus  XSonetPathStatus
    }

xsonetPathIntervalStatus  OBJECT-TYPE
    SYNTAX      XSonetPathStatus
    MAX-ACCESS  read-only
    STATUS      current
    DESCRIPTION
           "The bitwise ORing of the sonetPathStatus values (local 
            path status) encountered during the interval."
    ::= { xSonetPathIntervalEntry 1 }


-- ****************************************************************
-- Conformance Information
-- ****************************************************************

xSonetCompliances OBJECT IDENTIFIER ::= { xSonetConformance 1 }
xSonetGroups      OBJECT IDENTIFIER ::= { xSonetConformance 2 }

--
-- Compliance Statements
--

xSonetCompliance MODULE-COMPLIANCE
    STATUS      current
    DESCRIPTION
        "The compliance statement for all agents that support this
        MIB. A compliant agent implements all objects defined in this
        MIB."
    MODULE  -- this module
    MANDATORY-GROUPS {
        xSonetAllGroup
    }
    ::= { xSonetCompliances 1 }

--
-- All Object Groups
--
xSonetAllGroup OBJECT-GROUP
    OBJECTS {
      xsonetTransmitClockSource,
      xsonetLoopbackConfig,

      xsonetSectionCurrentStatus,
      xsonetSectionIntervalStatus,

      xsonetLineCurrentStatus,
      xsonetLineIntervalStatus,

      xsonetPathCurrentStatus,
      xsonetPathIntervalStatus
    }
    STATUS      current
    DESCRIPTION
        "The set of all accessible objects in this MIB."
    ::= { xSonetGroups 1 }

END
