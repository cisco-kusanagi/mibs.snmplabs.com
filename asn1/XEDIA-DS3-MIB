XEDIA-DS3-MIB DEFINITIONS ::= BEGIN

IMPORTS 
    MODULE-IDENTITY, OBJECT-TYPE
        FROM SNMPv2-SMI
    TEXTUAL-CONVENTION
        FROM SNMPv2-TC
    dsx3ConfigEntry, dsx3CurrentEntry, dsx3IntervalEntry, dsx3TotalEntry
    FROM DS3-MIB 
    PerfCurrentCount, PerfIntervalCount, PerfTotalCount
    FROM PerfHist-TC-MIB    
    MODULE-COMPLIANCE, OBJECT-GROUP
        FROM SNMPv2-CONF
    xediaMibs
        FROM XEDIA-REG
    ;    

xediaDs3MIB MODULE-IDENTITY
    LAST-UPDATED "9712072155Z" -- December 27, 1997
    ORGANIZATION "Xedia Corp."
    CONTACT-INFO
        "support@xedia.com"
    DESCRIPTION
        "This module defines additional objects for management of DS3 
        links in Xedia devices, above and beyond what is defined in the
        standard DS3 mib, and proposed drafts."
    ::= { xediaMibs 11 }

-- Top-level organization of the MIB

xDs3Objects          OBJECT IDENTIFIER ::= { xediaDs3MIB 1 }
xDs3Tables           OBJECT IDENTIFIER ::= { xediaDs3MIB 2 }
xDs3Conformance      OBJECT IDENTIFIER ::= { xediaDs3MIB 3 }

-- Textual Conventions

XDsx3LineStatus ::= TEXTUAL-CONVENTION
        STATUS  current
        DESCRIPTION
                "This type is a bit string representing a sum of line conditions, 
                 therefore, it can indicate multiple failures and loopback 
                 simultaneously. The value dsx3NoAlarm is set if and only if no
                 other flag is set."
        REFERENCE
                "DS3 MIB dsx3LineStatus"
        SYNTAX  BIT STRING {
                    dsx3NoAlarm(0),          -- No alarm present
                    dsx3RcvRAIFailure(1),    -- Receiving Yellow/Remote
                                             --   Alarm Indication
                    dsx3XmitRAIAlarm(2),     -- Transmitting Yellow/Remote
                                             --   Alarm Indication
                    dsx3RcvAIS(3),           -- Receiving AIS failure state
                    dsx3XmitAIS(4),          -- Transmitting AIS
                    dsx3LOF(5),              -- Receiving LOF failure state
                    dsx3LOS(6),              -- Receiving LOS failure state
                    dsx3LoopbackState(7),    -- Looping the received signal
                    dsx3RcvTestCode(8),      -- Receiving a Test Pattern
                    dsx3OtherFailure(9),     -- Any line status not defined
                                             --   here
                    dsx3UnavailSigState(10), -- Near End in Unavailable Signal
                                             --   State
                    dsx3NetEquipOOS(11)      -- Carrier Equipment Out of Service
                }


-- ***************************************
-- Extensions to the DS3 'Config' Table
-- ***************************************

xDsx3ConfigTable        OBJECT-TYPE
    SYNTAX      SEQUENCE OF XDsx3ConfigEntry
    MAX-ACCESS  not-accessible
    STATUS      current
    DESCRIPTION
            "The Xedia DS3 Config table contains extensions to
             the DS3 Config table."
    ::= { xDs3Tables 1 }

xDsx3ConfigEntry        OBJECT-TYPE
    SYNTAX      XDsx3ConfigEntry
    MAX-ACCESS  not-accessible
    STATUS      current
    DESCRIPTION
            "An entry in the Xedia DS3 Config table."
    AUGMENTS    { dsx3ConfigEntry }
    ::= { xDsx3ConfigTable 1 }

XDsx3ConfigEntry ::=
    SEQUENCE {
        xdsx3LineStatus         XDsx3LineStatus,
        xdsx3LoopbackStatus     BIT STRING,
        xdsx3Scrambling         INTEGER
    }

xdsx3LineStatus OBJECT-TYPE
  SYNTAX        XDsx3LineStatus
    MAX-ACCESS  read-only
    STATUS      current
    DESCRIPTION
        "Indicates the line status of the interface. This obect 
         is identical to dsx3LineStatus in the DS3 MIB except
         that it uses the SNMPv2 BIT STRING object type."
    ::= { xDsx3ConfigEntry 1 }


xdsx3LoopbackStatus OBJECT-TYPE
    SYNTAX      BIT STRING {  
                    dsx3NoLoopback(0),
                    dsx3NearEndPayloadLoopback(1),
                    dsx3NearEndLineLoopback(2),
                    dsx3NearEndOtherLoopback(3),
                    dsx3NearEndInwardLoopback(4),
                    dsx3FarEndPayloadLoopback(5),
                    dsx3FarEndLineLoopback(6)
            }
    MAX-ACCESS  read-only
    STATUS      current
    DESCRIPTION
        "Indicates the local and remote loopback status of the 
         interface. This object is identical to dsx3LoopbackStatus
         in the DS3 MIB except that it uses the SNMPv2 BIT STRING 
         object type."
    ::= { xDsx3ConfigEntry 2 }


xdsx3Scrambling OBJECT-TYPE
    SYNTAX      INTEGER {
                  dsx3None(1),
                  dsx3Cisco(2),
                  dsx3Kentrox(3)
                  }
    MAX-ACCESS  read-write
    STATUS      current
    DESCRIPTION
    "The status of payload scrambling type
    is enabled at the data port."
    DEFVAL      { dsx3None }
    ::= { xDsx3ConfigEntry 3 }


-- ***************************************
-- Extensions to the DS3 'Current' Table
-- ***************************************

xDsx3CurrentTable        OBJECT-TYPE
    SYNTAX      SEQUENCE OF XDsx3CurrentEntry
    MAX-ACCESS  not-accessible
    STATUS      current
    DESCRIPTION
            "The Xedia DS3 Current table contains extensions to
             the DS3 Current table which includes statistics 
             being collected for the current 15 minute interval."
    ::= { xDs3Tables 2 }
 
xDsx3CurrentEntry        OBJECT-TYPE
    SYNTAX      XDsx3CurrentEntry
    MAX-ACCESS  not-accessible
    STATUS      current
    DESCRIPTION
            "An entry in the Xedia DS3 Current table."
    AUGMENTS    { dsx3CurrentEntry}
    ::= { xDsx3CurrentTable 1 }

XDsx3CurrentEntry ::=
    SEQUENCE {
      xdsx3CurrentFBEs             PerfCurrentCount,
      xdsx3CurrentFEBEs            PerfCurrentCount,
      xdsx3CurrentPBESs            PerfCurrentCount,
      xdsx3CurrentCBESs            PerfCurrentCount,

      xdsx3CurrentLocalLineStatus  XDsx3LineStatus,
      xdsx3CurrentRemoteLineStatus XDsx3LineStatus
    }

xdsx3CurrentFBEs OBJECT-TYPE
    SYNTAX      PerfCurrentCount
    MAX-ACCESS  read-only
    STATUS      current
    DESCRIPTION
           "The number of F and M Frame Bit Errored Seconds 
            encountered during the current 15 minute interval."
    ::= { xDsx3CurrentEntry 1 }

xdsx3CurrentFEBEs OBJECT-TYPE
    SYNTAX      PerfCurrentCount
    MAX-ACCESS  read-only
    STATUS      current
    DESCRIPTION
           "The number of Far End Block Errors encountered
            in the current 15 minute interval."
    ::= {  xDsx3CurrentEntry 2 }

xdsx3CurrentPBESs OBJECT-TYPE
    SYNTAX      PerfCurrentCount
    MAX-ACCESS  read-only
    STATUS      current
    DESCRIPTION
           "The number of P-Bit Bursty Errored Seconds (PBES) 
            encountered during the current 15 minute interval.
            
            A PBES is a second with more than 1 and less than
            45 ocurring p-bit coding violations and NO Out of 
            Frame defects nor detected incoming AIS. This gauge 
            is not incremented when UASs are counted."
    ::= {  xDsx3CurrentEntry 3 }

xdsx3CurrentCBESs OBJECT-TYPE
    SYNTAX      PerfCurrentCount
    MAX-ACCESS  read-only
    STATUS      current
    DESCRIPTION
           "The number of C-Bit Bursty Errored Seconds (CBES) 
            encountered during the current 15 minute interval.
            
            A CBES is a second with more than 1 and less than
            45 ocurring c-bit coding violations and NO Out of 
            Frame defects nor detected incoming AIS. This gauge 
            is not incremented when UASs are counted."
    ::= {  xDsx3CurrentEntry 4 }

xdsx3CurrentLocalLineStatus  OBJECT-TYPE
    SYNTAX      XDsx3LineStatus
    MAX-ACCESS  read-only
    STATUS      current
    DESCRIPTION
           "The bitwise ORing of the dsx3LineStatus values (local 
            line status) encountered during the current 15 
            minute interval. This object is useful in identifying 
            all xdsx3LineStatus conditions which occured during
            the interval including the NO_ALARM condition."
    ::= { xDsx3CurrentEntry 5 }

xdsx3CurrentRemoteLineStatus  OBJECT-TYPE
    SYNTAX      XDsx3LineStatus
    MAX-ACCESS  read-only
    STATUS      current
    DESCRIPTION
           "The bitwise ORing of the far end dsx3LineStatus values 
            (remote line status) encountered during the current 15 
            minute interval. This object is useful in identifying 
            all dsx3LineStatus conditions which occured during the
            interval including the NO_ALARM condition."
    ::= { xDsx3CurrentEntry 6 }


-- ***************************************
-- Extensions to the DS3 'Interval' Table
-- ***************************************

xDsx3IntervalTable        OBJECT-TYPE
    SYNTAX      SEQUENCE OF XDsx3IntervalEntry
    MAX-ACCESS  not-accessible
    STATUS      current
    DESCRIPTION
            "The Xedia DS3 Interval Table contains extensions to 
             the DS3 Interval table which includes statistics 
             collected over the previous 24 hours of operation.
             The past 24 hours are broken into 96 completed 15 
             minute intervals."
    ::= { xDs3Tables 3 }
 
xDsx3IntervalEntry        OBJECT-TYPE
    SYNTAX      XDsx3IntervalEntry
    MAX-ACCESS  not-accessible
    STATUS      current
    DESCRIPTION
            "An entry in the Xedia DS3 Interval Table."
    AUGMENTS    { dsx3IntervalEntry}
    ::= { xDsx3IntervalTable 1 }

XDsx3IntervalEntry ::=
    SEQUENCE {
      xdsx3IntervalFBEs             PerfIntervalCount,
      xdsx3IntervalFEBEs            PerfIntervalCount,
      xdsx3IntervalPBESs            PerfIntervalCount,
      xdsx3IntervalCBESs            PerfIntervalCount,

      xdsx3IntervalLocalLineStatus  XDsx3LineStatus,
      xdsx3IntervalRemoteLineStatus XDsx3LineStatus
    }

xdsx3IntervalFBEs OBJECT-TYPE
    SYNTAX      PerfIntervalCount
    MAX-ACCESS  read-only
    STATUS      current
    DESCRIPTION
           "The number of F and M Frame Bit Errored Seconds 
            encountered during the interval."
    ::= { xDsx3IntervalEntry 1 }

xdsx3IntervalFEBEs OBJECT-TYPE
    SYNTAX      PerfIntervalCount
    MAX-ACCESS  read-only
    STATUS      current
    DESCRIPTION
           "The number of Far End Block Errors encountered
            during the interval."
    ::= {  xDsx3IntervalEntry 2 }

xdsx3IntervalPBESs OBJECT-TYPE
    SYNTAX      PerfIntervalCount
    MAX-ACCESS  read-only
    STATUS      current
    DESCRIPTION
           "The number of P-Bit Bursty Errored Seconds (PBES) 
            encountered during the interval."
    ::= {  xDsx3IntervalEntry 3 }

xdsx3IntervalCBESs OBJECT-TYPE
    SYNTAX      PerfIntervalCount
    MAX-ACCESS  read-only
    STATUS      current
    DESCRIPTION
           "The number of C-Bit Bursty Errored Seconds (CBES) 
            encountered during the interval."
    ::= {  xDsx3IntervalEntry 4 }

xdsx3IntervalLocalLineStatus  OBJECT-TYPE
    SYNTAX      XDsx3LineStatus
    MAX-ACCESS  read-only
    STATUS      current
    DESCRIPTION
           "The bitwise ORing of the dsx3LineStatus values (local 
            line status) encountered during the interval."
    ::= { xDsx3IntervalEntry 5 }

xdsx3IntervalRemoteLineStatus  OBJECT-TYPE
    SYNTAX    XDsx3LineStatus
    MAX-ACCESS  read-only
    STATUS      current
    DESCRIPTION
           "The bitwise ORing of the far end dsx3LineStatus values 
            (remote line status) encountered during the interval."
    ::= { xDsx3IntervalEntry 6 }

-- ***************************************
-- Extensions to the DS3 'Total' Table
-- ***************************************

xDsx3TotalTable        OBJECT-TYPE
    SYNTAX      SEQUENCE OF XDsx3TotalEntry
    MAX-ACCESS  not-accessible
    STATUS      current
    DESCRIPTION
            "The Xedia DS3 Total Table contains extensions to the
             DS3 Total table which includes cumulative sums of the 
             various statistics for the 24 hour period preceding 
             the current interval. Invalid 15 minute intervals count 
             as 0."
    ::= { xDs3Tables 4 }
 
xDsx3TotalEntry        OBJECT-TYPE
    SYNTAX      XDsx3TotalEntry
    MAX-ACCESS  not-accessible
    STATUS      current
    DESCRIPTION
            "An entry in the Xedai DS3 Total Table."
    AUGMENTS    { dsx3TotalEntry}
    ::= { xDsx3TotalTable 1 }

XDsx3TotalEntry ::=
    SEQUENCE {
      xdsx3TotalFBEs             PerfTotalCount,
      xdsx3TotalFEBEs            PerfTotalCount,
      xdsx3TotalPBESs            PerfTotalCount,
      xdsx3TotalCBESs            PerfTotalCount,

      xdsx3TotalLocalLineStatus  XDsx3LineStatus,
      xdsx3TotalRemoteLineStatus XDsx3LineStatus
    }
 
xdsx3TotalFBEs OBJECT-TYPE
    SYNTAX      PerfTotalCount
    MAX-ACCESS  read-only
    STATUS      current
    DESCRIPTION
           "The sum of F and M Frame Bit Errored Seconds 
            for all intervals in the interval table."
    ::= { xDsx3TotalEntry 1 }

xdsx3TotalFEBEs OBJECT-TYPE
    SYNTAX      PerfTotalCount
    MAX-ACCESS  read-only
    STATUS      current
    DESCRIPTION
           "The sum of Far End Block Errors for all intervals
            in the interval table."
    ::= {  xDsx3TotalEntry 2 }

xdsx3TotalPBESs OBJECT-TYPE
    SYNTAX      PerfTotalCount
    MAX-ACCESS  read-only
    STATUS      current
    DESCRIPTION
           "The sum of P-Bit Bursty Errored Seconds (PBES)
            for all intervals in the interval table."
    ::= {  xDsx3TotalEntry 3 }

xdsx3TotalCBESs OBJECT-TYPE
    SYNTAX      PerfTotalCount
    MAX-ACCESS  read-only
    STATUS      current
    DESCRIPTION
           "The sum of C-Bit Bursty Errored Seconds (CBES)
            for all intervals in the interval table."
    ::= {  xDsx3TotalEntry 4 }

xdsx3TotalLocalLineStatus  OBJECT-TYPE
    SYNTAX    XDsx3LineStatus
    MAX-ACCESS  read-only
    STATUS      current
    DESCRIPTION
           "The bitwise ORing of the dsx3LineStatus values (local 
            line status) for all intervals in the interval table."
    ::= { xDsx3TotalEntry 5 }

xdsx3TotalRemoteLineStatus  OBJECT-TYPE
    SYNTAX    XDsx3LineStatus
    MAX-ACCESS  read-only
    STATUS      current
    DESCRIPTION
           "The bitwise ORing of the far end dsx3LineStatus values 
            (remote line status) for all intervals in the interval
            table."
    ::= { xDsx3TotalEntry 6 }


-- ****************************************************************
-- Conformance Information
-- ****************************************************************

xDs3Compliances OBJECT IDENTIFIER ::= { xDs3Conformance 1 }
xDs3Groups      OBJECT IDENTIFIER ::= { xDs3Conformance 2 }

--
-- Compliance Statements
--

xDs3Compliance MODULE-COMPLIANCE
    STATUS      current
    DESCRIPTION
        "The compliance statement for all agents that support this
        MIB. A compliant agent implements all objects defined in this
        MIB."
    MODULE  -- this module
    MANDATORY-GROUPS {
        xDs3AllGroup
    }
    ::= { xDs3Compliances 1 }

--
-- All Object Groups
--
xDs3AllGroup OBJECT-GROUP
    OBJECTS {
      xdsx3LineStatus,
      xdsx3LoopbackStatus,
      xdsx3Scrambling,

      xdsx3CurrentFBEs,
      xdsx3CurrentFEBEs,
      xdsx3CurrentPBESs,
      xdsx3CurrentCBESs,
      xdsx3CurrentLocalLineStatus,
      xdsx3CurrentRemoteLineStatus,

      xdsx3IntervalFBEs,
      xdsx3IntervalFEBEs,
      xdsx3IntervalPBESs,
      xdsx3IntervalCBESs,
      xdsx3IntervalLocalLineStatus,
      xdsx3IntervalRemoteLineStatus,

      xdsx3TotalFBEs,
      xdsx3TotalFEBEs,
      xdsx3TotalPBESs,
      xdsx3TotalCBESs,
      xdsx3TotalLocalLineStatus,
      xdsx3TotalRemoteLineStatus
    }
    STATUS      current
    DESCRIPTION
        "The set of all accessible objects in this MIB."
    ::= { xDs3Groups 1 }

END
