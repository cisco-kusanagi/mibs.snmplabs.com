--
--          Computer Network Technology, Corp.
--          6000 Nathan Lane North 
--          Plymouth, Minnesota  55442   
--
--                phone:  763-268-6000
--                  fax:  763-268-6800
--              support:  1-800-752-8061 or 1-763-268-6600
--                email:  info@cnt.com
--
--
--	MIB Version:     2.9
--	Product Family:  CNT Access Units
--
--

CNTAU-MIB DEFINITIONS ::= BEGIN

	IMPORTS
		PhysAddress FROM SNMPv2-TC
		Gauge, IpAddress, enterprises, Counter
			FROM RFC1065-SMI
		OBJECT-TYPE
			FROM RFC-1212
			DisplayString FROM RFC1213-MIB
		TRAP-TYPE FROM RFC-1215;

        cnt     OBJECT IDENTIFIER ::= { enterprises 333 }
        cntau   OBJECT IDENTIFIER ::= { cnt 1 }

	--	cntsystem       OBJECT IDENTIFIER ::= { cntau 1 }
   	--	cntinterfaces   OBJECT IDENTIFIER ::= { cntau 2 }
   	--	cnticmp         OBJECT IDENTIFIER ::= { cntau 5 }
   	--	cnttransmission OBJECT IDENTIFIER ::= { cntau 10 }
   	--	cntsnmp         OBJECT IDENTIFIER ::= { cntau 11 }
	--	cntdiagnostics  OBJECT IDENTIFIER ::= { cntau 12 }
	--	cntdatalink     OBJECT IDENTIFIER ::= { cntau 13 }
	--	cntlua          OBJECT IDENTIFIER ::= { cntau 14 }


		-- the CNT Access Units System group

		cntsystem     OBJECT IDENTIFIER ::= { cntau 1 }

		cntSysNodeAddress OBJECT-TYPE
			SYNTAX  IpAddress
			ACCESS  read-only
			STATUS  mandatory
			DESCRIPTION
				"Node address of this CNT platform.  This value
				contains the region (1 byte), the bus (1 byte),
				and the node (2 bytes)."
			::= { cntsystem 1 }

		cntSysTimeofDay OBJECT-TYPE
			SYNTAX  DisplayString
			ACCESS  read-only
			STATUS  mandatory
			DESCRIPTION
				"The date and time from Battery-Backed-up RAM
				(BBRAM)."
			::= { cntsystem 2 }

		cntSysMsgTable OBJECT-TYPE
			SYNTAX  SEQUENCE OF CntMsgEntry
			ACCESS  not-accessible
			STATUS  mandatory
			DESCRIPTION
				"List of entries in the global mail box.  This
				mail box contains any message that have been
				entered by any software residing in the node."
			::= { cntsystem 3 }

		cntMsgEntry OBJECT-TYPE
			SYNTAX  CntMsgEntry
			ACCESS  not-accessible
			STATUS  mandatory
			DESCRIPTION
				"A mail box entry."
			INDEX	{ cntMsgIndex }
			::= { cntSysMsgTable 1 }

		CntMsgEntry ::= SEQUENCE {
			cntMsgIndex
				INTEGER,
			cntMsgSeverity
				INTEGER,
			cntMsgTaskName
				DisplayString,
			cntMsgNumber
				INTEGER,
			cntMsgCpuNumber
				INTEGER,
			cntMsgNodeNumber
				DisplayString,
			cntMsgDateTime
				DisplayString,
			cntMsgContent
				DisplayString,
			cntMsgSeqNumber
				INTEGER
		}

		cntMsgIndex OBJECT-TYPE
			SYNTAX  INTEGER
			ACCESS  read-only
			STATUS  mandatory
			DESCRIPTION
				"The relative index of this mail box message."
			::= { cntMsgEntry 1 }

		cntMsgSeverity OBJECT-TYPE
			SYNTAX  INTEGER {
					information-msg(1),
					possible-error(2),
					recoverable-error(3),
					fatal-error(4)
				}
			ACCESS  read-only
			STATUS  mandatory
			DESCRIPTION
				"The severity of this mail box message."
			::= { cntMsgEntry 2 }

		cntMsgTaskName OBJECT-TYPE
			SYNTAX  DisplayString
			ACCESS  read-only
			STATUS  mandatory
			DESCRIPTION
				"The name of the module that sent this message
				to the mail box."
			::= { cntMsgEntry 3 }

		cntMsgNumber OBJECT-TYPE
			SYNTAX  INTEGER
			ACCESS  read-only
			STATUS  mandatory
			DESCRIPTION
				"The number of this message.  Each module
				numbers its message type as another way of
				describing it.  This message can then be 
				cross-referenced in the CNT system messages
				reference manual."
			::= { cntMsgEntry 4 }

		cntMsgCpuNumber OBJECT-TYPE
			SYNTAX  INTEGER {
				lcp-1(1),
				lcp-2(2),
				lcp-3(3),
				lcp-4(4),
				lcp-5(5),
				lcp-6(6),
				lcp-7(7)
			}
			ACCESS  read-only
			STATUS  mandatory
			DESCRIPTION
				"The CPU of the module that sent this message
				to the mail box."
			::= { cntMsgEntry 5 }

		cntMsgNodeNumber OBJECT-TYPE
			SYNTAX  DisplayString
			ACCESS  read-only
			STATUS  mandatory
			DESCRIPTION
				"The node number of the module that sent this
				message to the mail box."
			::= { cntMsgEntry 6 }

		cntMsgDateTime OBJECT-TYPE
			SYNTAX  DisplayString
			ACCESS  read-only
			STATUS  mandatory
			DESCRIPTION
				"The date and time that this message was sent
				to the mail box."
			::= { cntMsgEntry 7 }

		cntMsgContent OBJECT-TYPE
			SYNTAX  DisplayString
			ACCESS  read-only
			STATUS  mandatory
			DESCRIPTION
				"The textual contents of the message sent to
				the mail box."
			::= { cntMsgEntry 8 }

		cntMsgSeqNumber OBJECT-TYPE
			SYNTAX  INTEGER
			ACCESS  read-only
			STATUS  mandatory
			DESCRIPTION
				"The sequence number for this message."
			::= { cntMsgEntry 9 }


		cntSysHardware OBJECT IDENTIFIER ::= { cntsystem 4 }

		cntHwBBramType OBJECT-TYPE
			SYNTAX  INTEGER {
				bbram-6500(1),
				bbram-6704(2)
			}
			ACCESS  read-only
			STATUS  mandatory
			DESCRIPTION
				"The type of battery backed up memory."
			::= { cntSysHardware 1 }
	
		cntHwBBramStatus OBJECT-TYPE
			SYNTAX  INTEGER {
				good(1),
				failing(2)
			}
			ACCESS  read-only
			STATUS  mandatory
			DESCRIPTION
				"The status of the batteries used in the BBRAM.
				A failing status indicates that one or more of
				the batteries are failing."
			::= { cntSysHardware 2 }
	
		cntHwFailedCpu OBJECT-TYPE
			SYNTAX  INTEGER {
				no-failure(1),
				lcp-1(2),
				lcp-2(3),
				lcp-3(4),
				lcp-4(5),
				lcp-5(6),
				lcp-6(7),
				lcp-7(8)
			}
			ACCESS  read-only
			STATUS  mandatory
			DESCRIPTION
				"The CPU number where a failure occurred.
				If this value is zero then there are no
				failures."
			::= { cntSysHardware 3 }
	
		cntHwMonCpu OBJECT-TYPE
			SYNTAX  INTEGER {
				no-failure(1),
				lcp-1(2),
				lcp-2(3),
				lcp-3(4),
				lcp-4(5),
				lcp-5(6),
				lcp-6(7),
				lcp-7(8)
			}
			ACCESS  read-only
			STATUS  mandatory
			DESCRIPTION
				"The CPU number of the monitor that noticed
				the CPU failure."
			::= { cntSysHardware 4 }
	
		cntHwFailStatus OBJECT-TYPE
			SYNTAX  INTEGER {
				not-up(1),
				ok(2),
				abort-switch(3),
				abort-remote(4),
				parity-error(5),
				ac-failure(6),
				system-failure(7)
			}
			ACCESS  read-only
			STATUS  mandatory
			DESCRIPTION
				"Status that the failing CPU recorded at the
				time of the failure."
			::= { cntSysHardware 5 }
	
		cntHwMonFailStatus OBJECT-TYPE
			SYNTAX  INTEGER {
				not-up(1),
				ok(2),
				failed(3),
				mdm-error(4),
				poll-error(5)
			}
			ACCESS  read-only
			STATUS  mandatory
			DESCRIPTION
				"Status that the monitoring CPU recorded at
				the time of the failure."
			::= { cntSysHardware 6 }
	
		cntHwFailDate OBJECT-TYPE
			SYNTAX  DisplayString
			ACCESS  read-only
			STATUS  mandatory
			DESCRIPTION
				"Time and date when the processor failed."
			::= { cntSysHardware 7 }
	
		cntHwReset1Why OBJECT-TYPE
			SYNTAX  DisplayString
			ACCESS  read-only
			STATUS  mandatory
			DESCRIPTION
				"The reason for the last reset."
			::= { cntSysHardware 8 }
	
		cntHwReset1Date OBJECT-TYPE
			SYNTAX  DisplayString
			ACCESS  read-only
			STATUS  mandatory
			DESCRIPTION
				"The time and date of the last reset."
			::= { cntSysHardware 9 }
	
		cntHwReset2Why OBJECT-TYPE
			SYNTAX  DisplayString
			ACCESS  read-only
			STATUS  mandatory
			DESCRIPTION
				"The reason for the second-to-last reset."
			::= { cntSysHardware 10 }
	
		cntHwReset2Date OBJECT-TYPE
			SYNTAX  DisplayString
			ACCESS  read-only
			STATUS  mandatory
			DESCRIPTION
				"The time and date of the second-to-last
				reset."
			::= { cntSysHardware 11 }
	
		cntHwReset3Why OBJECT-TYPE
			SYNTAX  DisplayString
			ACCESS  read-only
			STATUS  mandatory
			DESCRIPTION
				"The reason for the third-to-last reset."
			::= { cntSysHardware 12 }
	
		cntHwReset3Date OBJECT-TYPE
			SYNTAX  DisplayString
			ACCESS  read-only
			STATUS  mandatory
			DESCRIPTION
				"The time and date of the third-to-last reset."
			::= { cntSysHardware 13 }
	
		cntHwPowerSupply OBJECT-TYPE
			SYNTAX  INTEGER {
				good(1),
				bad(2)
			}
			ACCESS  read-only
			STATUS  mandatory
			DESCRIPTION
				"The status of the power supply or power
				supplies.  This value will indicate good
				only if all power supplies in the node are
				working.  If any fan or power supply is
				failing, this object will indicate a failure
				even if enough power is supplied to keep
				the node operating."
			::= { cntSysHardware 14 }

                cntHwCpuTable OBJECT-TYPE
                        SYNTAX  SEQUENCE OF CntHwCpuEntry
                        ACCESS  not-accessible
                        STATUS  mandatory
                        DESCRIPTION
                                "A list of CPU statistics entries.  All
                                possible CPUs for a box are accessible
                                whether or not they even exist."
                        ::= { cntSysHardware 15 }
 
                cntHwCpuEntry OBJECT-TYPE
                        SYNTAX  CntHwCpuEntry
                        ACCESS  not-accessible
                        STATUS  mandatory
                        DESCRIPTION
                                "A CPU statistics entry."
                        INDEX   { cntCpuNum }
                        ::= { cntHwCpuTable 1 }

                CntHwCpuEntry ::= SEQUENCE {
                        cntCpuNum
                                INTEGER,
                        cntCpuType
                                INTEGER,
                        cntCpuSemCount
                                INTEGER,
                        cntCpuSemLost
                                INTEGER,
                        cntCpuStatus
                                INTEGER,
                        cntCpuMonStatus
                                INTEGER,
                        cntCpuPollStatus
                                INTEGER,
                        cntCpuPolls
                                Counter,
                        cntCpuResetDelayTime
                                INTEGER,
                        cntCpuMonBy
                                INTEGER,
                        cntCpuPort
                                INTEGER,
                        cntCpuUnclaims
                                Counter,
                        cntCpuXtraInts
                                Counter,
                        cntCpuLevel7s
                                Counter,
                        cntCpuMsgRets
                                Counter,
                        cntCpuMsgHolds
                                Counter,
                        cntCpuResetFlag
                                INTEGER,
                        cntCpuUtil
                                INTEGER,
                        cntCpuLastFailDate
                                DisplayString,
                        cntCpuLastChgDate
                                DisplayString
                }

		cntCpuNum OBJECT-TYPE
			SYNTAX  INTEGER {
				lcp-1(1),
				lcp-2(2),
				lcp-3(3),
				lcp-4(4),
				lcp-5(5),
				lcp-6(6),
				lcp-7(7)
			}
			ACCESS  read-only
			STATUS  mandatory
			DESCRIPTION
				"The cpu index." 
			::= { cntHwCpuEntry 1 }
	
		cntCpuType OBJECT-TYPE
			SYNTAX  INTEGER {
				no-cpu(1),
				lcp-type1(2),
				lcp-type2(3),
				lcp-type3(4),
				lcp-type4(5)
			}
			ACCESS  read-only
			STATUS  mandatory
			DESCRIPTION
				"The type of the CPU requested."
			::= { cntHwCpuEntry 2 }

		cntCpuSemCount OBJECT-TYPE
			SYNTAX  INTEGER
			ACCESS  read-only
			STATUS  mandatory
			DESCRIPTION
				"The number of semaphores for this CPU."
			::= { cntHwCpuEntry 3 }
	
		cntCpuSemLost OBJECT-TYPE
			SYNTAX  INTEGER
			ACCESS  read-only
			STATUS  mandatory
			DESCRIPTION
				"The number of semaphores lost for this CPU."
			::= { cntHwCpuEntry 4 }
	
		cntCpuStatus OBJECT-TYPE
			SYNTAX  INTEGER {
				not-up(1),
				ok(2),
				abort-switch(3),
				abort-remote(4),
				parity-error(5),
				ac-failure(6),
				system-failure(7)
			}
			ACCESS  read-only
			STATUS  mandatory
			DESCRIPTION
				"The current known status of this CPU."
			::= { cntHwCpuEntry 5 }
	
		cntCpuMonStatus OBJECT-TYPE
			SYNTAX  INTEGER {
				not-up(1),
				ok(2),
				failed(3),
				mdm-error(4),
				poll-error(5)
			}
			ACCESS  read-only
			STATUS  mandatory
			DESCRIPTION
				"The current status of this CPU as known by
				the monitoring CPU."
			::= { cntHwCpuEntry 6 }
	
		cntCpuPollStatus OBJECT-TYPE
			SYNTAX  INTEGER {
				none(1),
				normal(2)
			}
			ACCESS  read-only
			STATUS  mandatory
			DESCRIPTION
				"The status of the current polling request for
				this CPU."
			::= { cntHwCpuEntry 7 }
	
		cntCpuPolls OBJECT-TYPE
			SYNTAX  Counter
			ACCESS  read-only
			STATUS  mandatory
			DESCRIPTION
				"The number of polls sent for this CPU."
			::= { cntHwCpuEntry 8 }
	
		cntCpuResetDelayTime OBJECT-TYPE
			SYNTAX  INTEGER
			ACCESS  read-only
			STATUS  mandatory
			DESCRIPTION
				"The reset delay time, in seconds."
			::= { cntHwCpuEntry 9 }
	
		cntCpuMonBy OBJECT-TYPE
			SYNTAX  INTEGER {
				lcp-1(1),
				lcp-2(2),
				lcp-3(3),
				lcp-4(4),
				lcp-5(5),
				lcp-6(6),
				lcp-7(7)
			}
			ACCESS  read-only
			STATUS  mandatory
			DESCRIPTION
				"The system number for the CPU monitoring
				this CPU."
			::= { cntHwCpuEntry 10 }
	
		cntCpuPort OBJECT-TYPE
			SYNTAX  INTEGER
			ACCESS  read-only
			STATUS  mandatory
			DESCRIPTION
				"The port number for this CPU."
			::= { cntHwCpuEntry 11 }
	
		cntCpuUnclaims OBJECT-TYPE
			SYNTAX  Counter
			ACCESS  read-only
			STATUS  mandatory
			DESCRIPTION
				"The number of unclaimed grant interrupts on
				the system controller CPU."
			::= { cntHwCpuEntry 12 }
	
		cntCpuXtraInts OBJECT-TYPE
			SYNTAX  Counter
			ACCESS  read-only
			STATUS  mandatory
			DESCRIPTION
				"The number of spurious interrupts."
			::= { cntHwCpuEntry 13 }
	
		cntCpuLevel7s OBJECT-TYPE
			SYNTAX  Counter
			ACCESS  read-only
			STATUS  mandatory
			DESCRIPTION
				"The number of unidentified level seven
				interrupts."
			::= { cntHwCpuEntry 14 }
	
		cntCpuMsgRets OBJECT-TYPE
			SYNTAX  Counter
			ACCESS  read-only
			STATUS  mandatory
			DESCRIPTION
				"The number of undeliverable MDM interprocessor
				 messages."
			::= { cntHwCpuEntry 15 }
	
		cntCpuMsgHolds OBJECT-TYPE
			SYNTAX  Counter
			ACCESS  read-only
			STATUS  mandatory
			DESCRIPTION
				"The number of messages held which were being
				returned to the failed processor."
			::= { cntHwCpuEntry 16 }
	
		cntCpuResetFlag OBJECT-TYPE
			SYNTAX  INTEGER {
				off(1),
				on(2)
			}
			ACCESS  read-only
			STATUS  mandatory
			DESCRIPTION
				"The value of the reset flag."
			::= { cntHwCpuEntry 17 }
	
		cntCpuUtil OBJECT-TYPE
			SYNTAX  INTEGER
			ACCESS  read-only
			STATUS  mandatory
			DESCRIPTION
				"The CPU utilization, in percent utilized."
			::= { cntHwCpuEntry 18 }
	
		cntCpuLastFailDate OBJECT-TYPE
			SYNTAX  DisplayString
			ACCESS  read-only
			STATUS  mandatory
			DESCRIPTION
				"The date and time of the last failure."
			::= { cntHwCpuEntry 19 }
	
		cntCpuLastChgDate OBJECT-TYPE
			SYNTAX  DisplayString
			ACCESS  read-only
			STATUS  mandatory
			DESCRIPTION
				"The date and time of the last change."
			::= { cntHwCpuEntry 20 }
	
		cntHwStatusLED OBJECT-TYPE
			SYNTAX  INTEGER
			ACCESS  read-only
			STATUS  mandatory
			DESCRIPTION
				"Two digit, LCD display.  During system
				initialization it indicates the processor
				that is being initialized.  Successful
				initialization is indicated by a display
				of '00'."
			::= { cntSysHardware 16 }


		cntSysBuild OBJECT IDENTIFIER ::= { cntsystem 5 }

		cntRevDate OBJECT-TYPE
			SYNTAX  IpAddress
			ACCESS  read-only
			STATUS  mandatory
			DESCRIPTION
				"The BBRAM revision date of the system
				description (!RV2) file."
			::= { cntSysBuild 1 }

		cntCustomer OBJECT-TYPE
			SYNTAX  DisplayString
			ACCESS  read-only
			STATUS  mandatory
			DESCRIPTION
				"Customer name and other identifying
				information."
			::= { cntSysBuild 2 }

		cntMachineType OBJECT-TYPE
			SYNTAX  DisplayString
			ACCESS  read-only
			STATUS  mandatory
			DESCRIPTION
				"The machine type of this node."
			::= { cntSysBuild 3 }

		cntSerialNumber OBJECT-TYPE
			SYNTAX  INTEGER
			ACCESS  read-only
			STATUS  mandatory
			DESCRIPTION
				"The machine serial number of this node."
			::= { cntSysBuild 4 }

		cntWorkOrderNumber OBJECT-TYPE
			SYNTAX  INTEGER
			ACCESS  read-only
			STATUS  mandatory
			DESCRIPTION
				"The original manufacturing build work order
				number of this node."
			::= { cntSysBuild 5 }

		cntChassisNumber OBJECT-TYPE
			SYNTAX  INTEGER
			ACCESS  read-only
			STATUS  mandatory
			DESCRIPTION
				"The machine chassis number of this node."
			::= { cntSysBuild 6 }

		cntModelNumber OBJECT-TYPE
			SYNTAX  DisplayString
			ACCESS  read-only
			STATUS  mandatory
			DESCRIPTION
				"The machine model number of this node."
			::= { cntSysBuild 7 }

		cntReleaseLevel OBJECT-TYPE
			SYNTAX  DisplayString
			ACCESS  read-only
			STATUS  mandatory
			DESCRIPTION
				"The original software release level installed
				in this node."
			::= { cntSysBuild 8 }

		cntRevEditDate OBJECT-TYPE
			SYNTAX  IpAddress
			ACCESS  read-only
			STATUS  mandatory
			DESCRIPTION
				"The date that this version of the system
				description (!RV2) file was edited
				dynamically."
			::= { cntSysBuild 9 }

		cntRevEditTime OBJECT-TYPE
			SYNTAX  IpAddress
			ACCESS  read-only
			STATUS  mandatory
			DESCRIPTION
				"The time that this version of the system
				description (!RV2) file was edited
				dynamically."
			::= { cntSysBuild 10 }

		cntFeatureTable OBJECT-TYPE
			SYNTAX  SEQUENCE OF CntFeatureEntry
			ACCESS  not-accessible
			STATUS  mandatory
			DESCRIPTION
				"The list of manufacturing features originally
				installed in this node."
			::= { cntSysBuild 11 }
               
		cntFeatureEntry OBJECT-TYPE
			SYNTAX  CntFeatureEntry
			ACCESS  not-accessible
			STATUS  mandatory
			DESCRIPTION
				"A node feature entry."
			INDEX	{ cntFeatureIndex }
			::= { cntFeatureTable 1 }

		CntFeatureEntry	::= SEQUENCE {
			cntFeatureIndex
				INTEGER,
			cntFeatureName
				DisplayString,
			cntFeatureQuantity
				INTEGER,
			cntFeatureDescr
				DisplayString
		}

		cntFeatureIndex OBJECT-TYPE
			SYNTAX  INTEGER
			ACCESS  read-only
			STATUS  mandatory
			DESCRIPTION
				"The feature index."
			::= { cntFeatureEntry 1 }

		cntFeatureName OBJECT-TYPE
			SYNTAX  DisplayString
			ACCESS  read-only
			STATUS  mandatory
			DESCRIPTION
				"The name of this feature."
			::= { cntFeatureEntry 2 }

		cntFeatureQuantity OBJECT-TYPE
			SYNTAX  INTEGER
			ACCESS  read-only
			STATUS  mandatory
			DESCRIPTION
				"The quantity of this feature."
			::= { cntFeatureEntry 3 }

		cntFeatureDescr OBJECT-TYPE
			SYNTAX  DisplayString
			ACCESS  read-only
			STATUS  mandatory
			DESCRIPTION
				"A description of this feature."
			::= { cntFeatureEntry 4 }


		cntSlotTable OBJECT-TYPE
			SYNTAX  SEQUENCE OF CntSlotEntry
			ACCESS  not-accessible
			STATUS  mandatory
			DESCRIPTION
				"The list of VME slots in this node."
			::= { cntSysBuild 12 }

		cntSlotEntry OBJECT-TYPE
			SYNTAX  CntSlotEntry
			ACCESS  not-accessible
			STATUS  mandatory
			DESCRIPTION
				"A node slot entry."
			INDEX	{ cntSlotIndex }
			::= { cntSlotTable 1 }

		CntSlotEntry ::= SEQUENCE {
			cntSlotIndex
				INTEGER,
			cntSlotName
				DisplayString,
			cntSlotPartNumber
				INTEGER,
			cntSlotSerialNumber
				INTEGER,
			cntSlotRevLevel
				DisplayString,
			cntSlotInterface
				INTEGER,
			cntSlotCpuNumber
				INTEGER,
			cntSlotVMEbusGrant
				INTEGER
		}

		cntSlotIndex OBJECT-TYPE
			SYNTAX  INTEGER
			ACCESS  read-only
			STATUS  mandatory
			DESCRIPTION
				"The slot index."
			::= { cntSlotEntry 1 }

		cntSlotName OBJECT-TYPE
			SYNTAX  DisplayString
			ACCESS  read-only
			STATUS  mandatory
			DESCRIPTION
				"The board name in this slot."
			::= { cntSlotEntry 2 }

		cntSlotPartNumber OBJECT-TYPE
			SYNTAX  INTEGER
			ACCESS  read-only
			STATUS  mandatory
			DESCRIPTION
				"The part number for the board in this slot."
			::= { cntSlotEntry 3 }

		cntSlotSerialNumber OBJECT-TYPE
			SYNTAX  INTEGER
			ACCESS  read-only
			STATUS  mandatory
			DESCRIPTION
				"The serial number for the board in this
				slot."
			::= { cntSlotEntry 4 }

		cntSlotRevLevel OBJECT-TYPE
			SYNTAX  DisplayString
			ACCESS  read-only
			STATUS  mandatory
			DESCRIPTION
				"The revision number of the board in this
				slot."
			::= { cntSlotEntry 5 }

		cntSlotInterface OBJECT-TYPE
			SYNTAX  INTEGER
			ACCESS  read-only
			STATUS  mandatory
			DESCRIPTION
				"The interface name of the board in this
				slot."
			::= { cntSlotEntry 6 }

		cntSlotCpuNumber OBJECT-TYPE
			SYNTAX  INTEGER {
				lcp-1(1),
				lcp-2(2),
				lcp-3(3),
				lcp-4(4),
				lcp-5(5),
				lcp-6(6),
				lcp-7(7)
			}
			ACCESS  read-only
			STATUS  mandatory
			DESCRIPTION
				"The cpu number of the board in this slot."
			::= { cntSlotEntry 7 }

		cntSlotVMEbusGrant OBJECT-TYPE
			SYNTAX  INTEGER
			ACCESS  read-only
			STATUS  mandatory
			DESCRIPTION
				"The VME bus grant priority of the board in
				this slot."
			::= { cntSlotEntry 8 }

		cntIOTable OBJECT-TYPE
			SYNTAX  SEQUENCE OF CntIOEntry
			ACCESS  not-accessible
			STATUS  mandatory
			DESCRIPTION
				"The list of VME I/O boards in this node."
			::= { cntSysBuild 13 }

		cntIOEntry OBJECT-TYPE
			SYNTAX  CntIOEntry
			ACCESS  not-accessible
			STATUS  mandatory
			DESCRIPTION
				"A node board entry."
			INDEX	{ cntIOIndex }
			::= { cntIOTable 1 }

		CntIOEntry ::= SEQUENCE {
			cntIOIndex
				INTEGER,
			cntIOName
				DisplayString,
			cntIOPartNumber
				INTEGER,
			cntIOSerialNumber
				INTEGER,
			cntIORevLevel
				DisplayString,
			cntIOInterface
				INTEGER,
			cntIOCpuNumber
				INTEGER
		}

		cntIOIndex OBJECT-TYPE
			SYNTAX  INTEGER
			ACCESS  read-only
			STATUS  mandatory
			DESCRIPTION
				"The I/O board index."
			::= { cntIOEntry 1 }

		cntIOName OBJECT-TYPE
			SYNTAX  DisplayString
			ACCESS  read-only
			STATUS  mandatory
			DESCRIPTION
				"The I/O board name."
			::= { cntIOEntry 2 }

		cntIOPartNumber OBJECT-TYPE
			SYNTAX  INTEGER
			ACCESS  read-only
			STATUS  mandatory
			DESCRIPTION
				"The part number for this I/O board."
			::= { cntIOEntry 3 }

		cntIOSerialNumber OBJECT-TYPE
			SYNTAX  INTEGER
			ACCESS  read-only
			STATUS  mandatory
			DESCRIPTION
				"The serial number for this I/O board."
			::= { cntIOEntry 4 }

		cntIORevLevel OBJECT-TYPE
			SYNTAX  DisplayString
			ACCESS  read-only
			STATUS  mandatory
			DESCRIPTION
				"The revision number of this I/O board."
			::= { cntIOEntry 5 }

		cntIOInterface OBJECT-TYPE
			SYNTAX  INTEGER
			ACCESS  read-only
			STATUS  mandatory
			DESCRIPTION
				"The interface name of this I/O board."
			::= { cntIOEntry 6 }

		cntIOCpuNumber OBJECT-TYPE
			SYNTAX  INTEGER {
				lcp-1(1),
				lcp-2(2),
				lcp-3(3),
				lcp-4(4),
				lcp-5(5),
				lcp-6(6),
				lcp-7(7)
			}
			ACCESS  read-only
			STATUS  mandatory
			DESCRIPTION
				"The cpu number of this I/O board."
			::= { cntIOEntry 7 }


		cntPowerTable OBJECT-TYPE
			SYNTAX  SEQUENCE OF CntPowerEntry
			ACCESS  not-accessible
			STATUS  mandatory
			DESCRIPTION
				"The list of power supplies in this node."
			::= { cntSysBuild 14 }

		cntPowerEntry OBJECT-TYPE
			SYNTAX  CntPowerEntry
			ACCESS  not-accessible
			STATUS  mandatory
			DESCRIPTION
				"A node power supply entry."
			INDEX	{ cntPowerIndex }
			::= { cntPowerTable 1 }

		CntPowerEntry ::= SEQUENCE {
			cntPowerIndex
				INTEGER,
			cntPowerName
				DisplayString,
			cntPowerPartNumber
				INTEGER,
			cntPowerSerialNumber
				INTEGER,
			cntPowerRevLevel
				DisplayString
		}

		cntPowerIndex OBJECT-TYPE
			SYNTAX  INTEGER
			ACCESS  read-only
			STATUS  mandatory
			DESCRIPTION
				"The power supply index."
			::= { cntPowerEntry 1 }

		cntPowerName OBJECT-TYPE
			SYNTAX  DisplayString
			ACCESS  read-only
			STATUS  mandatory
			DESCRIPTION
				"The power supply name."
			::= { cntPowerEntry 2 }

		cntPowerPartNumber OBJECT-TYPE
			SYNTAX  INTEGER
			ACCESS  read-only
			STATUS  mandatory
			DESCRIPTION
				"The part number for this power supply."
			::= { cntPowerEntry 3 }

		cntPowerSerialNumber OBJECT-TYPE
			SYNTAX  INTEGER
			ACCESS  read-only
			STATUS  mandatory
			DESCRIPTION
				"The serial number for this power supply."
			::= { cntPowerEntry 4 }

		cntPowerRevLevel OBJECT-TYPE
			SYNTAX  DisplayString
			ACCESS  read-only
			STATUS  mandatory
			DESCRIPTION
				"The revision number of this power supply."
			::= { cntPowerEntry 5 }

		cntSCRTable OBJECT-TYPE
			SYNTAX  SEQUENCE OF CntSCREntry
			ACCESS  not-accessible
			STATUS  mandatory
			DESCRIPTION
				"The list of SCRs in this node."
			::= { cntSysBuild 15 }

		cntSCREntry OBJECT-TYPE
			SYNTAX  CntSCREntry
			ACCESS  not-accessible
			STATUS  mandatory
			DESCRIPTION
				"A node SCR entry."
			INDEX	{ cntSCRIndex }
			::= { cntSCRTable 1 }

		CntSCREntry ::= SEQUENCE {
			cntSCRIndex
				INTEGER,
			cntSCRNumber
				INTEGER
		}

		cntSCRIndex OBJECT-TYPE
			SYNTAX  INTEGER
			ACCESS  read-only
			STATUS  mandatory
			DESCRIPTION
				"The SCR index."
			::= { cntSCREntry 1 }

		cntSCRNumber OBJECT-TYPE
			SYNTAX  INTEGER
			ACCESS  read-only
			STATUS  mandatory
			DESCRIPTION
				"A SCR number installed in this node."
			::= { cntSCREntry 2 }
	
		-- PSR 24227 start 
		-- This is a new version of serial #.  It is now 
		-- string based and is longer 
		cntSerialAlfaNumber OBJECT-TYPE
			SYNTAX  DisplayString
			ACCESS  read-only
			STATUS  mandatory
			DESCRIPTION
				"The machine serial number of this node."
			::= { cntSysBuild 16 }
		-- PSR 24227 end 


		cntSysMemory OBJECT IDENTIFIER ::= { cntsystem 6 }
		
		cntMemBBramAddress OBJECT-TYPE
			SYNTAX  INTEGER
			ACCESS  read-only
			STATUS  mandatory
			DESCRIPTION
				"The starting address of battery-backed-up
				RAM.  BBRAM is used to store the software and
				configuration files."
			::= { cntSysMemory 1 }
	
		cntMemBBramSpace OBJECT-TYPE
			SYNTAX  INTEGER
			ACCESS  read-only
			STATUS  mandatory
			DESCRIPTION
				"The amount of BBRAM memory in bytes installed
				in this node."
			::= { cntSysMemory 2 }
	
		cntMemBBramFree OBJECT-TYPE
			SYNTAX  INTEGER
			ACCESS  read-only
			STATUS  mandatory
			DESCRIPTION
				"The amount of BBRAM memory in bytes available
				in this node."
			::= { cntSysMemory 3 }

		cntMemSramAddress OBJECT-TYPE
			SYNTAX  INTEGER
			ACCESS  read-only
			STATUS  mandatory
			DESCRIPTION
				"The starting address of static ram.  SRAM is
				used as buffer space."
			::= { cntSysMemory 4 }
	
		cntMemSramSpace OBJECT-TYPE
			SYNTAX  INTEGER
			ACCESS  read-only
			STATUS  mandatory
			DESCRIPTION
				"The amount of SRAM memory in bytes installed
				in this node."
			::= { cntSysMemory 5 }
	
		cntMemSramFree OBJECT-TYPE
			SYNTAX  INTEGER
			ACCESS  read-only
			STATUS  mandatory
			DESCRIPTION
				"The amount of SRAM memory in bytes available
				in this node."
			::= { cntSysMemory 6 }

		cntSysCpuTable OBJECT-TYPE
			SYNTAX  SEQUENCE OF CntSysCpuEntry
			ACCESS  not-accessible
			STATUS  mandatory
			DESCRIPTION
				"List of cpu entries."
			::= { cntsystem 7 }

		cntSysCpuEntry OBJECT-TYPE
			SYNTAX  CntSysCpuEntry
			ACCESS  not-accessible
			STATUS  mandatory
			DESCRIPTION
				"A cpu entry."
			INDEX	{ cntCpuIndex }
			::= { cntSysCpuTable 1 }

		CntSysCpuEntry ::= SEQUENCE {
			cntCpuIndex
				INTEGER,
			cntCpuMemSpace
				INTEGER,
			cntCpuMemFree
				INTEGER
		}

		cntCpuIndex OBJECT-TYPE
			SYNTAX  INTEGER {
				lcp-1(1),
				lcp-2(2),
				lcp-3(3),
				lcp-4(4),
				lcp-5(5),
				lcp-6(6),
				lcp-7(7)
			}
			ACCESS  read-only
			STATUS  mandatory
			DESCRIPTION
				"The cpu index." 
			::= { cntSysCpuEntry 1 }
	
		cntCpuMemSpace OBJECT-TYPE
			SYNTAX  INTEGER
			ACCESS  read-only
			STATUS  mandatory
			DESCRIPTION
				"The amount of memory in bytes installed
				in this cpu."
			::= { cntSysCpuEntry 2 }
	
		cntCpuMemFree OBJECT-TYPE
			SYNTAX  INTEGER
			ACCESS  read-only
			STATUS  mandatory
			DESCRIPTION
				"The amount of memory in bytes available
				in this cpu."
			::= { cntSysCpuEntry 3 }

		cntCpuTaskTable OBJECT-TYPE
			SYNTAX  SEQUENCE OF CntCpuTaskEntry
			ACCESS  not-accessible
			STATUS  mandatory
			DESCRIPTION
				"List of cpu task entries."
			::= { cntSysCpuEntry 4 }

		cntCpuTaskEntry OBJECT-TYPE
			SYNTAX  CntCpuTaskEntry
			ACCESS  not-accessible
			STATUS  mandatory
			DESCRIPTION
				"A cpu task list entry."
			INDEX	{ cntCpuTaskIndex }
			::= { cntCpuTaskTable 1 }

		CntCpuTaskEntry ::= SEQUENCE {
			cntCpuTaskIndex
				INTEGER,
			cntCpuTaskName
				DisplayString
		}

		cntCpuTaskIndex OBJECT-TYPE
			SYNTAX  INTEGER
			ACCESS  read-only
			STATUS  mandatory
			DESCRIPTION
				"The relative index of the task on this cpu." 
			::= { cntCpuTaskEntry 1 }
	
		cntCpuTaskName OBJECT-TYPE
			SYNTAX  DisplayString
			ACCESS  read-only
			STATUS  mandatory
			DESCRIPTION
				"The operating system name for a loaded and
				possibly executing task on this cpu."
			::= { cntCpuTaskEntry 2 }



		-- the CNT Access Units Interface group

   		cntinterfaces  OBJECT IDENTIFIER ::= { cntau 2 }

		cntifTable OBJECT-TYPE
			SYNTAX  SEQUENCE OF CntifEntry
			ACCESS  not-accessible
			STATUS  mandatory
			DESCRIPTION
				"A list of CNT interface entries."
			::= { cntinterfaces 1 }
	
		cntifEntry OBJECT-TYPE
			SYNTAX  CntifEntry
			ACCESS  not-accessible
			STATUS  mandatory
			DESCRIPTION
				"An CNT interface entry."
			INDEX	{ cntifIndex }
			::= { cntifTable 1 }
	
		CntifEntry ::= SEQUENCE {
			cntifIndex
				INTEGER,
			cntifType
				INTEGER,
			cntifCpu
				INTEGER,
			cntifSubIndex
				INTEGER
		}
	
		cntifIndex OBJECT-TYPE
        		SYNTAX  INTEGER
        		ACCESS  read-only
        		STATUS  mandatory
			DESCRIPTION
				"An index value that uniquely identifies an
				interface on a CNT node.  The interface
				identified by a particular value of this index
				is the same interface as identified by the same
				value of IfIndex."
			::= { cntifEntry 1 }

		cntifType OBJECT-TYPE
			SYNTAX  INTEGER {
				other(1),
				regular1822(2),
				hdh1822(3),
				ddn-x25(4),
				rfc877-x25(5),
				ethernet(6),
				ethernet88023(7),
				tokenBus(8),
				tokenRing(9),
				smds(10),
				starLan(11),
				proteon-10MBit(12),
				proteon-80MBit(13),
				hyperchannel(14),
				fddi(15),
				lapb(16),
				sdlc(17),
				t1(18),
				cept(19),
				basicIsdn(20),
				primaryIsdn(21),
				maintenance(22),
				ppp(23),
				sofwareLoopback(24),
				eon(25),
				ethernet-3Mbit(26),
				nsip(27),
				slip(28),
				ultra(29),
				ds3(30),
				sip(31),
				frame-relay(32),
				hssi-dte(33),
				fibre-trunk(34),
				hippi(35),
				crayfullduplex(36),
				pt-to-pt-fiber(37),
				channel-to-channel(38),
				peripheral-gateway(39),
				tape-pipelining(40),
				tape-dasd(41),
				hssi-dce(42),
				ibm-channel(43),
				dual-trunk(44),
				teradata(45),
				cray-hyperchannel(46),
				scsi-target(47),
				snmp-gateway(48), 
				ppp-async(49),
				escon-host(50),
				escon-peripheral(51),
				tapecontrol-rs232(52),
				ultra-dte(53),
				ultra-dce(54),
				fddi-ss(55),
				hssi-ss(56),
				tunneling(57),
				stackstarter(58),
				ethernet-geni(59),
				tokenring-geni(60),
				atm(61),
				scsi-initiator(62),
				escon-srdf(63)
			}
			ACCESS  read-only
			STATUS  mandatory
			DESCRIPTION
				"The type of interface.  For standardized
				interface types in mib-2, this number is
				redundant.  CNT specific interface types are
				appended to the end of the standardized list."
			::= { cntifEntry 2 }

               	cntifCpu OBJECT-TYPE
			SYNTAX  INTEGER {
				lcp-1(1),
				lcp-2(2),
				lcp-3(3),
				lcp-4(4),
				lcp-5(5),
				lcp-6(6),
				lcp-7(7)
			}
			ACCESS  read-only
			STATUS  mandatory
			DESCRIPTION
				"The cpu number where the device driver for
				this interface resides."
			::= { cntifEntry 3 }

               	cntifSubIndex OBJECT-TYPE
			SYNTAX  INTEGER
			ACCESS  read-only
			STATUS  mandatory
			DESCRIPTION
				"A value that uniquely indexes an interface
				in a multiply-interfaced device driver."
			::= { cntifEntry 4 }

		cntIfsState OBJECT-TYPE
			SYNTAX  INTEGER
			ACCESS  read-only
			STATUS  mandatory
			DESCRIPTION
				"A 32 bit-map of the interface states.  The
				bits are ordered from 1 to 32 with the most
				significant bit on the left.  if the bit is
				set, the corresponding interface is up.  if
				the bit is clear, the interface is not up -
				down or in test mode."
			::= { cntinterfaces 2 }



		-- the CNT Access Units ICMP group

   		cnticmp   OBJECT IDENTIFIER ::= { cntau 5 }

               	cnticmpInDuNets OBJECT-TYPE
			SYNTAX  Counter
			ACCESS  read-only
			STATUS  mandatory
			DESCRIPTION
				"The number of times a destination unreachable
				message was received for an unreachable
				network."
			::= { cnticmp 1 }

                cnticmpInDuHosts OBJECT-TYPE
                          SYNTAX  Counter
                          ACCESS  read-only
                          STATUS  mandatory
			  DESCRIPTION
				"The number of times a destination unreachable
				message was received for an unreachable host."
                         	::= { cnticmp 2 }

                cnticmpInDuProtos OBJECT-TYPE
                          SYNTAX  Counter
                          ACCESS  read-only
                          STATUS  mandatory
			  DESCRIPTION
				"The number of times a destination unreachable
				message was received due to an unreachable
				protocol."
                         	::= { cnticmp 3 }

                cnticmpInDuPorts OBJECT-TYPE
                          SYNTAX  Counter
                          ACCESS  read-only
                          STATUS  mandatory
			  DESCRIPTION
				"The number of times a destination unreachable
				message was received due to an unreachable
				port."
                         	::= { cnticmp 4 }

               	cnticmpInDuFrags OBJECT-TYPE
                          SYNTAX  Counter
                          ACCESS  read-only
                          STATUS  mandatory
			  DESCRIPTION
				"The number of times a destination unreachable
				message was received due to a fragmentation
				requirement but the Don't Fragment flag is
				set."
                         	::= { cnticmp 5 }

                cnticmpInDuSources OBJECT-TYPE
                          SYNTAX  Counter
                          ACCESS  read-only
                          STATUS  mandatory
			  DESCRIPTION
				"The number of times a destination unreachable
				message was received due to a source route
				that is not usable."
                         	::= { cnticmp 6 }

               	cnticmpInTmXceeds OBJECT-TYPE
                          SYNTAX  Counter
                          ACCESS  read-only
                          STATUS  mandatory
			  DESCRIPTION
				"The number of times a time exceeded message
				was received for an expired datagram."
                         	::= { cnticmp 7 }

                cnticmpInTmFrags OBJECT-TYPE
                          SYNTAX  Counter
                          ACCESS  read-only
                          STATUS  mandatory
			  DESCRIPTION
				"The number of times a time exceeded message
				was received for a datagram that could not be
				reassembled before its lifetime expired."
                         	::= { cnticmp 8 }

               	cnticmpInReNets OBJECT-TYPE
                          SYNTAX  Counter
                          ACCESS  read-only
                          STATUS  mandatory
			  DESCRIPTION
				"The number of times a redirect message was
				received due to a shorter path to a
				destination network having been found." 
                         	::= { cnticmp 9 }

                cnticmpInReHosts OBJECT-TYPE
                          SYNTAX  Counter
                          ACCESS  read-only
                          STATUS  mandatory
			  DESCRIPTION
				"The number of times a redirect message was
				received due to a shorter path to a
				destination host having been found." 
                         	::= { cnticmp 10 }

               	cnticmpInReServnets OBJECT-TYPE
                          SYNTAX  Counter
                          ACCESS  read-only
                          STATUS  mandatory
			  DESCRIPTION
				"The number of times a redirect message was
				received due to a shorter path to a
				destination network with the requested type of
				service having been found." 
                         	::= { cnticmp 11 }

                cnticmpInReServhosts OBJECT-TYPE
                          SYNTAX  Counter
                          ACCESS  read-only
                          STATUS  mandatory
			  DESCRIPTION
				"The number of times a redirect message was
				received due to a shorter path to a
				destination host with the requested type of
				service having been found." 
                         	::= { cnticmp 12 }

                cnticmpOutDuNets OBJECT-TYPE
                          SYNTAX  Counter
                          ACCESS  read-only
                          STATUS  mandatory
			  DESCRIPTION
				"The number of times a destination unreachable
				message was sent to a requester when it
				attempted to send a datagram to an unreachable
				network."
                         	::= { cnticmp 13 }

                cnticmpOutDuHosts OBJECT-TYPE
                          SYNTAX  Counter
                          ACCESS  read-only
                          STATUS  mandatory
			  DESCRIPTION
				"The number of times a destination unreachable
				message was sent to a requester when it
				attempted to send a datagram to an unreachable
				host."
                         	::= { cnticmp 14 }

                cnticmpOutDuProtos OBJECT-TYPE
                          SYNTAX  Counter
                          ACCESS  read-only
                          STATUS  mandatory
			  DESCRIPTION
				"The number of times a destination unreachable
				message was sent to a requester when it
				attempted to send a datagram to an unreachable
				protocol."
                         	::= { cnticmp 15 }

                cnticmpOutDuPorts OBJECT-TYPE
                          SYNTAX  Counter
                          ACCESS  read-only
                          STATUS  mandatory
			  DESCRIPTION
				"The number of times a destination unreachable
				message was sent to a requester when it
				attempted to send a datagram to an unreachable
				port."
                         	::= { cnticmp 16 }

               	cnticmpOutDuFrags OBJECT-TYPE
                          SYNTAX  Counter
                          ACCESS  read-only
                          STATUS  mandatory
			  DESCRIPTION
				"The number of times a destination unreachable
				message was sent to a requester when it
				attempted to send a datagram requiring
				fragmentation but the Don't Fragment flag is
				set."
                         	::= { cnticmp 17 }

                cnticmpOutDuSources OBJECT-TYPE
                          SYNTAX  Counter
                          ACCESS  read-only
                          STATUS  mandatory
			  DESCRIPTION
				"The number of times a destination unreachable
				message was sent due to a source route that is
				not usable."
                         	::= { cnticmp 18 }

               	cnticmpOutTmXceeds OBJECT-TYPE
                          SYNTAX  Counter
                          ACCESS  read-only
                          STATUS  mandatory
			  DESCRIPTION
				"The number of times a time exceeded message
				was sent for an expired datagram."
                         	::= { cnticmp 19 }

                cnticmpOutTmFrags OBJECT-TYPE
                          SYNTAX  Counter
                          ACCESS  read-only
                          STATUS  mandatory
			  DESCRIPTION
				"The number of times a time exceeded message
				was sent for a datagram that could not be
				reassembled before its lifetime expired."
                         	::= { cnticmp 20 }

               	cnticmpOutReNets OBJECT-TYPE
                          SYNTAX  Counter
                          ACCESS  read-only
                          STATUS  mandatory
			  DESCRIPTION
				"The number of times a redirect message was
				sent due to a shorter path to a destination
				network having been found." 
                         	::= { cnticmp 21 }

                cnticmpOutReHosts OBJECT-TYPE
                          SYNTAX  Counter
                          ACCESS  read-only
                          STATUS  mandatory
			  DESCRIPTION
				"The number of times a redirect message was
				sent due to a shorter path to a destination
				host having been found." 
                         	::= { cnticmp 22 }

               	cnticmpOutReServnets OBJECT-TYPE
                          SYNTAX  Counter
                          ACCESS  read-only
                          STATUS  mandatory
			  DESCRIPTION
				"The number of times a redirect message was
				sent due to a shorter path to a destination
				network with the requested type of service
				having been found." 
                         	::= { cnticmp 23 }

                cnticmpOutReServhosts OBJECT-TYPE
                          SYNTAX  Counter
                          ACCESS  read-only
                          STATUS  mandatory
			  DESCRIPTION
				"The number of times a redirect message was
				sent due to a shorter path to a destination
				host with the requested type of service having
				been found." 
                         	::= { cnticmp 24 }



		--- the CNT Access Units Transmission group

   		cnttransmission OBJECT IDENTIFIER ::= { cntau 10 }


   		cntdot3	  OBJECT IDENTIFIER ::= { cnttransmission 1 }

		cntdot3Table OBJECT-TYPE
			SYNTAX SEQUENCE OF CntDot3Entry
			ACCESS not-accessible
			STATUS mandatory
			DESCRIPTION
				"Status information and control variables
				for a collection of ethernet software device
				drivers in a particular CNT system."
			::= { cntdot3 1 }

		cntdot3Entry OBJECT-TYPE
			SYNTAX CntDot3Entry
			ACCESS not-accessible
			STATUS mandatory
			DESCRIPTION
				"Status information and control variables
				for a particular CNT ethernet software device
				driver."
			INDEX	{ cntdot3Index }
			::= { cntdot3Table 1 }

		CntDot3Entry ::= SEQUENCE {
				cntdot3Index
					INTEGER,
				cntdot3SoftwareID
					IpAddress,
				cntdot3BufsAllocated
					INTEGER,
				cntdot3BufTooManys
					Counter,
				cntdot3BufNotAvails
					Counter,
				cntdot3BufPriority
					INTEGER,
				cntdot3PICBusErrs
					Counter,
				cntdot3PICDMAErrs
					Counter,
				cntdot3PICMemSeqErrs
					Counter,
				cntdot3PICMemParityErrs
					Counter,
				cntdot3PICSpuriousInts
					Counter,
				cntdot3LanceInts
					Counter,
				cntdot3LanceParityErrs
					Counter,
				cntdot3LanceMemErrs
					Counter,
				cntdot3LanceMissedPkts
					Counter,
				cntdot3LanceUnderFlows
					Counter,
				cntdot3LanceOverFlows
					Counter,
				cntdot3LanceTxWaitQ
					INTEGER,
				cntdot3DMAChan1RxErr
					INTEGER,
				cntdot3DMAChan3RxErr
					INTEGER,
				cntdot3DMAChan0TxErr
					INTEGER,
				cntdot3DMAChan2TxErr
					INTEGER,
				cntdot3DMAChan1RxErrs
					Counter,
				cntdot3DMAChan3RxErrs
					Counter,
				cntdot3DMAChan0TxErrs
					Counter,
				cntdot3DMAChan2TxErrs
					Counter,
				cntdot3DMARxWaitQ
					INTEGER,
				cntdot3DMATxWaitQ
					INTEGER,
				cntdot3LPXParityErrs
					Counter,
				cntdot3Chan1Misreads
					Counter
			}

		cntdot3Index OBJECT-TYPE
        		SYNTAX  INTEGER
        		ACCESS  read-only
        		STATUS  mandatory
			DESCRIPTION
				"An index value that uniquely identifies an
				interface to a CNT ethernet-like medium.  The
				interface identified by a particular value of
				this index is the same interface as identified
				by the same value of IfIndex."
        		::= { cntdot3Entry 1 }

		cntdot3SoftwareID OBJECT-TYPE
        		SYNTAX  IpAddress
        		ACCESS  read-only
        		STATUS  mandatory
			DESCRIPTION
				"The binary software revision number in the
				header of the ethernet driver."
        		::= { cntdot3Entry 2 }

		cntdot3BufsAllocated OBJECT-TYPE
        		SYNTAX  INTEGER
        		ACCESS  read-only
        		STATUS  mandatory
			DESCRIPTION
				"The number of CNT buffers allocated by the
				ethernet device driver at initialization."
        		::= { cntdot3Entry 3 }

		cntdot3BufTooManys OBJECT-TYPE
        		SYNTAX  Counter
        		ACCESS  read-only
        		STATUS  mandatory
			DESCRIPTION
				"The number of buffers sent by a higher layer
				that were returned to that layer without
				transmission due to a full queue of waiting 
				outbound buffers." 
        		::= { cntdot3Entry 4 }

		cntdot3BufNotAvails OBJECT-TYPE
        		SYNTAX  Counter
        		ACCESS  read-only
        		STATUS  mandatory
			DESCRIPTION
				"The number of requests made to the free pool
				of ethernet buffers that failed due to a lack
				buffers in that pool."
        		::= { cntdot3Entry 5 }

		cntdot3BufPriority OBJECT-TYPE
        		SYNTAX  INTEGER
        		ACCESS  read-only
        		STATUS  mandatory
			DESCRIPTION
				"The priority value assigned to inbound
				ethernet buffers."
        		::= { cntdot3Entry 6 }

		cntdot3PICBusErrs OBJECT-TYPE
        		SYNTAX  Counter
        		ACCESS  read-only
        		STATUS  mandatory
			DESCRIPTION
				"The number of times a failure was detected
				when attempting to access the VME bus."
        		::= { cntdot3Entry 7 }

		cntdot3PICDMAErrs OBJECT-TYPE
        		SYNTAX  Counter
        		ACCESS  read-only
        		STATUS  mandatory
			DESCRIPTION
				"The number of times ethernet local memory had
				a parity error during a DMA memory cycle.
				These errors would normally indicate a hardware
				problem."
        		::= { cntdot3Entry 8 }

		cntdot3PICMemSeqErrs OBJECT-TYPE
        		SYNTAX  Counter
        		ACCESS  read-only
        		STATUS  mandatory
			DESCRIPTION
				"The number of times the hardware could not
				successfully arbitrate multiple requests to
				access ethernet local memory.  These errors
				would normally indicate a hardware problem." 
        		::= { cntdot3Entry 9 }

		cntdot3PICMemParityErrs OBJECT-TYPE
        		SYNTAX  Counter
        		ACCESS  read-only
        		STATUS  mandatory
			DESCRIPTION
				"The number of ethernet local memory parity
				errors.  These errors would normally indicate
				a hardware problem."
        		::= { cntdot3Entry 10 }

		cntdot3PICSpuriousInts OBJECT-TYPE
        		SYNTAX  Counter
        		ACCESS  read-only
        		STATUS  mandatory
			DESCRIPTION
				"The number of interrupts generated by the PIC
				that were not mapped to any particular hardware
				event."
        		::= { cntdot3Entry 11 }

		cntdot3LanceInts OBJECT-TYPE
        		SYNTAX  Counter
        		ACCESS  read-only
        		STATUS  mandatory
			DESCRIPTION
				"The number of LANCE hardware interrupts
				detected by the controlling CPU."
        		::= { cntdot3Entry 12 }

		cntdot3LanceParityErrs OBJECT-TYPE
        		SYNTAX  Counter
        		ACCESS  read-only
        		STATUS  mandatory
			DESCRIPTION
				"The number of parity errors detected when the
				LANCE was accessing local memory.  These errors
				would normally indicate a hardware problem."
        		::= { cntdot3Entry 13 }

		cntdot3LanceMemErrs OBJECT-TYPE
        		SYNTAX  Counter
        		ACCESS  read-only
        		STATUS  mandatory
			DESCRIPTION
				"The number of times the LANCE detected a local
				memory access failure."
        		::= { cntdot3Entry 14 }

		cntdot3LanceMissedPkts OBJECT-TYPE
        		SYNTAX  Counter
        		ACCESS  read-only
        		STATUS  mandatory
			DESCRIPTION
				"The number of packets on the ethernet medium
				that were detected by the LANCE but failed to
				be captured in the inbound queue."
        		::= { cntdot3Entry 15 }

		cntdot3LanceUnderFlows OBJECT-TYPE
        		SYNTAX  Counter
        		ACCESS  read-only
        		STATUS  mandatory
			DESCRIPTION
				"The number of message truncated by the LANCE
				transmitter due to data late from memory.  An
				underflow indication by the LANCE indicates
				that the silo was emptied before the end of the
				packet was reached."
        		::= { cntdot3Entry 16 }

		cntdot3LanceOverFlows OBJECT-TYPE
        		SYNTAX  Counter
        		ACCESS  read-only
        		STATUS  mandatory
			DESCRIPTION
				"The number of times the LANCE receiver lost
				all or part of the incoming packet due to an
				inability to store the packet in a memory
				buffer before the internal silo overflowed."	
        		::= { cntdot3Entry 17 }

		cntdot3LanceTxWaitQ OBJECT-TYPE
        		SYNTAX  INTEGER
        		ACCESS  read-only
        		STATUS  mandatory
			DESCRIPTION
				"The number of buffers in local memory and on
				the ethernet device driver's software queue
				awaiting transmission by the LANCE."
        		::= { cntdot3Entry 18 }

		cntdot3DMAChan1RxErr OBJECT-TYPE
        		SYNTAX  INTEGER {
					no-error (0),
					config(1),
					operation-timing(2),
					address-mar(5),
					address-dar(6),
					address-bar(7),
					buserr-mar(9),
					buserr-dar(10),
					buserr-bar(11),
					count-mtc(13),
					count-btc(15),
					external-abort(16),
					external-software-abort(17)
					}
        		ACCESS  read-only
        		STATUS  mandatory
			DESCRIPTION
				"The error code reported by the DMA controller
				channel 1.  This channel is used to write
				inbound ethernet messages."
        		::= { cntdot3Entry 19 }

		cntdot3DMAChan3RxErr OBJECT-TYPE
        		SYNTAX  INTEGER {
					no-error(1),
					config(2),
					operation-timing(3),
					address-mar(6),
					address-dar(7),
					address-bar(8),
					buserr-mar(10),
					buserr-dar(11),
					buserr-bar(12),
					count-mtc(14),
					count-btc(16),
					external-abort(17),
					external-software-abort(18)
					}
        		ACCESS  read-only
        		STATUS  mandatory
			DESCRIPTION
				"The error code reported by the DMA controller
				channel 3.  This channel is used to write
				inbound ethernet messages."
        		::= { cntdot3Entry 20 }

		cntdot3DMAChan0TxErr OBJECT-TYPE
        		SYNTAX  INTEGER {
					no-error(1),
					config(2),
					operation-timing(3),
					address-mar(6),
					address-dar(7),
					address-bar(8),
					buserr-mar(10),
					buserr-dar(11),
					buserr-bar(12),
					count-mtc(14),
					count-btc(16),
					external-abort(17),
					external-software-abort(18)
					}
        		ACCESS  read-only
        		STATUS  mandatory
			DESCRIPTION
				"The error code reported by the DMA controller
				channel 0.  This channel is used to write
				outbound ethernet messages."
        		::= { cntdot3Entry 21 }

		cntdot3DMAChan2TxErr OBJECT-TYPE
        		SYNTAX  INTEGER {
					no-error(1),
					config(2),
					operation-timing(3),
					address-mar(6),
					address-dar(7),
					address-bar(8),
					buserr-mar(10),
					buserr-dar(11),
					buserr-bar(12),
					count-mtc(14),
					count-btc(16),
					external-abort(17),
					external-software-abort(18)
					}
        		ACCESS  read-only
        		STATUS  mandatory
			DESCRIPTION
				"The error code reported by the DMA controller
				channel 2.  This channel is used to write
				outbound ethernet messages."
        		::= { cntdot3Entry 22 }

		cntdot3DMAChan1RxErrs OBJECT-TYPE
        		SYNTAX  Counter 
        		ACCESS  read-only
        		STATUS  mandatory
			DESCRIPTION
				"The number of errors reported by the DMA
				controller channel 1.  This channel is used to
				write inbound ethernet messages."
        		::= { cntdot3Entry 23 }

		cntdot3DMAChan3RxErrs OBJECT-TYPE
        		SYNTAX  Counter
        		ACCESS  read-only
        		STATUS  mandatory
			DESCRIPTION
				"The number of errors reported by the DMA
				controller channel 1.  This channel is used to
				write inbound ethernet messages."
        		::= { cntdot3Entry 24 }

		cntdot3DMAChan0TxErrs OBJECT-TYPE
        		SYNTAX  Counter
        		ACCESS  read-only
        		STATUS  mandatory
			DESCRIPTION
				"The number of errors reported by the DMA
				controller channel 1.  This channel is used to
				write outbound ethernet messages."
        		::= { cntdot3Entry 25 }

		cntdot3DMAChan2TxErrs OBJECT-TYPE
        		SYNTAX  Counter
        		ACCESS  read-only
        		STATUS  mandatory
			DESCRIPTION
				"The number of errors reported by the DMA
				controller channel 1.  This channel is used to
				write outbound ethernet messages."
        		::= { cntdot3Entry 26 }

		cntdot3DMARxWaitQ OBJECT-TYPE
        		SYNTAX  INTEGER
        		ACCESS  read-only
        		STATUS  mandatory
			DESCRIPTION
				"The number of successfully received ethernet
				messages awaiting transmission by the DMA to
				global memory buffers."
        		::= { cntdot3Entry 27 }

		cntdot3DMATxWaitQ OBJECT-TYPE
        		SYNTAX  INTEGER
        		ACCESS  read-only
        		STATUS  mandatory
			DESCRIPTION
				"The number of buffers waiting in an outbound
				queue ready to transmitted to local memory from
				global memory.  Buffers must be moved from
				global memory to local memory in order to be
				transmitted by the LANCE." 
        		::= { cntdot3Entry 28 }

		cntdot3LPXParityErrs OBJECT-TYPE
        		SYNTAX  Counter
        		ACCESS  read-only
        		STATUS  mandatory
			DESCRIPTION
				"The number of local memory parity errors
				during an LPX memory cycle."
        		::= { cntdot3Entry 29 }

		cntdot3Chan1Misreads OBJECT-TYPE
        		SYNTAX  Counter
        		ACCESS  read-only
        		STATUS  mandatory
			DESCRIPTION
				"The number of times a mismatch was detected
				between the DMA channel 1 table and the DMA
				Memory Access Register." 
        		::= { cntdot3Entry 30 }


   		cntfddi          OBJECT IDENTIFIER ::= { cnttransmission 2 }

          	cntFddiSMT       OBJECT IDENTIFIER ::= { cntfddi 1 }
          	cntFddiMAC       OBJECT IDENTIFIER ::= { cntfddi 2 }
          	cntFddiPATH      OBJECT IDENTIFIER ::= { cntfddi 3 }
          	cntFddiPORT      OBJECT IDENTIFIER ::= { cntfddi 4 }

          	-- the SMT group

          	cntFddiSMTNumber OBJECT-TYPE
              	SYNTAX  INTEGER (0..65535)
              	ACCESS  read-only
              	STATUS  mandatory
	      	DESCRIPTION
			"The number of SMT implementations on this network
			 management application entity."
             	::= { cntFddiSMT  1 }

          	-- the SMT table

          	cntFddiSMTTable OBJECT-TYPE
              		SYNTAX  SEQUENCE OF CntFddiSMTEntry
              		ACCESS  not-accessible
              		STATUS  mandatory
	      		DESCRIPTION
				"A list of SMT entries. The number of entries
				 is given by the value of snmpFddiSMTNumber."
              		::= { cntFddiSMT  2 }

          	cntFddiSMTEntry OBJECT-TYPE
              		SYNTAX  CntFddiSMTEntry
              		ACCESS  not-accessible
              		STATUS  mandatory
	      		DESCRIPTION
				"An SMT entry containing information common to
				 a given SMT."
			INDEX	{ cntFddiSMTIndex }
              		::= { cntFddiSMTTable 1 }

          	CntFddiSMTEntry	::= SEQUENCE {
               	   	cntFddiSMTIndex
               	       	    INTEGER,
               	   	cntFddiSMTManufacturerData
               	            OCTET STRING,
               	   	cntFddiSMTUserData
               	            OCTET STRING,
               	   	cntFddiSMTReportLimit
                            INTEGER,
                   	cntFddiSMTMsgTimeStamp
                            OCTET STRING,
                   	cntFddiSMTTransitionTimeStamp
                            OCTET STRING,
                   	cntFddiSMTSetCount
                            OCTET STRING,
                   	cntFddiSMTLastSetStationID
                            OCTET STRING
              	    }

          	cntFddiSMTIndex OBJECT-TYPE
	               	SYNTAX  INTEGER (1..65535)
       		       	ACCESS  read-only
       		       	STATUS  mandatory 
		       	DESCRIPTION
		 	       "A unique value for each SMT. Its value ranges
			        between 1 and the value of snmpFddiSMTNumber."
       	       		::= { cntFddiSMTEntry 1 }

       		cntFddiSMTManufacturerData OBJECT-TYPE
              		SYNTAX  OCTET STRING 
              		ACCESS  read-only
              		STATUS  optional 
	      		DESCRIPTION
		  		"32 octets of manufacturer data. The first
				 component is the three octet Organizationally
				 Unique Identifier (OUI) assigned by IEEE. The
				 second component is the FDDI manufacturer's
				 data (29 octets)." 
              		::= { cntFddiSMTEntry 2 }

          	cntFddiSMTUserData OBJECT-TYPE
              		SYNTAX  OCTET STRING 
              		ACCESS  read-only
              		STATUS   optional
	      		DESCRIPTION
		  		"32 octets of user defined information."
              		::= { cntFddiSMTEntry 3 }

          	cntFddiSMTReportLimit OBJECT-TYPE
              		SYNTAX  INTEGER 
              		ACCESS  read-only
              		STATUS  optional
	      		DESCRIPTION
		  		"Gives the limit on the number of Status Report
				 Frames that shall be queued for transmission
				 after supported Condition becomes inactive or
				 after any supported Event has been detected."
              		::= { cntFddiSMTEntry 4 }

          	cntFddiSMTMsgTimeStamp OBJECT-TYPE
              		SYNTAX  OCTET STRING 
              		ACCESS  read-only
              		STATUS  mandatory
	      		DESCRIPTION
		  		"This timestamp is used in some SMT frames as
				 an indication of the time the message was
				 created at the sending station.  When read,
				 the accessed value shall be greater than or
				 equal to the value used in the station's last
				 message. The timestamp may be reset whenever
				 there is a discontinuity in the accumulation
				 of a statistical counter."

              		::= { cntFddiSMTEntry 5 }

          	cntFddiSMTTransitionTimeStamp OBJECT-TYPE
              		SYNTAX  OCTET STRING 
              		ACCESS  read-only
              		STATUS  mandatory
	      		DESCRIPTION
		  		"This timestamp holds the time of occurrence
				 of the last condition or event in the station.
				 It is used in the SMT Status Report Frame
				 (SRF). It is set to a new value on each event
				 to capture the time of the latest event
				 occurrence. On power-up, the value of the
				 attribute is zero."
              		::= { cntFddiSMTEntry 6 }

          	cntFddiSMTSetCount OBJECT-TYPE
              		SYNTAX  OCTET STRING 
              		ACCESS  read-only
              		STATUS  optional
	      		DESCRIPTION
		  		"This count is updated each time a parameter is
		   		changed on behalf of a request from either the
		   		local management interface or the remote
				interface via SMT Parameter Management Frames.
				It is used to provide consistency control for
				MIB updates."
              		::= { cntFddiSMTEntry 7 }
 
          	cntFddiSMTLastSetStationID OBJECT-TYPE
              		SYNTAX  OCTET STRING 
              		ACCESS  read-only
              		STATUS  optional
	      		DESCRIPTION
		  		"This object identifies the last station to set
		   		MIB information in the FDDI MIB." 
              		::= { cntFddiSMTEntry 8 }


          	-- the MAC group

          	cntFddiMACNumber OBJECT-TYPE
              		SYNTAX  INTEGER 
              		ACCESS  read-only
              		STATUS  mandatory
	      		DESCRIPTION
		  		"The total number of MAC implementations across
		   		all SMTs on this network management application
		  	 	entity."
              		::= { cntFddiMAC  1 }


          	-- the MAC table

          	cntFddiMACTable OBJECT-TYPE
              		SYNTAX  SEQUENCE OF CntFddiMACEntry
              		ACCESS  not-accessible
              		STATUS  mandatory
	      		DESCRIPTION
		  		"A list of MAC entries. The number of entries
				 is given by the value of snmpFddiMACNumber."
              		::= { cntFddiMAC  2 }

          	cntFddiMACEntry OBJECT-TYPE
              		SYNTAX  CntFddiMACEntry
              		ACCESS  not-accessible
              		STATUS  mandatory
	      		DESCRIPTION
 		  		"A MAC entry containing information common to
		   		a given MAC."
			INDEX	{ cntFddiMACSMTIndex }
              		::= { cntFddiMACTable 1 }

          	CntFddiMACEntry	::= SEQUENCE {
                  	cntFddiMACSMTIndex
                        	INTEGER,
                  	cntFddiMACIndex
                        	INTEGER,
                  	cntFddiMACBridgeFunction
                          	INTEGER,
                  	cntFddiMACDownstreamNbr
                        	OCTET STRING,
                  	cntFddiMACOldDownstreamNbr
                          	OCTET STRING,
                  	cntFddiMACRootConcentratorMac
                        	INTEGER,
                  	cntFddiMACLongAlias
                        	INTEGER,
                  	cntFddiMACShortAlias
                        	INTEGER,
                  	cntFddiMACLongGrpAddr
                        	INTEGER,
                  	cntFddiMACShortGrpAddr
                        	INTEGER,
                  	cntFddiMACTPri0
                        	INTEGER,
                  	cntFddiMACTPri1
                        	INTEGER,
                  	cntFddiMACTPri2
                        	INTEGER,
                  	cntFddiMACTPri3
                        	INTEGER,
                  	cntFddiMACTPri4
                        	INTEGER,
                  	cntFddiMACTPri5
                        	INTEGER,
                  	cntFddiMACTPri6
                        	INTEGER,
                  	cntFddiMACCopies
                        	Counter,
                  	cntFddiMACTransmits
                        	Counter,
                  	cntFddiMACTokens
                        	Counter,
                  	cntFddiMACTvxExpires
                        	Counter,
                  	cntFddiMACNotCopies
                        	Counter,
                  	cntFddiMACLates
                        	Counter,
                  	cntFddiMACRingOps
                          	Counter,
                  	cntFddiMACBaseFrames
                        	Counter,
                  	cntFddiMACBaseErrs
                        	Counter,
                  	cntFddiMACBaseLosts
                        	Counter,
                  	cntFddiMACBaseTimeFrameError
                        	OCTET STRING,
                  	cntFddiMACBaseNotCopies
                        	Counter,
                  	cntFddiMACBaseTimeNotCopied
                        	OCTET STRING,
                  	cntFddiMACNotCopiedThreshold
                        	INTEGER,
                  	cntFddiMACBaseCopies
                        	Counter,
                  	cntFddiMACNotCopiedRatio
                        	INTEGER,
                  	cntFddiMACNotCopiedCondition
                        	INTEGER,
                  	cntFddiMACLLCServiceAvailable
                        	INTEGER,
                  	cntFddiMACMasterSlaveLoopStatus
                        	INTEGER,
                  	cntFddiMACRootMACDownStreamPORTType
                        	INTEGER,
                  	cntFddiMACRootMACCurrentPath
                        	INTEGER
              		}


          	cntFddiMACSMTIndex OBJECT-TYPE
              		SYNTAX  INTEGER (1..65535)
              		ACCESS  read-only
              		STATUS  mandatory
	      		DESCRIPTION
		  		"The value of the SMT index associated with
				 this MAC."
              		::= { cntFddiMACEntry 1 }

          	cntFddiMACIndex OBJECT-TYPE
              		SYNTAX  INTEGER (1..65535)
              		ACCESS  read-only
              		STATUS  mandatory
	      		DESCRIPTION
		  		"A unique value for each MAC on the managed
				 entity.  The MAC identified by a particular
				 value of this index is that identified by the
				 same value of an ifIndex object instance."
              		::= { cntFddiMACEntry 2 }

          	cntFddiMACBridgeFunction OBJECT-TYPE
              		SYNTAX  INTEGER 
              		ACCESS  read-only
              		STATUS  optional 
	      		DESCRIPTION
		  		"Gives the bridge type for a MAC that has a
				 bridge capability."	
              		::= { cntFddiMACEntry 3 }

          	cntFddiMACDownstreamNbr OBJECT-TYPE
              		SYNTAX OCTET STRING 
              		ACCESS  read-only
              		STATUS  optional
	      		DESCRIPTION
		  		"The MAC's downstream neighbor's long
				 individual MAC address. It may be determined
				 by the Neighbor Information Frame Request/
				 Response protocol. It is optional an reported
				 as zero in SMT frames if unknown or
				 unsupported."
              		::= { cntFddiMACEntry 4 }

          	cntFddiMACOldDownstreamNbr OBJECT-TYPE
              		SYNTAX OCTET STRING 
              		ACCESS  read-only
              		STATUS  optional 
	      		DESCRIPTION
		  		"This object identifies this MAC's previous
				 downstream neighbor."
              		::= { cntFddiMACEntry 5 }

          	cntFddiMACRootConcentratorMac OBJECT-TYPE
              		SYNTAX  INTEGER 
              		ACCESS  read-only
              		STATUS   optional
	      		DESCRIPTION
		  		"A MAC in a concentrator is a root concentrator
				 MAC if its transmit path exits the
				 concentrator via a Port in a peer node; or if
				 the MAC exits via a Port in a tree node and
				 there is no A, B, or S Ports that are active
				 on that MAC's current Path."
              		::= { cntFddiMACEntry 6 }

          	cntFddiMACLongAlias OBJECT-TYPE
              		SYNTAX  INTEGER 
              		ACCESS  read-only
              		STATUS  optional
	      		DESCRIPTION
		  		"A possibly null set of 48 bit addresses
				 (aliases) for this MAC."
              		::= { cntFddiMACEntry 7 }

          	cntFddiMACShortAlias OBJECT-TYPE
              		SYNTAX  INTEGER 
              		ACCESS  read-only
              		STATUS  optional
	      		DESCRIPTION
		  		"A possibly null set of 16 bit addresses
				 (aliases) for this MAC."
              		::= { cntFddiMACEntry 8 }

          	cntFddiMACLongGrpAddr OBJECT-TYPE
              		SYNTAX  INTEGER 
              		ACCESS  read-only
              		STATUS  optional
	      		DESCRIPTION
		  		"A possibly null set of 48 bit group addresses
		   		(aliases) for this MAC."
              		::= { cntFddiMACEntry 9 }

          	cntFddiMACShortGrpAddr OBJECT-TYPE
              		SYNTAX  INTEGER 
              		ACCESS  read-only
              		STATUS  optional
	      		DESCRIPTION
		  		"A possibly null set of 16 bit group addresses
		   		(aliases) for this MAC."
              		::= { cntFddiMACEntry 10 }

          	cntFddiMACTPri0 OBJECT-TYPE
              		SYNTAX  INTEGER 
              		ACCESS  read-only
              		STATUS   optional
	      		DESCRIPTION
		  		"Reference: Mac 2.2.1. It is reported as the
				 unsigned twos-complement of the number (as
				 described in the MAC specification; ref. MAC
				 7.3.5.2)."
              		::= { cntFddiMACEntry 11 }

          	cntFddiMACTPri1 OBJECT-TYPE
              		SYNTAX  INTEGER 
              		ACCESS  read-only
              		STATUS   optional
	      		DESCRIPTION
		  		"Reference: Mac 2.2.1. It is reported as the
				 unsigned twos-complement of the number (as
				 described in the MAC specification; ref. MAC
				 7.3.5.2)."
              		::= { cntFddiMACEntry 12 }

          	cntFddiMACTPri2 OBJECT-TYPE
              		SYNTAX  INTEGER 
              		ACCESS  read-only
              		STATUS   optional
	      		DESCRIPTION
		  		"Reference: Mac 2.2.1. It is reported as the
				 unsigned twos-complement of the number (as
				 described in the MAC specification; ref. MAC
				 7.3.5.2)."
              		::= { cntFddiMACEntry 13 }

          	cntFddiMACTPri3 OBJECT-TYPE
              		SYNTAX  INTEGER 
              		ACCESS  read-only
              		STATUS   optional
	      		DESCRIPTION
		  		"Reference: Mac 2.2.1. It is reported as the
				 unsigned twos-complement of the number (as
				 described in the MAC specification; ref. MAC
				 7.3.5.2)."
              		::= { cntFddiMACEntry 14 }

          	cntFddiMACTPri4 OBJECT-TYPE
              		SYNTAX  INTEGER 
              		ACCESS  read-only
              		STATUS   optional
	      		DESCRIPTION
		  		"Reference: Mac 2.2.1. It is reported as the
				 unsigned twos-complement of the number (as
				 described in the MAC specification; ref. MAC
				 7.3.5.2)."
              		::= { cntFddiMACEntry 15 }

          	cntFddiMACTPri5 OBJECT-TYPE
              		SYNTAX  INTEGER 
              		ACCESS  read-only
              		STATUS   optional
	      		DESCRIPTION
		  		"Reference: Mac 2.2.1. It is reported as the
				 unsigned twos-complement of the number (as
				 described in the MAC specification; ref. MAC
				 7.3.5.2)."
              		::= { cntFddiMACEntry 16 }

          	cntFddiMACTPri6 OBJECT-TYPE
              		SYNTAX  INTEGER 
              		ACCESS  read-only
              		STATUS   optional
	      		DESCRIPTION
		  		"Reference: Mac 2.2.1. It is reported as the
				 unsigned twos-complement of the number (as
				 described in the MAC specification; ref. MAC
				 7.3.5.2)."
              		::= { cntFddiMACEntry 17 }

          	cntFddiMACCopies OBJECT-TYPE
              		SYNTAX  Counter 
              		ACCESS  read-only
              		STATUS  optional 
	      		DESCRIPTION
		  		"The count of frames successfully received
				 into the station's receive buffers by this
				 MAC. Note that this count does not include the
				 frames that are not copied. This counter is
				 optional."
              		::= { cntFddiMACEntry 18 }

               	cntFddiMACTransmits OBJECT-TYPE
              		SYNTAX  Counter
              		ACCESS  read-only
              		STATUS  optional 
	      		DESCRIPTION
		  		"The count of frames transmitted by the MAC."
              		::= { cntFddiMACEntry 19 }

          	cntFddiMACTokens OBJECT-TYPE
              		SYNTAX  Counter
              		ACCESS  read-only
              		STATUS  optional 
	      		DESCRIPTION
		  		"The total count of the number of times the
				 station has received a token (total of
				 non-restricted and restricted) on this MAC.
				 This count is used for determination of
				 network load." 
              		::= { cntFddiMACEntry 20 }

          	cntFddiMACTvxExpires OBJECT-TYPE
              		SYNTAX  Counter
              		ACCESS  read-only
              		STATUS  optional 
	      		DESCRIPTION
		  		"A count of the times that TVX expired."
              		::= { cntFddiMACEntry 21 }

          	cntFddiMACNotCopies OBJECT-TYPE
              		SYNTAX  Counter
              		ACCESS  read-only
              		STATUS  optional 
	      		DESCRIPTION
		  		"The count of frames that should have been
				 copied but were not. This might occur due to
				 local buffer congestion. Because of
				 implementation considerations, this count may
				 be less than the actual number of frames not
				 copied. It is not a requirement that this
				 count be exact."
              		::= { cntFddiMACEntry 22 }

          	cntFddiMACLates OBJECT-TYPE
              		SYNTAX  Counter
              		ACCESS  read-only
              		STATUS  optional 
	      		DESCRIPTION
		  		"Reference: MAC 2.2.1, LateCt."
              		::= { cntFddiMACEntry 23 }

          	cntFddiMACRingOps OBJECT-TYPE
              		SYNTAX  Counter
              		ACCESS  read-only
              		STATUS  optional 
	      		DESCRIPTION
		  		"The count of the number of times the ring has
		   		entered the 'Ring Operational' state from 'Ring
		   		Not Operational' state. Because of
				implementation considerations, this count may
				not be exact."
              		::= { cntFddiMACEntry 24 }

          	cntFddiMACBaseFrames OBJECT-TYPE
              		SYNTAX  Counter
              		ACCESS  read-only
              		STATUS  optional 
	      		DESCRIPTION
		  		"The value of FddiMACFrameCt at the sample time 
		   		prior to the sample time when the
				FrameErrorThreshold was reached. It is used in
				reporting the condition to give the manager the
				necessary data to reconstruct the condition at
				the station. Reset when the associated
				condition becomes active."
              		::= { cntFddiMACEntry 25 }

          	cntFddiMACBaseErrs OBJECT-TYPE
              		SYNTAX  Counter
              		ACCESS  read-only
              		STATUS  optional 
	      		DESCRIPTION
		  		"The value of FddiMACErrorCt at the sample time 
		   		prior to the sample time when the
				FrameErrorThreshold was reached. It is used in
				reporting the condition to give the manager
				the necessary data to reconstruct the condition
				at the station. Reset to the current value of
				the corresponding 'real' counter when the
		   		associated condition becomes active."
              		::= { cntFddiMACEntry 26 }

          	cntFddiMACBaseLosts OBJECT-TYPE
              		SYNTAX  Counter
              		ACCESS  read-only
              		STATUS  optional 
	      		DESCRIPTION
		  		"The value of FddiMACLostCt at the sample time 
		   		prior to the sample time when the	
				FrameErrorThreshold was reached. It is used in
				reporting the condition to give the manager the
				necessary data to reconstruct the condition at
				the station. Reset to the current value of the
				corresponding 'real' counter when the
				associated condition becomes active."
              		::= { cntFddiMACEntry 27 }

          	cntFddiMACBaseTimeFrameError OBJECT-TYPE
              		SYNTAX  OCTET STRING 
              		ACCESS  read-only
              		STATUS  optional 
	      		DESCRIPTION
		  		"The value of the station timer at the sample
				 time prior to the sample time when the
				 FrameErrorThreshold was reached. It is used in
				 reporting the condition to give the manager
				 the necessary data to reconstruct the
				 condition at the station. Reset when the new 
		   		 condition becomes active."
              		::= { cntFddiMACEntry 28 }

          	cntFddiMACBaseNotCopies OBJECT-TYPE
              		SYNTAX  Counter
              		ACCESS  read-only
              		STATUS  optional 
	      		DESCRIPTION
		  		"The value of FddiMACNotCopiedCt at the sample
				 time prior to the sample time when the
				 NotCopiedThreshold was reached. It is used in
				 reporting the condition to give the manager
				 the necessary data to reconstruct the
				 condition at the station. Reset when the new 
		   		 condition becomes active."
              		::= { cntFddiMACEntry 29 }

          	cntFddiMACBaseTimeNotCopied OBJECT-TYPE
              		SYNTAX  OCTET STRING
              		ACCESS  read-only
              		STATUS  optional 
	      		DESCRIPTION
		  		"The value of the station timer at the sample
				 time prior to the sample time when the
				 NotCopiedThreshold was reached. It is used in
				 reporting the condition to give the manager
				 the necessary data to reconstruct the
				 condition at the station. Reset when the new 
		   		 condition becomes active."
              		::= { cntFddiMACEntry 30 }

          	cntFddiMACNotCopiedThreshold OBJECT-TYPE
              		SYNTAX  INTEGER 
              		ACCESS  read-only
              		STATUS  optional 
	      		DESCRIPTION
		  		"A threshold for determining when a MAC
				Condition report should be generated. It is
				used to determine when a station has an
				unacceptable count of frames 'not-copied'. It
				could be used as an indication of buffer
				congestion on this MAC."
              		::= { cntFddiMACEntry 31 }

          	cntFddiMACBaseCopies OBJECT-TYPE
              		SYNTAX  Counter
              		ACCESS  read-only
              		STATUS  optional 
	      		DESCRIPTION
		  		"The value of FddiMACCopiedCt at the sample
				 time prior to the sample time when the
				 NotCopiedThreshold was reached. It is used in
				 reporting the condition to give the manager
				 the necessary data to reconstruct the
				 condition at the station. Reset when the new 
		   		 condition becomes active."
              		::= { cntFddiMACEntry 32 }

          	cntFddiMACNotCopiedRatio OBJECT-TYPE
              		SYNTAX  INTEGER 
              		ACCESS  read-only
              		STATUS  optional 
	      		DESCRIPTION
		  		"This attribute is the value of the ratio:

		   			  FddiMACNotCopiedCt
		   		----------------------------------- * (2 ** 16)
		   		FddiMACCopiedCt + FddiMACNotCopiedCt"
              		::= { cntFddiMACEntry 33 }

          	cntFddiMACNotCopiedCondition OBJECT-TYPE
              		SYNTAX  INTEGER 
              		ACCESS  read-only
              		STATUS  optional 
	      		DESCRIPTION
		  		"Indicates the NotCopiedCondition is active
				 when set. Cleared when the condition clears
				 and on power up."
              		::= { cntFddiMACEntry 34 }

          	cntFddiMACLLCServiceAvailable OBJECT-TYPE
              		SYNTAX  INTEGER 
              		ACCESS  read-only
              		STATUS  optional 
	      		DESCRIPTION
		  		"Indicates whether the LLC Service is enabled."
              		::= { cntFddiMACEntry 35 }

          	cntFddiMACMasterSlaveLoopStatus OBJECT-TYPE
              		SYNTAX  INTEGER 
              		ACCESS  read-only
              		STATUS  optional 
	      		DESCRIPTION
		  		"Indicates this MAC's Master/Slave Loop Status.
		   		This status would be obtained with the Root MAC
		   		Information Protocol." 
              		::= { cntFddiMACEntry 36 }

          	cntFddiMACRootMACDownStreamPORTType OBJECT-TYPE
              		SYNTAX  INTEGER 
              		ACCESS  read-only
              		STATUS  optional 
	      		DESCRIPTION
		  		"Indicates the PC-Type of the first PORT that
				 is downstream of the Root MAC associated with
				 this MAC. The Root MAC information would be
				 determined in the Root MAC Information
				 Protocol."
              		::= { cntFddiMACEntry 37 }

          	cntFddiMACRootMACCurrentPath OBJECT-TYPE
              		SYNTAX  INTEGER 
              		ACCESS  read-only
              		STATUS  optional 
	      		DESCRIPTION
		  		"Indicates the current path of the Root MAC on
				 the same logical ring as this MAC. This Root
				 MAC information would be determined in the
				 Root MAC Information Protocol." 
              		::= { cntFddiMACEntry 38 }



          	-- the PATH group

          	cntFddiPATHNumber OBJECT-TYPE
              		SYNTAX  INTEGER (0..65535)
              		ACCESS  read-only
              		STATUS  mandatory
	      		DESCRIPTION
		  		"The total number of PATH implementations
				 across all SMTs on this network management
				 application entity."
              		::= { cntFddiPATH  1 }


          	-- the PATH table

          	cntFddiPATHTable OBJECT-TYPE
              		SYNTAX  SEQUENCE OF CntFddiPATHEntry
              		ACCESS  not-accessible
              		STATUS  mandatory
	      		DESCRIPTION
		  		"A list of PATH entries. The number of entries
				 is given by the value of snmpFddiPATHNumber."
              		::= { cntFddiPATH  2 }

          	cntFddiPATHEntry OBJECT-TYPE
              		SYNTAX  CntFddiPATHEntry
              		ACCESS  not-accessible
              		STATUS  mandatory
	      		DESCRIPTION
		  		"A PATH entry containing information common to
				 a given PATH."
			INDEX	{ cntFddiPATHSMTIndex }
              		::= { cntFddiPATHTable 1 }

          	CntFddiPATHEntry ::= SEQUENCE {
                  	cntFddiPATHSMTIndex
                        	INTEGER,
                  	cntFddiPATHIndex
                       		INTEGER,
                  	cntFddiPATHTraceMaxExpiration
                          	INTEGER,
                  	cntFddiPATHTVXLowerBound
                          	INTEGER,
                  	cntFddiPATHTMaxLowerBound
                          	INTEGER,
                  	cntFddiPATHType
                          	INTEGER,
                  	cntFddiPATHPORTOrder
                          	INTEGER,
                  	cntFddiPATHRingLatency
                          	INTEGER,
                  	cntFddiPATHTraceStatus
                          	INTEGER,
                  	cntFddiPATHSba
                          	INTEGER,
                  	cntFddiPATHSbaOverhead
                          	INTEGER,
                  	cntFddiPATHStatus
                          	INTEGER,
                  	cntFddiPATHTRmode
                          	INTEGER
              		}

          	cntFddiPATHSMTIndex OBJECT-TYPE
              		SYNTAX  INTEGER (1..65535)
              		ACCESS  read-only
              		STATUS  mandatory
	      		DESCRIPTION
		  		"The value of the SMT index associated with
				 this PATH."
              		::= { cntFddiPATHEntry 1 }

          	cntFddiPATHIndex OBJECT-TYPE
              		SYNTAX  INTEGER (1..65535)
              		ACCESS  read-only
              		STATUS  mandatory
	      		DESCRIPTION
		  		"A unique value for each PATH within a given
				 SMT. Its value ranges between 1 and the sum of
				 the values of snmpFddiSMTNonMasterCt and
				 snmpFddiSMTMasterCt on the given SMT."
              		::= { cntFddiPATHEntry 2 }

          	cntFddiPATHTraceMaxExpiration OBJECT-TYPE
              		SYNTAX  INTEGER 
              		ACCESS  read-only
              		STATUS  mandatory
	      		DESCRIPTION
		  		"Reference: SMT 9.4.4.2.2 TraceMax."
              		::= { cntFddiPATHEntry 3 }

          	cntFddiPATHTVXLowerBound OBJECT-TYPE
              		SYNTAX  INTEGER 
              		ACCESS  read-only
              		STATUS  optional
	      		DESCRIPTION
		  		"The lower bound of TVX supported for this
				 PATH."
              		::= { cntFddiPATHEntry 4 }

          	cntFddiPATHTMaxLowerBound OBJECT-TYPE
              		SYNTAX  INTEGER 
              		ACCESS  read-only
              		STATUS  optional
	      		DESCRIPTION
		  		"The lower bound of TMax supported for this
				 PATH class."
              		::= { cntFddiPATHEntry 5 }

          	cntFddiPATHType OBJECT-TYPE
              		SYNTAX  INTEGER 
              		ACCESS  read-only
              		STATUS  mandatory
	      		DESCRIPTION
		  		"This object describes the type of PATH:
		   		1 = Primary, 2 = Secondary, 3 = Local."
              		::= { cntFddiPATHEntry 6 }

          	cntFddiPATHPORTOrder OBJECT-TYPE
              		SYNTAX  INTEGER 
              		ACCESS  read-only
              		STATUS  mandatory
	      		DESCRIPTION
		  		"Tells whether the PORTs on this path are
				 numbered in ascending of descending order."
              		::= { cntFddiPATHEntry 7 }

          	cntFddiPATHRingLatency OBJECT-TYPE
              		SYNTAX  INTEGER 
              		ACCESS  read-only
              		STATUS  optional
	      		DESCRIPTION
		  		"Gives the total accumulated latency of the
				 ring associated with this PATH. May be
				 measured directly by the station or may be
				 calculated by a management station."
              		::= { cntFddiPATHEntry 8 }

          	cntFddiPATHTraceStatus OBJECT-TYPE
              		SYNTAX  INTEGER 
              		ACCESS  read-only
              		STATUS  optional
	      		DESCRIPTION
		  		"Gives the current trace status of the PATH."
              		::= { cntFddiPATHEntry 9 }

          	cntFddiPATHSba OBJECT-TYPE
              		SYNTAX  INTEGER 
              		ACCESS  read-only
              		STATUS  mandatory
	      		DESCRIPTION
		  		"The Synchronous Bandwidth Allocation for this
				 PATH within the station in octet units. In
				 stations that don't support synchronous
				 service, this attribute is read only and has
		   		 the value of 0."
              		::= { cntFddiPATHEntry 10 }

          	cntFddiPATHSbaOverhead OBJECT-TYPE
              		SYNTAX  INTEGER 
              		ACCESS  read-only
              		STATUS  mandatory
	      		DESCRIPTION
		  		"The Synchronous Bandwidth Allocation overhead
				 for this PATH (bytes/frame). In stations that
				 don't support synchronous service, this
				 attribute is read only and has the value of 0."
              		::= { cntFddiPATHEntry 11 }

          	cntFddiPATHStatus OBJECT-TYPE
              		SYNTAX  INTEGER 
              		ACCESS  read-only
              		STATUS  mandatory
	      		DESCRIPTION
		  		"The current status of the PATH."
              		::= { cntFddiPATHEntry 12 }

          	cntFddiPATHTRmode OBJECT-TYPE
              		SYNTAX  INTEGER 
              		ACCESS  read-only
              		STATUS  optional
	      		DESCRIPTION
		  		"Used by RMT to limit the duration of
				 restricted dialogs on a PATH."
              		::= { cntFddiPATHEntry 13 }


          	-- the PORT group

          	cntFddiPORTNumber OBJECT-TYPE
              		SYNTAX  INTEGER (0..65535)
              		ACCESS  read-only
              		STATUS  mandatory
	      		DESCRIPTION
		  		"The total number of PORT implementations
				 across all SMTs on this network management
				 application entity."
              		::= { cntFddiPORT  1 }


          	-- the PORT table

          	cntFddiPORTTable OBJECT-TYPE
              		SYNTAX  SEQUENCE OF CntFddiPORTEntry
              		ACCESS  not-accessible
              		STATUS  mandatory
	      		DESCRIPTION
		  		"A list of PORT entries. The number of entries
				 is given by the value of snmpFddiPORTNumber."
              		::= { cntFddiPORT  2 }

          	cntFddiPORTEntry OBJECT-TYPE
              		SYNTAX  CntFddiPORTEntry
              		ACCESS  not-accessible
              		STATUS  mandatory
	      		DESCRIPTION
		  		"A PORT entry containing information common to
				 a given PORT."
			INDEX	{ cntFddiPORTSMTIndex }
              		::= { cntFddiPORTTable 1 }

          	CntFddiPORTEntry ::= SEQUENCE {
                  	cntFddiPORTSMTIndex
                          	INTEGER,
                  	cntFddiPORTIndex
                          	INTEGER,
                  	cntFddiPORTFotxClass
                          	INTEGER,
                  	cntFddiPORTMaintLineState
                          	INTEGER,
                  	cntFddiPORTEBErrs
                          	Counter,
                  	cntFddiPORTBaseLerEstimate
                          	INTEGER,
                  	cntFddiPORTBaseLemRejects
                          	Counter,
                  	cntFddiPORTBaseLems
                          	Counter,
                  	cntFddiPORTBaseLerTimeStamp
                          	OCTET STRING
              		}

          	cntFddiPORTSMTIndex OBJECT-TYPE
              		SYNTAX  INTEGER (1..65535)
              		ACCESS  read-only
              		STATUS  mandatory
	      		DESCRIPTION
		  		"The value of the SMT index associated with
				 this PORT."
              		::= { cntFddiPORTEntry 1 }

          	cntFddiPORTIndex OBJECT-TYPE
              		SYNTAX  INTEGER (1..65535)
              		ACCESS  read-only
              		STATUS  mandatory
	      		DESCRIPTION
		  		"A unique value for each PORT within a given
				 SMT. Its value ranges between 1 and the sum of
				 the values of snmpFddiSMTNonMasterCt and
				 snmpFddiSMTMasterCt on the given SMT."
              		::= { cntFddiPORTEntry 2 }

          	cntFddiPORTFotxClass OBJECT-TYPE
              		SYNTAX  INTEGER 
              		ACCESS  read-only
              		STATUS  optional
	      		DESCRIPTION
		  		"The Fiber Optic Transmitter Class."
              		::= { cntFddiPORTEntry 3 }

          	cntFddiPORTMaintLineState OBJECT-TYPE
              		SYNTAX  INTEGER 
              		ACCESS  read-only
              		STATUS  optional
	      		DESCRIPTION
		  		"The current maintenance line status of this
				 PORT."
              		::= { cntFddiPORTEntry 4 }

          	cntFddiPORTEBErrs OBJECT-TYPE
              		SYNTAX  Counter
              		ACCESS  read-only
              		STATUS  optional
	      		DESCRIPTION
		  		"The count of the times an Elasticity Buffer
				 Error has occurred."
              		::= { cntFddiPORTEntry 5 }

          	cntFddiPORTBaseLerEstimate OBJECT-TYPE
              		SYNTAX  INTEGER 
              		ACCESS  read-only
              		STATUS  mandatory
	      		DESCRIPTION
		  		"The value of FddiPORTLerEstimate at the sample
				 time prior to when the sample time that the
				 PORT LER Event was generated (the condition
				 became active)."
              		::= { cntFddiPORTEntry 6 }


          	cntFddiPORTBaseLemRejects OBJECT-TYPE
              		SYNTAX  Counter
              		ACCESS  read-only
              		STATUS  mandatory
	      		DESCRIPTION
		  		"The value of FddiPORTLerRejectCt at the sample
				 time prior to when the sample time that the
				 PORT LER Event was generated (the condition
				 became active)."
              		::= { cntFddiPORTEntry 7 }

          	cntFddiPORTBaseLems OBJECT-TYPE
              		SYNTAX  Counter
              		ACCESS  read-only
              		STATUS  mandatory
	      		DESCRIPTION
		  		"The value of FddiPORTLerCt at the sample time
				 prior to when the sample time that the PORT
				 LER Event was generated (the condition became
				 active)."
              		::= { cntFddiPORTEntry 8 }

          	cntFddiPORTBaseLerTimeStamp OBJECT-TYPE
              		SYNTAX  OCTET STRING
              		ACCESS  read-only
              		STATUS  mandatory
	      		DESCRIPTION
		  		"The value of FddiSMTMsgTimestamp at the sample
				 time prior to when the sample time that the
				 PORT LER Event was generated (the condition
				 became active)."
              		::= { cntFddiPORTEntry 9 }



		-- the CNT Access Units SNMP group

   		cntsnmp       OBJECT IDENTIFIER ::= { cntau 11 }

   		cntsnmpconfig OBJECT IDENTIFIER ::= { cntsnmp 1 }

		cntMibVersion OBJECT-TYPE
			SYNTAX  IpAddress
			ACCESS  read-only
			STATUS  mandatory
			DESCRIPTION
				"The version identifier of the mib file that
				the agent has loaded from BBRAM."
			::= { cntsnmpconfig 1 }

		cntMibObjectCount OBJECT-TYPE
			SYNTAX  INTEGER
			ACCESS  read-only
			STATUS  mandatory
			DESCRIPTION
				"Number of objects in the MIB description file,
				!MIB, in this CNT platform.  This file contains
				objects from RFC 1213, RFC 1284, RFC 1285, and
				CNT's enterprise.  Depending upon the
				configuration of this node, the node may or may
				not support all of these objects."
			::= { cntsnmpconfig 2 }

		cntConfigVersion OBJECT-TYPE
			SYNTAX  INTEGER
			ACCESS  read-only
			STATUS  mandatory
			DESCRIPTION
				"Version number of this SNMP agent from the
				configuration record."
			::= { cntsnmpconfig 3 }

		cntProxyStatus OBJECT-TYPE
			SYNTAX  INTEGER {
				no-proxy(1),
				proxy-agent(2),
				proxied-node(3)
			}
			ACCESS  read-only
			STATUS  mandatory
			DESCRIPTION
				"This flag indicates whether this SNMP agent is
				 acting as a proxy, is being proxied, or is a
				 normally behaving SNMP agent."
			::= { cntsnmpconfig 4 }

		cntProxyCount OBJECT-TYPE
			SYNTAX  INTEGER
			ACCESS  read-only
			STATUS  mandatory
			DESCRIPTION
				"If this node is configured to operate as a
				proxy agent, this number reflects the number
				of proxied nodes that this node is configured
				to manage in !NDE."
			::= { cntsnmpconfig 5 }

		cntSnmpBufferCount OBJECT-TYPE
			SYNTAX  INTEGER
			ACCESS  read-only
			STATUS  mandatory
			DESCRIPTION
				"Number of buffers reserved for this SNMP
				agent for outgoing message from the
				configuration record."
			::= { cntsnmpconfig 6 }

		cntIfPollInterval OBJECT-TYPE
			SYNTAX  INTEGER
			ACCESS  read-only
			STATUS  mandatory
			DESCRIPTION
				"Number of seconds for the SNMP agent to wait
				between checks of the CNT platform's
				interfaces for operation status.  These
				interface checks result in the link down and
				link up traps.  This value is from the
				configuration record."
			::= { cntsnmpconfig 7 }

		cntIfNextPoll OBJECT-TYPE
			SYNTAX  INTEGER
			ACCESS  read-only
			STATUS  mandatory
			DESCRIPTION
				"Number of seconds for the next internal
				SNMP agent interface poll.  These interface
				checks result in the link down and link up
				traps.  This value is from the configuration
				record."
			::= { cntsnmpconfig 8 }

		cntDoDIPCount OBJECT-TYPE
			SYNTAX  INTEGER
			ACCESS  read-only
			STATUS  mandatory
			DESCRIPTION
				"The number of DoD IP addresses (internet
				records in !CFG) configured in this node
				that the agent detected upon startup.  This
				will not equal the number of interfaces on
				this node."
			::= { cntsnmpconfig 9 }

		cntDot3Count OBJECT-TYPE
			SYNTAX  INTEGER
			ACCESS  read-only
			STATUS  mandatory
			DESCRIPTION
				"The number of ethernet interfaces that are
				manageable by this agent on this node."
			::= { cntsnmpconfig 10 }

		cntFddiCount OBJECT-TYPE
			SYNTAX  INTEGER
			ACCESS  read-only
			STATUS  mandatory
			DESCRIPTION
				"The number of FDDI interfaces that are
				manageable by this agent on this node."
			::= { cntsnmpconfig 11 }

		cntFddiPortCount OBJECT-TYPE
			SYNTAX  INTEGER
			ACCESS  read-only
			STATUS  mandatory
			DESCRIPTION
				"The number of FDDI ports that are
				manageable by this agent on this node."
			::= { cntsnmpconfig 12 }

		cntDataLinkCount OBJECT-TYPE
			SYNTAX  INTEGER
			ACCESS  read-only
			STATUS  mandatory
			DESCRIPTION
				"The number of Data Link Layers Instances
				that are manageable by this agent on this node."
			::= { cntsnmpconfig 13 }

		cntLLC1Count OBJECT-TYPE
			SYNTAX  INTEGER
			ACCESS  read-only
			STATUS  mandatory
			DESCRIPTION
				"The number of Data Link Layers Instances of
				type Logical Link Control 1 (ISO 8802/2) that
				are manageable by this agent on this node."
			::= { cntsnmpconfig 14 }

		cntCofiVersion OBJECT-TYPE
			SYNTAX  IpAddress
			ACCESS  read-only
			STATUS  mandatory
			DESCRIPTION
				"The version of the the COmmon File
				Interface (COFI) module that is loaded into
				this node.  COFI is required by the snmp
				agent for access to some CNT system
				objects.  The version is in the format:
				version.day.month.year."
			::= { cntsnmpconfig 15 }

   		cntsnmpstat OBJECT IDENTIFIER ::= { cntsnmp 2 }

		cntMib2Requests OBJECT-TYPE
			SYNTAX  Counter
			ACCESS  read-only
			STATUS  mandatory
			DESCRIPTION
				"The number of requests received by the agent
				for mib-2 objects."
			::= { cntsnmpstat 1 }

		cntFddiRequests OBJECT-TYPE
			SYNTAX  Counter
			ACCESS  read-only
			STATUS  mandatory
			DESCRIPTION
				"The number of requests received by the agent
				for FDDI objects in the experimental or
				transmission subtree."
			::= { cntsnmpstat 2 }

		cntDot3Requests OBJECT-TYPE
			SYNTAX  Counter
			ACCESS  read-only
			STATUS  mandatory
			DESCRIPTION
				"The number of requests received by the agent
				for 802.3 objects in the experimental or
				transmission subtree."
			::= { cntsnmpstat 3 }

		cntCntRequests OBJECT-TYPE
			SYNTAX  Counter
			ACCESS  read-only
			STATUS  mandatory
			DESCRIPTION
				"The number of requests received by the agent
				for objects in the Computer Network Technology
				Corp. private enterprise subtree."
			::= { cntsnmpstat 4 }

		cntRowAdditions OBJECT-TYPE
			SYNTAX  Counter
			ACCESS  read-only
			STATUS  mandatory
			DESCRIPTION
				"The number of table row additions that have
				been successful through SNMP requests from a
				network management station."
			::= { cntsnmpstat 5 }

		cntRowModifies OBJECT-TYPE
			SYNTAX  Counter
			ACCESS  read-only
			STATUS  mandatory
			DESCRIPTION
				"The number of table row modifications that
				have been successful through SNMP requests
				from a network management station."
			::= { cntsnmpstat 6 }

		cntRowDeletions OBJECT-TYPE
			SYNTAX  Counter
			ACCESS  read-only
			STATUS  mandatory
			DESCRIPTION
				"The number of table row deletions that have
				been successful through SNMP requests from a
				network management station."
			::= { cntsnmpstat 7 }

		cntRowErrors OBJECT-TYPE
			SYNTAX  Counter
			ACCESS  read-only
			STATUS  mandatory
			DESCRIPTION
				"The number of table row additions that were
				attempted through SNMP requests from a
				network management station, but were not
				complete in a single request.  These requests
				were not successfully completed."
			::= { cntsnmpstat 8 }

		cntBadVersions OBJECT-TYPE
			SYNTAX  Counter
			ACCESS  read-only
			STATUS  mandatory
			DESCRIPTION
				"The number of table row additions that were
				attempted through SNMP requests from a
				network management station, but were not
				complete in a single request.  These requests
				were not successfully completed."
			::= { cntsnmpstat 9 }

		cntNoBuffers OBJECT-TYPE
			SYNTAX  Counter
			ACCESS  read-only
			STATUS  mandatory
			DESCRIPTION
				"The number of times the agent needed a buffer
				and did not have one.  The agent uses buffers
				when making requests to the MEs."
			::= { cntsnmpstat 10 }

		cntMailTimeouts OBJECT-TYPE
			SYNTAX  Counter
			ACCESS  read-only
			STATUS  mandatory
			DESCRIPTION
				"The number of timeouts received from the MEs
				when a mib request was given."
			::= { cntsnmpstat 11 }

		cntCachedResponses OBJECT-TYPE
			SYNTAX  Counter
			ACCESS  read-only
			STATUS  mandatory
			DESCRIPTION
				"The number of requests to the MEs that were
				cached.  Each cached message contains as many
				mib objects as the request to the ME."
			::= { cntsnmpstat 12 }

		cntUsedCaches OBJECT-TYPE
			SYNTAX  Counter
			ACCESS  read-only
			STATUS  mandatory
			DESCRIPTION
				"The number of objects for which the cached
				mib objects were used."
			::= { cntsnmpstat 13 }

   		cntsnmptrap OBJECT IDENTIFIER ::= { cntsnmp 3 }

		cntTrapDestCount OBJECT-TYPE
			SYNTAX  INTEGER
			ACCESS  read-only
			STATUS  mandatory
			DESCRIPTION
				"The number of trap destinations that the
				agent will forward the configured traps to."
			::= { cntsnmptrap 1 }

		cntLastTrapMsg OBJECT-TYPE
			SYNTAX  DisplayString
			ACCESS  read-only
			STATUS  mandatory
			DESCRIPTION
				"Textual description of the last trap message
				sent from this SNMP agent.  The object
				identifier for cntSysLastTrapMsg is sent
				along with each trap."
			::= { cntsnmptrap 2 }

		cntTrapTable OBJECT-TYPE
			SYNTAX  SEQUENCE OF CntTrapEntry
			ACCESS  not-accessible
			STATUS  mandatory
			DESCRIPTION
				"A list of trap entries.  There is a maximum
				of six trap entries.  These values, except
				TrapIf, are set in the configuration record."
			::= { cntsnmptrap 3 }

		cnttrapEntry OBJECT-TYPE
			SYNTAX  CntTrapEntry
			ACCESS  not-accessible
			STATUS  mandatory
			DESCRIPTION
				"A trap entry containing the information needed
				to send out a trap."
			INDEX	{ cnttrapIndex }
			::= { cntTrapTable 1 }

		CntTrapEntry ::= SEQUENCE {
		     cnttrapIndex
			INTEGER,
		     cnttrapAddress
			IpAddress,
		     cntsnmpTrapFlags
			INTEGER,
		     cntTrapFlags
			INTEGER,
		     cnttrapIf
			IpAddress
		}

		cnttrapIndex OBJECT-TYPE
			SYNTAX  INTEGER
			ACCESS  read-only
			STATUS  mandatory
			DESCRIPTION
				"Trap table index."
			::= { cnttrapEntry 1 }

		cnttrapAddress OBJECT-TYPE
			SYNTAX  IpAddress
			ACCESS  read-only
			STATUS  mandatory
			DESCRIPTION
				"Trap destination address."
			::= { cnttrapEntry 2 }

		cntsnmpTrapFlags OBJECT-TYPE
			SYNTAX  INTEGER
			ACCESS  read-only
			STATUS  mandatory
			DESCRIPTION
				"Flag setting specifying which types of traps
				to send to this destination.  This value is
				derived from 'or'ing the following values:
				cold start(0x01), link down(0x04), link
				up(0x08), and authentication failure(0x10)."
			::= { cnttrapEntry 3 }

		cntTrapFlags OBJECT-TYPE
			SYNTAX  INTEGER
			ACCESS  read-only
			STATUS  mandatory
			DESCRIPTION
				"Flag settings reserved for future enterprise
				specific trap enabling."
			::= { cnttrapEntry 4 }

		cnttrapIf OBJECT-TYPE
			SYNTAX  IpAddress
			ACCESS  read-only
			STATUS  mandatory
			DESCRIPTION
				"Trap source address."
			::= { cnttrapEntry 5 }

   		cntsnmpproxy OBJECT IDENTIFIER ::= { cntsnmp 4 }

		cntProxyTable OBJECT-TYPE
			SYNTAX  SEQUENCE OF CntProxyEntry
			ACCESS  not-accessible
			STATUS  mandatory
			DESCRIPTION
				"A list of proxy entries.  This table contains
				an entry for each proxied node from this proxy
				agent.  If this node is not configured as a
				proxy agent then this table is empty."
			::= { cntsnmpproxy 1 }

		cntproxyEntry OBJECT-TYPE
			SYNTAX  CntProxyEntry
			ACCESS  not-accessible
			STATUS  mandatory
			DESCRIPTION
				"A proxy entry containing the information
				needed to carry an SNMP request to a proxied
				node."
			INDEX	{ cntproxyIndex }
			::= { cntProxyTable 1 }

		CntProxyEntry	::= SEQUENCE {
			cntproxyIndex
				INTEGER,
			cntproxyAddress
				IpAddress,
			cntproxyNode
				IpAddress
		}

		cntproxyIndex OBJECT-TYPE
			SYNTAX  INTEGER
			ACCESS  read-only
			STATUS  mandatory
			DESCRIPTION
				"Proxy table index."
			::= { cntproxyEntry 1 }

		cntproxyAddress OBJECT-TYPE
			SYNTAX  IpAddress
			ACCESS  read-only
			STATUS  mandatory
			DESCRIPTION
				"Proxied node destination DoD IP address that
				is used by the NMS."
			::= { cntproxyEntry 2 }

		cntproxyNode OBJECT-TYPE
			SYNTAX  IpAddress
			ACCESS  read-only
			STATUS  mandatory
			DESCRIPTION
				"Proxied node destination CNT node address that
				is used by the local CNT router to access the
				destination."
			::= { cntproxyEntry 3 }
		

		-- CNT Access Units Diagnostics group
		--	most of the information contained in this group is not
		--	useful in atomic form, but rather is used by appli-
		--	cations for support personnel and customized displays
		--	and snmp applications.

		cntdiagnostics  OBJECT IDENTIFIER ::= { cntau 12 }

		cntTraceTable OBJECT-TYPE
			SYNTAX  SEQUENCE OF CntTraceEntry
			ACCESS  not-accessible
			STATUS  mandatory
			DESCRIPTION
				"List of entries in the global trace area."
			::= { cntdiagnostics 1 }

		cnttraceEntry OBJECT-TYPE
			SYNTAX  CntTraceEntry
			ACCESS  not-accessible
			STATUS  mandatory
			DESCRIPTION
				"A trace entry."
			INDEX	{ cnttraceIndex }
			::= { cntTraceTable 1 }

		CntTraceEntry ::= SEQUENCE {
			cnttraceIndex
				INTEGER,
			cnttraceType
				INTEGER,
			cnttraceCpu
				INTEGER,
			cnttraceData
				OCTET STRING
		}

		cnttraceIndex OBJECT-TYPE
			SYNTAX  INTEGER
			ACCESS  read-only
			STATUS  mandatory
			DESCRIPTION
				"The index which uniquely identifies the trace
				row instance in a CNT node."
			::= { cnttraceEntry 1 }

		cnttraceType OBJECT-TYPE
			SYNTAX  INTEGER
			ACCESS  read-only
			STATUS  mandatory
			DESCRIPTION
				"The type of trace entry."
			::= { cnttraceEntry 2 }

		cnttraceCpu OBJECT-TYPE
			SYNTAX  INTEGER {
				lcp-1(1),
				lcp-2(2),
				lcp-3(3),
				lcp-4(4),
				lcp-5(5),
				lcp-6(6),
				lcp-7(7)
			}
			ACCESS  read-only
			STATUS  mandatory
			DESCRIPTION
				"The CPU number of the module that entered
				this trace entry."
			::= { cnttraceEntry 3 }

		cnttraceData OBJECT-TYPE
			SYNTAX  OCTET STRING
			ACCESS  read-only
			STATUS  mandatory
			DESCRIPTION
				"The remaining 14 octets of trace information."
			::= { cnttraceEntry 4 }

		cntMailQueue  OBJECT IDENTIFIER ::= { cntdiagnostics 2 }

		cntMDMTable OBJECT-TYPE
			SYNTAX	SEQUENCE OF CntMDMEntry
			ACCESS	not-accessible
			STATUS	mandatory
			DESCRIPTION
				"A list of Message Distribution Manager (MDM)
				interprocessor queue global table entries."
			::= { cntMailQueue 1 }

		cntMDMEntry OBJECT-TYPE
			SYNTAX	CntMDMEntry
			ACCESS	not-accessible
			STATUS	mandatory
			DESCRIPTION
				"A Message Distribution Manager (MDM) queue
				global table entry."
			INDEX	{ cntmdmQIndex }
			::= { cntMDMTable 1 }

		CntMDMEntry ::= SEQUENCE {
			cntmdmQIndex
				INTEGER,
			cntmdmQName
				DisplayString,
			cntmdmQProcessId
				INTEGER,
			cntmdmQTaskId
				INTEGER
		}

		cntmdmQIndex OBJECT-TYPE
			SYNTAX  INTEGER
			ACCESS  read-only
			STATUS  mandatory
			DESCRIPTION
				"The relative index of the MDM entry in the
				system's global table."
			::= { cntMDMEntry 1 }

		cntmdmQName OBJECT-TYPE
			SYNTAX  DisplayString
			ACCESS  read-only
			STATUS  mandatory
			DESCRIPTION
				"The MDM queue name for this entry in the
				system global table."
			::= { cntMDMEntry 2 }

		cntmdmQProcessId OBJECT-TYPE
			SYNTAX  INTEGER
			ACCESS  read-only
			STATUS  mandatory
			DESCRIPTION
				"The MDM processor number for this entry in
				the system global table."
			::= { cntMDMEntry 3 }

		cntmdmQTaskId OBJECT-TYPE
			SYNTAX  INTEGER
			ACCESS  read-only
			STATUS  mandatory
			DESCRIPTION
				"The MDM task identifier for this entry in the
				system global table."
			::= { cntMDMEntry 4 }

		cntmdmQList OBJECT-TYPE
			SYNTAX  DisplayString
			ACCESS  read-only
			STATUS  mandatory
			DESCRIPTION
				"The MDM queue name list in one long string."
			::= { cntMailQueue 2 }

		
		-- Data Link Layer group

		cntdatalink OBJECT IDENTIFIER ::= { cntau 13 }

		cntdlNumber OBJECT-TYPE
			SYNTAX INTEGER
			ACCESS read-only
			STATUS mandatory
			DESCRIPTION
				"The number of network data link layers
				present on this system."
			::= { cntdatalink 1 }

		cntdlTable OBJECT-TYPE
			SYNTAX SEQUENCE OF CntDLEntry
			ACCESS not-accessible
			STATUS mandatory
			DESCRIPTION
				"A list of data link layer entries.  The
				number of entries is given by the value
				of cntdlNumber."
			::= { cntdatalink 2 }

		cntdlEntry OBJECT-TYPE
			SYNTAX CntDLEntry
			ACCESS not-accessible
			STATUS mandatory
			DESCRIPTION
				"A data link layer entry containing objects
				for a particular data link layer."
			INDEX	{ cntdlIndex }
			::= { cntdlTable 1 }
	
		CntDLEntry ::= SEQUENCE {
			cntdlIndex
				INTEGER,
			cntdlDescr
				DisplayString,
			cntdlType
				INTEGER,
			cntdlTypeofService
				INTEGER,
			cntdlMtu
				INTEGER,
			cntdlPortAddrLen
				INTEGER,
			cntdlMaxPort
				INTEGER,
			cntdlActivePort
				INTEGER,
			cntdlInOctets
				Counter,
			cntdlInUcastPkts
				Counter,
			cntdlInNUcastPkts
				Counter,
			cntdlInDiscards
				Counter,
			cntdlInErrors
				Counter,
			cntdlInUnknownProtos
				Counter,
			cntdlOutOctets
				Counter,
			cntdlOutUcastPkts
				Counter,
			cntdlOutNUcastPkts
				Counter,
			cntdlOutDiscards
				Counter,
			cntdlOutErrors
				Counter,
			cntdlOutQLen
				Gauge
		}

		cntdlIndex OBJECT-TYPE
			SYNTAX INTEGER
			ACCESS read-only
			STATUS mandatory
			DESCRIPTION
				"A unique value for each data link layer.
				It's value ranges between one and the value
				of dlNumber.  The value for each data link
				layer must remain constant at least from one
				reinitialization of the entity's network
				management system to the next
				reinitialization."
			::= { cntdlEntry 1 }

		cntdlDescr OBJECT-TYPE
			SYNTAX DisplayString
			ACCESS read-only
			STATUS mandatory
			DESCRIPTION
				"A textual string containing information
				about the data link layer.  This string
				should include the name of the manufacturer,
				the product name and the version of the data
				link layer."
			::= { cntdlEntry 2 }

		cntdlType OBJECT-TYPE
			SYNTAX INTEGER {
					llc1(1),
					llc2(2),
					llc3(3),
					snap(4),
					cnet(5),
					dnls(6),
					strp(7),
					ppp(8)
				}
			ACCESS read-only
			STATUS mandatory
			DESCRIPTION
				"The type of this data link layer."
			::= { cntdlEntry 3 }

		cntdlTypeofService OBJECT-TYPE
			SYNTAX INTEGER {
					unacked-connectionless(1),
					connection-oriented(2),
					acked-connectionless(3)
				}
			ACCESS read-only
			STATUS mandatory
			DESCRIPTION
				"The type of this data link layer service."
			::= { cntdlEntry 4 }
	
		cntdlMtu OBJECT-TYPE
			SYNTAX INTEGER
			ACCESS read-only
			STATUS mandatory
			DESCRIPTION
				"The size of the largest datagram which can
				be sent/received on this data link layer,
				specified in octets."
			::= { cntdlEntry 5 }
	
		cntdlPortAddrLen OBJECT-TYPE
			SYNTAX INTEGER
			ACCESS read-only
			STATUS mandatory
			DESCRIPTION
				"The length of all port addresses used by
				this data link layer service."
			::= { cntdlEntry 6 }
	
		cntdlMaxPort OBJECT-TYPE
			SYNTAX INTEGER
			ACCESS read-only
			STATUS mandatory
			DESCRIPTION
				"The maximum number of ports supported by this
				data link layer service."
			::= { cntdlEntry 7 }
	
		cntdlActivePort OBJECT-TYPE
			SYNTAX INTEGER
			ACCESS read-only
			STATUS mandatory
			DESCRIPTION
				"The current number of active ports."
			::= { cntdlEntry 8 }
	
		cntdlInOctets OBJECT-TYPE
			SYNTAX Counter
			ACCESS read-only
			STATUS mandatory
			DESCRIPTION
				"The total number of octets received on
				this data link layer."
			::= { cntdlEntry 9 }
	
		cntdlInUcastPkts OBJECT-TYPE
			SYNTAX Counter
			ACCESS read-only
			STATUS mandatory
			DESCRIPTION
				"The number of unicast packets delivered to
				a higher layer protocol."
			::= { cntdlEntry 10 }
	
		cntdlInNUcastPkts OBJECT-TYPE
			SYNTAX Counter
			ACCESS read-only
			STATUS mandatory
			DESCRIPTION
				"The number of non-unicast packets delivered
				to a higher layer protocol."
			::= { cntdlEntry 11 }
	
		cntdlInDiscards OBJECT-TYPE
			SYNTAX Counter
			ACCESS read-only
			STATUS mandatory
			DESCRIPTION
				"The number of inbound packets which were
				chosen to be discarded even though no errors
				had been detected to prevent their being
				deliverable to a higher layer protocol."
			::= { cntdlEntry 12 }
	
		cntdlInErrors OBJECT-TYPE
			SYNTAX Counter
			ACCESS read-only
			STATUS mandatory
			DESCRIPTION
				"The number of inbound packets that contained
				errors preventing them from being deliverable
				to a higher-layer protocol."
			::= { cntdlEntry 13 }
	
		cntdlInUnknownProtos OBJECT-TYPE
			SYNTAX Counter
			ACCESS read-only
			STATUS mandatory
			DESCRIPTION
				"The number of packets received via the data
				link layer which were discareded because of
				an unknown or unsupported protocol."
			::= { cntdlEntry 14 }
	
		cntdlOutOctets OBJECT-TYPE
			SYNTAX Counter
			ACCESS read-only
			STATUS mandatory
			DESCRIPTION
				"The total number of octets transmitted by this
				this data link layer service."
			::= { cntdlEntry 15 }
	
		cntdlOutUcastPkts OBJECT-TYPE
			SYNTAX Counter
			ACCESS read-only
			STATUS mandatory
			DESCRIPTION
				"The total number of packets that higher-level
				protocols requested be transmitted to a
				unicast address, including those that were
				discarded or not sent."
			::= { cntdlEntry 16 }
	
		cntdlOutNUcastPkts OBJECT-TYPE
			SYNTAX Counter
			ACCESS read-only
			STATUS mandatory
			DESCRIPTION
				"The total number of packets that higher-level
				protocols requested be transmitted to a
				non-unicast address, including those that were
				discarded or not sent."
			::= { cntdlEntry 17 }
	
		cntdlOutDiscards OBJECT-TYPE
			SYNTAX Counter
			ACCESS read-only
			STATUS mandatory
			DESCRIPTION
				"The number of outbound packets which were
				chose to be discarded even though no errors
				had been detected to prevent their being
				transmitted."
			::= { cntdlEntry 18 }
	
		cntdlOutErrors OBJECT-TYPE
			SYNTAX Counter
			ACCESS read-only
			STATUS mandatory
			DESCRIPTION
				"The number of outbound packets that could
				not be transmitted because of errors."
			::= { cntdlEntry 19 }
	
		cntdlOutQLen OBJECT-TYPE
			SYNTAX Gauge
			ACCESS read-only
			STATUS mandatory
			DESCRIPTION
				"The length of the output packet queue, in
				packets."
			::= { cntdlEntry 20 }
	
		cntdlPortTable OBJECT-TYPE
			SYNTAX SEQUENCE OF CntDLPortEntry
			ACCESS not-accessible
			STATUS mandatory
			DESCRIPTION
				"A list of data link layer entries.  The
				number of entries is given by the value of
				dlActivePorts."
			::= { cntdlEntry 21 }
	
		cntdlPortEntry OBJECT-TYPE
			SYNTAX CntDLPortEntry
			ACCESS not-accessible
			STATUS mandatory
			DESCRIPTION
				"A data link layer entry containing objects
				for a particular port."
			INDEX { cntdlPortIndex }
			::= { cntdlPortTable 1 }
	
		CntDLPortEntry ::= SEQUENCE {
			cntdlPortIndex
				INTEGER,
			cntdlState
				INTEGER,
			cntdlSourcePort
				INTEGER,
			cntdlDestPort
				INTEGER,
			cntdlPortType
				INTEGER
		}
	
		cntdlPortIndex OBJECT-TYPE
			SYNTAX INTEGER
			ACCESS read-only
			STATUS mandatory
			DESCRIPTION
				"The port entry's index."
			::= { cntdlPortEntry 1 }
	
		cntdlState OBJECT-TYPE
			SYNTAX INTEGER {
				connected(1),
				data-transfer(2),
				disconnected(3),
				waiting-for-ack(4),
				down(5),
				closed(6),
				listen(7),
				ack-sent(8)
			}
			ACCESS read-only
			STATUS mandatory
			DESCRIPTION
				"The state of this port."
			::= { cntdlPortEntry 2 }
	
		cntdlSourcePort OBJECT-TYPE
			SYNTAX INTEGER
			ACCESS read-only
			STATUS mandatory
			DESCRIPTION
				"The source port number."
			::= { cntdlPortEntry 3 }
	
		cntdlDestPort OBJECT-TYPE
			SYNTAX INTEGER
			ACCESS read-only
			STATUS mandatory
			DESCRIPTION
				"The destination port number."
			::= { cntdlPortEntry 4 }
	
		cntdlPortType OBJECT-TYPE
			SYNTAX INTEGER {
				dod-ip(1),
				arp(2),
				snmp(3)
			}
			ACCESS read-only
			STATUS mandatory
			DESCRIPTION
				"The port type.  This value is not redundant
				to dlType since a link layer service may
				support multiple port types.  For example, 
				LLC1 has both llc1 and snap ports."
			::= { cntdlPortEntry 5 }
	

		-- LLC1 data link layer group
	
		cntllc1 OBJECT IDENTIFIER ::= { cntdatalink 3 }
	
		cntllc1ConfigTable OBJECT-TYPE
			SYNTAX SEQUENCE OF CntLLC1ConfigEntry
			ACCESS not-accessible
			STATUS mandatory
			DESCRIPTION
				"A list of the LLC1 configuration entries."
			::= { cntllc1 1 }
	
		cntllc1ConfigEntry OBJECT-TYPE
			SYNTAX CntLLC1ConfigEntry
			ACCESS not-accessible
			STATUS mandatory
			DESCRIPTION
				"A LLC1 configuration entry."
			INDEX	{ cntllc1ConfigIndex }
			::= { cntllc1ConfigTable 1 }
	
		CntLLC1ConfigEntry ::= SEQUENCE {
			cntllc1ConfigIndex
				INTEGER,
			cntllc1DriverType
				INTEGER,
			cntllc1Addr
				OCTET STRING,
			cntllc1InitFlag
				INTEGER,
			cntllc1TraceFlag
				INTEGER,
			cntllc1BufCnt
				INTEGER,
			cntllc1BusId
				INTEGER,
			cntllc1CpuNum
				INTEGER,
			cntllc1BufPriority
				INTEGER,
			cntllc1WaitTimeOut
				INTEGER
		}
	
		cntllc1ConfigIndex OBJECT-TYPE
			SYNTAX INTEGER
			ACCESS read-only
			STATUS mandatory
			DESCRIPTION
				"The index that uniquely identifies an instance
				of a LLC1 process in a CNT node."
			::= { cntllc1ConfigEntry 1 }
	
		cntllc1DriverType OBJECT-TYPE
			SYNTAX INTEGER {
				cnt-node(1),
				fddi(2),
				fibre-trunk(3),
				native(4),
				ethernet(5),
				hippi(6)
			}
			ACCESS read-only
			STATUS mandatory
			DESCRIPTION
				"The physical layer device driver type that
				has identified to this llc1 service."
			::= { cntllc1ConfigEntry 2 }
	
		cntllc1Addr OBJECT-TYPE
			SYNTAX OCTET STRING
			ACCESS read-only
			STATUS mandatory
			DESCRIPTION
				"The MAC address for the physical layer over
				which this link layer is operating."
			::= { cntllc1ConfigEntry 3 }
	
		cntllc1InitFlag OBJECT-TYPE
			SYNTAX INTEGER {
				uninitialized(1),
				initialized(2)
			}
			ACCESS read-only
			STATUS mandatory
			DESCRIPTION
				"The initialization flag indicating whether
				or not this module has finished initializing
				the data link layer stack."
			::= { cntllc1ConfigEntry 4 }
	
		cntllc1TraceFlag OBJECT-TYPE
			SYNTAX INTEGER
			ACCESS read-only
			STATUS mandatory
			DESCRIPTION
				"The trace flags in bit-oriented form.  The
				values are as follows:
					.... ...1  - phase 2 entry point
					.... ..1.  - phase 3 entry point
					.... .1..  - messages in
					.... 1...  - transmit completions
					...1 ....  - messages received
					..1. ....  - message to a ULP."
			::= { cntllc1ConfigEntry 5 }
	
		cntllc1BufCnt OBJECT-TYPE
			SYNTAX INTEGER
			ACCESS read-only
			STATUS mandatory
			DESCRIPTION
				"The number of free buffers in the free pool."
			::= { cntllc1ConfigEntry 6 }
	
		cntllc1BusId OBJECT-TYPE
			SYNTAX INTEGER
			ACCESS read-only
			STATUS mandatory
			DESCRIPTION
				"The bus number for this network interface."
			::= { cntllc1ConfigEntry 7 }
	
		cntllc1CpuNum OBJECT-TYPE
			SYNTAX INTEGER {
				lcp-1(1),
				lcp-2(2),
				lcp-3(3),
				lcp-4(4),
				lcp-5(5),
				lcp-6(6),
				lcp-7(7)
			}
			ACCESS read-only
			STATUS mandatory
			DESCRIPTION
				"The CPU number where this data link layer is
				running, 1 through 8."
			::= { cntllc1ConfigEntry 8 }
	
		cntllc1BufPriority OBJECT-TYPE
			SYNTAX INTEGER
			ACCESS read-only
			STATUS mandatory
			DESCRIPTION
				"The assigned buffer priority for messages
				received from the physical layer."
			::= { cntllc1ConfigEntry 9 }
	
		cntllc1WaitTimeOut OBJECT-TYPE
			SYNTAX INTEGER
			ACCESS read-only
			STATUS mandatory
			DESCRIPTION
				"The wait timeout in seconds for XID/TEST
				frames sent to a peer llc1 data link layer."
			::= { cntllc1ConfigEntry 10 }
		
		cntllc1StatsTable OBJECT-TYPE
			SYNTAX SEQUENCE OF CntLLC1StatsEntry
			ACCESS not-accessible
			STATUS mandatory
			DESCRIPTION
				"A list of LLC1 statistics entries."
			::= { cntllc1 2 }
	
		cntllc1StatsEntry OBJECT-TYPE
			SYNTAX CntLLC1StatsEntry
			ACCESS not-accessible
			STATUS mandatory
			DESCRIPTION
				"A LLC1 statistics entry."
			INDEX	{ cntllc1StatIndex }
			::= { cntllc1StatsTable 1 }
	
		CntLLC1StatsEntry ::= SEQUENCE {
			cntllc1StatIndex
				INTEGER,
			cntllc1InXids
				Counter,
			cntllc1InTests
				Counter,
			cntllc1InUIs
				Counter,
			cntllc1InNoDsaps
				Counter,
			cntllc1InXidOks
				Counter,
			cntllc1InTestOks
				Counter,
			cntllc1InSnapIps
				Counter,
			cntllc1InSnapArps
				Counter,
			cntllc1InSnapNoProts
				Counter,
			cntllc1InSnapNoTypes
				Counter,
			cntllc1OutSnapIps
				Counter,
			cntllc1OutSnapArps
				Counter,
			cntllc1OutXids
				Counter,
			cntllc1OutXidResps
				Counter,
			cntllc1OutTests
				Counter,
			cntllc1OutTestResps
				Counter,
			cntllc1OutRetOks
				Counter,
			cntllc1OutFragPkts
				Counter
		}
	
		cntllc1StatIndex OBJECT-TYPE
			SYNTAX INTEGER
			ACCESS read-only
			STATUS mandatory
			DESCRIPTION
				"The index that uniquely identifies an instance
				of a LLC1 process in a CNT node."
			::= { cntllc1StatsEntry 1 }
	
		cntllc1InXids OBJECT-TYPE
			SYNTAX Counter
			ACCESS read-only
			STATUS mandatory
			DESCRIPTION
				"The number of LLC XID frames received from a
				peer data link layer."
			::= { cntllc1StatsEntry 2 }
	
		cntllc1InTests OBJECT-TYPE
			SYNTAX Counter
			ACCESS read-only
			STATUS mandatory
			DESCRIPTION
				"The number of LLC TEST frames received from a
				peer data link layer."
			::= { cntllc1StatsEntry 3 }
	
		cntllc1InUIs OBJECT-TYPE
			SYNTAX Counter
			ACCESS read-only
			STATUS mandatory
			DESCRIPTION
				"The number of LLC UI frames received from a
				peer data link layer."
			::= { cntllc1StatsEntry 4 }
	
		cntllc1InNoDsaps OBJECT-TYPE
			SYNTAX Counter
			ACCESS read-only
			STATUS mandatory
			DESCRIPTION
				"The number of unknown DSAPs received from a
				peer data link layer."
			::= { cntllc1StatsEntry 5 }
	
		cntllc1InXidOks OBJECT-TYPE
			SYNTAX Counter
			ACCESS read-only
			STATUS mandatory
			DESCRIPTION
				"The number of successful LLC XID frames from
				a peer data link layer."
			::= { cntllc1StatsEntry 6 }
	
		cntllc1InTestOks OBJECT-TYPE
			SYNTAX Counter
			ACCESS read-only
			STATUS mandatory
			DESCRIPTION
				"The number of successful LLC TEST frames from
				a peer data link layer."
			::= { cntllc1StatsEntry 7 }
	
		cntllc1InSnapIps OBJECT-TYPE
			SYNTAX Counter
			ACCESS read-only
			STATUS mandatory
			DESCRIPTION
				"The number of SNAP IP packets received from a
				peer SNAP."
			::= { cntllc1StatsEntry 8 }
	
		cntllc1InSnapArps OBJECT-TYPE
			SYNTAX Counter
			ACCESS read-only
			STATUS mandatory
			DESCRIPTION
				"The number of SNAP ARP packets received from
				a peer SNAP."
			::= { cntllc1StatsEntry 9 }
	
		cntllc1InSnapNoProts OBJECT-TYPE
			SYNTAX Counter
			ACCESS read-only
			STATUS mandatory
			DESCRIPTION
				"The number of unknown SNAP protocols received
				from a peer SNAP."
			::= { cntllc1StatsEntry 10 }
	
		cntllc1InSnapNoTypes OBJECT-TYPE
			SYNTAX Counter
			ACCESS read-only
			STATUS mandatory
			DESCRIPTION
				"The number of unknown SNAP ethertypes received
				from a peer SNAP."
			::= { cntllc1StatsEntry 11 }
	
		cntllc1OutSnapIps OBJECT-TYPE
			SYNTAX Counter
			ACCESS read-only
			STATUS mandatory
			DESCRIPTION
				"The number of SNAP IP packets sent to a peer
				 SNAP."
			::= { cntllc1StatsEntry 12 }
	
		cntllc1OutSnapArps OBJECT-TYPE
			SYNTAX Counter
			ACCESS read-only
			STATUS mandatory
			DESCRIPTION
				"The number of SNAP ARP packets sent to a peer
				SNAP."
			::= { cntllc1StatsEntry 13 }
	
		cntllc1OutXids OBJECT-TYPE
			SYNTAX Counter
			ACCESS read-only
			STATUS mandatory
			DESCRIPTION
				"The number of LLC XID requests sent to a peer
				data link layer."
			::= { cntllc1StatsEntry 14 }
	
		cntllc1OutXidResps OBJECT-TYPE
			SYNTAX Counter
			ACCESS read-only
			STATUS mandatory
			DESCRIPTION
				"The number of LLC XID responses received from
				a peer data link layer."
			::= { cntllc1StatsEntry 15 }
	
		cntllc1OutTests OBJECT-TYPE
			SYNTAX Counter
			ACCESS read-only
			STATUS mandatory
			DESCRIPTION
				"The number of LLC TEST requests sent to a peer
				data link layer."
			::= { cntllc1StatsEntry 16 }
	
		cntllc1OutTestResps OBJECT-TYPE
			SYNTAX Counter
			ACCESS read-only
			STATUS mandatory
			DESCRIPTION
				"The number of LLC TEST responses sent to a
				peer data link layer."
			::= { cntllc1StatsEntry 17 }
	
		cntllc1OutRetOks OBJECT-TYPE
			SYNTAX Counter
			ACCESS read-only
			STATUS mandatory
			DESCRIPTION
				"The number of packets passed successfully to 
				the physical layer."
			::= { cntllc1StatsEntry 18 }
	
		cntllc1OutFragPkts OBJECT-TYPE
			SYNTAX Counter
			ACCESS read-only
			STATUS mandatory
			DESCRIPTION
				"The number of packet sent with fragments."
			::= { cntllc1StatsEntry 19 }
	
	
		cntllc1ErrorTable OBJECT-TYPE
			SYNTAX SEQUENCE OF CntLLC1ErrorEntry
			ACCESS not-accessible
			STATUS mandatory
			DESCRIPTION
				"A list of LLC1 error entries."
			::= { cntllc1 3 }
	
		cntllc1ErrorEntry OBJECT-TYPE
			SYNTAX CntLLC1ErrorEntry
			ACCESS not-accessible
			STATUS mandatory
			DESCRIPTION
				"A LLC1 error entry."
			INDEX	{ cntllc1ErrorIndex }
			::= { cntllc1ErrorTable 1 }
	
		CntLLC1ErrorEntry ::= SEQUENCE {
			cntllc1ErrorIndex
				INTEGER,
			cntllc1ArpMailErrs
				Counter,
			cntllc1IpMailErrs
				Counter,
			cntllc1OutXmitErrs
				Counter,
			cntllc1OutMcastErrs
				Counter,
			cntllc1XidErrs
				Counter,
			cntllc1TestErrs
				Counter,
			cntllc1InBadTypes
				Counter,
			cntllc1OutMismIpSizes
				Counter,
			cntllc1OutBadIpSizes
				Counter,
			cntllc1InMismIpSizes
				Counter,
			cntllc1InBadIpSizes
				Counter,
			cntllc1InLateXids
				Counter,
			cntllc1InLateTests
				Counter,
			cntllc1OutTooBigs
				Counter,
			cntllc1OutNoRooms
				Counter,
			cntllc1OutRetBads
				Counter
		}
	
		cntllc1ErrorIndex OBJECT-TYPE
			SYNTAX INTEGER
			ACCESS read-only
			STATUS mandatory
			DESCRIPTION
				"The index that uniquely identifies an instance
				of a LLC1 process in a CNT node."
			::= { cntllc1ErrorEntry 1 }
	
		cntllc1ArpMailErrs OBJECT-TYPE
			SYNTAX Counter
			ACCESS read-only
			STATUS mandatory
			DESCRIPTION
				"The number of errors encountered when mailing
				to ARP."
			::= { cntllc1ErrorEntry 2 }
	
		cntllc1IpMailErrs OBJECT-TYPE
			SYNTAX Counter
			ACCESS read-only
			STATUS mandatory
			DESCRIPTION
				"The number of errors encountered when mailing
				to IP."
			::= { cntllc1ErrorEntry 3 }
	
		cntllc1OutXmitErrs OBJECT-TYPE
			SYNTAX Counter
			ACCESS read-only
			STATUS mandatory
			DESCRIPTION
				"The number of times and error was received
				from the physical layer when a transmission
				was attempted by this data link layer."
			::= { cntllc1ErrorEntry 4 }
	
		cntllc1OutMcastErrs OBJECT-TYPE
			SYNTAX Counter
			ACCESS read-only
			STATUS mandatory
			DESCRIPTION
				"The number of times and error was received
				from the physical layer when a multicast
				message was attempted by this data link layer."
			::= { cntllc1ErrorEntry 5 }
	
		cntllc1XidErrs OBJECT-TYPE
			SYNTAX Counter
			ACCESS read-only
			STATUS mandatory
			DESCRIPTION
				"The number of times and error was received
				from the physical layer when an LLC XID message
				was attempted by this data link layer."
			::= { cntllc1ErrorEntry 6 }
	
		cntllc1TestErrs OBJECT-TYPE
			SYNTAX Counter
			ACCESS read-only
			STATUS mandatory
			DESCRIPTION
				"The number of times and error was received
				from the physical layer when an LLC TEST
				message was attempted by this data link layer."
			::= { cntllc1ErrorEntry 7 }
	
		cntllc1InBadTypes OBJECT-TYPE
			SYNTAX Counter
			ACCESS read-only
			STATUS mandatory
			DESCRIPTION
				"The number of messages received from a peer
				data link layer with invalid or unsupported
				LLC type fields."
			::= { cntllc1ErrorEntry 8 }
	
		cntllc1OutMismIpSizes OBJECT-TYPE
			SYNTAX Counter
			ACCESS read-only
			STATUS mandatory
			DESCRIPTION
				"The number of messages received from a ULP
				that has an included IP header that indicates
				the message size is smaller than the actual
				size of the message."
			::= { cntllc1ErrorEntry 9 }
	
		cntllc1OutBadIpSizes OBJECT-TYPE
			SYNTAX Counter
			ACCESS read-only
			STATUS mandatory
			DESCRIPTION
				"The number of messages received from a ULP
				that has an included IP header that indicates
				the message size is larger than the actual
				size of the message."
			::= { cntllc1ErrorEntry 10 }
	
		cntllc1InMismIpSizes OBJECT-TYPE
			SYNTAX Counter
			ACCESS read-only
			STATUS mandatory
			DESCRIPTION
				"The number of messages received from a 
				physical layer that has an included IP header
				that indicates the message size is smaller
				than the actual size of the message."
			::= { cntllc1ErrorEntry 11 }
	
		cntllc1InBadIpSizes OBJECT-TYPE
			SYNTAX Counter
			ACCESS read-only
			STATUS mandatory
			DESCRIPTION
				"The number of messages received from a 
				physical layer that has an included IP header
				that indicates the message size is larger
				than the actual size of the message."
			::= { cntllc1ErrorEntry 12 }
	
		cntllc1InLateXids OBJECT-TYPE
			SYNTAX Counter
			ACCESS read-only
			STATUS mandatory
			DESCRIPTION
				"The number of times an LLC XID request was
				sent to a peer data link layer and the return
				reponse was late or invalid."
			::= { cntllc1ErrorEntry 13 }
	
		cntllc1InLateTests OBJECT-TYPE
			SYNTAX Counter
			ACCESS read-only
			STATUS mandatory
			DESCRIPTION
				"The number of times an LLC TEST request was
				sent to a peer data link layer and the return
				reponse was late or invalid."
			::= { cntllc1ErrorEntry 14 }
	
		cntllc1OutTooBigs OBJECT-TYPE
			SYNTAX Counter
			ACCESS read-only
			STATUS mandatory
			DESCRIPTION
				"The number of times this link layer service
				could not build the outgoing message due to
				a Maximum Transmission Unit (MTU) limitation."
			::= { cntllc1ErrorEntry 15 }
	
		cntllc1OutNoRooms OBJECT-TYPE
			SYNTAX Counter
			ACCESS read-only
			STATUS mandatory
			DESCRIPTION
				"The number of times this data link layer
				service could not build the outgoing message
				due to lack of space in the s_message area of
				the buffer."
			::= { cntllc1ErrorEntry 16 }
	
		cntllc1OutRetBads OBJECT-TYPE
			SYNTAX Counter
			ACCESS read-only
			STATUS mandatory
			DESCRIPTION
				"The number of times the physical layer
				returned an error upon return of the message
				to this data link layer service."
			::= { cntllc1ErrorEntry 17 }
	
	
	
		-- the CNT Access Units LUA group
	
		cntlua   OBJECT IDENTIFIER ::= { cntau 14 }

		cntLuaCount OBJECT-TYPE
			SYNTAX  INTEGER 
			ACCESS  read-only
			STATUS  mandatory
			DESCRIPTION
				"The number of Logical Unit Adaptors (LUAs)
				present on this system."
			::= { cntlua 1 }

		cntLuaTable OBJECT-TYPE
			SYNTAX  SEQUENCE OF CntLuaEntry
			ACCESS  not-accessible
			STATUS  mandatory
			DESCRIPTION
				"A list of entries describing an individual
				Logical Unit Adaptor (LUA).  A specific
				lua object is terminated with the channel
				number."
			::= { cntlua 2 }

		cntluaEntry OBJECT-TYPE
			SYNTAX  CntLuaEntry
			ACCESS  not-accessible
			STATUS  mandatory
			DESCRIPTION
				"An individual LUA entry."
			INDEX { cntluaIf }
			::= { cntLuaTable 1 }

		CntLuaEntry ::= SEQUENCE {
			cntluaIf
				INTEGER,
			cntluaNumber
				INTEGER,
			cntSubChanCount
				INTEGER
		}

		cntluaIf OBJECT-TYPE
			SYNTAX  INTEGER
			ACCESS  read-only
			STATUS  mandatory
			DESCRIPTION
				"The corresponding SNMP interface index for
				this LUA."
			::= { cntluaEntry 1 }
	
		cntluaNumber OBJECT-TYPE
			SYNTAX  INTEGER
			ACCESS  read-only
			STATUS  mandatory
			DESCRIPTION
				"The LUA number (0-255)."
			::= { cntluaEntry 2 }
	
		cntSubChanCount OBJECT-TYPE
			SYNTAX  INTEGER
			ACCESS  read-only
			STATUS  mandatory
			DESCRIPTION
				"The number of subchannels on the LUA (0-255)."
			::= { cntluaEntry 3 }
	
		cntSubChanTable OBJECT-TYPE
			SYNTAX  SEQUENCE OF CntSubchanEntry
			ACCESS  not-accessible
			STATUS  mandatory
			DESCRIPTION
				"A list of entries describing an individual
				subchannel.  A specific subchannel object is
				referenced from the LUA table with instance
				object identifiers .lua.subchannel."
			::= { cntluaEntry 4 }

		cntsubchanEntry OBJECT-TYPE
			SYNTAX  CntSubchanEntry
			ACCESS  not-accessible
			STATUS  mandatory
			DESCRIPTION
				"An individual subchannel entry."
			INDEX { cntsctIndex }
			::= { cntSubChanTable 1 }

		CntSubchanEntry	::= SEQUENCE {
			cntsctIndex
				INTEGER,
			cntsctNumber
				INTEGER,
			cntsctTxStatus
				INTEGER,
			cntsctRxStatus
				INTEGER,
			cntsctSubChanStatus
				INTEGER,
			cntsctState
				INTEGER,
			cntsctRxCredit
				INTEGER,
			cntsctRxMsgs
				Counter,
			cntsctRxMsgBytes
				Counter,
			cntsctRxDataBytes
				Counter,
			cntsctTxMsgs
				Counter,
			cntsctTxMsgBytes
				Counter,
			cntsctTxDataBytes
				Counter,
			cntsctTxErrMsgs
				Counter,
			cntsctTotalBytes
				Counter,
			cntsctDrecPid
				DisplayString,
			cntsctDrecTask
				DisplayString
		}

		cntsctIndex OBJECT-TYPE
			SYNTAX  INTEGER
			ACCESS  read-only
			STATUS  mandatory
			DESCRIPTION
				"The relative subchannel index for this lua."
			::= { cntsubchanEntry 1 }

		cntsctNumber OBJECT-TYPE
			SYNTAX  INTEGER
			ACCESS  read-only
			STATUS  mandatory
			DESCRIPTION
				"The sub-channel number (0-255)."
			::= { cntsubchanEntry 2 }

		cntsctTxStatus OBJECT-TYPE
			SYNTAX  INTEGER
			ACCESS  read-only
			STATUS  mandatory
			DESCRIPTION
				"Bit value for the transmit status.
					Bit	Definition
					0	Transmit to be cancelled
					4	Transmit in operation
					8	Buffer available to subchannel
					9	Subchannel ready to accept
						POST_XMITs"
			::= { cntsubchanEntry 3 }

		cntsctRxStatus OBJECT-TYPE
			SYNTAX  INTEGER 
			ACCESS  read-only
			STATUS  mandatory
			DESCRIPTION
				"Bit value for the receive status.
					Bit	Definition
					0	Receive operation begun from
						host
					1	Receive enabled/disabled
					2	Cancel current receive message
						sequence
					3	Pending associated data
						sequence
					4	Request transport error
						notification"
			::= { cntsubchanEntry 4 }

		cntsctSubChanStatus OBJECT-TYPE
			SYNTAX  INTEGER
			ACCESS  read-only
			STATUS  mandatory
			DESCRIPTION
				"Bit value for the device subchannel status.
					Bit	Definition
					0	Subchannel is allocated
					1	Subchannel is established
					2	Subchannel is sharable
					3	Subchannel has dedicated
						buffers
					4	Subchannel has pending
						completion
					5	Subchannel has xmit multiple
						from user
					6	Subchannel has receive multiple
						from user
					7	Subchannel has buffer not
						available condition
					8	Subchannel reason for no buffer
						(0=no credit; 1=no buffers)
					9	Subchannel has network level
						doing flow control
					10	Subchannel has pending connect
					11	Subchannel has transmitted
						disconnect
					12	Subchannel ignores buffer not
						available condition
					13	Subchannel support Bus0 if not
						set, Bus1 if set
					14	Subchannel has possible error
						during data transfer
					15	Subchannel is allocated"
			::= { cntsubchanEntry 5 }

		cntsctState OBJECT-TYPE
			SYNTAX  INTEGER
			ACCESS  read-only
			STATUS  mandatory
			DESCRIPTION
				"Bit value for the subchannel state.
					Bit	Definition
					0	Wait flag
					1	Subchannel busy
					2	Pending command retry
					3	Pending completion status
					4	Pending unsolicited status
					6	Status stacked
					7	Damage control active flag"
			::= { cntsubchanEntry 6 }

		cntsctRxCredit OBJECT-TYPE
			SYNTAX  INTEGER
			ACCESS  read-only
			STATUS  mandatory
			DESCRIPTION
				"Current receive buffer credit."
			::= { cntsubchanEntry 7 }

		cntsctRxMsgs OBJECT-TYPE
			SYNTAX  Counter
			ACCESS  read-only
			STATUS  mandatory
			DESCRIPTION
				"Receive message count."
			::= { cntsubchanEntry 8 }

		cntsctRxMsgBytes OBJECT-TYPE
			SYNTAX  Counter
			ACCESS  read-only
			STATUS  mandatory
			DESCRIPTION
				"Receive message byte count."
			::= { cntsubchanEntry 9 }

		cntsctRxDataBytes OBJECT-TYPE
			SYNTAX  Counter
			ACCESS  read-only
			STATUS  mandatory
			DESCRIPTION
				"Receive data byte count."
			::= { cntsubchanEntry 10 }

		cntsctTxMsgs OBJECT-TYPE
			SYNTAX  Counter
			ACCESS  read-only
			STATUS  mandatory
			DESCRIPTION
				"Transmit message count."
			::= { cntsubchanEntry 11 }

		cntsctTxMsgBytes OBJECT-TYPE
			SYNTAX  Counter
			ACCESS  read-only
			STATUS  mandatory
			DESCRIPTION
				"Transmit message byte count."
			::= { cntsubchanEntry 12 }

		cntsctTxDataBytes OBJECT-TYPE
			SYNTAX  Counter
			ACCESS  read-only
			STATUS  mandatory
			DESCRIPTION
				"Transmit data byte count."
			::= { cntsubchanEntry 13 }

		cntsctTxErrMsgs OBJECT-TYPE
			SYNTAX  Counter
			ACCESS  read-only
			STATUS  mandatory
			DESCRIPTION
				"Transmit error message count."
			::= { cntsubchanEntry 14 }

		cntsctTotalBytes OBJECT-TYPE
			SYNTAX  Counter
			ACCESS  read-only
			STATUS  mandatory
			DESCRIPTION
				"Total number of bytes transmitted and 
				received for this subchannel."
			::= { cntsubchanEntry 15 }

		cntsctDrecPid OBJECT-TYPE
			SYNTAX  DisplayString
			ACCESS  read-only
			STATUS  mandatory
			DESCRIPTION
				"Channel PID name."
			::= { cntsubchanEntry 16 }

		cntsctDrecTask OBJECT-TYPE
			SYNTAX  DisplayString
			ACCESS  read-only
			STATUS  mandatory
			DESCRIPTION
				"Device specific driver task name."
			::= { cntsubchanEntry 17 }

	--
	--	CNT supported traps
	--
	--	coldStart TRAP-TYPE
	--		ENTERPRISE snmp
	--		DESCRIPTION
	--			"A coldstart trap signifies that the cnt
	--			node has reset such that the agent's
	--			configuration or the implementation may be
	--			altered."
	--		::= 0

	--	linkDown TRAP-TYPE
	--		ENTERPRISE snmp
	--		VARIABLES { ifIndex }
	--		DESCRIPTION
	--			"a linkdown trap signifies that the cnt
	--			agent recognizes a failure in one of the
	--			communications links/interfaces represented
	--			in the agent's configuration."
	--		::= 2


	--	linkUp TRAP-TYPE
	--		ENTERPRISE snmp
	--		VARIABLES { ifIndex }
	--		DESCRIPTION
	--			"a linkup trap signifies that the cnt agent
	--			recognizes that one of the communications
	--			links/interfaces represented in the agent's
	--			configuration has come up."
	--		::= 3

	--	authenticationFailure TRAP-TYPE
	--		ENTERPRISE snmp
	--		DESCRIPTION
	--			"a authentication failure trap signifies
	--			that the cnt agent has rejected a manage-
	--			ment station request based on an invalid
	--			community string."
	--		::= 4

		cntInformationalMsg TRAP-TYPE
			ENTERPRISE cntau
			VARIABLES { cntMsgTaskName,
				    cntMsgNumber,
				    cntMsgCpuNumber,
				    cntMsgNodeNumber,
				    cntMsgDateTime,
				    cntMsgContent }
			DESCRIPTION
				"A cnt level one trap signifies that an
				event has occured that is informational in
				severity.  The network will not be affected
				by this error."
			::= 1

		cntPossibleErrMsg TRAP-TYPE
			ENTERPRISE cntau
			VARIABLES { cntMsgTaskName,
				    cntMsgNumber,
  			 	    cntMsgCpuNumber,
				    cntMsgNodeNumber,
				    cntMsgDateTime,
				    cntMsgContent }
			DESCRIPTION
				"A cnt level two trap signifies that an
				event has occured that is possibly severe
				in nature.  The scope of this failure is
				dependent on the network design."
			::= 2

		cntSevereErrMsg TRAP-TYPE
			ENTERPRISE cntau
			VARIABLES { cntMsgTaskName,
				    cntMsgNumber,
				    cntMsgCpuNumber,
				    cntMsgNodeNumber,
				    cntMsgDateTime,
				    cntMsgContent }
			DESCRIPTION
				"A cnt level three trap signifies that an
				event has occured that is unrecoverable.
				Some aspect of the CNT network will not
				function as expected.  Related aspects may
				also be affected."
			::= 3

		cntCriticalErrMsg TRAP-TYPE
			ENTERPRISE cntau
			VARIABLES { cntMsgTaskName,
				    cntMsgNumber,
				    cntMsgCpuNumber,
				    cntMsgNodeNumber,
				    cntMsgDateTime,
				    cntMsgContent }
			DESCRIPTION
				"A cnt level four trap signifies that an
     				event has occured that is critical and 
				possibly fatal.  Some aspect of the cnt
				network will not function or is seriously
				impaired.  This failure will likely affect
				related functions as well."
			::= 4

	END
