-- Copyright 1994 General DataComm Inc., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.

-- Revision History
-- Version   Date	Name		Description
-- 1.00A     31-Oct-94  W. Meltzer	Initial Revision
-- 1.01A     27-Jan-95  W. Meltzer	Remove datxCarrierDropAck
-- 1.01B     28-Sep-95  C. Amorossi	Add datxAlarmStatus to StatusTable

GDCDATX-MIB DEFINITIONS ::= BEGIN

IMPORTS
	enterprises,TimeTicks		FROM RFC1155-SMI
	OBJECT-TYPE			FROM RFC-1212
	DisplayString			FROM RFC1213-MIB
	SCinstance			FROM GDCMACRO-MIB;

gdc 			OBJECT IDENTIFIER ::= { enterprises 498 }
datx			OBJECT IDENTIFIER ::= { gdc 7 }
datxSystem		OBJECT IDENTIFIER ::= { datx 1 }
dtx2011			OBJECT IDENTIFIER ::= { datx 2 }

datxVersion		OBJECT IDENTIFIER ::= { datxSystem 1 }
datxMaintenance		OBJECT IDENTIFIER ::= { datxSystem 2 }
datxConfiguration	OBJECT IDENTIFIER ::= { datxSystem 3 }
datxDiagnostics		OBJECT IDENTIFIER ::= { datxSystem 4 }
datxStatus	 	OBJECT IDENTIFIER ::= { datxSystem 5 }

-- This MIB module uses the extended OBJECT-TYPE macro as
-- defined in RFC 1212.

-- The implementation of all groups is mandatory for all products that
-- support a DS1 interface.

-- Note:  All rows in all tables defined within this MIB module are
-- virtual.  They can neither be created or deleted by management
-- operations.


datxMIBversion OBJECT-TYPE
    SYNTAX DisplayString (SIZE (5))
    ACCESS read-only
    STATUS mandatory
    DESCRIPTION
    	"Identifies the version of the MIB. The format of the version
    	is x.yzT, where 'x' identifies the major revision number, 'y'
    	identifies the minor revision number, 'z' identifies the
    	typographical revision, and T identifies the test revision.
    	Acceptable values for the individual revision components are
    	as follows:

    		x: 1 - 9
    		y: 0 - 9
    		z: 0 - 9
    		T: A - Z

    	Upon formal release, no designation for the test revision will
    	be present."
    ::= { datxVersion 1 }


-- *****************************************************************************
-- The GDC Datx Maintenance Table
-- *****************************************************************************

datxMaintTable OBJECT-TYPE
	SYNTAX	SEQUENCE OF DatxMaintEntry
	ACCESS	not-accessible
	STATUS	mandatory
	DESCRIPTION
		"This table describes the maintenance objects for the unit "
	::= { datxMaintenance 1 }

datxMaintEntry OBJECT-TYPE
	SYNTAX	DatxMaintEntry
	ACCESS	not-accessible
	STATUS	mandatory
	DESCRIPTION
		"An entry in the GDC Datx Maintenance Table."
	INDEX	{ datxMaintIndex }
	::= { datxMaintTable 1 }

DatxMaintEntry ::=
	SEQUENCE {
		datxMaintIndex
			SCinstance,
		datxFirmwareRev
			DisplayString,
		datxDefaultInit
			INTEGER,
		datxFrontPanel
			INTEGER,
		datxLedStatus
			OCTET STRING
		}

datxMaintIndex OBJECT-TYPE
	SYNTAX	SCinstance
	ACCESS	read-only
	STATUS	mandatory
	DESCRIPTION
		"The index value which uniquely identifies the interface to
	        which this entry is applicable.  This has the form of a
        	slot, line, drop, and sub-identifier."
	::= { datxMaintEntry 1 }

datxFirmwareRev OBJECT-TYPE
	SYNTAX	DisplayString (SIZE(2))
	ACCESS	read-only
	STATUS	mandatory
	DESCRIPTION
		"The version number of the firmware, to allow products to
		know which revision is installed.  The released version
		number is sequenced from --, A-, ... AA, ... ZZ.  Test
		versions are numerical from 01 to 99."
	::= { datxMaintEntry 2 }

datxDefaultInit OBJECT-TYPE
        SYNTAX  INTEGER {
                        normal(1),
                        factoryDefault(2)
                }
        ACCESS  read-write
        STATUS  mandatory
        DESCRIPTION
                "This is used to allow the NonVolatile Configuration to
                be set to a factory default state.  When this value is set to
                factoryDefault(2) the unit will perform
                a reset to make the default configuration take affect.
                The value of normal(1) will be returned when the initialization
                is complete."
        ::= { datxMaintEntry 3 }

datxFrontPanel OBJECT-TYPE
        SYNTAX  INTEGER {
                        inhibit(1),
                        enable(2)
                }
        ACCESS  read-write
        STATUS  mandatory
        DESCRIPTION
                "This variable is used to indicate whether the front
                panel switches are operational or not.

                 'inhibit' refers to when the front panel switches are
                not operational.

                 'enable' refers to when the front panel switches are
                operational."

        ::= { datxMaintEntry 4 }

datxLedStatus OBJECT-TYPE
	SYNTAX  OCTET STRING (SIZE(2))
	ACCESS  read-only
	STATUS  mandatory
	DESCRIPTION
		"Returns a bitwise snapshot of the front panel LED state.
		Octet 1 bit 7 - not used
		        bit 6 - ON
		        bit 5 - RD
		        bit 4 - SD
		        bit 3 - CS
		        bit 2 - CO
		        bit 1 - ALM
		        bit 0 - TM

		Octet 2 bit 7 - not used
		        bit 6 - ST
		        bit 5 - LL
		        bit 4 - RDL
                        bit 3 - future use
                        bit 2 - future use
                        bit 1 - future use
                        bit 0 - future use"
 	::= { datxMaintEntry 5 }


-- *****************************************************************************
-- The GDC Datx Configuration Tables
-- *****************************************************************************

datxTransConfigTable OBJECT-TYPE
        SYNTAX	SEQUENCE OF  DatxTransConfigEntry
        ACCESS	not-accessible
        STATUS	mandatory
        DESCRIPTION
		"This table describes the DATX transmission mode
		configuration options"
        ::= { datxConfiguration 1 }

datxTransConfigEntry OBJECT-TYPE
        SYNTAX	DatxTransConfigEntry
        ACCESS	not-accessible
        STATUS	mandatory
        DESCRIPTION
                "An entry in the transmission configuration table"
        INDEX	{ datxTransConfigIndex }
	::= { datxTransConfigTable 1 }

DatxTransConfigEntry ::=
        SEQUENCE {
		datxTransConfigIndex
			SCinstance,
		datxBaudRate
			INTEGER,
		datxSyncTxClockSource
			INTEGER,
		datxEiaSyncClock
			INTEGER
		}

datxTransConfigIndex OBJECT-TYPE
        SYNTAX  SCinstance
        ACCESS  read-only
        STATUS	mandatory
        DESCRIPTION
		"The index value which uniquely identifies the interface to
	        which this entry is applicable.  This has the form of a
        	slot, line, drop, and sub-identifier."
        ::= { datxTransConfigEntry 1 }

datxBaudRate OBJECT-TYPE
        SYNTAX INTEGER {
			asynchronous(1),
			synchronous1200(2),
			synchronous2400(3),
			synchronous4800(4),
			synchronous7200(5),
			synchronous9600(6),
			synchronous14400(7),
			synchronous19200(8)
		}
        ACCESS	read-write
        STATUS	mandatory
        DESCRIPTION
		"SYNC/ASYNC Mode operation and Baud Rates"
        ::={ datxTransConfigEntry 2 }

datxSyncTxClockSource OBJECT-TYPE
        SYNTAX	INTEGER {
			internal(1),
			slave(2),
			external(3)
		}
        ACCESS	read-write
        STATUS	mandatory
        DESCRIPTION
		"Synchronous Tx Clock Configuration"
        ::={ datxTransConfigEntry 3 }

datxEiaSyncClock OBJECT-TYPE
        SYNTAX	INTEGER {
			disable(1),
			enable(2)
		}
        ACCESS	read-write
        STATUS	mandatory
        DESCRIPTION
                "Control for the EIA sync clock"
        ::={ datxTransConfigEntry 4 }

-- EIA configuration

datxEiaConfigTable OBJECT-TYPE
        SYNTAX  SEQUENCE OF  DatxEiaConfigEntry
        ACCESS   not-accessible
        STATUS  mandatory
        DESCRIPTION
		"DATX EIA line configuration options"
        ::= { datxConfiguration 2 }

datxEiaConfigEntry OBJECT-TYPE
        SYNTAX DatxEiaConfigEntry
        ACCESS   not-accessible
        STATUS  mandatory
        DESCRIPTION
                "An entry in the EIA config table"
        INDEX   { datxEIAIndex }
        ::= { datxEiaConfigTable 1 }

DatxEiaConfigEntry ::=
        SEQUENCE {
		datxEIAIndex
			SCinstance,
		datxCarrierControl
			INTEGER,
		datxRtsMode
			INTEGER,
		datxRtsCtsDelay
			INTEGER,
		datxEiaRdlControl
			INTEGER,
		datxDsrInAl
			INTEGER,
		datxEiaAlControl
			INTEGER
		}

datxEIAIndex OBJECT-TYPE
        SYNTAX  SCinstance
        ACCESS  read-only
        STATUS mandatory
        DESCRIPTION
		"The index value which uniquely identifies the interface to
	        which this entry is applicable.  This has the form of a
        	slot, line, drop, and sub-identifier."
        ::= { datxEiaConfigEntry 1 }

datxCarrierControl OBJECT-TYPE
        SYNTAX	INTEGER {
			dtr(1),
			rts(2)
		}
        ACCESS	read-write
        STATUS	mandatory
        DESCRIPTION
		""
        ::={ datxEiaConfigEntry 2 }

datxRtsMode OBJECT-TYPE
        SYNTAX	INTEGER {
			real(1),
			forced(2)
		}
        ACCESS	read-write
        STATUS	mandatory
        DESCRIPTION
		"RTS mode selection"
        ::={ datxEiaConfigEntry 3 }

datxRtsCtsDelay OBJECT-TYPE
        SYNTAX	INTEGER {
			t8mSec(1),
			t75mSec(2)
		}
        ACCESS	read-write
        STATUS	mandatory
        DESCRIPTION
		"RTS/CTS Delay time"
        ::={ datxEiaConfigEntry 4 }

datxEiaRdlControl OBJECT-TYPE
        SYNTAX	INTEGER {
			disabled(1),
			enabled(2)
		}
        ACCESS	read-write
        STATUS	mandatory
        DESCRIPTION
		"EIA RDL control selection"
        ::={ datxEiaConfigEntry 5 }

datxDsrInAl OBJECT-TYPE
        SYNTAX	INTEGER {
			off(1),
			on(2)
		}
        ACCESS	read-write
        STATUS	mandatory
        DESCRIPTION
		"Selection for providing DSR will in AL mode"
        ::={ datxEiaConfigEntry 6 }

datxEiaAlControl OBJECT-TYPE
        SYNTAX	INTEGER {
			disabled(1),
			enabled(2)
		}
        ACCESS	read-write
        STATUS	mandatory
        DESCRIPTION
		"EIA AL control"
        ::={ datxEiaConfigEntry 7 }


-- Misc configuration

datxMiscConfigTable OBJECT-TYPE
        SYNTAX	SEQUENCE OF  DatxMiscConfigEntry
        ACCESS	not-accessible
        STATUS	mandatory
        DESCRIPTION
		"DATX misc configuration options"
        ::= { datxConfiguration 3 }

datxMiscConfigEntry OBJECT-TYPE
        SYNTAX	DatxMiscConfigEntry
        ACCESS	not-accessible
        STATUS	mandatory
        DESCRIPTION
                "An entry in the misc config table"
        INDEX   { datxMiscIndex }
        ::= { datxMiscConfigTable 1 }

DatxMiscConfigEntry ::=
        SEQUENCE {
		datxMiscIndex
			SCinstance,
		datxSystemStatusOption
			INTEGER,
		datxDualSignalingTimer
			INTEGER,
		datxRegenCharLength
			INTEGER,
		datxRegenMode
			INTEGER,
		datxAsyncRate
			INTEGER
		}

datxMiscIndex OBJECT-TYPE
        SYNTAX	SCinstance
        ACCESS	read-only
        STATUS	mandatory
        DESCRIPTION
		"The index value which uniquely identifies the interface to
	        which this entry is applicable.  This has the form of a
        	slot, line, drop, and sub-identifier."
        ::= { datxMiscConfigEntry 1 }

datxSystemStatusOption OBJECT-TYPE
        SYNTAX	INTEGER {
			disabled(1),
			enabled(2)
		}
        ACCESS	read-write
        STATUS	mandatory
        DESCRIPTION
		"Causes to drop CTS in master mode when remote drops line"
        ::={ datxMiscConfigEntry 2 }

datxDualSignalingTimer OBJECT-TYPE
        SYNTAX	INTEGER {
			disable(1),
			time3Sec(2),
			time1Sec(3),
			immediate(4)
		}
        ACCESS	read-write
        STATUS	mandatory
        DESCRIPTION
		""
        ::={ datxMiscConfigEntry 3 }


datxRegenCharLength OBJECT-TYPE
        SYNTAX  INTEGER {
			bits8(1),
			bits9(2),
			bits10(3),
			bits11(4)
			}
        ACCESS	read-write
        STATUS	mandatory
        DESCRIPTION
		"Synchronous Tx Clock Configuration"
        ::={ datxMiscConfigEntry 4 }

datxRegenMode OBJECT-TYPE
        SYNTAX	INTEGER {
			enable(1),
			disable(2)
		}
        ACCESS	read-write
        STATUS	mandatory
        DESCRIPTION
                "Regen Mode Control"
        ::={ datxMiscConfigEntry 5 }

datxAsyncRate OBJECT-TYPE
        SYNTAX	INTEGER {
			async4800(1),
			async7200(2),
			async9600(3),
			async14400(4),
			async19200(5)
		}
        ACCESS	read-write
        STATUS	mandatory
        DESCRIPTION
                ""
        ::={ datxMiscConfigEntry 6 }

-- *****************************************************************************
-- The GDC Datx Diagnostics Tables
-- *****************************************************************************

datxDiagnosticsTable OBJECT-TYPE
        SYNTAX	SEQUENCE OF  DatxDiagEntry
        ACCESS	not-accessible
        STATUS	mandatory
        DESCRIPTION
		"DATX diagnostics options"
        ::= { datxDiagnostics 1 }

datxDiagEntry OBJECT-TYPE
        SYNTAX DatxDiagEntry
        ACCESS   not-accessible
        STATUS  mandatory
        DESCRIPTION
		"List of Diagnostic Tests and Status Indicators
		related to the tests"

        INDEX   { datxDiagnosticsIndex }
        ::= { datxDiagnosticsTable 1 }

DatxDiagEntry ::=
        SEQUENCE {
		datxDiagnosticsIndex
			SCinstance,
		datxDiagTest
			INTEGER,
		datxTestError
			INTEGER,
		datxTestDuration
			TimeTicks
		}

datxDiagnosticsIndex OBJECT-TYPE
        SYNTAX  SCinstance
        ACCESS  read-only
        STATUS mandatory
        DESCRIPTION
		"The index value which uniquely identifies the interface to
	        which this entry is applicable.  This has the form of a
        	slot, line, drop, and sub-identifier."
        ::= { datxDiagEntry 1 }

datxDiagTest OBJECT-TYPE
        SYNTAX	INTEGER {
			noTest(1),
			selfTest(2),
                        analoop(3),
			analoopSelfTest(4),
			remoteDL(5),
			remoteDLselfTest(6)
		}
        ACCESS	read-write
        STATUS	mandatory
        DESCRIPTION
		"Perform diagnostic tests on a unit
		noTest -           stops any test in progress
		selfTest -         sends a selftest pattern
		analoop -          puts the unit into analog loopback
		analoopSelfTest -  puts the unit into analog loopback with
		                   a self test pattern
		remoteDL -         performs a remote digital loopback
		remoteDLselfTest - performs a remote digital loopback with
		                   a self test pattern"
        ::={ datxDiagEntry 2 }

datxTestError OBJECT-TYPE
        SYNTAX	INTEGER {
			noError(1),
			testError(2)
		}
        ACCESS	read-only
        STATUS	mandatory
        DESCRIPTION
		"Test result indicator, shows the results of the last test"
        ::={ datxDiagEntry 3 }

datxTestDuration OBJECT-TYPE
	SYNTAX	TimeTicks
        ACCESS	read-only
        STATUS	mandatory
        DESCRIPTION
		"Indicates the time duration of any test in progress"
        ::={ datxDiagEntry 4 }


--*****************************************************************************
--*****************************************************************************
datxStatusTable OBJECT-TYPE
        SYNTAX	SEQUENCE OF  DatxStatusEntry
        ACCESS	not-accessible
        STATUS	mandatory
        DESCRIPTION
		"DATX Status indicators"
        ::= { datxStatus 1 }

datxStatusEntry OBJECT-TYPE
        SYNTAX	DatxStatusEntry
        ACCESS	not-accessible
        STATUS	mandatory
        DESCRIPTION
                "Entry in the status indicator table"
        INDEX   { datxStatusIndex }
        ::= { datxStatusTable 1 }

DatxStatusEntry ::=
        SEQUENCE {
		datxStatusIndex
			SCinstance,
		datxDTRstatus
			INTEGER,
		datxRDLstatus
			INTEGER,
		datxCOstatus
			INTEGER,
		datxCTSstatus
			INTEGER,
		datxRTSstatus
			INTEGER,
		datxTMstatus
			INTEGER,
		datxALstatus
			INTEGER,
		datxDSRstatus
			INTEGER,
		datxRXclock
			INTEGER,
		datxTXclock
			INTEGER,
		datxEXTclock
			INTEGER,
		datxAlarmStatus
			OCTET STRING
		}

datxStatusIndex OBJECT-TYPE
        SYNTAX  SCinstance
        ACCESS  read-only
        STATUS mandatory
        DESCRIPTION
		"The index value which uniquely identifies the interface to
	        which this entry is applicable.  This has the form of a
        	slot, line, drop, and sub-identifier."
        ::= { datxStatusEntry 1 }


datxDTRstatus OBJECT-TYPE
        SYNTAX	INTEGER {
			off(1),
			on(2)
		}
        ACCESS	read-only
        STATUS	mandatory
        DESCRIPTION
		"DTR EIA status indicator "
        ::={ datxStatusEntry 2 }

datxRDLstatus OBJECT-TYPE
        SYNTAX	INTEGER {
			off(1),
			on(2)
			}
        ACCESS	read-only
        STATUS	mandatory
        DESCRIPTION
		"RDL EIA control status indicator"
        ::={ datxStatusEntry 3 }

datxCOstatus OBJECT-TYPE
        SYNTAX	INTEGER {
			off(1),
			on(2)
		}
        ACCESS	read-only
        STATUS	mandatory
        DESCRIPTION
		"CO EIA status indicator "
        ::={ datxStatusEntry 4 }

datxCTSstatus OBJECT-TYPE
        SYNTAX	INTEGER {
			off(1),
			on(2)
		}
        ACCESS	read-only
        STATUS	mandatory
        DESCRIPTION
		"CTS EIA indicator "
        ::={ datxStatusEntry 5 }

datxRTSstatus OBJECT-TYPE
        SYNTAX	INTEGER {
			off(1),
			on(2)
		}
        ACCESS	read-only
        STATUS	mandatory
        DESCRIPTION
		"RTS EIA indicator"
        ::={ datxStatusEntry 6 }

datxTMstatus OBJECT-TYPE
        SYNTAX	INTEGER {
			off(1),
			on(2)
		}
        ACCESS	read-only
        STATUS	mandatory
        DESCRIPTION
		"Test mode EIA indicator"
        ::={ datxStatusEntry 7 }

datxALstatus OBJECT-TYPE
        SYNTAX	INTEGER {
			off(1),
			on(2)
		}
        ACCESS	read-only
        STATUS	mandatory
        DESCRIPTION
		"Analoop EIA status indicator "
        ::={ datxStatusEntry 8 }

datxDSRstatus OBJECT-TYPE
        SYNTAX	INTEGER {
			off(1),
			on(2)
		}
        ACCESS	read-only
        STATUS	mandatory
        DESCRIPTION
		"DSR EIA status indicator "
        ::={ datxStatusEntry 9 }

datxRXclock OBJECT-TYPE
        SYNTAX	INTEGER {
			inactive(1),
			active(2)
		}
        ACCESS	read-only
        STATUS	mandatory
        DESCRIPTION
		"RxClk activity indicator "
        ::={ datxStatusEntry 10 }

datxTXclock OBJECT-TYPE
        SYNTAX	INTEGER {
			inactive(1),
			active(2)
		}
        ACCESS	read-only
        STATUS	mandatory
        DESCRIPTION
		"TxClk activity indicator "
        ::={ datxStatusEntry 11 }

datxEXTclock OBJECT-TYPE
        SYNTAX	INTEGER {
			inactive(1),
			active(2)
		}
        ACCESS	read-only
        STATUS	mandatory
        DESCRIPTION
		"External clock activity indicator "
        ::={ datxStatusEntry 12 }

datxAlarmStatus  OBJECT-TYPE
	SYNTAX	  OCTET STRING (SIZE (1..255))
	ACCESS	  read-only
	STATUS	  mandatory
	DESCRIPTION
		"The current alarms of the unit without the alarm masks."
        ::={ datxStatusEntry 13 }

-- **************************************************************************
--                    DTX2011  Alarms
-- **************************************************************************

dtx2011AlarmData	OBJECT IDENTIFIER ::= { dtx2011 1 }
dtx2011NoResponseAlm	OBJECT IDENTIFIER ::= { dtx2011AlarmData 1 }
dtx2011DiagRxErrAlm	OBJECT IDENTIFIER ::= { dtx2011AlarmData 2 }
dtx2011PowerUpAlm	OBJECT IDENTIFIER ::= { dtx2011AlarmData 3 }
dtx2011DCDLossAlm	OBJECT IDENTIFIER ::= { dtx2011AlarmData 4 }
dtx2011NoExtClockAlm	OBJECT IDENTIFIER ::= { dtx2011AlarmData 5 }

END
