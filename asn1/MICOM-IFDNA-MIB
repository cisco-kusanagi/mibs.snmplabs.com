--
-- MIB Revision Dated: 09-07-96 
--
-- 
-- MIB Revision : 1.0 dated 1-17-97
-- Change Desc. : None. 
-- 
-- MIB Revision : 1.1 dated 3-20-97
-- Change Desc. : Specified ranges for different objects. 
--
--
-- MIB Revision : 1.2 dated 04-22-97
-- Change Desc. : Specified Capabilities for objects.
--
-- MIB Revision : 1.3 dated 5-17-97
-- Change Desc. : Updated Description entry DESC -BP
--
--
-- MIB Revision : 1.4 dated 8-7-98
-- Change Desc. : Increased the range to 1 to 34 for (mcm/nvm)IfDNADigits,
--                                                  S. Gaur

MICOM-IFDNA-MIB DEFINITIONS ::= BEGIN
	IMPORTS
		OBJECT-TYPE
                    			FROM RFC-1212
		micom-oscar 
				FROM MICOM-OSCAR-MIB
		DisplayString 
				FROM SNMPv2-TC;


-- group OBJECT IDENTIFIERs

micom-ifdna OBJECT IDENTIFIER ::= {micom-oscar 18}
ifDna OBJECT IDENTIFIER ::= {micom-ifdna 1}
ifNvDna OBJECT IDENTIFIER ::= {micom-ifdna 2}


-- Interface DNA Map Table
--   This table contains one entry for each Interface which has a
--   DNA associated with it.

mcmIfDnaTable OBJECT-TYPE
	SYNTAX      SEQUENCE OF McmIfDnaEntry
	ACCESS      not-accessible
	STATUS      mandatory
	DESCRIPTION
	  "NAME = ;
	   DESC = The Interface DNA Map Table.;
	   HELP = ;
	   CAPABILITIES = NET_CFG, VPN_DISP;"
   ::= {ifDna 1}

mcmIfDnaEntry OBJECT-TYPE
	SYNTAX      McmIfDnaEntry
	ACCESS      not-accessible
	STATUS      mandatory
	DESCRIPTION
	  "NAME = ;
	   DESC = Each entry corresponds to each interface \
		  which has a DNA  associated with it.;
	   HELP = ;
	   CAPABILITIES = ;"
	
   INDEX       { mcmIfDnaIfIndex, mcmIfDnaType }
   ::= {mcmIfDnaTable 1}

McmIfDnaEntry ::= SEQUENCE {
                        mcmIfDnaIfIndex
                           INTEGER,
                        mcmIfDnaType
                           INTEGER,
                        mcmIfDNADigits
                           DisplayString,
                        mcmIfDnaStatus
                           INTEGER
                    }
                           
mcmIfDnaIfIndex OBJECT-TYPE
	SYNTAX      INTEGER (1..255)
	ACCESS      read-only
	STATUS      mandatory
	DESCRIPTION
	  "NAME = ;
	   DESC = The unique identifier of the interface. \
		  Same value as the  ifIndex from MIB-II.;
	   HELP = First of the indicies to a row in this \
		  table.;
	   CAPABILITIES = ;"
   ::= {mcmIfDnaEntry 1}

mcmIfDnaType OBJECT-TYPE
	SYNTAX      INTEGER { provisioned(1), learnt(2) }
	ACCESS      read-only
	STATUS      mandatory
	DESCRIPTION
	  "NAME = ;
	   DESC = Indicates whether the DNA on this interface \
		  was provisioned by the user or was \
		  learned from the switch;
	   HELP = This is the second index \
		  identifying a row in \
		  this table.;
	   CAPABILITIES = ;"
   ::= {mcmIfDnaEntry 2}

mcmIfDNADigits OBJECT-TYPE
	SYNTAX      DisplayString(SIZE(1..34))
	ACCESS      read-write
	STATUS      mandatory
	DESCRIPTION
	  "NAME = ;
	   DESC = The DNA digits in ASCII format which \
		  uniquely identify the row in the table.;
	   HELP = Every interface has an unique DNA number \
		  assigned to it.;
	   CAPABILITIES = ;"
   ::= {mcmIfDnaEntry 3}

mcmIfDnaStatus OBJECT-TYPE
	SYNTAX      INTEGER { valid(1), active(2), invalid(3) }
	ACCESS      read-write
	STATUS      mandatory
	DESCRIPTION
	  "NAME = ;
	   DESC = Indicates the validity of the row in \
		  the table.;
	   HELP = A value of active means \
		  this is the DNA used by the NAC to \
		  register with the NAS. A value of valid \
		  means that the row is valid but not \
		  used to register with the NAS. It is \
		  left to the implementor whether to \
		  remove a row from the table when the \
		  value of this object is equal to invalid.;
	   CAPABILITIES = ;"
   ::= {mcmIfDnaEntry 4}


-- Flash Parameters
--   This table contains the system parameters stored in permanent
--   memory. This is used to store the provisioned DNA in permanent
--   memory. It contains the management information that should be made
--   available by all implementations of OSCAR.


-- Interface DNA Map Table
--   This table contains one entry for each Interface which has a
--   DNA associated with it.

nvmIfDnaTable OBJECT-TYPE
	SYNTAX      SEQUENCE OF NvmIfDnaEntry
	ACCESS      not-accessible
	STATUS      mandatory
	DESCRIPTION
	  "NAME = ;
	   DESC = The Interface DNA Map Table.;
	   HELP = ;
	   CAPABILITIES = NET_CFG, VPN_DISP;"
   ::= {ifNvDna 1}

nvmIfDnaEntry OBJECT-TYPE
	SYNTAX      NvmIfDnaEntry
	ACCESS      not-accessible
	STATUS      mandatory
	DESCRIPTION
	  "NAME = ;
	   DESC = Each entry corresponds to each interface \
		  which has a DNA  associated with it.;
	   HELP = ;
	   CAPABILITIES = ;"
	
   INDEX       { nvmIfDnaIfIndex, nvmIfDnaType }
   ::= {nvmIfDnaTable 1}

NvmIfDnaEntry ::= SEQUENCE {
                        nvmIfDnaIfIndex
                           INTEGER,
                        nvmIfDnaType
                           INTEGER,
                        nvmIfDNADigits
                           DisplayString,
                        nvmIfDnaStatus
                           INTEGER
                    }
                           
nvmIfDnaIfIndex OBJECT-TYPE
	SYNTAX      INTEGER (1..255)
	ACCESS      read-only
	STATUS      mandatory
	DESCRIPTION
	  "NAME = ;
	   DESC = The unique identifier of the interface. \
		  Same value as the  ifIndex from MIB-II.;
	   HELP = First of the indicies to a row in this \
		  table.;
	   CAPABILITIES = ;"
   ::= {nvmIfDnaEntry 1}

nvmIfDnaType OBJECT-TYPE
	SYNTAX      INTEGER { provisioned(1), learnt(2) }
	ACCESS      read-only
	STATUS      mandatory
	DESCRIPTION
	  "NAME = ;
	   DESC = Indicates whether the DNA on this interface \
		  was provisioned by the user or was \
		  learned from the switch.;
	   HELP = This is the second index \
		  identifying a row in \
		  this table.;
	   CAPABILITIES = ;"
   ::= {nvmIfDnaEntry 2}

nvmIfDNADigits OBJECT-TYPE
	SYNTAX      DisplayString(SIZE(1..34))
	ACCESS      read-only
	STATUS      mandatory
	DESCRIPTION
	  "NAME = ;
	   DESC = The DNA digits in ASCII format which \
		  uniquely identify the row in the table.;
	   HELP = Every interface has an unique DNA number \
		  assigned to it.;
	   CAPABILITIES = ;"
   ::= {nvmIfDnaEntry 3}

nvmIfDnaStatus OBJECT-TYPE
	SYNTAX      INTEGER { valid(1), active(2), invalid(3) }
	ACCESS      read-only
	STATUS      mandatory
	DESCRIPTION
	  "NAME = ;
	   DESC = Indicates the validity of the row in \
		  the table.;
	   HELP = A value of active means \
		  this is the DNA used by the NAC to \
		  register with the NAS. A value of valid \
		  means that the row is valid but not \
		  used to register with the NAS. It is \
		  left to the implementor whether to \
		  remove a row from the table when the \
		  value of this object is equal to invalid.;
	   CAPABILITIES = ;"
   ::= {nvmIfDnaEntry 4}

END
