--
-- This SMIv2 module has been generated by smidump 0.2-cvs. Do not edit.
--

SONUS-NTP-SERVICES-MIB DEFINITIONS ::= BEGIN

IMPORTS
    Integer32, IpAddress, MODULE-IDENTITY, NOTIFICATION-TYPE, 
    OBJECT-TYPE
        FROM SNMPv2-SMI
    DisplayString, RowStatus
        FROM SNMPv2-TC
    sonusEventClass, sonusEventDescription, sonusEventLevel, 
    sonusShelfIndex, sonusSlotIndex
        FROM SONUS-COMMON-MIB
    sonusServicesMIBs
        FROM SONUS-SMI
    SonusName, SonusNameReference
        FROM SONUS-TC;

sonusNtpServicesMIB MODULE-IDENTITY
    LAST-UPDATED    "200004230000Z"
    ORGANIZATION    
            "Sonus Networks, Inc."
    CONTACT-INFO    
            "   Customer Support    
             Sonus Networks, Inc,
             5 carlisle Road
             Westford, MA 01886
             USA
             
             Tel: 978-692-8999
             Fax: 978-392-9118
             E-mail: cs.snmp@sonusnet.com"
    DESCRIPTION     
            "The MIB Module for NTP Services Management."
    ::= { sonusServicesMIBs 2 }


sonusNtpServicesMIBObjects OBJECT IDENTIFIER
    ::= { sonusNtpServicesMIB 1 }

sonusTimeZoneObjects OBJECT IDENTIFIER
    ::= { sonusNtpServicesMIBObjects 1 }

sonusTimeZone OBJECT-TYPE
    SYNTAX          INTEGER { gmtMinus12-Eniuetok(1), 
                        gmtMinus11-MidwayIsland(2), gmtMinus10-Hawaii(3), 
                        gmtMinus09-Alaska(4), gmtMinus08-Pacific-US(5), 
                        gmtMinus07-Arizona(6), gmtMinus07-Mountain(7), 
                        gmtMinus06-Central-US(8), gmtMinus06-Mexico(9), 
                        gmtMinus06-Saskatchewan(10), 
                        gmtMinus05-Bojota(11), gmtMinus05-Eastern-US(12), 
                        gmtMinus05-Indiana(13), 
                        gmtMinus04-Atlantic-Canada(14), 
                        gmtMinus04-Caracas(15), 
                        gmtMinus03-BuenosAires(16), 
                        gmtMinus02-MidAtlantic(17), 
                        gmtMinus01-Azores(18), gmt(19), 
                        gmtPlus01-Berlin(20), gmtPlus02-Athens(21), 
                        gmtPlus03-Moscow(22), gmtPlus0330-Tehran(23), 
                        gmtPlus04-AbuDhabi(24), gmtPlus0430-Kabul(25), 
                        gmtPlus05-Islamabad(26), 
                        gmtPlus0530-NewDelhi(27), gmtPlus06-Dhaka(28), 
                        gmtPlus07-Bangkok(29), gmtPlus08-Beijing(30), 
                        gmtPlus09-Tokyo(31), gmtPlus0930-Adelaide(32), 
                        gmtPlus10-Guam(33), gmtPlus11-Magadan(34), 
                        gmtPlus12-Fiji(35) }
    MAX-ACCESS      read-write
    STATUS          current
    DESCRIPTION     
            "This is the Time Zone that this GSX9000 Node is In."
    DEFVAL          { 12 }
    ::= { sonusTimeZoneObjects 1 }

sonusNtpPeer OBJECT IDENTIFIER
    ::= { sonusNtpServicesMIBObjects 2 }

sonusNtpPeerNextIndex OBJECT-TYPE
    SYNTAX          Integer32
    MAX-ACCESS      read-only
    STATUS          current
    DESCRIPTION     
            "The next valid index to use when creating a new sonusNtpAdmnEntry"
    ::= { sonusNtpPeer 1 }

sonusNtpPeerTable OBJECT-TYPE
    SYNTAX          SEQUENCE OF SonusNtpAdmnEntry
    MAX-ACCESS      not-accessible
    STATUS          current
    DESCRIPTION     
            "This table contains information about each NTP Server 
             configured to provide network time. "
    ::= { sonusNtpPeer 2 }

sonusNtpAdmnEntry OBJECT-TYPE
    SYNTAX          SonusNtpAdmnEntry
    MAX-ACCESS      not-accessible
    STATUS          current
    DESCRIPTION     
            "This table describes the NTPs' configurations that this
             GSX9000 node has access to their services."
    INDEX           { sonusNtpPeerIndex }
    ::= { sonusNtpPeerTable 1 }

SonusNtpAdmnEntry ::=
    SEQUENCE {
        sonusNtpPeerIndex               Integer32,
        sonusNtpServerName              SonusName,
        sonusNtpPeerIpaddr              IpAddress,
        sonusNtpPeerMode                INTEGER,
        sonusNtpPeerVersion             INTEGER,
        sonusNtpPeerMinPoll             Integer32,
        sonusNtpPeerMaxPoll             Integer32,
        sonusNtpPeerAdmnState           INTEGER,
        sonusNtpPeerAdmnRowStatus       RowStatus
    }

sonusNtpPeerIndex OBJECT-TYPE
    SYNTAX          Integer32 (1..3)
    MAX-ACCESS      read-only
    STATUS          current
    DESCRIPTION     
            "The index of NTP Server Peer."
    ::= { sonusNtpAdmnEntry 1 }

sonusNtpServerName OBJECT-TYPE
    SYNTAX          SonusName
    MAX-ACCESS      read-write
    STATUS          current
    DESCRIPTION     
            "The name of this NTP Server Peer."
    ::= { sonusNtpAdmnEntry 2 }

sonusNtpPeerIpaddr OBJECT-TYPE
    SYNTAX          IpAddress
    MAX-ACCESS      read-write
    STATUS          current
    DESCRIPTION     
            "The IP address of this NTP Peer. "
    ::= { sonusNtpAdmnEntry 3 }

sonusNtpPeerMode OBJECT-TYPE
    SYNTAX          INTEGER { poll(3), broadcast(8) }
    MAX-ACCESS      read-write
    STATUS          current
    DESCRIPTION     
            "The operating client peer mode to this NTP Server. "
    DEFVAL          { poll }
    ::= { sonusNtpAdmnEntry 4 }

sonusNtpPeerVersion OBJECT-TYPE
    SYNTAX          INTEGER { version3(3), version4(4) }
    MAX-ACCESS      read-write
    STATUS          current
    DESCRIPTION     
            "The NTP version of this NTP Server "
    DEFVAL          { version3 }
    ::= { sonusNtpAdmnEntry 5 }

sonusNtpPeerMinPoll OBJECT-TYPE
    SYNTAX          Integer32 (1..63)
    MAX-ACCESS      read-write
    STATUS          current
    DESCRIPTION     
            "The minimum poll interval to this NTP Server. 
             Intervals are set in powers of 2. "
    DEFVAL          { 3 }
    ::= { sonusNtpAdmnEntry 6 }

sonusNtpPeerMaxPoll OBJECT-TYPE
    SYNTAX          Integer32 (1..63)
    MAX-ACCESS      read-write
    STATUS          current
    DESCRIPTION     
            "The maxiimum poll interval to this NTP Server. 
             Intervals are set in powers of 2."
    DEFVAL          { 10 }
    ::= { sonusNtpAdmnEntry 7 }

sonusNtpPeerAdmnState OBJECT-TYPE
    SYNTAX          INTEGER { disabled(1), enabled(2) }
    MAX-ACCESS      read-write
    STATUS          current
    DESCRIPTION     
            "The configured state of the NTP."
    DEFVAL          { disabled }
    ::= { sonusNtpAdmnEntry 8 }

sonusNtpPeerAdmnRowStatus OBJECT-TYPE
    SYNTAX          RowStatus
    MAX-ACCESS      read-write
    STATUS          current
    DESCRIPTION     
            ""
    ::= { sonusNtpAdmnEntry 9 }

sonusNtpPeerStatTable OBJECT-TYPE
    SYNTAX          SEQUENCE OF SonusNtpPeerStatEntry
    MAX-ACCESS      not-accessible
    STATUS          current
    DESCRIPTION     
            "This table contains status information about each NTP server per shelf"
    ::= { sonusNtpServicesMIBObjects 3 }

sonusNtpPeerStatEntry OBJECT-TYPE
    SYNTAX          SonusNtpPeerStatEntry
    MAX-ACCESS      not-accessible
    STATUS          current
    DESCRIPTION     
            "This table describes the NTP peer's status"
    INDEX           { sonusNtpPeerStatShelfIndex, sonusNtpPeerStatIndex }
    ::= { sonusNtpPeerStatTable 1 }

SonusNtpPeerStatEntry ::=
    SEQUENCE {
        sonusNtpPeerStatShelfIndex      Integer32,
        sonusNtpPeerStatIndex           Integer32,
        sonusNtpPeerState               INTEGER,
        sonusNtpPeerStratum             Integer32,
        sonusNtpPeerRefTime             DisplayString
    }

sonusNtpPeerStatShelfIndex OBJECT-TYPE
    SYNTAX          Integer32
    MAX-ACCESS      read-only
    STATUS          current
    DESCRIPTION     
            "Identifies the shelf NTP service is provided on."
    ::= { sonusNtpPeerStatEntry 1 }

sonusNtpPeerStatIndex OBJECT-TYPE
    SYNTAX          Integer32
    MAX-ACCESS      read-only
    STATUS          current
    DESCRIPTION     
            "Identifies the NTP peer for this shelf."
    ::= { sonusNtpPeerStatEntry 2 }

sonusNtpPeerState OBJECT-TYPE
    SYNTAX          INTEGER { outofsync(1), insync(2) }
    MAX-ACCESS      read-only
    STATUS          current
    DESCRIPTION     
            "Identifies the state of the NTP peer for this shelf."
    ::= { sonusNtpPeerStatEntry 3 }

sonusNtpPeerStratum OBJECT-TYPE
    SYNTAX          Integer32
    MAX-ACCESS      read-only
    STATUS          current
    DESCRIPTION     
            "Identifies the NTP peer's stratum level."
    ::= { sonusNtpPeerStatEntry 4 }

sonusNtpPeerRefTime OBJECT-TYPE
    SYNTAX          DisplayString (SIZE(0..23))
    MAX-ACCESS      read-only
    STATUS          current
    DESCRIPTION     
            "The time this NTP peer on this shelf is last updated."
    ::= { sonusNtpPeerStatEntry 5 }

sonusNtpSysStatTable OBJECT-TYPE
    SYNTAX          SEQUENCE OF SonusNtpSysStatEntry
    MAX-ACCESS      not-accessible
    STATUS          current
    DESCRIPTION     
            "This table contains status information about each NTP"
    ::= { sonusNtpServicesMIBObjects 4 }

sonusNtpSysStatEntry OBJECT-TYPE
    SYNTAX          SonusNtpSysStatEntry
    MAX-ACCESS      not-accessible
    STATUS          current
    DESCRIPTION     
            "This table describes the NTP stat"
    INDEX           { sonusNtpSysShelfIndex }
    ::= { sonusNtpSysStatTable 1 }

SonusNtpSysStatEntry ::=
    SEQUENCE {
        sonusNtpSysShelfIndex           Integer32,
        sonusNtpSysClock                DisplayString,
        sonusNtpSysRefTime              DisplayString,
        sonusNtpSysLastSelect           DisplayString,
        sonusNtpSysPeer                 SonusNameReference
    }

sonusNtpSysShelfIndex OBJECT-TYPE
    SYNTAX          Integer32
    MAX-ACCESS      read-only
    STATUS          current
    DESCRIPTION     
            "Identifies the shelf NTP service is provided on."
    ::= { sonusNtpSysStatEntry 1 }

sonusNtpSysClock OBJECT-TYPE
    SYNTAX          DisplayString (SIZE(0..23))
    MAX-ACCESS      read-only
    STATUS          current
    DESCRIPTION     
            "The system clock time of this shelf."
    ::= { sonusNtpSysStatEntry 2 }

sonusNtpSysRefTime OBJECT-TYPE
    SYNTAX          DisplayString (SIZE(0..23))
    MAX-ACCESS      read-only
    STATUS          current
    DESCRIPTION     
            "The time this shelf is last updated."
    ::= { sonusNtpSysStatEntry 3 }

sonusNtpSysLastSelect OBJECT-TYPE
    SYNTAX          DisplayString (SIZE(0..23))
    MAX-ACCESS      read-only
    STATUS          current
    DESCRIPTION     
            "The system clock time before last update."
    ::= { sonusNtpSysStatEntry 4 }

sonusNtpSysPeer OBJECT-TYPE
    SYNTAX          SonusNameReference
    MAX-ACCESS      read-only
    STATUS          current
    DESCRIPTION     
            "The name of current NTP server peer. "
    ::= { sonusNtpSysStatEntry 5 }

sonusNtpServicesMIBNotifications OBJECT IDENTIFIER
    ::= { sonusNtpServicesMIB 2 }

sonusNtpServicesMIBNotificationsPrefix OBJECT IDENTIFIER
    ::= { sonusNtpServicesMIBNotifications 0 }

sonusNtpServicesMIBNotificationsObjects OBJECT IDENTIFIER
    ::= { sonusNtpServicesMIBNotifications 1 }

sonusNtpServerOutOfServiceReason OBJECT-TYPE
    SYNTAX          INTEGER { ntpServerDisabled(1), 
                        ntpServerOutOfSync(2) }
    MAX-ACCESS      read-only
    STATUS          current
    DESCRIPTION     
            "The reason why this Network Timing Protocol Server is out of service."
    ::= { sonusNtpServicesMIBNotificationsObjects 1 }

sonusNtpDownReason OBJECT-TYPE
    SYNTAX          INTEGER { noNtpServerConfigured(1), 
                        allNtpServersOutOfSync(2) }
    MAX-ACCESS      read-only
    STATUS          current
    DESCRIPTION     
            "The reason why the Network Timing Protocol is down for this GSX."
    ::= { sonusNtpServicesMIBNotificationsObjects 2 }

sonusNtpServerInServiceNotification NOTIFICATION-TYPE
    OBJECTS         { sonusShelfIndex, sonusSlotIndex, 
                      sonusNtpServerName, sonusEventDescription, 
                      sonusEventClass, sonusEventLevel }
    STATUS          current
    DESCRIPTION     
            "This trap indicates that a Network Timing Protocol Server is in service."
    ::= { sonusNtpServicesMIBNotificationsPrefix 1 }

sonusNtpServerOutOfServiceNotification NOTIFICATION-TYPE
    OBJECTS         { sonusShelfIndex, sonusSlotIndex, 
                      sonusNtpServerName, 
                      sonusNtpServerOutOfServiceReason, 
                      sonusEventDescription, sonusEventClass, 
                      sonusEventLevel }
    STATUS          current
    DESCRIPTION     
            "This trap indicates that a Network Timing Protocol Server is out of service."
    ::= { sonusNtpServicesMIBNotificationsPrefix 2 }

sonusNtpUpNotification NOTIFICATION-TYPE
    OBJECTS         { sonusShelfIndex, sonusSlotIndex, 
                      sonusEventDescription, sonusEventClass, 
                      sonusEventLevel }
    STATUS          current
    DESCRIPTION     
            "This trap indicates that Network Timing Protocol Server is Up."
    ::= { sonusNtpServicesMIBNotificationsPrefix 3 }

sonusNtpDownNotification NOTIFICATION-TYPE
    OBJECTS         { sonusShelfIndex, sonusSlotIndex, 
                      sonusNtpDownReason, sonusEventDescription, 
                      sonusEventClass, sonusEventLevel }
    STATUS          current
    DESCRIPTION     
            "This trap indicates that Network Timing Protocol is down."
    ::= { sonusNtpServicesMIBNotificationsPrefix 4 }

END -- end of module SONUS-NTP-SERVICES-MIB.
