--			Ascend Miscellaneous (misc) Mib
--
--			Ascend Communications, Inc
--			1275 Harbor Bay Pkwy
--			Alameda, CA 94502
--			+1 510 769 6001
--			info@ascend.com
--
--		Copyright (c) 1993-1997 Ascend Communications, Inc.
--		All rights reserved.
--
-- $Id: misc.mib,v 29.1 1997/12/17 19:26:48 ravedian Exp $
--
-- 25 Nov 97 (raffi)  Initially created
--

ASCEND-MISC-MIB DEFINITIONS ::= BEGIN

    IMPORTS
	miscGroup
	    FROM ASCEND-MIB
	OBJECT-TYPE
	    FROM RFC-1212;

	--
	-- Ascend Miscellaneous group
	--
	-- This group contains a table of entries to define enterprise
	-- specific orphan variables.
	--

    miscGroupFRTable	OBJECT-TYPE
	SYNTAX		SEQUENCE OF MiscGroupFREntry
	ACCESS		not-accessible
	STATUS		mandatory
	DESCRIPTION	"Variables in Frame Relay profile."
	::= { miscGroup 1 }


    miscGroupFREntry	OBJECT-TYPE
	SYNTAX		MiscGroupFREntry
	ACCESS		not-accessible
	STATUS		mandatory
	DESCRIPTION	"An entry containing object variables for 
			 Frame Relay profile."
	INDEX   	{ miscGroupFRLMIIndex }
	::= { miscGroupFRTable 1 }


    MiscGroupFREntry ::=
	SEQUENCE {
	    miscGroupFRLMIIndex
		INTEGER,
	    miscGroupFRLMIDlci
		INTEGER
	}


    miscGroupFRLMIIndex  OBJECT-TYPE
        SYNTAX  INTEGER
        ACCESS  read-only
        STATUS  mandatory
        DESCRIPTION
           "The index in to Frame Relay profile variables."
       ::= { miscGroupFREntry 1 }


    miscGroupFRLMIDlci	OBJECT-TYPE
	SYNTAX		INTEGER {
			    dlci-0(1),		-- use DLCI 0 for LMI
			    dlci-1023(2)	-- use DLCI 1023
			}
	ACCESS		read-write
	STATUS		mandatory
	DESCRIPTION	"The value of Link Management DLCI."
	::= { miscGroupFREntry 2 }


END
