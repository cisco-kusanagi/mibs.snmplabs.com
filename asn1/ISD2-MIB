ISD2-MIB DEFINITIONS ::= BEGIN

-- Copyright (C) 1997 Intel Corporation. All rights reserved.
--
-- Intel Private ISDN MIB, 06-06-1997
--
-- This MIB provides objects for ISDN
--
-- Change History:
-- <date> <change>
--

IMPORTS
	Counter FROM RFC1155-SMI
    scanet                     FROM SCANET-MIB
    OBJECT-TYPE                FROM RFC-1212;

isd2             OBJECT IDENTIFIER ::= { scanet 48 }
isd2SigChan      OBJECT IDENTIFIER ::= { isd2 1 }
isd2Dchan        OBJECT IDENTIFIER ::= { isd2 2 }
isd2Phys         OBJECT IDENTIFIER ::= { isd2 3 }
isd2CallCtrl     OBJECT IDENTIFIER ::= { isd2 4 }

isd2SigChanTable OBJECT-TYPE
    SYNTAX SEQUENCE OF Isd2SigChanEntry
    ACCESS not-accessible
    STATUS mandatory
    DESCRIPTION "Table containing configuration and operational parameters
                 for all ISDN Signalling Channels on this managed device."
    ::= { isd2SigChan 1 }

isd2SigChanEntry OBJECT-TYPE
    SYNTAX Isd2SigChanEntry
    ACCESS not-accessible
    STATUS mandatory
    DESCRIPTION "An entry in the ISDN Signalling Channel Table."
    INDEX { isd2SigChanIfIndex }
    ::= { isd2SigChanTable 1 }

Isd2SigChanEntry ::= SEQUENCE {
                        isd2SigChanIfIndex
                           INTEGER,
                        isd2SigChanL2State
                           Counter,
                        isd2SigChanCES
                           Counter,
                        isd2SigChanSAPI
                           Counter,
                        isd2SigChanCallCollisions
                           Counter,
                        isd2SigChanAddressCheckFails
                           Counter
                        }

isd2SigChanIfIndex OBJECT-TYPE
    SYNTAX INTEGER
    ACCESS read-only
    STATUS mandatory
    DESCRIPTION "Interface index for this signalling channel."
    ::= { isd2SigChanEntry 1 }

isd2SigChanL2State OBJECT-TYPE
    SYNTAX INTEGER {
       teiUnassigned(1),
       assignAwaitTei(2),
       establishAwaitTei(3),
       teiAssigned(4),
       awaitEstablishment(5),
       awaitRelease(6),
       multipleFrameEstablished(7),
       timerRecovery(8)
    }
    ACCESS read-only
    STATUS mandatory
    DESCRIPTION "Signalling layer-2 state (Q.921)."
    ::= { isd2SigChanEntry 2 }

isd2SigChanCES OBJECT-TYPE
    SYNTAX Counter
    ACCESS read-only
    STATUS mandatory
    DESCRIPTION "Connection Endpoint Suffix (CES) for this signalling channel."
    ::= { isd2SigChanEntry 3 }

isd2SigChanSAPI OBJECT-TYPE
    SYNTAX Counter
    ACCESS read-only
    STATUS mandatory
    DESCRIPTION "Service Access Point Identifier (SAPI) for this
                 signalling channel"
    ::= { isd2SigChanEntry 4 }

isd2SigChanCallCollisions OBJECT-TYPE
    SYNTAX Counter
    ACCESS read-only
    STATUS mandatory
    DESCRIPTION
            "The number of calls over this signalling channel which failed
             because of collision."
    ::= { isd2SigChanEntry 5 }

isd2SigChanAddressCheckFails OBJECT-TYPE
    SYNTAX Counter
    ACCESS read-only
    STATUS mandatory
    DESCRIPTION
            "The number of incoming calls over this signalling channel
             which were refused because of address mismatch."
    ::= { isd2SigChanEntry 6 }

isd2DchanTable OBJECT-TYPE
    SYNTAX SEQUENCE OF Isd2DchanEntry
    ACCESS not-accessible
    STATUS mandatory
    DESCRIPTION "Table containing statistics for all ISDN D-Channels on
                 this managed device."
    ::= { isd2Dchan 1 }

isd2DchanEntry OBJECT-TYPE
    SYNTAX Isd2DchanEntry
    ACCESS not-accessible
    STATUS mandatory
    DESCRIPTION "An entry in the ISDN D-Channel Table."
    INDEX { isd2DchanIfIndex }
    ::= { isd2DchanTable 1 }

Isd2DchanEntry ::= SEQUENCE {
                        isd2DchanIfIndex
                           INTEGER,
                        isd2DchanRxShort
                           Counter,
                        isd2DchanRxLong
                           Counter,
                        isd2DchanRxCRCerror
                           Counter,
                        isd2DchanRxResidual
                           Counter,
                        isd2DchanRxAborts
                           Counter,
                        isd2DchanRxOverrun
                           Counter,
                        isd2DchanRxLostSync
                           Counter,
                        isd2DchanRxBufferLack
                           Counter,
                        isd2DchanRxApplnotready
                           Counter,
                        isd2DchanRxUnknownProto
                           Counter,
                        isd2DchanTxDiscardedProto
                           Counter,
                        isd2DchanTxDiscardedData
                           Counter,
                        isd2DchanTxUnderrun
                           Counter,
                        isd2DchanTxCollision
                           Counter
                        }

isd2DchanIfIndex OBJECT-TYPE
    SYNTAX INTEGER
    ACCESS read-only
    STATUS mandatory
    DESCRIPTION "The Ifindex of this D-channel."
    ::= { isd2DchanEntry 1 }

isd2DchanRxShort OBJECT-TYPE
    SYNTAX Counter
    ACCESS read-only
    STATUS mandatory
    DESCRIPTION
        "The number of frames received which were discarded
         due to the frame length being too short."
    ::= { isd2DchanEntry 2 }

isd2DchanRxLong OBJECT-TYPE
    SYNTAX Counter
    ACCESS read-only
    STATUS mandatory
    DESCRIPTION
        "The number of frames received which were discarded
         due to the frame length being too long."
    ::= { isd2DchanEntry 3 }

isd2DchanRxCRCerror OBJECT-TYPE
    SYNTAX Counter
    ACCESS read-only
    STATUS mandatory
    DESCRIPTION
        "The number of frames received which were discarded
         due to Cyclic Redundancy Check (CRC) errors. This
         figure indicates the number of bit errors occuring
         over the WAN link."
    ::= { isd2DchanEntry 4 }

isd2DchanRxResidual OBJECT-TYPE
    SYNTAX Counter
    ACCESS read-only
    STATUS mandatory
    DESCRIPTION
        "The number of times the frame contained residual
         bits. This should not occur."
    ::= { isd2DchanEntry 5 }

isd2DchanRxAborts OBJECT-TYPE
    SYNTAX Counter
    ACCESS read-only
    STATUS mandatory
    DESCRIPTION
        "The number of times the High-Level Data Link Control
         (HDLC) 'Abort' signal was received, indicating that
         the received packet should be ignored."
    ::= { isd2DchanEntry 6 }

isd2DchanRxOverrun OBJECT-TYPE
    SYNTAX Counter
    ACCESS read-only
    STATUS mandatory
    DESCRIPTION
        "The number of frames which were lost due to bus
         overload within the router. This should not occur."
    ::= { isd2DchanEntry 7 }

isd2DchanRxLostSync OBJECT-TYPE
    SYNTAX Counter
    ACCESS read-only
    STATUS mandatory
    DESCRIPTION
        "The number of frames which were lost due to drop
         of signal on the line."
    ::= { isd2DchanEntry 8 }

isd2DchanRxBufferLack OBJECT-TYPE
    SYNTAX Counter
    ACCESS read-only
    STATUS mandatory
    DESCRIPTION
        "The number of received frames which were lost due to
         RAM (buffer) overload within the router."
    ::= { isd2DchanEntry 9 }

isd2DchanRxApplnotready OBJECT-TYPE
    SYNTAX Counter
    ACCESS read-only
    STATUS mandatory
    DESCRIPTION
        "The number of received frames which were discarded since
         there was a temporary situation with no upper layer
         to receive the frame."
    ::= { isd2DchanEntry 10 }

isd2DchanRxUnknownProto OBJECT-TYPE
    SYNTAX Counter
    ACCESS read-only
    STATUS mandatory
    DESCRIPTION "The number of incoming frames which were discarded
                 due to unknown protocol field."
    ::= { isd2DchanEntry 11 }

isd2DchanTxDiscardedProto OBJECT-TYPE
    SYNTAX Counter
    ACCESS read-only
    STATUS mandatory
    DESCRIPTION
        "The number of protocol frames for transmission which were
          lost due to RAM (buffer) overload within the router."
    ::= { isd2DchanEntry 12 }

isd2DchanTxDiscardedData OBJECT-TYPE
    SYNTAX Counter
    ACCESS read-only
    STATUS mandatory
    DESCRIPTION
        "The number of data frames for transmission which were
         lost due to RAM (buffer) overload within the router."
    ::= { isd2DchanEntry 13 }

isd2DchanTxUnderrun OBJECT-TYPE
    SYNTAX Counter
    ACCESS read-only
    STATUS mandatory
    DESCRIPTION
        "The number of frames for transmission that were not
         successfully transmitted due to CPU (processor)
         overload within the router."
    ::= { isd2DchanEntry 14 }

isd2DchanTxCollision OBJECT-TYPE
    SYNTAX Counter
    ACCESS read-only
    STATUS mandatory
    DESCRIPTION "The number of outgoing frames which were discarded
                 due to collisions that occured during transmission."
    ::= { isd2DchanEntry 15 }

isd2PhysTable OBJECT-TYPE
    SYNTAX SEQUENCE OF Isd2PhysEntry
    ACCESS not-accessible
    STATUS mandatory
    DESCRIPTION "Table containing physical layer status for all
                 ISDN ports on this managed device."
    ::= { isd2Phys 1 }

isd2PhysEntry OBJECT-TYPE
    SYNTAX Isd2PhysEntry
    ACCESS not-accessible
    STATUS mandatory
    DESCRIPTION "An entry in the ISDN physical layer Table."
    INDEX { isd2PhysIfIndex }
    ::= { isd2PhysTable 1 }

Isd2PhysEntry ::= SEQUENCE {
                        isd2PhysIfIndex
                           INTEGER,
                        isd2PhysL1State
                           Counter,
                        isd2PhysL1Alarm
                           Counter
                        }

isd2PhysIfIndex OBJECT-TYPE
    SYNTAX INTEGER
    ACCESS read-only
    STATUS mandatory
    DESCRIPTION "IfIndex for this ISDN port."
    ::= { isd2PhysEntry 1 }

isd2PhysL1State OBJECT-TYPE
    SYNTAX INTEGER {
       inactive(1),
       sensing(2),
       deactivated(3),
       awaitingSignal(4),
       identifyingInput(5),
       synchronized(6),
       activated(7),
       lostFraming(8),
       lossOfPower(100),
       operational(101),
       fault1(102),
       fault2(103),
       fault3(104),
       fault4(105),
       powerOn(106)
    }
    ACCESS read-only
    STATUS mandatory
    DESCRIPTION "Physical layer state for this ISDN port."
    ::= { isd2PhysEntry 2 }

isd2PhysL1Alarm OBJECT-TYPE
    SYNTAX INTEGER {
       noCableInserted(1),
       lossOfSignal(2),
       txCableNotConnected(3),
       alarmIndicationSignal(4),
       remoteAlarmIndication(5),
       noMultiFrameAlignment(6),
       noBasicFrameAlignment(7),
       noSyncPattern(8),
       ncrc4(9),
       crce0(10),
       crce1(11),
       ebit0(12),
       ebit1(13)
    }
    ACCESS read-only
    STATUS mandatory
    DESCRIPTION "Primary Rate Interface alarm for this ISDN port.
                 This entry is unused for BRI. 0 means noDetectedProblem"
    ::= { isd2PhysEntry 3 }

isd2CallCtrlTable OBJECT-TYPE
    SYNTAX SEQUENCE OF Isd2CallCtrlEntry
    ACCESS not-accessible
    STATUS mandatory
    DESCRIPTION "Table containing configuration and operational parameters
                 for all ISDN links on this managed device."
    ::= { isd2CallCtrl 1 }

isd2CallCtrlEntry OBJECT-TYPE
    SYNTAX Isd2CallCtrlEntry
    ACCESS not-accessible
    STATUS mandatory
    DESCRIPTION "An entry in the ISDN link Table."
    INDEX { isd2CallCtrlSigchanIfIndex }
    ::= { isd2CallCtrlTable 1 }

Isd2CallCtrlEntry ::= SEQUENCE {
                        isd2CallCtrlSigchanIfIndex
                           INTEGER,
                        isd2CallCtrlBchanIfIndex
                           INTEGER,
                        isd2CallCtrlLocalNumber
                           OCTET STRING,
                        isd2CallCtrlLocalSubaddr
                           OCTET STRING,
                        isd2CallCtrlRemoteNumber
                           OCTET STRING,
                        isd2CallCtrlRemoteSubaddr
                           OCTET STRING,
                        isd2CallCtrlL3State
                           INTEGER,
                        isd2CallCtrlCallRef
                           INTEGER,
                        isd2CallCtrlChannelNum
                           INTEGER,
                        isd2CallCtrlOutCallsConnected
                           Counter,
                        isd2CallCtrlOutCallsFailed
                           Counter,
                        isd2CallCtrlInCallsConnected
                           Counter,
                        isd2CallCtrlInCallsRefused
                           Counter,
                        isd2CallCtrlCallCollisions
                           Counter,
                        isd2CallCtrlCauseCode
                           INTEGER,
                        isd2CallCtrlLocationCode
                           INTEGER,
                        isd2CallCtrlCauseText
                           OCTET STRING
                        }

isd2CallCtrlSigchanIfIndex OBJECT-TYPE
    SYNTAX INTEGER
    ACCESS read-only
    STATUS mandatory
    DESCRIPTION "Interface index for the current signalling-channel
                 associated with this link. The index is zero if no
                 signalling-channel is associated."
    ::= { isd2CallCtrlEntry 1 }

isd2CallCtrlBchanIfIndex OBJECT-TYPE
    SYNTAX INTEGER
    ACCESS read-only
    STATUS mandatory
    DESCRIPTION "Interface index for the current B-channel
                 associated with this link. The index is
                 zero if no B-channel is allocated."
    ::= { isd2CallCtrlEntry 2 }

isd2CallCtrlLocalNumber OBJECT-TYPE
    SYNTAX OCTET STRING (SIZE(22))
    ACCESS read-only
    STATUS mandatory
    DESCRIPTION "The local ISDN number for this link."
    ::= { isd2CallCtrlEntry 3 }

isd2CallCtrlLocalSubaddr OBJECT-TYPE
    SYNTAX OCTET STRING (SIZE(14))
    ACCESS read-only
    STATUS mandatory
    DESCRIPTION "The local ISDN subaddress for this link."
    ::= { isd2CallCtrlEntry 4 }

isd2CallCtrlRemoteNumber OBJECT-TYPE
    SYNTAX OCTET STRING (SIZE(22))
    ACCESS read-only
    STATUS mandatory
    DESCRIPTION
            "The ISDN number the current or last call is or was
             connected to."
    ::= { isd2CallCtrlEntry 5 }

isd2CallCtrlRemoteSubaddr OBJECT-TYPE
    SYNTAX OCTET STRING (SIZE(14))
    ACCESS read-only
    STATUS mandatory
    DESCRIPTION
            "The ISDN subaddress the current or last call is or was
             connected to."
    ::= { isd2CallCtrlEntry 6 }

isd2CallCtrlL3State OBJECT-TYPE
    SYNTAX INTEGER {
       callInit(1),
       overlapSending(2),
       outCallProc(3),
       callDelivered(4),
       undef5(5),
       callPresent(6),
       callReceived(7),
       connectRequest(8),
       inCallProc(9),
       callActive(10),
       disconnectRequest(11),
       disconnectInd(12),
       passiveAwaitingConf(13),
       callPassive(14),
       suspendRequest(15),
       undef16(16),
       resumeRequest(17),
       undef18(18),
       releaseRequest(19),
       registerRequest(20),
       cancelRequest(21),
       undef22(22),
       undef23(23),
       undef24(24),
       overlapReceive(25),
       idleState(26),
       establishWait(27),
       asaiTr1State(28),
       u10HoldRequest(29),
       u10TransferRequest(30),
       u10ConferenceRequest(31),
       u10ReconnectRequest(32),
       u10AwaitingDisc(33),
       u10CallOnHold(34),
       deactivated(35),
       reactivateRequested(36),
       deactivateRequested(37),
       ni1HoldReqU3(38),
       ni1HoldReqU4(39),
       ni1HoldReqU10(40),
       ni1RetrieveU3(41),
       ni1RetrieveU4(42),
       ni1RetrieveU10(43),
       ni1HoldActiveU3(44),
       ni1HoldActiveU4(45),
       ni1HoldActiveU10(46),
       broadcastState(47)
    }
    ACCESS read-only
    STATUS mandatory
    DESCRIPTION "Signalling layer-3 state (Q.931 and custom).
                 0 means nullState."
    ::= { isd2CallCtrlEntry 7 }

isd2CallCtrlCallRef OBJECT-TYPE
    SYNTAX INTEGER
    ACCESS read-only
    STATUS mandatory
    DESCRIPTION "Signalling layer-3 call reference (Q.931)."
    ::= { isd2CallCtrlEntry 8 }

isd2CallCtrlChannelNum OBJECT-TYPE
    SYNTAX INTEGER
    ACCESS read-only
    STATUS mandatory
    DESCRIPTION "The current B-channel number associated with this link."
    ::= { isd2CallCtrlEntry 9 }

isd2CallCtrlOutCallsConnected OBJECT-TYPE
    SYNTAX Counter
    ACCESS read-only
    STATUS mandatory
    DESCRIPTION
            "The number of outgoing calls on this link which were
             actually connected."
    ::= { isd2CallCtrlEntry 10 }

isd2CallCtrlOutCallsFailed OBJECT-TYPE
    SYNTAX Counter
    ACCESS read-only
    STATUS mandatory
    DESCRIPTION
            "The number of outgoing calls on this link
             which failed."
    ::= { isd2CallCtrlEntry 11 }

isd2CallCtrlInCallsConnected OBJECT-TYPE
    SYNTAX Counter
    ACCESS read-only
    STATUS mandatory
    DESCRIPTION
            "The number of incoming calls on this link
             which were actually connected."
    ::= { isd2CallCtrlEntry 12 }

isd2CallCtrlInCallsRefused OBJECT-TYPE
    SYNTAX Counter
    ACCESS read-only
    STATUS mandatory
    DESCRIPTION
            "The number of incoming calls on this link
             which were refused."
    ::= { isd2CallCtrlEntry 13 }

isd2CallCtrlCallCollisions OBJECT-TYPE
    SYNTAX Counter
    ACCESS read-only
    STATUS mandatory
    DESCRIPTION
            "The number of calls on this link which failed
             because of collision."
    ::= { isd2CallCtrlEntry 14 }

isd2CallCtrlCauseCode OBJECT-TYPE
    SYNTAX INTEGER
    ACCESS read-only
    STATUS mandatory
    DESCRIPTION
            "The encoded network cause value associated with the last
             call.
             This object will be updated whenever a call is started
             or cleared.
             The value of this object will depend on the interface type
             as well as on the protocol and protocol version being
             used on this interface. Some references for possible cause
             values are given below."
    REFERENCE
            "- Bellcore SR-NWT-001953, Generic Guidelines for
               ISDN Terminal Equipment On Basic Access Interfaces,
               chapter 5.2.5.8.
             - Bellcore SR-NWT-002343, ISDN Primary Rate Interface
               Generic Guidelines for Customer Premises Equipment,
               chapter 8.2.5.8.
             - ITU-T Q.931, Appendix I.
             - ITU-T X.25, CAUSE and DIAGNOSTIC field values.
             - German Telekom FTZ 1TR6, chapter 3.2.3.4.4.4."
    ::= { isd2CallCtrlEntry 15 }

isd2CallCtrlLocationCode OBJECT-TYPE
    SYNTAX INTEGER
    ACCESS read-only
    STATUS mandatory
    DESCRIPTION
            "The encoded network cause location value associated with
             the last call.
             This object will be updated whenever a call is started
             or cleared."
    ::= { isd2CallCtrlEntry 16 }

isd2CallCtrlCauseText OBJECT-TYPE
    SYNTAX OCTET STRING (SIZE(100))
    ACCESS read-only
    STATUS mandatory
    DESCRIPTION
            "ASCII text describing the reason for the last call
             termination.
             This object will be updated whenever a call is started
             or cleared."
    ::= { isd2CallCtrlEntry 17 }

END
