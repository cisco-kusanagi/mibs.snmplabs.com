-- extracted from draft-ietf-disman-alarm-mib-18.txt
-- at Thu Feb 12 06:16:55 2004

   ITU-ALARM-TC DEFINITIONS ::= BEGIN

   IMPORTS
      MODULE-IDENTITY, mib-2      FROM SNMPv2-SMI
      TEXTUAL-CONVENTION          FROM SNMPv2-TC;

     ituAlarmTc MODULE-IDENTITY
         LAST-UPDATED "200402090000Z"
         ORGANIZATION "IETF Distributed Management Working Group"
         CONTACT-INFO
            " WG EMail: disman@ietf.org
              Subscribe: disman-request@ietf.org
              http://www.ietf.org/html.charters/disman-charter.html

              Chair:     Randy Presuhn
                         randy_presuhn@mindspring.com

              Editors:   Sharon Chisholm
                         Nortel Networks
                         PO Box 3511 Station C
                         Ottawa, Ont.  K1Y 4H7
                         Canada
                         schishol@nortelnetworks.com

                         Dan Romascanu
                         Avaya
                         Atidim Technology Park, Bldg. #3
                         Tel Aviv, 61131
                         Israel
                         Tel: +972-3-645-8414
                         Email: dromasca@avaya.com"
         DESCRIPTION
            "This MIB module defines the ITU Alarm
            textual convention for objects not expected to require
            regular extension.

            Copyright (C) The Internet Society (2004).  The
            initial version of this MIB module was published
            in RFC YYYY. For full legal notices see the RFC
            itself. Supplementary information may be available on:
               http://www.ietf.org/copyrights/ianamib.html"
         -- RFC Ed.: replace yyyy with actual RFC number & remove
         -- this note
         REVISION    "200402090000Z"
         DESCRIPTION
             "Initial version, published as RFC yyyy."
             -- RFC-Editor assigns yyyy
        ::= { mib-2 XX } -- to be assigned by IANA

   ItuPerceivedSeverity ::= TEXTUAL-CONVENTION
       STATUS current
       DESCRIPTION
               "ITU perceived severity values"
       REFERENCE
              "ITU Recommendation M.3100, 'Generic Network Information
               Model', 1995
               ITU Recommendation X.733, 'Information Technology - Open
               Systems Interconnection - System Management: Alarm
               Reporting Function', 1992"
       SYNTAX         INTEGER
              {
              cleared (1),
              indeterminate (2),
              critical (3),
              major (4),
              minor (5),
              warning (6)
              }

   ItuTrendIndication ::= TEXTUAL-CONVENTION
       STATUS current
       DESCRIPTION
               "ITU trend indication values for alarms."
       REFERENCE
              "ITU Recommendation M.3100, 'Generic Network Information
               Model', 1995
               ITU Recommendation X.733, 'Information Technology - Open
               Systems Interconnection - System Management: Alarm
               Reporting Function', 1992"
       SYNTAX         INTEGER
         {
         moreSevere (1),
         noChange (2),
         lessSevere (3)
         }


   END

-- 
--   Copyright (C) The Internet Society (2004). All Rights Reserved.
-- 
--   This document and translations of it may be copied and furnished to
--   others, and derivative works that comment on or otherwise explain it
--   or assist in its implementation may be prepared, copied, published
--   and distributed, in whole or in part, without restriction of any kind,
--   provided that the above copyright notice and this paragraph are
--   included on all such copies and derivative works.  However, this
--   document itself may not be modified in any way, such as by removing
--   the copyright notice or references to the Internet Society or other
--   Internet organizations, except as needed for the  purpose of
--   developing Internet standards in which case the procedures for
--   copyrights defined in the Internet Standards process must be followed,
--   or as required to translate it into languages other than English.
-- 
--   The limited permissions granted above are perpetual and will not be
--   revoked by the Internet Society or its successors or assigns.
-- 
--   This document and the information contained herein is provided on an
--   "AS IS" basis and THE INTERNET SOCIETY AND THE INTERNET ENGINEERING
--   TASK FORCE DISCLAIMS ALL WARRANTIES, EXPRESS OR IMPLIED, INCLUDING BUT
--   NOT LIMITED TO ANY WARRANTY THAT THE USE OF THE INFORMATION HEREIN
--   WILL NOT INFRINGE ANY RIGHTS OR ANY IMPLIED WARRANTIES OF
--   MERCHANTABILITY OR FITNESS FOR A PARTICULAR PURPOSE.
