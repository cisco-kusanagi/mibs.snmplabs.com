-- |**********************************************************************|
 -- | Copyright 1998 - Sonoma Systems, Inc. Marina del Rey, CA 90292       |
 -- |    Unpublished software - All rights reserved.                       |
 -- |                                                                      |
 -- | The information in this software is subject to change without notice |
 -- | and should not be construed as a commitment by Sonoma Systems, Inc.  |
 -- |                                                                      |
 -- | Sonoma Systems, Inc. assumes no responsibility for the use or        |
 -- | reliability of its software on equipment which is not supplied by    |
 -- | Sonoma Systems, Inc.                                                 |
 -- |                                                                      |
 -- | This software is furnished under a license and may be copied only    |
 -- | under the terms of that license and with the inclusion of this       |
 -- | notice. This software, or any other copies thereof, may not be       |
 -- | provided or otherwise made available to any other person except to   |
 -- | one who agrees to these license terms. Title to and ownership of the |
 -- | software shall at all times remain with Sonoma Systems, Inc.         |
 -- |**********************************************************************|
 --
 -- Sonoma Systems Inc.,
 -- 4640 Admiralty Way, Suite #600,
 -- Marina Del Rey,
 -- California 90292-6695.
 --
 -- Web : www.sonoma-systems.com
 -- Phone:  310.827.8000
 --
 -- NAME        : tr_mib.def
 --
 -- DESCRIPTION : This is the MIB for the Sonoma Token Ring adapter group.
 --
 -- ARCHIVE : $Archive:   M:\pvcs\pvcsproj\sonoma3\src\mib\tr_mib.dev  $
 -- REVISION: $Revision:   1.4  $
 -- AUTHOR  : $Author:   FREEVE  $
 -- DATE    : $Date:   Nov 13 1998 10:34:02  $
    
    SONOMASYSTEMS-SONOMA-TRNCPQ-MIB    DEFINITIONS ::= BEGIN
    
    IMPORTS
             Counter, TimeTicks
             FROM RFC1155-SMI
             OBJECT-TYPE
             FROM RFC-1212
             sonomaLAN 
	     FROM SONOMASYSTEMS-SONOMA-MIB;
    
    PhysAddress ::= OCTET STRING

    -- Hierarchy for these groups
    -- enterprises     OBJECT IDENTIFIER ::= { private 4 }
    -- sonomaSystems   OBJECT IDENTIFIER ::= {  enterprises 2926 }
    -- sonomaSeries    OBJECT IDENTIFIER ::= { sonomaSystems 25 }
    -- sonomaLAN       OBJECT IDENTIFIER ::= { sonomaSeries 5 }
    sonomaTokenRing  OBJECT IDENTIFIER ::= { sonomaLAN 2 }
    tokenRingAdapterGroup OBJECT IDENTIFIER ::= { sonomaTokenRing 1 }
    trnCpqGroup    OBJECT IDENTIFIER ::= { tokenRingAdapterGroup 1 }

    
    trnCpqAdapterTable  OBJECT-TYPE
        SYNTAX  SEQUENCE OF TrnCpqAdapterEntry
        ACCESS  not-accessible
        STATUS  mandatory
        DESCRIPTION
        "This table contains the configuration and status information
         for the Token Ring 4/16 adapter cards."
        ::= { trnCpqGroup 1 }
    
    trnCpqAdapterEntry OBJECT-TYPE
        SYNTAX  TrnCpqAdapterEntry
        ACCESS  not-accessible
        STATUS  mandatory
        DESCRIPTION
        "An entry in the table of configuration and status information
         for the Token Ring 4/16 adapter cards."
        INDEX { trnCpqAdapterIndex }
        ::= { trnCpqAdapterTable 1 }
            
    TrnCpqAdapterEntry ::= SEQUENCE {
        trnCpqAdapterIndex             INTEGER,
        trnCpqAdapterCheckState        INTEGER,
        trnCpqAdapterOpenInWrapMode    INTEGER,
        trnCpqAdapterEarlyTokenRelease INTEGER,
        trnCpqAdapterGroupAddress      PhysAddress,
        trnCpqRingSpeedDetect 	       INTEGER,
        trnCpqMtu					   INTEGER
    }
            
    trnCpqAdapterIndex OBJECT-TYPE
        SYNTAX  INTEGER
        ACCESS  read-only
        STATUS  mandatory
        DESCRIPTION
        "The adapter number which identifies the instance of this
         adapter in the Sonoma system."
        ::= { trnCpqAdapterEntry 1 }
    
    trnCpqAdapterCheckState OBJECT-TYPE
        SYNTAX  INTEGER {
                         noErrors(1),              -- No Errors detected
                         adapterParity(2),        -- Adapter parity error
                         illegalOpCode(3),        -- Illegal Op code
                         arithmeticFault(4),      -- Arithmetic fault error
                         illegalMAC(5),           -- Illegal Memory Access
                         dioParity(6),            -- DIO parity
                         dmaParity(7),            -- DMA parity
                         dmaBus(8),               -- DMA Bus Error
                         dmaTimeout(9),           -- DMA Timeout Error
                         unknown(10),              -- Unknown Error
                         invalidXOP(11),          -- Invalid XOP Error
                         invalidINTR(12),         -- Invalid Interrupt Error
                         registerParity(13),      -- UserRegisterParityError
                         ramFailure(14),          -- Extended RAM Failure
                         phtxHalt(15),            -- UnabletohaltPHTransmit
                         phtxRun(16),             -- PHTransmitUnderrunError
                         adapterOutput(17),       -- Adapter Output Error
                         adapterProcessComplete(18) -- Adapter ProcessComplete
                        }
        ACCESS  read-only
        STATUS  mandatory
        DESCRIPTION
        "This object signifies the adapter check information when
         the AdapterCheck Interrupt has occured and the adapter is
         in a closed state waiting to be reset."
        ::= { trnCpqAdapterEntry 2 }
    
    trnCpqAdapterOpenInWrapMode OBJECT-TYPE
        SYNTAX  INTEGER{
				    enabled   (1),
					disabled  (2)
				}
        ACCESS  read-write
        STATUS  mandatory
        DESCRIPTION
        "This enables the adapter to open in Wrap Mode.
         In order to set/reset this parameter, close the logical port, change 
         the value and open the port."

        ::= { trnCpqAdapterEntry 3 }

    trnCpqAdapterEarlyTokenRelease OBJECT-TYPE
        SYNTAX  INTEGER{
				    enabled   (1),
					disabled  (2)
				}
        ACCESS  read-write
        STATUS  mandatory
        DESCRIPTION
        "This enables the early token release .
         In order to set/reset this parameter, close the logical port, change 
         the value and open the port."
        ::= { trnCpqAdapterEntry 4 }



    trnCpqAdapterGroupAddress OBJECT-TYPE
        SYNTAX   PhysAddress
        ACCESS   read-write
        STATUS   mandatory
        DESCRIPTION
        "The Group address of the adapter."
        ::= { trnCpqAdapterEntry 5 }
   

	trnCpqRingSpeedDetect OBJECT-TYPE
        SYNTAX  INTEGER {
						   auto (1),
						   manual (2)
					}
        ACCESS  read-write
        STATUS  mandatory
        DESCRIPTION
        "This specifies whether during open operation the card should
        autodetect the ring speed or read the dot5RingSpeed value and
        try to insert into the ring."
        ::= { trnCpqAdapterEntry 6 }
 
	trnCpqMtu OBJECT-TYPE
        SYNTAX  INTEGER (256..17952)
        ACCESS  read-write
        STATUS  mandatory
        DESCRIPTION
        "This specifies the mtu for the adapter.  The actual packet size may
		 be less depending on other adapters in the unit.  Changes will not 
		 take affect until the next reboot."
        ::= { trnCpqAdapterEntry 7 }
 
    trnCpqAdapterCheckStatsTable  OBJECT-TYPE
        SYNTAX  SEQUENCE OF TrnCpqAdapterCheckStatsEntry
        ACCESS  not-accessible
        STATUS  mandatory
        DESCRIPTION
        "A Table having Adapter Check statistics specific to 
         the Sonoma TRNCPQ Token Ring Adapter Cards, 
         one entry per card."
       ::= { trnCpqGroup  2 }
              
    trnCpqAdapterCheckStatsEntry  OBJECT-TYPE
        SYNTAX  TrnCpqAdapterCheckStatsEntry
        ACCESS  not-accessible
        STATUS  mandatory
        DESCRIPTION
        "An entry contains the sonoma token ring adapter check
         statistics for a particular interface."
        INDEX  { trnCpqAdapterCheckStatsIndex }
        ::= { trnCpqAdapterCheckStatsTable 1 }
    
    TrnCpqAdapterCheckStatsEntry  ::= SEQUENCE {
              trnCpqAdapterCheckStatsIndex   INTEGER,
              trnCpqAdapParityErrors         Counter,
              trnCpqIllOpCodeErrors          Counter,
              trnCpqArithFaultErrors         Counter,
              trnCpqIllMemErrors             Counter,
              trnCpqDIOParityErrors          Counter,
              trnCpqDMAParityErrors          Counter,
              trnCpqDMABusErrors             Counter,
              trnCpqDMATimeoutErrors         Counter,
              trnCpqInvIntrErrors            Counter,
              trnCpqInvXOPErrors             Counter,
              trnCpqRegParityErrors          Counter,
              trnCpqRAMFailErrors            Counter,
              trnCpqPHTxHaltErrors           Counter,
              trnCpqPHTxRunErrors            Counter
              }
    
    trnCpqAdapterCheckStatsIndex  OBJECT-TYPE
        SYNTAX  INTEGER
        ACCESS  read-only
        STATUS  mandatory
        DESCRIPTION
        "The value of this object identifies the sonoma token ring
         adapter interface for which this entry contains management
         information."
        ::= { trnCpqAdapterCheckStatsEntry 1 }
    
    trnCpqAdapParityErrors OBJECT-TYPE
        SYNTAX  Counter
        ACCESS  read-only
        STATUS  mandatory
        DESCRIPTION
        "The number of times the adapter detected a bus parity error
         on the adapter's internal bus."
        ::= { trnCpqAdapterCheckStatsEntry  2 } 
    
    trnCpqIllOpCodeErrors OBJECT-TYPE
        SYNTAX  Counter
        ACCESS  read-only
        STATUS  mandatory
        DESCRIPTION
       "The number of times the adapter's communications processor
        detected an illegal opcode in the adapter's internal program."
        ::= { trnCpqAdapterCheckStatsEntry  3 } 
    
    trnCpqArithFaultErrors OBJECT-TYPE
        SYNTAX  Counter
        ACCESS  read-only
        STATUS  mandatory
        DESCRIPTION
        "The number of times there was an arithmetic fault."
        ::= { trnCpqAdapterCheckStatsEntry  4 }
    
    trnCpqIllMemErrors OBJECT-TYPE
        SYNTAX  Counter
        ACCESS  read-only
        STATUS  mandatory
        DESCRIPTION
        "The number of illegal memory access occured."
        ::= { trnCpqAdapterCheckStatsEntry  5 }

    trnCpqDIOParityErrors OBJECT-TYPE
        SYNTAX  Counter
        ACCESS  read-only
        STATUS  mandatory
        DESCRIPTION
        "The number of times the adapter detected a bad parity on
         data passed from the attached system to the adapter through
         a direct I/O access."
        ::= { trnCpqAdapterCheckStatsEntry  6 }
    
    trnCpqDMAParityErrors OBJECT-TYPE
        SYNTAX  Counter
        ACCESS  read-only
        STATUS  mandatory
        DESCRIPTION
        "The number of times the adapter aborted a DMA operation as a
         result of parity errors."
        ::= { trnCpqAdapterCheckStatsEntry  7 }
    
    trnCpqDMABusErrors OBJECT-TYPE
        SYNTAX  Counter
        ACCESS  read-only
        STATUS  mandatory
        DESCRIPTION
        "The number of times the adapter aborted a DMA operation as
         a result of bus errors."
        ::= { trnCpqAdapterCheckStatsEntry  8 }
    
    trnCpqDMATimeoutErrors OBJECT-TYPE
        SYNTAX  Counter
        ACCESS  read-only
        STATUS  mandatory
        DESCRIPTION
        "The number of times the adapter timed out waiting for the
         completion of a DMA operation."
        ::= { trnCpqAdapterCheckStatsEntry  9 }

    trnCpqInvIntrErrors OBJECT-TYPE
        SYNTAX  Counter
        ACCESS  read-only
        STATUS  mandatory
        DESCRIPTION
        "The number of times an unrecognized error interrupt was
         generated."
        ::= { trnCpqAdapterCheckStatsEntry  10 }
    
    trnCpqInvXOPErrors OBJECT-TYPE
        SYNTAX  Counter
        ACCESS  read-only
        STATUS  mandatory
        DESCRIPTION
        "The number of times an unrecognized XOP request was generated
         in the communications processor code."
        ::= { trnCpqAdapterCheckStatsEntry  11 }    

    trnCpqRegParityErrors OBJECT-TYPE
        SYNTAX  Counter
        ACCESS  read-only
        STATUS  mandatory
        DESCRIPTION
        "The number of times a parity error occured in the user
         register."
        ::= { trnCpqAdapterCheckStatsEntry  12 }
    
    trnCpqRAMFailErrors OBJECT-TYPE
        SYNTAX  Counter
        ACCESS  read-only
        STATUS  mandatory
        DESCRIPTION
        "The number of times Extended RAM failure occured."
        ::= { trnCpqAdapterCheckStatsEntry  13 }
    
    trnCpqPHTxHaltErrors OBJECT-TYPE
        SYNTAX  Counter
        ACCESS  read-only
        STATUS  mandatory
        DESCRIPTION
        "The number of times DMA was unable to be stopped."
        ::= { trnCpqAdapterCheckStatsEntry  14 }
    
    trnCpqPHTxRunErrors OBJECT-TYPE
        SYNTAX  Counter
        ACCESS  read-only
        STATUS  mandatory
        DESCRIPTION
        "The number of internal DMA underruns when transmitting onto
         the ring."
        ::= { trnCpqAdapterCheckStatsEntry  15 }

    trnCpqBUDStatsTable  OBJECT-TYPE
        SYNTAX  SEQUENCE OF TrnCpqBUDStatsEntry
        ACCESS  not-accessible
        STATUS  mandatory
        DESCRIPTION
        "A Table having BUD statistics specific to the Sonoma
         TRNCPQ Token Ring Adapter Cards, one entry per card."
       ::= { trnCpqGroup  3 }
              
    trnCpqBUDStatsEntry  OBJECT-TYPE
        SYNTAX  TrnCpqBUDStatsEntry
        ACCESS  not-accessible
        STATUS  mandatory
        DESCRIPTION
        "An entry contains the sonoma token ring adapter statistics for
         a particular interface."
        INDEX  { trnCpqBUDStatsIndex }
        ::= { trnCpqBUDStatsTable 1 }
    
    TrnCpqBUDStatsEntry  ::= SEQUENCE {
              trnCpqBUDStatsIndex            INTEGER,
              trnCpqInitialTestErrors        Counter,
              trnCpqChecksumErrors           Counter,
              trnCpqAdapterRAMErrors         Counter,
              trnCpqInstructionTestErrors    Counter,
              trnCpqCtxtorIntrTestErrors     Counter,
              trnCpqProtocolHandlerHWErrors  Counter,
              trnCpqSystemInterfaceRegErrors Counter
              }
    
    trnCpqBUDStatsIndex  OBJECT-TYPE
        SYNTAX  INTEGER
        ACCESS  read-only
        STATUS  mandatory
        DESCRIPTION
        "The value of this object identifies the sonoma token ring
         adapter interface for which this entry contains management
         information."
        ::= { trnCpqBUDStatsEntry 1 }

    trnCpqInitialTestErrors OBJECT-TYPE
        SYNTAX  Counter
        ACCESS  read-only
        STATUS  mandatory
        DESCRIPTION
        "Initial Test error during BUD."
        ::= { trnCpqBUDStatsEntry  2 }

    trnCpqChecksumErrors OBJECT-TYPE
        SYNTAX  Counter
        ACCESS  read-only
        STATUS  mandatory
        DESCRIPTION
        "Checksum errors during BUD."
        ::= { trnCpqBUDStatsEntry  3 }

    trnCpqAdapterRAMErrors OBJECT-TYPE
        SYNTAX  Counter
        ACCESS  read-only
        STATUS  mandatory
        DESCRIPTION
        "Adapter RAM errors during BUD."
        ::= { trnCpqBUDStatsEntry  4 }

    trnCpqInstructionTestErrors OBJECT-TYPE
        SYNTAX  Counter
        ACCESS  read-only
        STATUS  mandatory
        DESCRIPTION
        "Instruction Test errors during BUD."
        ::= { trnCpqBUDStatsEntry  5 }
    
    trnCpqCtxtorIntrTestErrors OBJECT-TYPE
        SYNTAX  Counter
        ACCESS  read-only
        STATUS  mandatory
        DESCRIPTION
        "Context or Interrupt test errors during BUD."
         ::= { trnCpqBUDStatsEntry  6 }
    
    trnCpqProtocolHandlerHWErrors OBJECT-TYPE
        SYNTAX  Counter
        ACCESS  read-only
        STATUS  mandatory
        DESCRIPTION
        "Protocol handler hardware error during BUD."
        ::= { trnCpqBUDStatsEntry  7 }
    
    trnCpqSystemInterfaceRegErrors OBJECT-TYPE
        SYNTAX  Counter
        ACCESS  read-only
        STATUS  mandatory
        DESCRIPTION
        "System Interface register error during BUD."
        ::= { trnCpqBUDStatsEntry  8 }

    trnCpqInitStatsTable  OBJECT-TYPE
        SYNTAX  SEQUENCE OF TrnCpqInitStatsEntry
        ACCESS  not-accessible
        STATUS  mandatory
        DESCRIPTION
        "A Table having BUD and Initialization statistics 
         specific to the Sonoma TRNCPQ Token Ring Adapter 
         Cards, one entry per card."
       ::= { trnCpqGroup  4 }
              
    trnCpqInitStatsEntry  OBJECT-TYPE
        SYNTAX  TrnCpqInitStatsEntry
        ACCESS  not-accessible
        STATUS  mandatory
        DESCRIPTION
        "An entry contains the sonoma token ring adapter statistics for
         a particular interface."
        INDEX  { trnCpqInitStatsIndex }
        ::= { trnCpqInitStatsTable 1 }
    
    TrnCpqInitStatsEntry  ::= SEQUENCE {
              trnCpqInitStatsIndex           INTEGER,
              trnCpqInvInitBlocksErrors      Counter,
              trnCpqInvInitOptionsErrors     Counter,
              trnCpqNoResourcesErrors        Counter,
              trnCpqInitAddressErrors        Counter,
              trnCpqInitDIOParityErrors      Counter,
              trnCpqInitDMAParityErrors      Counter,
              trnCpqInitDMABusErrors         Counter,
              trnCpqInitDMATimeoutErrors     Counter,
              trnCpqInitDMADataErrors        Counter,
              trnCpqAdapterCheckErrors       Counter
              }
    
    trnCpqInitStatsIndex  OBJECT-TYPE
        SYNTAX  INTEGER
        ACCESS  read-only
        STATUS  mandatory
        DESCRIPTION
        "The value of this object identifies the sonoma token ring
         adapter interface for which this entry contains management
         information."
        ::= { trnCpqInitStatsEntry 1 }

    trnCpqInvInitBlocksErrors OBJECT-TYPE
        SYNTAX  Counter
        ACCESS  read-only
        STATUS  mandatory
        DESCRIPTION
        "The number of times the initialization parameter block was
         not transferred in full to the adapter."
        ::= { trnCpqInitStatsEntry  2 }
    
    trnCpqInvInitOptionsErrors OBJECT-TYPE
        SYNTAX  Counter
        ACCESS  read-only
        STATUS  mandatory
        DESCRIPTION
        "The number of times the bit 0 was not 1 or the other bits
         were not 0 in the initialization parameter block."
        ::= { trnCpqInitStatsEntry 3 }

    trnCpqNoResourcesErrors OBJECT-TYPE
        SYNTAX  Counter
        ACCESS  read-only
        STATUS  mandatory
        DESCRIPTION
        "The number of times there was insufficient adapter memory for
         the microcode."
        ::= { trnCpqInitStatsEntry 4 }

    trnCpqInitAddressErrors OBJECT-TYPE
        SYNTAX  Counter
        ACCESS  read-only
        STATUS  mandatory
        DESCRIPTION
        "The number of times invalid  hcb/hsb addresses caused an error
         during initialization." 
        ::= { trnCpqInitStatsEntry  5 }

   trnCpqInitDIOParityErrors OBJECT-TYPE
        SYNTAX  Counter
        ACCESS  read-only
        STATUS  mandatory
        DESCRIPTION
        "The number of times the adapter detected a bad parity on
         data passed from the attached system to the adapter through
         a direct I/O access, during initialization."
        ::= { trnCpqInitStatsEntry  6 }
    
    trnCpqInitDMAParityErrors OBJECT-TYPE
        SYNTAX  Counter
        ACCESS  read-only
        STATUS  mandatory
        DESCRIPTION
        "The number of times the adapter aborted a DMA operation as a
         result of parity errors during initialization."
        ::= { trnCpqInitStatsEntry  7 }
    
    trnCpqInitDMABusErrors OBJECT-TYPE
        SYNTAX  Counter
        ACCESS  read-only
        STATUS  mandatory
        DESCRIPTION
        "The number of times the adapter aborted a DMA operation as
         a result of bus errors during initialization."
        ::= { trnCpqInitStatsEntry  8 }
    
    trnCpqInitDMATimeoutErrors OBJECT-TYPE
        SYNTAX  Counter
        ACCESS  read-only
        STATUS  mandatory
        DESCRIPTION
        "The number of times the adapter timed out waiting for the
         completion of a DMA operationduring initialization."
        ::= { trnCpqInitStatsEntry  9 }
    
    trnCpqInitDMADataErrors OBJECT-TYPE
        SYNTAX  Counter
        ACCESS  read-only
        STATUS  mandatory
        DESCRIPTION
        "The number of times a DMA test failed because of data
         miscompare during initialization."
        ::= { trnCpqInitStatsEntry  10 }

    trnCpqAdapterCheckErrors OBJECT-TYPE
        SYNTAX  Counter
        ACCESS  read-only
        STATUS  mandatory
        DESCRIPTION
        "The number of times an unrecoverable hardware or
         software error occured during initialization."
        ::= { trnCpqInitStatsEntry  11 }

    trnCpqMiscStatsTable  OBJECT-TYPE
        SYNTAX  SEQUENCE OF TrnCpqMiscStatsEntry
        ACCESS  not-accessible
        STATUS  mandatory
        DESCRIPTION
        "A Table having miscellaneous statistics 
         specific to the Sonoma TRNCPQ Token Ring Adapter 
         Cards, one entry per card."
       ::= { trnCpqGroup  5 }
              
    trnCpqMiscStatsEntry  OBJECT-TYPE
        SYNTAX  TrnCpqMiscStatsEntry
        ACCESS  not-accessible
        STATUS  mandatory
        DESCRIPTION
        "An entry contains the sonoma token ring adapter statistics for
         a particular interface."
        INDEX  { trnCpqMiscStatsIndex }
        ::= { trnCpqMiscStatsTable 1 }
    
    TrnCpqMiscStatsEntry  ::= SEQUENCE {
              trnCpqMiscStatsIndex           INTEGER,
              trnCpqCounterOverflowErrors    Counter,
              trnCpqAutoRemovalErrors        Counter,
              trnCpqFrameBigErrors           Counter,
              trnCpqNoHostBufErrors          Counter,
              trnCpqAddressErrors            Counter,
              trnCpqAdapNotInsertedErrors    Counter,
              trnCpqMiscRcvErrors            Counter,
              trnCpqNoOfLinkResets           Counter,
              trnCpqLastLinkResetReason      INTEGER,
              trnCpqTimeSinceLastLinkReset   TimeTicks
              }

    trnCpqMiscStatsIndex  OBJECT-TYPE
        SYNTAX  INTEGER
        ACCESS  read-only
        STATUS  mandatory
        DESCRIPTION
        "The value of this object identifies the sonoma token ring
         adapter interface for which this entry contains management
         information."
        ::= { trnCpqMiscStatsEntry 1 }

    trnCpqCounterOverflowErrors OBJECT-TYPE
        SYNTAX  Counter
        ACCESS  read-only
        STATUS  mandatory
        DESCRIPTION
        "The number of times the adapter error counters have
      incremented from 254 to 255."
        ::= { trnCpqMiscStatsEntry 2 }

   trnCpqAutoRemovalErrors OBJECT-TYPE
        SYNTAX  Counter
        ACCESS  read-only
        STATUS  mandatory
        DESCRIPTION
        "The number of times the adapter has failed the lobe wrap test
         resulting from the beacon auto-removal process and has
         de-inserted from the ring."
        ::= { trnCpqMiscStatsEntry 3 }

    trnCpqFrameBigErrors OBJECT-TYPE
        SYNTAX  Counter
        ACCESS  read-only
        STATUS  mandatory
        DESCRIPTION
        "The number of times a received packet was discarded because
         the received frame was larger than Max_Frame_Size."
        ::= { trnCpqMiscStatsEntry 4 }
    
    trnCpqNoHostBufErrors OBJECT-TYPE
        SYNTAX  Counter
        ACCESS  read-only
        STATUS  mandatory
        DESCRIPTION
        "The number of times a received packet was discarded because
         there was no host buffer available in the Receive Structure
         Array."
        ::= { trnCpqMiscStatsEntry 5 }

    trnCpqAddressErrors OBJECT-TYPE
        SYNTAX  Counter
        ACCESS  read-only
        STATUS  mandatory
        DESCRIPTION
        "The number of times an error occured due to invalid addresses.
         This does not include errors that occur during initialization.
         Those errors are being handled in the BUD specific table."
        ::= { trnCpqMiscStatsEntry 6 }

    trnCpqAdapNotInsertedErrors OBJECT-TYPE
        SYNTAX  Counter
        ACCESS  read-only
        STATUS  mandatory
        DESCRIPTION
        "The number of times an operation failed because of the
         adapter not being inserted."
        ::= { trnCpqMiscStatsEntry 7 }
    
    trnCpqMiscRcvErrors OBJECT-TYPE
        SYNTAX  Counter
        ACCESS  read-only
        STATUS  mandatory
        DESCRIPTION
        "The number of times a receive error was detected by the
         microcode."
        ::= { trnCpqMiscStatsEntry 8 }
    
    trnCpqNoOfLinkResets  OBJECT-TYPE
        SYNTAX  Counter
        ACCESS  read-only
        STATUS  mandatory
        DESCRIPTION
        "This object is a count of the number of resets which have
         occurred on this Token Ring link, since the last
         reinitialization of the unit."
        ::= { trnCpqMiscStatsEntry 9 }
    
    trnCpqLastLinkResetReason  OBJECT-TYPE
        SYNTAX  INTEGER {
                         noReason (1),
                         management (2),
                         deviceError(3)
                        } 
        ACCESS  read-only
        STATUS  mandatory
        DESCRIPTION
        "This object gives the a reason code for the last reset which
         occurred on this Token ring port. This object gives the
         reason code for the last reset which occurred on this LAN
         physical link. A value of noReason(1) is returned if the link
         has not reset.  A value of management(2) is returned when a
         link reset has been caused by SNMP.  A value of deviceError(3)
         is returned if the link reset was caused by a hardware failure."
        ::= { trnCpqMiscStatsEntry 10 }
    
    trnCpqTimeSinceLastLinkReset  OBJECT-TYPE
        SYNTAX  TimeTicks 
        ACCESS  read-only
        STATUS  mandatory
        DESCRIPTION
        "This object gives the time (in hundreths of seconds) since
         the last link reset, eg. The time since the last link went
         down.  The value of this object is zero if no link resets
         have occured since the last reinitialization of the unit."
        ::= { trnCpqMiscStatsEntry 11 }
    
        END
