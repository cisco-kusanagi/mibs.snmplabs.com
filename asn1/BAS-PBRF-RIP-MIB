BAS-PBRF-RIP-MIB DEFINITIONS ::= BEGIN

IMPORTS
    MODULE-IDENTITY, OBJECT-TYPE, IpAddress, Integer32  FROM SNMPv2-SMI
    RowStatus                                           FROM SNMPv2-TC
    BasChassisId, BasSlotId, BasInterfaceId,
    BasLogicalPortId, basPbrfRIP                        FROM BAS-MIB;

basPbrfRIPMIB MODULE-IDENTITY
    LAST-UPDATED "9812220800Z"
    ORGANIZATION "Broadband Access Systems, Inc."
    CONTACT-INFO
        " Tech Support
          Broadband Access Systems, Inc.
          201 Forest Street
          Marlborough, MA 01752
          USA

          508-485-8200
          support@basystems.com"
    DESCRIPTION
        "The MIB module defines the configuration MIB objects
         for Broadband Access Systems, Inc. RIP Export
	 policy based routing filters."
    ::= { basPbrfRIP 1 }

basPbrfRIPImport  OBJECT IDENTIFIER ::= { basPbrfRIPMIB 1 }
basPbrfRIPExport  OBJECT IDENTIFIER ::= { basPbrfRIPMIB 2 }

-- the BAS RIP Import PBRF filter table

-- The BAS RIP Import PBRF test filter table contains BAS proprietary
-- information of a BAS RIP Import PBRF filter.

basPbrfRIPImportTable OBJECT-TYPE
    SYNTAX      SEQUENCE OF BasPbrfRIPImportEntry
    MAX-ACCESS  not-accessible
    STATUS      current
    DESCRIPTION
        "A table of RIP import PBRF test filter entries."
    ::= { basPbrfRIPImport 1 }

basPbrfRIPImportEntry OBJECT-TYPE
    SYNTAX      BasPbrfRIPImportEntry
    MAX-ACCESS  not-accessible
    STATUS      current
    DESCRIPTION
        "An entry containing management information applicable
        to an RIP import PBRF filter used for testing the
        validity of a filter."
    INDEX { basPbrfRIPImportChassis,
            basPbrfRIPImportSlot,
            basPbrfRIPImportIf,
            basPbrfRIPImportLPort,
            basPbrfRIPImportIndex }
    ::= { basPbrfRIPImportTable 1 }

BasPbrfRIPImportEntry ::=
    SEQUENCE {
        basPbrfRIPImportChassis         BasChassisId,
        basPbrfRIPImportSlot            BasSlotId,
        basPbrfRIPImportIf              BasInterfaceId,
        basPbrfRIPImportLPort           BasLogicalPortId,
        basPbrfRIPImportIndex           Integer32,
        -- basPbrfRIPImportTestStatus      INTEGER,
        basPbrfRIPImportTemplateCount   Integer32,
        basPbrfRIPImportRowStatus       RowStatus,
	basPbrfRIPImportDescr           OCTET STRING
    }

basPbrfRIPImportChassis OBJECT-TYPE
    SYNTAX      BasChassisId
    MAX-ACCESS  not-accessible
    STATUS      current
    DESCRIPTION
        "The chassis identifier of this chassis."
    ::= { basPbrfRIPImportEntry 1 }

basPbrfRIPImportSlot OBJECT-TYPE
    SYNTAX      BasSlotId
    MAX-ACCESS  not-accessible
    STATUS      current
    DESCRIPTION
        "The BAS slot ID of this card."
    ::= { basPbrfRIPImportEntry 2 }

basPbrfRIPImportIf OBJECT-TYPE
    SYNTAX      BasInterfaceId
    MAX-ACCESS  not-accessible
    STATUS      current
    DESCRIPTION
        "The BAS interface ID of this card."
    ::= { basPbrfRIPImportEntry 3 }

basPbrfRIPImportLPort OBJECT-TYPE
    SYNTAX      BasLogicalPortId
    MAX-ACCESS  not-accessible
    STATUS      current
    DESCRIPTION
        "The BAS logical port ID of this card."
    ::= { basPbrfRIPImportEntry 4 }

basPbrfRIPImportIndex OBJECT-TYPE
    SYNTAX      Integer32
    MAX-ACCESS  not-accessible
    STATUS      current
    DESCRIPTION
        "The index of the filter."
    ::= { basPbrfRIPImportEntry 5 }

-- basPbrfRIPImportTestStatus OBJECT-TYPE
--    SYNTAX      INTEGER {
--                        startTest(1),
--                        testing(2),
--                        testSucceed(3),
--                        testFail(4),
--                       notTested(5)
--                }
--    MAX-ACCESS  read-create
--    STATUS      current
--    DESCRIPTION
--        "The status of validating the filter. The value
--        startTest(1) is the only value that my be specified
--        in a write operation. The values testing(2),
--        testSucceed(3), testFail(4), and notTested(5) may be
--        returned by a read operation."
--    ::= { basPbrfRIPImportEntry 6 }

basPbrfRIPImportTemplateCount OBJECT-TYPE
    SYNTAX      Integer32
    MAX-ACCESS  read-only
    STATUS      current
    DESCRIPTION
        "The number of templates assigned to this filter."
    ::= { basPbrfRIPImportEntry 7 }

basPbrfRIPImportRowStatus OBJECT-TYPE
    SYNTAX      RowStatus
    MAX-ACCESS  read-create
    STATUS      current
    DESCRIPTION
        "The row status of the filter."
    ::= { basPbrfRIPImportEntry 8 }

basPbrfRIPImportDescr OBJECT-TYPE
    SYNTAX      OCTET STRING(SIZE(0..64))
    MAX-ACCESS  read-create
    STATUS      current
    DESCRIPTION
        "The descr of the RIP Import."
    ::= { basPbrfRIPImportEntry 9 }


-- the BAS RIP Import PBRF filter template table

-- The BAS RIP Import PBRF filter template table contains BAS
-- proprietary information on policy based route filtering filter
-- structure for RIP Import filtering.

basPbrfRIPImportFilterTempTable OBJECT-TYPE
    SYNTAX      SEQUENCE OF BasPbrfRIPImportFilterTempEntry
    MAX-ACCESS  not-accessible
    STATUS      current
    DESCRIPTION
        "A table of RIP import PBRF filters."
    ::= { basPbrfRIPImport 2 }

basPbrfRIPImportFilterTempEntry OBJECT-TYPE
    SYNTAX      BasPbrfRIPImportFilterTempEntry
    MAX-ACCESS  not-accessible
    STATUS      current
    DESCRIPTION
        "An entry containing management information applicable
        to a RIP import PBRF filter."
    INDEX { basPbrfRIPImportFilterTempChassis,
            basPbrfRIPImportFilterTempSlot,
            basPbrfRIPImportFilterTempIf,
            basPbrfRIPImportFilterTempLPort,
            basPbrfRIPImportFilterTempIndex,
            basPbrfRIPImportFilterTempTemplate }
    ::= { basPbrfRIPImportFilterTempTable 1 }

BasPbrfRIPImportFilterTempEntry ::=
    SEQUENCE {
        basPbrfRIPImportFilterTempChassis         BasChassisId,
        basPbrfRIPImportFilterTempSlot            BasSlotId,
        basPbrfRIPImportFilterTempIf              BasInterfaceId,
        basPbrfRIPImportFilterTempLPort           BasLogicalPortId,
        basPbrfRIPImportFilterTempIndex           Integer32,
        basPbrfRIPImportFilterTempTemplate        Integer32,
        basPbrfRIPImportFilterTempOrder           Integer32,
        basPbrfRIPImportFilterTempRowStatus       RowStatus
    }

basPbrfRIPImportFilterTempChassis OBJECT-TYPE
    SYNTAX      BasChassisId
    MAX-ACCESS  not-accessible
    STATUS      current
    DESCRIPTION
        "The BAS chassis identifier of this chassis."
    ::= { basPbrfRIPImportFilterTempEntry 1 }

basPbrfRIPImportFilterTempSlot OBJECT-TYPE
    SYNTAX      BasSlotId
    MAX-ACCESS  not-accessible
    STATUS      current
    DESCRIPTION
        "The BAS slot ID of this card."
    ::= { basPbrfRIPImportFilterTempEntry 2 }

basPbrfRIPImportFilterTempIf OBJECT-TYPE
    SYNTAX      BasInterfaceId
    MAX-ACCESS  not-accessible
    STATUS      current
    DESCRIPTION
        "The BAS interface ID of this card."
    ::= { basPbrfRIPImportFilterTempEntry 3 }

basPbrfRIPImportFilterTempLPort OBJECT-TYPE
    SYNTAX      BasLogicalPortId
    MAX-ACCESS  not-accessible
    STATUS      current
    DESCRIPTION
        "The BAS logical port ID of this card."
    ::= { basPbrfRIPImportFilterTempEntry 4 }

basPbrfRIPImportFilterTempIndex OBJECT-TYPE
    SYNTAX      Integer32
    MAX-ACCESS  not-accessible
    STATUS      current
    DESCRIPTION
        "The index of the filter."
    ::= { basPbrfRIPImportFilterTempEntry 5 }

basPbrfRIPImportFilterTempTemplate OBJECT-TYPE
    SYNTAX      Integer32
    MAX-ACCESS  not-accessible
    STATUS      current
    DESCRIPTION
        "The index for the specific template."
    ::= { basPbrfRIPImportFilterTempEntry 6 }

basPbrfRIPImportFilterTempOrder OBJECT-TYPE
    SYNTAX      Integer32
    MAX-ACCESS  read-create
    STATUS      current
    DESCRIPTION
        "The order in which the template is applied."
    ::= { basPbrfRIPImportFilterTempEntry 7 }

basPbrfRIPImportFilterTempRowStatus OBJECT-TYPE
    SYNTAX      RowStatus
    MAX-ACCESS  read-create
    STATUS      current
    DESCRIPTION
        "The row status of the filter."
    ::= { basPbrfRIPImportFilterTempEntry 8 }


-- the BAS RIP IMPORT PBRF template table

-- The BAS RIP IMPORT TEMPLATE PBRF table contains BAS proprietary
-- information on RIP Import policy based route filtering template structure.

basPbrfRIPImportTemplateTable OBJECT-TYPE
    SYNTAX      SEQUENCE OF BasPbrfRIPImportTemplateEntry
    MAX-ACCESS  not-accessible
    STATUS      current
    DESCRIPTION
        "A table of RIP Import template entries."
    ::= { basPbrfRIPImport 3 }

basPbrfRIPImportTemplateEntry OBJECT-TYPE
    SYNTAX      BasPbrfRIPImportTemplateEntry
    MAX-ACCESS  not-accessible
    STATUS      current
    DESCRIPTION
        "An entry containing management information applicable
        to a RIP Import PBRF template."
    INDEX { basPbrfRIPImportTemplateChassis,
            basPbrfRIPImportTemplateSlot,
            basPbrfRIPImportTemplateIf,
            basPbrfRIPImportTemplateLPort,
            basPbrfRIPImportTemplateIndex }
    ::= { basPbrfRIPImportTemplateTable 1 }

BasPbrfRIPImportTemplateEntry ::=
    SEQUENCE {
        basPbrfRIPImportTemplateChassis         BasChassisId,
        basPbrfRIPImportTemplateSlot            BasSlotId,
        basPbrfRIPImportTemplateIf              BasInterfaceId,
        basPbrfRIPImportTemplateLPort           BasLogicalPortId,
        basPbrfRIPImportTemplateIndex           Integer32,
        basPbrfRIPImportTemplateRouteAddr       IpAddress,
        basPbrfRIPImportTemplateRouteMask       IpAddress,
        basPbrfRIPImportTemplatePeerAddr        IpAddress,
        basPbrfRIPImportTemplatePeerMask        IpAddress,
        basPbrfRIPImportTemplateTag	        Integer32,
        basPbrfRIPImportTemplateKeyBits	        Integer32,
        basPbrfRIPImportTemplatePref	        Integer32,
        basPbrfRIPImportTemplateMetric	        Integer32,
        basPbrfRIPImportTemplateFlags	        Integer32,
        basPbrfRIPImportTemplateActionTag       Integer32,
	basPbrfRIPImportTemplateRowStatus       RowStatus,
        basPbrfRIPImportTemplateDescr           OCTET STRING       
   }

basPbrfRIPImportTemplateChassis OBJECT-TYPE
    SYNTAX      BasChassisId
    MAX-ACCESS  not-accessible
    STATUS      current
    DESCRIPTION
        "The BAS chassis identifier of this chassis."
    ::= { basPbrfRIPImportTemplateEntry 1 }

basPbrfRIPImportTemplateSlot OBJECT-TYPE
    SYNTAX      BasSlotId
    MAX-ACCESS  not-accessible
    STATUS      current
    DESCRIPTION
        "The BAS slot ID of this card."
    ::= { basPbrfRIPImportTemplateEntry 2 }

basPbrfRIPImportTemplateIf OBJECT-TYPE
    SYNTAX      BasInterfaceId
    MAX-ACCESS  not-accessible
    STATUS      current
    DESCRIPTION
        "The BAS interface ID of this card."
    ::= { basPbrfRIPImportTemplateEntry 3 }

basPbrfRIPImportTemplateLPort OBJECT-TYPE
    SYNTAX      BasLogicalPortId
    MAX-ACCESS  not-accessible
    STATUS      current
    DESCRIPTION
        "The BAS logical port ID of this card."
    ::= { basPbrfRIPImportTemplateEntry 4 }

basPbrfRIPImportTemplateIndex OBJECT-TYPE
    SYNTAX      Integer32
    MAX-ACCESS  not-accessible
    STATUS      current
    DESCRIPTION
        "The index of the template."
    ::= { basPbrfRIPImportTemplateEntry 5 }

basPbrfRIPImportTemplateRouteAddr OBJECT-TYPE
    SYNTAX      IpAddress
    MAX-ACCESS  read-create
    STATUS      current
    DESCRIPTION
        "The Route Address key of the template."
    ::= { basPbrfRIPImportTemplateEntry 6 }

basPbrfRIPImportTemplateRouteMask OBJECT-TYPE
    SYNTAX      IpAddress
    MAX-ACCESS  read-create
    STATUS       current
    DESCRIPTION
        "The Route Mask key of the template."
    ::= { basPbrfRIPImportTemplateEntry 7 }

basPbrfRIPImportTemplatePeerAddr OBJECT-TYPE
    SYNTAX      IpAddress
    MAX-ACCESS  read-create
    STATUS      current
    DESCRIPTION
        "The PeerAddr key of the template."
    ::= { basPbrfRIPImportTemplateEntry 8 }

basPbrfRIPImportTemplatePeerMask OBJECT-TYPE
    SYNTAX      IpAddress
    MAX-ACCESS  read-create
    STATUS      current
    DESCRIPTION
        "The PeerMask key of the template."
    ::= { basPbrfRIPImportTemplateEntry 9 }

basPbrfRIPImportTemplateTag OBJECT-TYPE
    SYNTAX      Integer32
    MAX-ACCESS  read-create
    STATUS      current
    DESCRIPTION
        "The tag key of the template."
    ::= { basPbrfRIPImportTemplateEntry 10 }

basPbrfRIPImportTemplateKeyBits OBJECT-TYPE
    SYNTAX      Integer32
    MAX-ACCESS  read-create
    STATUS      current
    DESCRIPTION
        "The key bits key mask of the template."
    ::= { basPbrfRIPImportTemplateEntry 11 }

basPbrfRIPImportTemplatePref OBJECT-TYPE
    SYNTAX      Integer32
    MAX-ACCESS  read-create
    STATUS      current
    DESCRIPTION
        "The preference of the template action."
    ::= { basPbrfRIPImportTemplateEntry 12 }

basPbrfRIPImportTemplateMetric OBJECT-TYPE
    SYNTAX      Integer32
    MAX-ACCESS  read-create
    STATUS      current
    DESCRIPTION
        "The metric of the template action."
    ::= { basPbrfRIPImportTemplateEntry 13 }

basPbrfRIPImportTemplateFlags OBJECT-TYPE
    SYNTAX      Integer32
    MAX-ACCESS  read-create
    STATUS      current
    DESCRIPTION
        "The flags of the template action."
    ::= { basPbrfRIPImportTemplateEntry 14 }

basPbrfRIPImportTemplateActionTag OBJECT-TYPE
    SYNTAX      Integer32
    MAX-ACCESS  read-create
    STATUS      current
    DESCRIPTION
        "The tag of the template action."
    ::= { basPbrfRIPImportTemplateEntry 15 }

basPbrfRIPImportTemplateRowStatus OBJECT-TYPE
    SYNTAX      RowStatus
    MAX-ACCESS  read-create
    STATUS      current
    DESCRIPTION
        "The row status of the template."
    ::= { basPbrfRIPImportTemplateEntry 16 }

basPbrfRIPImportTemplateDescr OBJECT-TYPE
    SYNTAX      OCTET STRING(SIZE(0..64))
    MAX-ACCESS  read-create
    STATUS      current
    DESCRIPTION
        "The descr of the RIP Import template."
    ::= { basPbrfRIPImportTemplateEntry 17 }


-- the BAS RIP Import PBRF filter table

-- The BAS RIP Import PBRF test filter table contains BAS proprietary
-- information of a BAS RIP Import PBRF filter.

basPbrfRIPExportTable OBJECT-TYPE
    SYNTAX      SEQUENCE OF BasPbrfRIPExportEntry
    MAX-ACCESS  not-accessible
    STATUS      current
    DESCRIPTION
        "A table of RIP export PBRF test filter entries."
    ::= { basPbrfRIPExport 1 }

basPbrfRIPExportEntry OBJECT-TYPE
    SYNTAX      BasPbrfRIPExportEntry
    MAX-ACCESS  not-accessible
    STATUS      current
    DESCRIPTION
        "An entry containing management information applicable
        to an RIP export PBRF filter used for testing the
        validity of a filter."
    INDEX { basPbrfRIPExportChassis,
            basPbrfRIPExportSlot,
            basPbrfRIPExportIf,
            basPbrfRIPExportLPort,
            basPbrfRIPExportIndex }
    ::= { basPbrfRIPExportTable 1 }

BasPbrfRIPExportEntry ::=
    SEQUENCE {
        basPbrfRIPExportChassis         BasChassisId,
        basPbrfRIPExportSlot            BasSlotId,
        basPbrfRIPExportIf              BasInterfaceId,
        basPbrfRIPExportLPort           BasLogicalPortId,
        basPbrfRIPExportIndex           Integer32,
        -- basPbrfRIPExportTestStatus      INTEGER,
        basPbrfRIPExportTemplateCount   Integer32,
        basPbrfRIPExportRowStatus       RowStatus,
	basPbrfRIPExportDescr		OCTET STRING
    }

basPbrfRIPExportChassis OBJECT-TYPE
    SYNTAX      BasChassisId
    MAX-ACCESS  not-accessible
    STATUS      current
    DESCRIPTION
        "The chassis identifier of this chassis."
    ::= { basPbrfRIPExportEntry 1 }

basPbrfRIPExportSlot OBJECT-TYPE
    SYNTAX      BasSlotId
    MAX-ACCESS  not-accessible
    STATUS      current
    DESCRIPTION
        "The BAS slot ID of this card."
    ::= { basPbrfRIPExportEntry 2 }

basPbrfRIPExportIf OBJECT-TYPE
    SYNTAX      BasInterfaceId
    MAX-ACCESS  not-accessible
    STATUS      current
    DESCRIPTION
        "The BAS interface ID of this card."
    ::= { basPbrfRIPExportEntry 3 }

basPbrfRIPExportLPort OBJECT-TYPE
    SYNTAX      BasLogicalPortId
    MAX-ACCESS  not-accessible
    STATUS      current
    DESCRIPTION
        "The BAS logical port ID of this card."
    ::= { basPbrfRIPExportEntry 4 }

basPbrfRIPExportIndex OBJECT-TYPE
    SYNTAX      Integer32
    MAX-ACCESS  not-accessible
    STATUS      current
    DESCRIPTION
        "The index of the filter."
    ::= { basPbrfRIPExportEntry 5 }

-- basPbrfRIPExportTestStatus OBJECT-TYPE
--   SYNTAX      INTEGER {
--                       startTest(1),
--                        testing(2),
--                        testSucceed(3),
--                        testFail(4),
--                        notTested(5)
--                }
--   MAX-ACCESS  read-create
--    STATUS      current
--    DESCRIPTION
--        "The status of validating the filter. The value
--        startTest(1) is the only value that my be specified
--        in a write operation. The values testing(2),
--        testSucceed(3), testFail(4), and notTested(5) may be
--        returned by a read operation."
--    DEFVAL { notTested }
--    ::= { basPbrfRIPExportEntry 6 }

basPbrfRIPExportTemplateCount OBJECT-TYPE
    SYNTAX      Integer32
    MAX-ACCESS  read-only
    STATUS      current
    DESCRIPTION
        "The number of templates assigned to this filter."
    ::= { basPbrfRIPExportEntry 7 }

basPbrfRIPExportRowStatus OBJECT-TYPE
    SYNTAX      RowStatus
    MAX-ACCESS  read-create
    STATUS      current
    DESCRIPTION
        "The row status of the filter."
    ::= { basPbrfRIPExportEntry 8 }

basPbrfRIPExportDescr OBJECT-TYPE
    SYNTAX      OCTET STRING(SIZE(0..64))
    MAX-ACCESS  read-create
    STATUS      current
    DESCRIPTION
        "The descr of the RIP Export."
    ::= { basPbrfRIPExportEntry 9 }


-- the BAS RIP Export PBRF filter template table

-- The BAS RIP Export PBRF filter template table contains BAS
-- proprietary information on policy based route filtering filter
-- structure for RIP Export filtering.

basPbrfRIPExportFilterTempTable OBJECT-TYPE
    SYNTAX      SEQUENCE OF BasPbrfRIPExportFilterTempEntry
    MAX-ACCESS  not-accessible
    STATUS      current
    DESCRIPTION
        "A table of RIP Export PBRF filter/template bindings."
    ::= { basPbrfRIPExport 2 }

basPbrfRIPExportFilterTempEntry OBJECT-TYPE
    SYNTAX      BasPbrfRIPExportFilterTempEntry
    MAX-ACCESS  not-accessible
    STATUS      current
    DESCRIPTION
        "An entry containing management information applicable
        to a RIP export PBRF filter."
    INDEX { basPbrfRIPExportFilterTempChassis,
            basPbrfRIPExportFilterTempSlot,
            basPbrfRIPExportFilterTempIf,
            basPbrfRIPExportFilterTempLPort,
            basPbrfRIPExportFilterTempIndex,
            basPbrfRIPExportFilterTempTemplate }
    ::= { basPbrfRIPExportFilterTempTable 1 }

BasPbrfRIPExportFilterTempEntry ::=
    SEQUENCE {
        basPbrfRIPExportFilterTempChassis         BasChassisId,
        basPbrfRIPExportFilterTempSlot            BasSlotId,
        basPbrfRIPExportFilterTempIf              BasInterfaceId,
        basPbrfRIPExportFilterTempLPort           BasLogicalPortId,
        basPbrfRIPExportFilterTempIndex           Integer32,
        basPbrfRIPExportFilterTempTemplate        Integer32,
        basPbrfRIPExportFilterTempOrder           Integer32,
        basPbrfRIPExportFilterTempRowStatus       RowStatus
      }

basPbrfRIPExportFilterTempChassis OBJECT-TYPE
    SYNTAX      BasChassisId
    MAX-ACCESS  not-accessible
    STATUS      current
    DESCRIPTION
        "The BAS chassis identifier of this chassis."
    ::= { basPbrfRIPExportFilterTempEntry 1 }

basPbrfRIPExportFilterTempSlot OBJECT-TYPE
    SYNTAX      BasSlotId
    MAX-ACCESS  not-accessible
    STATUS      current
    DESCRIPTION
        "The BAS slot ID of this card."
    ::= { basPbrfRIPExportFilterTempEntry 2 }

basPbrfRIPExportFilterTempIf OBJECT-TYPE
    SYNTAX      BasInterfaceId
    MAX-ACCESS  not-accessible
    STATUS      current
    DESCRIPTION
        "The BAS interface ID of this card."
    ::= { basPbrfRIPExportFilterTempEntry 3 }

basPbrfRIPExportFilterTempLPort OBJECT-TYPE
    SYNTAX      BasLogicalPortId
    MAX-ACCESS  not-accessible
    STATUS      current
    DESCRIPTION
        "The BAS logical port ID of this card."
    ::= { basPbrfRIPExportFilterTempEntry 4 }

basPbrfRIPExportFilterTempIndex OBJECT-TYPE
    SYNTAX      Integer32
    MAX-ACCESS  not-accessible
    STATUS      current
    DESCRIPTION
        "The index of the filter."
    ::= { basPbrfRIPExportFilterTempEntry 5 }

basPbrfRIPExportFilterTempTemplate OBJECT-TYPE
    SYNTAX      Integer32
    MAX-ACCESS  not-accessible
    STATUS      current
    DESCRIPTION
        "The index for the specific template."
    ::= { basPbrfRIPExportFilterTempEntry 6 }

basPbrfRIPExportFilterTempOrder OBJECT-TYPE
    SYNTAX      Integer32
    MAX-ACCESS  read-create
    STATUS      current
    DESCRIPTION
        "The order in which the template is applied."
    ::= { basPbrfRIPExportFilterTempEntry 7 }

basPbrfRIPExportFilterTempRowStatus OBJECT-TYPE
    SYNTAX      RowStatus
    MAX-ACCESS  read-create
    STATUS      current
    DESCRIPTION
        "The row status of the filter."
    ::= { basPbrfRIPExportFilterTempEntry 8 }


-- the BAS RIP EXPORT PBRF template table

-- The BAS RIP EXPORT TEMPLATE PBRF table contains BAS proprietary
-- information on RIP Export policy based route filtering template structure.

basPbrfRIPExportTemplateTable OBJECT-TYPE
    SYNTAX      SEQUENCE OF BasPbrfRIPExportTemplateEntry
    MAX-ACCESS  not-accessible
    STATUS      current
    DESCRIPTION
        "A table of RIP Export template entries."
    ::= { basPbrfRIPExport 3 }

basPbrfRIPExportTemplateEntry OBJECT-TYPE
    SYNTAX      BasPbrfRIPExportTemplateEntry
    MAX-ACCESS  not-accessible
    STATUS      current
    DESCRIPTION
        "An entry containing management information applicable
        to an RIP Export PBRF template."
    INDEX { basPbrfRIPExportTemplateChassis,
            basPbrfRIPExportTemplateSlot,
            basPbrfRIPExportTemplateIf,
            basPbrfRIPExportTemplateLPort,
            basPbrfRIPExportTemplateIndex }
    ::= { basPbrfRIPExportTemplateTable 1 }

BasPbrfRIPExportTemplateEntry ::=
    SEQUENCE {
        basPbrfRIPExportTemplateChassis         BasChassisId,
        basPbrfRIPExportTemplateSlot            BasSlotId,
        basPbrfRIPExportTemplateIf              BasInterfaceId,
        basPbrfRIPExportTemplateLPort           BasLogicalPortId,
        basPbrfRIPExportTemplateIndex           Integer32,
        basPbrfRIPExportTemplateRouteAddr       IpAddress,
        basPbrfRIPExportTemplateRouteMask       IpAddress,
        basPbrfRIPExportTemplateIntfAddr        IpAddress,
        basPbrfRIPExportTemplateProtocol        Integer32,
        basPbrfRIPExportTemplateSpecific        IpAddress,
        basPbrfRIPExportTemplatePeerMask        IpAddress,
        basPbrfRIPExportTemplateTag             Integer32,
        basPbrfRIPExportTemplateKeyBits         Integer32,
        basPbrfRIPExportTemplateMetric          Integer32,
        basPbrfRIPExportTemplateFlags           Integer32,
	basPbrfRIPExportTemplateActionTag       Integer32,
	basPbrfRIPExportTemplateRowStatus       RowStatus,
	basPbrfRIPExportTemplateDescr           OCTET STRING
   }

basPbrfRIPExportTemplateChassis OBJECT-TYPE
    SYNTAX      BasChassisId
    MAX-ACCESS  not-accessible
    STATUS      current
    DESCRIPTION
        "The BAS chassis identifier of this chassis."
    ::= { basPbrfRIPExportTemplateEntry 1 }

basPbrfRIPExportTemplateSlot OBJECT-TYPE
    SYNTAX      BasSlotId
    MAX-ACCESS  not-accessible
    STATUS      current
    DESCRIPTION
        "The BAS slot ID of this card."
    ::= { basPbrfRIPExportTemplateEntry 2 }

basPbrfRIPExportTemplateIf OBJECT-TYPE
    SYNTAX      BasInterfaceId
    MAX-ACCESS  not-accessible
    STATUS      current
    DESCRIPTION
        "The BAS interface ID of this card."
    ::= { basPbrfRIPExportTemplateEntry 3 }

basPbrfRIPExportTemplateLPort OBJECT-TYPE
    SYNTAX      BasLogicalPortId
    MAX-ACCESS  not-accessible
    STATUS      current
    DESCRIPTION
        "The BAS logical port ID of this card."
    ::= { basPbrfRIPExportTemplateEntry 4 }

basPbrfRIPExportTemplateIndex OBJECT-TYPE
    SYNTAX      Integer32
    MAX-ACCESS  not-accessible
    STATUS      current
    DESCRIPTION
        "The index of the template"
    ::= { basPbrfRIPExportTemplateEntry 5 }

basPbrfRIPExportTemplateRouteAddr OBJECT-TYPE
    SYNTAX      IpAddress
    MAX-ACCESS  read-create
    STATUS      current
    DESCRIPTION
        "The Route Address key of the template."
    ::= { basPbrfRIPExportTemplateEntry 6 }

basPbrfRIPExportTemplateRouteMask OBJECT-TYPE
    SYNTAX      IpAddress
    MAX-ACCESS  read-create
    STATUS      current
    DESCRIPTION
        "The Route Mask key of the template."
    ::= { basPbrfRIPExportTemplateEntry 7 }

basPbrfRIPExportTemplateIntfAddr OBJECT-TYPE
    SYNTAX      IpAddress
    MAX-ACCESS  read-create
    STATUS      current
    DESCRIPTION
        "The Interface address key of the template."
    ::= { basPbrfRIPExportTemplateEntry 8 }

basPbrfRIPExportTemplateProtocol OBJECT-TYPE
    SYNTAX      Integer32
    MAX-ACCESS  read-create
    STATUS      current
    DESCRIPTION
        "The protocol key of the template."
    ::= { basPbrfRIPExportTemplateEntry 9 }

basPbrfRIPExportTemplateSpecific OBJECT-TYPE
    SYNTAX      IpAddress
    MAX-ACCESS  read-create
    STATUS      current
    DESCRIPTION
        "The specific key of the template."
    ::= { basPbrfRIPExportTemplateEntry 10 }

basPbrfRIPExportTemplatePeerMask OBJECT-TYPE
    SYNTAX      IpAddress
    MAX-ACCESS  read-create
    STATUS      current
    DESCRIPTION
        "The peer mask key of the template."
    ::= { basPbrfRIPExportTemplateEntry 11 }

basPbrfRIPExportTemplateTag OBJECT-TYPE
    SYNTAX      Integer32
    MAX-ACCESS  read-create
    STATUS      current
    DESCRIPTION
        "The tag key of the template."
    ::= { basPbrfRIPExportTemplateEntry 12 }

basPbrfRIPExportTemplateKeyBits OBJECT-TYPE
    SYNTAX      Integer32
    MAX-ACCESS  read-create
    STATUS      current
    DESCRIPTION
        "The key bits key mask of the template."
    ::= { basPbrfRIPExportTemplateEntry 13 }

basPbrfRIPExportTemplateMetric OBJECT-TYPE
    SYNTAX      Integer32
    MAX-ACCESS  read-create
    STATUS      current
    DESCRIPTION
        "The metric of the template action."
    ::= { basPbrfRIPExportTemplateEntry 14 }

basPbrfRIPExportTemplateFlags OBJECT-TYPE
    SYNTAX      Integer32
    MAX-ACCESS  read-create
    STATUS      current
    DESCRIPTION
        "The flags of the template action."
    ::= { basPbrfRIPExportTemplateEntry 15 }

basPbrfRIPExportTemplateActionTag OBJECT-TYPE
    SYNTAX      Integer32
    MAX-ACCESS  read-create
    STATUS      current
    DESCRIPTION
        "The tag of the template action."
    ::= { basPbrfRIPExportTemplateEntry 16 }

basPbrfRIPExportTemplateRowStatus OBJECT-TYPE
    SYNTAX      RowStatus
    MAX-ACCESS  read-create
    STATUS      current
    DESCRIPTION
        "The row status of the template."
    ::= { basPbrfRIPExportTemplateEntry 17 }

basPbrfRIPExportTemplateDescr OBJECT-TYPE
    SYNTAX      OCTET STRING(SIZE(0..64))
    MAX-ACCESS  read-create
    STATUS      current
    DESCRIPTION
        "The descr of the RIP Export template."
    ::= { basPbrfRIPExportTemplateEntry 18 }

END
