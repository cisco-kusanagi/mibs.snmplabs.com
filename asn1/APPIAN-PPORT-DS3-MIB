APPIAN-PPORT-DS3-MIB DEFINITIONS ::= BEGIN

     IMPORTS
      acPport, AcSlotNumber, AcPortNumber,
      AcAdminStatus, AcOpStatus, AcNodeId        FROM APPIAN-SMI-MIB 

      acChassisCurrentTime, acChassisRingId      FROM APPIAN-CHASSIS-MIB

      MODULE-IDENTITY, OBJECT-TYPE,
      NOTIFICATION-TYPE                          FROM SNMPv2-SMI
      
      DisplayString, TimeStamp, TruthValue       FROM SNMPv2-TC
      
      PerfIntervalCount                          FROM PerfHist-TC-MIB;

     acDs3 MODULE-IDENTITY
         LAST-UPDATED   "0003190000Z"
         ORGANIZATION   "Appian Communications, Inc."
         CONTACT-INFO   "Brian Johnson"
         DESCRIPTION
         "The is the MIB module that describes DS3 interfaces and objects 
         for Appian Communications OSAP2k platforms.  The tables in
         this DS3 mib are NOT SHARED between OSAPs."

         ::= { acPport 5 }

     -- The Appian  DS3 Near End Group

     -- The Appian  DS3 Near End Group consists of three tables:
     --    DS3  Configuration
     --    DS3  Interval
     --    DS3  Day

     -- the Appian  DS3  Configuration Table

     acDs3ConfigTable OBJECT-TYPE
          SYNTAX  SEQUENCE OF AcDs3ConfigEntry
          MAX-ACCESS  not-accessible
          STATUS  current
          DESCRIPTION
          "The Appian  DS3 Configuration table.  This table is created
          by EMS/CLI."

          ::= { acDs3 1 }

     acDs3ConfigEntry OBJECT-TYPE
          SYNTAX  AcDs3ConfigEntry
          MAX-ACCESS  not-accessible
          STATUS  current
          DESCRIPTION
          "An entry in the Appian DS3 Configuration table."

          INDEX   { acDs3ConfigNodeId, acDs3ConfigSlot, acDs3ConfigPort }
          ::= { acDs3ConfigTable 1 }

     AcDs3ConfigEntry ::=
          SEQUENCE {
              acDs3ConfigNodeId                     AcNodeId,
              acDs3ConfigSlot                       AcSlotNumber,
              acDs3ConfigPort                       AcPortNumber,
              acDs3ConfigAdminStatus                AcAdminStatus,
              acDs3ConfigOpStatus                   AcOpStatus,
              acDs3ConfigType                       INTEGER,
              acDs3ConfigTimeElapsedInterval        INTEGER,
              acDs3ConfigValidIntervals             INTEGER,
              acDs3ConfigTimeElapsedDay             INTEGER,
              acDs3ConfigValidDays                  INTEGER,
              acDs3ConfigTimeElapsedFarEndInterval  INTEGER,
              acDs3ConfigValidFarEndIntervals       INTEGER,
              acDs3ConfigTimeElapsedFarEndDay       INTEGER,
              acDs3ConfigValidFarEndDays            INTEGER,
              acDs3ConfigLineType                   INTEGER,
              acDs3ConfigLineCoding                 INTEGER,
              acDs3ConfigSendCode                   INTEGER,
              acDs3ConfigCircuitIdentifier          DisplayString,
              acDs3ConfigLoopbackConfig             INTEGER,
              acDs3ConfigLineStatus                 INTEGER,
              acDs3ConfigTransmitClockSource        INTEGER,
              acDs3ConfigInvalidIntervals           INTEGER,
              acDs3ConfigInvalidDays                INTEGER,
              acDs3ConfigInvalidFarEndIntervals     INTEGER,
              acDs3ConfigInvalidFarEndDays          INTEGER,
              acDs3ConfigLineLength                 INTEGER,
              acDs3ConfigLineStatusLastChange       TimeStamp,
              acDs3ConfigLineStatusChangeTrapEnable INTEGER,
              acDs3ConfigLoopbackStatus             INTEGER,
              acDs3ConfigChannelization             INTEGER,
              acDs3ConfigDs1ForRemoteLoop           INTEGER,
              acDs3ConfigFarEndEquipCode            DisplayString,
              acDs3ConfigFarEndLocationIDCode       DisplayString,
              acDs3ConfigFarEndFrameIDCode          DisplayString,
              acDs3ConfigFarEndUnitCode             DisplayString,
              acDs3ConfigFarEndFacilityIDCode       DisplayString,
              acDs3ConfigInterfaceName              DisplayString
     }

     acDs3ConfigNodeId OBJECT-TYPE
          SYNTAX  AcNodeId
          MAX-ACCESS  accessible-for-notify
          STATUS  current
          DESCRIPTION
                 "The node id is the id for this specific node in the OSAP 
                 ring."
          ::= { acDs3ConfigEntry 1 }

     acDs3ConfigSlot OBJECT-TYPE
          SYNTAX  AcSlotNumber
          MAX-ACCESS  accessible-for-notify
          STATUS  current
          DESCRIPTION
                 "The physical slot number for the port."
          ::= { acDs3ConfigEntry 2 }

     acDs3ConfigPort OBJECT-TYPE
          SYNTAX  AcPortNumber
          MAX-ACCESS  accessible-for-notify
          STATUS  current
          DESCRIPTION
                 "The physical port number for the port."
          ::= { acDs3ConfigEntry 3 }
          
     acDs3ConfigAdminStatus OBJECT-TYPE
          SYNTAX AcAdminStatus
          MAX-ACCESS read-create
          STATUS    current
          DESCRIPTION
                 "Appian Administrative Status attribute used to set the 
                 provisioning state as either activate(1), inactivate(2) or 
                 delete(3).  Refer to the Appian-SMI.mib file for 
                 additional information."
          DEFVAL { inactivate }

          ::= { acDs3ConfigEntry 4 }

     acDs3ConfigOpStatus OBJECT-TYPE
          SYNTAX AcOpStatus
          MAX-ACCESS read-create
          STATUS    current
          DESCRIPTION
                 "The operational or actual state of this DS3."

          ::= { acDs3ConfigEntry 5 }

     acDs3ConfigType OBJECT-TYPE
          SYNTAX  INTEGER {
                     ds3Access(1),
                     ds3Network(2)
          }
          MAX-ACCESS  read-only
          STATUS  current
          DESCRIPTION
                 "The field defines the type of DS3 port that this instance
                 configures.  The type can be either Access or Network."
          ::= { acDs3ConfigEntry 6 }

     acDs3ConfigTimeElapsedInterval OBJECT-TYPE
          SYNTAX  INTEGER (0..899)
          MAX-ACCESS  read-only
          STATUS  current
          DESCRIPTION
                 "The number of seconds that have elapsed since the
                 beginning of the near end current error-
                 measurement period.  If, for some reason, such as
                 an adjustment in the system's time-of-day clock,
                 the current interval exceeds the maximum value,
                 the agent will return the maximum value."
          ::= { acDs3ConfigEntry 7 }

     acDs3ConfigValidIntervals OBJECT-TYPE
          SYNTAX  INTEGER (0..96)
          MAX-ACCESS  read-only
          STATUS  current
          DESCRIPTION
                 "The number of previous near end intervals for
                 which data was collected.  The value will be
                 96 unless the interface was brought online within
                 the last 24 hours, in which case the value will be
                 the number of complete 15 minute near end
                 intervals since the interface has been online.  In
                 the case where the agent is a proxy, it is
                 possible that some intervals are unavailable.  In
                 this case, this interval is the maximum interval
                 number for which data is available."
          ::= { acDs3ConfigEntry 8 }

     acDs3ConfigTimeElapsedDay OBJECT-TYPE
          SYNTAX  INTEGER (0..86399)
          MAX-ACCESS  read-only
          STATUS  current
          DESCRIPTION
                 "The number of seconds that have elapsed since the
                 beginning of the near end current day error-
                 measurement period.  If, for some reason, such as
                 an adjustment in the system's time-of-day clock,
                 the current interval exceeds the maximum value,
                 the agent will return the maximum value."

          ::= { acDs3ConfigEntry 9 }

     acDs3ConfigValidDays OBJECT-TYPE
          SYNTAX  INTEGER (0..30)
          MAX-ACCESS  read-only
          STATUS  current
          DESCRIPTION
                 "The number of previous near end intervals for
                 which data was collected.  The value will be
                 30 unless the interface was brought online within
                 the last 30 days, in which case the value will be
                 the number of complete 24 hour near end days
                 since the interface has been online.  In
                 the case where the agent is a proxy, it is
                 possible that some intervals are unavailable.  In
                 this case, this interval is the maximum interval
                 number for which data is available."
          ::= { acDs3ConfigEntry 10 }

     acDs3ConfigTimeElapsedFarEndInterval OBJECT-TYPE
          SYNTAX  INTEGER (0..899)
          MAX-ACCESS  read-only
          STATUS  current
          DESCRIPTION
                 "The number of seconds that have elapsed since the
                 beginning of the far end current error-measurement
                 period.  If, for some reason, such as an
                 adjustment in the system's time-of-day clock, the
                 current interval exceeds the maximum value, the
                 agent will return the maximum value."
          ::= { acDs3ConfigEntry 11 }

     acDs3ConfigValidFarEndIntervals OBJECT-TYPE
          SYNTAX  INTEGER (0..96)
          MAX-ACCESS  read-only
          STATUS  current
          DESCRIPTION
                 "The number of previous far end intervals for
                 which data was collected.  The value will be
                 96 unless the interface was brought online within
                 the last 24 hours, in which case the value will be
                 the number of complete 15 minute far end intervals
                 since the interface has been online."
          ::= { acDs3ConfigEntry 12 }

     acDs3ConfigTimeElapsedFarEndDay OBJECT-TYPE
          SYNTAX  INTEGER (0..86399)
          MAX-ACCESS  read-only
          STATUS  current
          DESCRIPTION
                 "The number of seconds that have elapsed since the
                 beginning of the far end current day error-
                 measurement period.  If, for some reason, such as
                 an adjustment in the system's time-of-day clock,
                 the current day exceeds the maximum value,
                 the agent will return the maximum value."

          ::= { acDs3ConfigEntry 13 }

     acDs3ConfigValidFarEndDays OBJECT-TYPE
          SYNTAX  INTEGER (0..30)
          MAX-ACCESS  read-only
          STATUS  current
          DESCRIPTION
                 "The number of previous far end days for
                 which data was collected.  The value will be
                 30 unless the interface was brought online within
                 the last 30 days, in which case the value will be
                 the number of complete 24 hour far end days
                 since the interface has been online.  In
                 the case where the agent is a proxy, it is
                 possible that some intervals are unavailable.  In
                 this case, this interval is the maximum interval
                 number for which data is available."
          ::= { acDs3ConfigEntry 14 }

     acDs3ConfigLineType OBJECT-TYPE
          SYNTAX  INTEGER {
                     ds3other(1),
                     ds3M23(2),
                     ds3SYNTRAN(3),
                     ds3CbitParity(4),
                     ds3ClearChannel(5)
                 }
          MAX-ACCESS  read-create
          STATUS  current
          DESCRIPTION
                 "This variable indicates the variety of DS3 C-bit
                 application implementing this interface. The
                 type of interface affects the interpretation of
                 the usage and error statistics.  The rate of DS3
                 is 44.736 Mbps.  The ds3ClearChannel value means 
                 that the C-bits are not used except for sending/
                 receiving AIS.  The values, in sequence, describe:

                 TITLE:            SPECIFICATION:
                 ds3M23            ANSI T1.107-1988 [9]
                 ds3SYNTRAN        ANSI T1.107-1988 [9]
                 ds3CbitParity     ANSI T1.107a-1990 [9a]
                 ds3ClearChannel   ANSI T1.102-1987 [8] "
          DEFVAL { ds3CbitParity }
          ::= { acDs3ConfigEntry 15 }

    acDs3ConfigLineCoding OBJECT-TYPE
          SYNTAX  INTEGER {
                     ds3Other(1),
                     ds3B3ZS(2),
                     e3HDB3(3)
                 }
          MAX-ACCESS  read-create
          STATUS  current
          DESCRIPTION
                 "This variable describes the variety of Zero Code
                 Suppression used on this interface, which in turn
                 affects a number of its characteristics.

                 ds3B3ZS and e3HDB3 refer to the use of specified
                 patterns of normal bits and bipolar violations
                 which are used to replace sequences of zero bits
                 of a specified length."
          DEFVAL { ds3B3ZS }
          ::= { acDs3ConfigEntry 16 }

     acDs3ConfigSendCode OBJECT-TYPE
          SYNTAX  INTEGER {
                    ds3SendNoCode(1),
                    ds3SendLineCode(2),
                    ds3SendPayloadCode(3),
                    ds3SendResetCode(4),
                    ds3SendTestPattern(5)
                    }
          MAX-ACCESS  read-create
          STATUS  current
          DESCRIPTION
                 "This variable indicates what type of code is being sent 
                 across the DS3 interface by the device. Setting this 
                 variable causes the interface to begin sending the code 
                 requested.
                 The values mean:

                    ds3SendNoCode
                       sending looped or normal data

                    ds3SendLineCode
                       sending a request for a line loopback

                    ds3SendPayloadCode
                       sending a request for a payload loopback
                       (i.e., all DS1/E1s in a DS3 frame)

                    ds3SendResetCode
                       sending a loopback deactivation request

                    ds3SendTestPattern
                       sending a test pattern."
          DEFVAL { ds3SendNoCode }
          ::= { acDs3ConfigEntry 17 }

     acDs3ConfigCircuitIdentifier OBJECT-TYPE
          SYNTAX  DisplayString (SIZE (0..255))
          MAX-ACCESS  read-create
          STATUS  current
          DESCRIPTION
                 "This variable contains the transmission vendor's
                 circuit identifier, for the purpose of
                 facilitating troubleshooting."
          DEFVAL { "" }
          ::= { acDs3ConfigEntry 18 }

     acDs3ConfigLoopbackConfig OBJECT-TYPE
          SYNTAX  INTEGER {
                      ds3NoLoop(1),
                      ds3PayloadLoop(2),
                      ds3LineLoop(3),
                      ds3OtherLoop(4),
                      ds3InwardLoop(5)
                    }
          MAX-ACCESS  read-create
          STATUS  current
          DESCRIPTION
               "This variable represents the desired loopback
               configuration of the DS3 interface.

               The values mean:

               ds3NoLoop
                 Not in the loopback state.  A device that is
                 not capable of performing a loopback on
                 the interface shall always return this as
                 its value.

               ds3PayloadLoop
                 The received signal at this interface is looped
                 through the device.  Typically the received signal
                 is looped back for retransmission after it has
                 passed through the device's framing function.

               ds3LineLoop
                 The received signal at this interface does not
                 go through the device (minimum penetration) but
                 is looped back out.

               ds3OtherLoop
                 Loopbacks that are not defined here.

               ds3InwardLoop
                 The sent signal at this interface is looped back
                 through the device."

          DEFVAL { ds3NoLoop }
          ::= { acDs3ConfigEntry 19 }

     acDs3ConfigLineStatus OBJECT-TYPE
          SYNTAX  INTEGER (1..4095)
          MAX-ACCESS  read-only
          STATUS  current
          DESCRIPTION
                 "This variable indicates the Line Status of the
                 interface.  It contains loopback state information
                 and failure state information.  The ds3LineStatus
                 is a bit map represented as a sum, therefore, it
                 can represent multiple failures and a loopback
                 (see acDs3LoopbackConfig object for the type of
                 loopback) simultaneously.  The ds3NoAlarm must be
                 set if and only if no other flag is set.

                 If the ds3loopbackState bit is set, the loopback
                 in effect can be determined from the
                 ds3loopbackConfig object.
       The various bit positions are:
        1     ds3NoAlarm         No alarm present
        2     ds3RcvRAIFailure   Receiving Yellow/Remote
                                 Alarm Indication
        4     ds3XmitRAIAlarm    Transmitting Yellow/Remote
                                 Alarm Indication
        8     ds3RcvAIS          Receiving AIS failure state
       16     ds3XmitAIS         Transmitting AIS
       32     ds3LOF             Receiving LOF failure state
       64     ds3LOS             Receiving LOS failure state
      128     ds3LoopbackState   Looping the received signal
      256     ds3RcvTestCode     Receiving a Test Pattern
      512     ds3OtherFailure    any line status not defined
                                 here
     1024     ds3UnavailSigState Near End in Unavailable Signal
                                 State
     2048     ds3NetEquipOOS     Carrier Equipment Out of Service"
     ::= { acDs3ConfigEntry 20 }

    acDs3ConfigTransmitClockSource OBJECT-TYPE
    SYNTAX  INTEGER {
                loopTiming(1),
                localTiming(2),
                throughTiming(3)
            }
     MAX-ACCESS  read-create
     STATUS  current
     DESCRIPTION
            "The source of Transmit Clock.

            loopTiming indicates that the recovered receive clock
            is used as the transmit clock.

            localTiming indicates that a local clock source is used
            or that an external clock is attached to the box
            containing the interface.

            throughTiming indicates that transmit clock is derived
            from the recovered receive clock of another DS3
            interface."
          DEFVAL {localTiming}
          ::= { acDs3ConfigEntry 21 }

     acDs3ConfigInvalidIntervals OBJECT-TYPE
          SYNTAX  INTEGER (0..96)
          MAX-ACCESS  read-only
          STATUS  current
          DESCRIPTION
                 "The number of intervals in the range from 0 to
                 acDs3ConfigValidIntervals for which no data is
                 available.  This object will typically be zero
                 except in cases where the data for some intervals
                 are not available (e.g., in proxy situations)."
          ::= { acDs3ConfigEntry 22 }

     acDs3ConfigInvalidDays OBJECT-TYPE
          SYNTAX  INTEGER (0..30)
          MAX-ACCESS  read-only
          STATUS  current
          DESCRIPTION
                 "The number of days in the range from 0 to
                 acDs3ConfigValidDays for which no data is
                 available.  This object will typically be zero
                 except in cases where the data for some intervals
                 are not available (e.g., in proxy situations)."
          ::= { acDs3ConfigEntry 23 }

     acDs3ConfigInvalidFarEndIntervals OBJECT-TYPE
          SYNTAX  INTEGER (0..96)
          MAX-ACCESS  read-only
          STATUS  current
          DESCRIPTION
                      "The number of intervals in the range from 0 to
                 acDs3ConfigValidFarEndIntervals for which no data is
                 available.  This object will typically be zero
                 except in cases where the data for some intervals
                 are not available (e.g., in proxy situations)."
          ::= { acDs3ConfigEntry 24 }

     acDs3ConfigInvalidFarEndDays OBJECT-TYPE
          SYNTAX  INTEGER (0..30)
          MAX-ACCESS  read-only
          STATUS  current
          DESCRIPTION
                 "The number of days in the range from 0 to
                 acDs3ConfigValidFarEndDays for which no data is
                 available.  This object will typically be zero
                 except in cases where the data for some intervals
                 are not available (e.g., in proxy situations)."
          ::= { acDs3ConfigEntry 25 }

     acDs3ConfigLineLength OBJECT-TYPE
          SYNTAX  INTEGER (0..64000)
          UNITS "meters"
          MAX-ACCESS  read-create
          STATUS  current
          DESCRIPTION
                 "The length of the ds3 line in meters.  This
                 object provides information for line build out
                 circuitry if it exists and can use this object to
                 adjust the line build out."
          DEFVAL { 0 }
          ::= { acDs3ConfigEntry 26 }

     acDs3ConfigLineStatusLastChange OBJECT-TYPE
          SYNTAX  TimeStamp
          MAX-ACCESS  read-only
          STATUS  current
          DESCRIPTION
                 "The value of MIB II's sysUpTime object at the
                 time this DS3 entered its current line status
                 state.  If the current state was entered prior to
                 the last re-initialization of the proxy-agent,
                 then this object contains a zero value."

          ::= { acDs3ConfigEntry 27 }

     acDs3ConfigLineStatusChangeTrapEnable  OBJECT-TYPE
          SYNTAX      INTEGER {
                         enabled(1),
                         disabled(2)
                      }
          MAX-ACCESS  read-create
          STATUS      current
          DESCRIPTION
                 "Indicates whether acDs3ConfigLineStatusChange traps
                 should be generated for this interface."
          DEFVAL { disabled }
          ::= { acDs3ConfigEntry 28 }

     acDs3ConfigLoopbackStatus  OBJECT-TYPE
          SYNTAX      INTEGER (1..127)
          MAX-ACCESS  read-only
          STATUS      current
          DESCRIPTION
                 "This variable represents the current state of the
                 loopback on the DS3 interface.  It contains
                 information about loopbacks established by a
                 manager and remotely from the far end.

                 The acDs3ConfigLoopbackStatus is a bit map represented as
                 a sum, therefore is can represent multiple
                 loopbacks simultaneously.

                 The various bit positions are:
                  1  ds3NoLoopback
                  2  ds3NearEndPayloadLoopback
                  4  ds3NearEndLineLoopback
                  8  ds3NearEndOtherLoopback
                 16  ds3NearEndInwardLoopback
                 32  ds3FarEndPayloadLoopback
                 64  ds3FarEndLineLoopback"
          DEFVAL { 1 }
     ::= { acDs3ConfigEntry 29 }

     acDs3ConfigChannelization  OBJECT-TYPE
          SYNTAX      INTEGER {
                         disabled(1),
                         enabledDs1(2),
                         enabledDs2(3)
                      }
          MAX-ACCESS  read-create
          STATUS      current
          DESCRIPTION
                 "Indicates whether this ds3/e3 is channelized or
                 unchannelized.  The value of enabledDs1 indicates
                 that this is a DS3 channelized into DS1s.  The
                 value of enabledDs3 indicated that this is a DS3
                 channelized into DS2s.  "
          DEFVAL { disabled }
     ::= { acDs3ConfigEntry 30 }

     acDs3ConfigDs1ForRemoteLoop  OBJECT-TYPE
          SYNTAX      INTEGER (0..29)

          MAX-ACCESS  read-create
          STATUS      current
          DESCRIPTION
                 "Indicates which ds1/e1 on this ds3/e3 will be
                 indicated in the remote ds1 loopback request.  A
                 value of 0 means no DS1 will be looped.  A value
                 of 29 means all ds1s/e1s will be looped."
     ::= { acDs3ConfigEntry 31 }

     acDs3ConfigFarEndEquipCode OBJECT-TYPE
          SYNTAX  DisplayString (SIZE (0..10))
          MAX-ACCESS  read-only
          STATUS  current
          DESCRIPTION
                 "This is the Far End Equipment Identification code
                 that describes the specific piece of equipment.
                 It is sent within the Path Identification
                 Message (C-bits) from the remote end."
          ::= { acDs3ConfigEntry 32 }

     acDs3ConfigFarEndLocationIDCode OBJECT-TYPE
          SYNTAX  DisplayString (SIZE (0..11))
          MAX-ACCESS  read-only
          STATUS  current
          DESCRIPTION
                 "This is the Far End Location Identification code
                 that describes the specific location of the
                 equipment.  It is sent within the Path
                 Identification Message (C-bits) from the remote end."
          ::= { acDs3ConfigEntry 33 }

     acDs3ConfigFarEndFrameIDCode OBJECT-TYPE
          SYNTAX  DisplayString (SIZE (0..10))
          MAX-ACCESS  read-only
          STATUS  current
          DESCRIPTION
                 "This is the Far End Frame Identification code
                 that identifies where the equipment is located
                 within a building at a given location.  It is sent
                 within the Path Identification Message (C-bits) from 
                 the remote end."
          ::= { acDs3ConfigEntry 34 }

     acDs3ConfigFarEndUnitCode OBJECT-TYPE
          SYNTAX  DisplayString (SIZE (0..6))
          MAX-ACCESS  read-only
          STATUS  current
          DESCRIPTION
                 "This is the Far End code that identifies the
                 equipment location within a bay.  It is sent
                 within the Path Identification Message (C-bits) from 
                 the remote end."
          ::= { acDs3ConfigEntry 35 }

     acDs3ConfigFarEndFacilityIDCode OBJECT-TYPE
          SYNTAX  DisplayString (SIZE (0..38))
          MAX-ACCESS  read-only
          STATUS  current
          DESCRIPTION
                 "This code identifies a specific Far End DS3 path.
                 It is sent within the Path Identification
                 Message (C-bits) from the remote end."
          ::= { acDs3ConfigEntry 36 }


     acDs3ConfigInterfaceName OBJECT-TYPE
          SYNTAX  DisplayString (SIZE (0..64))
          MAX-ACCESS  read-create
          STATUS  current
          DESCRIPTION
                 "A user configurable interface name which uniquely 
                 identifies this physical interface.  The name can be
                 up to 64 bytes in length."
                 
          DEFVAL { "DS-3/TDM Interface" }
                           
          ::= { acDs3ConfigEntry 37 }


     -- the Appian  DS3 Interval Table

     acDs3IntervalTable OBJECT-TYPE
          SYNTAX  SEQUENCE OF AcDs3IntervalEntry
          MAX-ACCESS  not-accessible
          STATUS  current
          DESCRIPTION
                 "The Appian  DS3 Interval Table contains various
                 statistics collected by the DS3 Interface over
                 the previous 24 hours of operation as well as over
                 the current period.  The past 24 hours are broken 
                 into 96 completed 15 minute intervals.  The first
                 row in this table (identified by acDs3IntervalNumber=1)
                 represents the current interval statistics.  The next 96
                 rows of this table (represented by acDs3IntervalNubmer=2..97)
                 represents one of the past 15 minute intervals.  The final
                 row (identified by acDs3IntervalNumber=98) is the total of
                 all the past intervals (2..97).  This table is created
                 automatically."
          ::= { acDs3 2 }

     acDs3IntervalEntry OBJECT-TYPE
          SYNTAX  AcDs3IntervalEntry
          MAX-ACCESS  not-accessible
          STATUS  current
          DESCRIPTION
                 "An entry in the Appian  DS3 Interval table."
          INDEX   { acDs3IntervalNodeId,
                    acDs3IntervalSlot,
                    acDs3IntervalPort,
                    acDs3IntervalNumber }
          ::= { acDs3IntervalTable 1 }

     AcDs3IntervalEntry ::=
          SEQUENCE {
              acDs3IntervalNodeId          AcNodeId,
              acDs3IntervalSlot            AcSlotNumber,
              acDs3IntervalPort            AcPortNumber,
              acDs3IntervalNumber          INTEGER,
              acDs3IntervalValidStats      TruthValue,
              acDs3IntervalResetStats      TruthValue,
              acDs3IntervalPESs            PerfIntervalCount,
              acDs3IntervalPSESs           PerfIntervalCount,
              acDs3IntervalSEFSs           PerfIntervalCount,
              acDs3IntervalUASs            PerfIntervalCount,
              acDs3IntervalLCVs            PerfIntervalCount,
              acDs3IntervalPCVs            PerfIntervalCount,
              acDs3IntervalLESs            PerfIntervalCount,
              acDs3IntervalCCVs            PerfIntervalCount,
              acDs3IntervalCESs            PerfIntervalCount,
              acDs3IntervalCSESs           PerfIntervalCount
          }


     acDs3IntervalNodeId OBJECT-TYPE
          SYNTAX  AcNodeId
          MAX-ACCESS  accessible-for-notify
          STATUS  current
          DESCRIPTION
                 "The node id is the id for this specific node in the OSAP 
                 ring."
          ::= { acDs3IntervalEntry 1 }

     acDs3IntervalSlot OBJECT-TYPE
          SYNTAX  AcSlotNumber
          MAX-ACCESS  accessible-for-notify
          STATUS  current
          DESCRIPTION
                 "The physical slot number for the port."
          ::= { acDs3IntervalEntry 2 }

     acDs3IntervalPort OBJECT-TYPE
          SYNTAX  AcPortNumber
          MAX-ACCESS  accessible-for-notify
          STATUS  current
          DESCRIPTION
                 "The physical port number for the port."
          ::= { acDs3IntervalEntry 3 }

     acDs3IntervalNumber OBJECT-TYPE
          SYNTAX  INTEGER (1..98)
          MAX-ACCESS  accessible-for-notify
          STATUS  current
          DESCRIPTION
                 "A number between 1 and 98, where 1 is the current
                 15 minute interval in progress, 2 is the most
                 recently completed 15 minute interval and 97 is
                 the 15 minutes interval completed 23 hours and 45
                 minutes prior to interval 2, and 98 is the total of
                 all the completed intervals (2..97)."
          ::= { acDs3IntervalEntry 4 }

     acDs3IntervalValidStats OBJECT-TYPE
          SYNTAX  TruthValue
          MAX-ACCESS read-only
          STATUS current
          DESCRIPTION
                 "This variable indicates if the data for this
                 interval is valid."
          ::= { acDs3IntervalEntry 5 }

     acDs3IntervalResetStats OBJECT-TYPE
          SYNTAX  TruthValue
          MAX-ACCESS read-write
          STATUS current
          DESCRIPTION
                 "This variable allows the data from the current 
                 interval (acDs3IntervalIndex=1) to be reset.  
                 The acDs3IntervalValidFlag will be set to False
                 after the reset for the current interval.  This 
                 field has no effect on acDs3IntervalIndex=2..98.
                 This field will always show a value of False when
                 read."
          ::= { acDs3IntervalEntry 6 }


     acDs3IntervalPESs OBJECT-TYPE
          SYNTAX  PerfIntervalCount
          MAX-ACCESS  read-only
          STATUS  current
          DESCRIPTION
                 "The counter associated with the number of P-bit
                 Errored Seconds."
          ::= { acDs3IntervalEntry 7 }

     acDs3IntervalPSESs OBJECT-TYPE
          SYNTAX  PerfIntervalCount
          MAX-ACCESS  read-only
          STATUS  current
          DESCRIPTION
                 "The counter associated with the number of P-bit
                 Severely Errored Seconds."
          ::= { acDs3IntervalEntry 8 }

     acDs3IntervalSEFSs OBJECT-TYPE
          SYNTAX  PerfIntervalCount
          MAX-ACCESS  read-only
          STATUS  current
          DESCRIPTION
                 "The counter associated with the number of
                 Severely Errored Framing Seconds."
          ::= { acDs3IntervalEntry 9 }

     acDs3IntervalUASs OBJECT-TYPE
          SYNTAX  PerfIntervalCount
          MAX-ACCESS  read-only
          STATUS  current
          DESCRIPTION
                 "The counter associated with the number of
                 Unavailable Seconds.  This object may decrease if
                 the occurance of unavailable seconds occurs across
                 an inteval boundary."
          ::= { acDs3IntervalEntry 10 }

     acDs3IntervalLCVs OBJECT-TYPE
          SYNTAX  PerfIntervalCount
          MAX-ACCESS  read-only
          STATUS  current
          DESCRIPTION
                 "The counter associated with the number of Line
                 Coding Violations."
          ::= { acDs3IntervalEntry 11 }

     acDs3IntervalPCVs OBJECT-TYPE
          SYNTAX  PerfIntervalCount
          MAX-ACCESS  read-only
          STATUS  current
          DESCRIPTION
                 "The counter associated with the number of P-bit
                 Coding Violations."
          ::= { acDs3IntervalEntry 12 }

     acDs3IntervalLESs OBJECT-TYPE
          SYNTAX  PerfIntervalCount
          MAX-ACCESS  read-only
          STATUS  current
          DESCRIPTION
                 "The number of Line Errored  Seconds  (BPVs  or
                 illegal  zero  sequences)."
          ::= { acDs3IntervalEntry 13 }

     acDs3IntervalCCVs OBJECT-TYPE
          SYNTAX  PerfIntervalCount
          MAX-ACCESS  read-only
          STATUS  current
          DESCRIPTION
                 "The number of C-bit Coding Violations."
          ::= { acDs3IntervalEntry 14 }

     acDs3IntervalCESs OBJECT-TYPE
          SYNTAX  PerfIntervalCount
          MAX-ACCESS  read-only
          STATUS  current
          DESCRIPTION
                 "The number of C-bit Errored Seconds."
          ::= { acDs3IntervalEntry 15 }

     acDs3IntervalCSESs OBJECT-TYPE
          SYNTAX  PerfIntervalCount
          MAX-ACCESS  read-only
          STATUS  current
          DESCRIPTION
                 "The number of C-bit Severely Errored Seconds."
          ::= { acDs3IntervalEntry 16 }

     -- the Appian  DS3 Day Table

     acDs3DayTable OBJECT-TYPE
          SYNTAX  SEQUENCE OF AcDs3DayEntry
          MAX-ACCESS  not-accessible
          STATUS  current
          DESCRIPTION
                 "The Appian  DS3 Day Table contains various
                 statistics collected by the DS3 Interface over
                 the previous 30 days of operation as well as over
                 the current day period. The first row in this table 
                 (identified by acDs3DayNumber=1) represents the current 
                 day statistics.  The next 30 rows of this table 
                 (represented by acDs3DayNubmer=2..31) represents 
                 one of the 24 hour day intervals.  This table is created
                 automatically."
          ::= { acDs3 3 }

     acDs3DayEntry OBJECT-TYPE
          SYNTAX  AcDs3DayEntry
          MAX-ACCESS  not-accessible
          STATUS  current
          DESCRIPTION
                 "An entry in the Appian  DS3 Day table."
          INDEX   { acDs3DayNodeId, 
                    acDs3DaySlot, 
                    acDs3DayPort,
                    acDs3DayNumber }
          ::= { acDs3DayTable 1 }

     AcDs3DayEntry ::=
          SEQUENCE {
              acDs3DayNodeId          AcNodeId,
              acDs3DaySlot            AcSlotNumber,
              acDs3DayPort            AcPortNumber,
              acDs3DayNumber          INTEGER,
              acDs3DayValidStats      TruthValue,
              acDs3DayResetStats      TruthValue,
              acDs3DayPESs            PerfIntervalCount,
              acDs3DayPSESs           PerfIntervalCount,
              acDs3DaySEFSs           PerfIntervalCount,
              acDs3DayUASs            PerfIntervalCount,
              acDs3DayLCVs            PerfIntervalCount,
              acDs3DayPCVs            PerfIntervalCount,
              acDs3DayLESs            PerfIntervalCount,
              acDs3DayCCVs            PerfIntervalCount,
              acDs3DayCESs            PerfIntervalCount,
              acDs3DayCSESs           PerfIntervalCount
          }


     acDs3DayNodeId OBJECT-TYPE
          SYNTAX  AcNodeId
          MAX-ACCESS accessible-for-notify
          STATUS  current
          DESCRIPTION
                 "The node id is the id for this specific node in the OSAP 
                 ring."
          ::= { acDs3DayEntry 1 }

     acDs3DaySlot OBJECT-TYPE
          SYNTAX  AcSlotNumber
          MAX-ACCESS  accessible-for-notify
          STATUS  current
          DESCRIPTION
                 "The physical slot number for the port."
          ::= { acDs3DayEntry 2 }

     acDs3DayPort OBJECT-TYPE
          SYNTAX  AcPortNumber
          MAX-ACCESS  accessible-for-notify
          STATUS  current
          DESCRIPTION
                 "The physical port number for the port."
          ::= { acDs3DayEntry 3 }

     acDs3DayNumber OBJECT-TYPE
          SYNTAX  INTEGER (1..31)
          MAX-ACCESS  accessible-for-notify
          STATUS  current
          DESCRIPTION
                 "A number between 1 and 31, where 1 is the current
                 24 hour day interval in progress, 2 is the most
                 recently completed 24 hour day interval and 31 is
                 the 24 hour day interval completed 29 days prior to
                 interval 2."
          ::= { acDs3DayEntry 4 }

     acDs3DayValidStats OBJECT-TYPE
          SYNTAX  TruthValue
          MAX-ACCESS read-only
          STATUS current
          DESCRIPTION
                 "This variable indicates if the data for this
                 interval is valid."
          ::= { acDs3DayEntry 5 }

     acDs3DayResetStats OBJECT-TYPE
          SYNTAX  TruthValue
          MAX-ACCESS read-write
          STATUS current
          DESCRIPTION
                 "This variable allows the data from the day 
                 (acDs3DayIndex=1) to be reset.  The acDs3DayValidFlag
                 will be set to False after the reset for the current 
                 day.  This field has no effect on acDs3DayIndex=2..31.
                 This field will always show a value of False when read."
          ::= { acDs3DayEntry 6 }

     acDs3DayPESs OBJECT-TYPE
          SYNTAX  PerfIntervalCount
          MAX-ACCESS  read-only
          STATUS  current
          DESCRIPTION
                 "The counter associated with the number of P-bit
                 Errored Seconds."
          ::= { acDs3DayEntry 7 }

     acDs3DayPSESs OBJECT-TYPE
          SYNTAX  PerfIntervalCount
          MAX-ACCESS  read-only
          STATUS  current
          DESCRIPTION
                 "The counter associated with the number of P-bit
                 Severely Errored Seconds."
          ::= { acDs3DayEntry 8 }

     acDs3DaySEFSs OBJECT-TYPE
          SYNTAX  PerfIntervalCount
          MAX-ACCESS  read-only
          STATUS  current
          DESCRIPTION
                 "The counter associated with the number of
                 Severely Errored Framing Seconds."
          ::= { acDs3DayEntry 9 }

     acDs3DayUASs OBJECT-TYPE
          SYNTAX  PerfIntervalCount
          MAX-ACCESS  read-only
          STATUS  current
          DESCRIPTION
                 "The counter associated with the number of
                 Unavailable Seconds.  This object may decrease if
                 the occurance of unavailable seconds occurs across
                 an inteval boundary."
          ::= { acDs3DayEntry 10 }

     acDs3DayLCVs OBJECT-TYPE
          SYNTAX  PerfIntervalCount
          MAX-ACCESS  read-only
          STATUS  current
          DESCRIPTION
                 "The counter associated with the number of Line
                 Coding Violations."
          ::= { acDs3DayEntry 11 }

     acDs3DayPCVs OBJECT-TYPE
          SYNTAX  PerfIntervalCount
          MAX-ACCESS  read-only
          STATUS  current
          DESCRIPTION
                 "The counter associated with the number of P-bit
                 Coding Violations."
          ::= { acDs3DayEntry 12 }

     acDs3DayLESs OBJECT-TYPE
          SYNTAX  PerfIntervalCount
          MAX-ACCESS  read-only
          STATUS  current
          DESCRIPTION
                 "The number of Line Errored  Seconds  (BPVs  or
                 illegal  zero  sequences)."
          ::= { acDs3DayEntry 13 }

     acDs3DayCCVs OBJECT-TYPE
          SYNTAX  PerfIntervalCount
          MAX-ACCESS  read-only
          STATUS  current
          DESCRIPTION
                 "The number of C-bit Coding Violations."
          ::= { acDs3DayEntry 14 }

     acDs3DayCESs OBJECT-TYPE
          SYNTAX  PerfIntervalCount
          MAX-ACCESS  read-only
          STATUS  current
          DESCRIPTION
                 "The number of C-bit Errored Seconds."
          ::= { acDs3DayEntry 15 }

     acDs3DayCSESs OBJECT-TYPE
          SYNTAX  PerfIntervalCount
          MAX-ACCESS  read-only
          STATUS  current
          DESCRIPTION
                 "The number of C-bit Severely Errored Seconds."
          ::= { acDs3DayEntry 16 }


     -- The Appian  DS3 Far End Group

     -- The DS3 Far End Group consists of one table:
     --   DS3 Far End Interval

     -- The Appian  DS3 Far End Interval Table

     acDs3FarEndIntervalTable OBJECT-TYPE
          SYNTAX  SEQUENCE OF AcDs3FarEndIntervalEntry
          MAX-ACCESS  not-accessible
          STATUS  current
          DESCRIPTION
                "The Appian  DS3 Far End Interval Table contains various
                statistics collected by each DS3 Interface over
                the previous 24 hours of operation as well as over
                the current period.  The past 24 hours are broken
                into 96 completed 15 minute intervals.  The first
                row in this table (identified by
                acDs3FarEndIntervalNumber=1) represents the current
                interval statistics.  The next 96 rows in this table
                (represented by acDs3FarEndIntervalNumber=2..97) represents
                one of the past 15 minute intervals. The final row
                (identified by acDs3FarEndIntervalNumber=98) is the total of
                all the past intervals (2..97).  This table is created
                 automatically."
          ::= { acDs3 4 }

     acDs3FarEndIntervalEntry OBJECT-TYPE
          SYNTAX  AcDs3FarEndIntervalEntry
          MAX-ACCESS  not-accessible
          STATUS  current
          DESCRIPTION
                 "An entry in the DS3 Far End Interval table."
          INDEX   { acDs3FarEndIntervalNodeId,
                    acDs3FarEndIntervalSlot,
                    acDs3FarEndIntervalPort,
                    acDs3FarEndIntervalNumber }
          ::= { acDs3FarEndIntervalTable 1 }

     AcDs3FarEndIntervalEntry ::=
          SEQUENCE {
               acDs3FarEndIntervalNodeId     AcNodeId,
               acDs3FarEndIntervalSlot       AcSlotNumber,
               acDs3FarEndIntervalPort       AcPortNumber,
               acDs3FarEndIntervalNumber     INTEGER,
               acDs3FarEndIntervalValidStats TruthValue,
               acDs3FarEndIntervalResetStats TruthValue,
               acDs3FarEndIntervalCESs       PerfIntervalCount,
               acDs3FarEndIntervalCSESs      PerfIntervalCount,
               acDs3FarEndIntervalCCVs       PerfIntervalCount,
               acDs3FarEndIntervalUASs       PerfIntervalCount
         }

     acDs3FarEndIntervalNodeId OBJECT-TYPE
          SYNTAX  AcNodeId
          MAX-ACCESS  accessible-for-notify
          STATUS  current
          DESCRIPTION
                 "The node id is the id for this specific node in the OSAP 
                 ring."
          ::= { acDs3FarEndIntervalEntry 1 }

     acDs3FarEndIntervalSlot OBJECT-TYPE
          SYNTAX  AcSlotNumber
          MAX-ACCESS  accessible-for-notify
          STATUS  current
          DESCRIPTION
                 "The physical slot number for the port."
          ::= { acDs3FarEndIntervalEntry 2 }

     acDs3FarEndIntervalPort OBJECT-TYPE
          SYNTAX  AcPortNumber
          MAX-ACCESS  accessible-for-notify
          STATUS  current
          DESCRIPTION
                 "The physical port number for the port."
          ::= { acDs3FarEndIntervalEntry 3 }

     acDs3FarEndIntervalNumber OBJECT-TYPE
         SYNTAX  INTEGER (1..98)
         MAX-ACCESS  accessible-for-notify
         STATUS  current
         DESCRIPTION
                 "A number between 1 and 96, where 1 is the current
                 15 minute interval in progress, 2 is the most 
                 recently completed 15 minute interval and 97 is
                 the 15 minutes interval completed 23 hours and 45
                 minutes prior to interval 2, and 98 is the total of
                 all completed intervals (2..97)."
         ::= { acDs3FarEndIntervalEntry 4 }

     acDs3FarEndIntervalValidStats OBJECT-TYPE
          SYNTAX  TruthValue
          MAX-ACCESS  read-only
          STATUS  current
          DESCRIPTION
                 "This variable indicates if the data for this
                 interval is valid."
          ::= { acDs3FarEndIntervalEntry 5 }

     acDs3FarEndIntervalResetStats OBJECT-TYPE
          SYNTAX  TruthValue
          MAX-ACCESS  read-write
          STATUS  current
          DESCRIPTION
                 "This variable allows the data for the current
                 interval (acDs3FarEndIntervalIndex=1) to be reset.
                 The acSdx3FarEndIntervalValidFlag will be set to False
                 after the reset for the current interval.  This 
                 field has no effect on acDs3FarEndIntervalIndex 2..98.
                 This field will always show a vluae of false when read."
          ::= { acDs3FarEndIntervalEntry 6 }

     acDs3FarEndIntervalCESs OBJECT-TYPE
         SYNTAX  PerfIntervalCount
         MAX-ACCESS  read-only
         STATUS  current
         DESCRIPTION
                 "The counter associated with the number of Far End
                 C-bit Errored Seconds encountered by a DS3
                 interface. In the case where the agent is
                 a proxy and data is not available, return
                 noSuchInstance."
        ::= { acDs3FarEndIntervalEntry 7 }

     acDs3FarEndIntervalCSESs OBJECT-TYPE
         SYNTAX  PerfIntervalCount
         MAX-ACCESS  read-only
         STATUS  current
         DESCRIPTION
                 "The counter associated with the number of Far End
                 C-bit Severely Errored Seconds."
        ::= { acDs3FarEndIntervalEntry 8 }

     acDs3FarEndIntervalCCVs OBJECT-TYPE
          SYNTAX  PerfIntervalCount
          MAX-ACCESS  read-only
          STATUS  current
          DESCRIPTION
                 "The counter associated with the number of Far End
                 C-bit Coding Violations reported via the far end
                 block error count."
          ::= { acDs3FarEndIntervalEntry 9 }

     acDs3FarEndIntervalUASs OBJECT-TYPE
          SYNTAX  PerfIntervalCount
          MAX-ACCESS  read-only
          STATUS  current
          DESCRIPTION
                 "The counter associated with the number of Far End
                 unavailable seconds."
          ::= { acDs3FarEndIntervalEntry 10 }


     -- The Appian  DS3 Far End Day Table

     acDs3FarEndDayTable OBJECT-TYPE
          SYNTAX  SEQUENCE OF AcDs3FarEndDayEntry
          MAX-ACCESS  not-accessible
          STATUS  current
          DESCRIPTION
                "The Appian  DS3 Far End Day Table contains various
                statistics collected by each DS3 Interface over
                the previous 30 days of operation as well as over
                the current period.  The first row in this table 
                (identified by acDs3FarEndDayNumber=1) represents the 
                current day statistics.  The next 30 rows in this table 
                (represented by acDs3FarEndDayNumber=2..31) represents
                one of the past 24 hour days.  This table is created
                 automatically."
          ::= { acDs3 5 }

     acDs3FarEndDayEntry OBJECT-TYPE
          SYNTAX  AcDs3FarEndDayEntry
          MAX-ACCESS  not-accessible
          STATUS  current
          DESCRIPTION
                 "An entry in the DS3 Far End Day table."
          INDEX   { acDs3FarEndDayNodeId,
                    acDs3FarEndDaySlot,
                    acDs3FarEndDayPort,
                    acDs3FarEndDayNumber }
          ::= { acDs3FarEndDayTable 1 }

     AcDs3FarEndDayEntry ::=
          SEQUENCE {
               acDs3FarEndDayNodeId     AcNodeId,
               acDs3FarEndDaySlot       AcSlotNumber,
               acDs3FarEndDayPort       AcPortNumber,
               acDs3FarEndDayNumber     INTEGER,
               acDs3FarEndDayValidStats TruthValue,
               acDs3FarEndDayResetStats TruthValue,
               acDs3FarEndDayCESs       PerfIntervalCount,
               acDs3FarEndDayCSESs      PerfIntervalCount,
               acDs3FarEndDayCCVs       PerfIntervalCount,
               acDs3FarEndDayUASs       PerfIntervalCount
         }

     acDs3FarEndDayNodeId OBJECT-TYPE
          SYNTAX  AcNodeId
          MAX-ACCESS  accessible-for-notify
          STATUS  current
          DESCRIPTION
                 "The node id is the id for this specific node in the OSAP 
                 ring."
          ::= { acDs3FarEndDayEntry 1 }

     acDs3FarEndDaySlot OBJECT-TYPE
          SYNTAX  AcSlotNumber
          MAX-ACCESS  accessible-for-notify
          STATUS  current
          DESCRIPTION
                 "The physical port number for the port."
          ::= { acDs3FarEndDayEntry 2 }

     acDs3FarEndDayPort OBJECT-TYPE
          SYNTAX  AcPortNumber
          MAX-ACCESS  accessible-for-notify
          STATUS  current
          DESCRIPTION
                 "The physical port number for the port."
          ::= { acDs3FarEndDayEntry 3 }

     acDs3FarEndDayNumber OBJECT-TYPE
         SYNTAX  INTEGER (1..31)
         MAX-ACCESS  accessible-for-notify
         STATUS  current
         DESCRIPTION
                 "A number between 1 and 31, where 1 is the current
                 24 hour day interval in progress, 2 is the most 
                 recently completed 24 hour day and 31 is
                 the 24 hour day 29 days prior to interval 2."
         ::= { acDs3FarEndDayEntry 4 }

     acDs3FarEndDayValidStats OBJECT-TYPE
          SYNTAX  TruthValue
          MAX-ACCESS  read-only
          STATUS  current
          DESCRIPTION
                 "This variable indicates if the data for this
                 interval is valid."
          ::= { acDs3FarEndDayEntry 5 }

     acDs3FarEndDayResetStats OBJECT-TYPE
          SYNTAX  TruthValue
          MAX-ACCESS  read-write
          STATUS  current
          DESCRIPTION
                 "This variable allows the data for the current
                 interval (acDs3FarEndDayIndex=1) to be reset.
                 The acDs3FarEndDayValidFlag will be set to False
                 after the reset for the current day.  This 
                 field has no effect on acDs3FarEndDayIndex 2..31.
                 This field will always show a vluae of false when read."
          ::= { acDs3FarEndDayEntry 6 }

     acDs3FarEndDayCESs OBJECT-TYPE
         SYNTAX  PerfIntervalCount
         MAX-ACCESS  read-only
         STATUS  current
         DESCRIPTION
                 "The counter associated with the number of Far End
                 C-bit Errored Seconds encountered by a DS3
                 interface. In the case where the agent is
                 a proxy and data is not available, return
                 noSuchInstance."
        ::= { acDs3FarEndDayEntry 7 }

     acDs3FarEndDayCSESs OBJECT-TYPE
         SYNTAX  PerfIntervalCount
         MAX-ACCESS  read-only
         STATUS  current
         DESCRIPTION
                 "The counter associated with the number of Far End
                 C-bit Severely Errored Seconds."
        ::= { acDs3FarEndDayEntry 8 }

     acDs3FarEndDayCCVs OBJECT-TYPE
          SYNTAX  PerfIntervalCount
          MAX-ACCESS  read-only
          STATUS  current
          DESCRIPTION
                 "The counter associated with the number of Far End
                 C-bit Coding Violations reported via the far end
                 block error count."
          ::= { acDs3FarEndDayEntry 9 }

     acDs3FarEndDayUASs OBJECT-TYPE
          SYNTAX  PerfIntervalCount
          MAX-ACCESS  read-only
          STATUS  current
          DESCRIPTION
                 "The counter associated with the number of Far End
                 unavailable seconds."
          ::= { acDs3FarEndDayEntry 10 }


     -- The Appian  DS3 Threshold Table
     acDs3ThresholdTable OBJECT-TYPE
          SYNTAX SEQUENCE OF AcDs3ThresholdEntry
          MAX-ACCESS  not-accessible
          STATUS  current
          DESCRIPTION
                 "The Appian  DS3 Threshold Table allows the user to
                 configure the threshold values for each of the 
                 statistics found in the interval table base on
                 the 15 minute interval on the day.  This table is created
                 automatically."
          ::= { acDs3 6 }

     acDs3ThresholdEntry OBJECT-TYPE
          SYNTAX  AcDs3ThresholdEntry
          MAX-ACCESS  not-accessible
          STATUS  current
          DESCRIPTION
                 "An entry in the Appian DS1 Threshold table."
          INDEX   { acDs3ThresholdNodeId, 
                    acDs3ThresholdSlot, 
                    acDs3ThresholdPort }

          ::= { acDs3ThresholdTable 1 }

     AcDs3ThresholdEntry ::=
          SEQUENCE {
              acDs3ThresholdNodeId             AcNodeId,
              acDs3ThresholdSlot               AcSlotNumber,
              acDs3ThresholdPort               AcPortNumber,
              acDs3ThresholdNEIntervalPESs     INTEGER,
              acDs3ThresholdNEIntervalPSESs    INTEGER,
              acDs3ThresholdNEIntervalSEFSs    INTEGER,
              acDs3ThresholdNEIntervalUASs     INTEGER,
              acDs3ThresholdNEIntervalLCVs     INTEGER,
              acDs3ThresholdNEIntervalPCVs     INTEGER,
              acDs3ThresholdNEIntervalLESs     INTEGER,
              acDs3ThresholdNEIntervalCCVs     INTEGER,
              acDs3ThresholdNEIntervalCESs     INTEGER,
              acDs3ThresholdNEIntervalCSESs    INTEGER,
              acDs3ThresholdNEDayPESs          INTEGER,
              acDs3ThresholdNEDayPSESs         INTEGER,
              acDs3ThresholdNEDaySEFSs         INTEGER,
              acDs3ThresholdNEDayUASs          INTEGER,
              acDs3ThresholdNEDayLCVs          INTEGER,
              acDs3ThresholdNEDayPCVs          INTEGER,
              acDs3ThresholdNEDayLESs          INTEGER,
              acDs3ThresholdNEDayCCVs          INTEGER,
              acDs3ThresholdNEDayCESs          INTEGER,
              acDs3ThresholdNEDayCSESs         INTEGER,
              acDs3ThresholdFEIntervalCESs     INTEGER,
              acDs3ThresholdFEIntervalCSESs    INTEGER,
              acDs3ThresholdFEIntervalCCVs     INTEGER,
              acDs3ThresholdFEIntervalUASs     INTEGER,
              acDs3ThresholdFEDayCESs          INTEGER,
              acDs3ThresholdFEDayCSESs         INTEGER,
              acDs3ThresholdFEDayCCVs          INTEGER,
              acDs3ThresholdFEDayUASs          INTEGER
     }


     acDs3ThresholdNodeId OBJECT-TYPE
          SYNTAX  AcNodeId
          MAX-ACCESS  accessible-for-notify
          STATUS  current
          DESCRIPTION
                 "The node id is the id for this specific node in the OSAP 
                 ring."
          ::= { acDs3ThresholdEntry 1 }

     acDs3ThresholdSlot OBJECT-TYPE
          SYNTAX  AcSlotNumber
          MAX-ACCESS  accessible-for-notify
          STATUS  current
          DESCRIPTION
                 "The physical slot number for the port."
          ::= { acDs3ThresholdEntry 2 }

     acDs3ThresholdPort OBJECT-TYPE
          SYNTAX  AcPortNumber
          MAX-ACCESS  accessible-for-notify
          STATUS  current
          DESCRIPTION
                 "The physical port number for the port."
          ::= { acDs3ThresholdEntry 3 }

     acDs3ThresholdNEIntervalPESs OBJECT-TYPE
          SYNTAX  INTEGER
          MAX-ACCESS  read-write
          STATUS  current
          DESCRIPTION
                 "The threshold value for near end interval number of P-Bit 
                 Errored Seconds.  A value of 0 disables the threshold 
                 mechanism for this attribute."
          DEFVAL { 0 }
          ::= { acDs3ThresholdEntry 4 }

     acDs3ThresholdNEIntervalPSESs OBJECT-TYPE
          SYNTAX  INTEGER
          MAX-ACCESS  read-write
          STATUS  current
          DESCRIPTION
                 "The threshold value for the near end interval number of P-Bit
                  Severely Errored Seconds.  A value of 0 disables the 
                  threshold mechanism for this attribute."
          DEFVAL { 0 }
          ::= { acDs3ThresholdEntry 5 }

     acDs3ThresholdNEIntervalSEFSs OBJECT-TYPE
          SYNTAX  INTEGER
          MAX-ACCESS  read-write
          STATUS  current
          DESCRIPTION
                 "The threshold for the near end interval number of Severely 
                 Errored Framing Seconds.  A value of 0 disables the 
                 threshold mechanism for this attribute."
          DEFVAL { 0 }
          ::= { acDs3ThresholdEntry 6 }


     acDs3ThresholdNEIntervalUASs OBJECT-TYPE
          SYNTAX  INTEGER
          MAX-ACCESS  read-write
          STATUS  current
          DESCRIPTION
                 "The threshold for the near end interval number of Unavailable 
                 Seconds.  A value of 0 disables the threshold mechanism 
                 for this attribute."
          DEFVAL { 0 }
          ::= { acDs3ThresholdEntry 7 }


     acDs3ThresholdNEIntervalLCVs OBJECT-TYPE
          SYNTAX  INTEGER
          MAX-ACCESS  read-write
          STATUS  current
          DESCRIPTION
                 "The threshold for the near end interval number of Line
                 Coding Violations.  A value of 0 disables the threshold 
                 mechanism for this attribute."
          DEFVAL { 0 }
          ::= { acDs3ThresholdEntry 8 }


     acDs3ThresholdNEIntervalPCVs OBJECT-TYPE
          SYNTAX  INTEGER
          MAX-ACCESS  read-write
          STATUS  current
          DESCRIPTION
                 "The threshold for the near end interval number of Path 
                 Coding Violations.  A value of 0 disables the threshold 
                 mechanism for this attribute."
          DEFVAL { 0 }
          ::= { acDs3ThresholdEntry 9 }


     acDs3ThresholdNEIntervalLESs OBJECT-TYPE
          SYNTAX  INTEGER
          MAX-ACCESS  read-write
          STATUS  current
          DESCRIPTION
                 "The threshold value for the near end interval number of 
                 Line Errored Seconds.  A value of 0 disables the 
                 threshold mechanism for this attribute."
          DEFVAL { 0 }
          ::= { acDs3ThresholdEntry 10 }

     acDs3ThresholdNEIntervalCCVs OBJECT-TYPE
          SYNTAX INTEGER
          MAX-ACCESS read-write
          STATUS current
          DESCRIPTION
                 "The threshold for the near end interval number of C-Bit 
                 Coding Violations.  A value of 0 disables the threshold 
                 mechanism for this attribute."
          DEFVAL { 0 }
          ::= { acDs3ThresholdEntry 11 }


     acDs3ThresholdNEIntervalCESs OBJECT-TYPE
          SYNTAX INTEGER
          MAX-ACCESS read-write
          STATUS current
          DESCRIPTION
                 "The threshold for the near end interval number of C-Bit 
                 Errored Seconds.  A value of 0 disables the threshold mechanism 
                 for this attribute."
          DEFVAL { 0 }
          ::= { acDs3ThresholdEntry 12 }

     acDs3ThresholdNEIntervalCSESs OBJECT-TYPE
          SYNTAX INTEGER
          MAX-ACCESS read-write
          STATUS current
          DESCRIPTION
                 "The threshold for the near end interval number of C-Bit
                 Severely Errored Seconds.  A value of 0 disables the 
                 threshold mechanism for this attribute."
          DEFVAL { 0 }
          ::= { acDs3ThresholdEntry 13 }

     acDs3ThresholdNEDayPESs OBJECT-TYPE
          SYNTAX  INTEGER
          MAX-ACCESS  read-write
          STATUS  current
          DESCRIPTION
                 "The threshold value for near end day number of P-Bit Errored 
                 Seconds.  A value of 0 disables the threshold mechanism 
                 for this attribute."
          DEFVAL { 0 }
          ::= { acDs3ThresholdEntry 14 }

     acDs3ThresholdNEDayPSESs OBJECT-TYPE
          SYNTAX  INTEGER
          MAX-ACCESS  read-write
          STATUS  current
          DESCRIPTION
                 "The threshold for the near end day number of P-Bit Severely 
                 Errored Seconds.  A value of 0 disables the threshold 
                 mechanism for this attribute."
          DEFVAL { 0 }
          ::= { acDs3ThresholdEntry 15 }

     acDs3ThresholdNEDaySEFSs OBJECT-TYPE
          SYNTAX  INTEGER
          MAX-ACCESS  read-write
          STATUS  current
          DESCRIPTION
                 "The threshold value for the near end day number of Severely 
                 Errored Framing Seconds.  A value of 0 disables the 
                 threshold mechanism for this attribute."
          DEFVAL { 0 }
          ::= { acDs3ThresholdEntry 16 }

     acDs3ThresholdNEDayUASs OBJECT-TYPE
          SYNTAX  INTEGER
          MAX-ACCESS  read-write
          STATUS  current
          DESCRIPTION
                 "The threshold value for the near end day number of 
                 Unavailable Seconds.  A value of 0 disables the threshold 
                 mechanism for this attribute."
          DEFVAL { 0 }
          ::= { acDs3ThresholdEntry 17 }

     acDs3ThresholdNEDayLCVs OBJECT-TYPE
          SYNTAX  INTEGER
          MAX-ACCESS  read-write
          STATUS  current
          DESCRIPTION
                 "The threshold for the near end day number of Line Coding 
                 Violations.  A value of 0 disables the threshold 
                 mechanism for this attribute."
          DEFVAL { 0 }
          ::= { acDs3ThresholdEntry 18 }

     acDs3ThresholdNEDayPCVs OBJECT-TYPE
          SYNTAX  INTEGER
          MAX-ACCESS  read-write
          STATUS  current
          DESCRIPTION
                 "The threshold value for the near end day number of Path 
                 Coding Violations.  A value of 0 disables the threshold 
                 mechanism for this attribute."
          DEFVAL { 0 }
          ::= { acDs3ThresholdEntry 19 }

     acDs3ThresholdNEDayLESs OBJECT-TYPE
          SYNTAX  INTEGER
          MAX-ACCESS  read-write
          STATUS  current
          DESCRIPTION
                 "The threshold for the near end day number of Line Errored 
                 Seconds.  A value of 0 disables the threshold mechanism 
                 for this attribute."
          DEFVAL { 0 }
          ::= { acDs3ThresholdEntry 20 }

     acDs3ThresholdNEDayCCVs OBJECT-TYPE
          SYNTAX INTEGER
          MAX-ACCESS read-write
          STATUS current
          DESCRIPTION
                 "The threshold for the near end day number of C-Bit Coding 
                 Violations.  A value of 0 disables the threshold mechanism 
                 for this attribute."
          DEFVAL { 0 }
          ::= { acDs3ThresholdEntry 21 }

     acDs3ThresholdNEDayCESs OBJECT-TYPE
          SYNTAX INTEGER
          MAX-ACCESS read-write
          STATUS current
          DESCRIPTION
                 "The threshold for the near end day number of C-Bit Errored 
                 Seconds.  A value of 0 disables the threshold mechanism 
                 for this attribute."
          DEFVAL { 0 }
          ::= { acDs3ThresholdEntry 22 }


     acDs3ThresholdNEDayCSESs OBJECT-TYPE
          SYNTAX INTEGER
          MAX-ACCESS read-write
          STATUS current
          DESCRIPTION
                 "The threshold for the near end day number of C-Bit Severely
                 Errored Seconds.  A value of 0 disables the threshold mechanism 
                 for this attribute."
          DEFVAL { 0 }
          ::= { acDs3ThresholdEntry 23 }

     acDs3ThresholdFEIntervalCESs OBJECT-TYPE
          SYNTAX  INTEGER
          MAX-ACCESS  read-write
          STATUS  current
          DESCRIPTION
                 "The threshold for the far end interval counter associated 
                 with the number of Far End C-bit Errored Seconds.  A value 
                 of 0 disables the threshold mechanism for this attribute."
          DEFVAL { 0 }
          ::= { acDs3ThresholdEntry 24 }

     acDs3ThresholdFEIntervalCSESs OBJECT-TYPE
         SYNTAX  INTEGER
         MAX-ACCESS  read-write
         STATUS  current
         DESCRIPTION
                 "The threshold for the far end interval counter associated 
                 with the number of Far End C-bit Severely Errored Seconds.
                 A value of 0 disables the threshold mechanism for this
                 attribute."
          DEFVAL { 0 }
        ::= { acDs3ThresholdEntry 25 }

     acDs3ThresholdFEIntervalCCVs OBJECT-TYPE
          SYNTAX  INTEGER
          MAX-ACCESS  read-write
          STATUS  current
          DESCRIPTION
                 "The threshold for the far end interval counter associated 
                 with the number of Far End C-bit Coding Violations reported 
                 via the far end block error count.  A value of 0 disables 
                 the threshold mechanism for this attribute."
          DEFVAL { 0 }
          ::= { acDs3ThresholdEntry 26 }

     acDs3ThresholdFEIntervalUASs OBJECT-TYPE
          SYNTAX  INTEGER
          MAX-ACCESS  read-write
          STATUS  current
          DESCRIPTION
                 "The threshold for the far end interval counter associated 
                 with the number of Far End unavailable seconds.  A value 
                 of 0 disables the threshold mechanism for this attribute."
          DEFVAL { 0 }
          ::= { acDs3ThresholdEntry 27 }

     acDs3ThresholdFEDayCESs OBJECT-TYPE
         SYNTAX  INTEGER
         MAX-ACCESS  read-write
         STATUS  current
         DESCRIPTION
                 "The threshold for the far end day counter associated 
                 with the number of Far End C-bit Errored Seconds.  A value 
                 of 0 disables the threshold mechanism for this attribute."
          DEFVAL { 0 }
        ::= { acDs3ThresholdEntry 28 }

     acDs3ThresholdFEDayCSESs OBJECT-TYPE
         SYNTAX  INTEGER
         MAX-ACCESS  read-write
         STATUS  current
         DESCRIPTION
                 "The threshold for the far end day counter associated 
                 with the number of Far End C-bit Severely Errored Seconds.
                 A value of 0 disables the threshold mechanism for this
                 attribute."
          DEFVAL { 0 }
        ::= { acDs3ThresholdEntry 29 }

     acDs3ThresholdFEDayCCVs OBJECT-TYPE
          SYNTAX  INTEGER
          MAX-ACCESS  read-write
          STATUS  current
          DESCRIPTION
                 "The threshold for the far end day counter associated 
                 with the number of Far End C-bit Coding Violations reported 
                 via the far end block error count.  A value of 0 disables 
                 the threshold mechanism for this attribute."
          DEFVAL { 0 }
          ::= { acDs3ThresholdEntry 30 }

     acDs3ThresholdFEDayUASs OBJECT-TYPE
          SYNTAX  INTEGER
          MAX-ACCESS  read-write
          STATUS  current
          DESCRIPTION
                 "The threshold for the far end day counter associated with 
                 the number of Far End unavailable seconds.  A value of 0 
                 disables the threshold mechanism for this attribute."
          DEFVAL { 0 }
          ::= { acDs3ThresholdEntry 31 }


-- 
--   Ds3 TRAPS
--
--

acDs3Traps   OBJECT IDENTIFIER ::= { acDs3 0 }


acDs3LineStatusChange NOTIFICATION-TYPE
    OBJECTS { acChassisCurrentTime, acChassisRingId, acDs3ConfigNodeId,
              acDs3ConfigSlot,
              acDs3ConfigPort,
              acDs3ConfigLineStatus, 
              acDs3ConfigLineStatusLastChange }
    STATUS  current
    DESCRIPTION
    "An acLogcialDs3LineStatusChange trap is sent when the value of an 
    instance acDs3ConfigLineStatus changes. It can be utilized by 
    an NMS to trigger polls."

    ::= { acDs3Traps 1 }

acDs3StatsResetTrap  NOTIFICATION-TYPE 
    OBJECTS { acChassisCurrentTime, acChassisRingId, acDs3ConfigNodeId,
              acDs3ConfigSlot,
              acDs3ConfigPort }
    STATUS  current
    DESCRIPTION
    "The  Ds3 statistics for this interface have been reset to zero (0) 
    which may effect long term trending functions monitoring this interface."
    
    ::= { acDs3Traps 2 }

acDs3CfgErrorTrap  NOTIFICATION-TYPE 
    OBJECTS { acChassisCurrentTime, acChassisRingId, acDs3ConfigNodeId,
              acDs3ConfigSlot,
              acDs3ConfigPort }
    STATUS  current
    DESCRIPTION
    "A configuration request to the  Ds3 configuration table for an 
    interface has been detected as invalid or corrupt."
    
    ::= { acDs3Traps 3 }


acDs3LinkDownTrap  NOTIFICATION-TYPE
    OBJECTS { acChassisCurrentTime, acChassisRingId, acDs3ConfigNodeId,
              acDs3ConfigSlot,
              acDs3ConfigPort }
    STATUS  current
    DESCRIPTION
    "The link for this ds3 interface has obtained sync."

    ::= { acDs3Traps 4 }

acDs3LinkUpTrap  NOTIFICATION-TYPE
    OBJECTS { acChassisCurrentTime, acChassisRingId, acDs3ConfigNodeId,
              acDs3ConfigSlot,
              acDs3ConfigPort }
    STATUS  current
    DESCRIPTION
    "The link for this ds3 interface has lost sync."

    ::= { acDs3Traps 5 }

acDs3ExceededThresholdNEIntervalPESsTrap NOTIFICATION-TYPE
    OBJECTS { acChassisCurrentTime, acChassisRingId, acDs3ThresholdNodeId,
              acDs3ThresholdSlot,
              acDs3ThresholdPort }
    STATUS  current
    DESCRIPTION
    "The threshold specified has been exceeded on this interface."

    ::= { acDs3Traps 6 }
        
acDs3ExceededThresholdNEIntervalPSESsTrap NOTIFICATION-TYPE
    OBJECTS { acChassisCurrentTime, acChassisRingId, acDs3ThresholdNodeId,
              acDs3ThresholdSlot,
              acDs3ThresholdPort }
    STATUS  current
    DESCRIPTION
    "The threshold specified has been exceeded on this interface."

    ::= { acDs3Traps 7 }
        
acDs3ExceededThresholdNEIntervalSEFSsTrap NOTIFICATION-TYPE
    OBJECTS { acChassisCurrentTime, acChassisRingId, acDs3ThresholdNodeId,
              acDs3ThresholdSlot,
              acDs3ThresholdPort }
    STATUS  current
    DESCRIPTION
    "The threshold specified has been exceeded on this interface."

    ::= { acDs3Traps 8 }
        
acDs3ExceededThresholdNEIntervalUASsTrap NOTIFICATION-TYPE
    OBJECTS { acChassisCurrentTime, acChassisRingId, acDs3ThresholdNodeId,
              acDs3ThresholdSlot,
              acDs3ThresholdPort }
    STATUS  current
    DESCRIPTION
    "The threshold specified has been exceeded on this interface."

    ::= { acDs3Traps 9 }
        
acDs3ExceededThresholdNEIntervalLCVsTrap NOTIFICATION-TYPE
    OBJECTS { acChassisCurrentTime, acChassisRingId, acDs3ThresholdNodeId,
              acDs3ThresholdSlot,
              acDs3ThresholdPort }
    STATUS  current
    DESCRIPTION
    "The threshold specified has been exceeded on this interface."

    ::= { acDs3Traps 10 }
        
acDs3ExceededThresholdNEIntervalPCVsTrap NOTIFICATION-TYPE
    OBJECTS { acChassisCurrentTime, acChassisRingId, acDs3ThresholdNodeId,
              acDs3ThresholdSlot,
              acDs3ThresholdPort }
    STATUS  current
    DESCRIPTION
    "The threshold specified has been exceeded on this interface."

    ::= { acDs3Traps 11 }
        
acDs3ExceededThresholdNEIntervalLESsTrap NOTIFICATION-TYPE
    OBJECTS { acChassisCurrentTime, acChassisRingId, acDs3ThresholdNodeId,
              acDs3ThresholdSlot,
              acDs3ThresholdPort }
    STATUS  current
    DESCRIPTION
    "The threshold specified has been exceeded on this interface."

    ::= { acDs3Traps 12 }
        
acDs3ExceededThresholdNEIntervalCCVsTrap NOTIFICATION-TYPE
    OBJECTS { acChassisCurrentTime, acChassisRingId, acDs3ThresholdNodeId,
              acDs3ThresholdSlot,
              acDs3ThresholdPort }
    STATUS  current
    DESCRIPTION
    "The threshold specified has been exceeded on this interface."

    ::= { acDs3Traps 13 }
        
acDs3ExceededThresholdNEIntervalCESsTrap NOTIFICATION-TYPE
    OBJECTS { acChassisCurrentTime, acChassisRingId, acDs3ThresholdNodeId,
              acDs3ThresholdSlot,
              acDs3ThresholdPort }
    STATUS  current
    DESCRIPTION
    "The threshold specified has been exceeded on this interface."

    ::= { acDs3Traps 14 }
        
acDs3ExceededThresholdNEIntervalCSESsTrap NOTIFICATION-TYPE
    OBJECTS { acChassisCurrentTime, acChassisRingId, acDs3ThresholdNodeId,
              acDs3ThresholdSlot,
              acDs3ThresholdPort }
    STATUS  current
    DESCRIPTION
    "The threshold specified has been exceeded on this interface."

    ::= { acDs3Traps 15 }
        
acDs3ExceededThresholdNEDayPESsTrap NOTIFICATION-TYPE
    OBJECTS { acChassisCurrentTime, acChassisRingId, acDs3ThresholdNodeId,
              acDs3ThresholdSlot,
              acDs3ThresholdPort }
    STATUS  current
    DESCRIPTION
    "The threshold specified has been exceeded on this interface."

    ::= { acDs3Traps 16 }
        
acDs3ExceededThresholdNEDayPSESsTrap NOTIFICATION-TYPE
    OBJECTS { acChassisCurrentTime, acChassisRingId, acDs3ThresholdNodeId,
              acDs3ThresholdSlot,
              acDs3ThresholdPort }
    STATUS  current
    DESCRIPTION
    "The threshold specified has been exceeded on this interface."

    ::= { acDs3Traps 17 }
        
acDs3ExceededThresholdNEDaySEFSsTrap NOTIFICATION-TYPE
    OBJECTS { acChassisCurrentTime, acChassisRingId, acDs3ThresholdNodeId,
              acDs3ThresholdSlot,
              acDs3ThresholdPort }
    STATUS  current
    DESCRIPTION
    "The threshold specified has been exceeded on this interface."

    ::= { acDs3Traps 18 }
        
acDs3ExceededThresholdNEDayUASsTrap NOTIFICATION-TYPE
    OBJECTS { acChassisCurrentTime, acChassisRingId, acDs3ThresholdNodeId,
              acDs3ThresholdSlot,
              acDs3ThresholdPort }
    STATUS  current
    DESCRIPTION
    "The threshold specified has been exceeded on this interface."

    ::= { acDs3Traps 19 }
        
acDs3ExceededThresholdNEDayLCVsTrap NOTIFICATION-TYPE
    OBJECTS { acChassisCurrentTime, acChassisRingId, acDs3ThresholdNodeId,
              acDs3ThresholdSlot,
              acDs3ThresholdPort }
    STATUS  current
    DESCRIPTION
    "The threshold specified has been exceeded on this interface."

    ::= { acDs3Traps 20 }
        
acDs3ExceededThresholdNEDayPCVsTrap NOTIFICATION-TYPE
    OBJECTS { acChassisCurrentTime, acChassisRingId, acDs3ThresholdNodeId,
              acDs3ThresholdSlot,
              acDs3ThresholdPort }
    STATUS  current
    DESCRIPTION
    "The threshold specified has been exceeded on this interface."

    ::= { acDs3Traps 21 }
        
acDs3ExceededThresholdNEDayLESsTrap NOTIFICATION-TYPE
    OBJECTS { acChassisCurrentTime, acChassisRingId, acDs3ThresholdNodeId,
              acDs3ThresholdSlot,
              acDs3ThresholdPort }
    STATUS  current
    DESCRIPTION
    "The threshold specified has been exceeded on this interface."

    ::= { acDs3Traps 22 }
        
acDs3ExceededThresholdNEDayCCVsTrap NOTIFICATION-TYPE
    OBJECTS { acChassisCurrentTime, acChassisRingId, acDs3ThresholdNodeId,
              acDs3ThresholdSlot,
              acDs3ThresholdPort }
    STATUS  current
    DESCRIPTION
    "The threshold specified has been exceeded on this interface."

    ::= { acDs3Traps 23 }
        
acDs3ExceededThresholdNEDayCESsTrap NOTIFICATION-TYPE
    OBJECTS { acChassisCurrentTime, acChassisRingId, acDs3ThresholdNodeId,
              acDs3ThresholdSlot,
              acDs3ThresholdPort }
    STATUS  current
    DESCRIPTION
    "The threshold specified has been exceeded on this interface."

    ::= { acDs3Traps 24 }
        
acDs3ExceededThresholdNEDayCSESsTrap NOTIFICATION-TYPE
    OBJECTS { acChassisCurrentTime, acChassisRingId, acDs3ThresholdNodeId,
              acDs3ThresholdSlot,
              acDs3ThresholdPort }
    STATUS  current
    DESCRIPTION
    "The threshold specified has been exceeded on this interface."

    ::= { acDs3Traps 25 }
        
acDs3ExceededThresholdFEIntervalCESsTrap NOTIFICATION-TYPE
    OBJECTS { acChassisCurrentTime, acChassisRingId, acDs3ThresholdNodeId,
              acDs3ThresholdSlot,
              acDs3ThresholdPort }
    STATUS  current
    DESCRIPTION
    "The threshold specified has been exceeded on this interface."

    ::= { acDs3Traps 26 }
        
acDs3ExceededThresholdFEIntervalCSESsTrap NOTIFICATION-TYPE
    OBJECTS { acChassisCurrentTime, acChassisRingId, acDs3ThresholdNodeId,
              acDs3ThresholdSlot,
              acDs3ThresholdPort }
    STATUS  current
    DESCRIPTION
    "The threshold specified has been exceeded on this interface."

    ::= { acDs3Traps 27 }
        
acDs3ExceededThresholdFEIntervalCCVsTrap NOTIFICATION-TYPE
    OBJECTS { acChassisCurrentTime, acChassisRingId, acDs3ThresholdNodeId,
              acDs3ThresholdSlot,
              acDs3ThresholdPort }
    STATUS  current
    DESCRIPTION
    "The threshold specified has been exceeded on this interface."

    ::= { acDs3Traps 28 }
        
acDs3ExceededThresholdFEIntervalUASsTrap NOTIFICATION-TYPE
    OBJECTS { acChassisCurrentTime, acChassisRingId, acDs3ThresholdNodeId,
              acDs3ThresholdSlot,
              acDs3ThresholdPort }
    STATUS  current
    DESCRIPTION
    "The threshold specified has been exceeded on this interface."

    ::= { acDs3Traps 29 }
        
acDs3ExceededThresholdFEDayCESsTrap NOTIFICATION-TYPE
    OBJECTS { acChassisCurrentTime, acChassisRingId, acDs3ThresholdNodeId,
              acDs3ThresholdSlot,
              acDs3ThresholdPort }
    STATUS  current
    DESCRIPTION
    "The threshold specified has been exceeded on this interface."

    ::= { acDs3Traps 30 }
        
acDs3ExceededThresholdFEDayCSESsTrap NOTIFICATION-TYPE
    OBJECTS { acChassisCurrentTime, acChassisRingId, acDs3ThresholdNodeId,
              acDs3ThresholdSlot,
              acDs3ThresholdPort }
    STATUS  current
    DESCRIPTION
    "The threshold specified has been exceeded on this interface."

    ::= { acDs3Traps 31 }
        
acDs3ExceededThresholdFEDayCCVsTrap NOTIFICATION-TYPE
    OBJECTS { acChassisCurrentTime, acChassisRingId, acDs3ThresholdNodeId,
              acDs3ThresholdSlot,
              acDs3ThresholdPort }
    STATUS  current
    DESCRIPTION
    "The threshold specified has been exceeded on this interface."

    ::= { acDs3Traps 32 }
        
acDs3ExceededThresholdFEDayUASsTrap NOTIFICATION-TYPE
    OBJECTS { acChassisCurrentTime, acChassisRingId, acDs3ThresholdNodeId,
              acDs3ThresholdSlot,
              acDs3ThresholdPort }
    STATUS  current
    DESCRIPTION
    "The threshold specified has been exceeded on this interface."

    ::= { acDs3Traps 33 }
        
        
END
