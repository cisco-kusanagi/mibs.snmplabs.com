--
--
--          Computer Network Technology, Corp.
--              6000 Nathan Lane North 
--              Plymouth, Minnesota  55442   
--
--                phone:  (763) 268-6000
--                  fax:  (763) 268-6800
--              support:  1-800-NET-TECH
--                email:  cnt.com
--
--	MIB Version:     1.1
--	Product Family:  CNT Zeus(2)
--
-- +------------+ if you change this mib, you increment the version number.
-- | Attention! |
-- +------------+
--

CNT2-MIB DEFINITIONS ::= BEGIN

        IMPORTS enterprises FROM RFC1155-SMI;

    --- cnt enterprise mib
    cnt OBJECT IDENTIFIER ::= { enterprises 333 }


        --- cnt Zeus platform
        cnt2 OBJECT IDENTIFIER ::= { cnt 2 }


            --- cnt Zeus Mib-2-like Objects
            --- These objects mirror objects in the iso mib-2 tree.
            --- They are listed here as enterprise objects to allow for
            --- multiple instances of the mib-2 subtree for the master agent.
            cnt2Mib2 OBJECT IDENTIFIER ::= { cnt2 1 }


            --- cnt Zeus Experimental-like Objects
            --- These objects mirror objects in the iso experimental tree.
            --- They are listed here as enterprise objects to allow for
            --- multiple instances of these experimental subtrees for the
            --- master agent.  These subtree is only for those experimental
            --- mibs which do not allow for multiple instances.
            cnt2Experimental OBJECT IDENTIFIER ::= { cnt2 2 }


            --- cnt Zeus Master Agent Objects
            --- These objects are maintained by the master agent.
            --- They include information that applies to the global system.
            cnt2Snmp OBJECT IDENTIFIER ::= { cnt2 3 }


            --- cnt Zeus Subagent Objects
            --- Under this subtree are all of the objects that can be
            --- registered under the Zeus subagent subtree.  Each is
            --- a set of instanced tables that can be aggregated by the
            --- master agent.
            cnt2Subagent OBJECT IDENTIFIER ::= { cnt2 4 }

                --- Service Monitor objects
                --- cnt241  OBJECT IDENTIFIER ::= { cnt24 1 }

                --- Escon objects
                --- cnt242  OBJECT IDENTIFIER ::= { cnt24 2 }

                --- ATM Forum Aggregation objects (deprecated)
                --- cnt243  OBJECT IDENTIFIER ::= { cnt24 3 }

                --- reserved
                --- cnt244  OBJECT IDENTIFIER ::= { cnt24 4 }

                --- Compression/Decompression objects
                --- cnt245  OBJECT IDENTIFIER ::= { cnt24 5 }


            --- cnt Zeus Configuration Objects
            --- These objects are used to monitor and control the configuration
            --- of all of the components of the Zeus node.  This tree is
            --- separated into subtrees by file.
            cnt2Config OBJECT IDENTIFIER ::= { cnt2 5 }

END
