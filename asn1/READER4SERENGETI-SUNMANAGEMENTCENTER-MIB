-- This MIB was created by extracting information from 
-- Sun Mangement Center 3.5 for use in other applications
-- to help determine what is actually listed in the SMC snmp 
-- agent. Sun has/will not release their MIBS for this 
-- information, so I created them from all information that
-- they have released.
--
-- Most all the information should be correct, but
-- if you find a discrepency please let me know. I do not
-- have all available Sun hardware to test with, so not 
-- not all types of support hardware has been tested.
-- These MIBs have only been tested using the utilities
-- from net-snmp. They may or may not work with other
-- applications.
-- 
-- The MIBs are not detailed, they only are useful in 
-- mapping OIDs to names. At some point in time 
-- descriptions may be given.
--
-- Author: Brian T. O'Neill (btoneill@misplaced.net)
-- Date: 7-30-2003 
-- Version: 0.9
--
-- No guarantees are given regarding the accuracy of this
-- data.
--
-- Note: The naming was done in line with the published
-- MIBS from Sun Microsystems.
--
--
READER4SERENGETI-SUNMANAGEMENTCENTER-MIB DEFINITIONS ::= BEGIN

  IMPORTS
        enterprises, NOTIFICATION-TYPE, OBJECT-TYPE, MODULE-IDENTITY
                FROM SNMPv2-SMI;

sun             OBJECT IDENTIFIER ::= { enterprises 42 }
prod            OBJECT IDENTIFIER ::= { sun 2 }
sunsymon        OBJECT IDENTIFIER ::= { prod 12 }
agent           OBJECT IDENTIFIER ::= { sunsymon 2 }
base            OBJECT IDENTIFIER ::= { agent 1 }
modules         OBJECT IDENTIFIER ::= { agent 2 }
hardware        OBJECT IDENTIFIER ::= { modules 1 }
--
--
config          OBJECT IDENTIFIER ::= { hardware 1 }
reader4u        OBJECT IDENTIFIER ::= { config 1 }
reader4udt      OBJECT IDENTIFIER ::= { config 2 }
reader4uwg      OBJECT IDENTIFIER ::= { config 3 }
reader4u1P      OBJECT IDENTIFIER ::= { config 4 }
reader4u1D      OBJECT IDENTIFIER ::= { config 5 }
reader4unt      OBJECT IDENTIFIER ::= { config 6 }
readerSerengeti OBJECT IDENTIFIER ::= { config 7 }
reader4uvh      OBJECT IDENTIFIER ::= { config 8 }
readerECP       OBJECT IDENTIFIER ::= { config 9 }
readerELP       OBJECT IDENTIFIER ::= { config 10 }


sunSmTreeProp	OBJECT IDENTIFIER ::= { networkEntry 1 }
sunSmNodeName	OBJECT IDENTIFIER ::= { networkEntry 2 }
entry-no	OBJECT IDENTIFIER ::= { networkEntry 3 }
device-type	OBJECT IDENTIFIER ::= { networkEntry 4 }
ether	OBJECT IDENTIFIER ::= { networkEntry 5 }
inet	OBJECT IDENTIFIER ::= { networkEntry 6 }
interface-name	OBJECT IDENTIFIER ::= { networkEntry 7 }
node-hierarchy	OBJECT IDENTIFIER ::= { networkEntry 8 }
symbolic-name	OBJECT IDENTIFIER ::= { networkEntry 9 }
reg	OBJECT IDENTIFIER ::= { networkEntry 10 }
boardTbl	OBJECT IDENTIFIER ::= { board 1 }
cpu-unitTbl	OBJECT IDENTIFIER ::= { cpu-unit 1 }
sunSmTreeProp	OBJECT IDENTIFIER ::= { wciEntry 1 }
sunSmNodeName	OBJECT IDENTIFIER ::= { wciEntry 2 }
entry-no	OBJECT IDENTIFIER ::= { wciEntry 3 }
parolis	OBJECT IDENTIFIER ::= { wciEntry 4 }
sysctrlTbl	OBJECT IDENTIFIER ::= { sysctrl 1 }
eepromTbl	OBJECT IDENTIFIER ::= { eeprom 1 }
slotTbl	OBJECT IDENTIFIER ::= { slot 1 }
simm-groupTbl	OBJECT IDENTIFIER ::= { simm-group 1 }
sunSmTreeProp	OBJECT IDENTIFIER ::= { io-controllerEntry 1 }
sunSmNodeName	OBJECT IDENTIFIER ::= { io-controllerEntry 2 }
entry-no	OBJECT IDENTIFIER ::= { io-controllerEntry 3 }
device-type	OBJECT IDENTIFIER ::= { io-controllerEntry 4 }
instance	OBJECT IDENTIFIER ::= { io-controllerEntry 5 }
model	OBJECT IDENTIFIER ::= { io-controllerEntry 6 }
reg	OBJECT IDENTIFIER ::= { io-controllerEntry 7 }
portid	OBJECT IDENTIFIER ::= { io-controllerEntry 8 }
version-no	OBJECT IDENTIFIER ::= { io-controllerEntry 9 }
sunSmTreeProp	OBJECT IDENTIFIER ::= { dimm-entry 1 }
sunSmNodeName	OBJECT IDENTIFIER ::= { dimm-entry 2 }
entry-no	OBJECT IDENTIFIER ::= { dimm-entry 3 }
bank-no	OBJECT IDENTIFIER ::= { dimm-entry 4 }
bank-size	OBJECT IDENTIFIER ::= { dimm-entry 5 }
bank-status	OBJECT IDENTIFIER ::= { dimm-entry 6 }
fru	OBJECT IDENTIFIER ::= { dimm-entry 7 }
dimm-size	OBJECT IDENTIFIER ::= { dimm-entry 8 }
io-controllerEntry	OBJECT IDENTIFIER ::= { io-controllerTbl 1 }
cpu-unit-entry	OBJECT IDENTIFIER ::= { cpu-unitTbl 1 }
sunwffbTbl	OBJECT IDENTIFIER ::= { sunwffb 1 }
eeprom-entry	OBJECT IDENTIFIER ::= { eepromTbl 1 }
paroliEntry	OBJECT IDENTIFIER ::= { paroliTbl 1 }
ledTbl	OBJECT IDENTIFIER ::= { led 1 }
wciTbl	OBJECT IDENTIFIER ::= { wci 1 }
dimmTbl	OBJECT IDENTIFIER ::= { dimm 1 }
simm-status-entry	OBJECT IDENTIFIER ::= { simm-statusTbl 1 }
sunSmTreeProp	OBJECT IDENTIFIER ::= { led-entry 1 }
sunSmNodeName	OBJECT IDENTIFIER ::= { led-entry 2 }
entry-no	OBJECT IDENTIFIER ::= { led-entry 3 }
led-num	OBJECT IDENTIFIER ::= { led-entry 4 }
state	OBJECT IDENTIFIER ::= { led-entry 5 }
tapeTbl	OBJECT IDENTIFIER ::= { tape 1 }
sunSmTreeProp	OBJECT IDENTIFIER ::= { eeprom-entry 1 }
sunSmNodeName	OBJECT IDENTIFIER ::= { eeprom-entry 2 }
entry-no	OBJECT IDENTIFIER ::= { eeprom-entry 3 }
model	OBJECT IDENTIFIER ::= { eeprom-entry 4 }
reg	OBJECT IDENTIFIER ::= { eeprom-entry 5 }
sunSmTreeProp	OBJECT IDENTIFIER ::= { io-unitEntry 1 }
sunSmNodeName	OBJECT IDENTIFIER ::= { io-unitEntry 2 }
entry-no	OBJECT IDENTIFIER ::= { io-unitEntry 3 }
board-num	OBJECT IDENTIFIER ::= { io-unitEntry 4 }
device-id	OBJECT IDENTIFIER ::= { io-unitEntry 5 }
instance	OBJECT IDENTIFIER ::= { io-unitEntry 6 }
reg	OBJECT IDENTIFIER ::= { io-unitEntry 7 }
sunSmTreeProp	OBJECT IDENTIFIER ::= { ffb-entry 1 }
sunSmNodeName	OBJECT IDENTIFIER ::= { ffb-entry 2 }
entry-no	OBJECT IDENTIFIER ::= { ffb-entry 3 }
buffer	OBJECT IDENTIFIER ::= { ffb-entry 4 }
device-type	OBJECT IDENTIFIER ::= { ffb-entry 5 }
model	OBJECT IDENTIFIER ::= { ffb-entry 6 }
pathname-element	OBJECT IDENTIFIER ::= { ffb-entry 7 }
ffb-entry	OBJECT IDENTIFIER ::= { ffbTbl 1 }
readerSerengeti	OBJECT IDENTIFIER ::= { config 7 }
central-entry	OBJECT IDENTIFIER ::= { centralTbl 1 }
io-deviceEntry	OBJECT IDENTIFIER ::= { io-deviceTbl 1 }
memoryTbl	OBJECT IDENTIFIER ::= { memory 1 }
memory-entry	OBJECT IDENTIFIER ::= { memoryTbl 1 }
simm-statusTbl	OBJECT IDENTIFIER ::= { simm-status 1 }
sunSmTreeProp	OBJECT IDENTIFIER ::= { system 1 }
sunSmNodeName	OBJECT IDENTIFIER ::= { system 2 }
os	OBJECT IDENTIFIER ::= { system 3 }
osversion	OBJECT IDENTIFIER ::= { system 4 }
system-clock-frequency	OBJECT IDENTIFIER ::= { system 5 }
architecture	OBJECT IDENTIFIER ::= { system 6 }
hostname	OBJECT IDENTIFIER ::= { system 7 }
machine	OBJECT IDENTIFIER ::= { system 8 }
platform	OBJECT IDENTIFIER ::= { system 9 }
sample	OBJECT IDENTIFIER ::= { system 10 }
serial-number	OBJECT IDENTIFIER ::= { system 11 }
timestamp	OBJECT IDENTIFIER ::= { system 12 }
timestamp-raw	OBJECT IDENTIFIER ::= { system 13 }
total-disks	OBJECT IDENTIFIER ::= { system 14 }
total-memory	OBJECT IDENTIFIER ::= { system 15 }
total-processors	OBJECT IDENTIFIER ::= { system 16 }
total-tape-devices	OBJECT IDENTIFIER ::= { system 17 }
total-model-changes	OBJECT IDENTIFIER ::= { system 18 }
total-config-changes	OBJECT IDENTIFIER ::= { system 19 }
centralTbl	OBJECT IDENTIFIER ::= { central 1 }
sunSmTreeProp	OBJECT IDENTIFIER ::= { sunwffb-entry 1 }
sunSmNodeName	OBJECT IDENTIFIER ::= { sunwffb-entry 2 }
entry-no	OBJECT IDENTIFIER ::= { sunwffb-entry 3 }
dram3	OBJECT IDENTIFIER ::= { sunwffb-entry 4 }
dac	OBJECT IDENTIFIER ::= { sunwffb-entry 5 }
fbc-version	OBJECT IDENTIFIER ::= { sunwffb-entry 6 }
board-type	OBJECT IDENTIFIER ::= { sunwffb-entry 7 }
buffer	OBJECT IDENTIFIER ::= { sunwffb-entry 8 }
device-type	OBJECT IDENTIFIER ::= { sunwffb-entry 9 }
height	OBJECT IDENTIFIER ::= { sunwffb-entry 10 }
model	OBJECT IDENTIFIER ::= { sunwffb-entry 11 }
revision	OBJECT IDENTIFIER ::= { sunwffb-entry 12 }
upa-portid	OBJECT IDENTIFIER ::= { sunwffb-entry 13 }
width	OBJECT IDENTIFIER ::= { sunwffb-entry 14 }
sunSmTreeProp	OBJECT IDENTIFIER ::= { central-entry 1 }
sunSmNodeName	OBJECT IDENTIFIER ::= { central-entry 2 }
entry-no	OBJECT IDENTIFIER ::= { central-entry 3 }
reg	OBJECT IDENTIFIER ::= { central-entry 4 }
upa-mid	OBJECT IDENTIFIER ::= { central-entry 5 }
networkEntry	OBJECT IDENTIFIER ::= { networkTbl 1 }
sunSmTreeProp	OBJECT IDENTIFIER ::= { solt-entry 1 }
sunSmNodeName	OBJECT IDENTIFIER ::= { solt-entry 2 }
entry-no	OBJECT IDENTIFIER ::= { solt-entry 3 }
slot-num	OBJECT IDENTIFIER ::= { solt-entry 4 }
solt-entry	OBJECT IDENTIFIER ::= { slotTbl 1 }
sunSmTreeProp	OBJECT IDENTIFIER ::= { io-deviceEntry 1 }
sunSmNodeName	OBJECT IDENTIFIER ::= { io-deviceEntry 2 }
entry-no	OBJECT IDENTIFIER ::= { io-deviceEntry 3 }
device-type	OBJECT IDENTIFIER ::= { io-deviceEntry 4 }
disk-count	OBJECT IDENTIFIER ::= { io-deviceEntry 5 }
instance	OBJECT IDENTIFIER ::= { io-deviceEntry 6 }
model	OBJECT IDENTIFIER ::= { io-deviceEntry 7 }
node-hierarchy	OBJECT IDENTIFIER ::= { io-deviceEntry 8 }
network-count	OBJECT IDENTIFIER ::= { io-deviceEntry 9 }
reg	OBJECT IDENTIFIER ::= { io-deviceEntry 10 }
tape-count	OBJECT IDENTIFIER ::= { io-deviceEntry 11 }
sunSmTreeProp	OBJECT IDENTIFIER ::= { cpu-unit-entry 1 }
sunSmNodeName	OBJECT IDENTIFIER ::= { cpu-unit-entry 2 }
entry-no	OBJECT IDENTIFIER ::= { cpu-unit-entry 3 }
board-num	OBJECT IDENTIFIER ::= { cpu-unit-entry 4 }
clock-frequency	OBJECT IDENTIFIER ::= { cpu-unit-entry 5 }
cpu-type	OBJECT IDENTIFIER ::= { cpu-unit-entry 6 }
dcache-size	OBJECT IDENTIFIER ::= { cpu-unit-entry 7 }
device-type	OBJECT IDENTIFIER ::= { cpu-unit-entry 8 }
ecache-size	OBJECT IDENTIFIER ::= { cpu-unit-entry 9 }
fru	OBJECT IDENTIFIER ::= { cpu-unit-entry 10 }
icache-size	OBJECT IDENTIFIER ::= { cpu-unit-entry 11 }
model	OBJECT IDENTIFIER ::= { cpu-unit-entry 12 }
portid	OBJECT IDENTIFIER ::= { cpu-unit-entry 13 }
processor-id	OBJECT IDENTIFIER ::= { cpu-unit-entry 14 }
reg	OBJECT IDENTIFIER ::= { cpu-unit-entry 15 }
status	OBJECT IDENTIFIER ::= { cpu-unit-entry 16 }
unit	OBJECT IDENTIFIER ::= { cpu-unit-entry 17 }
io-deviceTbl	OBJECT IDENTIFIER ::= { io-device 1 }
led-entry	OBJECT IDENTIFIER ::= { ledTbl 1 }
paroliTbl	OBJECT IDENTIFIER ::= { paroli 1 }
sunSmTreeProp	OBJECT IDENTIFIER ::= { tapeEntry 1 }
sunSmNodeName	OBJECT IDENTIFIER ::= { tapeEntry 2 }
entry-no	OBJECT IDENTIFIER ::= { tapeEntry 3 }
device-type	OBJECT IDENTIFIER ::= { tapeEntry 4 }
fru	OBJECT IDENTIFIER ::= { tapeEntry 5 }
instance	OBJECT IDENTIFIER ::= { tapeEntry 6 }
model	OBJECT IDENTIFIER ::= { tapeEntry 7 }
node-hierarchy	OBJECT IDENTIFIER ::= { tapeEntry 8 }
tape-name	OBJECT IDENTIFIER ::= { tapeEntry 9 }
status	OBJECT IDENTIFIER ::= { tapeEntry 10 }
target	OBJECT IDENTIFIER ::= { tapeEntry 11 }
io-controllerTbl	OBJECT IDENTIFIER ::= { io-controller 1 }
sunSmTreeProp	OBJECT IDENTIFIER ::= { memory-controllerEntry 1 }
sunSmNodeName	OBJECT IDENTIFIER ::= { memory-controllerEntry 2 }
entry-no	OBJECT IDENTIFIER ::= { memory-controllerEntry 3 }
compatible0	OBJECT IDENTIFIER ::= { memory-controllerEntry 4 }
device-type	OBJECT IDENTIFIER ::= { memory-controllerEntry 5 }
portid	OBJECT IDENTIFIER ::= { memory-controllerEntry 6 }
reg	OBJECT IDENTIFIER ::= { memory-controllerEntry 7 }
tapeEntry	OBJECT IDENTIFIER ::= { tapeTbl 1 }
io-unitEntry	OBJECT IDENTIFIER ::= { io-unitTbl 1 }
sunSmTreeProp	OBJECT IDENTIFIER ::= { diskEntry 1 }
sunSmNodeName	OBJECT IDENTIFIER ::= { diskEntry 2 }
entry-no	OBJECT IDENTIFIER ::= { diskEntry 3 }
device-type	OBJECT IDENTIFIER ::= { diskEntry 4 }
disk-name	OBJECT IDENTIFIER ::= { diskEntry 5 }
fru	OBJECT IDENTIFIER ::= { diskEntry 6 }
instance	OBJECT IDENTIFIER ::= { diskEntry 7 }
node-hierarchy	OBJECT IDENTIFIER ::= { diskEntry 8 }
target	OBJECT IDENTIFIER ::= { diskEntry 9 }
memory-controllerEntry	OBJECT IDENTIFIER ::= { memory-controllerTbl 1 }
sunSmTreeProp	OBJECT IDENTIFIER ::= { memory-entry 1 }
sunSmNodeName	OBJECT IDENTIFIER ::= { memory-entry 2 }
entry-no	OBJECT IDENTIFIER ::= { memory-entry 3 }
pathname-element	OBJECT IDENTIFIER ::= { memory-entry 4 }
sunSmTreeProp	OBJECT IDENTIFIER ::= { board-entry 1 }
sunSmNodeName	OBJECT IDENTIFIER ::= { board-entry 2 }
entry-no	OBJECT IDENTIFIER ::= { board-entry 3 }
label-name	OBJECT IDENTIFIER ::= { board-entry 4 }
board-num	OBJECT IDENTIFIER ::= { board-entry 5 }
fru	OBJECT IDENTIFIER ::= { board-entry 6 }
hpu	OBJECT IDENTIFIER ::= { board-entry 7 }
hot-pluggable	OBJECT IDENTIFIER ::= { board-entry 8 }
memory-size	OBJECT IDENTIFIER ::= { board-entry 9 }
condition	OBJECT IDENTIFIER ::= { board-entry 10 }
type	OBJECT IDENTIFIER ::= { board-entry 11 }
type-int	OBJECT IDENTIFIER ::= { board-entry 12 }
sunSmTreeProp	OBJECT IDENTIFIER ::= { simm-group-entry 1 }
sunSmNodeName	OBJECT IDENTIFIER ::= { simm-group-entry 2 }
entry-no	OBJECT IDENTIFIER ::= { simm-group-entry 3 }
device-type	OBJECT IDENTIFIER ::= { simm-group-entry 4 }
group-no	OBJECT IDENTIFIER ::= { simm-group-entry 5 }
size	OBJECT IDENTIFIER ::= { simm-group-entry 6 }
status	OBJECT IDENTIFIER ::= { simm-group-entry 7 }
sunSmTreeProp	OBJECT IDENTIFIER ::= { clock-board 1 }
sunSmNodeName	OBJECT IDENTIFIER ::= { clock-board 2 }
memory-controllerTbl	OBJECT IDENTIFIER ::= { memory-controller 1 }
diskTbl	OBJECT IDENTIFIER ::= { disk 1 }
ffbTbl	OBJECT IDENTIFIER ::= { ffb 1 }
dimm-entry	OBJECT IDENTIFIER ::= { dimmTbl 1 }
sunSmTreeProp	OBJECT IDENTIFIER ::= { paroliEntry 1 }
sunSmNodeName	OBJECT IDENTIFIER ::= { paroliEntry 2 }
entry-no	OBJECT IDENTIFIER ::= { paroliEntry 3 }
fru	OBJECT IDENTIFIER ::= { paroliEntry 4 }
local-port-id	OBJECT IDENTIFIER ::= { paroliEntry 5 }
validity	OBJECT IDENTIFIER ::= { paroliEntry 6 }
status	OBJECT IDENTIFIER ::= { paroliEntry 7 }
remote-port-id	OBJECT IDENTIFIER ::= { paroliEntry 8 }
remote-member-name	OBJECT IDENTIFIER ::= { paroliEntry 9 }
sunSmTreeProp	OBJECT IDENTIFIER ::= { sysctrl-entry 1 }
sunSmNodeName	OBJECT IDENTIFIER ::= { sysctrl-entry 2 }
entry-no	OBJECT IDENTIFIER ::= { sysctrl-entry 3 }
instance	OBJECT IDENTIFIER ::= { sysctrl-entry 4 }
reg	OBJECT IDENTIFIER ::= { sysctrl-entry 5 }
board-entry	OBJECT IDENTIFIER ::= { boardTbl 1 }
sunSmTreeProp	OBJECT IDENTIFIER ::= { simm-status-entry 1 }
sunSmNodeName	OBJECT IDENTIFIER ::= { simm-status-entry 2 }
entry-no	OBJECT IDENTIFIER ::= { simm-status-entry 3 }
reg	OBJECT IDENTIFIER ::= { simm-status-entry 4 }
networkTbl	OBJECT IDENTIFIER ::= { network 1 }
io-unitTbl	OBJECT IDENTIFIER ::= { io-unit 1 }
simm-group-entry	OBJECT IDENTIFIER ::= { simm-groupTbl 1 }
sysctrl-entry	OBJECT IDENTIFIER ::= { sysctrlTbl 1 }
system	OBJECT IDENTIFIER ::= { readerSerengeti 1 }
clock-board	OBJECT IDENTIFIER ::= { readerSerengeti 2 }
slot	OBJECT IDENTIFIER ::= { readerSerengeti 3 }
board	OBJECT IDENTIFIER ::= { readerSerengeti 4 }
cpu-unit	OBJECT IDENTIFIER ::= { readerSerengeti 5 }
dimm	OBJECT IDENTIFIER ::= { readerSerengeti 6 }
simm-status	OBJECT IDENTIFIER ::= { readerSerengeti 7 }
simm-group	OBJECT IDENTIFIER ::= { readerSerengeti 8 }
led	OBJECT IDENTIFIER ::= { readerSerengeti 9 }
central	OBJECT IDENTIFIER ::= { readerSerengeti 10 }
eeprom	OBJECT IDENTIFIER ::= { readerSerengeti 11 }
sysctrl	OBJECT IDENTIFIER ::= { readerSerengeti 12 }
memory	OBJECT IDENTIFIER ::= { readerSerengeti 13 }
ffb	OBJECT IDENTIFIER ::= { readerSerengeti 14 }
sunwffb	OBJECT IDENTIFIER ::= { readerSerengeti 15 }
io-controller	OBJECT IDENTIFIER ::= { readerSerengeti 16 }
wci	OBJECT IDENTIFIER ::= { readerSerengeti 17 }
paroli	OBJECT IDENTIFIER ::= { readerSerengeti 18 }
io-device	OBJECT IDENTIFIER ::= { readerSerengeti 19 }
disk	OBJECT IDENTIFIER ::= { readerSerengeti 20 }
tape	OBJECT IDENTIFIER ::= { readerSerengeti 21 }
network	OBJECT IDENTIFIER ::= { readerSerengeti 22 }
io-unit	OBJECT IDENTIFIER ::= { readerSerengeti 23 }
memory-controller	OBJECT IDENTIFIER ::= { readerSerengeti 24 }
wciEntry	OBJECT IDENTIFIER ::= { wciTbl 1 }
sunwffb-entry	OBJECT IDENTIFIER ::= { sunwffbTbl 1 }
diskEntry	OBJECT IDENTIFIER ::= { diskTbl 1 }

END
