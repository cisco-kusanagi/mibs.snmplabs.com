----------------------------------------------------------------------------
--
-- The Madge Ringswitch MIB                             Madge Networks Ltd
--
-- Version 4.04                                               11th May 2000
--
----------------------------------------------------------------------------
--
-- Overview
-- --------
-- The Madge Ringswitch MIB defines enterprise specific objects to allow the
-- management of Madge Smart Ringswitches.
--
-- The Madge Ringswitch MIB contains the following groups:
--
--   ringswitchBase    - Ringswitch global information
--   ringswitchPort    - Ringswitch per-port information
--   ringswitchFwd     - Source routing and transparent bridging information
--   ringswitchLCD     - LCD message information
--   ringswitchLAN     - Virtual LAN information
--   ringswitchVirt    - Additional virtual LAN information
--   ringswitchSlot    - Ringswitch per slot information
--   ringswitchGenPort - Ringswitch general per-port information
--   ringswitchTR      - Ringswitch Token Ring per-interface information
--   ringswitchFDDI    - Ringswitch FDDI per-card information
--   ringswitchATM     - Ringswitch ATM per-card information
--   ringswitchPSU     - Ringswitch power supply information
--   ringswitchFan     - Ringswitch fan information
--   ringswitchTrap    - Variables used in TRAPS
--   ringswitchFilter  - Ringswitch protocol filter information
--   ringswitchTLS     - Ringswitch TLS per-card information
--   ringswitchEthernet- Ringswitch Ethernet per-card information
--
--   Traps:            - Ringswitch specific traps are at 494.4.0
--
----------------------------------------------------------------------------
	MADGERSW-MIB DEFINITIONS ::= BEGIN
	IMPORTS
		IpAddress, OBJECT-TYPE, enterprises
			FROM RFC1155-SMI
	TRAP-TYPE FROM RFC-1215;
-- Data Types
	DisplayString   ::= OCTET STRING
	--------------------------------------------------------------------
	-- Octet String encoding of a 48 bit integer, transmitted Most
	-- Significant Byte first
	--------------------------------------------------------------------
	INTEGER48 ::= OCTET STRING (SIZE (6))
	--------------------------------------------------------------------
	-- ATM address
	--------------------------------------------------------------------
	NSAP ::= OCTET STRING (SIZE(20))
	--------------------------------------------------------------------
	-- MAC addresses
	--
	-- TRNMacAddress is a 6 octet address in the "non-canonical" order,
	-- ie according to the IEEE 802.5 definition of MAC address
	--
	-- ETHMacAddress is a 6 octet address in the "canonical" order, ie
	-- according to the IEEE 802.1a definition of MAC address
	--------------------------------------------------------------------
	TRNMacAddress ::= OCTET STRING (SIZE (6))
	ETHMacAddress ::= OCTET STRING (SIZE (6))
	--------------------------------------------------------------------
	-- The state machine described by RingswitchRowStatus allows the
	-- following transitions, returning noSuchName for any other
	-- attempted set request:
	--
	-- valid ==> invalid            Use this to delete an entry from
	--                              the table.
	--
	-- valid ==> createRequest      Use this to change an entry in the
	--                              table.  The Ringswitch sets the
	--                              status to underCreation immediately.
	--
	-- invalid ==> createRequest    Use this to create an entry in the
	--                              table.  The Ringswitch sets the
	--                              status to underCreation immediately.
	--
	-- underCreation ==> valid      Use this to validate an entry in
	--                              the table; until this point, the
	--                              Ringswitch does not change its
	--                              switching behaviour.
	--
	-- underCreation ==> invalid    If the entry is not validated after
	--                              ?? seconds, the Ringswitch does this
	--                              transition automatically.
	--------------------------------------------------------------------
	RingswitchRowStatus ::= INTEGER {
					valid           (1),
					createRequest   (2),
					underCreation   (3),
					invalid         (4)
					}
-- the Ringswitch MIB
	madge                   OBJECT IDENTIFIER ::= { enterprises 494 }
	ringswitch              OBJECT IDENTIFIER ::= { madge 4 }
-- groups in the Ringswitch MIB
-- specific traps:                                { ringswitch 0 }
	ringswitchBase          OBJECT IDENTIFIER ::= { ringswitch 1 }
	ringswitchPort          OBJECT IDENTIFIER ::= { ringswitch 2 }
	ringswitchFwd           OBJECT IDENTIFIER ::= { ringswitch 3 }
	ringswitchLCD           OBJECT IDENTIFIER ::= { ringswitch 4 }
	ringswitchLAN           OBJECT IDENTIFIER ::= { ringswitch 5 }
	ringswitchVirt          OBJECT IDENTIFIER ::= { ringswitch 6 }
	ringswitchSlot          OBJECT IDENTIFIER ::= { ringswitch 7 }
	ringswitchGenPort       OBJECT IDENTIFIER ::= { ringswitch 8 }
	ringswitchTR            OBJECT IDENTIFIER ::= { ringswitch 9 }
	ringswitchFDDI          OBJECT IDENTIFIER ::= { ringswitch 10 }
	ringswitchATM           OBJECT IDENTIFIER ::= { ringswitch 11 }
	ringswitchPSU           OBJECT IDENTIFIER ::= { ringswitch 12 }
	ringswitchFan           OBJECT IDENTIFIER ::= { ringswitch 13 }
	ringswitchTrap          OBJECT IDENTIFIER ::= { ringswitch 14 }
	ringswitchFilter        OBJECT IDENTIFIER ::= { ringswitch 15 }
	ringswitchTLS	        OBJECT IDENTIFIER ::= { ringswitch 16 }
        ringswitchEthernet      OBJECT IDENTIFIER ::= { ringswitch 21 }
----------------------------------------------------------------------------
-- the ringswitchBase group
	ringswitchBasePSFanSpeed OBJECT-TYPE
		SYNTAX  INTEGER
		ACCESS  read-only
		STATUS  mandatory
		DESCRIPTION
			"The number of revolutions per minute being reported
			by the fan internal to the system power supply. If
			this value is read as zero, the fan is no longer
			operating"
		::= { ringswitchBase 1 }
	ringswitchBaseExtFanSpeed OBJECT-TYPE
		SYNTAX  INTEGER
		ACCESS  read-only
		STATUS  mandatory
		DESCRIPTION
			"The number of revolutions per minute being reported
			by the external system fan. If this value is read as
			zero, the fan is no longer operating"
		::= { ringswitchBase 2 }
	ringswitchBaseRipSapSuppression OBJECT-TYPE
		SYNTAX  INTEGER {
				enable          (1),
				disable         (2)
				}
		ACCESS  read-write
		STATUS  mandatory
		DESCRIPTION
			"If this variable is set to enable the system will
			only forward broadcast-addressed IPX RIP and SAP
			Response frames to those ports that have recently
			sourced such a frame. This reduces the number of
			gratuitous frames sent out on LANs that only have
			IPX workstations attached. A value of disable causes
			no special action to be taken for such frames."
		::= { ringswitchBase 3 }
	ringswitchBaseAREConversion OBJECT-TYPE
		SYNTAX  INTEGER {
				enable-first            (1),
				enable-all              (2),
				enable-bcast-first      (3),
				enable-bcast-all        (4),
				disable                 (5)
				}
		ACCESS  read-write
		STATUS  mandatory
		DESCRIPTION
			"This variable controls the action taken when
			forwarding All Routes Explorer frames.
			enable-first:       convert all ARE frames with a
					    RIF length of 2 to STE frames.
			enable-all:         convert all ARE frames to STE
					    frames.
			enable-bcast-first: convert all ARE frames with the
					    broadcast destination address,
					    with a RIF length of 2 to STE
					    frames.
			enable-bcast-all:   convert all ARE frames with the
					    broadcast destination address to
					    STE frames.
			disable:            follow normal forwarding rules
					    for ARE frames."
		::= { ringswitchBase 4 }
	ringswitchBaseStpMode OBJECT-TYPE
		SYNTAX  INTEGER  {
				ibm-sr          (1),
				ieee8021d       (2)
				}
		ACCESS  read-write
		STATUS  mandatory
		DESCRIPTION
			"This selects the mode of operation of the spanning
			tree protocol. When set to ibm-sr, spanning tree
			protocol BPDUs are sent to the 802.5 LBS functional
			address on all interface types, and TCN BPDUs are
			not generated.  When set to ieee8021d, TCN BPDUs are
			generated, and the IEEE 802.1D group address
			(01 80 C2 00 00 00 in canonical form) is used
			as the destination address for BPDUs on interfaces
			of types other than 802.5"
		::= { ringswitchBase 5 }
	ringswitchBaseRMONState OBJECT-TYPE
		SYNTAX  INTEGER {
				enable          (1),
				disable         (2)
				}
		ACCESS  read-write
		STATUS  mandatory
		DESCRIPTION
			"Setting this to 'enable' activates the RMON
			probe function in the Ringswitch. When RMON
			has been enabled it is configured according to
			ringswitchBaseRMONMirrorPort,
			ringswitchPortRMONMode and ringswitchPortRMONSnoop
			mib entries.
			Setting it to 'disable' de-activates the RMON probe
			function. When RMON is disabled, all other RMON
			related mib entries defined by the Madge Ringwitch
			MIB will be ignored (but their values will still
			be settable). ringswitchBaseRMONState defaults to
			'disable'."
		::= { ringswitchBase 6 }
	ringswitchBaseBackPlaneType OBJECT-TYPE
		SYNTAX  INTEGER {
				original          (1),
				dual-psu          (2),
				express           (3)
				}
		ACCESS  read-only
		STATUS  mandatory
		DESCRIPTION
			"This variable reports the type of chassis that
			the Ringswitch is mounted in."
	::= { ringswitchBase 7 }
	ringswitchBaseRMONMirrorPort OBJECT-TYPE
		SYNTAX  INTEGER
		ACCESS  read-write
		STATUS  mandatory
		DESCRIPTION
			"This variable controls the RMON mirroring facility.
			A value of 0 means mirroring is disabled.
			Mirroring is enabled by setting this variable to
			the ifNumber of the port to which mirroring will
			apply and by setting ringswitchBaseRMONState to
			'enable'.
			When mirroring is enabled, the Ringswitch sends
			all RMON related traffic to the mirror port (except
			for MAC frames)."
		::= { ringswitchBase 8 }
	ringswitchBaseTotalResetCounters OBJECT-TYPE
		SYNTAX  INTEGER {
				reset   (1)
				}
		ACCESS  read-write
		STATUS  mandatory
		DESCRIPTION
			"Use this variable to reset all the counters
			on the Ringswitch, including those in the
			ringswitchGenPort, dot1dSRPort, ifEntry and
			fddimib groups."
		::= { ringswitchBase 9 }
	ringswitchBaseDownloadMode OBJECT-TYPE
		SYNTAX  INTEGER {
				normal (1),
				active (2)
				}
		ACCESS  read-write
		STATUS  mandatory
		DESCRIPTION
			"Use this variable to select the mode for all 
			 subsequent download operations.
			 normal - device will enter the loader prior to 
				  downloading.
			 active - device will NOT enter the loader and 
				  perform the download online."
		::= { ringswitchBase 10 }
----------------------------------------------------------------------------
-- the ringswitchPort group
	ringswitchPortTable OBJECT-TYPE
		SYNTAX  SEQUENCE OF RingswitchPortEntry
		ACCESS  not-accessible
		STATUS  mandatory
		DESCRIPTION
			"A table that contains general port information."
		::= { ringswitchPort 1 }
	ringswitchPortEntry OBJECT-TYPE
		SYNTAX  RingswitchPortEntry
		ACCESS  not-accessible
		STATUS  mandatory
		DESCRIPTION
			""
		INDEX { ringswitchPortNum }
		::= { ringswitchPortTable 1 }
	RingswitchPortEntry ::=
		SEQUENCE        {
				ringswitchPortNum
					INTEGER,
				ringswitchPortRingStatus
					INTEGER,
				ringswitchPortAdapterStatus
					INTEGER,
				ringswitchPortMediaType
					INTEGER,
				ringswitchPortIfMode
					INTEGER,
				ringswitchPortRingSpeed
					INTEGER,
				ringswitchPortTestState
					INTEGER,
				ringswitchPortTestError
					INTEGER,
				ringswitchPortTestPhase
					INTEGER,
				ringswitchPortSummary
					INTEGER,
				ringswitchPortAddress
					TRNMacAddress,
				ringswitchPortLAA
					TRNMacAddress,
				ringswitchPortStationType
					INTEGER,
				ringswitchPortRPSEnable
					INTEGER,
				ringswitchPortCutThruEnable
					INTEGER,
				ringswitchPortInOctets
					INTEGER48,
				ringswitchPortOutOctets
					INTEGER48,
				ringswitchPortSpecInFrames
					INTEGER48,
				ringswitchPortSpecOutFrames
					INTEGER48,
				ringswitchPortApeInFrames
					INTEGER48,
				ringswitchPortApeOutFrames
					INTEGER48,
				ringswitchPortSteInFrames
					INTEGER48,
				ringswitchPortSteOutFrames
					INTEGER48,
				ringswitchPortResetCounters
					INTEGER,
				ringswitchPortFixupMode
					INTEGER,
				ringswitchPortForwardMode
					INTEGER,
				ringswitchPortRMONCapabilities
					INTEGER,
				ringswitchPortRMONMode
					INTEGER,
				ringswitchPortRMONSnoop
					TRNMacAddress,
				ringswitchPortTransparentInFrames
					INTEGER48,
				ringswitchPortTransparentOutFrames
					INTEGER48,
				ringswitchPortTransparentDiscFrames
					INTEGER48,
				ringswitchPortLEDs
					OCTET STRING
				}
	ringswitchPortNum OBJECT-TYPE
		SYNTAX  INTEGER (1..65535)
		ACCESS  read-only
		STATUS  mandatory
		DESCRIPTION
			"The port number of the port for which this entry
			contains Ringswitch management information."
		::= { ringswitchPortEntry 1 }
	ringswitchPortRingStatus OBJECT-TYPE
		SYNTAX  INTEGER {
				normal          (1),
				single          (2),
				beaconing       (3),
				normal-fdx      (4),
				dtr-wait        (5)
				}
		ACCESS  read-only       
		STATUS  mandatory
		DESCRIPTION
			"The status of the ring to which this port is
			connected.
			normal:     Inserted into Classic ring
			single:     Single Station
			beaconing:  Beaconing Detected
			normal-fdx: DTR link in full duplex (TXI) mode
			dtr-wait:   DTR Concentrator port waiting for
				    attached station to insert"
		::= { ringswitchPortEntry 2 }
	ringswitchPortAdapterStatus OBJECT-TYPE
		SYNTAX  INTEGER {
				open    (1),
				closed  (2),
				opening (3)
				}
		ACCESS  read-only
		STATUS  mandatory
		DESCRIPTION
			"The status of the adapter used by this port."
		::= { ringswitchPortEntry 3 }
	ringswitchPortMediaType OBJECT-TYPE
		SYNTAX  INTEGER {
				tr-copper       (1),
				tr-fiber        (2),
				fddi-fiber      (3),
				absent          (4)
				}
		ACCESS  read-only
		STATUS  mandatory
		DESCRIPTION
			"Media type of the port."
		::= { ringswitchPortEntry 4 }
	ringswitchPortIfMode OBJECT-TYPE
		SYNTAX  INTEGER {
				node            (1),
				concentrator    (2),
				node-fdx        (3),
				conc-fdx        (4),
				node-classic    (5),
				conc-classic    (6),
				node-cau-rio    (7)
				}
		ACCESS  read-write
		STATUS  mandatory
		DESCRIPTION
			"Node or concentrator status of the port."
		::= { ringswitchPortEntry 5 }
	ringswitchPortRingSpeed OBJECT-TYPE
		SYNTAX  INTEGER {
				four    (1),
				sixteen (2),
				hundred (3)
				}
		ACCESS  read-write
		STATUS  mandatory
		DESCRIPTION
			"Speed of the ring to which this port is connected."
		::= { ringswitchPortEntry 6 }
	ringswitchPortTestState OBJECT-TYPE
		SYNTAX  INTEGER {
				disabled        (1),
				running         (2),
				failed          (3),
				ok              (4),
				unknown         (5)
				}
		ACCESS  read-only
		STATUS  mandatory
		DESCRIPTION
			"Current state of the bridge test."
		::= { ringswitchPortEntry 7 }
	ringswitchPortTestError OBJECT-TYPE
		SYNTAX  INTEGER {
				no-error        (1),
				same-ring       (2),
				duplicate-ring  (3),
				fail-nb         (4),
				bad-rnum        (5),
				fail-b          (6)
				}
		ACCESS  read-only
		STATUS  mandatory
		DESCRIPTION
			"Result of the bridge test."
		::= { ringswitchPortEntry 8 }
	ringswitchPortTestPhase OBJECT-TYPE
		SYNTAX  INTEGER {
				not-running     (1),
				same-ring       (2),
				routed          (3),
				broadcast       (4),
				success         (5)
				}
		ACCESS  read-only
		STATUS  mandatory
		DESCRIPTION
			"Current phase of the bridge test."
		::= { ringswitchPortEntry 9 }
	ringswitchPortSummary OBJECT-TYPE
		SYNTAX  INTEGER
		ACCESS  read-only
		STATUS  mandatory
		DESCRIPTION
			"This is a four octet field which packs some of the
			port attributes into a single mib entry. Each nibble
			represents a different attribute of the port:
				ifAdminStatus (most significant),
				ringswitchPortRingStatus,
				ringswitchPortAdapterStatus,
				ringswitchPortMediaType,
				ringswitchPortIfMode,
				ringswitchPortRingSpeed,
				ringswitchPortTestState,
				ringswitchPortTestError (least significant)"
		::= { ringswitchPortEntry 10 }
	ringswitchPortAddress OBJECT-TYPE
		SYNTAX  TRNMacAddress
		ACCESS  read-only
		STATUS  mandatory
		DESCRIPTION
			"The hard wired address of the port."
		::= { ringswitchPortEntry 11 }
	ringswitchPortLAA OBJECT-TYPE
		SYNTAX  TRNMacAddress
		ACCESS  read-write
		STATUS  mandatory
		DESCRIPTION
			"The locally administered address of the port."
		::= { ringswitchPortEntry 12 }
	ringswitchPortStationType OBJECT-TYPE
		SYNTAX  INTEGER {
				anything        (1),
				workstations    (2)
				}
		ACCESS  read-write
		STATUS  mandatory
		DESCRIPTION
			"Workstations-only status of the port; if this is
			limited, the port only has workstations on it, and
			broadcast frames received on this port will not be
			transmitted on other limited ports."
		::= { ringswitchPortEntry 13 }
	ringswitchPortRPSEnable OBJECT-TYPE
		SYNTAX  INTEGER {
				enable          (1),
				disable         (2)
				}
		ACCESS  read-write
		STATUS  mandatory
		DESCRIPTION
			"Enables or disables the Ring Parameter Server
			function on the port. If this variable is set to
			enabled, the port will enable the RPS functional
			address, and respond to Request Parameters MAC
			frames, supplying the port's segment number in
			the response."
		::= { ringswitchPortEntry 14 }
	ringswitchPortCutThruEnable OBJECT-TYPE
		SYNTAX  INTEGER {
				enable          (1),
				disable         (2)
				}
		ACCESS  read-write
		STATUS  mandatory
		DESCRIPTION
			"Enables or disables cut-through switching on the
			port. In some circumstances (e.g., 4 to 16 MB
			switching), cut-through will always be disabled,
			irrespective of the state of this variable."
		::= { ringswitchPortEntry 15 }
	ringswitchPortInOctets OBJECT-TYPE
		SYNTAX  INTEGER48
		ACCESS  read-only
		STATUS  mandatory
		DESCRIPTION
			"48 bit version of the interface MIB counter
			ifInOctets."
		::= { ringswitchPortEntry 16 }
	ringswitchPortOutOctets OBJECT-TYPE
		SYNTAX  INTEGER48
		ACCESS  read-only
		STATUS  mandatory
		DESCRIPTION
			"48 bit version of the interface MIB counter
			ifOutOctets."
		::= { ringswitchPortEntry 17 }
	ringswitchPortSpecInFrames OBJECT-TYPE
		SYNTAX  INTEGER48
		ACCESS  read-only
		STATUS  mandatory
		DESCRIPTION
			"48 bit version of the Bridge MIB counter
			srPortSpecInFrames."
		::= { ringswitchPortEntry 18 }
	ringswitchPortSpecOutFrames OBJECT-TYPE
		SYNTAX  INTEGER48
		ACCESS  read-only
		STATUS  mandatory
		DESCRIPTION
			"48 bit version of the Bridge MIB counter
			srPortSpecOutFrames."
		::= { ringswitchPortEntry 19 }
	ringswitchPortApeInFrames OBJECT-TYPE
		SYNTAX  INTEGER48
		ACCESS  read-only
		STATUS  mandatory
		DESCRIPTION
			"48 bit version of the Bridge MIB counter
			srPortApeInFrames."
		::= { ringswitchPortEntry 20 }
	ringswitchPortApeOutFrames OBJECT-TYPE
		SYNTAX  INTEGER48
		ACCESS  read-only
		STATUS  mandatory
		DESCRIPTION
			"48 bit version of the Bridge MIB counter
			srPortApeOutFrames."
		::= { ringswitchPortEntry 21 }
	ringswitchPortSteInFrames OBJECT-TYPE
		SYNTAX  INTEGER48
		ACCESS  read-only
		STATUS  mandatory
		DESCRIPTION
			"48 bit version of the Bridge MIB counter
			srPortSteInFrames."
		::= { ringswitchPortEntry 22 }
	ringswitchPortSteOutFrames OBJECT-TYPE
		SYNTAX  INTEGER48
		ACCESS  read-only
		STATUS  mandatory
		DESCRIPTION
			"48 bit version of the Bridge MIB counter
			srPortSteOutFrames."
		::= { ringswitchPortEntry 23 }
	ringswitchPortResetCounters OBJECT-TYPE
		SYNTAX  INTEGER {
				reset   (1)
				}
		ACCESS  read-write
		STATUS  mandatory
		DESCRIPTION
			"Use this variable to reset all the counters on
			this port, including those in the ringswitchPort,
			dot1dSRPort, ifEntry and fddimib groups."
		::= { ringswitchPortEntry 24 }
	ringswitchPortFixupMode OBJECT-TYPE
		SYNTAX  INTEGER {
				disabled    (1),
				fddi-all    (2)
				}
		ACCESS  read-write
		STATUS  mandatory
		DESCRIPTION
			"This MIB variable controls operation of protocol
			fixups on an FDDI linecard. When set to fddi-all,
			embedded MAC addresses in frames are bit-reversed to
			convert the frames into native FDDI format"
		::= { ringswitchPortEntry 25 }
	ringswitchPortForwardMode OBJECT-TYPE
		SYNTAX  INTEGER {
				sr-only (1),
				tb-only (2),
				sr-tb   (3)
				}
		ACCESS  read-write
		STATUS  mandatory
		DESCRIPTION
			"This MIB variable controls the bridging modes that
			are enabled on this port. Any combination of the
			two types of bridging - transparent and source
			routing can be enabled/disabled."
		::= { ringswitchPortEntry 26 }
	ringswitchPortRMONCapabilities OBJECT-TYPE
		SYNTAX  INTEGER  {
				disabled      (1),
				economy       (2),
				standard      (3),
				snooping      (4)
				}
		ACCESS  read-only
		STATUS  mandatory
		DESCRIPTION
			"A value that indicates the RMON capabilities of the
			port. The value represents the highest level RMON
			mode which the port can support.
			  'disabled' is the lowest level and indicates
				     no RMON capabilities
			  'snooping' is the highest level and indicates
				     that the port is capable of
				     running in all RMON modes"
		::= { ringswitchPortEntry 27 }
	ringswitchPortRMONMode OBJECT-TYPE
		SYNTAX  INTEGER {
				disabled      (1),
				economy       (2),
				standard      (3),
				snooping      (4)
				}
		ACCESS  read-write
		STATUS  mandatory
		DESCRIPTION
			"Controls the types of frames passed to the RMON
			probe function for processing as follows:
			disabled - no frames passed to the RMON probe
			economy  - MAC frames required for token ring
				   specific groups as follows:
				   MLStats table
				   Token Ring Ring station table
			standard - all frames
			snooping - all frames provided by the 'economy'
				   mode plus any frames originating
				   from or destined for the 'snoop address'
				   controlled by ringswitchPortRMONSnoop"
		::= { ringswitchPortEntry 28 }
	ringswitchPortRMONSnoop OBJECT-TYPE
		SYNTAX  TRNMacAddress
		ACCESS  read-write
		STATUS  mandatory
		DESCRIPTION
			"This controls the RMON snoop address used when
			ringswitchPortRMONMode is set to 'snooping'.
			A value of all zeroes results in no snooping
			taking place."
		::= { ringswitchPortEntry 29 }
	ringswitchPortTransparentInFrames OBJECT-TYPE
		SYNTAX  INTEGER48
		ACCESS  read-only
		STATUS  mandatory
		DESCRIPTION
			"48 bit version of the Bridge MIB counter
			TpPortInFrames."
		::= { ringswitchPortEntry 30 }
	ringswitchPortTransparentOutFrames OBJECT-TYPE
		SYNTAX  INTEGER48
		ACCESS  read-only
		STATUS  mandatory
		DESCRIPTION
			"48 bit version of the Bridge MIB counter
			TpPortOutFrames."
		::= { ringswitchPortEntry 31 }
	ringswitchPortTransparentDiscFrames OBJECT-TYPE
		SYNTAX  INTEGER48
		ACCESS  read-only
		STATUS  mandatory
		DESCRIPTION
			"48 bit version of the Bridge MIB counter
			TpPortInDiscards."
		::= { ringswitchPortEntry 32 }
	ringswitchPortLEDs OBJECT-TYPE
		SYNTAX  OCTET STRING
		ACCESS  read-only
		STATUS  mandatory
		DESCRIPTION
			"An octet string containing the colour of every LED
			on the port, one per octet:
				off             	(1),
				on-red          	(2),
				on-green        	(3),
				on-yellow       	(4),
				flash-red       	(5),
				flash-green     	(6),
				flash-yellow    	(7),
				flash-blue      	(8),
				flash-green-anti-phase	(9),
				flash-yellow-anti-phase	(10)"
		::= { ringswitchPortEntry 33 }
----------------------------------------------------------------------------
-- the ringswitchFwd group
	ringswitchFwdAdminState OBJECT-TYPE
		SYNTAX  INTEGER {
				sr-only         (1),
				disable         (2),
				tb-only         (3),
				srt             (4),
				srt-plus        (5)
				}
		ACCESS  read-write
		STATUS  mandatory
		DESCRIPTION
			"The desired state of the switches forwarding
			modes. This allows source routing and/or transparent
			bridging to be enabled/disabled for the whole
			Ringswitch"
		::= { ringswitchFwd 1 }
	ringswitchFwdOperState OBJECT-TYPE
		SYNTAX  INTEGER {
				sr-only         (1),
				inactive        (2),
				tb-only         (3),
				srt             (4),
				srt-plus        (5)
				}
		ACCESS  read-only
		STATUS  mandatory
		DESCRIPTION
			"The actual state of switches forwarding modes.
			If for some reason the switch is unable operate in
			the mode requested then the operating state may
			differ from the AdminState."
		::= { ringswitchFwd 2 }

	-- the Forwarding table

	ringswitchFwdPortTable OBJECT-TYPE
		SYNTAX  SEQUENCE OF RingswitchFwdPortEntry
		ACCESS  not-accessible
		STATUS  mandatory
		DESCRIPTION
			"A table that contains forwarding information about
			every port that is associated with this Ringswitch.
			Transparent, source-route, srt and srt plus ports
			are included."
		::= { ringswitchFwd 3 }
	ringswitchFwdPortEntry OBJECT-TYPE
		SYNTAX  RingswitchFwdPortEntry
		ACCESS  not-accessible
		STATUS  mandatory
		DESCRIPTION
			"A list of forwarding information for each port of
			the Ringswitch."
		INDEX { ringswitchFwdPort }
		::= { ringswitchFwdPortTable 1 }

	RingswitchFwdPortEntry ::=
			SEQUENCE        {
					ringswitchFwdPort
						INTEGER,
					ringswitchFwdPortMode
						INTEGER,
					ringswitchFwdPortStationType
						INTEGER,
					ringswitchFwdPortCutThruEnable
						INTEGER,
					ringswitchFwdPortSpecInFrames
						INTEGER48,
					ringswitchFwdPortSpecOutFrames
						INTEGER48,
					ringswitchFwdPortApeInFrames
						INTEGER48,
					ringswitchFwdPortApeOutFrames
						INTEGER48,
					ringswitchFwdPortSteInFrames
						INTEGER48,
					ringswitchFwdPortSteOutFrames
						INTEGER48,
					ringswitchFwdPortTransparentInFrames
						INTEGER48,
					ringswitchFwdPortTransparentOutFrames
						INTEGER48,
					ringswitchFwdPortTransparentDiscFrames
						INTEGER48,
					ringswitchFwdPortTestState
						INTEGER,
					ringswitchFwdPortTestError
						INTEGER,
					ringswitchFwdPortTestPhase
						INTEGER,
					ringswitchFwdPortTbForce
						INTEGER,
					ringswitchFwdPortStpMaster
						INTEGER,
					ringswitchFwdPortTbState
						INTEGER,
					ringswitchFwdPortSteState
						INTEGER,
					ringswitchFwdPortTbUnicastInFrames
						INTEGER48,
					ringswitchFwdPortTbUnicastOutFrames
						INTEGER48,
					ringswitchFwdPortTbBroadcastInFrames
						INTEGER48,
					ringswitchFwdPortTbBroadcastOutFrames
						INTEGER48,
					ringswitchFwdPortTbMulticastInFrames
						INTEGER48,
					ringswitchFwdPortTbMulticastOutFrames
						INTEGER48,
					ringswitchFwdPortTbMiscInFrames
						INTEGER48,
					ringswitchFwdPortTbMiscOutFrames
						INTEGER48,
					ringswitchFwdPortMatrixSrSpecFrames
						OCTET STRING,
					ringswitchFwdPortMatrixTbUniFrames
						OCTET STRING,
					ringswitchFwdPortEthernetSRBlk
						INTEGER,
					ringswitchFwdPortAutoPathCost
						INTEGER,
                    ringswitchFwdPortBroadcastReflect
	                    INTEGER
					}
	ringswitchFwdPort OBJECT-TYPE
		SYNTAX  INTEGER (1..65535)
		ACCESS  read-only
		STATUS  mandatory
		DESCRIPTION
			"The port number of the port for which this entry
			contains forwarding information. This value is the
			same as the value of dot1dBasePort for the equivalent
			port."
		::= { ringswitchFwdPortEntry 1 }
	ringswitchFwdPortMode OBJECT-TYPE
		SYNTAX  INTEGER {
				sr-only     (1),
				tb-only     (2),
				sr-tb       (3)
				}
		ACCESS  read-write
		STATUS  mandatory
		DESCRIPTION
			"This MIB variable controls the bridging modes that
			are enabled on this port. Any combination of the
			two types of bridging - transparent and source
			routing can be enabled/disabled."
		::= { ringswitchFwdPortEntry 2 }
	ringswitchFwdPortStationType OBJECT-TYPE
		SYNTAX  INTEGER {
				anything        (1),
				workstations    (2)
				}
		ACCESS  read-write
		STATUS  mandatory
		DESCRIPTION
			"Workstations-only status of the port; if this is
			limited, the port only has workstations on it, and
			broadcast frames received on this port will not be
			transmitted on other limited ports."
		::= { ringswitchFwdPortEntry 3 }
	ringswitchFwdPortCutThruEnable OBJECT-TYPE
		SYNTAX  INTEGER {
				enable          (1),
				disable         (2)
				}
		ACCESS  read-write
		STATUS  mandatory
		DESCRIPTION
			"Enables or disables cut-through switching on the
			port. In some circumstances (e.g., 4 to 16 MB
			switching), cut-through will always be disabled,
			irrespective of the state of this variable."
		::= { ringswitchFwdPortEntry 4 }
	ringswitchFwdPortSpecInFrames OBJECT-TYPE
		SYNTAX  INTEGER48
		ACCESS  read-only
		STATUS  mandatory
		DESCRIPTION
			"48 bit version of the Bridge MIB counter
			srPortSpecInFrames."
		::= { ringswitchFwdPortEntry 5 }
	ringswitchFwdPortSpecOutFrames OBJECT-TYPE
		SYNTAX  INTEGER48
		ACCESS  read-only
		STATUS  mandatory
		DESCRIPTION
			"48 bit version of the Bridge MIB counter
			srPortSpecOutFrames."
		::= { ringswitchFwdPortEntry 6 }
	ringswitchFwdPortApeInFrames OBJECT-TYPE
		SYNTAX  INTEGER48
		ACCESS  read-only
		STATUS  mandatory
		DESCRIPTION
			"48 bit version of the Bridge MIB counter
			srPortApeInFrames."
		::= { ringswitchFwdPortEntry 7 }
	ringswitchFwdPortApeOutFrames OBJECT-TYPE
		SYNTAX  INTEGER48
		ACCESS  read-only
		STATUS  mandatory
		DESCRIPTION
			"48 bit version of the Bridge MIB counter
			srPortApeOutFrames."
		::= { ringswitchFwdPortEntry 8 }
	ringswitchFwdPortSteInFrames OBJECT-TYPE
		SYNTAX  INTEGER48
		ACCESS  read-only
		STATUS  mandatory
		DESCRIPTION
			"48 bit version of the Bridge MIB counter
			srPortSteInFrames."
		::= { ringswitchFwdPortEntry 9 }
	ringswitchFwdPortSteOutFrames OBJECT-TYPE
		SYNTAX  INTEGER48
		ACCESS  read-only
		STATUS  mandatory
		DESCRIPTION
			"48 bit version of the Bridge MIB counter
			srPortSteOutFrames."
		::= { ringswitchFwdPortEntry 10 }
	ringswitchFwdPortTransparentInFrames OBJECT-TYPE
		SYNTAX  INTEGER48
		ACCESS  read-only
		STATUS  mandatory
		DESCRIPTION
			"48 bit version of the Bridge MIB counter
			TpPortInFrames."
		::= { ringswitchFwdPortEntry 11 }
	ringswitchFwdPortTransparentOutFrames OBJECT-TYPE
		SYNTAX  INTEGER48
		ACCESS  read-only
		STATUS  mandatory
		DESCRIPTION
			"48 bit version of the Bridge MIB counter
			TpPortOutFrames."
		::= { ringswitchFwdPortEntry 12 }
	ringswitchFwdPortTransparentDiscFrames OBJECT-TYPE
		SYNTAX  INTEGER48
		ACCESS  read-only
		STATUS  mandatory
		DESCRIPTION
			"48 bit version of the Bridge MIB counter
			TpPortInDiscards."
		::= { ringswitchFwdPortEntry 13 }
	ringswitchFwdPortTestState OBJECT-TYPE
		SYNTAX  INTEGER {
				disabled        (1),
				running         (2),
				failed          (3),
				ok              (4),
				unknown         (5),
				ok-use-spt      (6)
				}
		ACCESS  read-only
		STATUS  mandatory
		DESCRIPTION
			"Current state of the bridge test."
		::= { ringswitchFwdPortEntry 14 }
	ringswitchFwdPortTestError OBJECT-TYPE
		SYNTAX  INTEGER {
				no-error        (1),
				same-ring       (2),
				duplicate-ring  (3),
				fail-nb         (4),
				bad-rnum        (5),
				fail-b          (6)
				}
		ACCESS  read-only
		STATUS  mandatory
		DESCRIPTION
			"Result of the bridge test."
		::= { ringswitchFwdPortEntry 15 }
	ringswitchFwdPortTestPhase OBJECT-TYPE
		SYNTAX  INTEGER {
				not-running     (1),
				same-ring       (2),
				routed          (3),
				broadcast       (4),
				success         (5)
				}
		ACCESS  read-only
		STATUS  mandatory
		DESCRIPTION
			"Current phase of the bridge test."
		::= { ringswitchFwdPortEntry 16 }
	ringswitchFwdPortTbForce OBJECT-TYPE
		SYNTAX  INTEGER {
				enable          (1),
				disable         (2)
				}
		ACCESS  read-write
		STATUS  mandatory
		DESCRIPTION
			"If this variable is set to enable, transparent
			forwarding will be enabled, regardless of the
			spanning tree state machine."
		::= { ringswitchFwdPortEntry 17 }
	ringswitchFwdPortStpMaster OBJECT-TYPE
		SYNTAX  INTEGER
		ACCESS  read-write
		STATUS  mandatory
		DESCRIPTION
			"If this variable is non-zero, it is the interface
			number of another port, and the spanning tree state
			machine will be slaved to that port. A port may not
			be slaved to itself, to any other slaved port, or
			to a port where transparent bridging is forced (see
			description of ringswitchFwdPortTbForce)."
		::= { ringswitchFwdPortEntry 18 }
	ringswitchFwdPortTbState OBJECT-TYPE
		SYNTAX  INTEGER {
				disabled        (1),
				blocking        (2),
				listening       (3),
				learning        (4),
				forwarding      (5),
				broken          (6)
				}
		ACCESS  read-only
		STATUS  mandatory
		DESCRIPTION
			"The current transparent bridging state."
		::= { ringswitchFwdPortEntry 19 }
	ringswitchFwdPortSteState OBJECT-TYPE
		SYNTAX  INTEGER {
				enabled         (1),
				disabled        (2)
				}
		ACCESS  read-only
		STATUS  mandatory
		DESCRIPTION
			"The current spanning tree explorer propagation
			state."
		::= { ringswitchFwdPortEntry 20 }
	ringswitchFwdPortTbUnicastInFrames OBJECT-TYPE
		SYNTAX  INTEGER48
		ACCESS  read-only
		STATUS  mandatory
		DESCRIPTION
			"The number of unicast frames received by this port
			and transparently forwarded to another port."
		::= { ringswitchFwdPortEntry 21 }
	ringswitchFwdPortTbUnicastOutFrames OBJECT-TYPE
		SYNTAX  INTEGER48
		ACCESS  read-only
		STATUS  mandatory
		DESCRIPTION
			"The number of unicast frames transmitted by this port
			having been transparently forwarded from another
			port."
		::= { ringswitchFwdPortEntry 22 }
	ringswitchFwdPortTbBroadcastInFrames OBJECT-TYPE
		SYNTAX  INTEGER48
		ACCESS  read-only
		STATUS  mandatory
		DESCRIPTION
			"The number of broadcast frames received by this port
			and transparently forwarded to other ports."
		::= { ringswitchFwdPortEntry 23 }
	ringswitchFwdPortTbBroadcastOutFrames OBJECT-TYPE
		SYNTAX  INTEGER48
		ACCESS  read-only
		STATUS  mandatory
		DESCRIPTION
			"The number of broadcast frames transmitted by this
			port having been transparently forwarded from another
			port."
		::= { ringswitchFwdPortEntry 24 }
	ringswitchFwdPortTbMulticastInFrames OBJECT-TYPE
		SYNTAX  INTEGER48
		ACCESS  read-only
		STATUS  mandatory
		DESCRIPTION
			"The number of multicast frames received by this port
			and transparently forwarded to other ports."
		::= { ringswitchFwdPortEntry 25 }
	ringswitchFwdPortTbMulticastOutFrames OBJECT-TYPE
		SYNTAX  INTEGER48
		ACCESS  read-only
		STATUS  mandatory
		DESCRIPTION
			"The number of multicast frames transmitted by this
			port having been transparently forwarded from another
			port."
		::= { ringswitchFwdPortEntry 26 }
	ringswitchFwdPortTbMiscInFrames OBJECT-TYPE
		SYNTAX  INTEGER48
		ACCESS  read-only
		STATUS  mandatory
		DESCRIPTION
			"The number of unicast frames received by this port
			and transparently forwarded (flooded) to other ports."
		::= { ringswitchFwdPortEntry 27 }
	ringswitchFwdPortTbMiscOutFrames OBJECT-TYPE
		SYNTAX  INTEGER48
		ACCESS  read-only
		STATUS  mandatory
		DESCRIPTION
			"The number of unicast frames transmitted by this
			port having been transparently forwarded (flooded) 
			from another port."
		::= { ringswitchFwdPortEntry 28 }
	ringswitchFwdPortMatrixSrSpecFrames OBJECT-TYPE
		SYNTAX  OCTET STRING
		ACCESS  read-only
		STATUS  mandatory
		DESCRIPTION
			"This string contains a count of the specifically
			routed frames that have been switched from port
			ringswitchFwdPortNum to each of the possible
			ports on the ringswitch.
			The string contains one four byte entry (MSB first)
			per port."
		::= { ringswitchFwdPortEntry 29 }
	ringswitchFwdPortMatrixTbUniFrames OBJECT-TYPE
		SYNTAX  OCTET STRING
		ACCESS  read-only
		STATUS  mandatory
		DESCRIPTION
			"This string contains a count of the transparent
			unicast frames that have been switched from port
			ringswitchFwdPortNum to each of the possible
			ports on the ringswitch.
			The string contains one four byte entry (MSB first)
			per port."
		::= { ringswitchFwdPortEntry 30 }
	ringswitchFwdPortEthernetSRBlk OBJECT-TYPE
		SYNTAX  INTEGER {
				enabled         (1),
				disabled        (2)
				}
		ACCESS  read-write
		STATUS  mandatory
		DESCRIPTION
			"If this variable is enabled, on an Ethernet LEC 
			port, then the switch will treat any SR frame (STE, 
			ARE or SRF) going to or from this port as an STE for 
			the purposes of deciding whether to forward it or 
			block it.  If it is disabled then the normal SR rules 
			apply.  It is ignored for non Ethernet-LEC ports."
		::= { ringswitchFwdPortEntry 31 }
       ringswitchFwdPortAutoPathCost OBJECT-TYPE
	       SYNTAX   INTEGER {
				enabled         (1),
				disabled        (2)
				}
	       ACCESS   read-write
	       STATUS   mandatory
	       DESCRIPTION
		       "If this variable is enabled on a switch running
		       microcode >= R3.3 then the spanning tree cost for
		       this port will be selected automatically."
		::= { ringswitchFwdPortEntry 32 }
       ringswitchFwdPortBroadcastReflect OBJECT-TYPE
	       SYNTAX   INTEGER {
				enabled         (1),
				disabled        (2)
				}
	       ACCESS   read-write
	       STATUS   mandatory
	       DESCRIPTION
                      "If this variable is enabled on a switch running
                       microcode >= v4.08.01 then, on a DTR link, broadcast
                       frames will be reflected back to the node."
		::= { ringswitchFwdPortEntry 33 }
-- Global forwarding counters
	ringswitchFwdTotalRxFrames OBJECT-TYPE
		SYNTAX  INTEGER48
		ACCESS  read-only
		STATUS  mandatory
		DESCRIPTION
			"The total number of received frames switched."
		::= { ringswitchFwd 4 }
	ringswitchFwdTotalTxFrames OBJECT-TYPE
		SYNTAX  INTEGER48
		ACCESS  read-only
		STATUS  mandatory
		DESCRIPTION
			"The total number of transmitted frames switched."
		::= { ringswitchFwd 5 }
	ringswitchFwdBridgeNum OBJECT-TYPE
		SYNTAX  INTEGER (0..15)
		ACCESS  read-only
		STATUS  mandatory
		DESCRIPTION
			"The global bridge number of the Ringswitch."
		::= { ringswitchFwd 6 }
	ringswitchFwdTbForced OBJECT-TYPE
		SYNTAX  OCTET STRING
		ACCESS  read-only
		STATUS  mandatory
		DESCRIPTION
			"An octet string containing the transparent
			force state of every port on the Ringswitch. See
			the description of ringswitchFwdPortTbForce for
			details."
		::= { ringswitchFwd 7 }
	ringswitchFwdStpMasters OBJECT-TYPE
		SYNTAX  OCTET STRING
		ACCESS  read-only
		STATUS  mandatory
		DESCRIPTION
			"An octet string containing one octet for each
			port on the Ringswitch. If an octet is non-zero,
			it is the interface number of another port, and
			the spanning tree state machine is slaved to that
			port. See description of ringswitchFwdPortStpMaster
			for details."
		::= { ringswitchFwd 8 }
	ringswitchFwdGlobalHopLimit OBJECT-TYPE
		SYNTAX  INTEGER (1..13)
		ACCESS  read-only
		STATUS  mandatory
		DESCRIPTION
			"The maximum number of source routing hops that
			the Ringswitch will forward on any port. This limit
			is applied to all types of source route frame
			including all routes explorer frames where it
			modifies the port hop count limits defined by
			dot1dSrPortHopCount."
		::= { ringswitchFwd 9 }
	ringswitchFwdTotalBadFrames OBJECT-TYPE
		SYNTAX  INTEGER48
		ACCESS  read-only
		STATUS  mandatory
		DESCRIPTION
			"The total number of incoming frames discarded 
			because of some error. This is the sum of the
			SR bridge error counters and CRC errors."
		::= { ringswitchFwd 10 }
	ringswitchFwdTotalSpecInFrames OBJECT-TYPE
		SYNTAX  INTEGER48
		ACCESS  read-only
		STATUS  mandatory
		DESCRIPTION
			"This is the sum of the dot1dSrPortSpecInFrames
			counter."
		::= { ringswitchFwd 11 }
	ringswitchFwdTotalSpecOutFrames OBJECT-TYPE
		SYNTAX  INTEGER48
		ACCESS  read-only
		STATUS  mandatory
		DESCRIPTION
			"This is the sum of the dot1dSrPortSpecOutFrames
			counter."
		::= { ringswitchFwd 12 }
	ringswitchFwdTotalApeInFrames OBJECT-TYPE
		SYNTAX  INTEGER48
		ACCESS  read-only
		STATUS  mandatory
		DESCRIPTION
			"This is the sum of the dot1dSrPortApeInFrames
			counter."
		::= { ringswitchFwd 13 }
	ringswitchFwdTotalApeOutFrames OBJECT-TYPE
		SYNTAX  INTEGER48
		ACCESS  read-only
		STATUS  mandatory
		DESCRIPTION
			"This is the sum of the dot1dSrPortApeOutFrames
			counter."
		::= { ringswitchFwd 14 }
	ringswitchFwdTotalSteInFrames OBJECT-TYPE
		SYNTAX  INTEGER48
		ACCESS  read-only
		STATUS  mandatory
		DESCRIPTION
			"This is the sum of the dot1dSrPortSteInFrames
			counter."
		::= { ringswitchFwd 15 }
	ringswitchFwdTotalSteOutFrames OBJECT-TYPE
		SYNTAX  INTEGER48
		ACCESS  read-only
		STATUS  mandatory
		DESCRIPTION
			"This is the sum of the dot1dSrPortSteOutFrames
			counter."
		::= { ringswitchFwd 16 }
	ringswitchFwdTotalTransparentInFrames OBJECT-TYPE
		SYNTAX  INTEGER48
		ACCESS  read-only
		STATUS  mandatory
		DESCRIPTION
			"This is the sum of the
			TpPortInFrames counter."
		::= { ringswitchFwd 17 }
	ringswitchFwdTotalTransparentOutFrames OBJECT-TYPE
		SYNTAX  INTEGER48
		ACCESS  read-only
		STATUS  mandatory
		DESCRIPTION
			"This is the sum of the
			TpPortOutFrames counter."
		::= { ringswitchFwd 18 }
	ringswitchFwdTotalTpUnicastInFrames OBJECT-TYPE
		SYNTAX  INTEGER48
		ACCESS  read-only
		STATUS  mandatory
		DESCRIPTION
			"This is the sum of the
			ringswitchFwdPortTbUnicastInFrames counter."
		::= { ringswitchFwd 19 }
	ringswitchFwdTotalTpUnicastOutFrames OBJECT-TYPE
		SYNTAX  INTEGER48
		ACCESS  read-only
		STATUS  mandatory
		DESCRIPTION
			"This is the sum of the
			ringswitchFwdPortTbUnicastOutFrames counter."
		::= { ringswitchFwd 20 }
	ringswitchFwdTotalTpBroadcastInFrames OBJECT-TYPE
		SYNTAX  INTEGER48
		ACCESS  read-only
		STATUS  mandatory
		DESCRIPTION
			"This is the sum of the
			ringswitchFwdPortTbBroadcastInFrames counter."
		::= { ringswitchFwd 21 }
	ringswitchFwdTotalTpBroadcastOutFrames OBJECT-TYPE
		SYNTAX  INTEGER48
		ACCESS  read-only
		STATUS  mandatory
		DESCRIPTION
			"This is the sum of the
			ringswitchFwdPortTbBroadcastOutFrames counter."
		::= { ringswitchFwd 22 }
	ringswitchFwdTotalTpMulticastInFrames OBJECT-TYPE
		SYNTAX  INTEGER48
		ACCESS  read-only
		STATUS  mandatory
		DESCRIPTION
			"This is the sum of the
			ringswitchFwdPortTbMulticastInFrames counter."
		::= { ringswitchFwd 23 }
	ringswitchFwdTotalTpMulticastOutFrames OBJECT-TYPE
		SYNTAX  INTEGER48
		ACCESS  read-only
		STATUS  mandatory
		DESCRIPTION
			"This is the sum of the
			ringswitchFwdPortTbMulticastOutFrames counter."
		::= { ringswitchFwd 24 }
	ringswitchFwdTotalTpMiscInFrames OBJECT-TYPE
		SYNTAX  INTEGER48
		ACCESS  read-only
		STATUS  mandatory
		DESCRIPTION
			"This is the sum of the
			ringswitchFwdPortTbMiscInFrames counter."
		::= { ringswitchFwd 25 }
	ringswitchFwdTotalTpMiscOutFrames OBJECT-TYPE
		SYNTAX  INTEGER48
		ACCESS  read-only
		STATUS  mandatory
		DESCRIPTION
			"This is the sum of the
			ringswitchFwdPortTbMiscOutFrames counter."
		::= { ringswitchFwd 26 }
	ringswitchFwdMaxFrameSize OBJECT-TYPE
		SYNTAX INTEGER {
				use18K-frames      (1),
				use4500-frames     (2)
			       }
		ACCESS  read-write
		STATUS  mandatory
		DESCRIPTION
			"Maximum frame size the switch will forward."
		::= { ringswitchFwd 27 }
----------------------------------------------------------------------------
-- the ringswitchLCD group
	-- LCDText is a 50 byte octet string, containing the first line of
	-- the LCD (24 bytes), a carriage return (1 byte), the second line
	-- of the LCD (24 bytes) and a null character (1 byte).
	LCDText ::= OCTET STRING (SIZE (50))
	ringswitchLCDTotalDisplays OBJECT-TYPE
		SYNTAX  INTEGER (1..65535)
		ACCESS  read-only
		STATUS  mandatory
		DESCRIPTION
			"The total number of displays on the Ringswitch."
		::= { ringswitchLCD 1 }
	ringswitchLCDCurrentDisplay OBJECT-TYPE
		SYNTAX  INTEGER (1..65535)
		ACCESS  read-write
		STATUS  mandatory
		DESCRIPTION
			"The number of the display that the Ringswitch is
			currently showing."
		::= { ringswitchLCD 2 }
	ringswitchLCDCurrentMsgText OBJECT-TYPE
		SYNTAX  LCDText
		ACCESS  read-only
		STATUS  mandatory
		DESCRIPTION
			"The actual lcd message text, including a carriage
			return after the first line, and a null character
			after the second line."
		::= { ringswitchLCD 3 }
	ringswitchLCDTable OBJECT-TYPE
		SYNTAX  SEQUENCE OF RingswitchLCDTableEntry
		ACCESS  not-accessible
		STATUS  mandatory
		DESCRIPTION
			"A table that contains all of the lcd messages that
			could be displayed by the Ringswitch if the user
			were to flick the paddle switch."
		::= { ringswitchLCD 4 }
	ringswitchLCDTableEntry OBJECT-TYPE
		SYNTAX  RingswitchLCDTableEntry
		ACCESS  not-accessible
		STATUS  mandatory
		DESCRIPTION
			"Arguments and message number details for each
			LCD entry."
		INDEX { ringswitchLCDNum }
		::= { ringswitchLCDTable 1 }
	RingswitchLCDTableEntry ::=
		SEQUENCE        {
				ringswitchLCDNum
					INTEGER,
				ringswitchLCDMsgText
					LCDText,
				ringswitchLCDUp
					INTEGER,
				ringswitchLCDDown
					INTEGER
				}
	ringswitchLCDNum OBJECT-TYPE
		SYNTAX  INTEGER (1..65535)
		ACCESS  read-only
		STATUS  mandatory
		DESCRIPTION
			"The lcd number of the lcd for which this entry
			contains display details."
		::= { ringswitchLCDTableEntry 1 }
	ringswitchLCDMsgText OBJECT-TYPE
		SYNTAX  LCDText
		ACCESS  read-only
		STATUS  mandatory
		DESCRIPTION
			"The actual lcd message text, including a carriage
			return after the first line, and a null character
			after the second line."
		::= { ringswitchLCDTableEntry 2 }
	ringswitchLCDUp OBJECT-TYPE
		SYNTAX  INTEGER (1..65535)
		ACCESS  read-only
		STATUS  mandatory
		DESCRIPTION
			"The lcd number of the lcd which would be displayed
			if the user clicked the paddle up."
		::= { ringswitchLCDTableEntry 3 }
	ringswitchLCDDown OBJECT-TYPE
		SYNTAX  INTEGER (1..65535)
		ACCESS  read-only
		STATUS  mandatory
		DESCRIPTION
			"The lcd number of the lcd which would be displayed
			if the user clicked the paddle down."
		::= { ringswitchLCDTableEntry 4 }
----------------------------------------------------------------------------
-- the ringswitchLAN group
	ringswitchLANTable OBJECT-TYPE
		SYNTAX  SEQUENCE OF RingswitchLANEntry
		ACCESS  not-accessible
		STATUS  mandatory
		DESCRIPTION
			"A table that contains virtual LAN information
			configured into the Ringswitch by the network
			administrator."
		::= { ringswitchLAN 1 }
	ringswitchLANEntry OBJECT-TYPE
		SYNTAX  RingswitchLANEntry
		ACCESS  not-accessible
		STATUS  mandatory
		DESCRIPTION
			"Name and status information associated with each
			virtual LAN entry."
		INDEX { ringswitchLANIndex }
		::= { ringswitchLANTable 1 }
	RingswitchLANEntry ::=
		SEQUENCE        {
				ringswitchLANIndex
					INTEGER,
				ringswitchLANName
					DisplayString,
				ringswitchLANPermeable
					INTEGER,
				ringswitchLANStatus
					INTEGER
				}
	ringswitchLANIndex OBJECT-TYPE
		SYNTAX  INTEGER (1..65535)
		ACCESS  read-only
		STATUS  mandatory
		DESCRIPTION
			"The virtual LAN number for which this entry
			contains virtual LAN details."
		::= { ringswitchLANEntry 1 }
	ringswitchLANName OBJECT-TYPE
		SYNTAX  DisplayString
		ACCESS  read-write
		STATUS  mandatory
		DESCRIPTION
			"The name that the administrator has given this
			virtual LAN."
		::= { ringswitchLANEntry 2 }
	ringswitchLANPermeable OBJECT-TYPE
		SYNTAX  INTEGER {
				impermeable     (1),
				permeable       (2)
				}
		ACCESS  read-write
		STATUS  mandatory
		DESCRIPTION
			"In an 'impermeable' group, broadcast frames which
			were received on a port in the group, but were not
			originated in the group, are discarded.  In a
			'permeable' group, such frames are transmitted on
			the other ports in the group."
		::= { ringswitchLANEntry 3 }
	ringswitchLANStatus OBJECT-TYPE
		SYNTAX  INTEGER {
				valid   (1),
				invalid (2)
				}
		ACCESS  read-write
		STATUS  mandatory
		DESCRIPTION
			"The current status of this virtual LAN, a status of
			'invalid' indicates that the virtual LAN's associated
			name and ring list are meaningless until the group is
			validated."
		::= { ringswitchLANEntry 4 }
	ringswitchLANRingTable OBJECT-TYPE
		SYNTAX  SEQUENCE OF RingswitchLANRingEntry
		ACCESS  not-accessible
		STATUS  mandatory
		DESCRIPTION
			"A table that contains the rings associated with
			a virtual LAN that has been configured into the
			Ringswitch by the network administrator."
		::= { ringswitchLAN 2 }
	ringswitchLANRingEntry OBJECT-TYPE
		SYNTAX  RingswitchLANRingEntry
		ACCESS  not-accessible
		STATUS  mandatory
		DESCRIPTION
			"Name and status information associated with each
			virtual LAN ring table entry."
		INDEX { ringswitchLANRingGroup, ringswitchLANRingIndex }
		::= { ringswitchLANRingTable 1 }
	RingswitchLANRingEntry ::=
		SEQUENCE        {
				ringswitchLANRingGroup
					INTEGER,
				ringswitchLANRingIndex
					INTEGER,
				ringswitchLANRingNum
					INTEGER,
				ringswitchLANRingStatus
					INTEGER
				}
	ringswitchLANRingGroup OBJECT-TYPE
		SYNTAX  INTEGER
		ACCESS  read-only
		STATUS  mandatory
		DESCRIPTION
			"The virtual LAN index for which this entry
			contains virtual LAN ring details."
		::= { ringswitchLANRingEntry 1 }
	ringswitchLANRingIndex OBJECT-TYPE
		SYNTAX  INTEGER
		ACCESS  read-only
		STATUS  mandatory
		DESCRIPTION
			"The ring index for which this entry
			contains virtual LAN ring details."
		::= { ringswitchLANRingEntry 2 }
	ringswitchLANRingNum OBJECT-TYPE
		SYNTAX  INTEGER
		ACCESS  read-write
		STATUS  mandatory
		DESCRIPTION
			"The ring number contained in the virtual LAN."
		::= { ringswitchLANRingEntry 3 }
	ringswitchLANRingStatus OBJECT-TYPE
		SYNTAX  INTEGER {
				valid           (1),
				invalid         (2)
				}
		ACCESS  read-write
		STATUS  mandatory
		DESCRIPTION
			"The current status of this virtual LAN ring entry,
			a status of 'invalid' indicates that the ring entry
			is not in use and the associated ring number is
			meaningless."
		::= { ringswitchLANRingEntry 4 }
----------------------------------------------------------------------------
-- the ringswitchVirt group
	ringswitchVirtTB OBJECT IDENTIFIER ::= { ringswitchVirt 1 }
-- the ringswitchVirtTB group
	ringswitchVirtTBTable OBJECT-TYPE
		SYNTAX  SEQUENCE OF RingswitchVirtTBEntry
		ACCESS  not-accessible
		STATUS  mandatory
		DESCRIPTION
			"A table that contains virtual LAN information
			configured into the Ringswitch by the network
			administrator."
		::= { ringswitchVirtTB 1 }
	ringswitchVirtTBEntry OBJECT-TYPE
		SYNTAX  RingswitchVirtTBEntry
		ACCESS  not-accessible
		STATUS  mandatory
		DESCRIPTION
			"Name and status information associated with each
			virtual LAN entry."
		INDEX { ringswitchVirtTBIndex }
		::= { ringswitchVirtTBTable 1 }
	RingswitchVirtTBEntry ::=
		SEQUENCE        {
				ringswitchVirtTBIndex
					INTEGER,
				ringswitchVirtTBStatus
					RingswitchRowStatus,
				ringswitchVirtTBName
					DisplayString,
				ringswitchVirtTBType
					INTEGER,
				ringswitchVirtTBNumArray
					OCTET STRING,
				ringswitchVirtTBNumSize
					INTEGER
				}
	ringswitchVirtTBIndex OBJECT-TYPE
		SYNTAX  INTEGER (1..31)
		ACCESS  read-only
		STATUS  mandatory
		DESCRIPTION
			"The virtual LAN number for which this entry
			contains virtual LAN details."
		::= { ringswitchVirtTBEntry 1 }
	ringswitchVirtTBStatus OBJECT-TYPE
		SYNTAX  RingswitchRowStatus
		ACCESS  read-write
		STATUS  mandatory
		DESCRIPTION
			"The current status of this virtual LAN, a status of
			'invalid' indicates that the virtual LAN's associated
			name and ring list are meaningless until the group is
			validated; see RingswitchRowStatus comments above."
		::= { ringswitchVirtTBEntry 2 }
	ringswitchVirtTBName OBJECT-TYPE
		SYNTAX  DisplayString
		ACCESS  read-write
		STATUS  mandatory
		DESCRIPTION
			"The name that the administrator has given this
			virtual LAN."
		::= { ringswitchVirtTBEntry 3 }
	ringswitchVirtTBType OBJECT-TYPE
		SYNTAX  INTEGER {
				port-only       (1)
				}
		ACCESS  read-write
		STATUS  mandatory
		DESCRIPTION
			"The type of this virtual LAN."
		::= { ringswitchVirtTBEntry 4 }
	ringswitchVirtTBNumArray OBJECT-TYPE
		SYNTAX  OCTET STRING
		ACCESS  read-write
		STATUS  mandatory
		DESCRIPTION
			"An octet string containing every port number in
			this virtual LAN, one per octet."
		::= { ringswitchVirtTBEntry 5 }
	ringswitchVirtTBNumSize OBJECT-TYPE
		SYNTAX  INTEGER
		ACCESS  read-only
		STATUS  mandatory
		DESCRIPTION
			"The number of ports in this virtual LAN."
		::= { ringswitchVirtTBEntry 6 }
----------------------------------------------------------------------------
-- the Slot group
	ringswitchSlotNumSlots OBJECT-TYPE
		SYNTAX  INTEGER
		ACCESS  read-only
		STATUS  mandatory
		DESCRIPTION
			"The number of slots available in this Ringswitch."
		::= { ringswitchSlot 1 }
	ringswitchSlotTable OBJECT-TYPE
		SYNTAX  SEQUENCE OF RingswitchSlotEntry
		ACCESS  not-accessible
		STATUS  mandatory
		DESCRIPTION
			"A table that contains information about each slot
			in the Ringswitch."
		::= { ringswitchSlot 2 }
	ringswitchSlotEntry OBJECT-TYPE
		SYNTAX  RingswitchSlotEntry
		ACCESS  not-accessible
		STATUS  mandatory
		DESCRIPTION ""
		INDEX { ringswitchSlotIndex }
		::= { ringswitchSlotTable 1 }
	RingswitchSlotEntry ::=
		SEQUENCE        {
				ringswitchSlotIndex           INTEGER,
				ringswitchSlotStatus          INTEGER,
				ringswitchSlotBasePort        INTEGER,
				ringswitchSlotCardType        INTEGER,
				ringswitchSlotCardId          INTEGER,
				ringswitchSlotCardRevision    INTEGER,
				ringswitchSlotCardDescription DisplayString,
				ringswitchSlotCardNumPorts    INTEGER,
				ringswitchSlotCardLAN         INTEGER,
				ringswitchSlotCardLEDs        OCTET STRING,
				ringswitchSlotIfAdminStatus   OCTET STRING,
				ringswitchSlotAdapterStatus   OCTET STRING,
				ringswitchSlotTestError       OCTET STRING,
				ringswitchSlotPortHealth      OCTET STRING,
				ringswitchSlotLastStatus      INTEGER,
				ringswitchSlotPortCreated     OCTET STRING,
				ringswitchSlotHealth          INTEGER,
                                ringswitchSlotVersion         INTEGER
				}
	ringswitchSlotIndex OBJECT-TYPE
		SYNTAX  INTEGER (1..65535)
		ACCESS  read-only
		STATUS  mandatory
		DESCRIPTION
			"The value of this object identifies the slot
			for which this entry contains management
			information."
		::= { ringswitchSlotEntry 1 }
	ringswitchSlotStatus OBJECT-TYPE
		SYNTAX  INTEGER {
				invalid         (1),
				full-support    (2),
				no-port-open    (3),
				no-port-fwd     (4)
				}
		ACCESS  read-only
		STATUS  mandatory
		DESCRIPTION
			"The value of this variable indicates whether or not
			this slot supports the card that is currently placed
			in it:
			invalid      - card not supported
			full-support - card fully supported
			no-port-open - cannot open ports on card
			no-port-fwd  - cannot forward frames."
		::= { ringswitchSlotEntry 2 }
	ringswitchSlotBasePort OBJECT-TYPE
		SYNTAX  INTEGER
		ACCESS  read-only
		STATUS  mandatory
		DESCRIPTION
			"The port number of the first port available
			in this slot."
		::= { ringswitchSlotEntry 3 }
	ringswitchSlotCardType OBJECT-TYPE
		SYNTAX  INTEGER {
				tr-copper-4        (1),
				tr-fiber-4         (2),
				fddi-fiber         (3),
				absent             (4),
				unknown            (5),
				tr-copper-8        (6),
				atm-fiber          (7),
				tr-fiber-8         (8),
				group-switch       (9),
				tr-copper-al-4     (10),
				tr-copper-hstr-2   (11),
				tr-copper-hstr-4   (12),
				tr-fiber-hstr-2    (13),
				tr-fiber-hstr-4    (14),
                                three-layer-switch (15),
				tr-copper-hstr-8   (16),
				tr-fiber-hstr-8    (17),
				ethernet           (18),
				gigabit-ethernet   (19)
				}
		ACCESS  read-only
		STATUS  mandatory
		DESCRIPTION
			"The type of card in this slot."
		::= { ringswitchSlotEntry 4 }
	ringswitchSlotCardId OBJECT-TYPE
		SYNTAX  INTEGER (0..255)
		ACCESS  read-only
		STATUS  mandatory
		DESCRIPTION
			"The hardware ID number for the card in this slot."
		::= { ringswitchSlotEntry 5 }
	ringswitchSlotCardRevision OBJECT-TYPE
		SYNTAX  INTEGER (0..255)
		ACCESS  read-only
		STATUS  mandatory
		DESCRIPTION
			"The hardware revision number for the card in this
			slot."
		::= { ringswitchSlotEntry 6 }
	ringswitchSlotCardDescription OBJECT-TYPE
		SYNTAX  DisplayString (SIZE (0..64))
		ACCESS  read-only
		STATUS  mandatory
		DESCRIPTION
			"A string containing a textual description for
			the card."
		::= { ringswitchSlotEntry 7 }
	ringswitchSlotCardNumPorts OBJECT-TYPE
		SYNTAX  INTEGER
		ACCESS  read-only
		STATUS  mandatory
		DESCRIPTION
			"The actual number of ports provided by this card
			when fully configured in this slot."
		::= { ringswitchSlotEntry 8 }
	ringswitchSlotCardLAN OBJECT-TYPE
		SYNTAX  INTEGER {
                                none            (1),
                                token-ring      (2),
                                fddi            (3),
                                atm             (4),
                                tls             (5),
                                ethernet        (6),
                                gigabit         (7)
				}
		ACCESS  read-only
		STATUS  mandatory
		DESCRIPTION
			"The type of LAN supported by the card in this slot."
		::= { ringswitchSlotEntry 9 }
	ringswitchSlotCardLEDs OBJECT-TYPE
		SYNTAX  OCTET STRING
		ACCESS  read-only
		STATUS  mandatory
		DESCRIPTION
			"An octet string containing the colour of every LED
			on the card, one per octet:
				off             	(1),
				on-red          	(2),
				on-green        	(3),
				on-yellow       	(4),
				flash-red       	(5),
				flash-green     	(6),
				flash-yellow    	(7),
				flash-blue      	(8),
				flash-green-anti-phase  (9),
				flash-yellow-anti-phase (10)"
		::= { ringswitchSlotEntry 10 }
	ringswitchSlotIfAdminStatus OBJECT-TYPE
		SYNTAX  OCTET STRING
		ACCESS  read-only
		STATUS  mandatory
		DESCRIPTION
			"An octet string containing the ifAdminStatus of
			every interface on the card, one per octet:
				up      (1),
				down    (2),
				testing (3)"
		::= { ringswitchSlotEntry 11 }
	ringswitchSlotAdapterStatus OBJECT-TYPE
		SYNTAX  OCTET STRING
		ACCESS  read-only
		STATUS  mandatory
		DESCRIPTION
			"An octet string containing the
			ringswitchGenPortAdapterStatus of every
			port on the card, one per octet:
				open    (1),
				closed  (2),
				opening (3)"
		::= { ringswitchSlotEntry 12 }
	ringswitchSlotTestError OBJECT-TYPE
		SYNTAX  OCTET STRING
		ACCESS  read-only
		STATUS  mandatory
		DESCRIPTION
			"An octet string containing the
			ringswitchFwdPortTestError of every
			port on the card, one per octet:
				no-error        (1),
				same-ring       (2),
				duplicate-ring  (3),
				fail-nb         (4),
				bad-rnum        (5),
				fail-b          (6)"
		::= { ringswitchSlotEntry 13 }
	ringswitchSlotPortHealth OBJECT-TYPE
		SYNTAX  OCTET STRING
		ACCESS  read-only
		STATUS  mandatory
		DESCRIPTION
			"An octet string containing the health of every
			port on the card, one per octet:
				normal          (1),
				warning         (2),
				degraded        (3),
				critical        (4)"
		::= { ringswitchSlotEntry 14 }
	ringswitchSlotLastStatus OBJECT-TYPE
		SYNTAX  INTEGER {
				atm-if-down     (1),
				atm-porta-down  (2),
				atm-portb-down  (3),
				fddi-if-down    (4),
				fddi-porta-iso  (5),
				fddi-portb-iso  (6)
				}
		ACCESS  read-only
		STATUS  mandatory
		DESCRIPTION
			"An enumerated value that records the last
			important event that occurred during
			the card's operation. This is used in
			sending traps when such events occur."
		::= { ringswitchSlotEntry 15 }
	ringswitchSlotPortCreated OBJECT-TYPE
		SYNTAX  OCTET STRING
		ACCESS  read-only
		STATUS  mandatory
		DESCRIPTION
			"An octet string containing the
			ringswitchGenPortCreate of every
			possible port on the card, one per octet:
				active          (1),
				inactive        (2)"
		::= { ringswitchSlotEntry 16 }
	ringswitchSlotHealth OBJECT-TYPE
		SYNTAX  INTEGER {
				normal   (1),
				warning  (2),
				degraded (3),
				critical (4)
				}
		ACCESS  read-only
		STATUS  mandatory
		DESCRIPTION
			"Current health of the card in the slot."
		::= { ringswitchSlotEntry 17 }
	ringswitchSlotVersion OBJECT-TYPE
		SYNTAX  INTEGER
		ACCESS  read-only
		STATUS  mandatory
		DESCRIPTION
                        "The version of code / hardware associated with
                         the slot."
		::= { ringswitchSlotEntry 18 }
----------------------------------------------------------------------------
-- the general port group
	ringswitchGenPortTable OBJECT-TYPE
		SYNTAX  SEQUENCE OF RingswitchGenPortEntry
		ACCESS  not-accessible
		STATUS  mandatory
		DESCRIPTION
			"A table that contains information applicable to all
			ports."
		::= { ringswitchGenPort 1 }
	ringswitchGenPortEntry OBJECT-TYPE
		SYNTAX  RingswitchGenPortEntry
		ACCESS  not-accessible
		STATUS  mandatory
		DESCRIPTION
			""
		INDEX { ringswitchGenPortNum }
		::= { ringswitchGenPortTable 1 }
	RingswitchGenPortEntry ::=
		SEQUENCE        {
				ringswitchGenPortNum
					INTEGER,
				ringswitchGenPortAdapterStatus
					INTEGER,
				ringswitchGenPortAddress
					TRNMacAddress,
				ringswitchGenPortLAA
					TRNMacAddress,
				ringswitchGenPortInOctets
					INTEGER48,
				ringswitchGenPortOutOctets
					INTEGER48,
				ringswitchGenPortResetCounters
					INTEGER,
				ringswitchGenPortRMONCapabilities
					INTEGER,
				ringswitchGenPortRMONMode
					INTEGER,
				ringswitchGenPortRMONSnoop
					TRNMacAddress,
				ringswitchGenPortIPXNet
					INTEGER,
				ringswitchGenPortLastStatus
					INTEGER,
				ringswitchGenPortCreate
					INTEGER,
				ringswitchGenPortHealth
					INTEGER
				}
	ringswitchGenPortNum OBJECT-TYPE
		SYNTAX  INTEGER (1..65535)
		ACCESS  read-only
		STATUS  mandatory
		DESCRIPTION
			"The port number of the port for which this entry
			contains Ringswitch management information."
		::= { ringswitchGenPortEntry 1 }
	ringswitchGenPortAdapterStatus OBJECT-TYPE
		SYNTAX  INTEGER {
				open    (1),
				closed  (2),
				opening (3),
				ready   (4)
				}
		ACCESS  read-only
		STATUS  mandatory
		DESCRIPTION
			"The status of the adapter used by this port."
		::= { ringswitchGenPortEntry 2 }
	ringswitchGenPortAddress OBJECT-TYPE
		SYNTAX  TRNMacAddress
		ACCESS  read-only
		STATUS  mandatory
		DESCRIPTION
			"The hard wired address of the port."
		::= { ringswitchGenPortEntry 3 }
	ringswitchGenPortLAA OBJECT-TYPE
		SYNTAX  TRNMacAddress
		ACCESS  read-write
		STATUS  mandatory
		DESCRIPTION
			"The locally administered address of the port."
		::= { ringswitchGenPortEntry 4 }
	ringswitchGenPortInOctets OBJECT-TYPE
		SYNTAX  INTEGER48
		ACCESS  read-only
		STATUS  mandatory
		DESCRIPTION
			"48 bit version of the interface MIB counter
			ifInOctets."
		::= { ringswitchGenPortEntry 5 }
	ringswitchGenPortOutOctets OBJECT-TYPE
		SYNTAX  INTEGER48
		ACCESS  read-only
		STATUS  mandatory
		DESCRIPTION
			"48 bit version of the interface MIB counter
			ifOutOctets."
		::= { ringswitchGenPortEntry 6 }
	ringswitchGenPortResetCounters OBJECT-TYPE
		SYNTAX  INTEGER {
				reset   (1)
				}
		ACCESS  read-write
		STATUS  mandatory
		DESCRIPTION
			"Use this variable to reset all the counters on
			this port, including those in the ringswitchGenPort,
			dot1dSRPort, ifEntry and fddimib groups."
		::= { ringswitchGenPortEntry 7 }
	ringswitchGenPortRMONCapabilities OBJECT-TYPE
		SYNTAX  INTEGER  {
				disabled      (1),
				economy       (2),
				standard      (3),
				snooping      (4)
				}
		ACCESS  read-only
		STATUS  mandatory
		DESCRIPTION
			"A value that indicates the RMON capabilities of the
			port. The value represents the highest level RMON
			mode which the port can support.
			   'disabled' is the lowest level and indicates
				      no RMON capabilities
			   'snooping' is the highest level and indicates
				      that the port is capable of
				      running in all RMON modes."
		::= { ringswitchGenPortEntry 8 }
	ringswitchGenPortRMONMode OBJECT-TYPE
		SYNTAX  INTEGER {
				disabled      (1),
				economy       (2),
				standard      (3),
				snooping      (4)
				}
		ACCESS  read-write
		STATUS  mandatory
		DESCRIPTION
			"Controls the types of frames passed to the RMON
			probe function for processing as follows:
			disabled - no frames passed to the RMON probe
			economy  - MAC frames required for token ring
				   specific groups as follows:
				   MLStats table
				   Token Ring Ring station table
			standard - all frames
			snooping - all frames provided by the 'economy'
				   mode plus any frames originating
				   from or destined for the 'snoop address'
				   controlled by ringswitchGenPortRMONSnoop"
		::= { ringswitchGenPortEntry 9 }
	ringswitchGenPortRMONSnoop OBJECT-TYPE
		SYNTAX  TRNMacAddress
		ACCESS  read-write
		STATUS  mandatory
		DESCRIPTION
			"This controls the RMON snoop address used when
			ringswitchGenPortRMONMode is set to 'snooping'.
			A value of all zeroes results in no snooping
			taking place."
		::= { ringswitchGenPortEntry 10 }
	ringswitchGenPortIPXNet OBJECT-TYPE
		SYNTAX  INTEGER
		ACCESS  read-only
		STATUS  mandatory
		DESCRIPTION
			"The IPX network number of the port."
		::= { ringswitchGenPortEntry 11 }
	ringswitchGenPortLastStatus OBJECT-TYPE
		SYNTAX  INTEGER {
				fddi-remove     (1),
				fddi-twisted    (2),
				fddi-bypass     (3)
				}
		ACCESS  read-only
		STATUS  mandatory
		DESCRIPTION
			"An enumerated value that records the last
			important event that occurred during the
			port's operation. This is used in sending
			traps when such events occur."
		::= { ringswitchGenPortEntry 12 }
	ringswitchGenPortCreate OBJECT-TYPE
		SYNTAX  INTEGER {
				active          (1),
				inactive        (2)
				}
		ACCESS  read-write
		STATUS  mandatory
		DESCRIPTION
			"This variable is used to dynamically create and
			destroy Ringswitch ports.
			When a port is active, all the mib table entries
			relevant to the type of port will be in existence.
			When a port is inactive no entry will exist for that
			port in the ringswitchGenPort table and no other port
			based mib table entries will exist for that port.
			To create a port the manager should issue a
			set request with a value of active which will
			result in an entry being created in the
			ringswitchGenPort table and all other port based
			tables relevant to the port.
			To destroy a port the manager should issue a set
			request with a value of inactive which will result
			in the deletion of the ringswitchGenPort table
			entry for the port and also the deletion of all
			other port based table entries associated with the
			port.
			Not all types of port can be created and destroyed
			dynamically."
		::= { ringswitchGenPortEntry 13 }
	ringswitchGenPortHealth OBJECT-TYPE
		SYNTAX INTEGER {
				normal   (1),
				warning  (2),
				degraded (3),
				critical (4)
				}
		ACCESS  read-only
		STATUS  mandatory
		DESCRIPTION
			"Current health of this port."
		::= { ringswitchGenPortEntry 14 }

----------------------------------------------------------------------------
-- the Ringswitch token ring group
	ringswitchTRIfTable OBJECT-TYPE
		SYNTAX  SEQUENCE OF RingswitchTRIfEntry
		ACCESS  not-accessible
		STATUS  mandatory
		DESCRIPTION
			"This table contains Token Ring interface
			parameters and state variables not available
			in dot5Table. There is one entry per 802.5
			interface."
		::= { ringswitchTR 1 }
	ringswitchTRIfEntry OBJECT-TYPE
		SYNTAX  RingswitchTRIfEntry
		ACCESS  not-accessible
		STATUS  mandatory
		DESCRIPTION
			"A list of Token Ring status and parameter
			values for an 802.5 interface."
		INDEX { ringswitchTRIfIndex }
		::= { ringswitchTRIfTable 1 }
	RingswitchTRIfEntry ::= 
                SEQUENCE        {
				ringswitchTRIfIndex                	 
                                      INTEGER,
				ringswitchTRIfRingSpeed            	 
                                      INTEGER,
				ringswitchTRIfMode                 	 
                                      INTEGER,
				ringswitchTRIfRPSEnable            	 
                                      INTEGER,
				ringswitchTRIfRingStatus           	 
                                      INTEGER,
				ringswitchTRIfSoftErrTimer         	 
                                      INTEGER,
				ringswitchTRIfFrameStatusControl   	 
                                      INTEGER,
				ringswitchTRIfTokenPriorityControl 	 
                                      INTEGER,
				ringswitchTRIfFastFailoverEnable   	 
                                      INTEGER,
				ringswitchTRIfFastFailoverStandbyStatus  
                                      INTEGER,
				ringswitchTRIfFastFailoverPrimaryPort    
                                      INTEGER,
				ringswitchTRIfFastFailoverTrapInfoReason 
                                      INTEGER				
				}
	ringswitchTRIfIndex OBJECT-TYPE
		SYNTAX  INTEGER
		ACCESS  read-only
		STATUS  mandatory
		DESCRIPTION
			"The value of this object identifies the
			802.5 interface for which this entry
			contains management information.  The
			value of this object for a particular
			interface has the same value as the
			ifIndex object for the same interface."
		::= { ringswitchTRIfEntry 1 }
	ringswitchTRIfRingSpeed OBJECT-TYPE
		SYNTAX  INTEGER {
				four    (1),
				sixteen (2),
				hundred (3)
				}
		ACCESS  read-write
		STATUS  mandatory
		DESCRIPTION
			"Speed of the ring to which this interface
			is connected."
		::= { ringswitchTRIfEntry 2 }
	ringswitchTRIfMode OBJECT-TYPE
		SYNTAX  INTEGER {
				node            (1),
				concentrator    (2),
				node-fdx        (3),
				conc-fdx        (4),
				node-classic    (5),
				conc-classic    (6),
				node-cau-rio    (7)
				}
		ACCESS  read-write
		STATUS  mandatory
		DESCRIPTION
			""
        ::= { ringswitchTRIfEntry 3 }
	ringswitchTRIfRPSEnable OBJECT-TYPE
		SYNTAX  INTEGER {
				enable          (1),
				disable         (2)
				}
		ACCESS  read-write
		STATUS  mandatory
		DESCRIPTION
			"Enables or disables the Ring Parameter Server
			function on the interface. If this variable is set to
			enabled, the interface will enable the RPS functional
			address, and respond to Request Parameters MAC
			frames, supplying the interface's segment number and
			soft error report timer value in the response."
		::= { ringswitchTRIfEntry 4 }
	ringswitchTRIfRingStatus OBJECT-TYPE
		SYNTAX  INTEGER {
				normal          (1),
				single          (2),
				beaconing       (3),
				normal-fdx      (4),
				dtr-wait        (5)
				}
		ACCESS  read-only
		STATUS  mandatory
		DESCRIPTION
			"The status of the ring to which this interface is
			connected.
			normal:     Inserted into Classic ring
			single:     Single Station
			beaconing:  Beaconing Detected
			normal-fdx: DTR link in full duplex (TXI) mode
			dtr-wait:   DTR Concentrator port waiting for
				    attached station to insert"
		::= { ringswitchTRIfEntry 5 }
	ringswitchTRIfSoftErrTimer OBJECT-TYPE
		SYNTAX  INTEGER (1..65535)
		ACCESS  read-write
		STATUS  mandatory
		DESCRIPTION
			"Sets the value of the Soft Error Timer Value used
			by the Ring Parameter Server function on this    
			interface. When this function is enabled it will
			respond to Request Parameters MAC frames, supplying 
			this value in the response as well as the segment
			number. Note that this value is in centiseconds."
		::= { ringswitchTRIfEntry 6 }
	ringswitchTRIfFrameStatusControl OBJECT-TYPE
		SYNTAX  INTEGER {
				enabled         (1),
				disabled        (2)
				}
		ACCESS  read-write
		STATUS  mandatory
		DESCRIPTION
			"Frame Status control is available on Aleutian
			based hardware. enabled (1); disabled(2)."
		::= { ringswitchTRIfEntry 7 }
	 ringswitchTRIfTokenPriorityControl OBJECT-TYPE
		SYNTAX  INTEGER {
				enabled         (1),
				disabled        (2)
				}
		ACCESS  read-write
		STATUS  mandatory
		DESCRIPTION
			"Frame Status control is available on Aleutian
			based hardware. enabled (1); disabled(2)."
		::= { ringswitchTRIfEntry 8 }
	 ringswitchTRIfFastFailoverEnable OBJECT-TYPE
		SYNTAX  INTEGER {
				enabled         (1),
				disabled        (2)
				}
		ACCESS  read-write
		STATUS  mandatory
		DESCRIPTION
			"Whether the port is a fast failover port. Only ports
			with odd port number on HSTR cards can be fast 
                        failover cards. On other ports this value is 
                        ignored. enabled (1); disabled(2)."
		::= { ringswitchTRIfEntry 9 }
	 ringswitchTRIfFastFailoverStandbyStatus OBJECT-TYPE
		SYNTAX  INTEGER {
				open	      (1),
				closed        (2),
				opening       (3),
				ready         (4),
				open-fail     (5)
				}
		ACCESS  read-only
		STATUS  mandatory
		DESCRIPTION
			"The status of the standby port in a fast failover 
                        pair. open (1); closed (2); opening (3); ready (4); 
                        open-fail(5)."
		::= { ringswitchTRIfEntry 10 }
	 ringswitchTRIfFastFailoverPrimaryPort OBJECT-TYPE
		SYNTAX  INTEGER {
				unknown         (0),
				left            (1),
				right           (2)
				}
		ACCESS  read-write
		STATUS  mandatory
		DESCRIPTION
			"The primary port in a fast failover pair. unknown (0);
			left (1); right (2)."
		::= { ringswitchTRIfEntry 11 }
	 ringswitchTRIfFastFailoverTrapInfoReason OBJECT-TYPE
		SYNTAX  INTEGER {
				primary-open-fail (1),
				standby-open-fail (2),
				links-swapped     (3)
				}
		ACCESS  not-accessible
		STATUS  mandatory
		DESCRIPTION
			"The reason why a fast failover trap was sent.
			primary-open-fail (1); standby-open-fail (2); 
                        links-swapped (3)"
		::= { ringswitchTRIfEntry 12 }



-- the Ringswitch token ring Group Switch group
	ringswitchTRGrpSwtchTable OBJECT-TYPE
		SYNTAX  SEQUENCE OF RingswitchTRGrpSwtchEntry
		ACCESS  not-accessible
		STATUS  mandatory
		DESCRIPTION
			"This table contains information relating to group 
                        switch rings (each containing five individual ports)."
		::= { ringswitchTR 2 }
	ringswitchTRGrpSwtchEntry OBJECT-TYPE
		SYNTAX  RingswitchTRGrpSwtchEntry
		ACCESS  not-accessible
		STATUS  mandatory
		DESCRIPTION
			"A list containing Group Switch ring information."
		INDEX { ringswitchTRGrpSwtchIfIndex }
		::= { ringswitchTRGrpSwtchTable 1 }
	RingswitchTRGrpSwtchEntry ::=
		SEQUENCE        {
				ringswitchTRGrpSwtchIfIndex
					INTEGER,
				ringswitchTRGrpSwtchRemoveThreshold
					INTEGER,
				ringswitchTRGrpSwtchRingPollAction
					INTEGER,
				ringswitchTRGrpSwtchBeaconThreshold
					INTEGER,
				ringswitchTRGrpSwtchBeaconAction
					INTEGER,
				ringswitchTRGrpSwtchPurgeThreshold
					INTEGER,
				ringswitchTRGrpSwtchPurgeAction
					INTEGER,
				ringswitchTRGrpSwtchIsoErrThreshold
					INTEGER,
				ringswitchTRGrpSwtchIsoErrAction
					INTEGER,
				ringswitchTRGrpSwtchRingPollThreshold
					INTEGER
				}
	ringswitchTRGrpSwtchIfIndex OBJECT-TYPE
		SYNTAX  INTEGER
		ACCESS  read-only
		STATUS  mandatory
		DESCRIPTION
			"The value of this object identifies the
			802.5 interface for which this entry
			contains management information.  The
			value of this object for a particular
			interface has the same value as the
			ifIndex object for the same interface."
		::= { ringswitchTRGrpSwtchEntry 1 }
	ringswitchTRGrpSwtchRemoveThreshold OBJECT-TYPE
		SYNTAX  INTEGER (1..255)
		ACCESS  read-write
		STATUS  mandatory
		DESCRIPTION
			"The removal threshold, this controls how many
			times a faulty but persistent node is allowed to
			attempt to insert into the ring before its port
			is permanently disabled."
		::= { ringswitchTRGrpSwtchEntry 2 }
	ringswitchTRGrpSwtchRingPollAction OBJECT-TYPE
		SYNTAX  INTEGER {
				ignore(1),
				inform(2),
				remove(3)
				}
		ACCESS  read-write
		STATUS  mandatory
		DESCRIPTION
			"Defines what happens when the group switch detects a
			ring poll failure."
		::= { ringswitchTRGrpSwtchEntry 3 }
	ringswitchTRGrpSwtchBeaconThreshold OBJECT-TYPE
		SYNTAX  INTEGER (1..255)
		ACCESS  read-write
		STATUS  mandatory
		DESCRIPTION
			"Number of successive beacon frames from one
			node before a problem is noticed."
		::= { ringswitchTRGrpSwtchEntry 4 }
	ringswitchTRGrpSwtchBeaconAction OBJECT-TYPE
		SYNTAX  INTEGER {
				ignore(1),
				inform(2),
				remove(3)
				}
		ACCESS  read-write
		STATUS  mandatory
		DESCRIPTION
			"Defines what happens when the group switch detects
			a succession of beacon frames from the same
			node."
		::= { ringswitchTRGrpSwtchEntry 5 }
	ringswitchTRGrpSwtchPurgeThreshold OBJECT-TYPE
		SYNTAX  INTEGER (1..255)
		ACCESS  read-write
		STATUS  mandatory
		DESCRIPTION
			"Number of successive ring purge frames from
			one node before a problem is noticed."
		::= { ringswitchTRGrpSwtchEntry 6 }
	ringswitchTRGrpSwtchPurgeAction OBJECT-TYPE
		SYNTAX  INTEGER {
				ignore(1),
				inform(2),
				remove(3)
				}
		ACCESS  read-write
		STATUS  mandatory
		DESCRIPTION
			"Defines what happens when the group switch detects a
			succession of ring purge frames from the same
			node."
		::= { ringswitchTRGrpSwtchEntry 7 }
	ringswitchTRGrpSwtchIsoErrThreshold OBJECT-TYPE
		SYNTAX  INTEGER (1..255)
		ACCESS  read-write
		STATUS  mandatory
		DESCRIPTION
			"Number of isolating errors before a problem
			is noticed."
		::= { ringswitchTRGrpSwtchEntry 8 }
	ringswitchTRGrpSwtchIsoErrAction OBJECT-TYPE
		SYNTAX  INTEGER {
				ignore(1),
				inform(2),
				remove(3)
				}
		ACCESS  read-write
		STATUS  mandatory
		DESCRIPTION
			"Defines what happens when the group switch detects
			too many isolating errors."
		::= { ringswitchTRGrpSwtchEntry 9 }
	ringswitchTRGrpSwtchRingPollThreshold OBJECT-TYPE
		SYNTAX  INTEGER (1..255)
		ACCESS  read-write
		STATUS  mandatory
		DESCRIPTION
			"Number of successive ring poll failures caused by one
			node before a problem is noticed."
		::= { ringswitchTRGrpSwtchEntry 10 }
-- the Ringswitch token ring group switch port group
	ringswitchTRGrpSwtchPortTable OBJECT-TYPE
		SYNTAX  SEQUENCE OF RingswitchTRGrpSwtchPortEntry
		ACCESS  not-accessible
		STATUS  mandatory
		DESCRIPTION
			"This table contains information relating to
			individual Group Switch ports."
		::= { ringswitchTR 3 }
	ringswitchTRGrpSwtchPortEntry OBJECT-TYPE
		SYNTAX  RingswitchTRGrpSwtchPortEntry
		ACCESS  not-accessible
		STATUS  mandatory
		DESCRIPTION
			"A list containing Group Switch port information."
		INDEX { ringswitchTRGrpSwtchPortIfIndex,
			ringswitchTRGrpSwtchPortIndex }
		::= { ringswitchTRGrpSwtchPortTable 1 }
	RingswitchTRGrpSwtchPortEntry
			::= SEQUENCE
				{
				ringswitchTRGrpSwtchPortIfIndex
					INTEGER,
				ringswitchTRGrpSwtchPortIndex
					INTEGER,
				ringswitchTRGrpSwtchPortAddress
					TRNMacAddress
				}
	ringswitchTRGrpSwtchPortIfIndex OBJECT-TYPE
		SYNTAX  INTEGER
		ACCESS  read-only
		STATUS  mandatory
		DESCRIPTION
			"The value of this object identifies the
			802.5 interface for which this entry
			contains management information.  The
			value of this object for a particular
			interface has the same value as the
			ifIndex object for the same interface."
		::= { ringswitchTRGrpSwtchPortEntry 1 }
	ringswitchTRGrpSwtchPortIndex OBJECT-TYPE
		SYNTAX  INTEGER (1..5)
		ACCESS  read-only
		STATUS  mandatory
		DESCRIPTION
			"Individual Group Switch port number"
		::= { ringswitchTRGrpSwtchPortEntry 2 }
	ringswitchTRGrpSwtchPortAddress OBJECT-TYPE
		SYNTAX  TRNMacAddress
		ACCESS  read-only
		STATUS  mandatory
		DESCRIPTION
			"Node address of device last inserted in the
			Group Switch port."
		::= { ringswitchTRGrpSwtchPortEntry 3 }
-- the Ringswitch token ring Group Switch trap information group
	ringswitchTRGrpSwtchTrapInfo OBJECT IDENTIFIER ::= { ringswitchTR 4 }
	ringswitchTRGrpSwtchTrapInfoReason OBJECT-TYPE
		SYNTAX  INTEGER{
			reason-unknown(1),    -- None of the reasons below
			ring-poll-failure(2), -- Node caused ring poll failure
			beaconing(3),         -- Node keeps beaconing
			ring-purges(4),       -- Node keeps purging ring
			isolating-errors(5),  -- Node has isolating errors
			removal-exceeded(6),  -- Node exceeded removal threshold
			beaconing-fault(7)    -- Node caused a beaconing fault
			}
		ACCESS  read-only
		STATUS  mandatory
		DESCRIPTION
			"Crime committed."
		::= { ringswitchTRGrpSwtchTrapInfo 1 }
-- the Ringswitch token ring Group Switch slot group
	ringswitchTRGrpSwtchSlotTable OBJECT-TYPE
		SYNTAX  SEQUENCE OF RingswitchTRGrpSwtchSlotEntry
		ACCESS  not-accessible
		STATUS  mandatory
		DESCRIPTION
			"This table contains information relating to
			Group Switch cards."
		::= { ringswitchTR 5 }
	ringswitchTRGrpSwtchSlotEntry OBJECT-TYPE
		SYNTAX  RingswitchTRGrpSwtchSlotEntry
		ACCESS  not-accessible
		STATUS  mandatory
		DESCRIPTION
			"A list containing Group Switch card information."
		INDEX { ringswitchTRGrpSwtchSlotIndex }
		::= { ringswitchTRGrpSwtchSlotTable 1 }
	RingswitchTRGrpSwtchSlotEntry
			::= SEQUENCE
				{
				ringswitchTRGrpSwtchSlotIndex
					INTEGER,
				ringswitchTRGrpSwtchSlotAdminStatii
					OCTET STRING,
				ringswitchTRGrpSwtchSlotAutoPartitions
					OCTET STRING,
				ringswitchTRGrpSwtchSlotOperStatii
					OCTET STRING
				}
	ringswitchTRGrpSwtchSlotIndex OBJECT-TYPE
		SYNTAX  INTEGER (1..65535)
		ACCESS  read-only
		STATUS  mandatory
		DESCRIPTION
			"Group Switch slot number"
		::= { ringswitchTRGrpSwtchSlotEntry 1 }
	ringswitchTRGrpSwtchSlotAdminStatii OBJECT-TYPE
		SYNTAX  OCTET STRING
		ACCESS  read-only
		STATUS  mandatory
		DESCRIPTION
			"An octet string containing the rptrPortAdminStatus
			of every Group Switch port on the card, one per octet:
				enabled(1),
				disabled(2)"
		::= { ringswitchTRGrpSwtchSlotEntry 2 }
	ringswitchTRGrpSwtchSlotAutoPartitions OBJECT-TYPE
		SYNTAX  OCTET STRING
		ACCESS  read-only
		STATUS  mandatory
		DESCRIPTION
			"An octet string with the rptrPortAutoPartitionState
			of every Group Switch port on the card, one per octet:
				notAutoPartitioned(1),
				autoPartitioned(2)"
		::= { ringswitchTRGrpSwtchSlotEntry 3 }
	ringswitchTRGrpSwtchSlotOperStatii OBJECT-TYPE
		SYNTAX  OCTET STRING
		ACCESS  read-only
		STATUS  mandatory
		DESCRIPTION
			"An octet string containing the rptrPortOperStatus
			of every Group Switch port on the card, one per octet:
				operational(1),
				notOperational(2),
				notPresent(3)"
		::= { ringswitchTRGrpSwtchSlotEntry 4 }
----------------------------------------------------------------------------
-- the FDDI group
	ringswitchFDDICardTable OBJECT-TYPE
		SYNTAX  SEQUENCE OF RingswitchFDDICardEntry
		ACCESS  not-accessible
		STATUS  mandatory
		DESCRIPTION
			"A table that contains information about each FDDI
			card in the Ringswitch."
		::= { ringswitchFDDI 1 }
	ringswitchFDDICardEntry OBJECT-TYPE
		SYNTAX  RingswitchFDDICardEntry
		ACCESS  not-accessible
		STATUS  mandatory
		DESCRIPTION
			"A list of FDDI status and parameter values for
			a FDDI card."
		INDEX { ringswitchFDDICardNum }
		::= { ringswitchFDDICardTable 1 }
	RingswitchFDDICardEntry ::=
		SEQUENCE
			{
			ringswitchFDDICardNum           INTEGER,
			ringswitchFDDICardSMTIndex      INTEGER,
			ringswitchFDDICardFixupMode     INTEGER,
			ringswitchFDDICardVRStatus      INTEGER,
			ringswitchFDDICardVRRingNum     INTEGER,
			ringswitchFDDICardVRBridgeNum   INTEGER,
			ringswitchFDDICardStatus        INTEGER
			}
	ringswitchFDDICardNum OBJECT-TYPE
		SYNTAX  INTEGER (1..65535)
		ACCESS  read-only
		STATUS  mandatory
		DESCRIPTION
			"The slot number of the card for which this entry
			contains Ringswitch management information."
		::= { ringswitchFDDICardEntry 1 }
	ringswitchFDDICardSMTIndex OBJECT-TYPE
		SYNTAX  INTEGER (1..65535)
		ACCESS  read-only
		STATUS  mandatory
		DESCRIPTION
			"This variable takes the same value as the
			fddimibSMTIndex variable associated with this
			FDDI card."
		::= { ringswitchFDDICardEntry 2 }
	ringswitchFDDICardFixupMode OBJECT-TYPE
		SYNTAX  INTEGER {
				disabled    (1),
				fddi-all    (2)
				}
		ACCESS  read-write
		STATUS  mandatory
		DESCRIPTION
			"This MIB variable controls operation of protocol
			fixups on the FDDI linecard. When set to fddi-all,
			embedded MAC addresses in frames are bit-reversed to
			convert the frames into native FDDI format"
		::= { ringswitchFDDICardEntry 3 }
	ringswitchFDDICardVRStatus OBJECT-TYPE
		SYNTAX  INTEGER {
				enable    (1),
				disable   (2)
				}
		ACCESS  read-write
		STATUS  mandatory
		DESCRIPTION
			"This variable is used to enable / disable the
			FDDI virtual ring."
		::= { ringswitchFDDICardEntry 4 }
	ringswitchFDDICardVRRingNum OBJECT-TYPE
		SYNTAX  INTEGER
		ACCESS  read-write
		STATUS  mandatory
		DESCRIPTION
			"The ring number of the virtual ring."
		::= { ringswitchFDDICardEntry 5 }
	ringswitchFDDICardVRBridgeNum OBJECT-TYPE
		SYNTAX  INTEGER
		ACCESS  read-write
		STATUS  mandatory
		DESCRIPTION
			"The bridge number of the virtual ring."
		::= { ringswitchFDDICardEntry 6 }
	ringswitchFDDICardStatus OBJECT-TYPE
		SYNTAX  INTEGER
		ACCESS  read-only
		STATUS  mandatory
		DESCRIPTION
			"This variable gives the status of the SMT.
			Each bit (when set) carries the following
			information:
			bit 0 (lsb) : ring-inop,
			bit 1       : mac-unavailable,
			bit 2       : twisted,
			bit 3       : i-am-duplicate,
			bit 4       : he-is-duplicate,
			bit 5       : bypass-stuck,
			bit 6       : trace,
			bit 7       : long-ring-inop
			Multiple status values can occur simultaneously.
			If the port is not open then all bits are set to 0."
		::= { ringswitchFDDICardEntry 7 }
----------------------------------------------------------------------------
-- the ATM card group
	ringswitchATMCardTable OBJECT-TYPE
		SYNTAX  SEQUENCE OF RingswitchATMCardEntry
		ACCESS  not-accessible
		STATUS  mandatory
		DESCRIPTION
			"A table that contains information about each ATM
			card in the Ringswitch."
		::= { ringswitchATM 1 }
	ringswitchATMCardEntry OBJECT-TYPE
		SYNTAX  RingswitchATMCardEntry
		ACCESS  not-accessible
		STATUS  mandatory
		DESCRIPTION
			"A list that contains information about each ATM
			card in the Ringswitch."
		INDEX { ringswitchATMCardNum }
		::= { ringswitchATMCardTable 1 }
	RingswitchATMCardEntry ::=
		SEQUENCE        {
				ringswitchATMCardNum            INTEGER,
				ringswitchATMCardAdminStatus    INTEGER,
				ringswitchATMCardRemoteUNIVer   INTEGER,
				ringswitchATMCardLECSAddress    NSAP,
				ringswitchATMCardLECSIlmi       INTEGER,
				ringswitchATMCardLECSWka        INTEGER,
				ringswitchATMCardLECSPvc        INTEGER,
				ringswitchATMCardActivePort     INTEGER,
				ringswitchATMCardILMIStatus     INTEGER,
				ringswitchATMCardSignalStatus   INTEGER,
				ringswitchATMCardHardWiredESI   ETHMacAddress,
				ringswitchATMCardLocalESI       ETHMacAddress,
				ringswitchATMCardPortB          INTEGER,
				ringswitchATMCardMode           INTEGER,
				ringswitchATMCardSONETIfIndex   INTEGER,
				ringswitchATMCardATMIfIndex     INTEGER,
				ringswitchATMCardAAL5IfIndex    INTEGER,
				ringswitchATMCardRowStatuses    OCTET STRING,
				ringswitchATMCardMediaType      INTEGER,
				ringswitchATMCardConfigUNIVer   INTEGER,
				ringswitchATMCardActualUNIVer   INTEGER,
				ringswitchATMCardEthLecSupport  INTEGER
				}
	ringswitchATMCardNum OBJECT-TYPE
		SYNTAX  INTEGER (1..65535)
		ACCESS  read-only
		STATUS  mandatory
		DESCRIPTION
			"The slot number of the card for which this entry
			contains Ringswitch management information."
		::= { ringswitchATMCardEntry 1 }
	ringswitchATMCardAdminStatus OBJECT-TYPE
		SYNTAX  INTEGER {
				up(1),
				down(2)
				}
		ACCESS  read-write
		STATUS  mandatory
		DESCRIPTION
			"This variable is a duplicate of the ifAdminStatus
			of the SONET interface associated with this ATM
			card. It is used to enable / disable the ATM card."
		::= { ringswitchATMCardEntry 2 }
	ringswitchATMCardRemoteUNIVer OBJECT-TYPE
		SYNTAX  INTEGER {
				unknown         (1),
				uni-30          (2),
				uni-31          (3),
				uni-40          (4)
				}
		ACCESS  read-only
		STATUS  mandatory
		DESCRIPTION
			"The type of signalling supported by the ATM
			switch at the remote end of this interface."
		::= { ringswitchATMCardEntry 3 }
	ringswitchATMCardLECSAddress OBJECT-TYPE
		SYNTAX  NSAP
		ACCESS  read-write
		STATUS  mandatory
		DESCRIPTION
			"The LECS address that a LEC associated with this
			card will use.
			If the configured address fails or is set to 0 then
			the LEC must find the location of the LECS by either:
			using a defined ILMI procedure to determine the LECS
			address; using the well-known LECS address; or using
			the well-known PVC to the LECS.
			The LEC will try each of these three methods in turn
			(if configured to use them) until the LECS is
			located."
		::= { ringswitchATMCardEntry 4 }
	ringswitchATMCardLECSIlmi OBJECT-TYPE
		SYNTAX  INTEGER  {
				enable  (1),
				disable (2)
				}
		ACCESS  read-write
		STATUS  mandatory
		DESCRIPTION
			"This variable indicates whether or not a LEC can
			try to determine the LECS address using ILMI."
		::= { ringswitchATMCardEntry 5 }
	ringswitchATMCardLECSWka OBJECT-TYPE
		SYNTAX  INTEGER  {
				enable  (1),
				disable (2)
				}
		ACCESS  read-write
		STATUS  mandatory
		DESCRIPTION
			"This variable indicates whether or not a LEC can
			use the well-known LECS address to locate the LECS."
		::= { ringswitchATMCardEntry 6 }
	ringswitchATMCardLECSPvc OBJECT-TYPE
		SYNTAX  INTEGER  {
				enable  (1),
				disable (2)
				}
		ACCESS  read-write
		STATUS  mandatory
		DESCRIPTION
			"This variable indicates whether or not a LEC can
			use the well-known PVC to locate the LECS."
		::= { ringswitchATMCardEntry 7 }
	ringswitchATMCardActivePort OBJECT-TYPE
		SYNTAX  INTEGER  {
				port-a          (1),
				port-b          (2)
				}
		ACCESS  read-only
		STATUS  mandatory
		DESCRIPTION
			"The port that the ATM card is currently using."
		::= { ringswitchATMCardEntry 8 }
	ringswitchATMCardILMIStatus OBJECT-TYPE
		SYNTAX  INTEGER  {
				up(1),
				down(2)
				}
		ACCESS  read-only
		STATUS  mandatory
		DESCRIPTION
			"The current state of the ILMI signalling for
			this card."
		::= { ringswitchATMCardEntry 9 }
	ringswitchATMCardSignalStatus OBJECT-TYPE
		SYNTAX  INTEGER  {
				up(1),
				down(2)
				}
		ACCESS  read-only
		STATUS  mandatory
		DESCRIPTION
			"The current state of the ATM signalling for
			this card."
		::= { ringswitchATMCardEntry 10 }
	ringswitchATMCardHardWiredESI OBJECT-TYPE
		SYNTAX  ETHMacAddress
		ACCESS  read-only
		STATUS  mandatory
		DESCRIPTION
			"The Hard wired ESI (End Station Identifier)
			for the card."
		::= { ringswitchATMCardEntry 11 }
	ringswitchATMCardLocalESI OBJECT-TYPE
		SYNTAX  ETHMacAddress
		ACCESS  read-write
		STATUS  mandatory
		DESCRIPTION
			"The locally administered ESI (End Station Identifier)
			for the card. When a set request for this variable
			is accepted the new value will not take effect until
			the next time the ATM card is rebooted."
		::= { ringswitchATMCardEntry 12 }
	ringswitchATMCardPortB OBJECT-TYPE
		SYNTAX  INTEGER {
				enabled         (1),
				disabled        (2)
				}
		ACCESS  read-write
		STATUS  mandatory
		DESCRIPTION
			"The state of Port B - whether or not an attempt will
			be made to use Port B in the event of Port A failing."
		::= { ringswitchATMCardEntry 13 }
	ringswitchATMCardMode OBJECT-TYPE
		SYNTAX  INTEGER {
				sonet           (1),
				sdh             (2)
				}
		ACCESS  read-write
		STATUS  mandatory
		DESCRIPTION
			"The framing mode used by the front-end."
		::= { ringswitchATMCardEntry 14 }
	ringswitchATMCardSONETIfIndex OBJECT-TYPE
		SYNTAX  INTEGER
		ACCESS  read-only
		STATUS  mandatory
		DESCRIPTION
			"Each ATM card provides one SONET interface.
			This variable takes the same value as the ifIndex
			associated with this SONET interface."
		::= { ringswitchATMCardEntry 15 }
	ringswitchATMCardATMIfIndex OBJECT-TYPE
		SYNTAX  INTEGER
		ACCESS  read-only
		STATUS  mandatory
		DESCRIPTION
			"Each ATM card provides one ATM interface.
			This variable takes the same value as the ifIndex
			associated with this ATM interface."
		::= { ringswitchATMCardEntry 16 }
	ringswitchATMCardAAL5IfIndex OBJECT-TYPE
		SYNTAX  INTEGER
		ACCESS  read-only
		STATUS  mandatory
		DESCRIPTION
			"Each ATM card provides one AAL5 interface.
			This variable takes the same value as the ifIndex
			associated with this AAL5 interface."
		::= { ringswitchATMCardEntry 17 }
	ringswitchATMCardRowStatuses OBJECT-TYPE
		SYNTAX  OCTET STRING
		ACCESS  read-only
		STATUS  mandatory
		DESCRIPTION
			"An octet string containing the lecRowStatus for
			each LEC on this ATM card."
		::= { ringswitchATMCardEntry 18 }
	ringswitchATMCardMediaType OBJECT-TYPE
		SYNTAX  INTEGER {
				multi-mode-fiber  (1),
				single-mode-fiber (2)
				}
		ACCESS  read-only
		STATUS  mandatory
		DESCRIPTION
			"The media type of this ATM card."
		::= { ringswitchATMCardEntry 19 }
	ringswitchATMCardConfigUNIVer OBJECT-TYPE
		SYNTAX  INTEGER {
				autoConfig      (1),
				uni-30          (2),
				uni-31          (3),
				uni-40          (4)
				}
		ACCESS  read-write
		STATUS  mandatory
		DESCRIPTION
			"The type of signalling that is configured for
			the interface."
		::= { ringswitchATMCardEntry 20 }
	ringswitchATMCardActualUNIVer OBJECT-TYPE
		SYNTAX  INTEGER {
				unknown         (1),
				uni-30          (2),
				uni-31          (3),
				uni-40          (4)
				}
		ACCESS  read-only
		STATUS  mandatory
		DESCRIPTION
			"The type of signalling that is currently being
			used on the interface.  This may reflect a manually
			configured value for the signalling type, or
			may be determined by other means such as auto-
			configuration."
		::= { ringswitchATMCardEntry 21 }
	ringswitchATMCardEthLecSupport OBJECT-TYPE
		SYNTAX  INTEGER {
				yes (1),
				no  (2)
				}
		ACCESS  read-only
		STATUS  mandatory
		DESCRIPTION
			"Does this ATM card support Ethernet LEC."
		::= { ringswitchATMCardEntry 22 }
-- the ATM port group
	ringswitchATMPortTable OBJECT-TYPE
		SYNTAX  SEQUENCE OF RingswitchATMPortEntry
		ACCESS  not-accessible
		STATUS  mandatory
		DESCRIPTION
			"A table that contains information about each LEC
			in the Ringswitch."
		::= { ringswitchATM 2 }
	ringswitchATMPortEntry OBJECT-TYPE
		SYNTAX  RingswitchATMPortEntry
		ACCESS  not-accessible
		STATUS  mandatory
		DESCRIPTION
			"A list that contains information about each LEC
			in the Ringswitch."
		INDEX { ringswitchATMPortNum }
		::= { ringswitchATMPortTable 1 }
	RingswitchATMPortEntry ::=
			SEQUENCE        {
					ringswitchATMPortNum
						INTEGER,
					ringswitchATMPortFailReason
						INTEGER,
					ringswitchATMPortFailSecondary
						INTEGER,
					ringswitchATMPortRxDiscards
						INTEGER,
					ringswitchATMPortTxDiscards
						INTEGER,
					ringswitchATMPortTxQuotaDiscards
						INTEGER,
					ringswitchATMPortTxBUSBroadcasts
						INTEGER,
					ringswitchATMPortTxBUSUnknowns
						INTEGER,
					ringswitchATMPortRxBUSFiltered
						INTEGER,
					ringswitchATMPortIPXTypeETH
						INTEGER,
					ringswitchATMPortIPXTypeTRN
						INTEGER,
					ringswitchATMPortIPXEvenize
						INTEGER,
					ringswitchATMPortIPXBufLimit
						INTEGER,
					ringswitchATMPortIPXEnable
						INTEGER,
					ringswitchATMPortIPEnable
						INTEGER,
                                        ringswitchATMPortIPMulticastType
                                                INTEGER
					}
	ringswitchATMPortNum OBJECT-TYPE
		SYNTAX  INTEGER (1..65535)
		ACCESS  read-only
		STATUS  mandatory
		DESCRIPTION
			"The port number of the port for which this entry
			contains LEC information."
		::= { ringswitchATMPortEntry 1 }
	ringswitchATMPortFailReason OBJECT-TYPE
		SYNTAX  INTEGER {
				success                 (1),
				sig-ilmi-fail           (2),
				lecs-not-found          (3),
				config-failed           (4),
				les-connect-fail        (5),
				join-failed             (6),
				bus-not-found           (7),
				bus-connect-fail        (8),
				bus-didnt-connect       (9),
				duplicate-elan          (10),
				les-vc-dropped          (11),
				bus-vc-dropped          (12),
				rejoin-wrong-elan       (13),
				insufficient-memory     (14),
				already-open            (15),
				invalid-port            (16),
				unknown                 (17)
				}
		ACCESS  read-only
		STATUS  mandatory
		DESCRIPTION
			"The reason why this LEC failed to open."
		::= { ringswitchATMPortEntry 2 }
	ringswitchATMPortFailSecondary OBJECT-TYPE
		SYNTAX  INTEGER {
				none                    (1),
				timeout                 (2),
				undefined-error         (3),
				version-not-supported   (4),
				invalid-request-params  (5),
				dup-lan-destination     (6),
				dup-atm-address         (7),
				insuff-resources        (8),
				access-denied           (9),
				invalid-requester-id    (10),
				invalid-lan-destination (11),
				invalid-atm-address     (12),
				no-configuration        (13),
				le-configure-error      (14),
				insuff-information      (15)
				}
		ACCESS  read-only
		STATUS  mandatory
		DESCRIPTION
			"More information on why this LEC failed to open.
			Only valid if ringswitchATMFailReason is either
			config-failed(4) or join-failed(6)."
		::= { ringswitchATMPortEntry 3 }
	ringswitchATMPortRxDiscards OBJECT-TYPE
		SYNTAX  INTEGER
		ACCESS  read-only
		STATUS  mandatory
		DESCRIPTION
			""
		::= { ringswitchATMPortEntry 4 }
	ringswitchATMPortTxDiscards OBJECT-TYPE
		SYNTAX  INTEGER
		ACCESS  read-only
		STATUS  mandatory
		DESCRIPTION
			""
		::= { ringswitchATMPortEntry 5 }
	ringswitchATMPortTxQuotaDiscards OBJECT-TYPE
		SYNTAX  INTEGER
		ACCESS  read-only
		STATUS  mandatory
		DESCRIPTION
			""
		::= { ringswitchATMPortEntry 6 }
	ringswitchATMPortTxBUSBroadcasts OBJECT-TYPE
		SYNTAX  INTEGER
		ACCESS  read-only
		STATUS  mandatory
		DESCRIPTION
			""
		::= { ringswitchATMPortEntry 7 }
	ringswitchATMPortTxBUSUnknowns OBJECT-TYPE
		SYNTAX  INTEGER
		ACCESS  read-only
		STATUS  mandatory
		DESCRIPTION
			""
		::= { ringswitchATMPortEntry 8 }
	ringswitchATMPortRxBUSFiltered OBJECT-TYPE
		SYNTAX  INTEGER
		ACCESS  read-only
		STATUS  mandatory
		DESCRIPTION
			""
		::= { ringswitchATMPortEntry 9 }
	ringswitchATMPortIPXTypeETH OBJECT-TYPE
		SYNTAX  INTEGER {
				auto            (1),
				ieee8022        (2),
				snap            (3),
				ieee8023        (4),
				dix             (5)
				}
		ACCESS  read-write
		STATUS  mandatory
		DESCRIPTION
			"This variable specifies the encapsulation type on
			Ethernet for all IPX frames forwarded from onto
			an Ethernet LEC"
		::= { ringswitchATMPortEntry 10 }
	ringswitchATMPortIPXTypeTRN OBJECT-TYPE
		SYNTAX  INTEGER {
				auto            (1),
				ieee8022        (2),
				snap            (3)
				}
		ACCESS  read-write
		STATUS  mandatory
		DESCRIPTION
			"This variable specifies the encapsulation type on 
			TRN for all IPX frames forwarded from an Ethernet LEC"
		::= { ringswitchATMPortEntry 11 }
	ringswitchATMPortIPXEvenize OBJECT-TYPE
		SYNTAX  INTEGER {
				enable          (1),
				disable         (2)
				}
		ACCESS  read-write
		STATUS  mandatory
		DESCRIPTION
			"If this variable is set to enable then all IPX
			packets forwarded in either direction to be even 
			length by adding a zero padding byte if required"
		::= { ringswitchATMPortEntry 12 }
	ringswitchATMPortIPXBufLimit OBJECT-TYPE
		SYNTAX  INTEGER {
				enable          (1),
				disable         (2)
				}
		ACCESS  read-write
		STATUS  mandatory
		DESCRIPTION
			"If this variable is enabled then any NCP buffer size
			negotiation requests are intercepted and the 
			requested frame size is limit to something less than
			the ELAN's maximum size"
		::= { ringswitchATMPortEntry 13 }
	ringswitchATMPortIPXEnable OBJECT-TYPE
		SYNTAX  INTEGER {
				enable          (1),
				disable         (2)
				}
		ACCESS  read-write
		STATUS  mandatory
		DESCRIPTION
			"If this variable is enabled on an Ethernet LEC port 
			 then the LEC will do translational bridging of IPX 
			 frames, otherwise it will discard them.  It is 
			 ignored for Token Ring LECs"
		::= { ringswitchATMPortEntry 14 }
	ringswitchATMPortIPEnable OBJECT-TYPE
		SYNTAX  INTEGER {
				enable          (1),
				disable         (2)
				}
		ACCESS  read-write
		STATUS  mandatory
		DESCRIPTION
			"If this variable is enabled on an Ethernet LEC port 
			 then the LEC will do translational bridging of IP,
			 ARP and RARP frames, otherwise it will discard them. 
			 It is ignored for Token Ring LECs"
		::= { ringswitchATMPortEntry 15 }
    ringswitchATMPortIPMulticastType OBJECT-TYPE
		SYNTAX	INTEGER {
				broadcast (1),
				functional(2),
				group     (3)
				}
		ACCESS  read-write
		STATUS  mandatory
		DESCRIPTION
			"This variable specifies the type of MAC address to
			use as the destination for IP multicast frames on
			Token Ring. It is ignored for Token Ring LECs"
		::= { ringswitchATMPortEntry 16 }

----------------------------------------------------------------------------
-- the TLS card group
	ringswitchTLSCardTable OBJECT-TYPE
		SYNTAX	SEQUENCE OF RingswitchTLSCardEntry
		ACCESS	not-accessible
		STATUS	mandatory
		DESCRIPTION
			"A table that contains information about each TLS
			card in the Ringswitch."
		::= { ringswitchTLS 1 }
	ringswitchTLSCardEntry OBJECT-TYPE
		SYNTAX	RingswitchTLSCardEntry
		ACCESS	not-accessible
		STATUS	mandatory
		DESCRIPTION
			"A list that contains information about each TLS
			card in the Ringswitch."
		INDEX { ringswitchTLSCardNum }
		::= { ringswitchTLSCardTable 1 }
	RingswitchTLSCardEntry ::=
		SEQUENCE
                {
            ringswitchTLSCardNum                		INTEGER,
            ringswitchTLSCardRowStatuses        		OCTET STRING,
            ringswitchTLSCardRIPTTL             		INTEGER,
            ringswitchTLSCardRIPInterval        		INTEGER,
            ringswitchTLSCardRIPAging           		INTEGER,
            ringswitchTLSCardDefRoute           		IpAddress,
            ringswitchTLSCardDefRouteMetric     		INTEGER,
            ringswitchTLSCardRIPFlags           		INTEGER,
            ringswitchTLSCardOSPFRouterId       		IpAddress,
            ringswitchTLSCardOSPFFlags          		INTEGER,
            ringswitchTLSCardStatsCpuUsage      		INTEGER,
            ringswitchTLSCardStatsFreeMem       		INTEGER,
            ringswitchTLSCardStatsFramesFwd     		INTEGER,
            ringswitchTLSCardStatsMaxCpuUsage   		INTEGER,
            ringswitchTLSCardStatsMinFreeMem    		INTEGER,
            ringswitchTLSCardStatsMaxFramesFwd  		INTEGER,
            ringswitchTLSCardStatsResetState    		INTEGER,
            ringswitchTLSCardARPFlush           		INTEGER,
            ringswitchTLSCardBootPRASecondsThreshold 	        INTEGER,
            ringswitchTLSCardBootPRAHopsThreshold               INTEGER
		}
	ringswitchTLSCardNum OBJECT-TYPE
		SYNTAX	INTEGER (1..65535)
		ACCESS	read-only
		STATUS	mandatory
		DESCRIPTION
			"The slot number of the card for which this entry
			contains Ringswitch management information."
		::= { ringswitchTLSCardEntry 1 }
	ringswitchTLSCardRowStatuses OBJECT-TYPE
		SYNTAX	OCTET STRING
		ACCESS	read-only
		STATUS	mandatory
		DESCRIPTION
			"An octet string containing the legRowStatus for
			each LEG on this TLS card."
		::= { ringswitchTLSCardEntry 2 }
	ringswitchTLSCardRIPTTL OBJECT-TYPE
		SYNTAX	INTEGER (1..255)
		ACCESS	read-write
		STATUS	mandatory
		DESCRIPTION
			"An integer giving the value to use for the TTL
                         (Time to Live) field in RIP frames."
		::= { ringswitchTLSCardEntry 3 }
	ringswitchTLSCardRIPInterval OBJECT-TYPE
		SYNTAX	INTEGER (1..65535)
		ACCESS	read-write
		STATUS	mandatory
		DESCRIPTION
			"An integer giving the interval in seconds
                         between RIP anouncements."
		::= { ringswitchTLSCardEntry 4 }
	ringswitchTLSCardRIPAging OBJECT-TYPE
		SYNTAX	INTEGER (1..65535)
		ACCESS	read-write
		STATUS	mandatory
		DESCRIPTION
			"Time in seconds to age out routes learnt
                         through RIP."
		::= { ringswitchTLSCardEntry 5 }
	ringswitchTLSCardDefRoute OBJECT-TYPE
		SYNTAX	IpAddress
		ACCESS	read-write
		STATUS	mandatory
		DESCRIPTION
			"The IP address of a gateway to use as the default 
                         route."
		::= { ringswitchTLSCardEntry 6 }
	ringswitchTLSCardDefRouteMetric OBJECT-TYPE
		SYNTAX	INTEGER (0..16)
		ACCESS	read-write
		STATUS	mandatory
		DESCRIPTION
			"The metric to use for the default route."
		::= { ringswitchTLSCardEntry 7 }
	ringswitchTLSCardRIPFlags OBJECT-TYPE
		SYNTAX	INTEGER (0..65535)
		ACCESS	read-write
		STATUS	mandatory
		DESCRIPTION
			"RIP flags for the TLS card.  Bit 0 is set to 
                        indicate Ignore the Neighbours List. Bit 1 is set 
                        to indicate that routes learnt through OSPF should 
                        be redistributed through RIP."
		::= { ringswitchTLSCardEntry 8 }
	ringswitchTLSCardOSPFRouterId OBJECT-TYPE
		SYNTAX	IpAddress
		ACCESS	read-write
		STATUS	mandatory
		DESCRIPTION
			"The OSPF router Identifier."
		::= { ringswitchTLSCardEntry 9 }
	ringswitchTLSCardOSPFFlags OBJECT-TYPE
		SYNTAX	INTEGER (0..65535)
		ACCESS	read-write
		STATUS	mandatory
		DESCRIPTION
			"OSPF flags for the TLS card.  Bit 0 must be set
                         in an autonomous system border router and cleared
                         otherwise.  Bit 1 is not currently used. Bit 2 
                         indicates that RIP routes should be exported to 
                         OSPF. Bit 3 indicates that static routes should be 
                         exported to OSPF. Bit 15 is the master OSPF enable 
                         for the card."
		::= { ringswitchTLSCardEntry 10 }
	ringswitchTLSCardStatsCpuUsage OBJECT-TYPE
		SYNTAX	INTEGER (0..10000)
		ACCESS	read-only
		STATUS	mandatory
		DESCRIPTION
			"The estimated CPU usage on the TLS card in a second
                         measured in hundredths of a percent."
		::= { ringswitchTLSCardEntry 11 }
	ringswitchTLSCardStatsFreeMem OBJECT-TYPE
		SYNTAX	INTEGER
		ACCESS	read-only
		STATUS	mandatory
		DESCRIPTION
			"The amount of free memory in the heap on the TLS card
                         measured in kilobytes."
		::= { ringswitchTLSCardEntry 12 }
	ringswitchTLSCardStatsFramesFwd OBJECT-TYPE
		SYNTAX	INTEGER
		ACCESS	read-only
		STATUS	mandatory
		DESCRIPTION
			"The number of frames forwarded per second by the
                         fast forwarding engine on the TLS card."
		::= { ringswitchTLSCardEntry 13 }
	ringswitchTLSCardStatsMaxCpuUsage OBJECT-TYPE
		SYNTAX	INTEGER (0..10000)
		ACCESS	read-only
		STATUS	mandatory
		DESCRIPTION
			"The maximum value recorded for the CPU usage 
                         parameter."
		::= { ringswitchTLSCardEntry 14 }
	ringswitchTLSCardStatsMinFreeMem OBJECT-TYPE
		SYNTAX	INTEGER
		ACCESS	read-only
		STATUS	mandatory
		DESCRIPTION
			"The minimum value recorded for the CPU usage 
                         parameter."
		::= { ringswitchTLSCardEntry 15 }
	ringswitchTLSCardStatsMaxFramesFwd OBJECT-TYPE
		SYNTAX	INTEGER
		ACCESS	read-only
		STATUS	mandatory
		DESCRIPTION
			"The maximum value recorded for the forwarding 
                         parameter."
		::= { ringswitchTLSCardEntry 16 }
	ringswitchTLSCardStatsResetState OBJECT-TYPE
		SYNTAX	INTEGER
		ACCESS	read-write
		STATUS	mandatory
		DESCRIPTION
			"Write any value to this to reset the three maximum and
                         minimum values above.  Always reads as 1."
		::= { ringswitchTLSCardEntry 17 }
	ringswitchTLSCardARPFlush OBJECT-TYPE
		SYNTAX  INTEGER
		ACCESS  read-write
		STATUS  mandatory
		DESCRIPTION
			"Write any value to this to flush the TLS's ARP cache."
		::= { ringswitchTLSCardEntry 18 }
	ringswitchTLSCardBootPRASecondsThreshold OBJECT-TYPE
		SYNTAX  INTEGER
		ACCESS  read-write
		STATUS  mandatory
		DESCRIPTION
			"Length of time, in seconds, since the moment a 
                         BootP/DHCP client was booted after which the a 
                         clients BootP/DHCP requests will no longer be 
                         forwarded. Default value is 86,400."
		::= { ringswitchTLSCardEntry 19 }
	ringswitchTLSCardBootPRAHopsThreshold OBJECT-TYPE
		SYNTAX  INTEGER (1..16)
		ACCESS  read-write
		STATUS  mandatory
		DESCRIPTION
			"A maximum value for the hops field in received 
                        BootP/DHCP requests. Default value is 4."
		::= { ringswitchTLSCardEntry 20 }

-- the TLS port group
	ringswitchTLSPortTable OBJECT-TYPE
		SYNTAX	SEQUENCE OF RingswitchTLSPortEntry
		ACCESS	not-accessible
		STATUS	mandatory
		DESCRIPTION
			"A table that contains information about each LEG
			in the Ringswitch."
		::= { ringswitchTLS 2 }
	ringswitchTLSPortEntry OBJECT-TYPE
		SYNTAX	RingswitchTLSPortEntry
		ACCESS	not-accessible
		STATUS	mandatory
		DESCRIPTION
			"A list that contains information about each LEG
			in the Ringswitch."
		INDEX { ringswitchTLSPortNum }
		::= { ringswitchTLSPortTable 1 }
	RingswitchTLSPortEntry ::=
		SEQUENCE
                {
			ringswitchTLSPortNum           		INTEGER,
			ringswitchTLSPortName          		DisplayString ,
			ringswitchTLSPortMTU           		INTEGER,
			ringswitchTLSPortEnable        		INTEGER,
			ringswitchTLSPortIpAddress     		IpAddress,
			ringswitchTLSPortIpSubnetMask  		IpAddress,
			ringswitchTLSPortRIPRxType     		INTEGER,
			ringswitchTLSPortRIPTxType     		INTEGER,
			ringswitchTLSPortRIPFlags      		INTEGER,
			ringswitchTLSPortIfArray       		OCTET STRING,
			ringswitchTLSPortRIP2AuthType  		INTEGER,
			ringswitchTLSPortRIP2AuthKey   		OCTET STRING (SIZE(0..16)),
			ringswitchTLSPortOSPFEnable    		INTEGER,
			ringswitchTLSPortOSPFAreaId    		IpAddress,
			ringswitchTLSPortLegFlags      		INTEGER,
			ringswitchTLSPortOSPFAuthType  		INTEGER,
			ringswitchTLSPortOSPFAuthMD5KeyId 	INTEGER,
			ringswitchTLSPortOSPFAuthKey    	OCTET STRING (SIZE(0..16)),
			ringswitchTLSPortOSPFCost    		INTEGER,
			ringswitchTLSPortOSPFPriority  		INTEGER,
			ringswitchTLSPortOSPFHelloInterval	INTEGER,
			ringswitchTLSPortOSPFDeadInterval	INTEGER,
			ringswitchTLSPortBootPFlags		INTEGER
		}
	ringswitchTLSPortNum OBJECT-TYPE
		SYNTAX	INTEGER (1..65535)
		ACCESS	read-only
		STATUS	mandatory
		DESCRIPTION
			"The port number of the port for which this entry
			contains LEG information."
		::= { ringswitchTLSPortEntry 1 }
	ringswitchTLSPortName OBJECT-TYPE
		SYNTAX	DisplayString
		ACCESS	read-write
		STATUS	mandatory
		DESCRIPTION
			"The name that the administrator has given 
                         this subnet."
		::= { ringswitchTLSPortEntry 2 }
	ringswitchTLSPortMTU OBJECT-TYPE
		SYNTAX	INTEGER (64..18432)
		ACCESS	read-write
		STATUS	mandatory
		DESCRIPTION
			"The maximum frame size allowed on this subnet.  The
                         value must not exceed the maximum frame size of the
                         switch."
		::= { ringswitchTLSPortEntry 3 }
	ringswitchTLSPortEnable OBJECT-TYPE
		SYNTAX	INTEGER	{
				enable		(1),
				disable		(2)
				}
		ACCESS	read-write
		STATUS	mandatory
		DESCRIPTION
			"Enable a port to use it.  Disable a port to
                         configure it.  A newly created port will be
                         disabled."
		::= { ringswitchTLSPortEntry 4 }
	ringswitchTLSPortIpAddress OBJECT-TYPE
		SYNTAX	IpAddress
		ACCESS	read-write
		STATUS	mandatory
		DESCRIPTION
			"IP Address of the port.  Used in conjunction with
                         the IP subnet mask to define the subnet for the
                         port."
		::= { ringswitchTLSPortEntry 5 }
	ringswitchTLSPortIpSubnetMask OBJECT-TYPE
		SYNTAX	IpAddress
		ACCESS	read-write
		STATUS	mandatory
		DESCRIPTION
			"IP subnet mask for the port.  Used in conjunction
                         with the port IP address to define the subnet for
                         the port."
		::= { ringswitchTLSPortEntry 6 }
	ringswitchTLSPortRIPRxType OBJECT-TYPE
                SYNTAX   INTEGER { rip1 (1),
                                   rip2 (2),
                                   rip1OrRip2 (3),
                                   doNotReceive (4)
                                 }
		ACCESS	read-write
		STATUS	mandatory
		DESCRIPTION
                    "This indicates which version of RIP updates
                     are to be accepted.  Note that rip2 and
                     rip1OrRip2 implies reception of multicast
                     packets."
		::= { ringswitchTLSPortEntry 7 }
	ringswitchTLSPortRIPTxType OBJECT-TYPE
                SYNTAX   INTEGER { doNotSend (1),
                                   ripVersion1 (2),
                                   rip1Compatible (3),
                                   ripVersion2 (4)
                                 }
		ACCESS	read-write
		STATUS	mandatory
		DESCRIPTION
                    "What the router sends on this interface.
                     ripVersion1 implies sending RIP updates compliant
                     with  RFC  1058.   rip1Compatible implies
                     broadcasting RIP-2 updates using RFC 1058 route
                     subsumption rules.  ripVersion2 implies
                     multicasting RIP-2 updates."
		::= { ringswitchTLSPortEntry 8 }
	ringswitchTLSPortRIPFlags OBJECT-TYPE
                SYNTAX   INTEGER (0..65535)
		ACCESS	read-write
		STATUS	mandatory
		DESCRIPTION
                     "A bit mask of flags to control RIP operation.  By
                      default, all defined bits are set to 1.  Bit 0 (LSB)
                      says announce default routes, bit 1 says announce
                      host routes, bit 2 says announce static routes, bit 4
                      says learn default routes, bit 5 says learn host routes,
                      bit 8 enables route hold-down, bit 9 enables split 
                      horizon, bit 10 enables poison reverse, and bit 11 
                      enable route summarising."
		::= { ringswitchTLSPortEntry 9 }
	ringswitchTLSPortIfArray OBJECT-TYPE
		SYNTAX	OCTET STRING
		ACCESS	read-write
		STATUS	mandatory
		DESCRIPTION
			"An octet string containing every interface port
			 number in this subnet, one port (1-64) per octet."
		::= { ringswitchTLSPortEntry 10 }
	ringswitchTLSPortRIP2AuthType OBJECT-TYPE
                SYNTAX   INTEGER {
                                    noAuthentication (1),
                                    simplePassword (2),
                                    md5 (3)
                                 }
		ACCESS	read-write
		STATUS	mandatory
		DESCRIPTION
                    "The RIP-v2 authentification type.  Valid values are
                     noAuthentication, simplePassword or md5."
		::= { ringswitchTLSPortEntry 11 }
	ringswitchTLSPortRIP2AuthKey OBJECT-TYPE
		SYNTAX	OCTET STRING (SIZE(0..16))
		ACCESS	read-write
		STATUS	mandatory
		DESCRIPTION
                     "The value to be used as the Authentication Key
                     whenever the corresponding instance of
                     ringswitchTLSPortRIP2AuthTypee has a value other than
                     noAuthentication.   If a string shorter
                     than 16 octets is supplied, it will be left-
                     justified and padded to 16 octets, on the right,
                     with nulls (0x00).
                     Reading this object always results in an  OCTET
                     STRING of length zero."
		::= { ringswitchTLSPortEntry 12 }
	ringswitchTLSPortOSPFEnable OBJECT-TYPE
		SYNTAX	INTEGER	{
				enable		(1),
				disable		(2)
				}
		ACCESS	read-write
		STATUS	mandatory
		DESCRIPTION
			"Enable a port to use OSPF."
		::= { ringswitchTLSPortEntry 13 }
	ringswitchTLSPortOSPFAreaId OBJECT-TYPE
		SYNTAX	IpAddress
		ACCESS	read-write
		STATUS	mandatory
		DESCRIPTION
			"OSPF area identifier for the port."
		::= { ringswitchTLSPortEntry 14 }
	ringswitchTLSPortLegFlags OBJECT-TYPE
		SYNTAX	INTEGER	(0..65535)
		ACCESS	read-write
		STATUS	mandatory
		DESCRIPTION
			"Bits 1 and 0 Configure how to send IP multicast frames
                         over Token Ring.  00 means use broadcast.  01 means
                         use the functional address C000-0004-0000.  02 means
                         use the Group address as on Ethernet."
		::= { ringswitchTLSPortEntry 15 }
	ringswitchTLSPortOSPFAuthType OBJECT-TYPE
                SYNTAX   INTEGER {
                                    noAuthentication (1),
                                    simplePassword (2),
                                    md5 (3)
                                 }
		ACCESS	read-write
		STATUS	mandatory
		DESCRIPTION
                    "The OSPF authentification type.  Valid values are
                     noAuthentication, simplePassword or md5."
		::= { ringswitchTLSPortEntry 16 }
	ringswitchTLSPortOSPFAuthMD5KeyId OBJECT-TYPE
                SYNTAX   INTEGER (0 .. 255)
		ACCESS	read-write
		STATUS	mandatory
		DESCRIPTION
                    "The OSPF MD5 key id.  This is a byte value of the
                    MD5 key id.  It is ignored if
                    ringswitchTLSPortOSPFAuthType is not md5."
		::= { ringswitchTLSPortEntry 17 }
	ringswitchTLSPortOSPFAuthKey OBJECT-TYPE
		SYNTAX	OCTET STRING (SIZE(0..16))
		ACCESS	read-write
		STATUS	mandatory
		DESCRIPTION
                     "The value to be used as the Authentication Key
                     whenever the corresponding instance of
                     ringswitchTLSPortOSPFAuthType has a value other than
                     noAuthentication.   If a string shorter
                     than 16 octets is supplied, it will be left-
                     justified and padded to 16 octets, on the right,
                     with nulls (0x00).

                     Simple passwords use 8 characters.
                     MD5 passwords use 16 characters.

                     Reading this object always results in an  OCTET
                     STRING of length zero."
		::= { ringswitchTLSPortEntry 18 }
	ringswitchTLSPortOSPFCost OBJECT-TYPE
                SYNTAX   INTEGER (1 .. 65535)
		ACCESS	read-write
		STATUS	mandatory
		DESCRIPTION
                    "The OSPF cost of sending a packet
		     from this interface. Default value is 1.
		     A value of 0 is not allowed."
		::= { ringswitchTLSPortEntry 19 }
	ringswitchTLSPortOSPFPriority OBJECT-TYPE
                SYNTAX   INTEGER (0 .. 65535)
		ACCESS	read-write
		STATUS	mandatory
		DESCRIPTION
                    "The priority of this interface when
		     deciding which interface on the attached
	    	     network should become the designated router.
		     A value of 0 will prevent the interface
		     from ever becoming the designated router.
		     Default value is 1."
		::= { ringswitchTLSPortEntry 20 }
	ringswitchTLSPortOSPFHelloInterval OBJECT-TYPE
                SYNTAX   INTEGER
		ACCESS	read-write
		STATUS	mandatory
		DESCRIPTION
                    "The length of time in seconds between
		     sending OSPF hello packets from this interface.
		     Default value is 10. A value of 0 is not allowed."
		::= { ringswitchTLSPortEntry 21 }
	ringswitchTLSPortOSPFDeadInterval OBJECT-TYPE
                SYNTAX   INTEGER
		ACCESS	read-write
		STATUS	mandatory
		DESCRIPTION
                    "The length of time in seconds before
		     neighbors declare the router down after ceasing
		     to hear a hello packet. It is recommended that
		     this be set to 4 times the hello interval. 
		     Default value is 40. The dead interval must be 
		     longer than the hello interval."
		::= { ringswitchTLSPortEntry 22 }
	ringswitchTLSPortBootPFlags OBJECT-TYPE
		SYNTAX	INTEGER	{
				relay-agent-enable	(1),
				relay-agent-disable	(0)
				}
		ACCESS	read-write
		STATUS	mandatory
		DESCRIPTION
                    "Whether the interface forwards BootP and
		DHCP requests or not. Default is disabled."
		::= { ringswitchTLSPortEntry 23 }

-- The TLS static route group
	ringswitchTLSStaticRouteTable OBJECT-TYPE
		SYNTAX	SEQUENCE OF RingswitchTLSStaticRouteEntry
		ACCESS	not-accessible
		STATUS	mandatory
		DESCRIPTION
			"A table that contains a list of static routes."
		::= { ringswitchTLS 3 }
	ringswitchTLSStaticRouteEntry OBJECT-TYPE
		SYNTAX	RingswitchTLSStaticRouteEntry
		ACCESS	not-accessible
		STATUS	mandatory
		DESCRIPTION
			"An that contains information about one static
			route."
		INDEX { ringswitchTLSStaticRouteCardNum ,
                        ringswitchTLSStaticRouteIpAddress
                      }
		::= { ringswitchTLSStaticRouteTable 1 }
	RingswitchTLSStaticRouteEntry ::=
		SEQUENCE
                {
                        ringswitchTLSStaticRouteCardNum   INTEGER,
                        ringswitchTLSStaticRouteIpAddress IpAddress,
                        ringswitchTLSStaticRouteMask      IpAddress,
                        ringswitchTLSStaticRouteGateway   IpAddress,
                        ringswitchTLSStaticRouteMetric    INTEGER
		}
	ringswitchTLSStaticRouteCardNum OBJECT-TYPE
		SYNTAX	INTEGER
		ACCESS	read-only
		STATUS	mandatory
		DESCRIPTION
			"The TLS card number using a static route."
		::= { ringswitchTLSStaticRouteEntry 1 }
	ringswitchTLSStaticRouteIpAddress OBJECT-TYPE
		SYNTAX	IpAddress
		ACCESS	read-only
		STATUS	mandatory
		DESCRIPTION
			"The IP address of a static route."
		::= { ringswitchTLSStaticRouteEntry 2 }
	ringswitchTLSStaticRouteMask OBJECT-TYPE
		SYNTAX	IpAddress
		ACCESS	read-write
		STATUS	mandatory
		DESCRIPTION
			"The IP subnet mask to use in a static route."
		::= { ringswitchTLSStaticRouteEntry 3 }
	ringswitchTLSStaticRouteGateway OBJECT-TYPE
		SYNTAX	IpAddress
		ACCESS	read-write
		STATUS	mandatory
		DESCRIPTION
			"The IP address of a gateway to use in a static route.
                         This table is indexed by the TLS card and the IP
                         address of the route."
		::= { ringswitchTLSStaticRouteEntry 4 }
	ringswitchTLSStaticRouteMetric OBJECT-TYPE
		SYNTAX	INTEGER (0..16)
		ACCESS	read-write
		STATUS	mandatory
		DESCRIPTION
			"The metric to use for a static route.  Setting the
                         value to zero will delete the entry.  Setting it to a
                         non-zero value will cause the route to be registered,
                         so set this field after the gateway and mask."
		::= { ringswitchTLSStaticRouteEntry 5 }

-- the TLS RIP neighbours group
	ringswitchTLSRIPNeighbourTable OBJECT-TYPE
		SYNTAX	SEQUENCE OF RingswitchTLSRIPNeighbourEntry
		ACCESS	not-accessible
		STATUS	mandatory
		DESCRIPTION
			"A table that contains a list of static routes."
		::= { ringswitchTLS 4 }
	ringswitchTLSRIPNeighbourEntry OBJECT-TYPE
		SYNTAX	RingswitchTLSRIPNeighbourEntry
		ACCESS	not-accessible
		STATUS	mandatory
		DESCRIPTION
			"An that contains information about one static
			route."
		INDEX { ringswitchTLSRIPNeighbourCardNum ,
                        ringswitchTLSRIPNeighbourIpAddress
                      }
		::= { ringswitchTLSRIPNeighbourTable 1 }
	RingswitchTLSRIPNeighbourEntry ::=
		SEQUENCE
                {
                        ringswitchTLSRIPNeighbourCardNum   INTEGER,
                        ringswitchTLSRIPNeighbourIpAddress IpAddress,
                        ringswitchTLSRIPNeighbourEnable    INTEGER
		}
	ringswitchTLSRIPNeighbourCardNum OBJECT-TYPE
		SYNTAX	INTEGER
		ACCESS	read-only
		STATUS	mandatory
		DESCRIPTION
			"The TLS card number using a RIP Neighbour."
		::= { ringswitchTLSRIPNeighbourEntry 1 }
	ringswitchTLSRIPNeighbourIpAddress OBJECT-TYPE
		SYNTAX	IpAddress
		ACCESS	read-only
		STATUS	mandatory
		DESCRIPTION
			"The IP address of a RIP Neighbour."
		::= { ringswitchTLSRIPNeighbourEntry 2 }
	ringswitchTLSRIPNeighbourEnable OBJECT-TYPE
		SYNTAX	INTEGER	{
				enable		(1),
				disable		(2)
				}
		ACCESS	read-write
		STATUS	mandatory
		DESCRIPTION
                        "Setting to 1 marks the given IP address as a RIP 
                         neighbour. Setting to 2 removes the IP address from 
                         the list."
		::= { ringswitchTLSRIPNeighbourEntry 3 }

-- the TLS RIP Advertise group
	ringswitchTLSRIPAdvertTable OBJECT-TYPE
		SYNTAX	SEQUENCE OF RingswitchTLSRIPAdvertEntry
		ACCESS	not-accessible
		STATUS	mandatory
		DESCRIPTION
			"A table that contains a list of addresses to be
			advertised."
		::= { ringswitchTLS 5 }
	ringswitchTLSRIPAdvertEntry OBJECT-TYPE
		SYNTAX	RingswitchTLSRIPAdvertEntry
		ACCESS	not-accessible
		STATUS	mandatory
		DESCRIPTION
			"One entry in the RIP advertisement table."
		INDEX { ringswitchTLSRIPAdvertPortNum,
                        ringswitchTLSRIPAdvertIpAddress
                      }
		::= { ringswitchTLSRIPAdvertTable 1 }
	RingswitchTLSRIPAdvertEntry ::=
		SEQUENCE
                {
                        ringswitchTLSRIPAdvertPortNum   INTEGER,
                        ringswitchTLSRIPAdvertIpAddress IpAddress,
			ringswitchTLSRIPAdvertEnable    INTEGER
		}
	ringswitchTLSRIPAdvertPortNum OBJECT-TYPE
		SYNTAX	INTEGER
		ACCESS	read-only
		STATUS	mandatory
		DESCRIPTION
			"TLS leg port number for rejection."
		::= { ringswitchTLSRIPAdvertEntry 1 }
	ringswitchTLSRIPAdvertIpAddress OBJECT-TYPE
		SYNTAX	IpAddress
		ACCESS	read-only
		STATUS	mandatory
		DESCRIPTION
			"IP address for advertising."
		::= { ringswitchTLSRIPAdvertEntry 2 }
	ringswitchTLSRIPAdvertEnable OBJECT-TYPE
		SYNTAX	INTEGER	{
				enable		(1),
				disable		(2)
				}
		ACCESS	read-write
		STATUS	mandatory
		DESCRIPTION
			"Setting to 1 marks the given IP address for RIP
                         advertisement. Setting to 2 removes the IP address
                         from the list."
		::= { ringswitchTLSRIPAdvertEntry 3 }

-- the TLS RIP reject group
	ringswitchTLSRIPRejectTable OBJECT-TYPE
		SYNTAX	SEQUENCE OF RingswitchTLSRIPRejectEntry
		ACCESS	not-accessible
		STATUS	mandatory
		DESCRIPTION
			"A table that contains a list of addresses to be
			rejected."
		::= { ringswitchTLS 6 }
	ringswitchTLSRIPRejectEntry OBJECT-TYPE
		SYNTAX	RingswitchTLSRIPRejectEntry
		ACCESS	not-accessible
		STATUS	mandatory
		DESCRIPTION
			"One entry in the RIP rejection table."
		INDEX { ringswitchTLSRIPRejectPortNum,
                        ringswitchTLSRIPRejectIpAddress
                      }
		::= { ringswitchTLSRIPRejectTable 1 }
	RingswitchTLSRIPRejectEntry ::=
		SEQUENCE
                {
			ringswitchTLSRIPRejectPortNum   INTEGER,
			ringswitchTLSRIPRejectIpAddress IpAddress,
			ringswitchTLSRIPRejectEnable    INTEGER
		}
	ringswitchTLSRIPRejectPortNum OBJECT-TYPE
		SYNTAX	INTEGER
		ACCESS	read-only
		STATUS	mandatory
		DESCRIPTION
			"TLE leg port number IP address for rejection."
		::= { ringswitchTLSRIPRejectEntry 1 }
	ringswitchTLSRIPRejectIpAddress OBJECT-TYPE
		SYNTAX	IpAddress
		ACCESS	read-only
		STATUS	mandatory
		DESCRIPTION
			"IP address for rejection."
		::= { ringswitchTLSRIPRejectEntry 2 }
	ringswitchTLSRIPRejectEnable OBJECT-TYPE
		SYNTAX	INTEGER	{
				enable		(1),
				disable		(2)
				}
		ACCESS	read-write
		STATUS	mandatory
		DESCRIPTION
			"Setting to 1 marks the given IP address for RIP
                         advertisement. Setting to 2 removes the IP address
                         from the list."
		::= { ringswitchTLSRIPRejectEntry 3 }

-- the TLS OSPF areas group
	ringswitchTLSOSPFAreaTable OBJECT-TYPE
		SYNTAX	SEQUENCE OF RingswitchTLSOSPFAreaEntry
		ACCESS	not-accessible
		STATUS	mandatory
		DESCRIPTION
			"A table that contains information about each
			 OSPF area for a TLS."
		::= { ringswitchTLS 7 }
	ringswitchTLSOSPFAreaEntry OBJECT-TYPE
		SYNTAX	RingswitchTLSOSPFAreaEntry
		ACCESS	not-accessible
		STATUS	mandatory
		DESCRIPTION
			"An entry containing information about one OSPF area."
		INDEX { ringswitchTLSOSPFAreaId }
		::= { ringswitchTLSOSPFAreaTable 1 }
	RingswitchTLSOSPFAreaEntry ::=
		SEQUENCE
                {
			ringswitchTLSOSPFAreaCardNum      INTEGER,
			ringswitchTLSOSPFAreaId           IpAddress,
			ringswitchTLSOSPFAreaAddress      IpAddress,
			ringswitchTLSOSPFAreaAddressMask  IpAddress,
			ringswitchTLSOSPFAreaFlags        INTEGER
		}
	ringswitchTLSOSPFAreaCardNum OBJECT-TYPE
		SYNTAX	INTEGER
		ACCESS	read-only
		STATUS	mandatory
		DESCRIPTION
			"TLS card for OSPF area."
		::= { ringswitchTLSOSPFAreaEntry 1 }
	ringswitchTLSOSPFAreaId OBJECT-TYPE
		SYNTAX	IpAddress
		ACCESS	read-only
		STATUS	mandatory
		DESCRIPTION
			"OSPF area identifier."
		::= { ringswitchTLSOSPFAreaEntry 2 }
	ringswitchTLSOSPFAreaAddress OBJECT-TYPE
		SYNTAX	IpAddress
		ACCESS	read-only
		STATUS	mandatory
		DESCRIPTION
			"OSPF area address."
		::= { ringswitchTLSOSPFAreaEntry 3 }
	ringswitchTLSOSPFAreaAddressMask OBJECT-TYPE
		SYNTAX	IpAddress
		ACCESS	read-write
		STATUS	mandatory
		DESCRIPTION
			"OSPF area address mask."
		::= { ringswitchTLSOSPFAreaEntry 4 }
	ringswitchTLSOSPFAreaFlags OBJECT-TYPE
		SYNTAX	INTEGER	(0..32767)
		ACCESS	read-write
		STATUS	mandatory
		DESCRIPTION
			"OSPF area flags.  Bit 0 indicates address range 
                         active, Bit 1 indicates advertise address range, 
                         and bit 2 indicates external routing capability.
                         Bit 15 is a destroy area flag.  Setting this bit 
                         will cause the area to be deleted."
		::= { ringswitchTLSOSPFAreaEntry 5 }

-- The TLS BootP Relay Agent server group
	ringswitchTLSBootPRAServerTable OBJECT-TYPE
		SYNTAX	SEQUENCE OF RingswitchTLSBootPRAServerEntry
		ACCESS	not-accessible
		STATUS	mandatory
		DESCRIPTION
			"A table containing BootP/DHCP servers
		         that the BootP Relay Agent can forward BootP/DHCP
		         packets to. BootP/DHCP requests will be shared
		         amongst the servers in this table unless the
		         requests specify a particular server name."
		::= { ringswitchTLS 8 }
	ringswitchTLSBootPRAServerEntry OBJECT-TYPE
		SYNTAX	RingswitchTLSBootPRAServerEntry
		ACCESS	not-accessible
		STATUS	mandatory
		DESCRIPTION
			"Contains information about the BootP/DHCP
			 server."
		INDEX { ringswitchTLSBootPRAServerCardNum ,
                ringswitchTLSBootPRAServerIpAddress }
		::= { ringswitchTLSBootPRAServerTable 1 }
	RingswitchTLSBootPRAServerEntry ::=
		SEQUENCE
                {
			ringswitchTLSBootPRAServerCardNum   INTEGER,
                        ringswitchTLSBootPRAServerIpAddress IpAddress,
			ringswitchTLSBootPRAServerName	    OCTET STRING (SIZE (64)),
			ringswitchTLSBootPRAServerEnable    INTEGER
		}
	ringswitchTLSBootPRAServerCardNum OBJECT-TYPE
		SYNTAX	INTEGER
		ACCESS	read-only
		STATUS	mandatory
		DESCRIPTION
			"The TLS card number using this BootP/DHCP server."
		::= { ringswitchTLSBootPRAServerEntry 1 }
	ringswitchTLSBootPRAServerIpAddress OBJECT-TYPE
		SYNTAX	IpAddress
		ACCESS	read-only
		STATUS	mandatory
		DESCRIPTION
			"The IP address of this BootP/DHCP server."
		::= { ringswitchTLSBootPRAServerEntry 2 }
	ringswitchTLSBootPRAServerName OBJECT-TYPE
		SYNTAX	OCTET STRING (SIZE (64))
		ACCESS	read-write
		STATUS	mandatory
		DESCRIPTION
			"The name of the BootP/DHCP server. Clients
	 	        specifying this name in their BootP/DHCP requests
        		have their request frames sent on to this particular
        		server."
		::= { ringswitchTLSBootPRAServerEntry 3 }
	ringswitchTLSBootPRAServerEnable OBJECT-TYPE
		SYNTAX	INTEGER	{
				enable		(1),
				disable		(2)
				}
		ACCESS	read-write
		STATUS	mandatory
		DESCRIPTION
			"Setting to 1 adds a BootP Relay Agent server with 
                        this port and IP address to the list of BootP Relay 
                        Agent servers. Setting to 2 removes this BootP Relay 
                        Agent Server from the list."
		::= { ringswitchTLSBootPRAServerEntry 4 }

-- The TLS VRRP virtual router group
	ringswitchTLSVRRPVRTRTable OBJECT-TYPE
		SYNTAX	SEQUENCE OF RingswitchTLSVRRPVRTREntry
		ACCESS	not-accessible
		STATUS	mandatory
		DESCRIPTION
			"A table containing a list of VRRP virtual routers."
		::= { ringswitchTLS 9 }
	ringswitchTLSVRRPVRTREntry OBJECT-TYPE
		SYNTAX	RingswitchTLSVRRPVRTREntry
		ACCESS	not-accessible
		STATUS	mandatory
		DESCRIPTION
			"Contains information about the
			virtual router."
		INDEX { ringswitchTLSVRRPVRTRPortNum ,
			ringswitchTLSVRRPVRTRIpAddress
                      }
		::= { ringswitchTLSVRRPVRTRTable 1 }
	RingswitchTLSVRRPVRTREntry ::=
		SEQUENCE
                {
            ringswitchTLSVRRPVRTRPortNum        INTEGER,
            ringswitchTLSVRRPVRTRIpAddress      IpAddress,
            ringswitchTLSVRRPVRTRVRID           INTEGER,
			ringswitchTLSVRRPVRTRMacAddress     TRNMacAddress,
			ringswitchTLSVRRPVRTREnable   	    INTEGER,
			ringswitchTLSVRRPVRTRAdvertInterval INTEGER,
			ringswitchTLSVRRPVRTRPriority	    INTEGER,
			ringswitchTLSVRRPVRTRAuthType	    INTEGER,
			ringswitchTLSVRRPVRTRAuthKey	    OCTET STRING (SIZE (8)),
			ringswitchTLSVRRPVRTRAdvertDeadInterval INTEGER
				}
	ringswitchTLSVRRPVRTRPortNum OBJECT-TYPE
		SYNTAX	INTEGER
		ACCESS	read-only
		STATUS	mandatory
		DESCRIPTION
			"The TLS leg port that this virtual
		router is configured to use. There can be a
		maximum of 1 virtual router per leg port."
		::= { ringswitchTLSVRRPVRTREntry 1 }
	ringswitchTLSVRRPVRTRIpAddress OBJECT-TYPE
		SYNTAX	IpAddress
		ACCESS	read-only
		STATUS	mandatory
		DESCRIPTION
			"The IP address of this VRRP virtual
		router. This must be a unique IP address on
		the same subnet as the leg port that the
		virtual router has been	configured to use."
		::= { ringswitchTLSVRRPVRTREntry 2 }
	ringswitchTLSVRRPVRTRVRID OBJECT-TYPE
		SYNTAX	INTEGER (1 .. 255)
		ACCESS	read-write
		STATUS	mandatory
		DESCRIPTION
			"The VRRP virtual router ID.
		Only 1 virtual router with this ID can
		be used on any single Ringswitch."
		::= { ringswitchTLSVRRPVRTREntry 3 }
	ringswitchTLSVRRPVRTRMacAddress OBJECT-TYPE
		SYNTAX	TRNMacAddress
		ACCESS	read-write
		STATUS	mandatory
		DESCRIPTION
			"This is the MAC address that the port
		will use for this VRRP virtual router. It will
		normally be derived from the virtual router VRID
		using the formula 00-00-7A-00-80-<bitswapped VRID>."
		::= { ringswitchTLSVRRPVRTREntry 4 }
	ringswitchTLSVRRPVRTREnable OBJECT-TYPE
		SYNTAX	INTEGER	{
				enable		(1),
				disable		(2)
				}
		ACCESS	read-write
		STATUS	mandatory
		DESCRIPTION
			"Setting to 1 adds a VRRP Virtual Router with this
		port and IP address to the list of VRRP virtual routers.
		Setting to 2 removes this virtual router from the list."
		::= { ringswitchTLSVRRPVRTREntry 5 }
	ringswitchTLSVRRPVRTRAdvertInterval OBJECT-TYPE
		SYNTAX	INTEGER
		ACCESS	read-write
		STATUS	mandatory
		DESCRIPTION
			"The length of time in seconds between
		sending VRRP advertisements. Default is 1 second.
		The value 0 is not allowed."
		::= { ringswitchTLSVRRPVRTREntry 6 }
	ringswitchTLSVRRPVRTRPriority OBJECT-TYPE
		SYNTAX	INTEGER (0 .. 255)
		ACCESS	read-write
		STATUS	mandatory
		DESCRIPTION
			"Priority value used for electing the
		master router for a VRRP virtual router. Default
		value is 100. A value of 255 will force this node
		to act as the master for this virtual router. A
		value of 0 will force this node to act as a 
		backup."
		::= { ringswitchTLSVRRPVRTREntry 7 }
	ringswitchTLSVRRPVRTRAuthType OBJECT-TYPE
		SYNTAX	INTEGER	{
				none		(1),
				simple		(2)
				}
		ACCESS	read-write
		STATUS	mandatory
		DESCRIPTION
			"The type of authentication used
		by VRRP on this port."
		::= { ringswitchTLSVRRPVRTREntry 8 }
	ringswitchTLSVRRPVRTRAuthKey OBJECT-TYPE
		SYNTAX	OCTET STRING (SIZE (8))
		ACCESS	read-write
		STATUS	mandatory
		DESCRIPTION
			"The authentication key to be used
		if ringswitchTLSVRRPVRTRAuthType is set to
		simple."
		::= { ringswitchTLSVRRPVRTREntry 9 }
	ringswitchTLSVRRPVRTRAdvertDeadInterval OBJECT-TYPE
		SYNTAX	INTEGER
		ACCESS	read-write
		STATUS	mandatory
		DESCRIPTION
			"The length of time in seconds after which
        		if no VRRP advert has been received by the master
	        	VRRP router then it will change to backup mode.
		        Default is 4 seconds. The value 0 is not allowed.
        		It is recommended that this value be 4 times the
	        	value set as the AdvertInterval."
		::= { ringswitchTLSVRRPVRTREntry 10 }

----------------------------------------------------------------------------
-- the Ethernet port group

	ringswitchEthernetIfTable OBJECT-TYPE
		SYNTAX  SEQUENCE OF RingswitchEthernetIfEntry
		ACCESS  not-accessible
		STATUS  mandatory
		DESCRIPTION
			"This table contains Ethernet interface parameters 
                        and state variables applying to each ethernet port, 
                        and Ethernet-type interface parameters to configure 
                        translational bridging to Token Ring."
		::= { ringswitchEthernet 1}

	ringswitchEthernetIfEntry OBJECT-TYPE
		SYNTAX  RingswitchEthernetIfEntry
		ACCESS  not-accessible
		STATUS  mandatory
		DESCRIPTION
			"A list of Ethernet status and parameter values for 
                        a ethernet interface, plus a list of Ethernet-type 
                        interface parameters to configure translational 
                        bridging to Token-Ring"
		INDEX { ringswitchEthernetIfIndex }
		::= { ringswitchEthernetIfTable 1 }

	RingswitchEthernetIfEntry ::=
                SEQUENCE        {
                                  ringswitchEthernetIfIndex
                                        INTEGER,
                                  ringswitchEthernetIfIPXEthType
                                        INTEGER,
                                  ringswitchEthernetIfOperIPXEthType
                                        INTEGER,
                                  ringswitchEthernetIfIPXTRType
                                        INTEGER,
                                  ringswitchEthernetIfOperIPXTRType
                                        INTEGER,
                                  ringswitchEthernetIfIPXEnable
                                        INTEGER,
                                  ringswitchEthernetIfIPEnable
                                        INTEGER,
                                  ringswitchEthernetIfAdminSpeed
				        INTEGER,	
                                  ringswitchEthernetIfOperSpeed         
				        INTEGER,
                                  ringswitchEthernetIfAdminDuplexMode
				        INTEGER,
                                  ringswitchEthernetIfOperDuplexMode          
				        INTEGER,
                                  ringswitchEthernetIfIPMulticastType	
				        INTEGER,
                                  ringswitchEthernetIfCacheClear
				        INTEGER,
                                  ringswitchEthernetIfSPTEncaps
				        INTEGER,
                                  ringswitchEthernetIfPriorityTagging  
				        INTEGER,
                                  ringswitchEthernetIfPriorityTaggingVLANId   
				        INTEGER,
                                  ringswitchEthernetIfAdminIPXNetwork
                                        INTEGER,
                                  ringswitchEthernetIfOperIPXNetwork
				        INTEGER,
                                  ringswitchEthernetIfSTPBlockingTrapInfo
                                        INTEGER,
                                  ringswitchEthernetIfAdminFlowCtrl
                                        INTEGER,
                                  ringswitchEthernetIfOperFlowCtrl
                                        INTEGER,
                                  ringswitchEthernetIfAutoNegotiate
                                        INTEGER,
                                  ringswitchEthernetIfMediaType
                                        INTEGER,
                                  ringswitchEthernetIfAdminMaxFrameSize
                                        INTEGER,
                                  ringswitchEthernetIfOperMaxFrameSize
                                        INTEGER
                                }

	ringswitchEthernetIfIndex OBJECT-TYPE
		SYNTAX  INTEGER (1..65535)
		ACCESS  read-only
		STATUS  mandatory
		DESCRIPTION
			"The port number of the Ethernet port for which 
                        this entry contains Ethernet information."
		::= { ringswitchEthernetIfEntry 1 }

	ringswitchEthernetIfIPXEthType OBJECT-TYPE
		SYNTAX  INTEGER {
				auto            (1),
				ieee8022        (2),
				snap            (3),
				ieee8023        (4),
				dix             (5)
				}
		ACCESS  read-write
		STATUS  mandatory
		DESCRIPTION
			"This variable specifies the encapsulation type on
			 the Ethernet card for all forwarded IPX frames 
                         from a TRN."
		::= { ringswitchEthernetIfEntry 2 }

	ringswitchEthernetIfOperIPXEthType OBJECT-TYPE
		SYNTAX	INTEGER	{
				unknown (1),
				ieee8022(2),
				snap    (3),
				ieee8023(4),
				dix     (5)
				}
		ACCESS  read-only
		STATUS  mandatory
		DESCRIPTION	
			"This variable specifies the actual encapsulation 
			type for all IPX frames forwarded onto Ethernet"
		::= { ringswitchEthernetIfEntry 3 }

	ringswitchEthernetIfIPXTRType OBJECT-TYPE
		SYNTAX  INTEGER {
				auto            (1),
				ieee8022        (2),
				snap            (3)
				}
		ACCESS  read-write
		STATUS  mandatory
		DESCRIPTION
			"This variable specifies the encapsulation type on 
			TRN for all IPX frames forwarded from an Ethernet port"
		::= { ringswitchEthernetIfEntry 4 }

	ringswitchEthernetIfOperIPXTRType OBJECT-TYPE
		SYNTAX	INTEGER	{
				unknown (1),
				ieee8022(2),
				snap    (3)
				}
		ACCESS  read-only
		STATUS  mandatory
		DESCRIPTION	       			    		
			"This variable specifies the actual encapsulation 
			type for all IPX frames forwarded onto Token Ring"
		::= { ringswitchEthernetIfEntry 5 }

	ringswitchEthernetIfIPXEnable OBJECT-TYPE
		SYNTAX  INTEGER {
				enable          (1),
				disable         (2)
				}
		ACCESS  read-write
		STATUS  mandatory
		DESCRIPTION
			"If this variable is enabled on an Ethernet port 
			 then the port will do translational bridging of IPX 
			 frames, otherwise it will discard them.  It is 
			 ignored for Token Ring ports"
		::= { ringswitchEthernetIfEntry 6 }

	ringswitchEthernetIfIPEnable OBJECT-TYPE
		SYNTAX  INTEGER {
				enable          (1),
				disable         (2)
				}
		ACCESS  read-write
		STATUS  mandatory
		DESCRIPTION
			"If this variable is enabled on an Ethernet port 
			 then the port will do translational bridging of IP,
			 ARP and RARP frames, otherwise it will discard them. 
			 It is ignored for Token Ring ports"
		::= { ringswitchEthernetIfEntry 7 }

	ringswitchEthernetIfAdminSpeed OBJECT-TYPE
		SYNTAX  INTEGER {
				auto               (1),
				speed10Mbps        (2),
                                speed100Mbps       (3),
                                speed1000Mbps      (4)
				}
		ACCESS  read-write
		STATUS  mandatory
		DESCRIPTION
			"This variable specifies the speed that the Ethernet 
                         port will open at."
		::= { ringswitchEthernetIfEntry 8 }

	ringswitchEthernetIfOperSpeed OBJECT-TYPE
		SYNTAX  INTEGER {
				unknown  (1), 
				ten      (2),
				hundred  (3),
                                thousand (4)
				}
		ACCESS  read-only
		STATUS  mandatory
		DESCRIPTION
			"The current operational speed of the network to 
			which this interface is connected."
		::= { ringswitchEthernetIfEntry 9 }

	ringswitchEthernetIfAdminDuplexMode OBJECT-TYPE
		SYNTAX  INTEGER {
                                auto             (1),
                                half             (2),
                                full             (3)
				}
		ACCESS  read-write
		STATUS  mandatory
		DESCRIPTION
			"This variable specifies the duplex mode of the 
                         Ethernet port."
		::= { ringswitchEthernetIfEntry 10 }

	ringswitchEthernetIfOperDuplexMode OBJECT-TYPE
		SYNTAX  INTEGER {
				unknown         (1),
				half-duplex     (2),
				full-duplex     (3)
				}
		ACCESS  read-only
		STATUS  mandatory
		DESCRIPTION
			"The current operational mode of this interface."
		::= { ringswitchEthernetIfEntry 11 }

	ringswitchEthernetIfIPMulticastType OBJECT-TYPE
		SYNTAX	INTEGER {
				broadcast (1),
				functional(2),
				group     (3)
				}
		ACCESS  read-write
		STATUS  mandatory
		DESCRIPTION
			"This variable specifies the type of MAC address to
			use as the destination for IP multicast frames on
			Token Ring"
		::= { ringswitchEthernetIfEntry 12 }
					
	ringswitchEthernetIfCacheClear OBJECT-TYPE
		SYNTAX	INTEGER {
				clear (1)
				}
		ACCESS  write-only
		STATUS  mandatory
		DESCRIPTION
			"This variable clears the RIF cache"
		::= { ringswitchEthernetIfEntry 13 }
					
	ringswitchEthernetIfSPTEncaps OBJECT-TYPE  
		SYNTAX	INTEGER	{
				enabled	(1),
				disabled(2)
				}
		ACCESS  read-write
		STATUS  mandatory
		DESCRIPTION
			"This variable specifies whether BPDU's received
			from Ethernet are encapsulated when forwared onto
			Token Ring. Encapsulated BPDU's are de-encapsulated
			when forwarded to Ethernet"
		::= { ringswitchEthernetIfEntry 14 }

	ringswitchEthernetIfPriorityTagging OBJECT-TYPE  
		SYNTAX	INTEGER	{
				enabled	(1),
				disabled(2)
				}
		ACCESS  read-write
		STATUS  mandatory
		DESCRIPTION
                        "When this variable is enabled, frames onto ethernet
                        ring are priority tagged (using 802.1p) with the 
                        token ring priority"
		::= { ringswitchEthernetIfEntry 15 }

	ringswitchEthernetIfPriorityTaggingVLANId OBJECT-TYPE  
		SYNTAX	INTEGER	(0..4095)
		ACCESS  read-write
		STATUS  mandatory
		DESCRIPTION
                        "VLAN ID to be used when 
                        ringswitchEthernetIfPriorityTagging is enabled."
		::= { ringswitchEthernetIfEntry 16 }

	ringswitchEthernetIfAdminIPXNetwork OBJECT-TYPE
		SYNTAX	INTEGER
		ACCESS  read-write
		STATUS  mandatory
		DESCRIPTION
			"The IPX network number of the port. If this is
			zero then the IPX network number is learned 
			automatically."
		::= { ringswitchEthernetIfEntry 17 }

	ringswitchEthernetIfOperIPXNetwork OBJECT-TYPE
		SYNTAX	INTEGER
		ACCESS  read-only
		STATUS  mandatory
		DESCRIPTION	    				
			"The actual IPX network number of the port."
		::= { ringswitchEthernetIfEntry 18 }

	ringswitchEthernetIfSTPBlockingTrapInfo OBJECT-TYPE
		SYNTAX	INTEGER {
                blocked   (1),
                unblocked (2)
                }
		ACCESS  read-only
		STATUS  mandatory
		DESCRIPTION
			"Trap set if circulating encapsulated BPDU frames 
                         are detected (indicating a 3rd party bridge) which 
                         cause the port to go into blocking mode. A trap is
			 also sent if the port becomes unblocked after 
                         previously being blocked."
		::= { ringswitchEthernetIfEntry 19 }

	ringswitchEthernetIfAdminFlowCtrl OBJECT-TYPE
		SYNTAX  INTEGER {
				not-applicable        (1),
				no-pause              (2),
                                tx-pause              (3),
                                rx-pause              (4),
                                tx-rx-pause           (5)
				}
		ACCESS  read-write
		STATUS  mandatory
		DESCRIPTION
			"This variable specifies the flow control abilities
                         that the Gigabit port will use. For 10/100 Ethernet 
                         ports this variable will always be not-applicable."
		::= { ringswitchEthernetIfEntry 20 }

	ringswitchEthernetIfOperFlowCtrl OBJECT-TYPE
		SYNTAX  INTEGER {
				unknown               (1),
				no-pause              (2),
                                tx-pause              (3),
                                rx-pause              (4),
                                tx-rx-pause           (5)
				}
		ACCESS  read-only
		STATUS  mandatory
		DESCRIPTION
			"The current flow control operational mode for the
                         Gigabit interface. For 10/100 Ethernet ports this 
                         variable will always be unknown."
		::= { ringswitchEthernetIfEntry 21 }

	ringswitchEthernetIfAutoNegotiate OBJECT-TYPE  
		SYNTAX	INTEGER	{
				enabled        (1),
				disabled       (2),
                                not-applicable (3)
				}
		ACCESS  read-write
		STATUS  mandatory
		DESCRIPTION
			"This variable specifies whether the Gigabit
                        interface will auto-negotiate the link properties
                        or whether it will force the link up. For 10/100
                        Ethernet interfaces this variable will always be
                        not applicable. Auto-negotiation for 10/100 Ethernet
                        is done by setting the speed or duplex mode to
                        auto."
		::= { ringswitchEthernetIfEntry 22 }

	ringswitchEthernetIfMediaType OBJECT-TYPE  
		SYNTAX	INTEGER	{
                                copper         (1),
				fibre-sx       (2),
				fibre-lx       (3)
				}
		ACCESS  read-only
		STATUS  mandatory
		DESCRIPTION
			"This variable specifies the media type of the 
                        10/100 Ethernet or Gigabit port."
		::= { ringswitchEthernetIfEntry 23 }

	ringswitchEthernetIfAdminMaxFrameSize OBJECT-TYPE
		SYNTAX	INTEGER
		ACCESS  read-write
		STATUS  mandatory
		DESCRIPTION	    				
			"The maximum frame size requested for the Ethernet
                        or Gigabit port. For 10/100 Ethernet this value can 
                        only be set to 1514. For Gigabit other larger values
                        are supported for jumbo frames. Any changes to this
                        value will not take place until the switch is 
                        rebooted. The max size available will be dependent
                        on the switch buffer size - 5K or 18K."
		::= { ringswitchEthernetIfEntry 24 }

	ringswitchEthernetIfOperMaxFrameSize OBJECT-TYPE
		SYNTAX	INTEGER
		ACCESS  read-write
		STATUS  mandatory
		DESCRIPTION	    				
			"The maximum frame size currently used on the Ethernet
                        or Gigabit port. For 10/100 Ethernet this value can 
                        only be 1514. For Gigabit other larger values
                        are supported for jumbo frames."
		::= { ringswitchEthernetIfEntry 25 }

        

-- the ringswitch ethernet translational bridge duplicate address group
	
	ringswitchEthernetXBDupAddrTable OBJECT-TYPE
		SYNTAX  SEQUENCE OF RingswitchEthernetXBDupAddrEntry
		ACCESS  not-accessible
		STATUS  mandatory
		DESCRIPTION
			"This table duplicate mac address information"
		::= { ringswitchEthernet 2 } 

	ringswitchEthernetXBDupAddrEntry OBJECT-TYPE
		SYNTAX  RingswitchEthernetXBDupAddrEntry
		ACCESS  not-accessible
		STATUS  mandatory
		DESCRIPTION
			"A list of duplicate mac addresses for each Ethernet port in the rsw"
		INDEX { ringswitchEthernetXBDupAddrIfIndex,
			ringswitchEthernetXBDupAddrIndex }
		::= { ringswitchEthernetXBDupAddrTable 1 }

	RingswitchEthernetXBDupAddrEntry
			::= SEQUENCE
			{		     		
			ringswitchEthernetXBDupAddrIfIndex    INTEGER,
			ringswitchEthernetXBDupAddrIndex      INTEGER,
			ringswitchEthernetXBDupAddrMacAddress TRNMacAddress
			}		 		
			
	ringswitchEthernetXBDupAddrIfIndex OBJECT-TYPE
		SYNTAX  INTEGER
		ACCESS  read-only
		STATUS  mandatory
		DESCRIPTION
			"The value of this object identifies the
			ethernet interface for which this entry
			contains management information.  The
			value of this object for a particular
			interface has the same value as the
			ifIndex object for the same interface."
		::= { ringswitchEthernetXBDupAddrEntry 1 }
			
	ringswitchEthernetXBDupAddrIndex OBJECT-TYPE
		SYNTAX  INTEGER (1..10)
		ACCESS  read-only
		STATUS  mandatory
		DESCRIPTION
			"An arbitrary index ..."
		::= { ringswitchEthernetXBDupAddrEntry 2 }

	ringswitchEthernetXBDupAddrMacAddress OBJECT-TYPE   
		SYNTAX	TRNMacAddress	
		ACCESS  read-write
		STATUS  mandatory
		DESCRIPTION
			""
		::= { ringswitchEthernetXBDupAddrEntry 3 }

-- the ringswitch ethernet to tokenring translational bridge statistics group

	ringswitchEthernetXBToTRNStatsTable OBJECT-TYPE
		SYNTAX  SEQUENCE OF RingswitchEthernetXBToTRNStatsEntry
		ACCESS  not-accessible
		STATUS  mandatory
		DESCRIPTION
			"This table contains information relating to the
			forwarding statistics that are maintained by each
			ethernet interface acting as a translational
			bridge to Token-ring."
		::= { ringswitchEthernet 3 } 

	ringswitchEthernetXBToTRNStatsEntry OBJECT-TYPE
		SYNTAX  RingswitchEthernetXBToTRNStatsEntry
		ACCESS  not-accessible
		STATUS  mandatory
		DESCRIPTION		      				
			"A list of information relating to the forwarding
			statistics of a single ethernet interface acting 
			as a translational bridge to Token-ring."
		INDEX { ringswitchEthernetXBToTRNStatsIfIndex }
		::= { ringswitchEthernetXBToTRNStatsTable 1 }
				
	RingswitchEthernetXBToTRNStatsEntry
		::= SEQUENCE
		{		     		
		ringswitchEthernetXBToTRNStatsIfIndex            INTEGER,
		ringswitchEthernetXBToTRNStatsDiscSptEncapsBlock INTEGER48,
		ringswitchEthernetXBToTRNStatsDiscFilter	 INTEGER48,
                ringswitchEthernetXBToTRNStatsDiscBPDU		 INTEGER48,
		ringswitchEthernetXBToTRNStatsDiscBPDUEncaps     INTEGER48,
		ringswitchEthernetXBToTRNStatsDiscTag8021qCfi    INTEGER48,
		ringswitchEthernetXBToTRNStatsDiscTag8021qVlan   INTEGER48,
		ringswitchEthernetXBToTRNStatsDiscBadRif         INTEGER48,
		ringswitchEthernetXBToTRNStatsDiscHopLimit       INTEGER48,
		ringswitchEthernetXBToTRNStatsDiscDuplicateRin   INTEGER48,
		ringswitchEthernetXBToTRNStatsDiscIPDisabled     INTEGER48,
		ringswitchEthernetXBToTRNStatsDiscARPDisabled    INTEGER48,
		ringswitchEthernetXBToTRNStatsDiscNCPCache       INTEGER48,
		ringswitchEthernetXBToTRNStatsDiscIPXDisabled    INTEGER48,
		ringswitchEthernetXBToTRNStatsDiscIPXTypeSnap    INTEGER48,
		ringswitchEthernetXBToTRNStatsDiscIPXType8022    INTEGER48,
		ringswitchEthernetXBToTRNStatsDiscIPXType8023    INTEGER48,
		ringswitchEthernetXBToTRNStatsDiscIPXTypeDix     INTEGER48,

		ringswitchEthernetXBToTRNStatsNoFakeBuffer       INTEGER48,
		ringswitchEthernetXBToTRNStatsCacheFull          INTEGER48,

		ringswitchEthernetXBToTRNStatsFwdIPFrames	 INTEGER48,
		ringswitchEthernetXBToTRNStatsFwdIPMulticast	 INTEGER48,
		ringswitchEthernetXBToTRNStatsFwdARPFrames	 INTEGER48,
		ringswitchEthernetXBToTRNStatsFwdIPXFrames	 INTEGER48,
		ringswitchEthernetXBToTRNStatsFwdAARPPh1Frames	 INTEGER48,
		ringswitchEthernetXBToTRNStatsFwdAARPPh2Frames	 INTEGER48,
		ringswitchEthernetXBToTRNStatsFwdOtherEthFrames	 INTEGER48,
		ringswitchEthernetXBToTRNStatsFwdZeroOUIFrames	 INTEGER48,
		ringswitchEthernetXBToTRNStatsFwdOtherDLCFrames	 INTEGER48,
		ringswitchEthernetXBToTRNStatsFwdBPDUEncaps	 INTEGER48,
		ringswitchEthernetXBToTRNStatsFwdBPDUDecaps	 INTEGER48
		}		 			
							
	ringswitchEthernetXBToTRNStatsIfIndex OBJECT-TYPE
		SYNTAX  INTEGER
		ACCESS  read-only
		STATUS  mandatory
		DESCRIPTION
			"The value of this object identifies the
			ethernet interface for which this entry
			contains management information.  The
			value of this object for a particular
			interface has the same value as the
			ifIndex object for the same interface."
		::= { ringswitchEthernetXBToTRNStatsEntry 1 }

	ringswitchEthernetXBToTRNStatsDiscSptEncapsBlock OBJECT-TYPE
		SYNTAX  INTEGER48
		ACCESS  read-only
		STATUS  mandatory
		DESCRIPTION						
			"The number of received frames discarded by this 
			interface because the encasulated spanning tree 
			detected a 3rd party bridge loop and has forced 
			blocking. These frames will be counted in forwarding
			statistics even	though the frame is discarded."
		::= { ringswitchEthernetXBToTRNStatsEntry 2 }

	ringswitchEthernetXBToTRNStatsDiscFilter OBJECT-TYPE
		SYNTAX  INTEGER48
		ACCESS  read-only
		STATUS  mandatory
		DESCRIPTION						
			"The number of received frames discarded by this 
			interface because the DA was known to be on Ethernet."
		::= { ringswitchEthernetXBToTRNStatsEntry 3 }

	ringswitchEthernetXBToTRNStatsDiscBPDU OBJECT-TYPE
		SYNTAX  INTEGER48
		ACCESS  read-only
		STATUS  mandatory
		DESCRIPTION
			"The number of BPDU's received from Ethernet 
			which have been discarded (i.e. not received)
			by this interface because they could not be   	
			encapsulated (e.g. because they are too big). Only 
			counted when encapsulated SPT is enabled."
		::= { ringswitchEthernetXBToTRNStatsEntry 4 }
	
	ringswitchEthernetXBToTRNStatsDiscBPDUEncaps OBJECT-TYPE
		SYNTAX  INTEGER48
		ACCESS  read-only
		STATUS  mandatory
		DESCRIPTION					  	
			"The number of received encapsulated BPDU frames 
			discarded by this interface because they are invalid
			or duplicates. Only counted when encapsulated SPT is 
			enabled."
		::= { ringswitchEthernetXBToTRNStatsEntry 5 }

	ringswitchEthernetXBToTRNStatsDiscTag8021qCfi OBJECT-TYPE
		SYNTAX  INTEGER48
		ACCESS  read-only
		STATUS  mandatory
		DESCRIPTION						
			"The number of received frames discarded by this 
			interface because they are 802.1Q encapsulated 
			Token Ring frames."
		::= { ringswitchEthernetXBToTRNStatsEntry 6 }

	ringswitchEthernetXBToTRNStatsDiscTag8021qVlan OBJECT-TYPE
		SYNTAX  INTEGER48
		ACCESS  read-only
		STATUS  mandatory
		DESCRIPTION						
			"The number of received frames discarded by this 
			interface because they have an 802.1Q tag with the 
			wrong VLAN id. Only counted when ethernet tagging 
			is enabled."
		::= { ringswitchEthernetXBToTRNStatsEntry 7 }

	ringswitchEthernetXBToTRNStatsDiscBadRif OBJECT-TYPE
		SYNTAX  INTEGER48
		ACCESS  read-only
		STATUS  mandatory
		DESCRIPTION						
			"The number of received frames discarded by this 
			interface because a non-cached RIF is invalid."
		::= { ringswitchEthernetXBToTRNStatsEntry 8 }

	ringswitchEthernetXBToTRNStatsDiscHopLimit OBJECT-TYPE
		SYNTAX  INTEGER48
		ACCESS  read-only
		STATUS  mandatory
		DESCRIPTION						
			"The number of received frames discarded by this 
			interface because a non-cached RIF is longer than 
			the hop-count limit."
		::= { ringswitchEthernetXBToTRNStatsEntry 9 }

	ringswitchEthernetXBToTRNStatsDiscDuplicateRin OBJECT-TYPE
		SYNTAX  INTEGER48
		ACCESS  read-only
		STATUS  mandatory
		DESCRIPTION						
			"The number of received frames discarded by this 
			interface because a non-cached RIF contains the 
			interface's ring number twice."
		::= { ringswitchEthernetXBToTRNStatsEntry 10 }

	ringswitchEthernetXBToTRNStatsDiscIPDisabled OBJECT-TYPE
		SYNTAX  INTEGER48
		ACCESS  read-only
		STATUS  mandatory
		DESCRIPTION						
			"The number of received frames discarded by this 
			interface because IP forwarding is disabled."
		::= { ringswitchEthernetXBToTRNStatsEntry 11 }

	ringswitchEthernetXBToTRNStatsDiscARPDisabled OBJECT-TYPE
		SYNTAX  INTEGER48
		ACCESS  read-only
		STATUS  mandatory
		DESCRIPTION	
			"The number of received ARP and RARP frames discarded 
			by this interface because IP forwarding is disabled."
		::= { ringswitchEthernetXBToTRNStatsEntry 12 }

	ringswitchEthernetXBToTRNStatsDiscNCPCache OBJECT-TYPE
		SYNTAX  INTEGER48
		ACCESS  read-only
		STATUS  mandatory
		DESCRIPTION				    		
			"The number of received NCP requests discarded by 
			this interface because they could not be cached."
		::= { ringswitchEthernetXBToTRNStatsEntry 13 }

	ringswitchEthernetXBToTRNStatsDiscIPXDisabled OBJECT-TYPE
		SYNTAX  INTEGER48
		ACCESS  read-only
		STATUS  mandatory
		DESCRIPTION						
			"The number of received frames discarded by this 
			interface because IPX forwarding is disabled."
		::= { ringswitchEthernetXBToTRNStatsEntry 14 }

	ringswitchEthernetXBToTRNStatsDiscIPXTypeSnap OBJECT-TYPE
		SYNTAX  INTEGER48
		ACCESS  read-only
		STATUS  mandatory
		DESCRIPTION				 		
			"The number of received IPX SNAP frames discarded by 
			this interface because SNAP encapsulation is not 
			selected on this interface."
		::= { ringswitchEthernetXBToTRNStatsEntry 15 }

	ringswitchEthernetXBToTRNStatsDiscIPXType8022 OBJECT-TYPE
		SYNTAX  INTEGER48
		ACCESS  read-only
		STATUS  mandatory
		DESCRIPTION	
			"The number of received 802.2 IPX frames discarded by 
			this interface because 802.2 encapsulation is not 
			selected on this interface."
		::= { ringswitchEthernetXBToTRNStatsEntry 16 }

	ringswitchEthernetXBToTRNStatsDiscIPXType8023 OBJECT-TYPE
		SYNTAX  INTEGER48
		ACCESS  read-only
		STATUS  mandatory
		DESCRIPTION				  		
			"The number of received 802.3 IPX frames discarded by 
			this interface because 802.3 encapsulation is not 
			selected on this interface."
		::= { ringswitchEthernetXBToTRNStatsEntry 17 }

	ringswitchEthernetXBToTRNStatsDiscIPXTypeDix OBJECT-TYPE
		SYNTAX  INTEGER48
		ACCESS  read-only
		STATUS  mandatory
		DESCRIPTION
			"The number of received DIX IPX frames discarded by 
			this interface because DIX encapsulation is not 
			selected on this interface."
		::= { ringswitchEthernetXBToTRNStatsEntry 18 }

	ringswitchEthernetXBToTRNStatsNoFakeBuffer OBJECT-TYPE
		SYNTAX  INTEGER48
		ACCESS  read-only
		STATUS  mandatory
		DESCRIPTION
			"The number of ICMP can't fragment frames which could
			not be sent due to resource limitations."
		::= { ringswitchEthernetXBToTRNStatsEntry 19 }

	ringswitchEthernetXBToTRNStatsCacheFull OBJECT-TYPE
		SYNTAX  INTEGER48
		ACCESS  read-only
		STATUS  mandatory
		DESCRIPTION
			"The number of frames received by this interface 
			whose source address could not be cached because 
			the cache is full."
		::= { ringswitchEthernetXBToTRNStatsEntry 20 }

	ringswitchEthernetXBToTRNStatsFwdIPFrames OBJECT-TYPE
		SYNTAX  INTEGER48
		ACCESS  read-only
		STATUS  mandatory
		DESCRIPTION						
			"The number of received IP frames forwarded to Token
			Ring by this interface."
		::= { ringswitchEthernetXBToTRNStatsEntry 21 }

	ringswitchEthernetXBToTRNStatsFwdIPMulticast OBJECT-TYPE
		SYNTAX  INTEGER48
		ACCESS  read-only
		STATUS  mandatory
		DESCRIPTION
			"The number of received IP multicast frames forwarded 
			to Token Ring by this interface. These are included 
			in the count of IP frames."
		::= { ringswitchEthernetXBToTRNStatsEntry 22 }

	ringswitchEthernetXBToTRNStatsFwdARPFrames OBJECT-TYPE
		SYNTAX  INTEGER48
		ACCESS  read-only
		STATUS  mandatory
		DESCRIPTION
			"The number of received ARP an RARP frames forwarded 
			to Token Ring by this interface."
		::= { ringswitchEthernetXBToTRNStatsEntry 23 }

	ringswitchEthernetXBToTRNStatsFwdIPXFrames OBJECT-TYPE
		SYNTAX  INTEGER48
		ACCESS  read-only
		STATUS  mandatory
		DESCRIPTION
			"The number of received IPX frames forwarded to Token
			Ring by this interface."
		::= { ringswitchEthernetXBToTRNStatsEntry 24 }

	ringswitchEthernetXBToTRNStatsFwdAARPPh1Frames OBJECT-TYPE
		SYNTAX  INTEGER48
		ACCESS  read-only
		STATUS  mandatory
		DESCRIPTION
			"The number of received Appletalk phase 1 (Ethertype)
			frames forwarded to Token Ring by this interface."
		::= { ringswitchEthernetXBToTRNStatsEntry 25 }

	ringswitchEthernetXBToTRNStatsFwdAARPPh2Frames OBJECT-TYPE
		SYNTAX  INTEGER48
		ACCESS  read-only
		STATUS  mandatory
		DESCRIPTION
			"The number of received Appletalk phase 2 (SNAP)
			frames forwarded to Token Ring by this interface."
		::= { ringswitchEthernetXBToTRNStatsEntry 26 }

	ringswitchEthernetXBToTRNStatsFwdOtherEthFrames OBJECT-TYPE
		SYNTAX  INTEGER48
		ACCESS  read-only
		STATUS  mandatory
		DESCRIPTION				  		
			"The number of received Ethertype frames forwarded to 
			Token Ring by this interface which have not been 
			included in a more specific counter."
		::= { ringswitchEthernetXBToTRNStatsEntry 27 }

	ringswitchEthernetXBToTRNStatsFwdZeroOUIFrames OBJECT-TYPE
		SYNTAX  INTEGER48
		ACCESS  read-only
	        STATUS  deprecated
		DESCRIPTION
			"The number of received zero OUI SNAP frames that
			have been converted to 802.1H tunnel frames and 
			forwarded to Token Ring by this interface."
		::= { ringswitchEthernetXBToTRNStatsEntry 28 }

	ringswitchEthernetXBToTRNStatsFwdOtherDLCFrames OBJECT-TYPE
		SYNTAX  INTEGER48
		ACCESS  read-only
		STATUS  mandatory
		DESCRIPTION
			"The number of received non-zero OUI SNAP and other 
			DLC frames that have been forwarded to Token Ring 
			and which have not been included in a more specific 
			counter."
		::= { ringswitchEthernetXBToTRNStatsEntry 29 }

	ringswitchEthernetXBToTRNStatsFwdBPDUEncaps OBJECT-TYPE
		SYNTAX  INTEGER48
		ACCESS  read-only
		STATUS  mandatory
		DESCRIPTION
			"The number of received BPDU's which have been
			encapsulated before being forwarded to Token Ring.
			Only counted when encapsulated SPT is enabled."
		::= { ringswitchEthernetXBToTRNStatsEntry 30 }

	ringswitchEthernetXBToTRNStatsFwdBPDUDecaps OBJECT-TYPE
		SYNTAX  INTEGER48
		ACCESS  read-only
		STATUS  mandatory
		DESCRIPTION
			"The number of received BPDU's which have been
			de-encapsulated before being forwarded to Token Ring.
			Only counted when encapsulated SPT is enabled."
		::= { ringswitchEthernetXBToTRNStatsEntry 31 }

-- the ringswitch tokenring to ethernet translational bridge statistics group

	ringswitchEthernetXBFromTRNStatsTable OBJECT-TYPE
		SYNTAX  SEQUENCE OF RingswitchEthernetXBFromTRNStatsEntry
		ACCESS  not-accessible
		STATUS  mandatory
		DESCRIPTION
			"This table contains information relating to the
			forwarding statistics that are maintained by each
			ethernet interface acting as a translational
			bridge from Token-ring."
		::= { ringswitchEthernet 4 } 

	ringswitchEthernetXBFromTRNStatsEntry OBJECT-TYPE
		SYNTAX  RingswitchEthernetXBFromTRNStatsEntry
		ACCESS  not-accessible
		STATUS  mandatory
		DESCRIPTION		      				
			"A list of information relating to the forwarding
			statistics of a single ethernet interface acting 
			as a translational bridge from Token-ring."
		INDEX { ringswitchEthernetXBFromTRNStatsIfIndex }
		::= { ringswitchEthernetXBFromTRNStatsTable 1 }
				
	RingswitchEthernetXBFromTRNStatsEntry
		::= SEQUENCE
		{		     		
		ringswitchEthernetXBFromTRNStatsIfIndex              INTEGER,
		ringswitchEthernetXBFromTRNStatsDiscTooBig	         INTEGER48,
		ringswitchEthernetXBFromTRNStatsDiscSptEncapsBlock   INTEGER48,
		ringswitchEthernetXBFromTRNStatsDiscFilter	         INTEGER48,
		ringswitchEthernetXBFromTRNStatsDiscBPDU		     INTEGER48,
		ringswitchEthernetXBFromTRNStatsDiscBPDUEncaps	     INTEGER48,
		ringswitchEthernetXBFromTRNStatsDiscTag8021qCfi	     INTEGER48,
		ringswitchEthernetXBFromTRNStatsDiscTag8021qVlan	 INTEGER48,
		ringswitchEthernetXBFromTRNStatsDiscBadRIF	         INTEGER48,
		ringswitchEthernetXBFromTRNStatsDiscZeroRingNum	     INTEGER48,
		ringswitchEthernetXBFromTRNStatsDiscNonTermRIF	     INTEGER48,
		ringswitchEthernetXBFromTRNStatsDiscIPDisabled	     INTEGER48,
		ringswitchEthernetXBFromTRNStatsDiscARPDisabled	     INTEGER48,
		ringswitchEthernetXBFromTRNStatsDiscIPCantFrag	     INTEGER48,
		ringswitchEthernetXBFromTRNStatsDiscNCPCache	     INTEGER48,
		ringswitchEthernetXBFromTRNStatsDiscIPXDisabled	     INTEGER48,
		ringswitchEthernetXBFromTRNStatsDiscIPXTypeSnap	     INTEGER48,
		ringswitchEthernetXBFromTRNStatsDiscIPXType8022	     INTEGER48,

		ringswitchEthernetXBFromTRNStatsCacheFull    	     INTEGER48,
		ringswitchEthernetXBFromTRNStatsRIFCacheFull 	     INTEGER48,

		ringswitchEthernetXBFromTRNStatsFwdIPFrames   	     INTEGER48,
		ringswitchEthernetXBFromTRNStatsFwdIPFragmented	     INTEGER48,
		ringswitchEthernetXBFromTRNStatsFwdIPMulticast	     INTEGER48,
		ringswitchEthernetXBFromTRNStatsFwdARPFrames	     INTEGER48,
		ringswitchEthernetXBFromTRNStatsFwdIPXFrames	     INTEGER48,
		ringswitchEthernetXBFromTRNStatsFwdAARPPh1Frames	 INTEGER48,
		ringswitchEthernetXBFromTRNStatsFwdAARPPh2Frames	 INTEGER48,
		ringswitchEthernetXBFromTRNStatsFwdTunnel8021hFrames INTEGER48,
		ringswitchEthernetXBFromTRNStatsFwdZeroOUISnapFrames INTEGER48,
		ringswitchEthernetXBFromTRNStatsFwdOtherDLCFrames    INTEGER48,
		ringswitchEthernetXBFromTRNStatsFwdBPDUDecaps	     INTEGER48,
 		ringswitchEthernetXBFromTRNStatsFwdBPDUEncaps 	     INTEGER48
		}		 			
							
	ringswitchEthernetXBFromTRNStatsIfIndex OBJECT-TYPE
		SYNTAX  INTEGER
		ACCESS  read-only
		STATUS  mandatory
		DESCRIPTION
			"The value of this object identifies the
			ethernet interface for which this entry
			contains management information.  The
			value of this object for a particular
			interface has the same value as the
			ifIndex object for the same interface."
		::= { ringswitchEthernetXBFromTRNStatsEntry 1 }
						
	ringswitchEthernetXBFromTRNStatsDiscTooBig OBJECT-TYPE
		SYNTAX  INTEGER48
		ACCESS  read-only
		STATUS  mandatory
		DESCRIPTION
			"The number of frames received from Token Ring 
			which have been discarded (i.e. not transmitted)
			by this interface because after translation to 
			Ethernet they were bigger than 1514 bytes. These
			frames are counted by the forwarding counters even
			though they are discarded."
		::= { ringswitchEthernetXBFromTRNStatsEntry 2 }

	ringswitchEthernetXBFromTRNStatsDiscSptEncapsBlock OBJECT-TYPE
		SYNTAX  INTEGER48
		ACCESS  read-only
		STATUS  mandatory
		DESCRIPTION
			"The number of frames received from Token Ring 
			which have been discarded (i.e. not transmitted)
			by this interface because the encasulated spanning 
			tree detected a 3rd party bridge loop and has forced 
			blocking. These	frames are counted by the forwarding 
			counters even though they are discarded."
		::= { ringswitchEthernetXBFromTRNStatsEntry 3 }

	ringswitchEthernetXBFromTRNStatsDiscFilter OBJECT-TYPE
		SYNTAX  INTEGER48
		ACCESS  read-only
		STATUS  mandatory
		DESCRIPTION
			"The number of frames received from Token Ring 
			which have been discarded (i.e. not transmitted)
			by this interface because the destination MAC address
			was known to be on Token Ring."
		::= { ringswitchEthernetXBFromTRNStatsEntry 4 }

	ringswitchEthernetXBFromTRNStatsDiscBPDU OBJECT-TYPE
		SYNTAX  INTEGER48
		ACCESS  read-only
		STATUS  mandatory
		DESCRIPTION
			"The number of BPDU's received from Token Ring 
			which have been discarded (i.e. not transmitted)
			by this interface because they could not be   	
			encapsulated (e.g. because they are too big). Only 
			counted when encapsulated SPT is enabled."
		::= { ringswitchEthernetXBFromTRNStatsEntry 5 }

	ringswitchEthernetXBFromTRNStatsDiscBPDUEncaps OBJECT-TYPE
		SYNTAX  INTEGER48
		ACCESS  read-only
		STATUS  mandatory
		DESCRIPTION				  		
			"The number of encapsulated BPDU's received from 
			Token Ring which have been discarded (i.e. not 
			transmitted) by this interface because they are 
			invalid or are ARE duplicates. Only counted when 
			encapsulated SPT is enabled."
		::= { ringswitchEthernetXBFromTRNStatsEntry 6 }

	ringswitchEthernetXBFromTRNStatsDiscTag8021qCfi OBJECT-TYPE
		SYNTAX  INTEGER48
		ACCESS  read-only
		STATUS  mandatory
		DESCRIPTION
			"The number of frames received from Token Ring 
			which have been discarded (i.e. not transmitted)
			by this interface because they are 802.1Q 
			encapsulated Ethernet frames."
		::= { ringswitchEthernetXBFromTRNStatsEntry 7 }

	ringswitchEthernetXBFromTRNStatsDiscTag8021qVlan OBJECT-TYPE
		SYNTAX  INTEGER48
		ACCESS  read-only
		STATUS  mandatory
		DESCRIPTION
			"The number of frames received from Token Ring 
			which have been discarded (i.e. not transmitted)
			by this interface because they have an 802.1Q tag
			with the wrong VLAN id. Only counted when Ethernet
			Tagging is enabled."
		::= { ringswitchEthernetXBFromTRNStatsEntry 8 }

	ringswitchEthernetXBFromTRNStatsDiscBadRIF OBJECT-TYPE
		SYNTAX  INTEGER48
		ACCESS  read-only
		STATUS  mandatory
		DESCRIPTION
			"The number of frames received from Token Ring 
			which have been discarded (i.e. not transmitted)
			by this interface because the RIF is invalid."
		::= { ringswitchEthernetXBFromTRNStatsEntry 9 }

	ringswitchEthernetXBFromTRNStatsDiscZeroRingNum OBJECT-TYPE
		SYNTAX  INTEGER48
		ACCESS  read-only
		STATUS  mandatory
		DESCRIPTION			     			
			"The number of source-routed frames received from 
			Token Ring which have been discarded (i.e. not 
			transmitted) by this interface because we do not have
			a ring number for the interface."
		::= { ringswitchEthernetXBFromTRNStatsEntry 10 }

	ringswitchEthernetXBFromTRNStatsDiscNonTermRIF OBJECT-TYPE
		SYNTAX  INTEGER48
		ACCESS  read-only
		STATUS  mandatory
		DESCRIPTION				   		
			"The number of specifically routed frames received 
			from Token Ring which have been discarded (i.e. not 
			transmitted) by this interface becuase the 
			interface's ring number is not last in the RIF."
		::= { ringswitchEthernetXBFromTRNStatsEntry 11 }

	ringswitchEthernetXBFromTRNStatsDiscIPDisabled OBJECT-TYPE
		SYNTAX  INTEGER48
		ACCESS  read-only
		STATUS  mandatory
		DESCRIPTION
			"The number of IP frames received from Token Ring 
			which have been discarded (i.e. not transmitted)
			by this interface because IP forwarding is disabled."
		::= { ringswitchEthernetXBFromTRNStatsEntry 12 }

	ringswitchEthernetXBFromTRNStatsDiscARPDisabled OBJECT-TYPE
		SYNTAX  INTEGER48
		ACCESS  read-only
		STATUS  mandatory
		DESCRIPTION			   			
			"The number of ARP and RARP frames received from 
			Token Ring which have been discarded (i.e. not 
			transmitted) by this interface because IP forwarding 
			is disabled."
		::= { ringswitchEthernetXBFromTRNStatsEntry 13 }

	ringswitchEthernetXBFromTRNStatsDiscIPCantFrag OBJECT-TYPE
		SYNTAX  INTEGER48
		ACCESS  read-only
		STATUS  mandatory
		DESCRIPTION
			"The number of IP frames received from Token Ring 
			which have been discarded (i.e. not transmitted)
			by this interface because they need fragmenting but 
			the DONT-FRAG bit is set.  An ICMP frame will be sent
			back to the source."
		::= { ringswitchEthernetXBFromTRNStatsEntry 14 }

	ringswitchEthernetXBFromTRNStatsDiscNCPCache OBJECT-TYPE
		SYNTAX  INTEGER48
		ACCESS  read-only
		STATUS  mandatory
		DESCRIPTION	
			"The number of NCP request frames received from Token 
			Ring which have been discarded (i.e. not transmitted)
			by this interface because they could not be cached."
		::= { ringswitchEthernetXBFromTRNStatsEntry 15 }

	ringswitchEthernetXBFromTRNStatsDiscIPXDisabled OBJECT-TYPE
		SYNTAX  INTEGER48
		ACCESS  read-only
		STATUS  mandatory
		DESCRIPTION
			"The number of IPX frames received from Token Ring 
			which have been discarded (i.e. not transmitted)
			by this interface because IPX forwarding is disabled."
		::= { ringswitchEthernetXBFromTRNStatsEntry 16 }

	ringswitchEthernetXBFromTRNStatsDiscIPXTypeSnap OBJECT-TYPE
		SYNTAX  INTEGER48
		ACCESS  read-only
		STATUS  mandatory
		DESCRIPTION						
			"The number of IPX SNAP frames received from Token 
			Ring which have been discarded (i.e. not transmitted)
			by this interface becuase SNAP encapsulation has not
			been selected."
		::= { ringswitchEthernetXBFromTRNStatsEntry 17 }

	ringswitchEthernetXBFromTRNStatsDiscIPXType8022 OBJECT-TYPE
		SYNTAX  INTEGER48
		ACCESS  read-only
		STATUS  mandatory
		DESCRIPTION
			"The number of IPX 802.2 frames received from Token 
			Ring which have been discarded (i.e. not transmitted)
			by this interface becuase 802.2 encapsulation has not
			been selected."
		::= { ringswitchEthernetXBFromTRNStatsEntry 18 }

	ringswitchEthernetXBFromTRNStatsCacheFull OBJECT-TYPE
		SYNTAX  INTEGER48
		ACCESS  read-only
		STATUS  mandatory
		DESCRIPTION
			"The number of frames received from Token Ring whose
			source MAC address could not be cached because the 
			cache is full. The frame is still forwarded."
		::= { ringswitchEthernetXBFromTRNStatsEntry 19 }

	ringswitchEthernetXBFromTRNStatsRIFCacheFull OBJECT-TYPE
		SYNTAX  INTEGER48
		ACCESS  read-only
		STATUS  mandatory
		DESCRIPTION			     			
			"The number of source-routed frames received from 
			Token Ring whose whose RIF could not be cached
			because the RIF cache is full.  The frame is still 
			forwarded."
		::= { ringswitchEthernetXBFromTRNStatsEntry 20 }

	ringswitchEthernetXBFromTRNStatsFwdIPFrames OBJECT-TYPE
		SYNTAX  INTEGER48
		ACCESS  read-only
		STATUS  mandatory
		DESCRIPTION		  				
			"The number of IP frames received from Token Ring 
			which have been forwarded by this interface."
		::= { ringswitchEthernetXBFromTRNStatsEntry 21 }

	ringswitchEthernetXBFromTRNStatsFwdIPFragmented OBJECT-TYPE
		SYNTAX  INTEGER48
		ACCESS  read-only
		STATUS  mandatory
		DESCRIPTION
			"The number of IP frames received from Token Ring 
			which have been fragmented before being forwarded 
			by this interface. These are also included in the 
			count of IP frames."
		::= { ringswitchEthernetXBFromTRNStatsEntry 22 }

	ringswitchEthernetXBFromTRNStatsFwdIPMulticast OBJECT-TYPE
		SYNTAX  INTEGER48
		ACCESS  read-only
		STATUS  mandatory
		DESCRIPTION			    			
			"The number of IP multicast frames received from 
			Token Ring that have been forwarded by this interface. 
			These are also included in the count of IP frames."
		::= { ringswitchEthernetXBFromTRNStatsEntry 23 }

	ringswitchEthernetXBFromTRNStatsFwdARPFrames OBJECT-TYPE
		SYNTAX  INTEGER48
		ACCESS  read-only
		STATUS  mandatory
		DESCRIPTION			   			
			"The number of ARP and RARP frames received from 
			Token Ring which have been forwarded by this 
			interface."
		::= { ringswitchEthernetXBFromTRNStatsEntry 24 }

	ringswitchEthernetXBFromTRNStatsFwdIPXFrames OBJECT-TYPE
		SYNTAX  INTEGER48
		ACCESS  read-only
		STATUS  mandatory
		DESCRIPTION
			"The number of IPX frames received from Token Ring 
			which have been forwarded by this interface."
		::= { ringswitchEthernetXBFromTRNStatsEntry 25 }

	ringswitchEthernetXBFromTRNStatsFwdAARPPh1Frames OBJECT-TYPE
		SYNTAX  INTEGER48
		ACCESS  read-only
		STATUS  mandatory
		DESCRIPTION
			"The number of Appletalk phase 1 frames (802.1H 
			tunnel encapsulated) ARP frames received from Token 
			Ring which have been forwarded by this interface."
		::= { ringswitchEthernetXBFromTRNStatsEntry 26 }

	ringswitchEthernetXBFromTRNStatsFwdAARPPh2Frames OBJECT-TYPE
		SYNTAX  INTEGER48
		ACCESS  read-only
		STATUS  mandatory
		DESCRIPTION
			"The number of Appletalk phase 2 frames (SNAP
			encapsulated) ARP frames received from Token Ring 
			which have been forwarded by this interface."
		::= { ringswitchEthernetXBFromTRNStatsEntry 27 }

	ringswitchEthernetXBFromTRNStatsFwdTunnel8021hFrames OBJECT-TYPE
		SYNTAX  INTEGER48
		ACCESS  read-only
		STATUS  mandatory
		DESCRIPTION		     		    		
			"The number of 802.1H tunnel frames received from 
			Token Ring which have been converted to zero OUI SNAP 
			frames before being forwarded by this interface."
		::= { ringswitchEthernetXBFromTRNStatsEntry 28 }

	ringswitchEthernetXBFromTRNStatsFwdZeroOUISnapFrames OBJECT-TYPE
		SYNTAX  INTEGER48
		ACCESS  read-only
		STATUS  mandatory
		DESCRIPTION	
			"The number of other zero OUI SNAP frames received 
			from Token Ring which have been converted to 
			Ethertype frames before being forwarded by this 
			interface."
		::= { ringswitchEthernetXBFromTRNStatsEntry 29 }

	ringswitchEthernetXBFromTRNStatsFwdOtherDLCFrames OBJECT-TYPE
		SYNTAX  INTEGER48
		ACCESS  read-only
		STATUS  mandatory
		DESCRIPTION					       	
			"The number of non-zero OUI SNAP and other DLC frames 
			received from Token Ring which have been forwarded 
			by this interface and which have not been included in
			a more specific counter."
		::= { ringswitchEthernetXBFromTRNStatsEntry 30 }

	ringswitchEthernetXBFromTRNStatsFwdBPDUDecaps OBJECT-TYPE
		SYNTAX  INTEGER48
		ACCESS  read-only
		STATUS  mandatory
		DESCRIPTION
			"The number of encapsulated BPDU's received from 
			Token Ring which have been de-encapsulated before
			being forwarded on this interface. Only counted when 
			encapsulated SPT is enabled."
		::= { ringswitchEthernetXBFromTRNStatsEntry 31 }
			      			
	ringswitchEthernetXBFromTRNStatsFwdBPDUEncaps OBJECT-TYPE
		SYNTAX  INTEGER48
		ACCESS  read-only
		STATUS  mandatory
		DESCRIPTION
			"The number of BPDU's received from Token Ring which 
			have been encapsulated before being forwarded on this
			interface. Only counted when encapsulated SPT is 
			enabled."
		::= { ringswitchEthernetXBFromTRNStatsEntry 32 }


-- the ringswitch gigabit extended physical statistics group

	ringswitchEthernetExtPhysStatsTable OBJECT-TYPE
		SYNTAX  SEQUENCE OF RingswitchEthernetExtPhysStatsEntry
		ACCESS  not-accessible
		STATUS  mandatory
		DESCRIPTION
			"This table contains physical layer statistics
                        associated with the gigabit interface that are
                        not available through the normal Ethernet physical
                        layer statistics."
		::= { ringswitchEthernet 5 } 

	ringswitchEthernetExtPhysStatsEntry OBJECT-TYPE
		SYNTAX  RingswitchEthernetExtPhysStatsEntry
		ACCESS  not-accessible
		STATUS  mandatory
		DESCRIPTION		      				
			"A list of information relating to the physical
			layer statistics of a single gigabit interface."
		INDEX { ringswitchEthernetExtPhysStatsIfIndex }
		::= { ringswitchEthernetExtPhysStatsTable 1 }
				
	RingswitchEthernetExtPhysStatsEntry
		::= SEQUENCE
		{		     		
		ringswitchEthernetExtPhysStatsIfIndex            INTEGER,
		ringswitchEthernetExtPhysStatsRxDataErrors	 INTEGER,
		ringswitchEthernetExtPhysStatsRxSequenceErrors	 INTEGER,
		ringswitchEthernetExtPhysStatsRxCarrierExtErrors INTEGER,
		ringswitchEthernetExtPhysStatsXonRxFrames	 INTEGER,
		ringswitchEthernetExtPhysStatsXonTxFrames	 INTEGER,
		ringswitchEthernetExtPhysStatsXoffRxFrames	 INTEGER,
		ringswitchEthernetExtPhysStatsXoffTxFrames	 INTEGER
		}		 			
							
	ringswitchEthernetExtPhysStatsIfIndex OBJECT-TYPE
		SYNTAX  INTEGER
		ACCESS  read-only
		STATUS  mandatory
		DESCRIPTION
			"The value of this object identifies the
			gigabitt interface for which this entry
			contains management information.  The
			value of this object for a particular
			interface has the same value as the
			ifIndex object for the same interface."
		::= { ringswitchEthernetExtPhysStatsEntry 1 }

	ringswitchEthernetExtPhysStatsRxDataErrors OBJECT-TYPE
		SYNTAX  INTEGER
		ACCESS  read-only
		STATUS  mandatory
		DESCRIPTION
			"The number of frames received with I-RX-ER
                        asserted by the front end."
		::= { ringswitchEthernetExtPhysStatsEntry 2 }

	ringswitchEthernetExtPhysStatsRxSequenceErrors OBJECT-TYPE
		SYNTAX  INTEGER
		ACCESS  read-only
		STATUS  mandatory
		DESCRIPTION
			"The number of sequence errors in the symbol
                        ordering received on the TBI interface."
		::= { ringswitchEthernetExtPhysStatsEntry 3 }

	ringswitchEthernetExtPhysStatsRxCarrierExtErrors OBJECT-TYPE
		SYNTAX  INTEGER
		ACCESS  read-only
		STATUS  mandatory
		DESCRIPTION
			"The number of receive data errors that were
                        detected during the carrier extension time of 
                        packet reception."
		::= { ringswitchEthernetExtPhysStatsEntry 4 }

	ringswitchEthernetExtPhysStatsXonRxFrames OBJECT-TYPE
		SYNTAX  INTEGER
		ACCESS  read-only
		STATUS  mandatory
		DESCRIPTION
			"The number of XON flow control frames received."
		::= { ringswitchEthernetExtPhysStatsEntry 5 }

	ringswitchEthernetExtPhysStatsXonTxFrames OBJECT-TYPE
		SYNTAX  INTEGER
		ACCESS  read-only
		STATUS  mandatory
		DESCRIPTION
			"Ther number of XON flow control frames transmitted."
		::= { ringswitchEthernetExtPhysStatsEntry 6 }

	ringswitchEthernetExtPhysStatsXoffRxFrames OBJECT-TYPE
		SYNTAX  INTEGER
		ACCESS  read-only
		STATUS  mandatory
		DESCRIPTION
			"The number of XOFF flow control frames received."
		::= { ringswitchEthernetExtPhysStatsEntry 7 }

	ringswitchEthernetExtPhysStatsXoffTxFrames OBJECT-TYPE
		SYNTAX  INTEGER
		ACCESS  read-only
		STATUS  mandatory
		DESCRIPTION
			"The number of XOFF flow control frames transmitted."
		::= { ringswitchEthernetExtPhysStatsEntry 8 }

----------------------------------------------------------------------------
-- the power supply group
	ringswitchPSUNumUnits OBJECT-TYPE
		SYNTAX  INTEGER
		ACCESS  read-only
		STATUS  mandatory
		DESCRIPTION
			"The number of power supply units in this Ring-
			switch."
		::= { ringswitchPSU 1 }
	ringswitchPSUTable      OBJECT-TYPE
		SYNTAX  SEQUENCE OF RingswitchPSUEntry
		ACCESS  not-accessible
		STATUS  mandatory
		DESCRIPTION
			"A table that contains information about each power
			supply unit in this Ringswitch."
		::= { ringswitchPSU 2 }
	ringswitchPSUEntry      OBJECT-TYPE
		SYNTAX  RingswitchPSUEntry
		ACCESS  not-accessible
		STATUS  mandatory
		DESCRIPTION ""
		INDEX { ringswitchPSUIndex }
		::= { ringswitchPSUTable 1 }
	RingswitchPSUEntry ::=
		SEQUENCE        {
				ringswitchPSUIndex       INTEGER,
				ringswitchPSUDescription DisplayString,
				ringswitchPSUStatus      INTEGER
				}
	ringswitchPSUIndex OBJECT-TYPE
		SYNTAX  INTEGER (1..65535)
		ACCESS  read-only
		STATUS  mandatory
		DESCRIPTION
			"The value of this object identifies the PSU
			for which this entry contains management
			information."
		::= { ringswitchPSUEntry 1 }
	ringswitchPSUDescription OBJECT-TYPE
		SYNTAX  DisplayString (SIZE (0..64))
		ACCESS  read-only
		STATUS  mandatory
		DESCRIPTION
			"A string containing a textual description for
			this power supply unit"
		::= { ringswitchPSUEntry 2 }
	ringswitchPSUStatus OBJECT-TYPE
		SYNTAX  INTEGER
			{
			unit-absent     (1),
			unit-broken     (2),
			unit-normal     (3)
			}
		ACCESS  read-only
		STATUS  mandatory
		DESCRIPTION
			"This variable gives the status
			of PSU1."
		::= { ringswitchPSUEntry 3 }
----------------------------------------------------------------------------
-- the fan group
	ringswitchFanNumUnits OBJECT-TYPE
		SYNTAX  INTEGER
		ACCESS  read-only
		STATUS  mandatory
		DESCRIPTION
			"The number of fans in this Ringswitch."
		::= { ringswitchFan 1 }
	ringswitchFanTable      OBJECT-TYPE
		SYNTAX  SEQUENCE OF RingswitchFanEntry
		ACCESS  not-accessible
		STATUS  mandatory
		DESCRIPTION
			"A table that contains information about each fan
			in this Ringswitch."
		::= { ringswitchFan 2 }
	ringswitchFanEntry      OBJECT-TYPE
		SYNTAX  RingswitchFanEntry
		ACCESS  not-accessible
		STATUS  mandatory
		DESCRIPTION ""
		INDEX { ringswitchFanIndex }
		::= { ringswitchFanTable 1 }
	RingswitchFanEntry ::=
		SEQUENCE        {
				ringswitchFanIndex       INTEGER,
				ringswitchFanDescription DisplayString,
				ringswitchFanSpeed       INTEGER
				}
	ringswitchFanIndex OBJECT-TYPE
		SYNTAX  INTEGER (1..65535)
		ACCESS  read-only
		STATUS  mandatory
		DESCRIPTION
			"The value of this object identifies the Fan
			for which this entry contains management
			information."
		::= { ringswitchFanEntry 1 }
	ringswitchFanDescription OBJECT-TYPE
		SYNTAX  DisplayString (SIZE (0..64))
		ACCESS  read-only
		STATUS  mandatory
		DESCRIPTION
			"A string containing a textual description for
			this Fan."
		::= { ringswitchFanEntry 2 }
	ringswitchFanSpeed OBJECT-TYPE
		SYNTAX  INTEGER (0..65535)
		ACCESS  read-only
		STATUS  mandatory
		DESCRIPTION
			"The number of revolutions per minute being
			reported by this fan. If this value is read as
			zero, then the fan is no longer operating."
		::= { ringswitchFanEntry 3 }
----------------------------------------------------------------------------
-- the Trap group
-- this group defines variables that need to be returned in the Ringswitch
-- specific traps. All of these variables are defined as not-accessible.
	ringswitchRouteDescrSegmentID OBJECT-TYPE
		SYNTAX  INTEGER (0..4095)
		ACCESS  not-accessible
		STATUS  mandatory
		DESCRIPTION
			"The LAN ID portion of the IEEE 802.5
			route descriptor that failed to register."
		::= { ringswitchTrap 1 }
	ringswitchRouteDescrBridgeNumber OBJECT-TYPE
		SYNTAX  INTEGER (0..15)
		ACCESS  not-accessible
		STATUS  mandatory
		DESCRIPTION
			"The Bridge Number portion of the IEEE 802.5 route
			descriptor that failed to register."
		::= { ringswitchTrap 2 }
	ringswitchVersionMismatch OBJECT-TYPE
		SYNTAX  INTEGER
			{
			boot-eprom-and-boot-flash(1)
			}
		ACCESS  not-accessible
		STATUS  mandatory
		DESCRIPTION
			"An enumerated value that describes which
			software components have a version mismatch."
		::= { ringswitchTrap 3 }
	ringswitchDownloadFailed OBJECT-TYPE
		SYNTAX  INTEGER
			{
			microcode(1),
			boot-code(2),
			fddi-code(3),
			atm-code(4)
			}
		ACCESS  not-accessible
		STATUS  mandatory
		DESCRIPTION
			"An enumerated value that describes which
			software component has had a failed 
			download that may compromise system operation
			at the next reboot."
		::= { ringswitchTrap 4 }
----------------------------------------------------------------------------
-- the Ringswitch filter group
	ringswitchFilterTable OBJECT-TYPE
		SYNTAX  SEQUENCE OF RingswitchFilterEntry
		ACCESS  not-accessible
		STATUS  mandatory
		DESCRIPTION
			"This table contains Ringswitch protocol filter
			information. There is one entry per filter."
		::= { ringswitchFilter 1 }
	ringswitchFilterEntry OBJECT-TYPE
		SYNTAX  RingswitchFilterEntry
		ACCESS  not-accessible
		STATUS  mandatory
		DESCRIPTION
			"A list of Ringswitch protocol filters."
		INDEX { ringswitchFilterIndex }
		::= { ringswitchFilterTable 1 }
	RingswitchFilterEntry ::= SEQUENCE
			{
			ringswitchFilterIndex           INTEGER,
			ringswitchFilterStatus          RingswitchRowStatus,
			ringswitchFilterName            DisplayString,
			ringswitchFilterData            OCTET STRING,
			ringswitchFilterExceptionType   INTEGER,
			ringswitchFilterType            INTEGER,
			ringswitchFilterForwardType     INTEGER
			}
	ringswitchFilterIndex OBJECT-TYPE
		SYNTAX  INTEGER
		ACCESS  read-only
		STATUS  mandatory
		DESCRIPTION
			"The index of this filter."
		::= { ringswitchFilterEntry 1 }
	ringswitchFilterStatus OBJECT-TYPE
		SYNTAX  RingswitchRowStatus
		ACCESS  read-write
		STATUS  mandatory
		DESCRIPTION
			"The filter status; see RingswitchRowStatus comments
			above for more details."
		::= { ringswitchFilterEntry 2 }
	ringswitchFilterName OBJECT-TYPE
		SYNTAX  DisplayString
		ACCESS  read-write
		STATUS  mandatory
		DESCRIPTION
			"The filter name."
		::= { ringswitchFilterEntry 3 }
	ringswitchFilterData OBJECT-TYPE
		SYNTAX  OCTET STRING (SIZE (0..64))
		ACCESS  read-write
		STATUS  mandatory
		DESCRIPTION
			"An octet string containing the filter definition.
			It consists of one or more sections in the format
				<length> <offset> <data1>...<datan>
			where the first byte is the length of this section
			in bytes (including the length and offset), and
			the second byte is the offset from the end of the
			routing information field.  The subsequent data
			bytes are compared with the data at the offset
			into broadcast frames received on each port on the
			Ringswitch."
		::= { ringswitchFilterEntry 4 }
	ringswitchFilterExceptionType OBJECT-TYPE
		SYNTAX  INTEGER {
				normal          (1),
				exception       (2)
				}
		ACCESS  read-write
		STATUS  mandatory
		DESCRIPTION
			"What this filter does when matching a frame: a
			value of 'normal' sends the frame to the ports
			on the row of the matrix corresponding to the
			input port; a value of 'exception' stops it going
			to those ports."
		::= { ringswitchFilterEntry 5 }
	ringswitchFilterType OBJECT-TYPE
		SYNTAX  INTEGER {
				normal          (1),
				match-all       (2)
				}
		ACCESS  read-write
		STATUS  mandatory
		DESCRIPTION
			"The filter type; for future expansion."
		::= { ringswitchFilterEntry 6 }
	ringswitchFilterForwardType OBJECT-TYPE
		SYNTAX  INTEGER {
				sr-only (1),
				tb-only (2),
				sr-tb   (3)
				}
		ACCESS  read-write
		STATUS  mandatory
		DESCRIPTION
			"The type of forwarding affected by the filter."
		::= { ringswitchFilterEntry 7 }
-- the Ringswitch filter matrix group
	ringswitchFilterMatrixTable OBJECT-TYPE
		SYNTAX  SEQUENCE OF RingswitchFilterMatrixEntry
		ACCESS  not-accessible
		STATUS  mandatory
		DESCRIPTION
			"This table contains Ringswitch protocol filter
			switching matrix information. There is one entry
			for each row of each switching matrix."
		::= { ringswitchFilter 2 }
	ringswitchFilterMatrixEntry OBJECT-TYPE
		SYNTAX  RingswitchFilterMatrixEntry
		ACCESS  not-accessible
		STATUS  mandatory
		DESCRIPTION
			"A list of Ringswitch protocol filter switching
			matrix rows."
		INDEX { ringswitchFilterMatrixIndex,
			ringswitchFilterMatrixRowIndex }
		::= { ringswitchFilterMatrixTable 1 }
	RingswitchFilterMatrixEntry ::= SEQUENCE
			{
			ringswitchFilterMatrixIndex     INTEGER,
			ringswitchFilterMatrixRowIndex  INTEGER,
			ringswitchFilterMatrixData      OCTET STRING
			}
	ringswitchFilterMatrixIndex OBJECT-TYPE
		SYNTAX  INTEGER
		ACCESS  read-only
		STATUS  mandatory
		DESCRIPTION
			"The index of this filter."
		::= { ringswitchFilterMatrixEntry 1 }
	ringswitchFilterMatrixRowIndex OBJECT-TYPE
		SYNTAX  INTEGER
		ACCESS  read-only
		STATUS  mandatory
		DESCRIPTION
			"The index of this row in this matrix."
		::= { ringswitchFilterMatrixEntry 2 }
	ringswitchFilterMatrixData OBJECT-TYPE
		SYNTAX  OCTET STRING
		ACCESS  read-write
		STATUS  mandatory
		DESCRIPTION
			"A single row of the matrix, with ports 1 to 8
			represented by the first octet (starting with the
			least significant bit), ports 9 to 16 by the next
			octet, and so on."
		::= { ringswitchFilterMatrixEntry 3 }
----------------------------------------------------------------------------
-- Madge Ringswitch specific traps
	fanPSSpeedFailed TRAP-TYPE
		ENTERPRISE ringswitch
		VARIABLES { ringswitchBasePSFanSpeed }
		DESCRIPTION
			"This trap is sent when the Power Supply fan has
			failed."
		::= 1
	fanExtSpeedFailed TRAP-TYPE
		ENTERPRISE ringswitch
		VARIABLES { ringswitchBaseExtFanSpeed }
		DESCRIPTION
			"This trap is sent when the external fan has
			failed."
		::= 2
	portFailed TRAP-TYPE
		ENTERPRISE ringswitch
		VARIABLES { ringswitchPortAdapterStatus }
		DESCRIPTION
			"This trap is sent when a port has auto-closed or
			failed to open."
		::= 3
	brTestFailed TRAP-TYPE
		ENTERPRISE ringswitch
		VARIABLES { ringswitchPortTestError }
		DESCRIPTION
			"This trap is sent when the bridge test on a port
			fails."
		::= 4
	elanRingnumFailed TRAP-TYPE
		ENTERPRISE ringswitch
		VARIABLES { ringswitchGenPortNum }
		DESCRIPTION
			"This trap is sent when the ELAN ring number for
			an ATM LEC is already configured on another port."
		::= 5
	routeDescriptorFailed TRAP-TYPE
		ENTERPRISE ringswitch
		VARIABLES { ringswitchGenPortNum,
			    ringswitchRouteDescrSegmentID,
			    ringswitchRouteDescrBridgeNumber }
		DESCRIPTION
			"This trap is sent when an ATM LEC has failed to
			register a route descriptor."
		::= 6
	fanSpeedFailed TRAP-TYPE
		ENTERPRISE ringswitch
		VARIABLES { ringswitchFanSpeed }
		DESCRIPTION
			"This trap is sent when a fan has failed."
		::= 7
	psuFailed TRAP-TYPE
		ENTERPRISE ringswitch
		VARIABLES { ringswitchPSUStatus }
		DESCRIPTION
			"This trap is sent when a PSU has broken."
		::= 8
	versionMismatch TRAP-TYPE
		ENTERPRISE ringswitch
		VARIABLES { ringswitchVersionMismatch }
		DESCRIPTION
			"This trap is sent when there is a version
			mismatch between some installed software
			components."
		::= 9
	genPortStatus TRAP-TYPE
		ENTERPRISE ringswitch
		VARIABLES { ringswitchGenPortLastStatus }
		DESCRIPTION
			"This trap is sent when an interesting
			status change occurs on a port."
		::= 10
	slotStatus TRAP-TYPE
		ENTERPRISE ringswitch
		VARIABLES { ringswitchSlotLastStatus }
		DESCRIPTION
			"This trap is sent when an interesting
			status change occurs on a slot."
		::= 11
	oneNodePerPortViolation TRAP-TYPE
		ENTERPRISE ringswitch
		VARIABLES { ringswitchTRGrpSwtchIfIndex }
		DESCRIPTION
			"Sent when two or more nodes are inserted in a 
			Group Switch port."
		::= 12
	grpSwitchPortDisabled TRAP-TYPE
		ENTERPRISE ringswitch
		VARIABLES { ringswitchTRGrpSwtchIfIndex,
			    ringswitchTRGrpSwtchPortIndex,
			    ringswitchTRGrpSwtchTrapInfoReason}
		DESCRIPTION
			"Sent when a group switch port is disabled."
		::= 13
	grpSwitchPortKilled TRAP-TYPE
		ENTERPRISE ringswitch
		VARIABLES { ringswitchTRGrpSwtchIfIndex,
			    ringswitchTRGrpSwtchPortIndex,
			    ringswitchTRGrpSwtchTrapInfoReason}
		DESCRIPTION
			"Sent when a group switch port is disabled by 
                         fault manager"
		::= 14
	downloadFailed TRAP-TYPE
		ENTERPRISE ringswitch
		VARIABLES { ringswitchDownloadFailed }
		DESCRIPTION
			"This trap is sent when a download
			operation has failed, and system operation
			may be compromised as the next reboot."
		::= 15
	grpSwitchPortFaultDetected TRAP-TYPE
		ENTERPRISE ringswitch
		VARIABLES { ringswitchTRGrpSwtchIfIndex,
			    ringswitchTRGrpSwtchPortIndex,
			    ringswitchTRGrpSwtchTrapInfoReason}
		DESCRIPTION
			"Sent when a group switch port causes a fault."
		::= 16
	fastFailoverWarning TRAP-TYPE
		ENTERPRISE ringswitch
		VARIABLES { ringswitchTRIfFastFailoverPrimaryPort,
			    ringswitchTRIfFastFailoverTrapInfoReason }
		DESCRIPTION
			"Sent when a fast failover switch port causes a 
                         warning"
		::= 17
     ethernetSTPBlockingTrap TRAP-TYPE
		ENTERPRISE ringswitch
		VARIABLES { ringswitchEthernetIfIndex,
			     ringswitchEthernetIfSTPBlockingTrapInfo}
		DESCRIPTION
			"Sent when a Ethernet port is forced into blocking mode
			 due to the presence of a 3rd party bridge. Also sent
			 when the port comes out of blocking"
		::= 18
	END
