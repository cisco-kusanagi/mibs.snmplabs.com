-- extracted from draft-thaler-idmr-multicast-routemib-00.txt
-- at Wed Jun  7 07:07:29 2000

    INETMROUTE-STD-MIB DEFINITIONS ::= BEGIN 
     
    IMPORTS 
        MODULE-IDENTITY, OBJECT-TYPE, mib-2,  
        Integer32, Counter32, Counter64, Gauge32,  
        TimeTicks                        FROM SNMPv2-SMI 
        RowStatus, TEXTUAL-CONVENTION,  
        TruthValue                       FROM SNMPv2-TC 
        MODULE-COMPLIANCE, OBJECT-GROUP  FROM SNMPv2-CONF 
        SnmpAdminString                  FROM SNMP-FRAMEWORK-MIB 
        InterfaceIndexOrZero, 
        InterfaceIndex                   FROM IF-MIB 
        IANAipRouteProtocol, 
        IANAipMRouteProtocol             FROM IANA-RTPROTO-MIB 
        InetAddress, InetAddressType     FROM INET-ADDRESS-MIB; 
     
    inetMRouteStdMIB MODULE-IDENTITY 
        LAST-UPDATED "200003090000Z" -- March 9, 2000 
        ORGANIZATION "IETF IDMR Working Group" 
        CONTACT-INFO 
                " Dave Thaler 
                  Microsoft Corporation 
                  One Microsoft Way 
                  Redmond, WA  98052-6399 
                  US 
     
                  Phone: +1 425 703 8835 
                  EMail: dthaler@dthaler.microsoft.com 
     
                  Andrew Adams 
                  Merit Network, Inc. 
  
 Thaler,Adams,Siadak  Experimental/Expires Dec 2000                   3 
                 draft-thaler-idmr-multicast-routemib-1       June 2000 


                  4251 Plymouth Rd. 
                  Ann Arbor, MI  48105-2785 
     
                  Phone: +1 734 763-6378 
                  EMail: ala@merit.edu 
     
                  William Siadak 
                  Merit Network, Inc. 
                  4251 Plymouth Rd. 
                  Ann Arbor, MI 48105-2785 
     
                  Phone: +1 734 936 2035 
                  EMail: wfs@merit.edu" 
     
        DESCRIPTION 
                "The MIB module for management of IP Multicast routing, 
                 but independent of the specific multicast routing 
                 protocol in use._ 
        REVISION     "200003090000Z" -- March 9, 2000 
        DESCRIPTION 
                "Initial version, published as RFC xxxx (to be filled 
    in 
                 by RFC-Editor)." 
        ::= { mib-2 XX } 
        -- NOTE TO RFC EDITOR: When this document is published as 
        -- an RFC, replace XX with IANA-assigned number, 
        -- and delete this comment. 
     
    -- Textual Conventions 
     
    LanguageTag ::= TEXTUAL-CONVENTION 
       DISPLAY-HINT "100a" 
       STATUS       current 
       DESCRIPTION 
                "An RFC 1766-style language tag, with all alphabetic 
                characters converted to lowercase.  This restriction is 
                intended to make the lexical ordering imposed by SNMP 
                useful when applied to language tags.  Note that it is 
                theoretically possible for a valid language tag to 
                exceed the allowed length of this syntax, and thus be 
                impossible to represent with this syntax.  Sampling of 
                language tags in current use on the Internet suggests 
                that this limit does not pose a serious problem in 
                practice." 
       SYNTAX       OCTET STRING (SIZE (1..100)) 
     
    -- Top-level structure of the MIB 
     
    inetMRouteMIBObjects OBJECT IDENTIFIER ::= { inetMRouteStdMIB 1 } 
     
    inetMRoute      OBJECT IDENTIFIER ::= { inetMRouteMIBObjects 1 } 
     
    -- the IP Multicast Routing MIB-Group 
  
 Thaler,Adams,Siadak  Experimental/Expires Dec 2000                   4 
                 draft-thaler-idmr-multicast-routemib-1       June 2000 


    -- 
    -- a collection of objects providing information about 
    -- IP Multicast Groups 
     
    inetMRouteEnabled OBJECT-TYPE 
        SYNTAX     TruthValue 
        MAX-ACCESS read-write 
        STATUS     current 
        DESCRIPTION 
                "The enabled status of IP Multicast routing on this 
    router." 
        ::= { inetMRoute 1 } 
     
    inetMRouteEntryCount OBJECT-TYPE 
        SYNTAX     Gauge32 
        MAX-ACCESS read-only 
        STATUS     current 
        DESCRIPTION 
                "The number of rows in the inetMRouteTable.  This can 
    be 
                used to monitor the multicast routing table size." 
        ::= { inetMRoute 7 } 
     
    inetMRouteTable OBJECT-TYPE 
        SYNTAX     SEQUENCE OF InetMRouteEntry 
        MAX-ACCESS not-accessible 
        STATUS     current 
        DESCRIPTION 
                "The (conceptual) table containing multicast routing 
                information for IP datagrams sent by particular sources 
                to the IP multicast groups known to this router." 
        ::= { inetMRoute 2 } 
     
    inetMRouteEntry OBJECT-TYPE 
        SYNTAX     InetMRouteEntry 
        MAX-ACCESS not-accessible 
        STATUS     current 
        DESCRIPTION 
                "An entry (conceptual row) containing the multicast 
                routing information for IP datagrams from a particular 
                source and addressed to a particular IP multicast group 
                address. Discontinuities in counters in this entry can 
                be detected by observing the value of 
    inetMRouteUpTime." 
        INDEX      { inetMRouteGroupType, 
                     inetMRouteGroup, 
                     inetMRouteGroupMaskLen, 
                     inetMRouteSourceType,  
                     inetMRouteSource,                  
                     inetMRouteSourceMaskLen }                 
        ::= { inetMRouteTable 1 } 
     
    InetMRouteEntry ::= SEQUENCE { 
  
 Thaler,Adams,Siadak  Experimental/Expires Dec 2000                   5 
                 draft-thaler-idmr-multicast-routemib-1       June 2000 


        inetMRouteGroupType             InetAddressType, 
        inetMRouteGroup                 InetAddress, 
        inetMRouteGroupMaskLen          INTEGER, 
        inetMRouteSourceType            InetAddressType, 
        inetMRouteSource                InetAddress, 
        inetMRouteSourceMaskLen         INTEGER, 
        inetMRouteUpstreamNeighborType  InetAddressType, 
        inetMRouteUpstreamNeighbor      InetAddress, 
        inetMRouteInIfIndex             InterfaceIndexOrZero, 
        inetMRouteUpTime                TimeTicks, 
        inetMRouteExpiryTime            TimeTicks, 
        inetMRoutePkts                  Counter32, 
        inetMRouteDifferentInIfPackets  Counter32, 
        inetMRouteOctets                Counter32, 
        inetMRouteProtocol              IANAipMRouteProtocol, 
        inetMRouteRtProto               IANAipRouteProtocol, 
        inetMRouteRtAddressType         InetAddressType, 
        inetMRouteRtAddress             InetAddress, 
        inetMRouteRtMaskLen             INTEGER, 
        inetMRouteRtType                INTEGER, 
        inetMRouteHCOctets              Counter64 
    } 
     
    inetMRouteGroupType OBJECT-TYPE 
        SYNTAX     InetAddressType 
        MAX-ACCESS not-accessible 
        STATUS     current 
        DESCRIPTION 
                "A value indicating the address family of the address 
                contained in inetMRouteGroup.  Legal values correspond 
                to the subset of address families for which multicast 
                forwarding is supported." 
        ::= { inetMRouteEntry 1 } 
     
    inetMRouteGroup OBJECT-TYPE 
        SYNTAX     InetAddress 
        MAX-ACCESS not-accessible 
        STATUS     current 
        DESCRIPTION 
                "The IP multicast group address which when combined 
    with 
                the corresponding value specified in 
                inetMRouteGroupMaskLen identifies the groups for which 
                this entry contains multicast routing information." 
        ::= { inetMRouteEntry 2 } 
     
    inetMRouteGroupMaskLen OBJECT-TYPE 
        SYNTAX     INTEGER (0..128) 
        MAX-ACCESS not-accessible 
        STATUS     current 
        DESCRIPTION 
                "The length in bits of the mask which when combined 
    with 
  
 Thaler,Adams,Siadak  Experimental/Expires Dec 2000                   6 
                 draft-thaler-idmr-multicast-routemib-1       June 2000 


                the corresponding value of inetMRouteGroup identifies 
                the groups for which this entry contains multicast 
                routing information." 
        ::= { inetMRouteEntry 3 } 
     
    inetMRouteSourceType OBJECT-TYPE 
        SYNTAX     InetAddressType 
        MAX-ACCESS not-accessible 
        STATUS     current 
        DESCRIPTION 
               "A value indicating the address family of the address 
               contained in inetMRouteSource. The value MUST be the 
    same 
               as the value of inetMRouteGroupType." 
        ::= { inetMRouteEntry 4 } 
     
    inetMRouteSource OBJECT-TYPE 
        SYNTAX     InetAddress 
        MAX-ACCESS not-accessible 
        STATUS     current 
        DESCRIPTION 
                "The network address which when combined with the 
                corresponding value of inetMRouteSourceMaskLen 
                identifies the sources for which this entry contains 
                multicast routing information." 
        ::= { inetMRouteEntry 5 } 
     
    inetMRouteSourceMaskLen OBJECT-TYPE 
        SYNTAX     INTEGER (0..128) 
        MAX-ACCESS not-accessible 
        STATUS     current 
        DESCRIPTION 
                "The length in bits of the mask which when combined 
    with 
                the corresponding value of inetMRouteSource identifies 
                the sources for which this entry contains multicast 
                routing information." 
        ::= { inetMRouteEntry 6 } 
     
    inetMRouteUpstreamNeighborType OBJECT-TYPE 
        SYNTAX     InetAddressType 
        MAX-ACCESS read-only 
        STATUS     current 
        DESCRIPTION 
                "A value indicating the address family of the address 
                contained in inetMRouteUpstreamNeighbor. The value MUST 
                be the same as the value of inetMRouteGroupType." 
        ::= { inetMRouteEntry 7 } 
     
    inetMRouteUpstreamNeighbor OBJECT-TYPE 
        SYNTAX     InetAddress 
        MAX-ACCESS read-only 
        STATUS     current 
  
 Thaler,Adams,Siadak  Experimental/Expires Dec 2000                   7 
                 draft-thaler-idmr-multicast-routemib-1       June 2000 


        DESCRIPTION 
                "The address of the upstream neighbor (e.g., RPF 
                neighbor) from which IP datagrams from these sources to 
                this multicast address are received. If the upstream 
                neighbor is unknown, then inetMRouteUpstreamNeighbor 
                will be 0.0.0.0 in the case of an IPv4 entry, and 
                0:0:0:0:0:0:0:0 in the case of an IPv6 entry. (e.g., in  
                CBT)." 
        ::= { inetMRouteEntry 8 } 
     
    inetMRouteInIfIndex OBJECT-TYPE 
        SYNTAX     InterfaceIndexOrZero 
        MAX-ACCESS read-only 
        STATUS     current 
        DESCRIPTION 
                "The value of ifIndex for the interface on which IP 
                datagrams sent by these sources to this multicast 
                address are received.  A value of 0 indicates that 
                datagrams are not subject to an incoming interface 
                check, but may be accepted on multiple interfaces 
    (e.g., 
                in CBT)." 
        ::= { inetMRouteEntry 9 } 
     
    inetMRouteUpTime OBJECT-TYPE 
        SYNTAX     TimeTicks 
        MAX-ACCESS read-only 
        STATUS     current 
        DESCRIPTION 
                "The time since the multicast routing information 
                represented by this entry was learned by the router." 
        ::= { inetMRouteEntry 10 } 
     
    inetMRouteExpiryTime OBJECT-TYPE 
        SYNTAX     TimeTicks 
        MAX-ACCESS read-only 
        STATUS     current 
        DESCRIPTION 
                "The minimum amount of time remaining before this entry 
                will be aged out.  The value 0 indicates that the entry 
                is not subject to aging." 
        ::= { inetMRouteEntry 11 } 
     
    inetMRoutePkts OBJECT-TYPE 
        SYNTAX     Counter32 
        MAX-ACCESS read-only 
        STATUS     current 
        DESCRIPTION 
                "The number of packets which this router has received 
                from these sources and addressed to this multicast 
    group 
                address." 
        ::= { inetMRouteEntry 12 } 
  
 Thaler,Adams,Siadak  Experimental/Expires Dec 2000                   8 
                 draft-thaler-idmr-multicast-routemib-1       June 2000 


     
    inetMRouteDifferentInIfPackets OBJECT-TYPE 
        SYNTAX     Counter32 
        MAX-ACCESS read-only 
        STATUS     current 
        DESCRIPTION 
                "The number of packets which this router has received 
                from these sources and addressed to this multicast 
    group 
                address, which were dropped because they were not 
                received on the interface indicated by 
                inetMRouteInIfIndex.  Packets which are not subject to 
                an incoming interface check (e.g., using CBT) are not 
                counted." 
        ::= { inetMRouteEntry 13 } 
     
    inetMRouteOctets OBJECT-TYPE 
        SYNTAX     Counter32 
        MAX-ACCESS read-only 
        STATUS     current 
        DESCRIPTION 
                "The number of octets contained in IP datagrams which 
                were received from these sources and addressed to this 
                multicast group address, and which were forwarded by 
                this router." 
        ::= { inetMRouteEntry 14 } 
     
    inetMRouteProtocol OBJECT-TYPE 
        SYNTAX     IANAipMRouteProtocol 
        MAX-ACCESS read-only 
        STATUS     current 
        DESCRIPTION 
                "The multicast routing protocol via which this 
    multicast 
                forwarding entry was learned." 
        ::= { inetMRouteEntry 15 } 
     
    inetMRouteRtProto OBJECT-TYPE 
        SYNTAX     IANAipRouteProtocol  
        MAX-ACCESS read-only 
        STATUS     current 
        DESCRIPTION 
                "The routing mechanism via which the route used to find 
                the upstream or parent interface for this multicast 
                forwarding entry was learned.  Inclusion of values for 
                routing protocols is not intended to imply that those 
                protocols need be supported." 
        ::= { inetMRouteEntry 16 } 
     
    inetMRouteRtAddressType OBJECT-TYPE 
        SYNTAX     InetAddressType 
        MAX-ACCESS read-only 
        STATUS     current 
  
 Thaler,Adams,Siadak  Experimental/Expires Dec 2000                   9 
                 draft-thaler-idmr-multicast-routemib-1       June 2000 


        DESCRIPTION 
                "A value indicating the address family of the address 
                contained in inetMRouteRtAddress. The value MUST be the 
                same as the value of inetMRouteGroupType." 
        ::= { inetMRouteEntry 17 } 
     
    inetMRouteRtAddress OBJECT-TYPE 
        SYNTAX     InetAddress 
        MAX-ACCESS read-only 
        STATUS     current 
        DESCRIPTION 
                "The address portion of the route used to find the 
                upstream or parent interface for this multicast 
                forwarding entry." 
        ::= { inetMRouteEntry 18 } 
     
    inetMRouteRtMaskLen OBJECT-TYPE 
        SYNTAX     INTEGER (0..128) 
        MAX-ACCESS read-only 
        STATUS     current 
        DESCRIPTION 
                "The length in bits of the mask associated with the 
                route used to find the upstream or parent interface for 
                this multicast forwarding entry." 
        ::= { inetMRouteEntry 19 } 
     
    inetMRouteRtType OBJECT-TYPE 
        SYNTAX     INTEGER { 
                    unicast   (1), -- Unicast route used in multicast 
                                      RIB 
                    multicast (2)  -- Multicast route 
                   } 
        MAX-ACCESS read-only 
        STATUS     current 
        DESCRIPTION 
                "The reason the given route was placed in the (logical) 
                multicast Routing Information Base (RIB).  A value of 
                unicast means that the route would normally be placed 
                only in the unicast RIB, but was placed in the 
    multicast 
                RIB (instead or in addition) due to local 
    configuration, 
                such as when running PIM over RIP.  A value of 
    multicast 
                means that the route was explicitly added to the 
                multicast RIB by the routing protocol, such as DVMRP or 
                Multiprotocol BGP." 
        ::= { inetMRouteEntry 20 } 
     
    inetMRouteHCOctets OBJECT-TYPE 
        SYNTAX     Counter64 
        MAX-ACCESS read-only 
        STATUS     current 
  
 Thaler,Adams,Siadak  Experimental/Expires Dec 2000                  10 
                 draft-thaler-idmr-multicast-routemib-1       June 2000 


        DESCRIPTION 
                "The number of octets contained in IP datagrams which 
                were received from these sources and addressed to this 
                multicast group address, and which were forwarded by 
                this router. This object is a 64-bit version of 
                inetMRouteOctets." 
        ::= { inetMRouteEntry 21 } 
     
    -- 
    --  The IP Multicast Routing Next Hop Table 
    -- 
     
    inetMRouteNextHopTable OBJECT-TYPE 
        SYNTAX     SEQUENCE OF InetMRouteNextHopEntry 
        MAX-ACCESS not-accessible 
        STATUS     current 
        DESCRIPTION 
                "The (conceptual) table containing information on the 
                next-hops on outgoing interfaces for routing IP 
                multicast datagrams.  Each entry is one of a list of 
                next-hops on outgoing interfaces for particular sources 
                sending to a particular multicast group address." 
        ::= { inetMRoute 3 } 
     
    inetMRouteNextHopEntry OBJECT-TYPE 
        SYNTAX     InetMRouteNextHopEntry 
        MAX-ACCESS not-accessible 
        STATUS     current 
        DESCRIPTION 
                "An entry (conceptual row) in the list of next-hops on 
                outgoing interfaces to which IP multicast datagrams 
    from 
                particular sources to a IP multicast group address are 
                routed.  Discontinuities in counters in this entry can 
                be detected by observing the value of 
    inetMRouteUpTime." 
        INDEX      { inetMRouteNextHopGroupType, 
                     inetMRouteNextHopGroup,  
                     inetMRouteNextHopSourceType, 
                     inetMRouteNextHopSource, 
                     inetMRouteNextHopSourceMaskLen, 
                     inetMRouteNextHopIfIndex, 
                     inetMRouteNextHopAddressType, 
                     inetMRouteNextHopAddress } 
        ::= { inetMRouteNextHopTable 1 } 
     
    InetMRouteNextHopEntry ::= SEQUENCE { 
        inetMRouteNextHopGroupType          InetAddressType, 
        inetMRouteNextHopGroup              InetAddress, 
        inetMRouteNextHopSourceType         InetAddressType, 
        inetMRouteNextHopSource             InetAddress, 
        inetMRouteNextHopSourceMaskLen      INTEGER, 
        inetMRouteNextHopIfIndex            InterfaceIndex, 
  
 Thaler,Adams,Siadak  Experimental/Expires Dec 2000                  11 
                 draft-thaler-idmr-multicast-routemib-1       June 2000 


        inetMRouteNextHopAddressType        InetAddressType, 
        inetMRouteNextHopAddress            InetAddress, 
        inetMRouteNextHopPruned             TruthValue, 
        inetMRouteNextHopUpTime             TimeTicks, 
        inetMRouteNextHopExpiryTime         TimeTicks, 
        inetMRouteNextHopClosestMemberHops  Integer32, 
        inetMRouteNextHopProtocol           IANAipMRouteProtocol, 
        inetMRouteNextHopPkts               Counter32 
    } 
     
    inetMRouteNextHopGroupType OBJECT-TYPE 
        SYNTAX     InetAddressType 
        MAX-ACCESS not-accessible 
        STATUS     current 
        DESCRIPTION 
                "A value indicating the address family of the address 
                contained in inetMRouteNextHopGroup. Legal values 
                correspond to the subset of address families for which 
                multicast forwarding is supported." 
        ::= { inetMRouteNextHopEntry 1 } 
     
    inetMRouteNextHopGroup OBJECT-TYPE 
        SYNTAX     InetAddress 
        MAX-ACCESS not-accessible 
        STATUS     current 
        DESCRIPTION 
                "The IP multicast group for which this entry specifies 
    a 
                next-hop on an outgoing interface." 
        ::= { inetMRouteNextHopEntry 2 } 
     
    inetMRouteNextHopSourceType OBJECT-TYPE 
        SYNTAX     InetAddressType 
        MAX-ACCESS not-accessible 
        STATUS     current 
        DESCRIPTION 
                "A value indicating the address family of the address 
                contained in inetMRouteNextHopSourceType. The value 
    MUST 
                be the same as the value of 
    inetMRouteNextHopGroupType." 
        ::= { inetMRouteNextHopEntry 3 } 
     
    inetMRouteNextHopSource OBJECT-TYPE 
        SYNTAX     InetAddress 
        MAX-ACCESS not-accessible 
        STATUS     current 
        DESCRIPTION 
                "The network address which when combined with the 
                corresponding value of the mask specified in  
                inetMRouteNextHopSourceMaskLen identifies the sources 
                for which this entry specifies a next-hop on an 
    outgoing 
  
 Thaler,Adams,Siadak  Experimental/Expires Dec 2000                  12 
                 draft-thaler-idmr-multicast-routemib-1       June 2000 


                interface." 
        ::= { inetMRouteNextHopEntry 4 } 
     
    inetMRouteNextHopSourceMaskLen OBJECT-TYPE 
        SYNTAX     INTEGER (0..128) 
        MAX-ACCESS not-accessible 
        STATUS     current 
        DESCRIPTION 
                "The length in bits of the mask which when combined 
    with 
                the corresponding value specified in 
                inetMRouteNextHopSource identifies the sources for 
    which 
                this entry specifies a next-hop on an outgoing 
                interface." 
        ::= { inetMRouteNextHopEntry 5 } 
     
    inetMRouteNextHopIfIndex OBJECT-TYPE 
        SYNTAX     InterfaceIndex 
        MAX-ACCESS not-accessible 
        STATUS     current 
        DESCRIPTION 
                "The ifIndex value of the interface for the outgoing 
                interface for this next-hop." 
        ::= { inetMRouteNextHopEntry 6 } 
     
    inetMRouteNextHopAddressType OBJECT-TYPE 
        SYNTAX     InetAddressType 
        MAX-ACCESS not-accessible 
        STATUS     current 
        DESCRIPTION 
                "A value indicating the address family of the address 
                contained in inetMRouteNextHopAddressType. The value 
                MUST be the same as the value of 
                inetMRouteNextHopGroupType." 
        ::= { inetMRouteNextHopEntry 7 } 
     
    inetMRouteNextHopAddress OBJECT-TYPE 
        SYNTAX     InetAddress 
        MAX-ACCESS not-accessible 
        STATUS     current 
        DESCRIPTION 
                "The address of the next-hop specific to this entry. 
                For most interfaces, this is identical to 
                inetMRouteNextHopGroup. NBMA interfaces, however, may 
                have multiple next-hop addresses out a single outgoing 
                interface." 
        ::= { inetMRouteNextHopEntry 8 } 
     
    inetMRouteNextHopPruned OBJECT-TYPE 
        SYNTAX     TruthValue 
        MAX-ACCESS read-only 
        STATUS     current 
  
 Thaler,Adams,Siadak  Experimental/Expires Dec 2000                  13 
                 draft-thaler-idmr-multicast-routemib-1       June 2000 


        DESCRIPTION 
                "An indication of whether the outgoing interface and 
                next-hop represented by this entry is currently being 
                used to forward IP datagrams.  The value 'false' 
                indicates it is currently being used; the value 'true' 
                indicates it is not." 
        ::= { inetMRouteNextHopEntry 9 } 
     
    inetMRouteNextHopUpTime OBJECT-TYPE 
        SYNTAX     TimeTicks 
        MAX-ACCESS read-only 
        STATUS     current 
        DESCRIPTION 
                "The time since the multicast routing information 
                represented by this entry was learned by the router." 
        ::= { inetMRouteNextHopEntry 10 } 
     
    inetMRouteNextHopExpiryTime OBJECT-TYPE 
        SYNTAX     TimeTicks 
        MAX-ACCESS read-only 
        STATUS     current 
        DESCRIPTION 
                "The minimum amount of time remaining before this entry 
                will be aged out.  If inetMRouteNextHopPruned is 
                pruned(1), the remaining time until the prune expires 
                and the state reverts to forwarding(2).  Otherwise, the 
                remaining time until this entry is removed from the 
                table.  The time remaining may be copied from 
                inetMRouteExpiryTime if the protocol in use for this 
                entry dos not specify next-hop timers.  The value 0 
                indicates that the entry is not subject to aging." 
        ::= { inetMRouteNextHopEntry 11 } 
     
    inetMRouteNextHopClosestMemberHops OBJECT-TYPE 
        SYNTAX     Integer32 
        MAX-ACCESS read-only 
        STATUS     current 
        DESCRIPTION 
                "The minimum number of hops between this router and any 
                member of this IP multicast group reached via this  
                next-hop on this outgoing interface.  Any IP multicast 
                datagrams for the group which have a TTL (IPv4) or Hop 
                Count (IPv6) less than this number of hops will not be 
                forwarded to this next-hop." 
        ::= { inetMRouteNextHopEntry 12 } 
     
    inetMRouteNextHopProtocol OBJECT-TYPE 
        SYNTAX     IANAipMRouteProtocol 
        MAX-ACCESS read-only 
        STATUS     current 
        DESCRIPTION 
                "The routing mechanism via which this next-hop was 
    learned." 
  
 Thaler,Adams,Siadak  Experimental/Expires Dec 2000                  14 
                 draft-thaler-idmr-multicast-routemib-1       June 2000 


        ::= { inetMRouteNextHopEntry 13 } 
     
    inetMRouteNextHopPkts OBJECT-TYPE 
        SYNTAX     Counter32 
        MAX-ACCESS read-only 
        STATUS     current 
        DESCRIPTION 
                "The number of packets which have been forwarded using 
                 this route." 
        ::= { inetMRouteNextHopEntry 14 } 
     
    -- 
    --  The Multicast Routing Interface Table 
    -- 
     
    inetMRouteInterfaceTable OBJECT-TYPE 
        SYNTAX     SEQUENCE OF InetMRouteInterfaceEntry 
        MAX-ACCESS not-accessible 
        STATUS     current 
        DESCRIPTION 
                "The (conceptual) table containing multicast routing 
                information specific to interfaces." 
        ::= { inetMRoute 4 } 
     
    inetMRouteInterfaceEntry OBJECT-TYPE 
        SYNTAX     InetMRouteInterfaceEntry 
        MAX-ACCESS not-accessible 
        STATUS     current 
        DESCRIPTION 
                "An entry (conceptual row) containing the multicast 
                routing information for a particular interface." 
        INDEX      { inetMRouteInterfaceIfIndex } 
        ::= { inetMRouteInterfaceTable 1 } 
     
    InetMRouteInterfaceEntry ::= SEQUENCE { 
        inetMRouteInterfaceIfIndex          InterfaceIndex, 
        inetMRouteInterfaceTtl              Integer32, 
        inetMRouteInterfaceProtocol         IANAipMRouteProtocol, 
        inetMRouteInterfaceRateLimit        Integer32, 
        inetMRouteInterfaceInMcastOctets    Counter32, 
        inetMRouteInterfaceOutMcastOctets   Counter32, 
        inetMRouteInterfaceHCInMcastOctets  Counter64, 
        inetMRouteInterfaceHCOutMcastOctets Counter64 
    } 
     
    inetMRouteInterfaceIfIndex OBJECT-TYPE 
        SYNTAX     InterfaceIndex 
        MAX-ACCESS not-accessible 
        STATUS     current 
        DESCRIPTION 
                "The ifIndex value of the interface for which this 
    entry 
                contains information." 
  
 Thaler,Adams,Siadak  Experimental/Expires Dec 2000                  15 
                 draft-thaler-idmr-multicast-routemib-1       June 2000 


        ::= { inetMRouteInterfaceEntry 1 } 
     
    inetMRouteInterfaceTtl OBJECT-TYPE 
        SYNTAX     Integer32 (0..255) 
        MAX-ACCESS read-write 
        STATUS     current 
        DESCRIPTION 
                "The datagram TTL threshold for the interface. Any IP 
                multicast datagrams with a TTL (IPv4) or Hop Count 
                (IPv6) less than this threshold will not be forwarded 
                out the interface. The default value of 0 means all 
                multicast packets are forwarded out the interface." 
        ::= { inetMRouteInterfaceEntry 2 } 
     
    inetMRouteInterfaceProtocol OBJECT-TYPE 
        SYNTAX     IANAipMRouteProtocol 
        MAX-ACCESS read-only 
        STATUS     current 
        DESCRIPTION 
                "The routing protocol running on this interface." 
        ::= { inetMRouteInterfaceEntry 3 } 
     
    inetMRouteInterfaceRateLimit OBJECT-TYPE 
        SYNTAX     Integer32 
        MAX-ACCESS read-write 
        STATUS     current 
        DESCRIPTION 
                "The rate-limit, in kilobits per second, of forwarded 
                multicast traffic on the interface.  A rate-limit of 0 
                indicates that no rate limiting is done." 
        DEFVAL     { 0 } 
        ::= { inetMRouteInterfaceEntry 4 } 
     
    inetMRouteInterfaceInMcastOctets OBJECT-TYPE 
        SYNTAX     Counter32 
        MAX-ACCESS read-only 
        STATUS     current 
        DESCRIPTION 
                "The number of octets of multicast packets that have 
                arrived on the interface, including framing characters. 
                This object is similar to ifInOctets in the Interfaces 
                MIB, except that only multicast packets are counted." 
        ::= { inetMRouteInterfaceEntry 5 } 
     
    inetMRouteInterfaceOutMcastOctets OBJECT-TYPE 
        SYNTAX     Counter32 
        MAX-ACCESS read-only 
        STATUS     current 
        DESCRIPTION 
                "The number of octets of multicast packets that have 
                 been sent on the interface." 
        ::= { inetMRouteInterfaceEntry 6 } 
     
  
 Thaler,Adams,Siadak  Experimental/Expires Dec 2000                  16 
                 draft-thaler-idmr-multicast-routemib-1       June 2000 


    inetMRouteInterfaceHCInMcastOctets OBJECT-TYPE 
        SYNTAX     Counter64 
        MAX-ACCESS read-only 
        STATUS     current 
        DESCRIPTION 
                "The number of octets of multicast packets that have 
                arrived on the interface, including framing characters. 
                This object is a 64-bit version of 
                inetMRouteInterfaceInMcastOctets.  It is similar to 
                ifHCInOctets in the Interfaces MIB, except that only 
                multicast packets are counted." 
        ::= { inetMRouteInterfaceEntry 7 } 
     
    inetMRouteInterfaceHCOutMcastOctets OBJECT-TYPE 
        SYNTAX     Counter64 
        MAX-ACCESS read-only 
        STATUS     current 
        DESCRIPTION 
                "The number of octets of multicast packets that have 
                been sent on the interface.  This object is a 64-bit 
                version of inetMRouteInterfaceOutMcastOctets." 
        ::= { inetMRouteInterfaceEntry 8 } 
     
    -- 
    --  The IP Multicast Scope Boundary Table 
    -- 
 inetMRouteBoundaryTable OBJECT
                               -TYPE 

        SYNTAX     SEQUENCE OF InetMRouteBoundaryEntry 
        MAX-ACCESS not-accessible 
        STATUS     current 
        DESCRIPTION 
                "The (conceptual) table listing the router's scoped 
                multicast address boundaries." 
        ::= { inetMRoute 5 } 
     
    inetMRouteBoundaryEntry OBJECT-TYPE 
        SYNTAX     InetMRouteBoundaryEntry 
        MAX-ACCESS not-accessible 
        STATUS     current 
        DESCRIPTION 
                "An entry (conceptual row) in the 
                inetMRouteBoundaryTable representing a scoped 
    boundary." 
        INDEX      { inetMRouteBoundaryIfIndex,  
                     inetMRouteBoundaryAddressType, 
                     inetMRouteBoundaryAddress, 
                     inetMRouteBoundaryAddressMaskLen } 
        ::= { inetMRouteBoundaryTable 1 } 
     
    InetMRouteBoundaryEntry ::= SEQUENCE { 
        inetMRouteBoundaryIfIndex            InterfaceIndex, 
        inetMRouteBoundaryAddressType        InetAddressType, 
  
 Thaler,Adams,Siadak  Experimental/Expires Dec 2000                  17 
                 draft-thaler-idmr-multicast-routemib-1       June 2000 


        inetMRouteBoundaryAddress            InetAddress, 
        inetMRouteBoundaryAddressMaskLen     INTEGER, 
    inetMRouteBoundaryStatus             RowStatus 
    } 
     
    inetMRouteBoundaryIfIndex OBJECT-TYPE 
        SYNTAX     InterfaceIndex 
        MAX-ACCESS not-accessible 
        STATUS     current 
        DESCRIPTION 
                "The IfIndex value for the interface to which this 
                boundary applies.  Packets with a destination address 
    in 
                the associated address/mask range will not be forwarded 
                out this interface." 
        ::= { inetMRouteBoundaryEntry 1 } 
     
    inetMRouteBoundaryAddressType OBJECT-TYPE 
        SYNTAX     InetAddressType 
        MAX-ACCESS not-accessible 
        STATUS     current 
        DESCRIPTION 
                "A value indicating the address family of the address 
                contained in inetMRouteBoundaryAddress. Legal values 
                correspond to the subset of address families for which 
                multicast forwarding is supported." 
        ::= { inetMRouteBoundaryEntry 2 } 
     
    inetMRouteBoundaryAddress OBJECT-TYPE 
        SYNTAX     InetAddress 
        MAX-ACCESS not-accessible 
        STATUS     current 
        DESCRIPTION 
                "The group address which when combined with the 
                corresponding value of inetMRouteBoundaryAddressMaskLen 
                identifies the group range for which the scoped 
    boundary 
                exists.  Scoped IPv4 addresses must come from the range 
                239.x.x.x as specified in RFC 2365. Scoped IPv6 
                addresses must come from range ff.nn.nn.nn.nn.nn.nn.nn, 
                where nn encodes the scope type and group identifier as 
                specified in RFC 2373." 
        ::= { inetMRouteBoundaryEntry 3 } 
     
    inetMRouteBoundaryAddressMaskLen OBJECT-TYPE 
        SYNTAX     INTEGER (0..128) 
        MAX-ACCESS not-accessible 
        STATUS     current 
        DESCRIPTION 
                "The length in bits of the mask which when combined 
    with 
                the corresponding value of inetMRouteBoundaryAddress 

  
 Thaler,Adams,Siadak  Experimental/Expires Dec 2000                  18 
                 draft-thaler-idmr-multicast-routemib-1       June 2000 


                identifies the group range for which the scoped 
    boundary 
                exists." 
        ::= { inetMRouteBoundaryEntry 4 } 
     
    inetMRouteBoundaryStatus OBJECT-TYPE 
        SYNTAX     RowStatus 
        MAX-ACCESS read-create 
        STATUS     current 
        DESCRIPTION 
                "The status of this row, by which new entries may be 
                created, or old entries deleted from this table." 
        ::= { inetMRouteBoundaryEntry 5 } 
     
    -- 
    --  The IP Multicast Scope Name Table 
    -- 
     
    inetMRouteScopeNameTable OBJECT-TYPE 
        SYNTAX     SEQUENCE OF InetMRouteScopeNameEntry 
        MAX-ACCESS not-accessible 
        STATUS     current 
        DESCRIPTION 
                "The (conceptual) table listing the multicast scope 
                names." 
        ::= { inetMRoute 6 } 
     
    inetMRouteScopeNameEntry OBJECT-TYPE 
        SYNTAX     InetMRouteScopeNameEntry 
        MAX-ACCESS not-accessible 
        STATUS     current 
        DESCRIPTION 
                "An entry (conceptual row) in the 
                inetMRouteScopeNameTable representing a multicast scope 
                name." 
        INDEX      { inetMRouteScopeNameAddressType, 
                     inetMRouteScopeNameAddress, 
                     inetMRouteScopeNameAddressMaskLen, 
                     IMPLIED inetMRouteScopeNameLanguage } 
        ::= { inetMRouteScopeNameTable 1 } 
     
    InetMRouteScopeNameEntry ::= SEQUENCE { 
        inetMRouteScopeNameAddressType        InetAddressType, 
        inetMRouteScopeNameAddress            InetAddress, 
        inetMRouteScopeNameAddressMaskLen     INTEGER, 
        inetMRouteScopeNameLanguage           LanguageTag, 
        inetMRouteScopeNameString             SnmpAdminString, 
        inetMRouteScopeNameDefault            TruthValue, 
        inetMRouteScopeNameStatus             RowStatus 
    } 
     
    inetMRouteScopeNameAddressType OBJECT-TYPE 
        SYNTAX     InetAddressType 
  
 Thaler,Adams,Siadak  Experimental/Expires Dec 2000                  19 
                 draft-thaler-idmr-multicast-routemib-1       June 2000 


        MAX-ACCESS not-accessible 
        STATUS     current 
        DESCRIPTION 
                "A value indicating the address family of the address 
                contained in inetMRouteScopeNameAddressType. Legal 
                values correspond to the subset of address families for 
                which multicast forwarding is supported." 
        ::= { inetMRouteScopeNameEntry 1 } 
     
    inetMRouteScopeNameAddress OBJECT-TYPE 
        SYNTAX     InetAddress 
        MAX-ACCESS not-accessible 
        STATUS     current 
        DESCRIPTION 
                "The group address which when combined with the 
                corresponding value of 
    inetMRouteScopeNameAddressMaskLen 
                identifies the group range associated with the 
    multicast 
                scope.  Scoped IPv4 addresses must come from the range 
                239.x.x.x. Scoped IPv6 addresses must come from 
                range ff.nn.nn.nn.nn.nn.nn.nn, where nn encodes the 
                scope type and group identifier as specified in RFC 
                2373." 
        ::= { inetMRouteScopeNameEntry 2 } 
     
    inetMRouteScopeNameAddressMaskLen OBJECT-TYPE 
        SYNTAX     INTEGER (0..128) 
        MAX-ACCESS not-accessible 
        STATUS     current 
        DESCRIPTION 
                "The length in bits of the mask which when combined 
                with the corresponding value of 
                inetMRouteScopeNameAddress identifies the group range 
                associated with the multicast scope." 
        ::= { inetMRouteScopeNameEntry 3 } 
     
    inetMRouteScopeNameLanguage OBJECT-TYPE 
        SYNTAX     LanguageTag 
        MAX-ACCESS not-accessible 
        STATUS     current 
        DESCRIPTION 
                "The RFC 1766-style language tag associated with the 
                scope name." 
        ::= { inetMRouteScopeNameEntry 4 } 
     
    inetMRouteScopeNameString OBJECT-TYPE 
        SYNTAX     SnmpAdminString 
        MAX-ACCESS read-create 
        STATUS     current 
        DESCRIPTION 
                "The textual name associated with the multicast scope. 
                The value of this object should be suitable for 
  
 Thaler,Adams,Siadak  Experimental/Expires Dec 2000                  20 
                 draft-thaler-idmr-multicast-routemib-1       June 2000 


                displaying to end-users, such as when allocating a 
                multicast address in this scope.  When no name is 
                specified, the default value of this object for IPv4 
                should be the string 239.x.x.x/y with x and y 
                replaced appropriately to describe the address and mask 
                length associated with the scope. Scoped IPv6 addresses 
                must come from range ff.nn.nn.nn.nn.nn.nn.nn, where nn 
                encodes the scope type and group identifier." 
     
        ::= { inetMRouteScopeNameEntry 5 } 
     
    inetMRouteScopeNameDefault OBJECT-TYPE 
        SYNTAX     TruthValue 
        MAX-ACCESS read-create 
        STATUS     current 
        DESCRIPTION 
                "If true, indicates a preference that the name in the 
                following language should be used by applications if no 
                name is available in a desired language." 
        DEFVAL { false } 
        ::= { inetMRouteScopeNameEntry 6 } 
     
    inetMRouteScopeNameStatus OBJECT-TYPE 
        SYNTAX     RowStatus 
        MAX-ACCESS read-create 
        STATUS     current 
        DESCRIPTION 
                "The status of this row, by which new entries may be 
                created, or old entries deleted from this table." 
        ::= { inetMRouteScopeNameEntry 7 } 
    -- conformance information 
     
    inetMRouteMIBConformance 
                      OBJECT IDENTIFIER ::= { inetMRouteStdMIB 2 } 
    inetMRouteMIBCompliances 
                      OBJECT IDENTIFIER ::= { inetMRouteMIBConformance 
    1 } 
    inetMRouteMIBGroups  OBJECT IDENTIFIER ::= { 
    inetMRouteMIBConformance 2 } 
     
    -- compliance statements 
     
    inetMRouteMIBCompliance MODULE-COMPLIANCE 
        STATUS  current 
        DESCRIPTION 
                "The compliance statement for the IP Multicast MIB." 
        MODULE  -- this module 
        MANDATORY-GROUPS { inetMRouteMIBBasicGroup, 
                           inetMRouteMIBRouteGroup} 
     
            GROUP   inetMRouteMIBBoundaryGroup 
            DESCRIPTION 
                "This group is mandatory if the router supports 
  
 Thaler,Adams,Siadak  Experimental/Expires Dec 2000                  21 
                 draft-thaler-idmr-multicast-routemib-1       June 2000 


                administratively-scoped multicast address boundaries." 
     
            OBJECT      inetMRouteBoundaryStatus 
            MIN-ACCESS  read-only 
            DESCRIPTION 
                "Write access is not required." 
     
            OBJECT      inetMRouteScopeNameStatus 
            MIN-ACCESS  read-only 
            DESCRIPTION 
                "Write access is not required." 
     
            GROUP   inetMRouteMIBHCInterfaceGroup 
            DESCRIPTION 
                "This group is mandatory only for those network 
                 interfaces for which the value of the corresponding 
                 instance of ifSpeed is greater than 20,000,000 
                 bits/second." 
     
        ::= { inetMRouteMIBCompliances 1 } 
     
    -- units of conformance 
    inetMRouteMIBBasicGroup OBJECT-GROUP 
        OBJECTS { inetMRouteEnabled, inetMRouteEntryCount, 
                  inetMRouteUpstreamNeighborType, 
                  inetMRouteUpstreamNeighbor,  
                  inetMRouteInIfIndex, 
                  inetMRouteUpTime, inetMRouteExpiryTime, 
                  inetMRouteNextHopPruned, 
                  inetMRouteNextHopUpTime, 
                  inetMRouteNextHopExpiryTime, 
                  inetMRouteNextHopProtocol, 
                  inetMRouteNextHopPkts, 
                  inetMRouteInterfaceTtl, 
                  inetMRouteInterfaceProtocol, 
                  inetMRouteInterfaceRateLimit, 
                  inetMRouteInterfaceInMcastOctets, 
                  inetMRouteInterfaceOutMcastOctets, 
                  inetMRouteProtocol 
                } 
        STATUS  current 
        DESCRIPTION 
                "A collection of objects to support basic management of 
                 IP Multicast routing." 
        ::= { inetMRouteMIBGroups 1 } 
     
    inetMRouteMIBHopCountGroup OBJECT-GROUP 
        OBJECTS { inetMRouteNextHopClosestMemberHops } 
        STATUS  current 
        DESCRIPTION 
                "A collection of objects to support management of the 
                 use of hop counts in IP Multicast routing." 
        ::= { inetMRouteMIBGroups 2 } 
  
 Thaler,Adams,Siadak  Experimental/Expires Dec 2000                  22 
                 draft-thaler-idmr-multicast-routemib-1       June 2000 


     
    inetMRouteMIBBoundaryGroup OBJECT-GROUP 
        OBJECTS { inetMRouteBoundaryStatus, inetMRouteScopeNameString, 
                  inetMRouteScopeNameDefault, inetMRouteScopeNameStatus 
    } 
        STATUS  current 
        DESCRIPTION 
                "A collection of objects to support management of 
    scoped 
                multicast address boundaries." 
        ::= { inetMRouteMIBGroups 3 } 
     
    inetMRouteMIBPktsOutGroup OBJECT-GROUP 
        OBJECTS { inetMRouteNextHopPkts } 
        STATUS  current 
        DESCRIPTION 
                "A collection of objects to support management of 
    packet 
                counters for each outgoing interface entry of a route." 
        ::= { inetMRouteMIBGroups 4 } 
     
    inetMRouteMIBHCInterfaceGroup OBJECT-GROUP 
        OBJECTS { inetMRouteInterfaceHCInMcastOctets, 
                  inetMRouteInterfaceHCOutMcastOctets, 
                  inetMRouteHCOctets } 
        STATUS  current 
        DESCRIPTION 
                "A collection of objects providing information specific 
                 to high speed (greater than 20,000,000 bits/second) 
                 network interfaces." 
        ::= { inetMRouteMIBGroups 5 } 
     
    inetMRouteMIBRouteGroup OBJECT-GROUP 
        OBJECTS { inetMRouteRtProto, inetMRouteRtAddressType, 
    inetMRouteRtAddress, 
                  inetMRouteRtMaskLen , inetMRouteRtType } 
        STATUS  current 
        DESCRIPTION 
                "A collection of objects providing information on the 
                relationship between multicast routing information,  
                and the IP Forwarding Table." 
        ::= { inetMRouteMIBGroups 6 } 
     
    inetMRouteMIBPktsGroup OBJECT-GROUP 
        OBJECTS { inetMRoutePkts, inetMRouteDifferentInIfPackets, 
                  inetMRouteOctets } 
        STATUS  current 
        DESCRIPTION 
                "A collection of objects to support management of 
    packet 
                counters for each forwarding entry." 
        ::= { inetMRouteMIBGroups 7 } 

  
 Thaler,Adams,Siadak  Experimental/Expires Dec 2000                  23 
                 draft-thaler-idmr-multicast-routemib-1       June 2000 

 END 

--     
--    Copyright (C) The Internet Society (1999).  All Rights Reserved. 
--    This document and translations of it may be copied and furnished to 
--    others, and derivative works that comment on or otherwise explain it 
--    or assist in its implmentation may be prepared, copied, published 
--    and distributed, in whole or in part, without restriction of any 
--    kind, provided that the above copyright notice and this paragraph 
--    are included on all such copies and derivative works.  However, this 
--    document itself may not be modified in any way, such as by removing 
--    the copyright notice or references to the Internet Society or other 
--    Internet organizations, except as needed for the purpose of 
--    developing Internet standards in which case the procedures for 
--    copyrights defined in the Internet Standards process must be 
--    followed, or as required to translate it into languages other than 
--    English. 
--     
--    The limited permissions granted above are perpetual and will not 
--    berevoked by the Internet Society or its successors or assigns. 
--     
--    This document and the information contained herein is provided on an 
--    "AS IS" basis and THE INTERNET SOCIETY AND THE INTERNET ENGINEERING 
--    TASK FORCE DISCLAIMS ALL WARRANTIES, EXPRESS OR IMPLIED, INCLUDING 
--    BUT NOT LIMITED TO ANY WARRANTY THAT THE USE OF THE INFORMATION 
--    HEREIN WILL NOT INFRINGE ANY RIGHTS OR ANY IMPLIED WARRANTIES OF 
--    MERCHANTABILITY OR FITNESS FOR A PARTICULAR PURPOSE. 
--
