--
--  Title:  Appian-TRUNKS-SHARE-MIB
--
--  Date:   02/13/00
--
--  Description:
--
--  This file contains the ASN.1 MIB definition for network level 
--  provisioning of an OSAP2K series platform.  Network provisioning
--  supports the configuration of an OSAP physical layer RING at layer
--  one(1).  SONET ring topology, Uplink Physical Port mapping, STS level
--  mapping (timeslots), Trunking and Frame Relay configuration are 
--  implemented as configuration tables.
--
--
APPIAN-TRUNK-SHARE-MIB DEFINITIONS ::= BEGIN

    IMPORTS

        acTrunks, AcAdminStatus                          FROM APPIAN-SMI-MIB
       
        MODULE-IDENTITY,OBJECT-TYPE                      FROM SNMPv2-SMI
            
        TEXTUAL-CONVENTION, DisplayString                FROM SNMPv2-TC;


acTrunksShare   MODULE-IDENTITY
    LAST-UPDATED    "0002130000Z"
    ORGANIZATION    "Appian Communications, Inc."
    CONTACT-INFO    "Douglas Theriault"
    DESCRIPTION
                    "Appian Communications Common trunking MIBs."
    REVISION
                    "0002130000Z"
    DESCRIPTION
                    "Draft engineering version.  Not for release."

    ::= { acTrunks 1 }


    AcTrunkTimeSlots   ::= TEXTUAL-CONVENTION
                STATUS          current
                DESCRIPTION
                        "List of timeslots bound to a trunk."
                SYNTAX OCTET STRING (SIZE (0..28))

--
-- Trunk Table
--
acTrunkSharedTable    OBJECT-TYPE
    SYNTAX  SEQUENCE OF AcTrunkSharedEntry
    MAX-ACCESS  not-accessible
    STATUS      current
    DESCRIPTION
    "The trunking provisioning table. Records in this table are
     created by management action and not by the OSAP."

    ::= { acTrunksShare 1 }

acTrunkSharedEntry    OBJECT-TYPE
    SYNTAX  AcTrunkSharedEntry
    MAX-ACCESS  not-accessible
    STATUS      current
    DESCRIPTION
    "A row within the trunk provisioning shared table."

    INDEX { acTrunkSharedIndex }
    
    ::= { acTrunkSharedTable 1 }

    AcTrunkSharedEntry ::=
        SEQUENCE {
            acTrunkSharedIndex                INTEGER,
            acTrunkSharedAdminStatus          AcAdminStatus,
            acTrunkSharedName                 DisplayString,
            acTrunkSharedIdentifier           INTEGER,
            acTrunkSharedDataProtocol         INTEGER,
            acTrunkSharedTimeslotList         AcTrunkTimeSlots
        }
--
-- TrunkEntry
--

acTrunkSharedIndex    OBJECT-TYPE
    SYNTAX      INTEGER 
    MAX-ACCESS  accessible-for-notify
    STATUS      current
    DESCRIPTION
    
    "An index key that uniquely identifies a row in the trunk table."

    ::= { acTrunkSharedEntry 1 }


acTrunkSharedAdminStatus    OBJECT-TYPE
    SYNTAX      AcAdminStatus
    MAX-ACCESS  read-create
    STATUS      current
    DESCRIPTION
    "Controls the operational status of the trunk "
    DEFVAL { inactivate }

    ::= { acTrunkSharedEntry 2 }


acTrunkSharedName OBJECT-TYPE
    SYNTAX      DisplayString (SIZE (0..255))
    MAX-ACCESS  read-create
    STATUS      current
    DESCRIPTION
    "The user assigned ASCII name for this trunk."
    DEFVAL      { "" }

    ::= { acTrunkSharedEntry 3 }


acTrunkSharedIdentifier   OBJECT-TYPE
    SYNTAX      INTEGER
    MAX-ACCESS  read-create
    STATUS      current
    DESCRIPTION
    "The user assigned numeric ID for this trunk"
    DEFVAL      { 0 }

    ::= { acTrunkSharedEntry 4 }


acTrunkSharedDataProtocol OBJECT-TYPE
    SYNTAX  INTEGER {
                unknown(0),
                frame-relay(1),
                mfr(2), 
                ppp(3), 
                mlppp(4),
                tls(5)
            }
    MAX-ACCESS  read-create
    STATUS      current
    DESCRIPTION
    "Defines the WAN protocol running over this trunk."
    DEFVAL      { unknown }

    ::= { acTrunkSharedEntry 5 }


acTrunkSharedTimeslotList OBJECT-TYPE
    SYNTAX      AcTrunkTimeSlots
    MAX-ACCESS  read-create
    STATUS      current
    DESCRIPTION
    "List of timeslots bound this this trunk (Logical ports map to 
    timeslots)."
    DEFVAL      { "" }

    ::= { acTrunkSharedEntry 6 }

END
