MSSCOMMON-MIB DEFINITIONS ::= BEGIN

IMPORTS
   DisplayString
         FROM RFC1213-MIB
   OBJECT-TYPE
         FROM RFC-1212
   enterprises
         FROM RFC1155-SMI;

--  MSSCOMMON-MIB MODULE-IDENTITY
--            LAST-UPDATED "9608281200Z"
--            ORGANIZATION "IBM Corporation"
--            CONTACT-INFO
--            " Florian K Kandefer
--               Postal:  IBM Corporation
--                        800 Park Offices Drive
--                        Research Triangle Park, NC 27709
--                        US
--               Tel:     +1 919 254 0685
--               Fax:     +1 919 254 0391
--               E-mail:  kandefer@vnet.ibm.com     "
--            DESCRIPTION
--             " MSS Common Enterprise MIB
--
--              This MIB defines the enterprise specific management objects that
--              are common in the IBM Nways Multiprotocol Switched Services (MSS).
--
--               This MIB is defined in the SNMP version 1 SMI format.
--
--               MIB Version:
--
--                1)  This is the first version of this MIB "

-- ===============
-- | Definitions |
-- ===============


-- =============
-- | Reminders |
-- =============

-- o The DisplayString data type is ASCII characters.
-- o An implementation that conforms to this MIB shall implement all
--   variables for each mandatory group.
-- o If an Optional Group is implemented, all variables of that group
--   must be implemented.

-- ========
-- | OID's|
-- ========

ibm            OBJECT IDENTIFIER ::= { enterprises 2 }

ibmProd        OBJECT IDENTIFIER ::= { ibm 6 }

nwaysMSS       OBJECT IDENTIFIER ::= { ibmProd 118 }

mssCommon      OBJECT IDENTIFIER ::= { nwaysMSS 1 }

-- ===============================
-- | Groups in MSSCOMMON-MIB |
-- ===============================

mssCommonHWVPD      OBJECT IDENTIFIER ::= { mssCommon 1 }

-- ========================
-- || The mssCommonHWVPD ||
-- ========================
-- The mssCommonHWVPD group is MANDATORY for all implementations of the
-- MSSCOMMON-MIB. All implementations that claim conformance to this
-- MIB shall implement this group.

mssHardwareVPDTable  OBJECT-TYPE
   SYNTAX  SEQUENCE OF MssHardwareVPDEntry
   ACCESS  not-accessible
   STATUS  mandatory
   DESCRIPTION
        "A table of the first hardware component's vpd."
   ::= {mssCommonHWVPD 1}

mssHardwareVPDEntry   OBJECT-TYPE
   SYNTAX  MssHardwareVPDEntry
   ACCESS  not-accessible
   STATUS  mandatory
   DESCRIPTION
        "A vpd entry containing objects to describe the hardware component."
   INDEX  { vpdHwComponentIndex, vpdIndex }
   ::= {mssHardwareVPDTable 1}

MssHardwareVPDEntry ::=
   SEQUENCE {
        vpdHwComponentIndex
           INTEGER,
        vpdIndex
           INTEGER,
        vpdKeyword
           DisplayString,
        vpdData
           OCTET STRING
   }

vpdHwComponentIndex  OBJECT-TYPE
   SYNTAX  INTEGER
   ACCESS  read-only
   STATUS  mandatory
   DESCRIPTION
        "The index of the hardware component. The hardware components are
        not in any type of ordering. An examples of a hardware component
        are the Wormwood mother board inside the standalone or the PCI
        adapters attached to the standalone."
   ::= {mssHardwareVPDEntry 1}

vpdIndex  OBJECT-TYPE
   SYNTAX  INTEGER
   ACCESS  read-only
   STATUS  mandatory
   DESCRIPTION
        "The index of the vdp entry for the hardware component."
   ::= {mssHardwareVPDEntry 2}

vpdKeyword  OBJECT-TYPE
   SYNTAX  DisplayString (SIZE(2))
   ACCESS  read-only
   STATUS  mandatory
   DESCRIPTION
        "The keyword identifier for the vpd data. Some of the possible
        values are Adapter Type(keyword = AT), Description(DS), FRU
        number(FN), Part Number(PN), Maintenance Level(ML), Engineering
        Change(EC), Manufacturer(MF), Serial Number(SN), Network
        Address(NA), Rom Level(RM), Type and Model(TM), Feature Number(F#),
        Option Number(O#), Assembly Number(AN), Box Serial Number(BS),
        Recycle Count(RC), User Supplied Data(US), Manufacturer ID(MN),
        Product Specific(Zx where x equals 0,1,2,3...)."
   ::= {mssHardwareVPDEntry 3}

vpdData OBJECT-TYPE
   SYNTAX  OCTET STRING (SIZE(0..256))
   ACCESS  read-only
   STATUS  mandatory
   DESCRIPTION
        "The data field of the vpd that corresponds with the keyword."
   ::= {mssHardwareVPDEntry 4}

END
