RADIUSCLIENTEXT-MIB

   --FORCE-INCLUDE <mib.h>
   --FORCE-INCLUDE <snmpdefs.h>
   --FORCE-INCLUDE <snmpstat.h>
   --FORCE-INCLUDE "mibproto.h"
 
	DEFINITIONS ::= BEGIN

	IMPORTS
	MODULE-IDENTITY, OBJECT-TYPE, Counter32, IpAddress, TimeTicks
			FROM SNMPv2-SMI
		DisplayString, RowStatus
			FROM SNMPv2-TC
		radiusClientExt
			FROM APENT-MIB;

--  RADIUSCLIENTEXT MIB

radiusClientExtMIB MODULE-IDENTITY
	LAST-UPDATED "9707202000Z" -- Wed July 20 20:00:00 EST 1997
	ORGANIZATION "ArrowPoint Communications Inc."
	CONTACT-INFO
	"                       Steve Colby
	Postal:               ArrowPoint Communications Inc.
				                 50 Nagog Park
				                 Acton, Massachusetts 01720
	   Tel:                   +1 978-206-3000  option 1
	   E-Mail:                support@arrowpoint.com"
	DESCRIPTION
		"This MIB module describes the ArrowPoint Communications
		extensions to the client side of the Remote Access Dialin 
		User Service (RADIUS) authentication protocol."
	::= { radiusClientExt 1 }

-- apRadiusClientExtMIBObjects OBJECT IDENTIFIER ::= { radiusClientExtMIB 1 }

-- apRadiusClientExt OBJECT IDENTIFIER ::= { apRadiusClientExtMIBObjects 1 }

apRadiusClientExtInvalidServerAddresses OBJECT-TYPE
	SYNTAX Counter32
	MAX-ACCESS read-only
	STATUS current
 	DESCRIPTION
		"The total number of RADIUS Access-Response packets
		received from unknown addresses since client start-up."
	::= { radiusClientExt 2 }

apRadiusClientExtIdentifier OBJECT-TYPE
	SYNTAX DisplayString
    MAX-ACCESS read-only
    STATUS current
    DESCRIPTION
	    "The NAS-Identifier of the RADIUS client."
	::= { radiusClientExt 3 }

-- Radius Client Globals

-- radius-client-globals OBJECT IDENTIFIER ::= { apRadiusClientExt 5 }

apRadiusClientExtDeadTimer OBJECT-TYPE
	SYNTAX  INTEGER ( 0..255 )
	MAX-ACCESS   read-write
	STATUS   current
	DESCRIPTION
	"This variable specifies the number of minutes to skip down or
	not responsing Radius Servers."
	DEFVAL { 5 }
	::= { radiusClientExt 4 }

apRadiusClientExtProbe OBJECT-TYPE
	SYNTAX  INTEGER { enabled(1), disabled(2) }
	MAX-ACCESS   read-write
	STATUS   current
	DESCRIPTION
	"This variable specifies whether the Radius Client will probe down or
	not responding Radius Servers with probe Access-Request packets to
	determine their availability."
	DEFVAL { enabled }
	::= { radiusClientExt 5 }

apRadiusClientExtRetransmitLimit OBJECT-TYPE
	SYNTAX  INTEGER ( 1..30 )
	MAX-ACCESS   read-write
	STATUS   current
	DESCRIPTION
	"This variable specifies the number of times an authentication or
	accounting request is resent to each radius server after a timeout."
	DEFVAL { 3 }
	::= { radiusClientExt 6 }

apRadiusClientExtTimeout OBJECT-TYPE
	SYNTAX  INTEGER ( 1..255 )
	MAX-ACCESS   read-write
	STATUS   current
	DESCRIPTION
	"This variable specifies the interval the Radius Client will wait for
	the Radius Server to reply to an Authentication or Accounting Request."
	DEFVAL { 10 }
	::= { radiusClientExt 7 }

apRadiusClientExtSourceIpAddress OBJECT-TYPE
	SYNTAX  IpAddress
	MAX-ACCESS   read-write
	STATUS   current
	DESCRIPTION
		"This variable specifies the source IP Address of the interface used
		by the Radius Client."
	DEFVAL { 10 }
	::= { radiusClientExt 8 }

apRadiusClientExtServerTable OBJECT-TYPE
	SYNTAX     SEQUENCE OF ApRadiusClientExtServerEntry
	MAX-ACCESS not-accessible
	STATUS     current
	DESCRIPTION
		"The (conceptual) table listing the RADIUS servers with
		which the client shares a secret."
	::= { radiusClientExt 9 }

apRadiusClientExtServerEntry OBJECT-TYPE
	SYNTAX     ApRadiusClientExtServerEntry
	MAX-ACCESS not-accessible
	STATUS     current
	DESCRIPTION
		"An entry (conceptual row) representing a RADIUS server
		with which the client shares a secret."
	INDEX      { apRadiusClientExtAddress }
	::= { apRadiusClientExtServerTable 1 }

ApRadiusClientExtServerEntry ::= SEQUENCE {
	apRadiusClientExtAddress                         IpAddress,
	apRadiusClientExtRoundTripTime                   TimeTicks,
	apRadiusClientExtAccessRequests                  Counter32,
	apRadiusClientExtAccessRetransmissions           Counter32,
	apRadiusClientExtAccessAccepts                   Counter32,
	apRadiusClientExtAccessRejects                   Counter32,
	apRadiusClientExtAccessChallenges                Counter32,
	apRadiusClientExtMalformedAccessResponses        Counter32,
	apRadiusClientExtAuthenticationBadAuthenticators Counter32,
	apRadiusClientExtAuthenticationPendingRequests   Counter32,
	apRadiusClientExtAuthenticationTimeouts          Counter32,
	apRadiusClientExtAccountingRequests              Counter32,
	apRadiusClientExtAccountingRetransmissions       Counter32,
	apRadiusClientExtAccountingResponses             Counter32,
	apRadiusClientExtMalformedAccountingResponses    Counter32,
	apRadiusClientExtAccountingBadAuthenticators     Counter32,
	apRadiusClientExtAccountingPendingRequests       Counter32,
	apRadiusClientExtAccountingTimeouts              Counter32,
	apRadiusClientExtUnknownType                     Counter32
	}

apRadiusClientExtAddress OBJECT-TYPE
	SYNTAX  IpAddress
	MAX-ACCESS  read-only
	STATUS  current
	DESCRIPTION
		"The IP address of the RADIUS server
		referred to in this table entry."
 ::= { apRadiusClientExtServerEntry 1 }

apRadiusClientExtRoundTripTime  OBJECT-TYPE
	SYNTAX  TimeTicks
	MAX-ACCESS  read-only
	STATUS  current
	DESCRIPTION
		"The total roundtrip time of the last packet sent
		between the client and the RADIUS server referred
		to in this table entry."
	::= { apRadiusClientExtServerEntry 2 }

apRadiusClientExtAccessRequests OBJECT-TYPE
	SYNTAX  Counter32
	MAX-ACCESS  read-only
	STATUS  current
	DESCRIPTION
		"The total number of RADIUS Access-Request packets sent
		to this server since client start-up. This does not
		include retransmissions."
	::= { apRadiusClientExtServerEntry 3 }

apRadiusClientExtAccessRetransmissions OBJECT-TYPE
	SYNTAX  Counter32
	MAX-ACCESS  read-only
	STATUS  current
	DESCRIPTION
		"The total number of RADIUS Access-Request packets
		retransmitted to the same server since client start-up."
	::= { apRadiusClientExtServerEntry 4 }

apRadiusClientExtAccessAccepts OBJECT-TYPE
	SYNTAX Counter32
	MAX-ACCESS read-only
	STATUS current
	DESCRIPTION
		"The total number of RADIUS Access-Accept packets
		received from this server since client start-up."
	::= { apRadiusClientExtServerEntry 5 }

apRadiusClientExtAccessRejects OBJECT-TYPE
	SYNTAX  Counter32
	MAX-ACCESS  read-only
	STATUS  current
	DESCRIPTION
		"The total number of RADIUS Access-Reject packets
		received from this server since client start-up."
	::= { apRadiusClientExtServerEntry  6 }

apRadiusClientExtAccessChallenges OBJECT-TYPE
	SYNTAX  Counter32
	MAX-ACCESS  read-only
	STATUS current
	DESCRIPTION
		"The total number of RADIUS Access-Challenge packets
		received from this server since client start-up."
	::= { apRadiusClientExtServerEntry 7 }

-- "Access-Response" includes an Access-Accept, Access-Challenge
-- or Access-Reject

apRadiusClientExtMalformedAccessResponses OBJECT-TYPE
	SYNTAX  Counter32
	MAX-ACCESS  read-only
	STATUS  current
	DESCRIPTION
		"The total number of malformed RADIUS Access-Response
		packets received from this server since client
		start-up. Bad authenticators are not included as
		malformed access responses."
	::= { apRadiusClientExtServerEntry 8 }

apRadiusClientExtAuthenticationBadAuthenticators OBJECT-TYPE
	SYNTAX  Counter32
	MAX-ACCESS  read-only
	STATUS  current
	DESCRIPTION
		"The total number of RADIUS Access-Response packets
		containing invalid authenticators received from this server
		since client start-up."
	::= { apRadiusClientExtServerEntry 9 }

apRadiusClientExtAuthenticationPendingRequests OBJECT-TYPE
	SYNTAX  Counter32
	MAX-ACCESS  read-only
	STATUS  current
	DESCRIPTION
		"The total number of RADIUS Access-Request packets
		destined for this server that have not yet timed out
		or received a response. This variable is incremented
		when an Access-Request is sent and decremented due to
		a timeout or retransmission."
	::= { apRadiusClientExtServerEntry 10 }

apRadiusClientExtAuthenticationTimeouts OBJECT-TYPE
	SYNTAX  Counter32
	MAX-ACCESS  read-only
	STATUS  current
	DESCRIPTION
		"The total number of authentication timeouts to this server
		since client startup. After a timeout the client may
		retry to the same server, send to a different server, or
		give up. A retry to the same server is counted as a
		retransmit as well as a timeout. A send to a different
		server is counted as a Request as well as a timeout."
	::= { apRadiusClientExtServerEntry  11 }

apRadiusClientExtAccountingRequests OBJECT-TYPE
	SYNTAX  Counter32
	MAX-ACCESS  read-only
	STATUS  current
	DESCRIPTION
		"The total number of RADIUS Accounting-Request packets
		sent since client start-up. This does not include
		retransmissions."
	::= { apRadiusClientExtServerEntry 12 }

apRadiusClientExtAccountingRetransmissions OBJECT-TYPE
	SYNTAX  Counter32
	MAX-ACCESS  read-only
	STATUS  current
	DESCRIPTION
		"The total number of RADIUS Accounting-Request packets
		retransmitted to the same server since client start-up.
		Retransmissions include retries where the
		Identifier and Acct-Delay have been updated."
	::= { apRadiusClientExtServerEntry 13 }

apRadiusClientExtAccountingResponses OBJECT-TYPE
	SYNTAX  Counter32
	MAX-ACCESS  read-only
	STATUS  current
	DESCRIPTION
		"The total number of RADIUS Accounting-Response
		packets received from this server since client start-up."
	::= { apRadiusClientExtServerEntry 14 }

apRadiusClientExtMalformedAccountingResponses OBJECT-TYPE
	SYNTAX  Counter32
	MAX-ACCESS  read-only
	STATUS  current
	DESCRIPTION
		"The total number of malformed RADIUS Accounting-Response
		packets received from this server since client start-up.
		Bad authenticators are not included as malformed access
		responses."
	::= { apRadiusClientExtServerEntry 15 }

apRadiusClientExtAccountingBadAuthenticators OBJECT-TYPE
	SYNTAX  Counter32
	MAX-ACCESS  read-only
	STATUS  current
	DESCRIPTION
		"The total number of RADIUS Accounting-Response
		packets which contained invalid authenticators
		received from this server since client start-up."
	::= { apRadiusClientExtServerEntry 16 }

apRadiusClientExtAccountingPendingRequests OBJECT-TYPE
	SYNTAX  Counter32
	MAX-ACCESS  read-only
	STATUS  current
	DESCRIPTION
		"The total number of RADIUS Accounting-Request packets
		sent to this server that have not yet timed out or
		received a response. This variable is incremented when an
		Accounting-Request is sent and decremented due to a timeout
		or retransmission."
	::= { apRadiusClientExtServerEntry 17 }

apRadiusClientExtAccountingTimeouts OBJECT-TYPE
	SYNTAX  Counter32
	MAX-ACCESS  read-only
	STATUS  current
	DESCRIPTION
		"The total number of accounting timeouts to this server
		since client startup. After a timeout the client may
		retry to the same server, send to a different server, or
		give up. A retry to the same server is counted as a
		retransmit as well as a timeout. A send to a different
		server is counted as an Accounting-Request as well as a timeout."
	::= { apRadiusClientExtServerEntry  18 }

apRadiusClientExtUnknownType OBJECT-TYPE
	SYNTAX  Counter32
	MAX-ACCESS  read-only
	STATUS  current
	DESCRIPTION
		"The total number of RADIUS packets of unknown type which
		were received from this server since client start-up."
	::= { apRadiusClientExtServerEntry  19 }

apRadiusClientExtTable        OBJECT-TYPE
SYNTAX	SEQUENCE OF ApRadiusClientExtRadServerEntry
	MAX-ACCESS  not-accessible
	STATUS  current
	DESCRIPTION
		"The table listing the RADIUS servers with which the client 
		shares a secret."
	::= { radiusClientExt 10 }

apRadiusClientExtRadServerEntry OBJECT-TYPE
	SYNTAX	ApRadiusClientExtRadServerEntry
	MAX-ACCESS  not-accessible
	STATUS  current
	DESCRIPTION
		"The information regarding a single RADIUS server with which
		the client shares a secret."
	INDEX	{ apRadiusClientExtRadServerIpAddress }
	::= { apRadiusClientExtTable 1 }

ApRadiusClientExtRadServerEntry ::= SEQUENCE {
	apRadiusClientExtRadServerIpAddress
		IpAddress,
	apRadiusClientExtRadServerAuthPort
		INTEGER,
	apRadiusClientExtRadServerAcctPort
		INTEGER,
	apRadiusClientExtRadServerSecret
		DisplayString,		
	apRadiusClientExtStatus
		RowStatus
}

apRadiusClientExtRadServerIpAddress OBJECT-TYPE
	SYNTAX  IpAddress
	MAX-ACCESS  read-create
	STATUS  current
	DESCRIPTION
		"The Radius Server IP Address."
	::= { apRadiusClientExtRadServerEntry 1 }	

apRadiusClientExtRadServerAuthPort OBJECT-TYPE
	SYNTAX  INTEGER ( 1..65535 )
	MAX-ACCESS  read-create
	STATUS  current
	DESCRIPTION
		"The UDP port number on the Radius Server which to send Radius
		Authentication packets."
	DEFVAL { 1645 }
	::= { apRadiusClientExtRadServerEntry 2 }

apRadiusClientExtRadServerAcctPort OBJECT-TYPE
	SYNTAX      INTEGER ( 1..65535 )
	MAX-ACCESS  read-create
	STATUS      current
	DESCRIPTION
		"The UDP port number on the Radius Server which to send Radius
		Accounting packets."
	DEFVAL { 1646 }
	::= { apRadiusClientExtRadServerEntry 3 }

apRadiusClientExtRadServerSecret OBJECT-TYPE
	SYNTAX		DisplayString (SIZE ( 1..16 ))
	MAX-ACCESS  read-create
	STATUS  	current
	DESCRIPTION
		"This is the Radius Secret which is shared between this Radius
		Client and the Radius Server."
	::= { apRadiusClientExtRadServerEntry 4 }

apRadiusClientExtStatus OBJECT-TYPE
	SYNTAX		RowStatus
	MAX-ACCESS	read-create
	STATUS		current
	DESCRIPTION      
		"This object is used to create and destroy a Radius Server
		instance."
	::= { apRadiusClientExtRadServerEntry 5 }

	END
