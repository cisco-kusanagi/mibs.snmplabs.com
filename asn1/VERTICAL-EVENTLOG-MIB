VERTICAL-EVENTLOG-MIB DEFINITIONS ::= BEGIN

IMPORTS
             Gauge, enterprises
                     FROM RFC1155-SMI
             DisplayString
                     FROM RFC1213-MIB
             OBJECT-TYPE
                     FROM RFC-1212
             TRAP-TYPE
                     FROM RFC-1215;
             

vertical OBJECT IDENTIFIER ::= { enterprises 2338 }  


     --  This MIB module uses the extended OBJECT-TYPE macro 
	 --  as defined in RFC 1212.
  
     --  This is the MIB module for Vertical Networks IO Box
     --  Event Log Traps. This module defines the Traps that 
     --  will be generated when specific (System, Application
	 --  and Security) WinNT events are logged.
	 --  This MIB is found in the private.enterprise branch 
	 --  of the MIB tree.

     --  Author  : Raju Viswambharan
     --  Version : 1.0
     --  Date    : 04 November, 1998
     --  Comments : created
 

     -- This MIB contains one group:
	 --	The Trap Info Group: Which contains more information
     --                      about the last Event Log Trap
	 --					     that was generated

	 eventLog    OBJECT IDENTIFIER ::= {vertical 13}
								   


	-- Trap Information Group - contains information about 
	--                 the last Event Log Trap generated

	eventLogTrapInfoGroup OBJECT IDENTIFIER ::= { eventLog 1 }
	
	

	lastTrapLogType OBJECT-TYPE
		SYNTAX	INTEGER {
						system		(1),
						security	(2),
						application	(3),
						unknown		(4)
				}
		ACCESS  read-only
		STATUS  mandatory
		DESCRIPTION
            "This object describes the Log Type of the last 
			 Event Log trap reported. The following are valid
			 values: 
			 system			(1) -> Win NT System Log
			 security		(2) -> Win NT Security Log
			 application	(3) -> The Application Log
			 unknown		(4) -> Unknown Log"
			::= { eventLogTrapInfoGroup 1 }

	lastTrapEventType OBJECT-TYPE
		SYNTAX	INTEGER {
						error			(1),
						warning			(2),
						information		(3),
						audit-success	(4),
						audit-fail		(5),
						unknown			(6)
				}
		ACCESS  read-only
		STATUS  mandatory
		DESCRIPTION
            "This object describes the Event Type of the last 
			 Event Log trap reported. The following are valid
			 values: 
			 error			(1) -> Error events indicate 
								   significant problems that 
								   the user should know about.
								   Error events usually 
								   indicate a loss of 
								   functionality or data. For
								   example, if a service 
								   cannot be loaded as the 
								   system boots, it can log 
								   an error event.
			 warning		(2) -> Warning events indicate 
								   problems that are not 
								   immediately significant, 
								   but that may indicate 
								   conditions that could 
								   cause future problems. 
								   For example,an application
								   can logs warning event if
								   disk space is low. 
			 information	(3) -> Information events indicate
								   infrequent but significant
								   successful operations. 
			 audit-success	(4) -> Success audit events are
								   security events that occur
								   when an audited access 
								   attempt is successful. For
								   example, a successful logon
								   attempt is a success audit
								   event.
			 audit-fail		(5) -> Failure audit events are 
								   security events that occur
								   when an audited access 
								   attempt fails. For example,
								   a failed attempt to open a
								   file is a failure audit 
								   event.
			unknown			(6)	-> Indicates an event type 
								   other than those described 
								   above."
			::= { eventLogTrapInfoGroup 2 }


	lastTrapInfoString OBJECT-TYPE
		SYNTAX      OCTET STRING (SIZE (0..512))
        ACCESS  read-only
        STATUS      mandatory
        DESCRIPTION
            "This object describes,in more detail,the last 
			 Event Log Trap event that occured. "
			::= { eventLogTrapInfoGroup 3 }

-- TRAP Definitions - 

eventLog-FailedToStartSTD TRAP-TYPE
	ENTERPRISE  vertical
	VARIABLES {lastTrapLogType, 
				lastTrapEventType, 
				lastTrapInfoString }
	DESCRIPTION
        " This notification is sent when an attempt to start
		  the Self Start Daemon fails."
	::= 53

eventLog-FailedToStopSTD TRAP-TYPE
	ENTERPRISE  vertical
	VARIABLES {lastTrapLogType, 
				lastTrapEventType, 
				lastTrapInfoString }
	DESCRIPTION
        " This notification is sent when an attempt to stop
		  the Self Start Daemon fails."
	::= 54

eventLog-CannotCreateUserTracePipe TRAP-TYPE
	ENTERPRISE  vertical
	VARIABLES {lastTrapLogType, 
				lastTrapEventType, 
				lastTrapInfoString }
	DESCRIPTION
        " This notification is sent when an attempt to 
		  create the User Trace request pipe fails."
	::= 55

eventLog-CannotConnectUserTracePipe TRAP-TYPE
	ENTERPRISE  vertical
	VARIABLES {lastTrapLogType, 
				lastTrapEventType, 
				lastTrapInfoString }
	DESCRIPTION
        " This notification is sent when an attempt to 
		  connect to the User Trace request pipe fails."
	::= 56

eventLog-VoiceMailDiskIsFull TRAP-TYPE
	ENTERPRISE  vertical
	VARIABLES {lastTrapLogType, 
				lastTrapEventType, 
				lastTrapInfoString }
	DESCRIPTION
        " This notification is sent when the Voice Mail 
		  disk capacity is reached."
	::= 57

eventLog-SystemDiskIsFull TRAP-TYPE
	ENTERPRISE  vertical
	VARIABLES {lastTrapLogType, 
				lastTrapEventType, 
				lastTrapInfoString }
	DESCRIPTION
        " This notification is sent when the specific 
		  disk capacity is reached."
	::= 58

eventLog-SecurityError TRAP-TYPE
	ENTERPRISE  vertical
	VARIABLES {lastTrapLogType, 
				lastTrapEventType, 
				lastTrapInfoString }
	DESCRIPTION
        " This notification is sent when a failure audit 
		  event occurs, i.e. an audited access attempt fails.
		  For example, a failed attempt to open a file is a 
		  failure audit event."
	::= 59

eventLog-SecuritySuccess TRAP-TYPE
	ENTERPRISE  vertical
	VARIABLES {lastTrapLogType, 
				lastTrapEventType, 
				lastTrapInfoString }
	DESCRIPTION
        " This notification is sent when a success audit 
		  event occurs, i.e. when an audited access attempt
		  is successful. For example, a successful logon 
		  attempt is a success audit event."
	::= 60

eventLog-GenericEventLogTrap TRAP-TYPE
	ENTERPRISE  vertical
	VARIABLES {lastTrapLogType, 
				lastTrapEventType, 
				lastTrapInfoString }
	DESCRIPTION
        " This notification is sent whenever an error or 
		  warning event is written to the Event Log. 
		  More information about this event (i.e. which log
		  - system, app or security, as well as which event
		  type - error, warning or audit,etc) can be found 
		  from the trap data."
	::= 61

END
