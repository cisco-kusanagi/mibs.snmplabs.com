-- *****************************************************************
--
-- STN-ATM-MIB.mib:  
--      Spring Tide Networks ATM MIB file.
--
--
--      Copyright (c) 1999, 2000 by Spring Tide Networks, Inc.
--                      ALL RIGHTS RESERVED       
--
-- *****************************************************************

-- MIB Object definitions for Spring Tide Network ATM 


STN-ATM-MIB DEFINITIONS ::= BEGIN

    IMPORTS
        MODULE-IDENTITY,
        OBJECT-TYPE,
        NOTIFICATION-TYPE, 
        Integer32,
        Counter32,
        IpAddress
                FROM SNMPv2-SMI

        TEXTUAL-CONVENTION,
        DisplayString,
        TruthValue
                FROM SNMPv2-TC

        MODULE-COMPLIANCE 
                FROM SNMPv2-CONF

        
        InterfaceIndex
                FROM IF-MIB

        NSAPAddress
                FROM SPRING-TIDE-NETWORKS-TC

        stnSystems,
        stnNotification
                FROM SPRING-TIDE-NETWORKS-SMI

        stnRouterIndex
                FROM STN-ROUTER-MIB;


    stnAtm          MODULE-IDENTITY
        LAST-UPDATED    "0002160000Z"
        ORGANIZATION    "Spring Tide Networks, Inc."
        CONTACT-INFO
                "
                Spring Tide Networks, Inc.
                Customer Service
                Postal: 3 Clock Tower Place
                        Maynard, MA 01754
                Tel:    1 888-786-4357
                Email:  stncs@springtidenet.com
                "
        DESCRIPTION
                "Initial version of this MIB module."
        ::= { stnSystems 6 }


    --
    -- Top Level STN ATM MIB Objects
    --
    stnAtmObjects           OBJECT IDENTIFIER ::= { stnAtm 1 }
    stnAtmMibConformance    OBJECT IDENTIFIER ::= { stnAtm 2 }

    stnAtmLinks             OBJECT IDENTIFIER ::= { stnAtmObjects 1 }
    stnAtmCrossConns        OBJECT IDENTIFIER ::= { stnAtmObjects 2 }
    stnAtmTrafficDescrs     OBJECT IDENTIFIER ::= { stnAtmObjects 3 }
    stnAtmPorts             OBJECT IDENTIFIER ::= { stnAtmObjects 4 }
    stnAtmTraces            OBJECT IDENTIFIER ::= { stnAtmObjects 5 }
    stnAtmQos               OBJECT IDENTIFIER ::= { stnAtmObjects 6 }
    stnAtmAddresses         OBJECT IDENTIFIER ::= { stnAtmObjects 7 }
    stnAtmThresholds        OBJECT IDENTIFIER ::= { stnAtmObjects 8 }
    stnAtmAcct              OBJECT IDENTIFIER ::= { stnAtmObjects 9 }

    -- Mid-Level STN ATM MIB Objects
    stnVcLinks              OBJECT IDENTIFIER ::= { stnAtmLinks 1 }

    stnVcCrossConns         OBJECT IDENTIFIER ::= { stnAtmCrossConns 1 }
    stnVpCrossConns         OBJECT IDENTIFIER ::= { stnAtmCrossConns 2 }

    stnAtmPortAttrs         OBJECT IDENTIFIER ::= { stnAtmPorts 1 }
    stnAtmPortIlmi          OBJECT IDENTIFIER ::= { stnAtmPorts 2 }
    stnAtmPortSignaling     OBJECT IDENTIFIER ::= { stnAtmPorts 3 }
    stnAtmPortTraffic       OBJECT IDENTIFIER ::= { stnAtmPorts 4 }

    stnTraceIps             OBJECT IDENTIFIER ::= { stnAtmTraces 1 }
    stnTracePd              OBJECT IDENTIFIER ::= { stnAtmTraces 2 }

    stnQosCLR               OBJECT IDENTIFIER ::= { stnAtmQos 1 }
    stnQosCDV               OBJECT IDENTIFIER ::= { stnAtmQos 2 }
    stnQosCTD               OBJECT IDENTIFIER ::= { stnAtmQos 3 }


    -- Low-Level STN ATM MIB Objects
    stnAtmPortSigs          OBJECT IDENTIFIER ::= { stnAtmPortSignaling 1 }
    stnAtmPortSigDurations  OBJECT IDENTIFIER ::= { stnAtmPortSignaling 2 }
    stnAtmPortSigRetries    OBJECT IDENTIFIER ::= { stnAtmPortSignaling 3 }


    -- Additional STN ATM MIB Textual Conventions
    VcLinkOperStatus ::= TEXTUAL-CONVENTION
        STATUS      current
        DESCRIPTION "Operational status of a VC Link."
        SYNTAX      INTEGER {
                                active(1),            --
                                not-in-service(2),    -- 
                                not-ready(3),         -- 
                                create-and-go(4),     -- 
                                create-and-wait(5),   -- 
                                destroy(6)            -- 
                            }

    VcCrossConnOperStatus ::= TEXTUAL-CONVENTION
        STATUS      current
        DESCRIPTION "Operational status of a VC cross connection."
        SYNTAX      INTEGER {   active(1),            --
                                not-in-service(2),    -- 
                                not-ready(3),         -- 
                                create-and-go(4),     -- 
                                create-and-wait(5),   -- 
                                destroy(6)            -- 
                            }

    TrafficDescrOperStatus ::= TEXTUAL-CONVENTION
        STATUS      current
        DESCRIPTION "Operational status of a traffic descriptor."
        SYNTAX      INTEGER {   active(1),            --
                                not-in-service(2),    -- 
                                not-ready(3),         -- 
                                create-and-go(4),     -- 
                                create-and-wait(5),   -- 
                                destroy(6)            -- 
                            }

    AtmPortOperStatus ::= TEXTUAL-CONVENTION
        STATUS      current
        DESCRIPTION "Operational status of an ATM port."
        SYNTAX      INTEGER {   active(1),          --
                                inactive(2)         -- 
                            }


    --
    -- STN ATM VC Link Table
    --

    stnVcLinkTable OBJECT-TYPE
        SYNTAX        SEQUENCE OF StnVcLinkEntry
        MAX-ACCESS    not-accessible
        STATUS        current
        DESCRIPTION   "A list of VC Link entries."
        ::= { stnVcLinks 1 }
 
    stnVcLinkEntry OBJECT-TYPE
        SYNTAX          StnVcLinkEntry
        MAX-ACCESS      not-accessible
        STATUS          current
        DESCRIPTION     "Entry contains information about a particular 
                        VC link."  
        INDEX           { stnVcLinkIfIndex, stnVcLinkVpi, stnVcLinkVci }
        ::= { stnVcLinkTable 1 }
 
    StnVcLinkEntry ::= 
        SEQUENCE {
                stnVcLinkIfIndex                InterfaceIndex,
                stnVcLinkVpi                    Integer32,
                stnVcLinkVci                    Integer32,
                stnVcLinkRcvTrafDescr           Integer32,
                stnVcLinkXmtTrafDescr           Integer32,
                stnVcLinkAalObjectsValid        Integer32,
                stnVcLinkAalType                INTEGER,
                stnVcLinkAal5XmtSDUSize         Integer32,
                stnVcLinkAal5RcvSDUSize         Integer32,
                stnVcLinkAal5EncapsType         Integer32,
                stnVcLinkCastType               INTEGER,
                stnVcLinkConnKind               INTEGER,
                stnVcLinkAccEnabled             TruthValue,
                stnVcLinkOAMMgmtEnabled         TruthValue,
                stnVcLinkOAMXmtFrequency        Integer32,
                stnVcLinkOAMRetryUpCount        Integer32,
                stnVcLinkOAMRetryDownCount      Integer32,
                stnVcLinkOAMRetryFrequency      Integer32,
                stnVcLinkPppId                  Integer32,     
                stnVcLinkOperStatus             VcLinkOperStatus
        }

    stnVcLinkIfIndex OBJECT-TYPE
        SYNTAX          InterfaceIndex
        MAX-ACCESS      read-only
        STATUS          current
        DESCRIPTION     "The interface index represents a connection point on
                         the switch fabric from a module or line card. It is
                         calculated based on the slot and port of the module."
        ::= { stnVcLinkEntry 1 }

    stnVcLinkVpi OBJECT-TYPE     
        SYNTAX          Integer32 
        MAX-ACCESS      read-only
        STATUS          current
        DESCRIPTION     "The VPI value of the VPL. Note that the VPI=0 is 
                        not used for a VPL not associated with a VCL.  
                        The maximum VPI value cannot exceed the value 
                        allowable by the atmInterfaceMaxVpiBits."
        ::= { stnVcLinkEntry 2 }

    stnVcLinkVci OBJECT-TYPE     
        SYNTAX          Integer32 
        MAX-ACCESS      read-only
        STATUS          current
        DESCRIPTION     "The VCI value of the VCL. The maximum VCI value 
                        cannot exceed the value allowable by the 
                        atmInterfaceMaxVciBits."
        ::= { stnVcLinkEntry 3 }

    stnVcLinkRcvTrafDescr OBJECT-TYPE     
        SYNTAX          Integer32 
        MAX-ACCESS      read-only
        STATUS          current
        DESCRIPTION     "Receive traffic descriptor identifier for this VPL."
        ::= { stnVcLinkEntry 4 }

    stnVcLinkXmtTrafDescr OBJECT-TYPE     
        SYNTAX          Integer32 
        MAX-ACCESS      read-only
        STATUS          current
        DESCRIPTION     "Transmit traffic descriptor identifier for this VPL."
        ::= { stnVcLinkEntry 5 }

    stnVcLinkAalObjectsValid OBJECT-TYPE
        SYNTAX          Integer32
        MAX-ACCESS      read-only
        STATUS          current
        DESCRIPTION     "Indicates whether the following AAL objects are valid
                         (whether the local VCL end-point is also the VCC
                         end-point). Transmit traffic descriptor identifier for
                        this VPL."
        ::= { stnVcLinkEntry 6 }

    stnVcLinkAalType OBJECT-TYPE     
        SYNTAX          INTEGER {
                                aal1(1),
                                aal3-4(2),
                                aal5(3),
                                other(4)
                        }
        MAX-ACCESS      read-only
        STATUS          current
        DESCRIPTION     "An instance of this object only exists when the 
                        local VCL end-point is also the VCC end-point, 
                        and AAL is in use. The type of AAL used on this VCC. 
                        The AAL type includes AAL1, AAL3/4, and AAL5. 
                        The other(4) may be used as a user-defined AAL type. 
                        The unknown type indicates that the AAL type cannot 
                        be determined."
        ::= { stnVcLinkEntry 7 }

    stnVcLinkAal5XmtSDUSize OBJECT-TYPE     
        SYNTAX          Integer32 
        MAX-ACCESS      read-only
        STATUS          current
        DESCRIPTION     "An instance of this object only exists when the 
                        local VCL end-point is also the VCC end-point, and 
                        AAL5 is in use. The maximum AAL5 CPCS SDUsize in 
                        octets that is supported on the transmit direction 
                        of this VCC."
        DEFVAL          { 4096 }
        ::= { stnVcLinkEntry 8 }

    stnVcLinkAal5RcvSDUSize OBJECT-TYPE     
        SYNTAX          Integer32 
        MAX-ACCESS      read-only
        STATUS          current
        DESCRIPTION     "An instance of this object only exists when the 
                        local VCL end-point is also the VCC end-point, and 
                        AAL5 is in use.  The maximum AAL5 CPCS SDU size in 
                        octets that is supported on the receive direction 
                        of this VCC."
        DEFVAL          { 4096 }
        ::= { stnVcLinkEntry 9 }

    stnVcLinkAal5EncapsType OBJECT-TYPE     
        SYNTAX          Integer32 
        MAX-ACCESS      read-only
        STATUS          current
        DESCRIPTION     "An instance of this object only exists when the 
                        local VCL end-point is also the VCC end-point, and 
                        AAL5 is in use.  The type of data encapsulation used 
                        over the AAL5 SSCS layer.  The definitions reference 
                        RFC 1483 Multiprotocol Encapsulation over ATM AAL5 
                        and to the ATM Forum LAN Emulation specification."
        ::= { stnVcLinkEntry 10 }

    stnVcLinkCastType OBJECT-TYPE     
        SYNTAX          INTEGER {
                                p2mpRoot(1),
                                p2mpLeaf(2)
                        }
        MAX-ACCESS      read-only
        STATUS          current
        DESCRIPTION     "The type of topology of a connection 
                        (point- to-point, point-to-multipoint).
                        In the case of point-to-multipoint, the orientation 
                        of this VPL in the connection.  On a host, p2mpRoot 
                        indicates that the host is the root of the p2mp 
                        connection, p2mpLeaf indicates that the host is a 
                        leaf of the p2mp connection.  On a switch, p2mpRoot 
                        indicates that cells received by the switching fabric 
                        from the interface are from the root of the p2mp 
                        connection, p2mpLeaf indicates that cells transmitted 
                        to the interface from the switching fabric are to the 
                        leaf of the p2mp connection."
        ::= { stnVcLinkEntry 11 }

    stnVcLinkConnKind OBJECT-TYPE    
        SYNTAX          INTEGER {
                                pvc(1),
                                svc-incomming(2),
                                svc-outgoing(3),
                                spvc-initiator(4),
                                spvc-target(5)
                        }
        MAX-ACCESS      read-only
        STATUS          current
        DESCRIPTION     "The use of call control.  An spvcInitiator is always
                        cross-connected to an svcOutgoing, and an spvcTarget
                        is always cross-connected to an svcIncoming."
        ::= { stnVcLinkEntry 12 }

    stnVcLinkAccEnabled OBJECT-TYPE     
        SYNTAX          TruthValue
        MAX-ACCESS      read-only
        STATUS          current
        DESCRIPTION     "ATM accounting is enabled for this VC Link."
        DEFVAL          { false }
        ::= { stnVcLinkEntry 13 }

    stnVcLinkOAMMgmtEnabled OBJECT-TYPE     
        SYNTAX          TruthValue
        MAX-ACCESS      read-only
        STATUS          current
        DESCRIPTION     "OAM management is enabled."
        DEFVAL          { false }
        ::= { stnVcLinkEntry 14 }

    stnVcLinkOAMXmtFrequency OBJECT-TYPE     
        SYNTAX          Integer32
        MAX-ACCESS      read-only
        STATUS          current
        DESCRIPTION     "Number of seconds between transmitting OAM 
                        loopback cells."
        DEFVAL          { 5 }
        ::= { stnVcLinkEntry 15 }

    stnVcLinkOAMRetryUpCount OBJECT-TYPE     
        SYNTAX          Integer32
        MAX-ACCESS      read-only
        STATUS          current
        DESCRIPTION     "Number of consecutive end-to-end F5 OAM loopback 
                        cell responses that must be received in order to 
                        change a PVC state to up. Does not apply to SVCs."
        DEFVAL          { 3 }
        ::= { stnVcLinkEntry 16 }

    stnVcLinkOAMRetryDownCount OBJECT-TYPE     
        SYNTAX          Integer32
        MAX-ACCESS      read-only
        STATUS          current
        DESCRIPTION     "Number of consecutive end-to-end F5 OAM loopback 
                        cell responses that are not received in order to 
                        change a PVC state to down or tear down an SVC."
        DEFVAL          { 5 }
        ::= { stnVcLinkEntry 17 }

    stnVcLinkOAMRetryFrequency OBJECT-TYPE     
        SYNTAX          Integer32
        MAX-ACCESS      read-only
        STATUS          current
        DESCRIPTION     "The frequency (in seconds) that end-to-end F5 
                        loopback cells should be transmitted when a change 
                        in UP/DOWN state is being verified. For example, if 
                        a PVC is up and a loopback cell response is not 
                        received after the frequency (in seconds, then 
                        loopback cells are sent at the retry-frequency to 
                        verify whether or not the PVC is down."
        DEFVAL          { 5 }
        ::= { stnVcLinkEntry 18 }

    stnVcLinkPppId OBJECT-TYPE     
        SYNTAX          Integer32
        MAX-ACCESS      read-only
        STATUS          current
        DESCRIPTION     "PPP ID"
        ::= { stnVcLinkEntry 19 }

    stnVcLinkOperStatus OBJECT-TYPE     
        SYNTAX          VcLinkOperStatus
        MAX-ACCESS      read-only
        STATUS          current
        DESCRIPTION     "Operational status of the VC Link."
        ::= { stnVcLinkEntry 20 }


    --
    -- STN ATM VC Cross Connection Table
    --

    stnVcCrossConnTable OBJECT-TYPE
        SYNTAX        SEQUENCE OF StnVcCrossConnEntry
        MAX-ACCESS    not-accessible
        STATUS        current
        DESCRIPTION   "A list of VC cross connection entries."
        ::= { stnVcCrossConns 1 }
 
    stnVcCrossConnEntry OBJECT-TYPE
        SYNTAX          StnVcCrossConnEntry
        MAX-ACCESS      not-accessible
        STATUS          current
        DESCRIPTION     "Entry contains information about a particular 
                        VC cross connection."
        INDEX           { stnVcCrossConnLowIfIndex,
                          stnVcCrossConnLowVpi,
                          stnVcCrossConnLowVci,
                          stnVcCrossConnHighIfIndex,
                          stnVcCrossConnHighVpi,
                          stnVcCrossConnHighVci }
        ::= { stnVcCrossConnTable 1 }
 
    StnVcCrossConnEntry ::= 
        SEQUENCE {
                stnVcCrossConnLowIfIndex        InterfaceIndex,
                stnVcCrossConnLowVpi            Integer32,
                stnVcCrossConnLowVci            Integer32,
                stnVcCrossConnHighIfIndex       InterfaceIndex,
                stnVcCrossConnHighVpi           Integer32,
                stnVcCrossConnHighVci           Integer32,
                stnVcCrossConnLowAutoAssign     TruthValue,
                stnVcCrossConnHighAutoAssign    TruthValue,
                stnVcCrossConnOperStatus        VcCrossConnOperStatus
        }

    stnVcCrossConnLowIfIndex OBJECT-TYPE     
        SYNTAX          InterfaceIndex
        MAX-ACCESS      read-only
        STATUS          current
        DESCRIPTION     "The value of this object is equal to MIB II's 
                        ifIndex value of the ATM interface port for this 
                        VP cross-connect. The term low implies that this ATM 
                        interface has the numerically lower ifIndex."
        ::= { stnVcCrossConnEntry 1 }

    stnVcCrossConnLowVpi OBJECT-TYPE     
        SYNTAX          Integer32
        MAX-ACCESS      read-only
        STATUS          current
        DESCRIPTION     "The value of this object is equal to the VPI value 
                        at the ATM interface associated with the VP 
                        cross-connect that is identified by LowIfIndex. 
                        The VPI value cannot exceed the number supported by 
                        the atmInterfaceMaxVpiBits at the low ATM interface 
                        port."
        ::= { stnVcCrossConnEntry 2 }

    stnVcCrossConnLowVci OBJECT-TYPE     
        SYNTAX          Integer32
        MAX-ACCESS      read-only
        STATUS          current
        DESCRIPTION     "The value of this object is equal to the VCI value 
                        at the ATM interface associated with the VC 
                        cross-connect that is identified by LowIfIndex. 
                        The VCI value cannot exceed the number supported by 
                        the atmInterfaceMaxVciBits at the low ATM interface 
                        port."
        ::= { stnVcCrossConnEntry 3 }

    stnVcCrossConnHighIfIndex OBJECT-TYPE     
        SYNTAX          InterfaceIndex
        MAX-ACCESS      read-only
        STATUS          current
        DESCRIPTION     "The value of this object is equal to MIB II's 
                        ifIndex value of the ATM interface port for this VP 
                        cross-connect. The term low implies that this ATM 
                        interface has the numerically lower ifIndex."
        ::= { stnVcCrossConnEntry 4 }

    stnVcCrossConnHighVpi OBJECT-TYPE     
        SYNTAX          Integer32
        MAX-ACCESS      read-only
        STATUS          current
        DESCRIPTION     "The value of this object is equal to the VPI value 
                        at the ATM interface associated with the VP 
                        cross-connect that is identified by LowIfIndex. 
                        The VPI value cannot exceed the number supported by 
                        the atmInterfaceMaxVpiBits at the low ATM interface 
                        port."
        ::= { stnVcCrossConnEntry 5 }

    stnVcCrossConnHighVci OBJECT-TYPE     
        SYNTAX          Integer32
        MAX-ACCESS      read-only
        STATUS          current
        DESCRIPTION     "The value of this object is equal to the VCI value 
                        at the ATM interface associated with the VC 
                        cross-connect that is identified by LowIfIndex. 
                        The VCI value cannot exceed the number supported by 
                        the atmInterfaceMaxVciBits at the low ATM interface 
                        port. "
        ::= { stnVcCrossConnEntry 6 }

    stnVcCrossConnLowAutoAssign OBJECT-TYPE     
        SYNTAX          TruthValue
        MAX-ACCESS      read-only
        STATUS          current
        DESCRIPTION     "Controls low vpi/vci/ifIndex auto assignement to an
                        ECF. If set to true MSM will attempt to dynamically
                        auto assign the connection to an available ECF."
        DEFVAL          { false }
        ::= { stnVcCrossConnEntry 7 }

    stnVcCrossConnHighAutoAssign OBJECT-TYPE     
        SYNTAX          TruthValue
        MAX-ACCESS      read-only
        STATUS          current
        DESCRIPTION     "Controls high vpi/vci/ifIndex auto assignement to an
                        ECF. If set to true MSM will attempt to dynamically
                        auto assign the connection to an available ECF."
        DEFVAL          { false }
        ::= { stnVcCrossConnEntry 8 }

    stnVcCrossConnOperStatus OBJECT-TYPE     
        SYNTAX          VcCrossConnOperStatus
        MAX-ACCESS      read-only
        STATUS          current
        DESCRIPTION     "Operational status of the VC cross connection."
        ::= { stnVcCrossConnEntry 9 }


    --
    -- STN ATM Traffic Descriptor Table
    --

    stnTrafficDescrTable OBJECT-TYPE
        SYNTAX        SEQUENCE OF StnTrafficDescrEntry
        MAX-ACCESS    not-accessible
        STATUS        current
        DESCRIPTION   "A list of ATM traffic descriptor entries."
        ::= { stnAtmTrafficDescrs 1 }
 
    stnTrafficDescrEntry OBJECT-TYPE
        SYNTAX          StnTrafficDescrEntry
        MAX-ACCESS      not-accessible
        STATUS          current
        DESCRIPTION     "Entry contains information about a particular 
                        ATM traffic descriptor."
        INDEX           { stnTrafDescrIndex }
        ::= { stnTrafficDescrTable 1 }
 
    StnTrafficDescrEntry ::= 
        SEQUENCE {
                stnTrafDescrIndex            Integer32,
                stnTrafDescrName             OCTET STRING,
                stnTrafDescrType             INTEGER,
                stnTrafDescrParam1           Integer32,
                stnTrafDescrParam2           Integer32,
                stnTrafDescrParam3           Integer32,
                stnTrafDescrParam4           Integer32,
                stnTrafDescrParam5           Integer32,
                stnTrafDescrQosClass         INTEGER,
                stnTrafDescrServiceCategory  INTEGER,
                stnTrafDescrFrameDiscard     TruthValue,
                stnTrafDescrOperStatus       TrafficDescrOperStatus,
                stnTrafDescrCommittedRate    Integer32,
                stnTrafDescrMaximumRate      Integer32
        }

    stnTrafDescrIndex OBJECT-TYPE     
        SYNTAX          Integer32
        MAX-ACCESS      read-only
        STATUS          current
        DESCRIPTION     "The value of this object identifies the row
                         in the stnTrafficDescrTable."
        ::= { stnTrafficDescrEntry 1 }

    stnTrafDescrName OBJECT-TYPE     
        SYNTAX          OCTET STRING (SIZE(0..32))
        MAX-ACCESS      read-only
        STATUS          current
        DESCRIPTION     "Text name assigned to this traffic descriptor."
        ::= { stnTrafficDescrEntry 2 }

    stnTrafDescrType OBJECT-TYPE     
        SYNTAX          INTEGER {
                                no-td(1),               --
                                no-clp-no-scr(2),       --
                                clp-no-tag-no-scr(3),   --
                                clp-tagging-no-scr(4),  --
                                no-clp-scr(5),          --
                                clp-no-tag-scr(6),      --
                                clp-tagging-scr(7),     --
                                clp-no-tag-mcr(8),      --
                                clp-trans-no-scr(9),    --
                                clp-trans-scr(10),      --
                                no-clp-tag-no-scr(11)   --
                        }
        MAX-ACCESS      read-only
        STATUS          current
        DESCRIPTION     "The value of this object identifies the type of ATM 
                        traffic descriptor. The type may indicate no traffic 
                        descriptor or traffic descriptor with one or more 
                        parameters.  These parameters are specified as a 
                        parameter vector, in the corresponding instances of 
                        the objects: 
                                    atmTrafDescrParam1, 
                                    atmTrafDescrParam2, 
                                    atmTrafDescrParam3, 
                                    atmTrafDescrParam4, 
                                    atmTrafDescrParam5 

                        Type values are as follows: 
                                    no-td
                                    no-clp-no-scr  
                                    clp-no-ag-no-scr
                                    clp-agging-no-scr
                                    no-clp-scr         
                                    clp-no-tag-scr  
                                    clp-tagging-scr  
                                    clp-no-tag-mcr    
                                    clp-trans-no-scr
                                    clp-trans-scr    
                                    no-clp-tag-no-scr" 
        DEFVAL          { no-td }
        ::= { stnTrafficDescrEntry 3 }

    stnTrafDescrParam1 OBJECT-TYPE     
        SYNTAX          Integer32
        MAX-ACCESS      read-only
        STATUS          current
        DESCRIPTION     "The first parameter of the ATM traffic descriptor 
                        used according to the value of atmTrafDescrType."
        DEFVAL          { 0 }
        ::= { stnTrafficDescrEntry 4 }

    stnTrafDescrParam2 OBJECT-TYPE     
        SYNTAX          Integer32
        MAX-ACCESS      read-only
        STATUS          current
        DESCRIPTION     "The second parameter of the ATM traffic descriptor 
                        used according to the value of atmTrafDescrType."
        DEFVAL          { 0 }
        ::= { stnTrafficDescrEntry 5 }

    stnTrafDescrParam3 OBJECT-TYPE     
        SYNTAX          Integer32
        MAX-ACCESS      read-only
        STATUS          current
        DESCRIPTION     "The third parameter of the ATM traffic descriptor 
                        used according to the value of atmTrafDescrType."
        DEFVAL          { 0 }
        ::= { stnTrafficDescrEntry 6 }

    stnTrafDescrParam4 OBJECT-TYPE     
        SYNTAX          Integer32
        MAX-ACCESS      read-only
        STATUS          current
        DESCRIPTION     "The fourth parameter of the ATM traffic descriptor 
                        used according to the value of atmTrafDescrType."
        DEFVAL          { 0 }
        ::= { stnTrafficDescrEntry 7 }

    stnTrafDescrParam5 OBJECT-TYPE     
        SYNTAX          Integer32
        MAX-ACCESS      read-only
        STATUS          current
        DESCRIPTION     "The fifth parameter of the ATM traffic descriptor 
                        used according to the value of atmTrafDescrType."
        DEFVAL          { 0 }
        ::= { stnTrafficDescrEntry 8 }

    stnTrafDescrQosClass OBJECT-TYPE     
        SYNTAX          INTEGER {
                                best-effort(0),
                                service-class-a(1),
                                service-class-b(2),
                                service-class-c(3),
                                service-class-d(4)
                        }
        MAX-ACCESS      read-only
        STATUS          current
        DESCRIPTION     "The value of this object identifies the QoS Class.  
                        Four Service classes have been specified in the ATM 
                        Forum UNI Specification: 

                        Service Class A: Constant bit rate video and Circuit emulation.
                        Service Class B: Variable bit rate video/audio.
                        Service Class C: Connection-oriented data.
                        Service Class D: Connectionless data.

                        Four QoS classes numbered 1, 2, 3, and 4 have been 
                        specified with the aim to support service classes 
                        A, B, C, and D respectively.  An unspecified QoS 
                        Class numbered '0' is used for best effort traffic."
        DEFVAL          { best-effort }
        ::= { stnTrafficDescrEntry 9 }

    stnTrafDescrServiceCategory OBJECT-TYPE
        SYNTAX          INTEGER {
                                other(1),   --
                                cbr(2),     --
                                rt-vbr(3),  --
                                nrt-vbr(4), --
                                abr(5),     --
                                ubr(6)      --  "
                        }
        MAX-ACCESS      read-only
        STATUS          current
        DESCRIPTION     "The ATM service category.
                        Service categories are as follows:
                                other,
                                cbr,
                                rt-vbr,
                                nrt-vbr,
                                abr,
                                ubr"
        DEFVAL          { ubr }
        ::= { stnTrafficDescrEntry 10 }
 
    stnTrafDescrFrameDiscard OBJECT-TYPE     
        SYNTAX          TruthValue 
        MAX-ACCESS      read-only
        STATUS          current
        DESCRIPTION     "Whether the network should discard frames rather
                        than cells."
        DEFVAL          { false }
        ::= { stnTrafficDescrEntry 11 }

    stnTrafDescrOperStatus OBJECT-TYPE     
        SYNTAX          TrafficDescrOperStatus
        MAX-ACCESS      read-only
        STATUS          current
        DESCRIPTION     "Operational status of the traffic descriptor."
        ::= { stnTrafficDescrEntry 12 }

    stnTrafDescrCommittedRate OBJECT-TYPE     
        SYNTAX          Integer32
        MAX-ACCESS      read-only
        STATUS          current
        DESCRIPTION     "The traffic rate in bits per second that the network 
                         is committed to transmit for VCs using this transmit
                         traffic descriptor."
        DEFVAL          { 0 }
        ::= { stnTrafficDescrEntry 13 }

    stnTrafDescrMaximumRate OBJECT-TYPE     
        SYNTAX          Integer32
        MAX-ACCESS      read-only
        STATUS          current
        DESCRIPTION     "The maximum traffic rate in bits per second that the 
                         network will transmit for VCs using this transmit
                         traffic descriptor, if it differs from the committed 
                         rate."
        DEFVAL          { 0 }
        ::= { stnTrafficDescrEntry 14 }

    --
    -- STN ATM Trace IPS 
    --

    stnTraceIpsEnabled OBJECT-TYPE     
        SYNTAX          TruthValue 
        MAX-ACCESS      read-only
        STATUS          current
        DESCRIPTION     "Specifies whether IPS tracing is enabled."
        DEFVAL          { false }
        ::= { stnTraceIps 1 }

    stnTraceIpsSize OBJECT-TYPE     
        SYNTAX          Integer32
        MAX-ACCESS      read-only
        STATUS          current
        DESCRIPTION     "Specifies the maximum IPS trace buffer size multipled
                        by 1024. The IPS trace log file will wrap when it 
                        reaches the maximum. Default: 1000 x 1024 Lines"
        DEFVAL          { 1000 }
        ::= { stnTraceIps 2 }

    stnTraceIpsFile OBJECT-TYPE     
        SYNTAX          OCTET STRING (SIZE(0..128))
        MAX-ACCESS      read-only
        STATUS          current
        DESCRIPTION     "Specifies the IPS output path and file name. Changes
                        to the path or filename take effect when IPS tracing
                        is disabled and restarted (close file and open new)."
        ::= { stnTraceIps 3 }


    --
    -- STN ATM Trace PD
    --

    stnTracePdProblemEnabled OBJECT-TYPE     
        SYNTAX          TruthValue 
        MAX-ACCESS      read-only
        STATUS          current
        DESCRIPTION     "Specifies whether PD problem tracing is enabled."
        DEFVAL          { true }
        ::= { stnTracePd 1 }

    stnTracePdExceptionEnabled OBJECT-TYPE     
        SYNTAX          TruthValue
        MAX-ACCESS      read-only
        STATUS          current
        DESCRIPTION     "Specifies whether PD exception tracing is enabled."
        DEFVAL          { true }
        ::= { stnTracePd 2 }

    stnTracePdAuditEnabled OBJECT-TYPE     
        SYNTAX          TruthValue
        MAX-ACCESS      read-only
        STATUS          current
        DESCRIPTION     "Specifies whether PD audit tracing is enabled."
        DEFVAL          { true }
        ::= { stnTracePd 3 }

    stnTracePdDeveloperEnabled OBJECT-TYPE     
        SYNTAX          TruthValue
        MAX-ACCESS      read-only
        STATUS          current
        DESCRIPTION     "Specifies whether PD developer tracing is enabled."
        DEFVAL          { false }
        ::= { stnTracePd 4 }

    stnTracePdSize OBJECT-TYPE     
        SYNTAX          Integer32
        MAX-ACCESS      read-only
        STATUS          current
        DESCRIPTION     "Specifies the maximum PD trace buffer size multipled
                        by 1024. The PD trace log file will wrap when it 
                        reaches the maximum."
        DEFVAL          { 25 }
        ::= { stnTracePd 5 }

    stnTracePdFile OBJECT-TYPE     
        SYNTAX          OCTET STRING (SIZE(0..128))
        MAX-ACCESS      read-only
        STATUS          current
        DESCRIPTION     "Specifies the IPS output path and file name. Changes
                        to the path or filename take effect when IPS tracing
                        is disabled and restarted."
        ::= { stnTracePd 6 }


    --
    -- STN ATM Qos CLR (Cell Loss Ratio)
    --

    stnQosClass1CLR OBJECT-TYPE     
        SYNTAX          Integer32 
        MAX-ACCESS      read-only
        STATUS          current
        DESCRIPTION     "QoS Class 1 cell loss ratio."
        ::= { stnQosCLR 1 }

    stnQosClass2CLR OBJECT-TYPE     
        SYNTAX          Integer32 
        MAX-ACCESS      read-only
        STATUS          current
        DESCRIPTION     "QoS Class 2 cell loss ratio."
        ::= { stnQosCLR 2 }

    stnQosClass3CLR OBJECT-TYPE     
        SYNTAX          Integer32 
        MAX-ACCESS      read-only
        STATUS          current
        DESCRIPTION     "QoS Class 3 cell loss ratio."
        ::= { stnQosCLR 3 }

    stnQosClass4CLR OBJECT-TYPE     
        SYNTAX          Integer32 
        MAX-ACCESS      read-only
        STATUS          current
        DESCRIPTION     "QoS Class 4 cell loss ratio."
        ::= { stnQosCLR 4 }


    --
    -- STN ATM Qos CDV (Cell Delay Variation)
    --

    stnQosClass1CDV OBJECT-TYPE     
        SYNTAX          Integer32 
        MAX-ACCESS      read-only
        STATUS          current
        DESCRIPTION     "QoS Class 1 cell delay variation."
        ::= { stnQosCDV 1 }

    stnQosClass2CDV OBJECT-TYPE     
        SYNTAX          Integer32 
        MAX-ACCESS      read-only
        STATUS          current
        DESCRIPTION     "QoS Class 2 cell delay variation."
        ::= { stnQosCDV 2 }

    stnQosClass3CDV OBJECT-TYPE     
        SYNTAX          Integer32 
        MAX-ACCESS      read-only
        STATUS          current
        DESCRIPTION     "QoS Class 3 cell delay variation."
        ::= { stnQosCDV 3 }

    stnQosClass4CDV OBJECT-TYPE     
        SYNTAX          Integer32 
        MAX-ACCESS      read-only
        STATUS          current
        DESCRIPTION     "QoS Class 4 cell delay variation."
        ::= { stnQosCDV 4 }


    --
    -- STN ATM Qos CTD (Cell Transfer Delay)
    --

    stnQosClass1MaxCTD OBJECT-TYPE     
        SYNTAX          Integer32 
        MAX-ACCESS      read-only
        STATUS          current
        DESCRIPTION     "QoS Class 1 cell transfer delay."
        ::= { stnQosCTD 1 }

    stnQosClass2MaxCTD OBJECT-TYPE     
        SYNTAX          Integer32 
        MAX-ACCESS      read-only
        STATUS          current
        DESCRIPTION     "QoS Class 2 cell transfer delay."
        ::= { stnQosCTD 2 }

    stnQosClass3MaxCTD OBJECT-TYPE     
        SYNTAX          Integer32 
        MAX-ACCESS      read-only
        STATUS          current
        DESCRIPTION     "QoS Class 3 cell delay transfer."
        ::= { stnQosCTD 3 }

    stnQosClass4MaxCTD OBJECT-TYPE     
        SYNTAX          Integer32 
        MAX-ACCESS      read-only
        STATUS          current
        DESCRIPTION     "QoS Class 4 cell delay transfer."
        ::= { stnQosCTD 4 }


    --
    -- STN ATM Port Attribute Table
    --

    stnAtmPortAttrTable OBJECT-TYPE
        SYNTAX        SEQUENCE OF StnAtmPortAttrEntry
        MAX-ACCESS    not-accessible
        STATUS        current
        DESCRIPTION   "A list of ATM port attribute entries."
        ::= { stnAtmPortAttrs 1 }
 
    stnAtmPortAttrEntry OBJECT-TYPE
        SYNTAX          StnAtmPortAttrEntry
        MAX-ACCESS      not-accessible
        STATUS          current
        DESCRIPTION     "Entry contains information about a particular 
                        ATM port attribute entry."
        INDEX           { stnAtmPortIfIndex }
        ::= { stnAtmPortAttrTable 1 }
 
    StnAtmPortAttrEntry ::= 
        SEQUENCE {
                stnAtmPortIfIndex               InterfaceIndex,
                stnAtmPortIfType                Integer32,
                stnAtmPortIfState               INTEGER,
                stnAtmPortEnabled               TruthValue,
                stnAtmPortMinVccVpi             INTEGER,
                stnAtmPortMaxVccVpi             INTEGER,
                stnAtmPortMinVccVci             INTEGER,
                stnAtmPortMaxVccVci             INTEGER,
                stnAtmPortMinVpcVpi             INTEGER,
                stnAtmPortMaxVpcVpi             INTEGER,
                stnAtmPortMaxActivePaths        INTEGER,
                stnAtmPortMaxActiveChannels     INTEGER,
                stnAtmPortPVCAddress            NSAPAddress,
                stnAtmPortSVCAddress            NSAPAddress,
                stnAtmPortSigVpi                Integer32,
                stnAtmPortSigVci                Integer32,
                stnAtmPortSigEnabled            TruthValue,
                stnAtmPortIlmiVpi               Integer32,
                stnAtmPortIlmiVci               Integer32,
                stnAtmPortIlmiEnabled           TruthValue,
                stnAtmPortOamManagementEnabled  TruthValue,
                stnAtmPortOamXmtFrequency       Integer32,
                stnAtmPortOamRetryUpCount       Integer32,
                stnAtmPortOamRetryDownCount     Integer32,
                stnAtmPortOamRetryFrequency     Integer32,
                stnAtmPortOperStatus            AtmPortOperStatus
        }

    stnAtmPortIfIndex OBJECT-TYPE
        SYNTAX          InterfaceIndex
        MAX-ACCESS      read-only
        STATUS          current
        DESCRIPTION     "The interface index represents a connection point on
                         the switch fabric from a module or line card. It is
                         calculated based on the slot and port of the module."
        ::= { stnAtmPortAttrEntry 1 }

    stnAtmPortIfType OBJECT-TYPE     
        SYNTAX          Integer32
        MAX-ACCESS      read-only
        STATUS          current
        DESCRIPTION     "The interface type of the connection point to the
                         switch fabric. Values are:
                                sonet(1),
                                enet(2),
                                epif(3),
                                rim-enet(4)."
        ::= { stnAtmPortAttrEntry 2 }

    stnAtmPortIfState OBJECT-TYPE     
        SYNTAX          INTEGER (0..8)
        MAX-ACCESS      read-only
        STATUS          current
        DESCRIPTION     "The interface state of the connection point to
                         the switch fabric. Values are:
                                not-present(0),
                                detected(1),
                                configured(2),
                                up-non-redundant(3),
                                up-redundant(4),
                                down-non-redundant(5),
                                down-redundant(6),
                                failed(7),
                                initialized(8)"
        ::= { stnAtmPortAttrEntry 3 }

    stnAtmPortEnabled OBJECT-TYPE
        SYNTAX          TruthValue
        MAX-ACCESS      read-only
        STATUS          current
        DESCRIPTION     "Whether the ATM port is enabled."
        DEFVAL          { true }
        ::= { stnAtmPortAttrEntry 4 }

    stnAtmPortMinVccVpi OBJECT-TYPE     
        SYNTAX          INTEGER (0..255)
        MAX-ACCESS      read-only
        STATUS          current
        DESCRIPTION     "Minimum VPI used for Virtual Channel Circuits."
        DEFVAL          { 0 }
        ::= { stnAtmPortAttrEntry 5 }

    stnAtmPortMaxVccVpi OBJECT-TYPE     
        SYNTAX          INTEGER (0..255)
        MAX-ACCESS      read-only
        STATUS          current
        DESCRIPTION     "Maximum VPI used for Virtual Channel Circuits."
        DEFVAL          { 0 }
        ::= { stnAtmPortAttrEntry 6 }

    stnAtmPortMinVccVci OBJECT-TYPE     
        SYNTAX          INTEGER (32..65554)
        MAX-ACCESS      read-only
        STATUS          current
        DESCRIPTION     "Minimum VCI used for Virtual Channel Circuits.
                        To avoid clashes with the reserved ATM VCI values 
                        (such as 5 for signaling and any other reserved values
                        including Connection Manager VCs), the recommended 
                        value is 32. "
        DEFVAL          { 32 }
        ::= { stnAtmPortAttrEntry 7 }

    stnAtmPortMaxVccVci OBJECT-TYPE     
        SYNTAX          INTEGER (32..65554)
        MAX-ACCESS      read-only
        STATUS          current
        DESCRIPTION     "Maximum VCI used for Virtual Channel Circuits."
        DEFVAL          { 4095 }
        ::= { stnAtmPortAttrEntry 8 }

    stnAtmPortMinVpcVpi OBJECT-TYPE     
        SYNTAX          INTEGER (1..255)
        MAX-ACCESS      read-only
        STATUS          current
        DESCRIPTION     "Minimum VPI used for Virtual Path Circuits. To avoid 
                        clashes with the reserved ATM VCCs values (such as 5 
                        for signaling and any other reserved values including 
                        Connection Manager VCs), the recommended value is 1."
        DEFVAL          { 1 }
        ::= { stnAtmPortAttrEntry 9 }

    stnAtmPortMaxVpcVpi OBJECT-TYPE     
        SYNTAX          INTEGER (1..255)
        MAX-ACCESS      read-only
        STATUS          current
        DESCRIPTION     "Maximum VCI used for Virtual Channel Circuits."
        DEFVAL          { 255 }
        ::= { stnAtmPortAttrEntry 10 }
 
    stnAtmPortMaxActivePaths OBJECT-TYPE     
        SYNTAX          INTEGER (0..255)
        MAX-ACCESS      read-only
        STATUS          current
        DESCRIPTION     "The maximum number of active paths that can be active
                        at any time on this port."
        DEFVAL          { 127 }
        ::= { stnAtmPortAttrEntry 11 }

    stnAtmPortMaxActiveChannels OBJECT-TYPE     
        SYNTAX          INTEGER (0..65554)
        MAX-ACCESS      read-only
        STATUS          current
        DESCRIPTION     "The maximum number of virtual channels that can be 
                        active at any time on this port."
        DEFVAL          { 4095 }
        ::= { stnAtmPortAttrEntry 12 }

    stnAtmPortPVCAddress OBJECT-TYPE
        SYNTAX          NSAPAddress
        MAX-ACCESS      read-only
        STATUS          current
        DESCRIPTION     "The default configured PVC address information
                        (20-byte NSAP address)."
        ::= { stnAtmPortAttrEntry 13 }

    stnAtmPortSVCAddress OBJECT-TYPE
        SYNTAX          NSAPAddress
        MAX-ACCESS      read-only
        STATUS          current
        DESCRIPTION     "The default configured SVC address information
                        (20-byte NSAP address)."
        ::= { stnAtmPortAttrEntry 14 }

    stnAtmPortSigVpi OBJECT-TYPE     
        SYNTAX          Integer32
        MAX-ACCESS      read-only
        STATUS          current
        DESCRIPTION     "The VPI used for the signaling channel."
        DEFVAL          { 0 }
        ::= { stnAtmPortAttrEntry 15 }

    stnAtmPortSigVci OBJECT-TYPE     
        SYNTAX          Integer32
        MAX-ACCESS      read-only
        STATUS          current
        DESCRIPTION     "The VCI used for the signaling channel."
        DEFVAL          { 5 }
        ::= { stnAtmPortAttrEntry 16 }

    stnAtmPortSigEnabled OBJECT-TYPE     
        SYNTAX          TruthValue
        MAX-ACCESS      read-only
        STATUS          current
        DESCRIPTION     "Indicates if port will have a signaling stack."
        DEFVAL          { false }
        ::= { stnAtmPortAttrEntry 17 }

    stnAtmPortIlmiVpi OBJECT-TYPE     
        SYNTAX          Integer32
        MAX-ACCESS      read-only
        STATUS          current
        DESCRIPTION     "The VPI used for ILMI channel."
        DEFVAL          { 0 }
        ::= { stnAtmPortAttrEntry 18 }

    stnAtmPortIlmiVci OBJECT-TYPE     
        SYNTAX          Integer32
        MAX-ACCESS      read-only
        STATUS          current
        DESCRIPTION     "The VCI used for ILMI channel."
        DEFVAL          { 16 }
        ::= { stnAtmPortAttrEntry 19 }
 
    stnAtmPortIlmiEnabled OBJECT-TYPE     
        SYNTAX          TruthValue
        MAX-ACCESS      read-only
        STATUS          current
        DESCRIPTION     "Indicates if port will use ILMI."
        DEFVAL          { false }
        ::= { stnAtmPortAttrEntry 20 }

    stnAtmPortOamManagementEnabled OBJECT-TYPE     
        SYNTAX          TruthValue
        MAX-ACCESS      read-only
        STATUS          current
        DESCRIPTION     "Indicates if port is using OAM Management Procedures."
        DEFVAL          { false }
        ::= { stnAtmPortAttrEntry 21 }

    stnAtmPortOamXmtFrequency OBJECT-TYPE     
        SYNTAX          Integer32
        MAX-ACCESS      read-only
        STATUS          current
        DESCRIPTION     "Indicates Frequency of OAM Transmit Cells."
        ::= { stnAtmPortAttrEntry 22 }

    stnAtmPortOamRetryUpCount OBJECT-TYPE     
        SYNTAX          Integer32
        MAX-ACCESS      read-only
        STATUS          current
        DESCRIPTION     "Indicates OAM Cell Retry Up Count value."
        ::= { stnAtmPortAttrEntry 23 }

    stnAtmPortOamRetryDownCount OBJECT-TYPE     
        SYNTAX          Integer32
        MAX-ACCESS      read-only
        STATUS          current
        DESCRIPTION     "Indicates OAM Cell Retry Down Count value."
        ::= { stnAtmPortAttrEntry 24 }

    stnAtmPortOamRetryFrequency OBJECT-TYPE     
        SYNTAX          Integer32
        MAX-ACCESS      read-only
        STATUS          current
        DESCRIPTION     "Indicates OAM Retry Frequency value."
        ::= { stnAtmPortAttrEntry 25 }

    stnAtmPortOperStatus OBJECT-TYPE     
        SYNTAX          AtmPortOperStatus
        MAX-ACCESS      read-only
        STATUS          current
        DESCRIPTION     "Operational status of the Port."
        ::= { stnAtmPortAttrEntry 26 }

    --
    -- STN ATM Port ILMI Table
    --
    stnAtmPortIlmiTable OBJECT-TYPE
        SYNTAX        SEQUENCE OF StnAtmPortIlmiEntry
        MAX-ACCESS    not-accessible
        STATUS        current
        DESCRIPTION   "A list of ATM ILMI Port entries."
        ::= { stnAtmPortIlmi 1 }
 
    stnAtmPortIlmiEntry OBJECT-TYPE
        SYNTAX          StnAtmPortIlmiEntry
        MAX-ACCESS      not-accessible
        STATUS          current
        DESCRIPTION     "Entry contains information about a particular 
                        ATM Port ILMI entry."
        INDEX           { stnAtmPortIlmiIfIndex }
        ::= { stnAtmPortIlmiTable 1 }
 
    StnAtmPortIlmiEntry ::= 
        SEQUENCE {
                stnAtmPortIlmiIfIndex               InterfaceIndex,
                stnAtmPortIlmiVersion               INTEGER,
                stnAtmPortIlmiNetworkOrientation    INTEGER,
                stnAtmPortIlmiAutoNegotiate         TruthValue,
                stnAtmPortIlmiPollInterval          Integer32,
                stnAtmPortIlmiCheckConnectionInt    Integer32,
                stnAtmPortIlmiInactivityFactor      Integer32,
                stnAtmPortIlmiLocalConn             INTEGER,
                stnAtmPortIlmiAdminStatus           BITS,
                stnAtmPortIlmiEnterprise            OBJECT IDENTIFIER,
                stnAtmPortIlmiLocalOid              OBJECT IDENTIFIER,
                stnAtmPortIlmiNetPrefix             OCTET STRING,
                stnAtmPortIlmiPrefixLen             Integer32
        }

    stnAtmPortIlmiIfIndex OBJECT-TYPE
        SYNTAX          InterfaceIndex
        MAX-ACCESS      read-only
        STATUS          current
        DESCRIPTION     "The interface index represents a connection point on
                         the switch fabric from a module or line card. It is
                         calculated based on the slot and port of the module."
        ::= { stnAtmPortIlmiEntry 1 }

    stnAtmPortIlmiVersion OBJECT-TYPE     
        SYNTAX          INTEGER {
                                uni-3-dot-0(1),
                                uni-3-dot-1(2),
                                uni-4-dot-0(3),
                                iisp-3-dot-1(4)
                        }
        MAX-ACCESS      read-only
        STATUS          current
        DESCRIPTION     "Specifies the signaling stack protocol type to be 
                        used on this port. Valid options are: 
                                uni-3-dot-0
                                uni-3-dot-1
                                uni-4-dot-0 
                                iisp-3-dot-1"
        DEFVAL          { uni-3-dot-1 }
        ::= { stnAtmPortIlmiEntry 2 }

    stnAtmPortIlmiNetworkOrientation OBJECT-TYPE     
        SYNTAX          INTEGER {
                                user(1),
                                network(2)
                        }
        MAX-ACCESS      read-only
        STATUS          current
        DESCRIPTION     "Specifies the ATM device type. Valid options are: 
                                user,
                                network"
        DEFVAL          { network }       
        ::= { stnAtmPortIlmiEntry 3 }

    stnAtmPortIlmiAutoNegotiate OBJECT-TYPE     
        SYNTAX          TruthValue
        MAX-ACCESS      read-only 
        STATUS          current
        DESCRIPTION     "Indicates ILMI auto negotiation mode"
        DEFVAL          { false }          
        ::= { stnAtmPortIlmiEntry 4 }

    stnAtmPortIlmiPollInterval OBJECT-TYPE     
        SYNTAX          Integer32
        MAX-ACCESS      read-only 
        STATUS          current
        DESCRIPTION     "ILMI connection poll interval (S) in seconds. When 
                        DC-ILMI is transmitting SNMP Get messages during the 
                        attempt to establish connectivity with the remote ILMI
                        component, this parameter determines the time in 
                        seconds between transmissions. The default value is
                        from the ATM Forum ILMI Specification Version 4.0:
                        ILMI Connectivity Procedures (section 8.3.1)."
        DEFVAL          { 1 }      
        ::= { stnAtmPortIlmiEntry 5 }

    stnAtmPortIlmiCheckConnectionInt OBJECT-TYPE     
        SYNTAX          Integer32
        MAX-ACCESS      read-only 
        STATUS          current
        DESCRIPTION     "ILMI check connection poll interval (T) in seconds. 
                        If connectivity checking is enabled (as spec by the 
                        value connect in the Admin_Status parameter below),
                        this parameter specifies the time in seconds between 
                        successive transmissions of MIB Get msgs for the 
                        purpose of detecting loss of ILMI connectivity. If
                        connectivity checking is not enabled, this parameter
                        must be set to zero. The default value is from the ATM
                        Forum ILMI Specification Version 4.0: ILMI 
                        Connectivity Procedures (section 8.3.1)."
        DEFVAL          { 5 }      
        ::= { stnAtmPortIlmiEntry 6 }

    stnAtmPortIlmiInactivityFactor OBJECT-TYPE     
        SYNTAX          Integer32
        MAX-ACCESS      read-only 
        STATUS          current
        DESCRIPTION     "ILMI inactivity factor (K). The number of 
                        consecutive polls for which no response is received 
                        from the remote ILMI component before ILMI 
                        connectivity is assumed to be lost. The dflt value is 
                        from the ATM Forum ILMI Specification Version 4.0: 
                        ILMI Connectivity Procedures (section 8.3.1)."
        DEFVAL          { 4 }      
        ::= { stnAtmPortIlmiEntry 7 }

    stnAtmPortIlmiLocalConn OBJECT-TYPE     
        SYNTAX          INTEGER {
                                other(1),
                                public(2),  
                                private(3) 
                        }
        MAX-ACCESS      read-only 
        STATUS          current
        DESCRIPTION     "Specifies whether the local end of the ILMI 
                        connection is advertised as a 'public' or 'private' 
                        ILMI device. Values are:
                                other,
                                public,  
                                private"
        DEFVAL          { private }    
        ::= { stnAtmPortIlmiEntry 8 }

    stnAtmPortIlmiAdminStatus OBJECT-TYPE     
        SYNTAX          BITS {
                                std-ilmi(0),
                                addr-reg(1),  
                                connect(2) 
                        }
        MAX-ACCESS      read-only 
        STATUS          current
        DESCRIPTION     "Specifies which functions of DC-ILMI are enabled. The
                        value std-ilmi must be specified; this value may be 
                        combined (using a bitwise OR) with one or more of the 
                        following values:  
                        std-ilmi - Standard ILMI functions are enabled.
                        addr-reg - Address registration is enabled.       
                        connect - Connectivity chcking is enabled (DC-ILMI 
                            periodically sends a MIB Get request for the 
                            remote system's System ID, to ensure that it can 
                            still send and rcvd data on the ILMI connection).

                        Default: (std-ilmi | addr-reg | connect)"
        ::= { stnAtmPortIlmiEntry 9 }

    stnAtmPortIlmiEnterprise OBJECT-TYPE    
        SYNTAX          OBJECT IDENTIFIER
        MAX-ACCESS      read-only 
        STATUS          current
        DESCRIPTION     "Enterprise Object ID that DC-ILMI will use in 
                        building SNMP traps (or other generic MIB traps). This
                        parameter can be used to identify the originator of
                        the trap.
                        
                        The Object ID is specified as an array of unsigned
                        long vals, as follows: 
                                                                     
                        The first entry in the array is the length of the
                        array (the num of unsigned long values it contains,
                        including the len value).  
                                                                     
                        The second entry in the array is an identifier
                        specifying the Family type of the Object ID. This reps
                        a prefix Object ID; the MIB Sub-Agent is responsible
                        for matching this id with the dotted-decimal notation
                        for this prefix.                    
                                                                     
                        The remainder of the array gives the index part of the
                        Object ID (the dotted-decimal notation from the end of
                        the Family), with 1 unsigned long for each decimal
                        number in this notation."
        ::= { stnAtmPortIlmiEntry 10 }

    stnAtmPortIlmiLocalOid OBJECT-TYPE     
        SYNTAX          OBJECT IDENTIFIER
        MAX-ACCESS      read-only 
        STATUS          current
        DESCRIPTION     "Object ID identifying the local machine - the first
                         4 octets indicate the length of the object id.  For
                         example, the null object id (0.0), which should be
                         used if no object id is specified,  is encoded as
                         3, 0, 0."
        ::= { stnAtmPortIlmiEntry 11 }

    stnAtmPortIlmiNetPrefix OBJECT-TYPE     
        SYNTAX          OCTET STRING (SIZE(0..13))
        MAX-ACCESS      read-only 
        STATUS          current
        DESCRIPTION     "Default network prefix. If the prefix length is 
                        non-zero, ILMI creates an entry in the ILMI NetPrefix 
                        Table for this prefix; otherwise the Net_Prefix 
                        parameter is not used."
        ::= { stnAtmPortIlmiEntry 12 }

    stnAtmPortIlmiPrefixLen OBJECT-TYPE     
        SYNTAX          Integer32
        MAX-ACCESS      read-only 
        STATUS          current
        DESCRIPTION     "The length of the default network prefix"
        ::= { stnAtmPortIlmiEntry 13 }


    --
    -- STN ATM Port Signaling Table
    --
    stnAtmPortSigTable OBJECT-TYPE
        SYNTAX        SEQUENCE OF StnAtmPortSigEntry
        MAX-ACCESS    not-accessible
        STATUS        current
        DESCRIPTION   "A list of ATM port signal entries."
        ::= { stnAtmPortSigs 1 }
 
    stnAtmPortSigEntry OBJECT-TYPE
        SYNTAX          StnAtmPortSigEntry
        MAX-ACCESS      not-accessible
        STATUS          current
        DESCRIPTION     "Entry contains information about a particular 
                        ATM port signal entry."
        INDEX           { stnAtmPortSigIfIndex }
        ::= { stnAtmPortSigTable 1 }
 
    StnAtmPortSigEntry ::= 
        SEQUENCE {
                stnAtmPortSigIfIndex                    InterfaceIndex,
                stnAtmPortSigVersion                    INTEGER,
                stnAtmPortSigNetworkOrientation         INTEGER,
                stnAtmPortSigAssignVpiVci               TruthValue,
                stnAtmPortSigVpSigType                  INTEGER,
                stnAtmPortSigParseMode                  INTEGER,
                stnAtmPortSigPrefCarrierPresent         TruthValue,
                stnAtmPortSigPrefCarrier                TruthValue
        }

    stnAtmPortSigIfIndex OBJECT-TYPE
        SYNTAX          InterfaceIndex
        MAX-ACCESS      read-only
        STATUS          current
        DESCRIPTION     "The interface index represents a connection point on
                         the switch fabric from a module or line card. It is
                         calculated based on the slot and port of the module."
        ::= { stnAtmPortSigEntry 1 }

    stnAtmPortSigVersion OBJECT-TYPE
        SYNTAX          INTEGER {
                            uni-3-dot-0(1),
                            uni-3-dot-1(2),
                            iisp-3-dot-1(3),
                            pnni-1-dot-0(4)
                        }
        MAX-ACCESS      read-only
        STATUS          current
        DESCRIPTION     "Specifies the signaling stack protocol type to be 
                        used on this port. Valid options are:
                            UNI 3.0, 
                            UNI 3.1,
                            IISP 3.1,
                            PNNI 1.0"
        ::= { stnAtmPortSigEntry 2 }

    stnAtmPortSigNetworkOrientation OBJECT-TYPE
        SYNTAX          INTEGER {
                            user(1),
                            network(2)
                        }
        MAX-ACCESS      read-only
        STATUS          current
        DESCRIPTION     "Indicates whether the ATM device is of the user or
                        network type. Valid values are:
                            user,
                            network"
        DEFVAL          { network }
        ::= { stnAtmPortSigEntry 3 }

    stnAtmPortSigAssignVpiVci OBJECT-TYPE
        SYNTAX          TruthValue
        MAX-ACCESS      not-accessible
        STATUS          current
        DESCRIPTION     "Specifies whether VPI/VCI assignment is the 
                        responsibility of the local signaling stack or of its
                        partner stack. This parameter is used only for UNI 
                        4.0. Values are: 
                            true  - The local signaling stack is responsible
                                    for assigning VPIs/VCIs. 
                            false - The parent-signaling stack is responsible
                                    for assigning VPIs/VCIs."
        DEFVAL          { true }
        ::= { stnAtmPortSigEntry 4 }

    stnAtmPortSigVpSigType OBJECT-TYPE
        SYNTAX          INTEGER {
                            associated-signaling(1),
                            explicit-vpci(2)
                        }
        MAX-ACCESS      read-only
        STATUS          current
        DESCRIPTION     "Specifies whether this signaling stack performs VP 
                        associated  signaling: Valid options are: 
                            associated-signaling 
                            explicit-vpci"
        DEFVAL          { explicit-vpci }
        ::= { stnAtmPortSigEntry 5 }

    stnAtmPortSigParseMode OBJECT-TYPE
        SYNTAX          INTEGER {
                            normal(1),
                            strict(2)
                        }
        MAX-ACCESS      read-only
        STATUS          current
        DESCRIPTION     "Specifies whether the message parser component of
                        Sig should perform validity checking on the contents 
                        of received IEs. This element resides in the CCS MIB
                        to allow software config of this behavior for 
                        compliance testing. Values are:   

                        normal - The parser checks the contents 
                                of the IEs the Sig uses and ensures that they
                                are valid. For other IEs, it checks only the
                                IE type and length and does not parse the 
                                contents.      
                        strict - The parser checks the contents of
                                addit IEs as well as those used by Signaling
                                and also checks for incorrect repetition of 
                                these add it IEs. Errors are handled in the
                                same way as for the IEs used by sig (by 
                                sending a status message in UNI 3.1 or by 
                                following the IE instruction indicator in 
                                UNI 4.0)."
        DEFVAL          { normal }
        ::= { stnAtmPortSigEntry 6 }

    stnAtmPortSigPrefCarrierPresent OBJECT-TYPE
        SYNTAX          TruthValue
        MAX-ACCESS      read-only
        STATUS          current
        DESCRIPTION     "Specifies whether a default prefrd carrier
                        (transit network) is defined. Valid options are: 
                    
                            true -  the Default_Network_Id below defines 
                                    which carr is the preferred carrier. 
                            false - no default preferred carrier is defined."
        DEFVAL          { false }
        ::= { stnAtmPortSigEntry 7 }

    stnAtmPortSigPrefCarrier OBJECT-TYPE
        SYNTAX          TruthValue
        MAX-ACCESS      read-only
        STATUS          current
        DESCRIPTION     "Specifies the default preferred carrier. If 
                        stnAtmPortIlmiPrefCarrierPresent is set to false, 
                        this element is not used."
        ::= { stnAtmPortSigEntry 8 }


    --
    -- STN ATM Port Signaling Timer Duration Table
    --
    --
    -- Signaling Timer Durations values milliseconds. For more info 
    -- on the usage of these timers, refer to the appropriate UNI/NNI 
    -- specification. 
    -- 
    stnAtmPortSigDurationTable OBJECT-TYPE
        SYNTAX        SEQUENCE OF StnAtmPortSigDurationEntry
        MAX-ACCESS    not-accessible
        STATUS        current
        DESCRIPTION   "A list of ATM Port Signaling Duration entries."
        ::= { stnAtmPortSigDurations 1 }
 
    stnAtmPortSigDurationEntry OBJECT-TYPE
        SYNTAX          StnAtmPortSigDurationEntry
        MAX-ACCESS      not-accessible
        STATUS          current
        DESCRIPTION     "Entry contains information about a particular 
                        ATM Port Signaling Duration entry."
        INDEX           { stnAtmPortSigDurIfIndex }
        ::= { stnAtmPortSigDurationTable 1 }
 
    StnAtmPortSigDurationEntry ::= 
        SEQUENCE {
                stnAtmPortSigDurIfIndex         InterfaceIndex,
                stnAtmPortSigT301Duration       Integer32,
                stnAtmPortSigT303Duration       Integer32,
                stnAtmPortSigT306Duration       Integer32,
                stnAtmPortSigT308Duration       Integer32,
                stnAtmPortSigT309Duration       Integer32,
                stnAtmPortSigT310Duration       Integer32,
                stnAtmPortSigT313Duration       Integer32,
                stnAtmPortSigT316Duration       Integer32,
                stnAtmPortSigT317Duration       Integer32,
                stnAtmPortSigT322Duration       Integer32,
                stnAtmPortSigT331Duration       Integer32,
                stnAtmPortSigT333Duration       Integer32,
                stnAtmPortSigT397Duration       Integer32,
                stnAtmPortSigT398Duration       Integer32,
                stnAtmPortSigT399Duration       Integer32,
                stnAtmPortSigSaalRetryDuration  Integer32
        }

    stnAtmPortSigDurIfIndex OBJECT-TYPE
        SYNTAX          InterfaceIndex
        MAX-ACCESS      read-only
        STATUS          current
        DESCRIPTION     "The interface index represents a connection point on
                         the switch fabric from a module or line card. It is
                         calculated based on the slot and port of the module."
        ::= { stnAtmPortSigDurationEntry 1 }

    stnAtmPortSigT301Duration OBJECT-TYPE     
        SYNTAX          Integer32
        MAX-ACCESS      read-only
        STATUS          current
        DESCRIPTION     "T301 timer. See ITU-T Q.2931 B-ISDN DSS2 User-Network
                         Interface (UNI) Layer 3 Specification for Basic
                         Call/Connection Control"
        DEFVAL          { 180000 }
        ::= { stnAtmPortSigDurationEntry 2 }

    stnAtmPortSigT303Duration OBJECT-TYPE     
        SYNTAX          Integer32
        MAX-ACCESS      read-only
        STATUS          current
        DESCRIPTION     "T303 timer. See ITU-T Q.2931 B-ISDN DSS2 User-Network
                         Interface (UNI) Layer 3 Specification for Basic
                         Call/Connection Control"
        DEFVAL          { 4000 }
        ::= { stnAtmPortSigDurationEntry 3 }

    stnAtmPortSigT306Duration OBJECT-TYPE     
        SYNTAX          Integer32
        MAX-ACCESS      read-only
        STATUS          current
        DESCRIPTION     "T306 timer. See ITU-T Q.2931 B-ISDN DSS2 User-Network
                         Interface (UNI) Layer 3 Specification for Basic
                         Call/Connection Control"
        DEFVAL          { 30000 }
        ::= { stnAtmPortSigDurationEntry 4 }

    stnAtmPortSigT308Duration OBJECT-TYPE     
        SYNTAX          Integer32
        MAX-ACCESS      read-only
        STATUS          current
        DESCRIPTION     "T308 timer. See ITU-T Q.2931 B-ISDN DSS2 User-Network
                         Intrface (UNI) Layer 3 Specification for Basic
                         Call/Connection Control"
        DEFVAL          { 30000 }
        ::= { stnAtmPortSigDurationEntry 5 }

    stnAtmPortSigT309Duration OBJECT-TYPE     
        SYNTAX          Integer32
        MAX-ACCESS      read-only
        STATUS          current
        DESCRIPTION     "T309 timer. See ITU-T Q.2931 B-ISDN DSS2 User-Network
                         Interface (UNI) Layer 3 Specification for Basic
                         Call/Connection Control"
        DEFVAL          { 10000 }
        ::= { stnAtmPortSigDurationEntry 6 }

    stnAtmPortSigT310Duration OBJECT-TYPE     
        SYNTAX          Integer32
        MAX-ACCESS      read-only
        STATUS          current
        DESCRIPTION     "T310 timer. See ITU-T Q.2931 B-ISDN DSS2 User-Network
                         Interface (UNI) Layer 3 Specification for Basic
                         Call/Connection Control"
        DEFVAL          { 10000 }
        ::= { stnAtmPortSigDurationEntry 7 }

    stnAtmPortSigT313Duration OBJECT-TYPE     
        SYNTAX          Integer32
        MAX-ACCESS      read-only
        STATUS          current
        DESCRIPTION     "T313 timer. See ITU-T Q.2931 B-ISDN DSS2 User-Network
                         Interface (UNI) Layer 3 Specification for Basic
                         Call/Connection Control"
        DEFVAL          { 30000 }
        ::= { stnAtmPortSigDurationEntry 8 }

    stnAtmPortSigT316Duration OBJECT-TYPE     
        SYNTAX          Integer32
        MAX-ACCESS      read-only
        STATUS          current
        DESCRIPTION     "T316 timer. See ITU-T Q.2931 B-ISDN DSS2 User-Network
                         Interface (UNI) Layer 3 Specification for Basic
                         Call/Connection Control"
        DEFVAL          { 120000 }
        ::= { stnAtmPortSigDurationEntry 9 }

    stnAtmPortSigT317Duration OBJECT-TYPE     
        SYNTAX          Integer32
        MAX-ACCESS      read-only
        STATUS          current
        DESCRIPTION     "T317 timer. See ITU-T Q.2931 B-ISDN DSS2 User-Network
                         Interface (UNI) Layer 3 Specification for Basic
                         Call/Connection Control"
        DEFVAL          { 60000 }
        ::= { stnAtmPortSigDurationEntry 10 }

    stnAtmPortSigT322Duration OBJECT-TYPE     
        SYNTAX          Integer32
        MAX-ACCESS      read-only
        STATUS          current
        DESCRIPTION     "T322 timer. See ITU-T Q.2931 B-ISDN DSS2 User-Network
                         Interface (UNI) Layer 3 Specification for Basic
                         Call/Connection Control"
        DEFVAL          { 4000 }
        ::= { stnAtmPortSigDurationEntry 11 }

    stnAtmPortSigT331Duration OBJECT-TYPE     
        SYNTAX          Integer32
        MAX-ACCESS      read-only
        STATUS          current
        DESCRIPTION     "T331 timer. See ITU-T Q.2931 B-ISDN DSS2 User-Network
                         Interface (UNI) Layer 3 Specification for Basic
                         Call/Connection Control"
        DEFVAL          { 60000 }
        ::= { stnAtmPortSigDurationEntry 12 }

    stnAtmPortSigT333Duration OBJECT-TYPE     
        SYNTAX          Integer32
        MAX-ACCESS      read-only
        STATUS          current
        DESCRIPTION     "T333 timer. See ITU-T Q.2931 B-ISDN DSS2 User-Network
                         Interface (UNI) Layer 3 Specification for Basic
                         Call/Connection Control"
        DEFVAL          { 10000 }
        ::= { stnAtmPortSigDurationEntry 13 }

    stnAtmPortSigT397Duration OBJECT-TYPE     
        SYNTAX          Integer32
        MAX-ACCESS      read-only
        STATUS          current
        DESCRIPTION     "T397 timer. See ITU-T Q.2931 B-ISDN DSS2 User-Network
                         Interface (UNI) Layer 3 Specification for Basic
                         Call/Connection Control"
        DEFVAL          { 180000 }
        ::= { stnAtmPortSigDurationEntry 14 }

    stnAtmPortSigT398Duration OBJECT-TYPE     
        SYNTAX          Integer32
        MAX-ACCESS      read-only
        STATUS          current
        DESCRIPTION     "T398 timer. See ITU-T Q.2931 B-ISDN DSS2 User-Network
                         Interface (UNI) Layer 3 Specification for Basic
                         Call/Connection Control"
        DEFVAL          { 4000 }
        ::= { stnAtmPortSigDurationEntry 15 }

    stnAtmPortSigT399Duration OBJECT-TYPE     
        SYNTAX          Integer32
        MAX-ACCESS      read-only
        STATUS          current
        DESCRIPTION     "T399 timer. See ITU-T Q.2931 B-ISDN DSS2 User-Network
                         Interface (UNI) Layer 3 Specification for Basic
                         Call/Connection Control"
        DEFVAL          { 14000 }
        ::= { stnAtmPortSigDurationEntry 16 }

    stnAtmPortSigSaalRetryDuration OBJECT-TYPE     
        SYNTAX          Integer32
        MAX-ACCESS      read-only
        STATUS          current
        DESCRIPTION     "SAAL retry duration. See ITU-T Q.2931 B-ISDN DSS2
                         User-Network Interface (UNI) Layer 3 Specification
                         for Basic Call/Connection Control"
        DEFVAL          { 10000 }
        ::= { stnAtmPortSigDurationEntry 17 }


    --
    -- STN ATM Port Signaling Timer Retry Table
    --
    --
    stnAtmPortSigRetryTable OBJECT-TYPE
        SYNTAX        SEQUENCE OF StnAtmPortSigRetryEntry
        MAX-ACCESS    not-accessible
        STATUS        current
        DESCRIPTION   "A list of ATM Port Signaling retry entries."
        ::= { stnAtmPortSigRetries 1 }
 
    stnAtmPortSigRetryEntry OBJECT-TYPE
        SYNTAX          StnAtmPortSigRetryEntry
        MAX-ACCESS      not-accessible
        STATUS          current
        DESCRIPTION     "Entry contains information about a ITU-T Q.2931
                         timer retry counters."
        INDEX           { stnAtmPortSigRetryIfIndex }
        ::= { stnAtmPortSigRetryTable 1 }
 
    StnAtmPortSigRetryEntry ::= 
        SEQUENCE {
                stnAtmPortSigRetryIfIndex       InterfaceIndex,
                stnAtmPortSigT303Retries        Integer32,
                stnAtmPortSigT308Retries        Integer32,
                stnAtmPortSigT316Retries        Integer32,
                stnAtmPortSigT322Retries        Integer32,
                stnAtmPortSigT331Retries        Integer32
        }

    stnAtmPortSigRetryIfIndex OBJECT-TYPE
        SYNTAX          InterfaceIndex
        MAX-ACCESS      read-only
        STATUS          current
        DESCRIPTION     "The interface index represents a connection point on
                         the switch fabric from a module or line card. It is
                         calculated based on the slot and port of the module."
        ::= { stnAtmPortSigRetryEntry 1 }

    stnAtmPortSigT303Retries OBJECT-TYPE     
        SYNTAX          Integer32
        MAX-ACCESS      read-only
        STATUS          current
        DESCRIPTION     "The number of ATM Port Signaling T303 retries."
        DEFVAL          { 1 }
        ::= { stnAtmPortSigRetryEntry 2 }

    stnAtmPortSigT308Retries OBJECT-TYPE     
        SYNTAX          Integer32
        MAX-ACCESS      read-only
        STATUS          current
        DESCRIPTION     "The number of ATM Port Signaling T308 retries."
        DEFVAL          { 1 }
        ::= { stnAtmPortSigRetryEntry 3 }

    stnAtmPortSigT316Retries OBJECT-TYPE     
        SYNTAX          Integer32
        MAX-ACCESS      read-only
        STATUS          current
        DESCRIPTION     "The number of ATM Port Signaling T316 retries."
        DEFVAL          { 1 }
        ::= { stnAtmPortSigRetryEntry 4 }

    stnAtmPortSigT322Retries OBJECT-TYPE     
        SYNTAX          Integer32
        MAX-ACCESS      read-only
        STATUS          current
        DESCRIPTION     "The number of ATM Port Signaling T322 retries."
        DEFVAL          { 1 }
        ::= { stnAtmPortSigRetryEntry 5 }

    stnAtmPortSigT331Retries OBJECT-TYPE     
        SYNTAX          Integer32
        MAX-ACCESS      read-only
        STATUS          current
        DESCRIPTION     "The number of ATM Port Signaling T331 retries."
        DEFVAL          { 1 }
        ::= { stnAtmPortSigRetryEntry 6 }


    --
    -- STN ATM Port Signaling Service Specific Convergence Sublayer (SSCS)
    -- Table
    --
    stnAtmPortSigSSCSTable OBJECT-TYPE
        SYNTAX        SEQUENCE OF StnAtmPortSigSSCSEntry
        MAX-ACCESS    not-accessible
        STATUS        current
        DESCRIPTION   "A list of ATM Port Signaling SSCS entries."
        ::= { stnAtmPortSigRetries 2 }
 
    stnAtmPortSigSSCSEntry OBJECT-TYPE
        SYNTAX          StnAtmPortSigSSCSEntry
        MAX-ACCESS      not-accessible
        STATUS          current
        DESCRIPTION     "Entry contains information about a particular 
                        Atm Port Signaling SSCS entry."
        INDEX           { stnAtmPortSigSSCSIfIndex }
        ::= { stnAtmPortSigSSCSTable 1 }
 
    StnAtmPortSigSSCSEntry ::= 
        SEQUENCE {
                stnAtmPortSigSSCSIfIndex            InterfaceIndex,
                stnAtmPortSigSSCSPollDuration       Integer32,
                stnAtmPortSigSSCSKeepAliveDuration  Integer32,
                stnAtmPortSigSSCSIdleDuration       Integer32,
                stnAtmPortSigSSCSNoRspDuration      Integer32,
                stnAtmPortSigSSCSCcDuration         Integer32,
                stnAtmPortSigSSCSMaxRcvWindowSize   Integer32,
                stnAtmPortSigSSCSMaxCcRetries       Integer32,
                stnAtmPortSigSSCSMaxSdBetwPolls     Integer32,
                stnAtmPortSigSSCSMaxStatListElms    Integer32,
                stnAtmPortSigSSCSPollAfterRetrans   TruthValue,
                stnAtmPortSigSSCSRepeatUstat        TruthValue,
                stnAtmPortSigSSCSUstatRspToPoll     TruthValue
        }

     stnAtmPortSigSSCSIfIndex OBJECT-TYPE
        SYNTAX          InterfaceIndex
        MAX-ACCESS      read-only
        STATUS          current
        DESCRIPTION     "The interface index represents a connection point on
                         the switch fabric from a module or line card. It is
                         calculated based on the slot and port of the module."
        ::= { stnAtmPortSigSSCSEntry 1 }

    stnAtmPortSigSSCSPollDuration OBJECT-TYPE     
        SYNTAX          Integer32
        MAX-ACCESS      read-only
        STATUS          current
        DESCRIPTION     "The duration of the SSCS Poll timer in milliseconds."
        DEFVAL          { 750 }
        ::= { stnAtmPortSigSSCSEntry 2 }

    stnAtmPortSigSSCSKeepAliveDuration OBJECT-TYPE     
        SYNTAX          Integer32
        MAX-ACCESS      read-only
        STATUS          current
        DESCRIPTION     "The duration of the SSCS keep-alive timer in
                         milliseconds."
        DEFVAL          { 2000 }
        ::= { stnAtmPortSigSSCSEntry 3 }

    stnAtmPortSigSSCSIdleDuration OBJECT-TYPE     
        SYNTAX          Integer32
        MAX-ACCESS      read-only
        STATUS          current
        DESCRIPTION     "The duration of the SSCS idle timer in milliseconds."
        DEFVAL          { 15000 }
        ::= { stnAtmPortSigSSCSEntry 4 }

    stnAtmPortSigSSCSNoRspDuration OBJECT-TYPE     
        SYNTAX          Integer32
        MAX-ACCESS      read-only
        STATUS          current
        DESCRIPTION     "The duration of the SSCS no-response timer in
                         milliseconds."
        DEFVAL          { 7000 }
        ::= { stnAtmPortSigSSCSEntry 5 }

    stnAtmPortSigSSCSCcDuration OBJECT-TYPE     
        SYNTAX          Integer32
        MAX-ACCESS      read-only
        STATUS          current
        DESCRIPTION     "The duration of the SSCS CC timer in milliseconds."
        DEFVAL          { 1000 }
        ::= { stnAtmPortSigSSCSEntry 6 }

    stnAtmPortSigSSCSMaxRcvWindowSize OBJECT-TYPE     
        SYNTAX          Integer32
        MAX-ACCESS      read-only
        STATUS          current
        DESCRIPTION     "The maximum size on a receive window."
        DEFVAL          { 20 }
        ::= { stnAtmPortSigSSCSEntry 7 }

    stnAtmPortSigSSCSMaxCcRetries OBJECT-TYPE     
        SYNTAX          Integer32
        MAX-ACCESS      read-only
        STATUS          current
        DESCRIPTION     "The maximum number of expiries and subsequent
                         connection control PDU retransmissions acceptable
                         before closing the connection."
        DEFVAL          { 4 }
        ::= { stnAtmPortSigSSCSEntry 8 }

    stnAtmPortSigSSCSMaxSdBetwPolls OBJECT-TYPE     
        SYNTAX          Integer32
        MAX-ACCESS      read-only
        STATUS          current
        DESCRIPTION     "The maximum number of STAT list elements in a STAT
                         PDU."
        DEFVAL          { 25 }
        ::= { stnAtmPortSigSSCSEntry 9 }

    stnAtmPortSigSSCSMaxStatListElms OBJECT-TYPE     
        SYNTAX          Integer32
        MAX-ACCESS      read-only
        STATUS          current
        DESCRIPTION     "The maximum number of STAT list elements in a STAT
                         PDU."
        DEFVAL          { 67 }
        ::= { stnAtmPortSigSSCSEntry 10 }

    stnAtmPortSigSSCSPollAfterRetrans OBJECT-TYPE     
        SYNTAX          TruthValue
        MAX-ACCESS      read-only
        STATUS          current
        DESCRIPTION     "Whether to send a POLL after retransmitting PDUs."
        DEFVAL          { false }
        ::= { stnAtmPortSigSSCSEntry 11 }

    stnAtmPortSigSSCSRepeatUstat OBJECT-TYPE     
        SYNTAX          TruthValue
        MAX-ACCESS      read-only
        STATUS          current
        DESCRIPTION     "QSAAL only: if true, send two USTATs each time a
                         USTAT is sent."
        DEFVAL          { false }
        ::= { stnAtmPortSigSSCSEntry 12 }

    stnAtmPortSigSSCSUstatRspToPoll OBJECT-TYPE     
        SYNTAX          TruthValue
        MAX-ACCESS      read-only
        STATUS          current
        DESCRIPTION     "QSAAL only: whether USTAT PDUs are issued in response
                         to POLLs."
        DEFVAL          { false }
        ::= { stnAtmPortSigSSCSEntry 13 }


    --
    -- STN ATM Port Traffic Table
    --
    stnAtmPortTrafficTable OBJECT-TYPE
        SYNTAX        SEQUENCE OF StnAtmPortTrafficEntry
        MAX-ACCESS    not-accessible
        STATUS        current
        DESCRIPTION   "A list of ATM port traffic entries."
        ::= { stnAtmPortTraffic 1 }
 
    stnAtmPortTrafficEntry OBJECT-TYPE
        SYNTAX          StnAtmPortTrafficEntry
        MAX-ACCESS      not-accessible
        STATUS          current
        DESCRIPTION     "Entry contains information about a particular 
                        ATM port traffic entry."
        INDEX           { stnAtmPortTrafIndex }
        ::= { stnAtmPortTrafficTable 1 }
 
    StnAtmPortTrafficEntry ::= 
        SEQUENCE {
                stnAtmPortTrafIndex                 InterfaceIndex,
                stnAtmPortTrafTxCells               Counter32,
                stnAtmPortTrafRxCells               Counter32,
                stnAtmPortTrafTxParityErrors        Counter32,
                stnAtmPortTrafRxHdrChkSumErrors     Counter32,
                stnAtmPortTrafPhyParityErrors       Counter32,
                stnAtmPortTrafCrc10Errors           Counter32
        }

     stnAtmPortTrafIndex OBJECT-TYPE 
        SYNTAX          InterfaceIndex
        MAX-ACCESS      read-only
        STATUS          current
        DESCRIPTION     "The interface index represents a connection point on
                         the switch fabric from a module or line card. It is
                         calculated based on the slot and port of the module."
        ::= { stnAtmPortTrafficEntry 1 }

    stnAtmPortTrafTxCells OBJECT-TYPE
        SYNTAX          Counter32
        MAX-ACCESS      read-only
        STATUS          current
        DESCRIPTION     "The number of ATM cells transmitted."
        ::= { stnAtmPortTrafficEntry 2 }

    stnAtmPortTrafRxCells OBJECT-TYPE
        SYNTAX          Counter32
        MAX-ACCESS      read-only
        STATUS          current
        DESCRIPTION     "The number of ATM cells received."
        ::= { stnAtmPortTrafficEntry 3 }

    stnAtmPortTrafTxParityErrors OBJECT-TYPE
        SYNTAX          Counter32
        MAX-ACCESS      read-only
        STATUS          current
        DESCRIPTION     "The number of ATM transmit parity errors."
        ::= { stnAtmPortTrafficEntry 4 }

    stnAtmPortTrafRxHdrChkSumErrors OBJECT-TYPE
        SYNTAX          Counter32
        MAX-ACCESS      read-only
        STATUS          current
        DESCRIPTION     "The number of received ATM header checksum errors."
        ::= { stnAtmPortTrafficEntry 5 }

    stnAtmPortTrafPhyParityErrors OBJECT-TYPE
        SYNTAX          Counter32
        MAX-ACCESS      read-only
        STATUS          current
        DESCRIPTION     "The number of ATM physical parity errors."
        ::= { stnAtmPortTrafficEntry 6 }

    stnAtmPortTrafCrc10Errors OBJECT-TYPE
        SYNTAX          Counter32
        MAX-ACCESS      read-only
        STATUS          current
        DESCRIPTION     "The number of ATM CRC-10 errors."
        ::= { stnAtmPortTrafficEntry 7 }


    --
    -- STN ATM Address Table
    --
    stnAtmAddressTable OBJECT-TYPE
        SYNTAX        SEQUENCE OF StnAtmAddressEntry
        MAX-ACCESS    not-accessible
        STATUS        current
        DESCRIPTION   "A list of ATM address entries."
        ::= { stnAtmAddresses 1 }
 
    stnAtmAddressEntry OBJECT-TYPE
        SYNTAX          StnAtmAddressEntry
        MAX-ACCESS      not-accessible
        STATUS          current
        DESCRIPTION     "Entry contains information about a particular 
                        session."
        INDEX           { stnAtmAddrIfIndex, stnAtmAddrAddress }
        ::= { stnAtmAddressTable 1 }
 
    StnAtmAddressEntry ::= 
        SEQUENCE {
                stnAtmAddrIfIndex       InterfaceIndex,
                stnAtmAddrAddress       NSAPAddress,
                stnAtmAddrAddressLen    Integer32
        }

    stnAtmAddrIfIndex OBJECT-TYPE
        SYNTAX          InterfaceIndex
        MAX-ACCESS      read-only
        STATUS          current
        DESCRIPTION     "The interface index represents a connection point on
                         the switch fabric from a module or line card. It is
                         calculated based on the slot and port of the module."
        ::= { stnAtmAddressEntry 1 }

    stnAtmAddrAddress OBJECT-TYPE
        SYNTAX          NSAPAddress
        MAX-ACCESS      read-only
        STATUS          current
        DESCRIPTION     "The value of the ATM NSAP address."
        ::= { stnAtmAddressEntry 2 }

    stnAtmAddrAddressLen OBJECT-TYPE
        SYNTAX          Integer32
        MAX-ACCESS      read-only
        STATUS          current
        DESCRIPTION     "The number of relevent bits in the ATM address."
        ::= { stnAtmAddressEntry 3 }


    --
    -- STN ATM Threshold Table
    --
    stnAtmThresholdTable OBJECT-TYPE
        SYNTAX        SEQUENCE OF StnAtmThresholdEntry
        MAX-ACCESS    not-accessible
        STATUS        current
        DESCRIPTION   "A list of ATM threshold entries."
        ::= { stnAtmThresholds 1 }
 
    stnAtmThresholdEntry OBJECT-TYPE
        SYNTAX          StnAtmThresholdEntry
        MAX-ACCESS      not-accessible
        STATUS          current
        DESCRIPTION     "Entry contains information about a particular 
                        ATM threshold entry."
        INDEX           { stnAtmTholdTgrpId, stnAtmTholdRegionId }
        ::= { stnAtmThresholdTable 1 }
 
    StnAtmThresholdEntry ::= 
        SEQUENCE {
                stnAtmTholdTgrpId               INTEGER,
                stnAtmTholdRegionId             INTEGER,
                stnAtmTholdCellLowerLimit       INTEGER,
                stnAtmTholdCellUpperLimit       INTEGER,
                stnAtmTholdCellQLimitMarking    INTEGER, 
                stnAtmTholdQLimitDiscard        INTEGER,
                stnAtmTholdQueueLimit           INTEGER
        }

    stnAtmTholdTgrpId OBJECT-TYPE
        SYNTAX          INTEGER (0..15)
        MAX-ACCESS      read-only
        STATUS          current
        DESCRIPTION     "Specifies the threshold group indentifier."
        ::= { stnAtmThresholdEntry 1 }

    stnAtmTholdRegionId OBJECT-TYPE
        SYNTAX          INTEGER (0..7)
        MAX-ACCESS      read-only
        STATUS          current
        DESCRIPTION     "Region identifier within a threshold group."
        ::= { stnAtmThresholdEntry 2 }

    stnAtmTholdCellLowerLimit OBJECT-TYPE
        SYNTAX          INTEGER (0..65535)
        MAX-ACCESS      read-only
        STATUS          current
        DESCRIPTION     "Lower Cell number limit for region."
        DEFVAL          { 0 }
        ::= { stnAtmThresholdEntry 3 }

    stnAtmTholdCellUpperLimit OBJECT-TYPE
        SYNTAX          INTEGER (0..65535)
        MAX-ACCESS      read-only
        STATUS          current
        DESCRIPTION     "Upper Cell number limit for region."
        DEFVAL          { 1023 }
        ::= { stnAtmThresholdEntry 4 }

    stnAtmTholdCellQLimitMarking OBJECT-TYPE    
        SYNTAX          INTEGER (0..65535)
        MAX-ACCESS      read-only
        STATUS          current
        DESCRIPTION     "Queue limit for any flow above which EFCI marking 
                        occurs."
        DEFVAL          { 1023 }
        ::= { stnAtmThresholdEntry 5 }

    stnAtmTholdQLimitDiscard OBJECT-TYPE
        SYNTAX          INTEGER (0..65535)
        MAX-ACCESS      read-only
        STATUS          current
        DESCRIPTION     "Queue limit for any flow above which Discard 
                        processing occurs."
        DEFVAL          { 1023 }
        ::= { stnAtmThresholdEntry 6 }

    stnAtmTholdQueueLimit OBJECT-TYPE
        SYNTAX          INTEGER (0..65535)
        MAX-ACCESS      read-only
        STATUS          current
        DESCRIPTION     "Queue limit for any flow above which cells are 
                        automatically discarded."
        DEFVAL          { 1023 }
        ::= { stnAtmThresholdEntry 7 }


    --
    -- STN ATM Accounting Table
    --

    stnAtmAcctEnabled OBJECT-TYPE     
        SYNTAX          TruthValue 
        MAX-ACCESS      read-only
        STATUS          current
        DESCRIPTION     "Specifies whether account logging is turned on
                        or off."
        DEFVAL          { false }
        ::= { stnAtmAcct 1 }

    stnAtmAcctMaxSize OBJECT-TYPE     
        SYNTAX          Integer32
        MAX-ACCESS      read-only
        STATUS          current
        DESCRIPTION     "Specifies the maximum accounting log buffer size.
                        in Kbytes. The accounting log file will be closed 
                        when it reaches the maximum size and the name 
                        appended with a numeric differentiation."
        DEFVAL          { 1024 }
        ::= { stnAtmAcct 2 }

    stnAtmAcctMaxFiles OBJECT-TYPE     
        SYNTAX          Integer32
        MAX-ACCESS      read-only
        STATUS          current
        DESCRIPTION     "Specifies the maximum number of history files to 
                        be stored. Once the maximum number of files is 
                        reached, the oldest file is deleted."
        DEFVAL          { 10 }
        ::= { stnAtmAcct 3 }

    stnAtmAcctFilePath OBJECT-TYPE     
        SYNTAX          OCTET STRING (SIZE(0..128))
        MAX-ACCESS      read-only
        STATUS          current
        DESCRIPTION     "Specifies the accounting log output path and file
                        name on remote device."
        ::= { stnAtmAcct 4 }

    stnAtmAcctFtpServer1 OBJECT-TYPE    
        SYNTAX          IpAddress
        MAX-ACCESS      read-only
        STATUS          current
        DESCRIPTION     "The IP address of the first remote FTP server."
        ::= { stnAtmAcct 5 }

    stnAtmAcctFtpUserName1 OBJECT-TYPE
        SYNTAX          DisplayString (SIZE(0..20))
        MAX-ACCESS      read-only
        STATUS          current
        DESCRIPTION     "The first FTP server username."
        ::= { stnAtmAcct 6 }

    stnAtmAcctFtpPassword1 OBJECT-TYPE
        SYNTAX          OCTET STRING (SIZE(0..255))
        MAX-ACCESS      not-accessible
        STATUS          current
        DESCRIPTION     "The first FTP server password."
        ::= { stnAtmAcct 7 }

    stnAtmAcctFtpServer2 OBJECT-TYPE    
        SYNTAX          IpAddress
        MAX-ACCESS      read-only
        STATUS          current
        DESCRIPTION     "The IP address of the second remote FTP server." 
        ::= { stnAtmAcct 8 }

    stnAtmAcctFtpUserName2 OBJECT-TYPE
        SYNTAX          DisplayString (SIZE(0..20))
        MAX-ACCESS      read-only
        STATUS          current
        DESCRIPTION     "The second FTP server username."
        ::= { stnAtmAcct 9 }

    stnAtmAcctFtpPassword2 OBJECT-TYPE
        SYNTAX          OCTET STRING (SIZE(0..255))
        MAX-ACCESS      not-accessible
        STATUS          current
        DESCRIPTION     "The second FTP server password."
        ::= { stnAtmAcct 10 }

    stnAtmAcctFtpServer3 OBJECT-TYPE    
        SYNTAX          IpAddress
        MAX-ACCESS      read-only
        STATUS          current
        DESCRIPTION     "The IP address of the third remote FTP server."
        ::= { stnAtmAcct 11 }

    stnAtmAcctFtpUserName3 OBJECT-TYPE
        SYNTAX          DisplayString (SIZE(0..20))
        MAX-ACCESS      read-only
        STATUS          current
        DESCRIPTION     "The third FTP server username."
        ::= { stnAtmAcct 12 }

    stnAtmAcctFtpPassword3 OBJECT-TYPE
        SYNTAX          OCTET STRING (SIZE(0..255))
        MAX-ACCESS      not-accessible
        STATUS          current
        DESCRIPTION     "The third FTP server password."
        ::= { stnAtmAcct 13 }
   
    stnAtmAcctCurrentFtpServer OBJECT-TYPE    
        SYNTAX          IpAddress
        MAX-ACCESS      read-only
        STATUS          current
        DESCRIPTION     "The IP address of the current FTP server."
        ::= { stnAtmAcct 14 }

    stnAtmAcctPreviousFtpServer OBJECT-TYPE    
        SYNTAX          IpAddress
        MAX-ACCESS      read-only
        STATUS          current
        DESCRIPTION     "The IP address of the previous FTP server."
        ::= { stnAtmAcct 15 }


    --
    -- STN Traps & Notifications 
    --
    stnCdrServerFailure NOTIFICATION-TYPE
        OBJECTS         { stnAtmAcctCurrentFtpServer, 
                          stnAtmAcctPreviousFtpServer }
        STATUS          current
        DESCRIPTION     "A stnCdrServerFailure trap signifies that the agent 
                        entity has detected that the accounting server has
                        failed over to an auxilary server.
                        The generation of this trap can be controlled by the
                        stnNotificationEnableCdrServerFailure object in this MIB."
        ::= { stnNotification 15 }

    stnCdrLogFailure NOTIFICATION-TYPE
        OBJECTS         { stnAtmAcctFtpServer1, stnAtmAcctFtpServer2,
                          stnAtmAcctFtpServer3 }
        STATUS          current
        DESCRIPTION     "A stnCdrLogFailure trap signifies that the agent 
                        entity has detected that all accounting servers
                        are inaccessible. Accounting data could be lost.
                        The generation of this trap can be controlled by the
                        stnNotificationEnableCdrLogFailure object in this MIB."
        ::= { stnNotification 16 }


    stnConfigAuditPvcFailure NOTIFICATION-TYPE
        OBJECTS         { stnVcLinkIfIndex, stnVcLinkVpi,
                          stnVcLinkVci,     stnRouterIndex }
        STATUS          current
        DESCRIPTION     "A stnConfigAuditPvcFailure trap signifies that the 
                        agent entity has detected an inconsistency between
                        an active and configured PVC after a failover.
                        The generation of this trap can be controlled by the
                        CfgAuditPvcTraps configuration object."
        ::= { stnNotification 31 }

    stnConfigAuditSpvcFailure NOTIFICATION-TYPE
        OBJECTS         { stnVcLinkIfIndex, stnVcLinkVpi,
                          stnVcLinkVci,     stnRouterIndex }
        STATUS          current
        DESCRIPTION     "A stnConfigAuditSpvcFailure trap signifies that the 
                        agent entity has detected an inconsistency between
                        an active and configured SPVC after a failover.
                        The generation of this trap can be controlled by the
                        CfgAuditSpvcTraps configuration object."
        ::= { stnNotification 32 }

END
