INTEL-ES480-SYSTEM-MIB DEFINITIONS ::= BEGIN

        IMPORTS
                MODULE-IDENTITY FROM SNMPv2-SMI
		OBJECT-TYPE     FROM SNMPv2-SMI
                TruthValue      FROM SNMPv2-TC
		DisplayString   FROM RFC1213-MIB
                es480tAgent   FROM INTEL-ES480-MIB;

        es480tSystem MODULE-IDENTITY
                LAST-UPDATED "0002140000Z"
                ORGANIZATION "Intel"
                CONTACT-INFO "www.intel.com"
                DESCRIPTION "Intel es480t system objects."
        ::= { es480tAgent 1 }

--
--  System group
--
--  Objects common to all platforms
--
--  Configuration save objects.  These objects are used by the network
--  management application to save configuration changes into the
--  persistant store.  There are 2 stores on the device; a primary and
--  a secondary.

        es480tSaveConfiguration OBJECT-TYPE
               	SYNTAX INTEGER {
                    	saveToPrimary(1),
                        saveToSecondary(2)
        	}
                MAX-ACCESS read-write
                STATUS current
                DESCRIPTION
            	"When this object is set, the device will copy the contents
		of the configuration database to a buffer and save it to the 
		persistant store specified by the value of the object.  The 
		save is	performed asynchronously, and the snmp agent will
                continue to respond to both gets and sets while the save is
                taking place.  A network management application may use the
		intelSaveStatus object to determine when the asynchronous
		save operation has completed."
	::= { es480tSystem 3 }

	es480tSaveStatus OBJECT-TYPE
               	SYNTAX INTEGER { saveInProgress(1), saveNotInProgress(2) }
                MAX-ACCESS	read-only
                STATUS current
                DESCRIPTION
           	"This object will return the status of a save operation invoked
		by setting the intelSaveConfiguration object.  A network
		management application can read this object to determine that a
		save operation has completed."
	::= { es480tSystem 4 }                

        es480tCurrentConfigInUse OBJECT-TYPE
                SYNTAX INTEGER { primary(1), secondary(2) }
        	MAX-ACCESS read-only
                STATUS current
                DESCRIPTION
                "Shows which NVRAM configuration store was used at last boot"
	::= { es480tSystem 5 }                

        es480tConfigToUseOnReboot OBJECT-TYPE
                SYNTAX INTEGER { primary(1), secondary(2) }
        	MAX-ACCESS read-write
                STATUS current
                DESCRIPTION
        	"Controls which NVRAM configuration store will be used 
                on next reboot."
	::= { es480tSystem 6 }               
 
        es480tOverTemperatureAlarm OBJECT-TYPE
                SYNTAX TruthValue
        	MAX-ACCESS read-only
                STATUS current
                DESCRIPTION
                "Alarm status of overtemperature sensor in device 
                enclosure."
	::= { es480tSystem 7 }

        es480tCurrentTemperature OBJECT-TYPE
                SYNTAX INTEGER (0..100)
        	MAX-ACCESS read-only
                STATUS current
                DESCRIPTION
                "Current temperature in degrees celcius measured inside
                device enclosure."
	::= { es480tSystem 8 }

--
-- Table of operational status of all internal Fans
--
        es480tFanStatusTable OBJECT-TYPE
		SYNTAX  SEQUENCE OF Es480tFanStatusEntry
		MAX-ACCESS  not-accessible
		STATUS current
                DESCRIPTION
                "Table of operational status of all internal cooling fans."
	::= { es480tSystem 9 }

        es480tFanStatusEntry OBJECT-TYPE
		SYNTAX  Es480tFanStatusEntry
		MAX-ACCESS  not-accessible
		STATUS current
		DESCRIPTION
                "Entry in table of all internal cooling fans."
		INDEX { es480tFanNumber }
	::= { es480tFanStatusTable 1 }

	Es480tFanStatusEntry ::=
		SEQUENCE {
			es480tFanNumber
				INTEGER,
			es480tFanOperational
				TruthValue
		}

        es480tFanNumber OBJECT-TYPE
                SYNTAX INTEGER
        	MAX-ACCESS read-only
                STATUS current
                DESCRIPTION
                "Identifier of cooling fan, numbered from the front and/or 
                left side of device."
	::= { es480tFanStatusEntry 1 }

        es480tFanOperational OBJECT-TYPE
                SYNTAX TruthValue
        	MAX-ACCESS read-only
                STATUS current
                DESCRIPTION
                "Operational status of a cooling fan."
	::= { es480tFanStatusEntry 2 }


        es480tPrimaryPowerOperational OBJECT-TYPE
                SYNTAX TruthValue
        	MAX-ACCESS read-only
                STATUS current
                DESCRIPTION
                "Operational status of internal power supply of a device."
	::= { es480tSystem 10 }

        es480tRedundantPowerStatus OBJECT-TYPE
                SYNTAX INTEGER { notPresent(1), presentOK(2), presentNotOK(3) }
        	MAX-ACCESS read-only
                STATUS current
                DESCRIPTION
                "Operational status of an external redundant power supply to a device."
	::= { es480tSystem 11 }

        es480tRedundantPowerAlarm OBJECT-TYPE
                SYNTAX TruthValue
        	MAX-ACCESS read-only
                STATUS current
                DESCRIPTION
                "Alarm state of an external redundant power supply to a device. 
                Alarm state indicates either fan failure or overtemperature 
                condition."
	::= { es480tSystem 12 }

        es480tPrimarySoftwareRev  OBJECT-TYPE
            SYNTAX DisplayString (SIZE(0..15))
            MAX-ACCESS read-only
            STATUS current
            DESCRIPTION
                "The software revision of the primary image stored in 
                this device.  This string will have a zero length if 
                the revision is unknown, invalid or not present. This
                will also be reported in RMON2 probeSoftwareRev if this
                is the software image currently running in the device."
	::= { es480tSystem 13 }

        es480tSecondarySoftwareRev  OBJECT-TYPE
            SYNTAX DisplayString (SIZE(0..15))
            MAX-ACCESS read-only
            STATUS current
            DESCRIPTION
                "The software revision of the secondary image stored in 
                this device.  This string will have a zero length if 
                the revision is unknown, invalid or not present. This
                will also be reported in RMON2 probeSoftwareRev if this
                is the software image currently running in the device."
	::= { es480tSystem 14 }

        es480tImageToUseOnReboot OBJECT-TYPE
                SYNTAX INTEGER { primary(1), secondary(2) }
        	MAX-ACCESS read-write
                STATUS current
                DESCRIPTION
        	"Controls which image will be used 
                on next reboot."
	::= { es480tSystem 15 }               

        es480tSystemID  OBJECT-TYPE
            SYNTAX DisplayString (SIZE(0..126))
            MAX-ACCESS read-only
            STATUS current
            DESCRIPTION
                "This represents the System ID of the Summit Switch."
	::= { es480tSystem 16 }

        es480tSystemBoardID  OBJECT-TYPE
            SYNTAX DisplayString (SIZE(0..126))
            MAX-ACCESS read-only
            STATUS current
            DESCRIPTION
                "This represents the Board ID of the Summit Switch."
	::= { es480tSystem 17 }

        es480tSystemLeftBoardID  OBJECT-TYPE
            SYNTAX DisplayString (SIZE(0..126))
            MAX-ACCESS read-only
            STATUS current
            DESCRIPTION
                "This represents the Left Board ID of the Summit Switch."
	::= { es480tSystem 18 }

        es480tSystemRightBoardID  OBJECT-TYPE
            SYNTAX DisplayString (SIZE(0..126))
            MAX-ACCESS read-only
            STATUS current
            DESCRIPTION
                "This represents the Right Board ID of the Summit Switch."
	::= { es480tSystem 19 }

	-- Add variables to report power supply data
	es480tInputPowerVoltage OBJECT-TYPE
		SYNTAX  INTEGER {
			v110 (1),
			v220 (2),
			v48DC (3)
		}	
		MAX-ACCESS  read-only
		STATUS current
		DESCRIPTION
		"The input power voltage at which the system is currently operating."
	::= { es480tSystem 20 }

        es480tPowerStatus OBJECT-TYPE
                SYNTAX INTEGER { notPresent(1), presentOK(2), presentNotOK(3) }
        	MAX-ACCESS read-only
                STATUS current
                DESCRIPTION
                "Operational status of the power supply to a device."
	::= { es480tSystem 21 }

        es480tPowerAlarm OBJECT-TYPE
                SYNTAX TruthValue
        	MAX-ACCESS read-only
                STATUS current
                DESCRIPTION
                "Alarm state of the power supply to a device. 
                Alarm state indicates either fan failure or overtemperature 
                condition."
	::= { es480tSystem 22 }

        es480tRmonEnable OBJECT-TYPE
                SYNTAX TruthValue
        	MAX-ACCESS read-write
                STATUS current
                DESCRIPTION
                      "Setting this to true will cause the agent to 
		       start collecting RMON statistics."
	::= { es480tSystem 23 }


END

-- ===========================================================================


-- ===============================================================================

--
--  Intel es480t VLAN objects
--
