-- Copyright 1993 General DataComm Ind., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive licence to use
-- this Specification in connection with the management of GDC's products.
--
-- This Specification is supplied "AS IS," and GDC makes no warranty,
-- either expressed or implied, as to the use operation, condition, or
-- performance of the Specification.

-- Revision History
-- Ver.	Date	   Name		Description
-- 1.0   1-Dec-93  W. Meltzer   Initial Release from rev R
-- 1.1  14-Apr-94  W. Meltzer   Added csuChan6456 object, fixed some typos
--
-- gdcds1.mib,v 1.1 1995/05/31 18:34:26 shankar Exp
-- 
-- gdcds1.mib
-- Revision 1.1  1995/05/31  18:34:26  shankar
-- initial ci for cvs
--
--Revision 1.2  1994/08/19  15:22:43  haggerty
--Changed MIBS for Release 2.0 of Vfast.
--NOTE: Most of these changes were problems with the comment of CVS REvisions
--      The only Real changes were in gdcvfast.mib
--
-- Revision 1.1  1994/06/29  21:56:01  haggerty
-- Moved MIBS from OVDEVEL area to here, also updated lasted scm
-- and vfast mibs...
--
--

GDCDS1-MIB DEFINITIONS	::=	BEGIN

IMPORTS
	enterprises, Gauge, TimeTicks   FROM RFC1155-SMI
	transmission,
	DisplayString		FROM RFC1213-MIB
	ds1			FROM RFC1406-MIB
	OBJECT-TYPE		FROM RFC-1212;


-- This is the GDC ds1 MIB for additional DS1 objects, that exist above
-- those that exist in the standard, RFC1406.
--
-- Support of this MIB requires a Privilege level of 'FULL CONTROL', for
-- the 551, 552a-1, 552a and the 552a v1.1.
--
-- This MIB is only usable when the configuration is software controllable.
-- If a GDC csu is HARD optioned, then errors will occur when trying to get
-- the information.
--
-- See the GDC SNMP Requirements Document to determine how the standard
-- DS1 MIB, RFC1406 is supported in GDC's products.
--
-- In each managed object, MIB term for variable, a description of what
-- the 551, 552a-1, 552a and the 552a V1.1 supports is available.
--
-- All csu*LineIndex objects like the dsx1LineIndex from rfc1406
-- define the instance of a specific Network Element.
-- The Network Element Address (NEadr) is set by a DIP switch on the NE.
-- The following formula is used to get to a specific instance:
--  Equipment side Index = (2 x NEadr) + 2
--  Network side Index = (2 x NEadr) + 3
--
gdc	OBJECT IDENTIFIER ::= { enterprises 498 }

csu	OBJECT IDENTIFIER ::= { gdc 2 }


-- GDC Additional Configuration Parameters

-- Implementation of this group is mandatory for all GDC csu's
-- that attach to a DS1 interface.

-- Configuration Table

	csuConfigTable	OBJECT-TYPE
		SYNTAX	SEQUENCE OF CsuConfigEntry
		ACCESS	not-accessible
		STATUS	mandatory
		DESCRIPTION
			"The GDC csu Configuration Table."
		::= { csu 1 }

	csuConfigEntry	OBJECT-TYPE
		SYNTAX	CsuConfigEntry
		ACCESS	not-accessible
		STATUS	mandatory
		DESCRIPTION
			"An entry in the GDC csu Configuration Table."
		INDEX	{ csuConfigLineIndex }
		::= { csuConfigTable 1 }

	CsuConfigEntry	::=
		SEQUENCE {
			csuConfigLineIndex
				INTEGER,
			csuOnesDensity
				INTEGER,
			csuFrontPanel
				INTEGER,
			csuInbandLoop
				INTEGER,
			csuILBFrame
				INTEGER,
			csuLineBuildOutCtrl
				INTEGER,
			csuLineBuildOutValue
				INTEGER,
			csuLineTypeCtrl
				INTEGER,
			csuAISLoopdown
				INTEGER,
			csuPreEqualizer
				INTEGER,
			csuInitialize
				INTEGER,
			csuTime
				DisplayString,
			csuDate
				DisplayString,
			csuTestType
				INTEGER,
			csuReceiveLevel
				DisplayString
		}


	csuConfigLineIndex OBJECT-TYPE
		SYNTAX	INTEGER
		ACCESS	read-only
		STATUS	mandatory
		DESCRIPTION
			"This object is the identifier of a DS1 interface on
			a managed object. It is used to associate the DS1
			Configuration Group in the standard, RFC-1406. It
			should reference the dsx1LineIndex associated with
			this object. This is used to expand the standard MIB
			with the GDC specific information on an object."
		::= { csuConfigEntry 1 }


	csuOnesDensity OBJECT-TYPE
		SYNTAX	INTEGER {
				inhibit(1),
				csuMax15Zeros(2),
				csuMax39Zeros(3),
				csu8N1Restrict(4),
				csuMin1in8(5)
			}
		ACCESS	read-write
		STATUS	mandatory
		DESCRIPTION
			"This variable is used to indicate the pulse density
			on the network side.

			inhibit refers to no minimum pulse density

			csuMax15Zeros refers to a maximum of 15 consecutive
			zeros transmitted toward the network before
			a one is inserted.

			csuMax39Zeros refers to a maximum of 39 consecutive
			zeros transmitted toward the network before
			a one is inserted.

			csu8N1Restrict refers to a minimum of N ones
			per 8(N+1) bits, where N = 1 to 24; the Line Code
			option for the network side must be set to AMI.

			csuMin1in8 refers to a minimum of 1 one per 8 bits;
			with this selection, pulse density violations are
			enforced but enforcement can't be read through this MIB.
GDCPRODUCT	EQUIVALENT		POSSIBLESELECTIONS
552a-1		Ones Density		Same as defined in managed object
552a		Ones Density		Same as defined in managed object
552a V1.1	Ones Density		Same as defined in managed object
551		Ones Density		Same as defined in managed object"
		::= { csuConfigEntry 2 }

	csuFrontPanel OBJECT-TYPE
		SYNTAX	INTEGER {
				inhibit(1),
				enable(2)
			}
		ACCESS	read-write
		STATUS	mandatory
		DESCRIPTION
			"This variable is used to indicate whether the front
			panel switches are operational or not.

			inhibit refers to when the front panel switches are
			not operational.

			enable refers to when the front panel switches are
			operational.
GDCPRODUCT	EQUIVALENT		POSSIBLESELECTIONS
552a-1		None
552a		None
552a V1.1	None
551		Front Panel		Same as defined in managed object"
		::= { csuConfigEntry 3 }

	csuInbandLoop OBJECT-TYPE
		SYNTAX	INTEGER {
				inhibit(1),
				enable(2)
			}
		ACCESS	read-write
		STATUS	mandatory
		DESCRIPTION
			"This variable is used to set the
			In-Band DS1 Loopback Code Detection.

			inhibit refers to when the in-band
			loopback codes are ignored.

			enable refers to when the in-band loopback codes
			are detected and reacted to. When enabled, the
			Loopback Configuration must also be set. When a
			loopback activation or deactivation code is detected,
			the DSU starts or stops the type of loopback test
			selected with the Loopback Configuration.
GDCPRODUCT	EQUIVALENT		POSSIBLESELECTIONS
552a-1		Inband Loop		Same as defined in managed object
552a		Inband Loop		Same as defined in managed object
552a V1.1	Inband Loop		Same as defined in managed object
551		Inband Loop		Same as defined in managed object"
		::= { csuConfigEntry 4 }

	csuILBFrame OBJECT-TYPE
		SYNTAX	INTEGER {
				unframed(1),
				framed(2)
			}
		ACCESS	read-write
		STATUS	mandatory
		DESCRIPTION
			"This variable is used to set the In-Band DS1
			Loopback Code Framing option.

			unframed refers to the DSU transmitting unframed in-band
			loopback codes when a DS1 Remote Test is started.

			framed refers to the DSU transmitting framed in-band
			loopback codes when a DS1 Remote Test is started.
GDCPRODUCT	EQUIVALENT		POSSIBLESELECTIONS
552a-1		ILB Frame		Same as defined in managed object
552a		ILB Frame		Same as defined in managed object
552a V1.1	ILB Frame		Same as defined in managed object
551		ILB Frame		Same as defined in managed object"
		::= { csuConfigEntry 5 }

	csuLineBuildOutCtrl OBJECT-TYPE
		SYNTAX	INTEGER {
				csuMan(1),
				csuAuto(2)
			}
		ACCESS	read-write
		STATUS	mandatory
		DESCRIPTION
			"This variable is used to set the Network Line
			Build-Out control option for the network side.

			Man refers to manually setting the Network Line
			Build-Out to one of the specified attenuation levels
			in csuLineBuildOutValue.

			Auto refers to automatic Network Line Build-Out, based
			on the signal level received from the network.
GDCPRODUCT	EQUIVALENT		POSSIBLESELECTIONS
552a-1		Line Build-out		Same as defined in managed object
552a		Line Build-out		Same as defined in managed object
552a V1.1	Line Build-out		Same as defined in managed object
551		Line Build-out		Same as defined in managed object"
		::= { csuConfigEntry 6 }


	csuLineBuildOutValue OBJECT-TYPE
		SYNTAX	INTEGER {
				other(1),
				csu00dB(2),
				csu75dB(3),		-- really 7.5
				csu150dB(4)
			}
		ACCESS	read-write
		STATUS	mandatory
		DESCRIPTION
			"This variable is used to set the Network Line
			Build-Out value on the network side.

			In manual mode, these values can be written and read
			back.  In auto mode, a read will retreive the value
			which was automatically derived and a write will have
			no effect.

GDCPRODUCT	EQUIVALENT		POSSIBLESELECTIONS
552a-1		Line Build-out		Same as defined in managed object
552a		Line Build-out		Same as defined in managed object
552a V1.1	Line Build-out		Same as defined in managed object
551		Line Build-out		Same as defined in managed object"
		::= { csuConfigEntry 7 }

	csuLineTypeCtrl OBJECT-TYPE
		SYNTAX	INTEGER {
				none(1),
				csuMan(2),
				csuAuto(3)
			}
		ACCESS	read-write
		STATUS	mandatory
		DESCRIPTION
			"This variable is used to set the Line Type
			control.

			None refers to the unframed mode of the DC551.

			Man refers to manually setting the line type
			to one of the specified types in dsx1LineType.
			When set, read and write dsx1LineType for ESF or D4.

			Auto refers to automatic setting of line type, based
			on the framing format received from the other side.
			When set, read dsx1LineType for negotiated value but,
			writing dsx1LineType should be ignored.

GDCPRODUCT	EQUIVALENT		POSSIBLESELECTIONS
552a-1		Network Frame		 AUTO, MAN
552a		Cascade or Network Frame AUTO, MAN
552a V1.1	Cascade or Network Frame AUTO, MAN
551		DTE or NET FRAME	 AUTO, MAN, NONE"
		::= { csuConfigEntry 8 }

	csuAISLoopdown OBJECT-TYPE
		SYNTAX	INTEGER (4..60)
		ACCESS	read-write
		STATUS	mandatory
		DESCRIPTION
			"This variable is used to set the AIS Loop-Down option
			for remotely-initiated DS1 loopbacks.

			4, inhibit, refers to when a continuous received AIS
			does not terminate the loopback.

			5-60, enable, refers to when a continuous received AIS
			terminates the loopback. The value is used to determine
			the loop-down activation time in seconds.
GDCPRODUCT	EQUIVALENT	POSSIBLESELECTIONS
552a-1		AIS Loopdown	inhibit, Enable-30seconds, Enable-<n> seconds
552a		AIS Loopdown	inhibit, Enable-30seconds, Enable-<n> seconds
552a V1.1	AIS Loopdown	inhibit, Enable-30seconds, Enable-<n> seconds
551		None"
		::= { csuConfigEntry 9 }

	csuPreEqualizer OBJECT-TYPE
		SYNTAX	INTEGER {
				csuNoEqual(1),
				csu130ft(2),
				csu260ft(3),
				csu390ft(4),
				csu530ft(5),
				csu655ft(6)
			}
		ACCESS	read-write
		STATUS	mandatory
		DESCRIPTION
			"This variable is used to set the Cascade
			PreEqualization option for matching the cascade port
			line length, providing transmitter pre-equalization for
			lengths of 130 ft (0-130 feet), 260 ft (130-260 feet)
			390 ft (260-390 feet), 530 ft (390-530 feet) or
			655 ft (530-655 feet). Selecting the proper length
			ensures that the signal reaching the customer
			cascade equipment is satisfactory.
GDCPRODUCT	EQUIVALENT		POSSIBLESELECTIONS
552a-1		None
552a		PreEqualization		Same as defined in managed object
552a V1.1	PreEqualization		Same as defined in managed object
551		PreEqualization		Same as defined in managed object"
		::= { csuConfigEntry 10 }

	csuInitialize OBJECT-TYPE
		SYNTAX	INTEGER {
				csuAlarmHistory(1),
				csu24HourCounter(2),
				csuFactoryDefaults(3)
			}
		ACCESS	write-only
		STATUS	mandatory
		DESCRIPTION
			"This variable is used to initialize specific items on
			the csu,

			csuAlarmHistory refers to initializing the
			Alarm History Report and a new start time is recorded.

			csu24HourCounter refers to initializing the 24 Hour
			statistics counters. All of the counters associated
			with the statistics will be initialized to zero.

			csuFactoryDefaults refers to initializing all
			soft-configurable options to the factory default
			settings. Option 'F' from the maintenance screen.
GDCPRODUCT	EQUIVALENT		POSSIBLESELECTIONS
552a-1		Initialize Alarm History, Initialize Local 24 Hour Counters
552a		Initialize Alarm History, Initialize Local 24 Hour Counters
552a V1.1	Initialize Alarm History, Initialize Local 24 Hour Counters
551		Initialize Alarm History, Initialize One Hour"
		::= { csuConfigEntry 11 }


	csuTime OBJECT-TYPE
		SYNTAX	DisplayString (SIZE (9))
		ACCESS	read-write
		STATUS	mandatory
		DESCRIPTION
			"This variable is used to set the time for the real-time
			clock located on the network element. The string is
			fixed at a length of 9 octets with the format of:
			hh:mm:ssA. Where hh is the hour (01-12) in 12 hour
			format, mm is minutes (00-59), ss is seconds (00-59)
			and A is am (A) or pm (P).
GDCPRODUCT	EQUIVALENT		POSSIBLESELECTIONS
552a-1		Maintenance menu	set time
552a		Maintenance menu	set time
552a V1.1	Maintenance menu	set time
551		none"
		::= { csuConfigEntry 12 }


	csuDate OBJECT-TYPE
		SYNTAX	DisplayString (SIZE (8))
		ACCESS	read-write
		STATUS	mandatory
		DESCRIPTION
			"This variable is used to set the date for the real-time
			clock located on the network element. The string is
			fixed at a length of 8 octets with the format of:
			mm-dd-yy. Where mm is the month (01-12), dd is the day
			(01-31), and yy is the year (00-99).
GDCPRODUCT	EQUIVALENT		POSSIBLESELECTIONS
552a-1		Maintenance menu	set date
552a		Maintenance menu	set date
552a V1.1	Maintenance menu	set date
551		none"
		::= { csuConfigEntry 13 }

	csuTestType OBJECT-TYPE
		SYNTAX	INTEGER {
				csuLLB(1),
				csuTLB(2)
			}
		ACCESS	read-write
		STATUS	mandatory
		DESCRIPTION
			"This variable is used to set the network side
			DS1 loop type.  If csuLLB is set, a line loop is
			done when the proper inband loop pattern is detected.
			If csuTLB is set, a test loop (or payload loop) is
			done when the proper inband loop pattern is detected.
GDCPRODUCT	EQUIVALENT		POSSIBLESELECTIONS
552a-1		Test Type		Same as defined in managed object
552a		Test Type		Same as defined in managed object
552a V1.1	Test Type		Same as defined in managed object
551		Test Type		Same as defined in managed object"
		::= { csuConfigEntry 14 }

	csuReceiveLevel OBJECT-TYPE
		SYNTAX	DisplayString (SIZE (0..10))
		ACCESS	read-only
		STATUS	mandatory
		DESCRIPTION
			"This variable is used to display the current
			receive level as reported by the Receive Level
			screen.
GDCPRODUCT	EQUIVALENT		POSSIBLESELECTIONS
552a-1		Receive Level
552a		Receive Level
552a V1.1	Receive Level
551		Receive Level"
		::= { csuConfigEntry 15 }



-- GDC Channel Configuration Parameters

-- Implementation of this group is mandatory for all GDC csu's
-- that support channels.

-- The following should be noted:
--	Only one channel available for a 552a-1
--	Channel Number relates to RFC1406 Fractional Group FracIfIndex

-- Channel Configuration Table

	csuChanConfigTable	OBJECT-TYPE
		SYNTAX	SEQUENCE OF CsuChanConfigEntry
		ACCESS	not-accessible
		STATUS	mandatory
		DESCRIPTION
			"The GDC csu Channel Configuration Table."
		::= { csu 2 }

	csuChanConfigEntry	OBJECT-TYPE
		SYNTAX	CsuChanConfigEntry
		ACCESS	not-accessible
		STATUS	mandatory
		DESCRIPTION
			"An entry in the GDC csu Channel Configuration Table."
		INDEX	{ csuChanConfigLineIndex, csuChanConfigNum }
		::= { csuChanConfigTable 1 }

	CsuChanConfigEntry	::=
		SEQUENCE {
			csuChanConfigLineIndex
				INTEGER,
			csuChanConfigNum
				INTEGER,
			csuStartDS0
				INTEGER,
			csuRTSCTS
				INTEGER,
			csuControlModeIdle
				INTEGER,
			csuRDLInbandCode
				INTEGER,
			csuChanRate
				INTEGER,
			csuAlternateDS0
				INTEGER,
			csuRespondRDL
				INTEGER,
			csuInbandDLTimeout
				INTEGER,
			csuChanStatus
				INTEGER
		}

	csuChanConfigLineIndex OBJECT-TYPE
		SYNTAX	INTEGER
		ACCESS	read-only
		STATUS	mandatory
		DESCRIPTION
			"This object is the identifier of a DS1 interface on
			a managed object. It is used to associate the DS1
			Configuration Group in the standard, RFC-1406.
			It should reference the dsx1LineIndex associated with
			this object. This is use to expand the standard MIB
			with the GDC specific information on an object."
		::= { csuChanConfigEntry 1 }

	csuChanConfigNum OBJECT-TYPE
		SYNTAX	INTEGER
		ACCESS	read-only
		STATUS	mandatory
		DESCRIPTION
			"This variable is used to link the Fractional Group
			from RFC1406 to its GDC configuration. It is linked
			by the FracIfIndex in the Fractional Group from RFC1406.
GDCPRODUCT	EQUIVALENT		POSSIBLESELECTIONS
552a-1		Channel Number		A
552a		Channel Number		A, B
552a V1.1	Channel Number		A, B
551		None"
		::= { csuChanConfigEntry 2 }


	csuStartDS0 OBJECT-TYPE
		SYNTAX	INTEGER (1..24)
		ACCESS	read-write
		STATUS	mandatory
		DESCRIPTION
			"This variable is used to set the Starting DS0 Number
			option for the selected channel to 0 to 24, defining
			where the selected bandwidth begins. The number of DS0s
			used (the DS0 bundle) depends on the equipment data
			rate and whether the network accommodates Nx56 kbps
			DS0s or Nx64 kbps 'Clear Channel' DS0s, and is
			calculated automatically by the DSU after entering
			the starting DS0.
GDCPRODUCT	EQUIVALENT		POSSIBLESELECTIONS
552a-1		Starting DS0		Same as defined in managed object
552a		Starting DS0		Same as defined in managed object
552a V1.1	Starting DS0		Same as defined in managed object
551		None"
		::= { csuChanConfigEntry 3 }

	csuRTSCTS OBJECT-TYPE
		SYNTAX	INTEGER {
				other(1),
				csuCTSDelayed(2),
				csuCTSForcedOn(3)
			}
		ACCESS	read-write
		STATUS	mandatory
		DESCRIPTION
			"This variable is used to set the CTS operation
			option for the selected channel.

			csuCTSDelayed refers to CTS responding to RTS
			after a 10 ms delay.

			csuCTSForcedOn refers to CTS forced ON at all times.
GDCPRODUCT	EQUIVALENT		POSSIBLESELECTIONS
552a-1		RTS to CTS Option	Same as defined in managed object
552a		RTS to CTS Option	Same as defined in managed object
552a V1.1	RTS to CTS Option	Same as defined in managed object
551		None"
		::= { csuChanConfigEntry 4 }

	csuControlModeIdle OBJECT-TYPE
		SYNTAX	INTEGER {
				off(1),
				on(2)
			}
		ACCESS	read-write
		STATUS	mandatory
		DESCRIPTION
			"This variable is used to set the CMI Signalling
			option for the selected channel.

			off refers to when the CMI signalling is disabled.

			on refers to when the CMI signalling is enabled
			for use in polling applications on 56 kbps DDS I
			lines with remote DSUs.
GDCPRODUCT	EQUIVALENT		POSSIBLESELECTIONS
552a-1		Control Mode Idle	Same as defined in managed object
552a		Control Mode Idle	Same as defined in managed object
552a V1.1	Control Mode Idle	Same as defined in managed object
551		None"
		::= { csuChanConfigEntry 5 }

	csuRDLInbandCode OBJECT-TYPE
		SYNTAX	INTEGER {
				other(1),
				csuPN127(2),
				csuFixed(3)
			}
		ACCESS	read-write
		STATUS	mandatory
		DESCRIPTION
			"This variable is used to set the Remote Digital
			Loop Pattern option for the selected channel.

			csuFixed refers to a proprietary 7-bit loop-up/down
			in-band codes for RDL.
			csuPN127 refers to CCITT V.54 PN-127 scrambled codes.
GDCPRODUCT	EQUIVALENT		POSSIBLESELECTIONS
552a-1		RDL Inband Code		Same as defined in managed object
552a		RDL Inband Code		Same as defined in managed object
552a V1.1	RDL Inband Code		Same as defined in managed object
551		None"
		::= { csuChanConfigEntry 6 }

	csuChanRate OBJECT-TYPE
		SYNTAX	INTEGER
		ACCESS	read-write
		STATUS	mandatory
		DESCRIPTION
			"This variable is used to setup the channel rate used
			by the DSU to calculate the number of DS0s, or
			bandwidth, required for the channel. The rate depends
			on the equipment data rate and must equal or exceed it.
			The available range is from 0 kbps to 1536 kbps,
			in multiples of Nx56 kbps and Nx64 kbps.
GDCPRODUCT	EQUIVALENT		POSSIBLESELECTIONS
552a-1		Channel Rate		Same as defined in managed object
552a		Channel Rate		Same as defined in managed object
552a V1.1	Channel Rate		Same as defined in managed object
551		None"
		::= { csuChanConfigEntry 7 }

	csuAlternateDS0 OBJECT-TYPE
		SYNTAX	INTEGER {
				off(1),
				on(2)
			}
		ACCESS	read-write
		STATUS	mandatory
		DESCRIPTION
			"This variable is used to set the Alternate DS0 option.

			off refers to channel data that is carried in
			consecutive blocks of DS0s and the full T1 bandwidth
			is available for customer data.

			on refers to the channel data that is carried in
			alternate DS0s, with unused DS0s carrying all ones.
GDCPRODUCT	EQUIVALENT		POSSIBLESELECTIONS
552a-1		Alternate DS0		Same as defined in managed object
552a		Alternate DS0		Same as defined in managed object
552a V1.1	Alternate DS0		Same as defined in managed object
551		None"
		::= { csuChanConfigEntry 8 }

	csuRespondRDL OBJECT-TYPE
		SYNTAX	INTEGER {
				no(1),
				yes(2)
			}
		ACCESS	read-write
		STATUS	mandatory
		DESCRIPTION
			"This variable is used to set the Channel
			RDL Response option.

			no refers to the channel ignores in-band loopback codes.

			yes refers to when the channel responds to in-band
			loopback codes for Digital Loop received from the
			network or the remote DSU.
GDCPRODUCT	EQUIVALENT		POSSIBLESELECTIONS
552a-1		Respond RDL		Same as defined in managed object
552a		Respond RDL		Same as defined in managed object
552a V1.1	Respond RDL		Same as defined in managed object
551		None"
		::= { csuChanConfigEntry 9 }

	csuInbandDLTimeout OBJECT-TYPE
		SYNTAX	INTEGER {
				inhibit(1),
				csuEnable10Min(2)
			}
		ACCESS	read-write
		STATUS	mandatory
		DESCRIPTION
			"This variable is used to set the Channel Digital
			Loop Timer option for remotely-initiated
			Channel Digital Loop tests.

			inhibit refers to when the test is unaffected.

			csuEnable10Min refers to when the test is terminated
			after 10 minutes.
GDCPRODUCT	EQUIVALENT		POSSIBLESELECTIONS
552a-1		Inband DL Time-out	Same as defined in managed object
552a		Inband DL Time-out	Same as defined in managed object
552a V1.1	Inband DL Time-out	Same as defined in managed object
551		None"
		::= { csuChanConfigEntry 10 }

	csuChanStatus OBJECT-TYPE
		SYNTAX	INTEGER (1..255)
		ACCESS	read-only
		STATUS	mandatory
		DESCRIPTION
			"This variable is used to read the status of the
			channel. Each bit in the csuChanStatus indicates
			some status information.

			NoAlarm		bit 1	Everything is ok
			ConfigErr	bit 2	A configuration error exists"
		::= { csuChanConfigEntry 11 }


	csuChan6456 OBJECT-TYPE
		SYNTAX	INTEGER {
				mode56(1),
				mode64(2)
			}
		ACCESS	read-write
		STATUS	mandatory
		DESCRIPTION
                          " This value is used by the csu if the value of
			    csuChanRate is a multiple of both 56 & 64. This
			    value is not used if dsx1FracNumber is used to
			    configure the csu. In that case dsx1LineCoding
			    will determine the channel rate if there is a
			    common multiple.

			    write to this variable:
	                    1) snmp set
			    2) dividing csuChanRate by the number of ds0s
			       found in dsx1FracNumber

			    read from this variable:
			    1) dividing csuChanRate by the number of ds0s
			       found in dsx1FracNumber"
		::= { csuChanConfigEntry 12 }



-- GDC Indicator Group

-- Implementation of this group is mandatory for all GDC csu's
-- The information found in this group is derived from the status
-- bar on the network element screen. DC552a & DC552a V1.1 are the same.
-- DC552a-1 & DC552a-1 V1.1 are the same


	csuIndicatorTable	OBJECT-TYPE
		SYNTAX	SEQUENCE OF CsuIndicatorEntry
		ACCESS	not-accessible
		STATUS	mandatory
		DESCRIPTION
			"The GDC csu Indicator Table."
		::= { csu 3 }

	csuIndicatorEntry	OBJECT-TYPE
		SYNTAX	CsuIndicatorEntry
		ACCESS	not-accessible
		STATUS	mandatory
		DESCRIPTION
			"An entry in the GDC Indicator Table."
		INDEX	{ csuIndicatorIndex }
		::= { csuIndicatorTable 1 }

	CsuIndicatorEntry	::=
		SEQUENCE {
			csuIndicatorIndex
				INTEGER,
			csuIndicatorOOF
				INTEGER,
			csuIndicatorNNS
				INTEGER,
			csuIndicatorYEL
				INTEGER,
			csuIndicatorAIS
				INTEGER,
			csuIndicatorNLB
				INTEGER,
			csuIndicatorBPV
				INTEGER,
			csuIndicatorCRC
				INTEGER,
			csuIndicatorTSY
				INTEGER,
			csuIndicatorTNS
				INTEGER,
			csuIndicatorOS
				INTEGER,
			csuIndicatorLAD
				INTEGER,
			csuIndicatorCascadeOOF
				INTEGER,
			csuIndicatorCascadeNS
				INTEGER,
			csuIndicatorNetworkLT
				INTEGER,
			csuIndicatorNetworkST
				INTEGER,
			csuIndicatorNetworkRT
				INTEGER,
			csuIndicatorChannelRDL
				INTEGER,
			csuIndicatorChannelST
				INTEGER,
			csuIndicatorChannelDL
				INTEGER,
			csuIndicatorChannelLL
				INTEGER,
			csuIndicatorMode
				INTEGER,
			csuIndicatorDS0LB
				INTEGER
		}


	csuIndicatorIndex OBJECT-TYPE
		SYNTAX	INTEGER
		ACCESS	read-only
		STATUS	mandatory
		DESCRIPTION
			"This object is the identifier of a DS1 interface on
			a managed object. It is used to associate the DS1
			Configuration Group in the standard, RFC-1406.
			It should reference the dsx1LineIndex associated with
			this object. This is use to expand the standard MIB
			with the GDC specific information on an object."
		::= { csuIndicatorEntry 1 }


-- Network Indicators

	csuIndicatorOOF OBJECT-TYPE
		SYNTAX	INTEGER {
				not-synchronized(1),
				synchronized(2),
				unframed(3)
			}
		ACCESS	read-only
		STATUS	mandatory
		DESCRIPTION
			"This object is the Network Out of Frame indicator.
			It indicates whether the CSU/DSU is or is not
			synchronized with network framing. In a CSU this
			is also known as Network Synchronization (SYN).
			GDCPRODUCT	STATUS BAR
			551		SYN
			551 (unframed)	none
			552a		OOF
			552a-1		OOF"
		::= { csuIndicatorEntry 2 }


	csuIndicatorNNS OBJECT-TYPE
		SYNTAX	INTEGER {
				no-signal(1),
				signal(2)
			}
		ACCESS	read-only
		STATUS	mandatory
		DESCRIPTION
			"This object is the Network No Signal indicator.
			It indicates whether the CSU/DSU is or is not
			receiving a network signal.
			GDCPRODUCT	STATUS BAR
			551		NNS
			551 (unframed)	NNS
			552a		NS
			552a-1		NS"
			::= { csuIndicatorEntry 3 }


	csuIndicatorYEL	 OBJECT-TYPE
		SYNTAX	INTEGER {
				not-receiving(1),
				receiving(2),
				unframed(3)
			}
		ACCESS	read-only
		STATUS	mandatory
		DESCRIPTION
			"This object is the Network Yellow Alarm receive
			indicator. It indicates whether the CSU/DSU is or
			is not receiving a network yellow alarm.
			GDCPRODUCT	STATUS BAR
			551		YEL
			551 (unframed)	none
			552a		YEL
			552a-1		YEL"
		::= { csuIndicatorEntry 4 }


	csuIndicatorAIS	 OBJECT-TYPE
		SYNTAX	INTEGER {
				not-receiving(1),
				receiving(2),
				unframed(3)
			}
		ACCESS	read-only
		STATUS	mandatory
		DESCRIPTION
			"This object is the Network Alarm Indication Signal
			indicator. It indicates whether the CSU/DSU is or
			is not receiving AIS from the network.
			GDCPRODUCT	STATUS BAR
			551		AIS
			551 (unframed)	none
			552a		AIS
			552a-1		AIS"
		::= { csuIndicatorEntry 5 }


	csuIndicatorNLB	 OBJECT-TYPE
		SYNTAX	INTEGER {
				not-loopback(1),
				loopback(2)
			}
		ACCESS	read-only
		STATUS	mandatory
		DESCRIPTION
			"This object is the Network Loopback indicator.
			It indicates whether the CSU/DSU is or is not
			in a DS1 loopback test towards the network.
			GDCPRODUCT	STATUS BAR
			551		NLB
			551 (unframed)	NLB
			552a		NLB
			552a-1		NLB"
		::= { csuIndicatorEntry 6 }


	csuIndicatorBPV	 OBJECT-TYPE
		SYNTAX	INTEGER {
				not-receiving(1),
				receiving(2)
			}
		ACCESS	read-only
		STATUS	mandatory
		DESCRIPTION
			"This object is the Network BiPolar Violation indicator.
			It indicates whether the CSU/DSU has or has not
			received a BPV.
			GDCPRODUCT	STATUS BAR
			551		BPV
			551 (unframed)	BPV
			552a		BPV
			552a-1		BPV"
		::= { csuIndicatorEntry 7 }


	csuIndicatorCRC	 OBJECT-TYPE
		SYNTAX	INTEGER {
				not-receiving(1),
				receiving(2),
				unframed(3)
			}
		ACCESS	read-only
		STATUS	mandatory
		DESCRIPTION
			"This object is the Network Cyclic Redundancy Check
			indicator. It indicates whether the CSU/DSU has
			or has not received a CRC error.
			GDCPRODUCT	STATUS BAR
			551		CRC
			551 (unframed)	none
			552a		CRC
			552a-1		CRC"
		::= { csuIndicatorEntry 8 }


-- Equipment Indicators

	csuIndicatorTSY	 OBJECT-TYPE
		SYNTAX	INTEGER {
				not-synchronized(1),
				synchronized(2),
				unframed(3)
			}
		ACCESS	read-only
		STATUS	mandatory
		DESCRIPTION
			"This object is the Terminal Equipment Synchronization
			indicator. It indicates whether the CSU is or
			is not synchronized with equipment framing.
			GDCPRODUCT	STATUS BAR
			551		TSY
			551 (unframed)	none
			552a		none
			552a-1		none"
		::= { csuIndicatorEntry 9 }


	csuIndicatorTNS	 OBJECT-TYPE
		SYNTAX	INTEGER {
				not-receiving(1),
				receiving(2)
			}
		ACCESS	read-only
		STATUS	mandatory
		DESCRIPTION
			"This object is the Terminal No Signal
			indicator. It indicates whether the CSU is or
			is not receiving an equipment signal.
			GDCPRODUCT	STATUS BAR
			551		TNS
			551 (unframed)	TNS
			552a		none
			552a-1		none"
		::= { csuIndicatorEntry 10 }


	csuIndicatorOS	 OBJECT-TYPE
		SYNTAX	INTEGER {
				not-receiving(1),
				receiving(2)
			}
		ACCESS	read-only
		STATUS	mandatory
		DESCRIPTION
			"This object is the Equipment Zero's
			indicator. It indicates whether the CSU is or
			is not receiving an excessive number of
			consecutive zero's (see one's density option).
			GDCPRODUCT	STATUS BAR
			551		0'S
			551 (unframed)	0'S
			552a		none
			552a-1		none"
		::= { csuIndicatorEntry 11 }


	csuIndicatorLAD	 OBJECT-TYPE
		SYNTAX	INTEGER {
				not-receiving(1),
				receiving(2)
			}
		ACCESS	read-only
		STATUS	mandatory
		DESCRIPTION
			"This object is the Low Average Density
			indicator. It indicates whether the CSU is or
			is not receiving an average pulse density less
			than that selected with the one's density option.
			GDCPRODUCT	STATUS BAR
			551		LAD
			551 (unframed)	LAD
			552a		none
			552a-1		none"
		::= { csuIndicatorEntry 12 }


-- Cascade Indicators

	csuIndicatorCascadeOOF	 OBJECT-TYPE
		SYNTAX	INTEGER {
				not-synchronized(1),
				synchronized(2)
			}
		ACCESS	read-only
		STATUS	mandatory
		DESCRIPTION
			"This object is the Cascade Out of Frame
			indicator. It indicates whether the T1 Cascade port
			is or is not synchronized with customer cascade
			equipment framing.
			GDCPRODUCT	STATUS BAR
			551		none
			551 (unframed)	none
			552a		OOF
			552a-1		none"
		::= { csuIndicatorEntry 13 }


	csuIndicatorCascadeNS	 OBJECT-TYPE
		SYNTAX	INTEGER {
				not-receiving(1),
				receiving(2)
			}
		ACCESS	read-only
		STATUS	mandatory
		DESCRIPTION
			"This object is the Cascade No Signal indicator.
			It indicates whether the T1 Cascade port is or
			is not receiving a customer cascade equipment
			signal.
			GDCPRODUCT	STATUS BAR
			551		none
			551 (unframed)	none
			552a		NS
			552a-1		none"
		::= { csuIndicatorEntry 14 }


-- Network Diagnostics Indicators

	csuIndicatorNetworkLT	 OBJECT-TYPE
		SYNTAX	INTEGER {
				not-active(1),
				active(2)
			}
		ACCESS	read-only
		STATUS	mandatory
		DESCRIPTION
			"This object is the Local Test indicator.
			It indicates whether the DS1 local test is or
			is not active.
			GDCPRODUCT	STATUS BAR
			551		LT
			551 (unframed)	LT
			552a		LT
			552a-1		LT"
		::= { csuIndicatorEntry 15 }


	csuIndicatorNetworkST	 OBJECT-TYPE
		SYNTAX	INTEGER {
				not-active(1),
				active-DS0(2),
				active-DS1(3)
			}
		ACCESS	read-only
		STATUS	mandatory
		DESCRIPTION
			"This object is the Self Test indicator.
			It indicates whether the DS0 self test, DS1 self
			test or no self test is active.
			GDCPRODUCT	STATUS BAR
			551		ST
			551 (unframed)	ST
			552a		ST
			552a-1		ST"
		::= { csuIndicatorEntry 16 }


	csuIndicatorNetworkRT	 OBJECT-TYPE
		SYNTAX	INTEGER {
				not-active(1),
				active(2)
			}
		ACCESS	read-only
		STATUS	mandatory
		DESCRIPTION
			"This object is the DS1 Remote Test indicator.
			It indicates whether the DS1 remote test is or
			is not active.
			GDCPRODUCT	STATUS BAR
			551		RT
			551 (unframed)	RT
			552a		RT
			552a-1		RT"
		::= { csuIndicatorEntry 17 }


-- Channel Diagnostics Indicators

	csuIndicatorChannelRDL	 OBJECT-TYPE
		SYNTAX	INTEGER {
				not-active(1),
				active-chA(2),
				active-chB(3),
				active-chAB(4)
			}
		ACCESS	read-only
		STATUS	mandatory
		DESCRIPTION
			"This object is the channel Remote Digital Loopback
			indicator. It indicates whether the channel Remote
			Digital Loop is active on channel A, active on
			channel B or is not active.
			GDCPRODUCT	STATUS BAR
			551		none
			551 (unframed)	none
			552a		RDL
			552a-1		RDL"
		::= { csuIndicatorEntry 18 }


	csuIndicatorChannelST	 OBJECT-TYPE
		SYNTAX	INTEGER {
				not-active(1),
				active-chA(2),
				active-chB(3)
			}
		ACCESS	read-only
		STATUS	mandatory
		DESCRIPTION
			"This object is the channel Self Test indicator.
			It indicates whether the channel Self Test is
			active on channel A, active on channel B or
			is not active.
			GDCPRODUCT	STATUS BAR
			551		none
			551 (unframed)	none
			552a		ST
			552a-1		ST"
		::= { csuIndicatorEntry 19 }


	csuIndicatorChannelDL	 OBJECT-TYPE
		SYNTAX	INTEGER {
				not-active(1),
				active-chA(2),
				active-chB(3),
				active-chAB(4)
			}
		ACCESS	read-only
		STATUS	mandatory
		DESCRIPTION
			"This object is the channel Digital Loopback indicator.
			It indicates whether the channel Digital Loop is
			active on channel A, active on channel B, active on
			both channels A and B or is not active.
			GDCPRODUCT	STATUS BAR
			551		none
			551 (unframed)	none
			552a		DL
			552a-1		DL"
		::= { csuIndicatorEntry 20 }


	csuIndicatorChannelLL	 OBJECT-TYPE
		SYNTAX	INTEGER {
				not-active(1),
				active-chA(2),
				active-chB(3),
				active-chAB(4)
			}
		ACCESS	read-only
		STATUS	mandatory
		DESCRIPTION
			"This object is the channel Local Loopback indicator.
			It indicates whether the channel Local Loop is
			active on channel A, active on channel B
			or is not active.
			GDCPRODUCT	STATUS BAR
			551		none
			551 (unframed)	none
			552a		LL
			552a-1		LL"
		::= { csuIndicatorEntry 21 }


	csuIndicatorMode	OBJECT-TYPE
		SYNTAX	INTEGER {
				none(1),
				hard(2),
				soft(3)
			}
		ACCESS	read-only
		STATUS	mandatory
		DESCRIPTION
			"This object is the unit mode indicator.
			It indicates whether the CSU/DSU is in hard (or LOR)
			mode where on board DIP switches are used or soft
			mode where programmable options are allowed.
			GDCPRODUCT	STATUS BAR
			551		LOR
			551 (unframed)	LOR
			552a		HARD
			552a-1		HARD"
		::= { csuIndicatorEntry 22 }


	csuIndicatorDS0LB	OBJECT-TYPE
		SYNTAX	INTEGER {
				not-loopback(1),
				loopback(2)
			}
		ACCESS	read-only
		STATUS	mandatory
		DESCRIPTION
			"This object is the DS) Loopback indicator.
			It indicates whether DS0 loopback at the local
			CSU is active or not.
			GDCPRODUCT	STATUS BAR
			551		DS0LB
			551 (unframed)	none
			552a		none
			552a-1		none"
		::= { csuIndicatorEntry 23 }



-- GDC Diagnostic Tests

-- Implementation of this group is mandatory for all GDC csu's
-- that support diagnostic tests.

-- This group is separated into the following sections:
--	Selftest Diagnostic Table
--	Loopback Diagnostic Table

-- The following should be noted:
--	GDCSelftestPattern will be used only if under SendCode (RFC1406),
--		SendOtherTestPattern is selected. If a pattern is
--		selected in RFC1406, other should be selected for the
--		GDCSelftestPattern.
--	GDCLoopback will be used only if under LoopbackConfig (RFC1406),
--		OtherLoop is selected. If a loopback is selected in
--		RFC1406, other should be selected for the GDCLoopback.
--	Initiate Test = PayloadLoop, LineLoop, LocalTest,
--		CascadeDigitalLoop or RemoteLoop
--	Terminate Test = NoLoop in the LoopbackConfig in RFC1406.

-- Selftest Diagnostic Table

	csuSelftestDiagTable 	OBJECT-TYPE
		SYNTAX	SEQUENCE OF CsuSelftestDiagEntry
		ACCESS	not-accessible
		STATUS	mandatory
		DESCRIPTION
			"The GDC csu Selftest Diagnostic Table."
		::= { csu 4 }

	csuSelftestDiagEntry 	OBJECT-TYPE
		SYNTAX	CsuSelftestDiagEntry
		ACCESS	not-accessible
		STATUS	mandatory
		DESCRIPTION
			"An entry in the GDC csu Selftest Diagnostic Table."
		INDEX	{ csuSelftestDiagLineIndex }
		::= { csuSelftestDiagTable 1 }

	CsuSelftestDiagEntry	::=
		SEQUENCE {
			csuSelftestDiagLineIndex
				INTEGER,
			csuDiagSelftest
				INTEGER,
			csuGDCSelftestPattern
				INTEGER,
			csuSelftestUserPattern
				DisplayString,
			csuSelftestFrame
				INTEGER,
			csuSelftestResults
				DisplayString,
                        csuSelftestTime
                                TimeTicks
		}


	csuSelftestDiagLineIndex OBJECT-TYPE
		SYNTAX	INTEGER
		ACCESS	read-only
		STATUS	mandatory
		DESCRIPTION
			"This object is the identifier of a DS1 interface on
			a managed object. It is used to associate the DS1
			Configuration Group in the standard, RFC-1406.
			It should reference the dsx1LineIndex associated with
			this object. This is use to expand the standard MIB
			with the GDC specific information on an object."
		::= { csuSelftestDiagEntry 1 }

	csuDiagSelftest OBJECT-TYPE
		SYNTAX	INTEGER {
				off(1),
				on(2)
			}
		ACCESS	read-write
		STATUS	obsolete
		DESCRIPTION
			"This variable is used to indicate whether a selftest
			is currently on going. This will allow a Loopback to
			occur while a selftest is occurring.
GDCPRODUCT	EQUIVALENT		POSSIBLESELECTIONS
552a-1		Selftest		Same as defined in managed object
552a		Selftest		Same as defined in managed object
552a V1.1	Selftest		Same as defined in managed object
551		Selftest		Same as defined in managed object"
		::= { csuSelftestDiagEntry 2 }

	csuGDCSelftestPattern OBJECT-TYPE
		SYNTAX	INTEGER {
				other(1),
				csu2047(2),
				csuPROG(3)
			}
		ACCESS	read-write
		STATUS	mandatory
		DESCRIPTION
			"This variable is used in conjunction with the
			dsx1SendCode managed object in the RFC1406
			Configuration Group. It selects the test pattern
			to be used in the BIT ERROR TEST mode.

			csu2047 refers to 2047-bit test pattern. When set,
			the 2047 selftest will start.

			csuPROG refers to a user-programmable test pattern.
			The pattern is defined in csuSelftestUserPattern.
			When set, the programmable pattern selftest will start.

			When dsx1SendCode is set to dsx1SendNoCode, these
			tests will stop.

			When the GDC specific test patterns defined here
			are used, reading dsx1SendCode will return
			dsx1SendOtherTestPattern. When the test patterns
			from dsx1SendCode are set, this object returns other.
GDCPRODUCT	EQUIVALENT		POSSIBLESELECTIONS
552a-1		Selftest Pattern	Same as defined in managed object
552a		Selftest Pattern	Same as defined in managed object
552a V1.1	Selftest Pattern	Same as defined in managed object
551		Selftest Pattern	Same as defined in managed object"
		::= { csuSelftestDiagEntry 3 }

	csuSelftestUserPattern OBJECT-TYPE
		SYNTAX	DisplayString (SIZE(16))
		ACCESS	read-write
		STATUS	mandatory
		DESCRIPTION
			"This variable contains a user specified 16 bit
			pattern that will be sent during a selftest.
			The default pattern is 1100000000000000.
GDCPRODUCT	EQUIVALENT		POSSIBLESELECTIONS
552a-1		Selftest User Pattern	default, pattern
552a		Selftest User Pattern	default, pattern
552a V1.1	Selftest User Pattern	default, pattern
551		Selftest User Pattern	default, pattern"
		::= { csuSelftestDiagEntry 4 }

	csuSelftestFrame OBJECT-TYPE
		SYNTAX	INTEGER {
				unframed(1),
				framed(2)
			}
		ACCESS	read-write
		STATUS	mandatory
		DESCRIPTION
			"This variable is used to set whether the self test
			pattern is ESF/D4 framed or not.
GDCPRODUCT	EQUIVALENT		POSSIBLESELECTIONS
552a-1		None
552a		None
552a V1.1	None
551		Selftest Frame		Same as defined in managed object"
		::= { csuSelftestDiagEntry 5 }


	csuSelftestResults OBJECT-TYPE
		SYNTAX	DisplayString (SIZE(0..16))
		ACCESS	read-only
		STATUS	mandatory
		DESCRIPTION
			"This variable is used to read the results of the
			selftest. BER Inactive is used to indicate that no
			selftest is running, otherwise the number of errors.
GDCPRODUCT	EQUIVALENT		POSSIBLESELECTIONS
552a-1		Test Results		Same as defined in managed object
552a		Test Results 		Same as defined in managed object
552a V1.1	Test Results 		Same as defined in managed object
551		Test Results 		Same as defined in managed object"
		::= { csuSelftestDiagEntry 6 }


	csuSelftestTime OBJECT-TYPE
		SYNTAX	TimeTicks
		ACCESS	read-only
		STATUS	mandatory
		DESCRIPTION
			"This variable is used to read the active test time.
GDCPRODUCT	EQUIVALENT		POSSIBLESELECTIONS
552a-1		Test Time 		Same as defined in managed object
552a		Test Time 		Same as defined in managed object
552a V1.1	Test Time 		Same as defined in managed object
551		Test Time 		Same as defined in managed object"
		::= { csuSelftestDiagEntry 7 }

-- Loopback Diagnostic Table

	csuLoopbackDiagTable 	OBJECT-TYPE
		SYNTAX	SEQUENCE OF CsuLoopbackDiagEntry
		ACCESS	not-accessible
		STATUS	mandatory
		DESCRIPTION
			"The GDC csu Loopback Diagnostic Table."
		::= { csu 5 }

	csuLoopbackDiagEntry 	OBJECT-TYPE
		SYNTAX	CsuLoopbackDiagEntry
		ACCESS	not-accessible
		STATUS	mandatory
		DESCRIPTION
			"An entry in the GDC csu Loopback Diagnostic Table."
		INDEX	{ csuLoopbackDiagLineIndex }
		::= { csuLoopbackDiagTable 1 }

	CsuLoopbackDiagEntry	::=
		SEQUENCE {
			csuLoopbackDiagLineIndex
				INTEGER,
			csuGDCLoopback
				INTEGER
		}


	csuLoopbackDiagLineIndex OBJECT-TYPE
		SYNTAX	INTEGER
		ACCESS	read-only
		STATUS	mandatory
		DESCRIPTION
			"This object is the identifier of a DS1 interface on a
			managed object. It is used to associate the DS1
			Configuration Group in the standard, RFC-1406. It should
			reference the dsx1LineIndex associated with this object.
			This is use to expand the standard MIB with the GDC
			specific information on an object."
		::= { csuLoopbackDiagEntry 1 }

	csuGDCLoopback OBJECT-TYPE
		SYNTAX	INTEGER {
				other(1),
				csuLocalTest(2),
				csuNILoop(3),
				csuCascadeDigitalLoop(4),
				csuRemoteLoop(5)
			}
		ACCESS	read-write
		STATUS	mandatory
		DESCRIPTION
			"This variable is used to initiate a specific test. It
			is used in conjunction with the dsx1LoopbackConfig
			managed object in RFC1406 Configuration Group.
			Setting dsx1NoLoop(1) stops all tests.
			Setting dsx1PayloadLoop(2) or dsx1LineLoop(3) causes
			that test to start as well as automatically setting
			this variable to other(1).

			other indicates that the dsx1LoopbackConfig option
			should be checked.

			The rest of the options have the following in common:
			Setting any of them causes that test to start as well
			as automatically setting dsx1LoopbackConfig
			to dsx1OtherLoop(4).

			csuLocalTest refers to a test that transmits a
			locally-generated test message through the DSU and
			looping it back at the network interface to the test
			equipment for verification. During this test, data is
			also transmitted to the T1 link, with pulse density
			constraints, but data is not received from the
			cascade port or the line.

			csuNILoop refers a test that tests the local DSU and
			the T1 link by transmitting a locally-generated test
			message through the local DSU to the remote DS1
			Interface Connector and looping it back to the test
			equipment for verification.

			csuCascadeDigitalLoop refers to a test that tests both
			DSUs' circuitry and the T1 link by transmitting a
			remotely-generated test message through the remote DSU
			to the local DSU's cascade port interface and looping
			it back to the test equipment for verification. This
			test loops only those DS0s allocated to equipment on
			the cascade side of the local DSU. DS0s allocated to
			the local DSU or to the DSU on the network side of
			T1 are unaffected.

			csuRemoteLoop refers to a test that activates the
			remote DSU's DS1 Line Loopback function or DS1 Test
			Loopback function, depending on which one is enabled
			in the remote DSU. This tests both DSUs and the T1 link
			by transmitting a locally-generated test message through
			the local DSU to the remote DSU and looping it back to
			the test equipment for verification. Bipolar violations
			are uncorrected during this test when the remote DSU
			has its LLB function enabled.
GDCPRODUCT	EQUIVALENT	POSSIBLESELECTIONS
552a-1		Loopback	Test Loop, Line Loop, Local Test, Remote Test,
				NI Loop
552a		Loopback	Test Loop, Line Loop, Local Test, Remote Test,
				NI Loop, Cascade Digital Loop
552a V1.1	Loopback	Test Loop, Line Loop, Local Test, Remote Test,
				NI Loop, Cascade Digital Loop
551		Loopback	Test Loop, Line Loop, Local Test, Remote Test,
				NI Loop"
		::= { csuLoopbackDiagEntry 2 }




-- GDC DS0 Diagnostic Tests

-- Implementation of this group is mandatory for all GDC csu's
-- that support DS0 diagnostic tests.

-- The following should be noted:
--	Initiate Test = BitErrorTest, DelayedTest or Loopback
--	Terminate Test = NoTest in the DS0 Diagnostic Test Group

-- DS0 Diagnostic Table

	csuDS0DiagTable 	OBJECT-TYPE
		SYNTAX	SEQUENCE OF CsuDS0DiagEntry
		ACCESS	not-accessible
		STATUS	mandatory
		DESCRIPTION
			"The GDC csu DS0 Diagnostic Table."
		::= { csu 6 }

	csuDS0DiagEntry 	OBJECT-TYPE
		SYNTAX	CsuDS0DiagEntry
		ACCESS	not-accessible
		STATUS	mandatory
		DESCRIPTION
			"An entry in the GDC csu DS0 Diagnostic Table."
		INDEX	{ csuDS0LineIndex }
		::= { csuDS0DiagTable 1 }

	CsuDS0DiagEntry	::=
		SEQUENCE {
			csuDS0LineIndex
				INTEGER,
			csuDS0Num
				INTEGER (1..24),
			csuTestPattern
				INTEGER,
			csuResetResults
				INTEGER,
			csuBERtest
				INTEGER,
			csuCumErrs
				DisplayString,
                        csuDataBlocks
				DisplayString,
			csuCircuitDelayCtrl
				INTEGER,
			csuCircuitDelayResult
				DisplayString,
			csuLBtest
				INTEGER
	}

	csuDS0LineIndex OBJECT-TYPE
		SYNTAX	INTEGER
		ACCESS	read-only
		STATUS	mandatory
		DESCRIPTION
			"This object is used to associate DS0s withe the
			appropriate DS1 interface on a managed object. It is
			used to associate the DS1 Configuration Group in the
			standard, RFC-1406. It should reference the
			dsx1LineIndex associated with this object. This is used
			to expand the standard MIB with the GDC specific
			information on an object."
		::= { csuDS0DiagEntry 1 }

	csuDS0Num OBJECT-TYPE
		SYNTAX	INTEGER (1..24)
		ACCESS	read-write
		STATUS	mandatory
		DESCRIPTION
			"This variable holds the DS0 number under test.
GDCPRODUCT	EQUIVALENT		POSSIBLESELECTIONS
552a-1		DS0 Channel Number	same as defined in managed object
552a		DS0 Channel Number	same as defined in managed object
552a V1.1	DS0 Channel Number	same as defined in managed object
551		DS0 Channel Number	same as defined in managed object"
		::= { csuDS0DiagEntry 2 }

	csuTestPattern OBJECT-TYPE
		SYNTAX	INTEGER {
				other(1),
				csu511(2),
				csuQRS(3),
				csu2047(4)
			}
		ACCESS	read-write
		STATUS	mandatory
		DESCRIPTION
			"This variable holds the test pattern the DS0
			will use for testing.
GDCPRODUCT	EQUIVALENT		POSSIBLESELECTIONS
552a-1		Test Pattern		511, QRS and 2047
552a		Test Pattern		511, QRS and 2047
552a V1.1	Test Pattern		511, QRS and 2047
551		Test Pattern		511, QRS and 2047"
		::= { csuDS0DiagEntry 3 }

	csuResetResults OBJECT-TYPE
		SYNTAX	INTEGER {
				yes(1),
				no(2)
			}
		ACCESS	write-only
		STATUS	mandatory
		DESCRIPTION
			"This variable is used to reset the results
			from the previous test.
GDCPRODUCT	EQUIVALENT		POSSIBLESELECTIONS
552a-1		Reset Test Results	same as defined in managed object
552a		Reset Test Results	same as defined in managed object
552a V1.1	Reset Test Results	same as defined in managed object
551		Reset Test Results	same as defined in managed object"
		::= { csuDS0DiagEntry 4 }

	csuBERtest OBJECT-TYPE
		SYNTAX	INTEGER {
                                ds0BERoff(1),
                                ds0BERon(2)
		}
		ACCESS	read-write
		STATUS	mandatory
		DESCRIPTION
			"This variable is used to control the DS0 BER test.
			It controls a combination of 'M', Test Mode to
			BIT ERROR TEST and 'I', Initiate Test for on(2)
			and 'T', Terminate Test for off(1).
GDCPRODUCT	EQUIVALENT		POSSIBLESELECTIONS
552a-1		BIT ERROR TEST		same as defined in managed object
552a		BIT ERROR TEST		same as defined in managed object
552a V1.1	BIT ERROR TEST		same as defined in managed object
551		BIT ERROR TEST		same as defined in managed object"
		::= { csuDS0DiagEntry 5 }

	csuCumErrs OBJECT-TYPE
		SYNTAX	DisplayString (SIZE(0..8))
		ACCESS	read-only
		STATUS	mandatory
		DESCRIPTION
			"This variable is used to read the cumulative errors
			counted during the test.
GDCPRODUCT	EQUIVALENT		POSSIBLESELECTIONS
552a-1		Cumulative Errors	same as defined in managed object
552a		Cumulative Errors	same as defined in managed object
552a V1.1	Cumulative Errors	same as defined in managed object
551		Cumulative Errors	same as defined in managed object"
		::= { csuDS0DiagEntry 6 }

	csuDataBlocks OBJECT-TYPE
		SYNTAX	DisplayString (SIZE(0..8))
		ACCESS	read-only
		STATUS	mandatory
		DESCRIPTION
			"This variable is used to read the number of
			blocks tested.
GDCPRODUCT	EQUIVALENT		POSSIBLESELECTIONS
552a-1		Test Data Blocks	same as defined in managed object
552a		Test Data Blocks	same as defined in managed object
552a V1.1	Test Data Blocks	same as defined in managed object
551		Test Data Blocks	same as defined in managed object"
		::= { csuDS0DiagEntry 7 }

	csuCircuitDelayCtrl OBJECT-TYPE
		SYNTAX	INTEGER
		ACCESS	write-only
		STATUS	mandatory
		DESCRIPTION
			"This variable is used to control the circuit delay
			test. It controls a combination of 'M', Test Mode to
			DELAY TEST and 'I', Initiate Test. A write of any value
			begins the test. The test ends by itself within
			within 2 seconds.
GDCPRODUCT	EQUIVALENT		POSSIBLESELECTIONS
552a-1		Circuit Delay		same as defined in managed object
552a		Circuit Delay		same as defined in managed object
552a V1.1	Circuit Delay		same as defined in managed object
551		Circuit Delay		same as defined in managed object"
		::= { csuDS0DiagEntry 8 }

	csuCircuitDelayResult OBJECT-TYPE
		SYNTAX	DisplayString (SIZE (0..16))
		ACCESS	read-only
		STATUS	mandatory
		DESCRIPTION
			"This variable is used to read the circuit delay
			detected during the test.
GDCPRODUCT	EQUIVALENT		POSSIBLESELECTIONS
552a-1		Circuit Delay		same as defined in managed object
552a		Circuit Delay		same as defined in managed object
552a V1.1	Circuit Delay		same as defined in managed object
551		Circuit Delay		same as defined in managed object"
		::= { csuDS0DiagEntry 9 }

	csuLBtest OBJECT-TYPE
		SYNTAX	INTEGER {
                                ds0LBoff(1),
                                ds0LBon(2)
		}
		ACCESS	read-write
		STATUS	mandatory
		DESCRIPTION
			"This variable is used to control the DS0 LOOPBACK test.
			It controls a combination of 'M', Test Mode to
			LOOPBACK and 'I', Initiate Test for DS0LBon(2)
			and 'T', Terminate Test for DS0LBoff(1).
GDCPRODUCT	EQUIVALENT		POSSIBLESELECTIONS
552a-1		LOOPBACK		same as defined in managed object
552a		LOOPBACK		same as defined in managed object
552a V1.1	LOOPBACK		same as defined in managed object
551		LOOPBACK		same as defined in managed object"
		::= { csuDS0DiagEntry 10 }


-- GDC Channel Diagnostic Tests

-- Implementation of this group is mandatory for all GDC csu's
-- that support channel diagnostic tests.

-- The following should be noted:
--	Initiate Test = RemoteDigitalLoop, DigitalLoop or LocalLoop
--	Terminate Test = NoLoop in the LoopbackConfig in RFC1406.
--	Only one channel available for a 552a-1

-- Channel Diagnostic Table

	csuChanDiagTable 	OBJECT-TYPE
		SYNTAX	SEQUENCE OF CsuChanDiagEntry
		ACCESS	not-accessible
		STATUS	mandatory
		DESCRIPTION
			"The GDC csu Channel Diagnostic Table."
		::= { csu 7 }

	csuChanDiagEntry 	OBJECT-TYPE
		SYNTAX	CsuChanDiagEntry
		ACCESS	not-accessible
		STATUS	mandatory
		DESCRIPTION
			"An entry in the GDC csu Channel Diagnostic Table."
		INDEX	{ csuChanLineIndex, csuChanNum }
		::= { csuChanDiagTable 1 }

	CsuChanDiagEntry	::=
		SEQUENCE {
			csuChanLineIndex
				INTEGER,
			csuChanNum
				INTEGER,
			csuChanSelftest
				INTEGER,
			csuChanLoopback
				INTEGER,
			csuChanSelftestStatus
				DisplayString
		}

	csuChanLineIndex OBJECT-TYPE
		SYNTAX	INTEGER
		ACCESS	read-only
		STATUS	mandatory
		DESCRIPTION
			"This object is the identifier of a DS1 interface on
			a managed object. It is used to associate the DS1
			Configuration Group in the standard, RFC-1406.
			It should reference the dsx1LineIndex associated with
			this object. This is use to expand the standard MIB
			with the GDC specific information on an object."
		::= { csuChanDiagEntry 1 }

	csuChanNum OBJECT-TYPE
		SYNTAX	INTEGER
		ACCESS	read-only
		STATUS	mandatory
		DESCRIPTION
			"This variable is used to link the Fractional Group
			from RFC1406 to its GDC configuration. It is linked by
			the FracIfIndex in the Fractional Group from RFC1406."
		::= { csuChanDiagEntry 2 }

	csuChanSelftest OBJECT-TYPE
		SYNTAX	INTEGER {
				off(1),
				on(2)
		}
		ACCESS	read-write
		STATUS	mandatory
		DESCRIPTION
			"This variable is used start and stop the selftest
			on the channel.
GDCPRODUCT	EQUIVALENT		POSSIBLESELECTIONS
552a-1		Selftest		same as defined in managed object
552a		Selftest		same as defined in managed object
552a V1.1	Selftest		same as defined in managed object
551		None"
		::= { csuChanDiagEntry 3 }

	csuChanLoopback OBJECT-TYPE
		SYNTAX	INTEGER {
				csuNoLoop(1),
				csuRDL(2),
				csuDL(3),
				csuLL(4)
			}
		ACCESS	read-write
		STATUS	mandatory
		DESCRIPTION
			"This variable is used to initiate a channel test.

			NoLoop refers to when no test is currently being
			performed, it also is used to terminate a test.

			csuRDL refers to a test that tests the local channel
			equipment, both DSUs and the T1 link. It does so by
			transmitting a locally-generated test message through
			the local DSU to the remote DSU, looping it back at the
			remote channel interface, and returning it to the test
			equipment for verification. Loopback of the remote
			channel is controlled by in-band loopback codes
			transmitted by the local DSU after starting
			or stopping the test.

			csuDL refers to a test that tests the remote channel
			equipment, both DSUs and the T1 link. It does so by
			transmitting a remotely-generated test message through
			the remote DSU to the local DSU, looping it back at
			the local channel interface, and returning it to the
			test equipment for verification.

			csuLL refers to a test that tests the local channel
			equipment and the local DSU. It does so by transmitting
			a locally-generated test message through the local DSU,
			looping it back at the local multiplexer interface,
			and returning it to the test equipment for verification.
GDCPRODUCT	EQUIVALENT		POSSIBLESELECTIONS
552a-1		Channel Diagnostic		RDL, DL, LL
552a		Channel Diagnostic		RDL, DL, LL
552a V1.1	Channel Diagnostic		RDL, DL, LL
551		None"
		::= { csuChanDiagEntry 4 }

	csuChanSelftestStatus OBJECT-TYPE
		SYNTAX	DisplayString (SIZE(0..32))
		ACCESS	read-only
		STATUS	mandatory
		DESCRIPTION
			"This variable is used to read the results of the
			selftest. The value will be OFF, Chx NO ERRORS
			or ChX ERRORS - Proceed to DS0 test
GDCPRODUCT	EQUIVALENT		POSSIBLESELECTIONS
552a-1		Test Results		Same as defined in managed object
552a		Test Results 		Same as defined in managed object
552a V1.1	Test Results 		Same as defined in managed object
551		None"
		::= { csuChanDiagEntry 5 }



-- GDC Alarm History

-- Implementation of this group is mandatory for all GDC csu's
-- that support alarm history.

-- Alarm History Table

	csuAlarmHistoryTable 	OBJECT-TYPE
		SYNTAX	SEQUENCE OF CsuAlarmHistoryEntry
		ACCESS	not-accessible
		STATUS	mandatory
		DESCRIPTION
			"The GDC csu Alarm History Table."
		::= { csu 8 }

	csuAlarmHistoryEntry 	OBJECT-TYPE
		SYNTAX	CsuAlarmHistoryEntry
		ACCESS	not-accessible
		STATUS	mandatory
		DESCRIPTION
			"An entry in the GDC csu Alarm History Table."
		INDEX	{ csuAlarmHistoryIndex, csuAlarmType }
		::= { csuAlarmHistoryTable 1 }

	CsuAlarmHistoryEntry	::=
		SEQUENCE {
			csuAlarmHistoryIndex
				INTEGER,
			csuAlarmType
				INTEGER,
			csuAlarmHistoryStart
				DisplayString,
			csuCount
				Gauge,
			csuFirstOccur
				DisplayString,
			csuLastOccur
				DisplayString
		}


	csuAlarmHistoryIndex OBJECT-TYPE
		SYNTAX	INTEGER
		ACCESS	read-only
		STATUS	mandatory
		DESCRIPTION
			"This object is the identifier of a DS1 interface on
			a managed object. It is used to associate the DS1
			Configuration Group in the standard, RFC-1406.
			It should reference the dsx1LineIndex associated with
			this object.  This is used to expand the standard MIB
			with the GDC specific information on an object."
		::= { csuAlarmHistoryEntry 1 }

	csuAlarmType OBJECT-TYPE
		SYNTAX	INTEGER {
				csuNetworkLossOfSignal(1),
				csuNetworkOutOfFrame(2),
				csuAlarmIndication(3),
				csuFailedSignalState(4),
				csuReceivedYellow(5),
				csuExcessiveZeros(6),
				csuLowAverageDensity(7),
				csuBipolarViolations(8),
				csuCRCErrors(9),
				csuControlledSlips(10),
				csuUnavailableSignalState(11),
				csuCascadeLossOfSignal(12),
				csuCascadeOutOfFrame(13)
			}
		ACCESS	read-only
		STATUS	mandatory
		DESCRIPTION
			"This variable is used to indicate the alarm that
			the count, first occurance and last occurance
			is associated with.
GDCPRODUCT	EQUIVALENT		POSSIBLESELECTIONS
552a-1		Major/Minor/Other	NLOS, NOOF, AI, FSS, RY, EZ, LAD,
					BPV, CRC,CS
552a		Major/Minor/Other	NLOS, NOOF, AI, FSS, RY, EZ, LAD,
					BPV, CRC, CS, CLOF, COOF
552a V1.1	Major/Minor/Other	NLOS, NOOF, AI, FSS, RY, EZ, LAD,
					BPV, CRC, CS, USS, CLOF, COOF
551		None"
		::= { csuAlarmHistoryEntry 2 }

	csuAlarmHistoryStart OBJECT-TYPE
		SYNTAX	DisplayString (SIZE(16))
		ACCESS	read-only
		STATUS	mandatory
		DESCRIPTION
			"This variable is used to hold when the
			alarm history was initialized.
GDCPRODUCT	EQUIVALENT		POSSIBLESELECTIONS
552a-1		Initialized		Time and Date
552a		Initialized		Time and Date
552a V1.1	Start Time		Time and Date
551		Elapsed Time		Hours and Minutes"
		::= { csuAlarmHistoryEntry 3 }

	csuCount OBJECT-TYPE
		SYNTAX	Gauge
		ACCESS	read-only
		STATUS	mandatory
		DESCRIPTION
			"This is used to indicate the number of recorded events
			of each of the listed errors, since the alarm history
			was initialized or cleared.
GDCPRODUCT	EQUIVALENT		POSSIBLESELECTIONS
552a-1		Count		Same as defined in managed object
552a		Count		Same as defined in managed object
552a V1.1	Count		Same as defined in managed object
551		Count		Same as defined in managed object"
		::= { csuAlarmHistoryEntry 4 }

	csuFirstOccur OBJECT-TYPE
		SYNTAX	DisplayString (SIZE(16))
		ACCESS	read-only
		STATUS	mandatory
		DESCRIPTION
			"This variable is used to indicate when a specific
			alarm first occurred since last initialized.
GDCPRODUCT	EQUIVALENT		POSSIBLESELECTIONS
552a-1		First Occurance		Time and Date
552a		First Occurance		Time and Date
552a V1.1	First Occurance		Time and Date
551		None"
		::= { csuAlarmHistoryEntry 5 }

	csuLastOccur OBJECT-TYPE
		SYNTAX	DisplayString (SIZE(16))
		ACCESS	read-only
		STATUS	mandatory
		DESCRIPTION
			"This variable is used to indicate when the
			last alarm occurred.
GDCPRODUCT	EQUIVALENT		POSSIBLESELECTIONS
552a-1		Last Occurance		Time and Date
552a		Last Occurance		Time and Date
552a V1.1	Last Occurance		Time and Date
551		None"
		::= { csuAlarmHistoryEntry 6 }



-- GDC Scheduled Performance Report

-- Implementation of this group is mandatory for all GDC csu's
-- that support scheduled performance reports.

-- Scheduled Performance Report Table

	csuSchedPerfRprtTable 	OBJECT-TYPE
		SYNTAX	SEQUENCE OF CsuSchedPerfRprtEntry
		ACCESS	not-accessible
		STATUS	mandatory
		DESCRIPTION
			"The GDC csu Scheduled Performance Report Table."
		::= { csu 9 }

	csuSchedPerfRprtEntry 	OBJECT-TYPE
		SYNTAX	CsuSchedPerfRprtEntry
		ACCESS	not-accessible
		STATUS	mandatory
		DESCRIPTION
			"An entry in the GDC csu Scheduled Performance Report
			Table."
		INDEX	{ csuSchedPerfRprtIndex, csuPerfRprtIntervalNumber }
		::= { csuSchedPerfRprtTable 1 }

	CsuSchedPerfRprtEntry	::=
		SEQUENCE {
			csuSchedPerfRprtIndex
				INTEGER,
			csuPerfRprtIntervalNumber
				INTEGER (1..4),
			csuPerfRprtMsg
				INTEGER,
			csuCRCErrEvent
				INTEGER,
			csuSEEvent
				INTEGER,
			csuFEEvent
				INTEGER,
			csuCVEvent
				INTEGER,
			csuCSEvent
				INTEGER,
			csuAPLoop
				INTEGER
		}


	csuSchedPerfRprtIndex OBJECT-TYPE
		SYNTAX	INTEGER
		ACCESS	read-only
		STATUS	mandatory
		DESCRIPTION
			"This object is the identifier of a DS1 interface on a
			managed object. It is used to associate the DS1
			Configuration Group in the standard, RFC-1406.
			It should reference the dsx1LineIndex associated with
			this object.  This is use to expand the standard MIB
			with the GDC specific information on an object."
		::= { csuSchedPerfRprtEntry 1 }

	csuPerfRprtIntervalNumber OBJECT-TYPE
		SYNTAX	INTEGER (1..4)
		ACCESS	read-only
		STATUS	mandatory
		DESCRIPTION
			"A number between 1 and 4 denoting a 1 second interval.
GDCPRODUCT	EQUIVALENT		POSSIBLESELECTIONS
552a-1		Interval		1st, 2nd, 3rd, 4th
552a		Interval		1st, 2nd, 3rd, 4th
552a V1.1	Interval		1st, 2nd, 3rd, 4th
551		Interval		1st, 2nd, 3rd, 4th"
		::= { csuSchedPerfRprtEntry 2 }

	csuPerfRprtMsg OBJECT-TYPE
		SYNTAX	INTEGER {
				inbound(1),
				outbound(2)
			}
		ACCESS	read-write
		STATUS	mandatory
		DESCRIPTION
			"This variable is used to toggle between the
			Performance Report Message transmitted toward the
			network, outbound, and received from the network,
			inbound.
GDCPRODUCT	EQUIVALENT		POSSIBLESELECTIONS
552a-1		Performance Report	Same as defined in managed object
552a		Performance Report	Same as defined in managed object
552a V1.1	Performance Report	Same as defined in managed object
551		Performance Report	Same as defined in managed object"
		::= { csuSchedPerfRprtEntry 3 }

	csuCRCErrEvent OBJECT-TYPE
		SYNTAX	INTEGER {
				csuNoErrors(1),
				csuOneError(2),
				csuLessFive(3),
				csuLessTen(4),
				csuLess100(5),
				csuLess320(6),
				csuGreater320(7)
			}
		ACCESS	read-only
		STATUS	mandatory
		DESCRIPTION
			"This variable is used to indicate the CRC-6 Error
			Events.  They are displayed in the ranges specified.
			RANGE		DESCRIPTION		SCREEN
			NoErrors 	no errors exist 	0
			OneError	one error		1
			LessFive	2-4 errors		<5
			LessTen		5-9 errors		<10
			Less100		10-99 errors		<100
			Less320		100-319 errors		<320
			Greater320	320 or more errors	>320

GDCPRODUCT	EQUIVALENT		POSSIBLESELECTIONS
552a-1		CRC Error Event		Same as defined in managed object
552a		CRC Error Event		Same as defined in managed object
552a V1.1	CRC Error Event		Same as defined in managed object
551		CRC Error Event		Same as defined in managed object"
		::= { csuSchedPerfRprtEntry 4 }

	csuSEEvent OBJECT-TYPE
		SYNTAX	INTEGER {
				csuNoErrors(1),
				csuOneOrMore(2)
			}
		ACCESS	read-only
		STATUS	mandatory
		DESCRIPTION
			"This variable is used to indicate Severe Error Events.
			RANGE		DESCRIPTION		SCREEN
			NoErrors	0 errors		.
			OneOrMore 	1 or more errors	*

GDCPRODUCT	EQUIVALENT		POSSIBLESELECTIONS
552a-1		SE Event		Same as defined in managed object
552a		SE Event		Same as defined in managed object
552a V1.1	SE Event		Same as defined in managed object
551		SE Event		Same as defined in managed object"
		::= { csuSchedPerfRprtEntry 5 }

	csuFEEvent OBJECT-TYPE
		SYNTAX	INTEGER {
				csuNoErrors(1),
				csuOneOrMore(2)
			}
		ACCESS	read-only
		STATUS	mandatory
		DESCRIPTION
			"This variable is used to indicate a Frame Error Event.
			RANGE		DESCRIPTION		SCREEN
			NoErrors	0 errors		.
			OneOrMore 	1 or more errors	*

GDCPRODUCT	EQUIVALENT		POSSIBLESELECTIONS
552a-1		FE Event		Same as defined in managed object
552a		FE Event		Same as defined in managed object
552a V1.1	FE Event		Same as defined in managed object
551		FE Event		Same as defined in managed object"
		::= { csuSchedPerfRprtEntry 6 }

	csuCVEvent OBJECT-TYPE
		SYNTAX	INTEGER {
				csuNoErrors(1),
				csuOneOrMore(2)
			}
		ACCESS	read-only
		STATUS	mandatory
		DESCRIPTION
			"This variable is used to indicate Code Violation Event.
			RANGE		DESCRIPTION		SCREEN
			NoErrors	0 errors		.
			OneOrMore 	1 or more errors	*

GDCPRODUCT	EQUIVALENT		POSSIBLESELECTIONS
552a-1		CV Event		Same as defined in managed object
552a		CV Event		Same as defined in managed object
552a V1.1	CV Event		Same as defined in managed object
551		CV Event		Same as defined in managed object"

		::= { csuSchedPerfRprtEntry 7 }

	csuCSEvent OBJECT-TYPE
		SYNTAX	INTEGER {
				csuNoErrors(1),
				csuOneOrMore(2)
			}
		ACCESS	read-only
		STATUS	mandatory
		DESCRIPTION
			"This variable is used to indicate Controlled Slip Event
			RANGE		DESCRIPTION		SCREEN
			NoErrors	0 errors		.
			OneOrMore 	1 or more errors	*

GDCPRODUCT	EQUIVALENT		POSSIBLESELECTIONS
552a-1		CS Event		Same as defined in managed object
552a		CS Event		Same as defined in managed object
552a V1.1	CS Event		Same as defined in managed object
551		CS Event		Same as defined in managed object"
		::= { csuSchedPerfRprtEntry 8 }

	csuAPLoop OBJECT-TYPE
		SYNTAX	INTEGER {
				csuNoErrors(1),
				csuInPayload(2)
			}
		ACCESS	read-only
		STATUS	mandatory
		DESCRIPTION
			"This variable is used to indicate Active Payload Loop
			condition occurred, this is the looping back toward the
			network frames consisting of the received 192
			information bits plus its own frame in, CRC-6,
			and Data Link bits.
			RANGE		DESCRIPTION		SCREEN
			NoErrors	0 errors		.
			InPayload 	in payload		*

GDCPRODUCT	EQUIVALENT		POSSIBLESELECTIONS
552a-1		AP Loop 		Same as defined in managed object
552a		AP Loop 		Same as defined in managed object
552a V1.1	AP Loop 		Same as defined in managed object
551		AP Loop			Same as defined in managed object"
		::= { csuSchedPerfRprtEntry 9 }




-- GDC Statistics - DS1 Near End Group

-- Implementation of this group is mandatory for all GDC csu's
-- that support extra statistics for the DS1 Near End or Local User.

-- Current Statistics Table

	csuCurrentStatsTable 	OBJECT-TYPE
		SYNTAX	SEQUENCE OF CsuCurrentStatsEntry
		ACCESS	not-accessible
		STATUS	mandatory
		DESCRIPTION
			"The GDC csu Current Statistics Table."
		::= { csu 10 }

	csuCurrentStatsEntry 	OBJECT-TYPE
		SYNTAX	CsuCurrentStatsEntry
		ACCESS	not-accessible
		STATUS	mandatory
		DESCRIPTION
			"An entry in the GDC csu Scheduled Performance
			Report Table."
		INDEX	{ csuCurrentIndex }
		::= { csuCurrentStatsTable 1 }

	CsuCurrentStatsEntry	::=
		SEQUENCE {
			csuCurrentIndex
				INTEGER,
			csuCurrentLOFC
				Gauge
		}


	csuCurrentIndex OBJECT-TYPE
		SYNTAX	INTEGER
		ACCESS	read-only
		STATUS	mandatory
		DESCRIPTION
			"The index value which uniquely identifies the DS1
			interface to which this entry is applicable.
			The interface identified by a particular value of this
			index is the same interface as identified by the same
			value as a dsx1LineIndex object instance."
		::= { csuCurrentStatsEntry 1 }

	csuCurrentLOFC OBJECT-TYPE
		SYNTAX	Gauge
		ACCESS	read-only
		STATUS	mandatory
		DESCRIPTION
			"The number of Loss of Frame Count encountered by a
			DS1 interface in the current 15 minute interval.
GDCPRODUCT	EQUIVALENT		POSSIBLESELECTIONS
552a-1		None
552a		None
552a V1.1	LOFC
551		None"
		::= { csuCurrentStatsEntry 2 }



-- Interval Statistics Table

	csuIntervalStatsTable 	OBJECT-TYPE
		SYNTAX	SEQUENCE OF CsuIntervalStatsEntry
		ACCESS	not-accessible
		STATUS	mandatory
		DESCRIPTION
			"The GDC csu Interval Statistics Table."
		::= { csu 11 }

	csuIntervalStatsEntry 	OBJECT-TYPE
		SYNTAX	CsuIntervalStatsEntry
		ACCESS	not-accessible
		STATUS	mandatory
		DESCRIPTION
			"An entry in the GDC csu Scheduled Performance
			Report Table."
		INDEX	{ csuIntervalIndex, csuIntervalNumber}
		::= { csuIntervalStatsTable 1 }

	CsuIntervalStatsEntry	::=
		SEQUENCE {
			csuIntervalIndex
				INTEGER,
			csuIntervalNumber
				INTEGER,
			csuIntervalLOFC
				Gauge
		}

	csuIntervalIndex OBJECT-TYPE
		SYNTAX	INTEGER
		ACCESS	read-only
		STATUS	mandatory
		DESCRIPTION
			"The index value which uniquely identifies the DS1
			interface to which this entry is applicable.
			The interface identified by a particular value of this
			index is the same interface as identified by the same
			value as a dsx1LineIndex object instance."
		::= { csuIntervalStatsEntry 1 }

	csuIntervalNumber OBJECT-TYPE
		SYNTAX	INTEGER (1..96)
		ACCESS	read-only
		STATUS	mandatory
		DESCRIPTION
			"A number between 1 and 96, where 1 is the most
			recently completed 15 minute interval and 96 is
			the least recently completed 15 minute interval
			(assuming tht all 96 intervals are valid)."
		::= { csuIntervalStatsEntry 2 }

	csuIntervalLOFC OBJECT-TYPE
		SYNTAX	Gauge
		ACCESS	read-only
		STATUS	mandatory
		DESCRIPTION
			"The number of Loss of Frame Count encountered by a
			DS1 interface in one of the previous 96,
			individual 15 minute, intervals.
GDCPRODUCT	EQUIVALENT		POSSIBLESELECTIONS
552a-1		None
552a		None
552a V1.1	LOFC
551		None"
		::= { csuIntervalStatsEntry 3 }



-- Total Statistics Table

	csuTotalStatsTable 	OBJECT-TYPE
		SYNTAX	SEQUENCE OF CsuTotalStatsEntry
		ACCESS	not-accessible
		STATUS	mandatory
		DESCRIPTION
			"The GDC csu Total Statistics Table."
		::= { csu 12 }

	csuTotalStatsEntry 	OBJECT-TYPE
		SYNTAX	CsuTotalStatsEntry
		ACCESS	not-accessible
		STATUS	mandatory
		DESCRIPTION
			"An entry in the GDC csu Scheduled Performance Report Table."
		INDEX	{ csuTotalIndex }
		::= { csuTotalStatsTable 1 }

	CsuTotalStatsEntry	::=
		SEQUENCE {
			csuTotalIndex
				INTEGER,
			csuTotalLOFC
				Gauge
		}


	csuTotalIndex OBJECT-TYPE
		SYNTAX	INTEGER
		ACCESS	read-only
		STATUS	mandatory
		DESCRIPTION
			"The index value which uniquely identifies the DS1
			interface to which this entry is applicable.
			The interface identified by a particular value of this
			index is the same interface as identified by the same
			value as a dsx1LineIndex object instance."
		::= { csuTotalStatsEntry 1 }

	csuTotalLOFC OBJECT-TYPE
		SYNTAX	Gauge
		ACCESS	read-only
		STATUS	mandatory
		DESCRIPTION
			"The number of Loss of Frame Count encountered by a
			DS1 interface in the previous 24 hour interval.
GDCPRODUCT	EQUIVALENT		POSSIBLESELECTIONS
552a-1		None
552a		None
552a V1.1	LOFC
551		None"
		::= { csuTotalStatsEntry 2 }




-- GDC Statistics - DS1 Far End Group

-- Implementation of this group is mandatory for all GDC csu's
-- that support extra statistics for the DS1 Far End.

-- Far End Current Statistics Table

	csuFarEndCurrentStatsTable 	OBJECT-TYPE
		SYNTAX	SEQUENCE OF CsuFarEndCurrentStatsEntry
		ACCESS	not-accessible
		STATUS	mandatory
		DESCRIPTION
			"The GDC csu Current Statistics Table."
		::= { csu 13 }

	csuFarEndCurrentStatsEntry 	OBJECT-TYPE
		SYNTAX	CsuFarEndCurrentStatsEntry
		ACCESS	not-accessible
		STATUS	mandatory
		DESCRIPTION
			"An entry in the GDC csu Scheduled Performance
			Report Table."
		INDEX	{ csuFarEndCurrentIndex }
		::= { csuFarEndCurrentStatsTable 1 }

	CsuFarEndCurrentStatsEntry	::=
		SEQUENCE {
			csuFarEndCurrentIndex
				INTEGER,
			csuFarEndCurrentLOFC
				Gauge
		}


	csuFarEndCurrentIndex OBJECT-TYPE
		SYNTAX	INTEGER
		ACCESS	read-only
		STATUS	mandatory
		DESCRIPTION
			"The index value which uniquely identifies the DS1
			interface to which this entry is applicable.
			The interface identified by a particular value of this
			index is the same interface as identified by the same
			value as a dsx1LineIndex object instance."
		::= { csuFarEndCurrentStatsEntry 1 }

	csuFarEndCurrentLOFC OBJECT-TYPE
		SYNTAX	Gauge
		ACCESS	read-only
		STATUS	mandatory
		DESCRIPTION
			"The number of LOFC encountered by a DS1 interface
			in the current 15 minute interval.
GDCPRODUCT	EQUIVALENT		POSSIBLESELECTIONS
552a-1		None
552a		None
552a V1.1	LOFC
551		None"
		::= { csuFarEndCurrentStatsEntry 2 }



-- Far End Interval Statistics Table

	csuFarEndIntervalStatsTable 	OBJECT-TYPE
		SYNTAX	SEQUENCE OF CsuFarEndIntervalStatsEntry
		ACCESS	not-accessible
		STATUS	mandatory
		DESCRIPTION
			"The GDC csu Interval Statistics Table."
		::= { csu 14 }

	csuFarEndIntervalStatsEntry 	OBJECT-TYPE
		SYNTAX	CsuFarEndIntervalStatsEntry
		ACCESS	not-accessible
		STATUS	mandatory
		DESCRIPTION
			"An entry in the GDC csu Scheduled Performance
			Report Table."
		INDEX	{ csuFarEndIntervalIndex, csuFarEndIntervalNumber }
		::= { csuFarEndIntervalStatsTable 1 }

	CsuFarEndIntervalStatsEntry	::=
		SEQUENCE {
			csuFarEndIntervalIndex
				INTEGER,
			csuFarEndIntervalNumber
				INTEGER,
			csuFarEndIntervalLOFC
				Gauge
		}


	csuFarEndIntervalIndex OBJECT-TYPE
		SYNTAX	INTEGER
		ACCESS	read-only
		STATUS	mandatory
		DESCRIPTION
			"The index value which uniquely identifies the DS1
			interface to which this entry is applicable.
			The interface identified by a particular value of this
			index is the same interface as identified by the same
			value as a dsx1LineIndex object instance."
		::= { csuFarEndIntervalStatsEntry 1 }

	csuFarEndIntervalNumber OBJECT-TYPE
		SYNTAX	INTEGER (1..96)
		ACCESS	read-only
		STATUS	mandatory
		DESCRIPTION
			"A number between 1 and 96, where 1 is the most
			recently completed 15 minute interval and 96 is
			the least recently completed 15 minute interval
			(assuming tht all 96 intervals are valid)."
		::= { csuFarEndIntervalStatsEntry 2 }

	csuFarEndIntervalLOFC OBJECT-TYPE
		SYNTAX	Gauge
		ACCESS	read-only
		STATUS	mandatory
		DESCRIPTION
			"The number of LOFC encountered by a DS1 interface in
			one of the previous 96, individual 15 minute, intervals.
GDCPRODUCT	EQUIVALENT		POSSIBLESELECTIONS
552a-1		None
552a		None
552a V1.1	LOFC
551		None"
		::= { csuFarEndIntervalStatsEntry 3 }



-- Far End Total Statistics Table

	csuFarEndTotalStatsTable 	OBJECT-TYPE
		SYNTAX	SEQUENCE OF CsuFarEndTotalStatsEntry
		ACCESS	not-accessible
		STATUS	mandatory
		DESCRIPTION
			"The GDC csu Total Statistics Table."
		::= { csu 15 }

	csuFarEndTotalStatsEntry 	OBJECT-TYPE
		SYNTAX	CsuFarEndTotalStatsEntry
		ACCESS	not-accessible
		STATUS	mandatory
		DESCRIPTION
			"An entry in the GDC csu Scheduled Performance
			Report Table."
		INDEX	{ csuFarEndTotalIndex }
		::= { csuFarEndTotalStatsTable 1 }

	CsuFarEndTotalStatsEntry	::=
		SEQUENCE {
			csuFarEndTotalIndex
				INTEGER,
			csuFarEndTotalLOFC
				Gauge
		}


	csuFarEndTotalIndex OBJECT-TYPE
		SYNTAX	INTEGER
		ACCESS	read-only
		STATUS	mandatory
		DESCRIPTION
			"The index value which uniquely identifies the DS1
			interface to which this entry is applicable.
			The interface identified by a particular value of this
			index is the same interface as identified by the same
			value as a dsx1LineIndex object instance."
		::= { csuFarEndTotalStatsEntry 1 }

	csuFarEndTotalLOFC OBJECT-TYPE
		SYNTAX	Gauge
		ACCESS	read-only
		STATUS	mandatory
		DESCRIPTION
			"The number of LOFC encountered by a DS1 interface
			in the previous 24 hour interval.
GDCPRODUCT	EQUIVALENT		POSSIBLESELECTIONS
552a-1		None
552a		None
552a V1.1	LOFC
551		None"
		::= { csuFarEndTotalStatsEntry 2 }


END
