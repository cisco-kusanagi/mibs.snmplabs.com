Bellcore                Intercarrier Frame Relay MIB          September 1994





                         Definitions of Managed Objects
                          for Intercarrier Frame Relay

                                   SNMPv2 MIB
                           bellcore-frxaomv2-00.txt
                                 September 1994
                                  Version 1.0

                            Andrew J. Mayer (editor)
                              Robert M. Davenport
                          Bell Communications Research
                            331 Newman Springs Road
                              Red Bank, NJ  07701

                             ajm2@cc.bellcore.com
                             rmd2@cc.bellcore.com




Status of this Memo

   This document is a private extension to the SNMP MIB.
   Distribution of this memo is unlimited.  Please send
   comments to the editor.

Abstract

   This memo defines a private extension to the Management Information
   Base (MIB) for use with network management protocols in TCP/IP-based
   internets.  In particular, it defines objects that Local Exchange
   Carriers (LECs) and Interexchange Carriers (ICs) can use to manage
   intercarrier Frame Relay (i.e., when multiple carriers are involved
   in providing Frame Relay Service to end-users).

   This memo does not specify a standard for the Internet community.

Table of Contents

   1. The SNMPv2 Network Management Framework ...............    2
   2. Object Definitions ....................................    3
   3. Overview ..............................................    4
   3.1 Scope of MIB Module...................................    4
   4. Object Definitions ....................................    6
   5. References ............................................   11
   6. Security Considerations ...............................   13
   7. Author's Address ......................................   13


A. J. Mayer (editor)                                                [Page 1]

Bellcore                Intercarrier Frame Relay MIB          September 1994


1.  The SNMPv2 Network Management Framework

   The SNMPv2 Network Management Framework consists of four major
   components.  They are:

      o    RFC 1442 [1] which defines the SMI, the mechanisms used for
           describing and naming objects for the purpose of
           management.

      o    STD 17, RFC 1213 [2] defines MIB-II, the core set of managed
           objects for the Internet suite of protocols.

      o    RFC 1445 [3] which defines the administrative and other
           architectural aspects of the framework.

      o    RFC 1448 [4] which defines the protocol used for network
           access to managed objects.

   The Framework permits new objects to be defined for the purpose of
   experimentation and evaluation.
































A. J. Mayer (editor)                                                [Page 2]

Bellcore                Intercarrier Frame Relay MIB          September 1994


2.  Object Definitions

   Managed objects are accessed via a virtual information store, termed
   the Management Information Base or MIB.  Objects in the MIB are
   defined using the subset of Abstract Syntax Notation One (ASN.1)
   defined in the SMI.  In particular, each object type is named
   by an OBJECT IDENTIFIER, an administratively assigned name.  The
   object type together with an object instance serves to uniquely
   identify a specific instantiation of the object.  For human
   convenience, we often use a textual string, termed the descriptor,
   to refer to the object type.









































A. J. Mayer (editor)                                                [Page 3]

Bellcore                Intercarrier Frame Relay MIB          September 1994


3.  Overview

   This section provides an overview and background of how to use this MIB
   module and other potential MIB modules when managing a Frame Relay
   Intercarrier Interface (ICI).  A Frame Relay ICI interconnects two
   Frame Relay carriers involved in providing an end-to-end Frame
   Relay Service [5].

   An Exchange Access Operations Management (XA-OM) service is a set of
   network management capabilities provided by a Local Exchange Carrier
   (LEC) to an Interexchange Carrier (IC).  These capabilities are
   intended to enable an IC to directly manage aspects of its exchange
   access service.  Exchange access service is provided by a LEC to an
   IC in support of the IC's inter-Local Access and Transport Area (LATA)
   service offering.

   The following diagram shows the MIB stack that could be followed for
   managing intercarrier Frame Relay.  This is only an example and not
   meant to be inclusive.

         +----------------------------------------------------------+
         +  MIB  |  Intercarrier FR    |  FR Service MIB    |   T   +
         +   II  |---------------------|--------------------|   C   +
         +       |                 DS1 & DS3                |   A   +
         +----------------------------------------------------------+

3.1.  Scope of MIB Module

   The intercarrier Frame Relay MIB module will only manage the Frame
   Relay portion of the network related to the Frame Relay ICI. Frame
   Relay XA-OM also relies on the Frame Relay Service MIB module [6],
   the DS3 MIB module [7], the DS1 MIB module[8], and TCA MIB module [9].

   This MIB will NOT be implemented on User Equipment (e.g., DTE).
   The Frame Relay DTE MIB (RFC 1315) should be used to manage those
   devices [10].

   The Frame Relay SNMP MIB module for XA-OM is an SNMPv2 MIB.  It
   provides read-only information that allows an IC to obtain performance
   monitoring information about the ICIs that interconnect its network
   with a LEC's network to provide intercarrier Frame Relay.  By using
   this and other related MIB modules, a carrier's (i.e., IC's) NM
   application can monitor ICIs and service aspects of intercarrier
   Frame Relay.  Internal aspects of the network (e.g., switching
   elements, and line cards) are outside the scope of this MIB module.
   The carrier's NM application will be able to access the SNMP proxy
   agent within a LEC's Frame Relay network using SNMP over UDP over
   IP with IP encapsulated in Frame Relay according to RFC1490/ANSI
   T1.617 Annex F [11,12].



A. J. Mayer (editor)                                                [Page 4]

Bellcore                Intercarrier Frame Relay MIB          September 1994


   The initial implementation of the MIB module is based on SNMPv2.  The
   service capabilities include retrieving information.  This MIB module
   does NOT include managed objects that: 

       1) Monitor the physical layer,

       2) Support Threshold Crossing Alerts specified for Frame
          Relay XA-OM, and

       3) Provide information pertaining to the overall management
          of the Frame Relay Service.  

   These objects have already been defined in the DS1, DS3, TCA, and
   Frame Relay Service MIB modules referred to earlier.






































A. J. Mayer (editor)                                                [Page 5]

Bellcore                Intercarrier Frame Relay MIB          September 1994


4.  Object Definitions

 INTERCARRIER-FR-MIB DEFINITIONS ::= BEGIN
 IMPORTS
    MODULE-IDENTITY, OBJECT-TYPE, Counter32  FROM SNMPv2-SMI
    ifIndex                                  FROM RFC-1213;

 bellcore         OBJECT IDENTIFIER ::= { enterprises 148 }
 requirements     OBJECT IDENTIFIER ::= { bellcore 1 }


 gr1430 MODULE-IDENTITY
      LAST-UPDATED "9409301200Z"
      ORGANIZATION "Bellcore"
      CONTACT-INFO
            "   Andrew J. Mayer
                Bellcore
                331 Newman Springs Rd.
                Red Bank, NJ 07701 USA

                Tel: 1-908-758-2148
                Fax: 1-908-758-4177
                E-mail: ajm2@cc.bellcore.com

                Robert M. Davenport
                Bellcore
                331 Newman Springs Rd.
                Red Bank, NJ 07701 USA

                Tel: 1-908-758-2194
                Fax: 1-908-758-4177
                E-mail: rmd2@cc.bellcore.com."

      DESCRIPTION
               "The MIB module to describe generic objects for
               Intercarrier Frame Relay Network Service."
      ::= { requirements 9 }

              friciObjects  OBJECT IDENTIFIER ::= { gr1430 1 }

 -- The Frame Relay ICI Group

 friciTable OBJECT-TYPE
    SYNTAX  SEQUENCE OF FrIciEntry
    MAX-ACCESS  not-accessible
    STATUS  current
    DESCRIPTION
       "The Frame Relay ICI table."
    ::= { friciObjects 1 }



A. J. Mayer (editor)                                                [Page 6]

Bellcore                Intercarrier Frame Relay MIB          September 1994


 friciEntry OBJECT-TYPE
    SYNTAX  FrIciEntry
    MAX-ACCESS  not-accessible
    STATUS  current
    DESCRIPTION
       "An entry in the Frame Relay ICI table."
    INDEX   { ifIndex }
    ::= { friciTable 1 }

 FrIciEntry ::=
    SEQUENCE {
       friciLevel2ErrorDiscards
           Counter32,
       friciLevel3ErrorDiscards
           Counter32,
       friciSigUserInvalidEvents
           Counter32,
       friciSigUserIncorrectEvents
           Counter32,
       friciSigNetInvalidEvents
           Counter32,
       friciSigNetIncorrectEvents
           Counter32,
       friciCongestionDiscards
           Counter32,
       friciDisagreementsDiscards
           Counter32
 }

 friciLevel2ErrorDiscards OBJECT-TYPE
    SYNTAX  Counter32
    MAX-ACCESS  read-only
    STATUS  current
    DESCRIPTION
       "The number of frames discarded per FR_ICI 
        transmission path in the ingress direction
        due to Level 2 errors.  The specific Level 2
        errors that contributed to the discard of frames
        are described in Section 5.4.3, R 5-31 of
        GR-1327-CORE"
 ::= { friciEntry 1 }











A. J. Mayer (editor)                                                [Page 7]

Bellcore                Intercarrier Frame Relay MIB          September 1994


 friciLevel3ErrorDiscards OBJECT-TYPE
    SYNTAX  Counter32
    MAX-ACCESS  read-only
    STATUS  current
    DESCRIPTION
       "The number of frames discarded per FR_ICI 
        transmission path in the ingress direction
        due to Level 3 errors.  The specific Level 3
        errors that contributed to the discard of frames
        are described in Section 5.4.3, R 5-31 of
        GR-1327-CORE"
 ::= { friciEntry 2 }

 friciSigUserInvalidEvents OBJECT-TYPE
    SYNTAX  Counter32
    MAX-ACCESS  read-only
    STATUS  current
    DESCRIPTION
       "The number of frames discarded per FR_ICI 
        transmission path in the ingress direction
        because of user side status signaling invalid
        fields.  The specific status signaling invalid field
        errors that contributed to the discard of frames
        are described in Section 5.4.3, R 5-31 of
        GR-1327-CORE"
 ::= { friciEntry 3 }

 friciSigUserIncorrectEvents OBJECT-TYPE
    SYNTAX  Counter32
    MAX-ACCESS  read-only
    STATUS  current
    DESCRIPTION
       "The number of frames discarded per FR_ICI 
        transmission path in the ingress direction
        because of user side status signaling incorrect
        fields.  The specific status signaling incorrect field
        errors that contributed to the discard of frames
        are described in Section 5.4.3, R 5-31 of
        GR-1327-CORE"
 ::= { friciEntry 4 }












A. J. Mayer (editor)                                                [Page 8]

Bellcore                Intercarrier Frame Relay MIB          September 1994


 friciSigNetInvalidEvents OBJECT-TYPE
    SYNTAX  Counter32
    MAX-ACCESS  read-only
    STATUS  current
    DESCRIPTION
       "The number of frames discarded per FR_ICI 
        transmission path in the ingress direction
        because of network side status signaling invalid
        fields.  The specific status signaling invalid field
        errors that contributed to the discard of frames
        are described in Section 5.4.3, R 5-31 of
        GR-1327-CORE"
 ::= { friciEntry 5 }

 friciSigNetIncorrectEvents OBJECT-TYPE
    SYNTAX  Counter32
    MAX-ACCESS  read-only
    STATUS  current
    DESCRIPTION
       "The number of frames discarded per FR_ICI 
        transmission path in the ingress direction
        because of user side status signaling incorrect
        fields.  The specific status signaling incorrect field
        errors that contributed to the discard of frames
        are described in Section 5.4.3, R 5-31 of
        GR-1327-CORE"
 ::= { friciEntry 6 }

 friciCongestionDiscards OBJECT-TYPE
    SYNTAX  Counter32
    MAX-ACCESS  read-only
    STATUS  current
    DESCRIPTION
       "The number of frames discarded per FR_ICI 
        transmission path due to congestion.  This count
        includes frames with and without the DE bit set
        discarded due to congestion.  The specific reasons
        for discarding frames at a congestable resource
        are described in Section 7.2.1, R 7-8, Items #5, #6,
        and #7 in GR-1327-CORE"
 ::= { friciEntry 7 }











A. J. Mayer (editor)                                                [Page 9]

Bellcore                Intercarrier Frame Relay MIB          September 1994


 friciDisagreementsDiscards OBJECT-TYPE
    SYNTAX  Counter32
    MAX-ACCESS  read-only
    STATUS  current
    DESCRIPTION
       "The number of frames discarded per FR_ICI 
        transmission path because of service disagreements
        The specific service disagreements that contribute
        to the discard of frames are described in Section 5.5
        R 5-42 of GR-1327-CORE"
 ::= { friciEntry 8 }


 END






































A. J. Mayer (editor)                                               [Page 10]

Bellcore                Intercarrier Frame Relay MIB          September 1994


5.  References

   [1]  Case, J., McCloghrie, K., Rose, M., and S. Waldbusser, "Structure
        of Management Information for version 2 of the Simple Network
        Management Protocol (SNMPv2)", RFC 1442, SNMP Research, Inc.,
        Hughes LAN Systems, Dover Beach Consulting, Inc., Carnegie Mellon
        University, April 1993.

   [2]  K. McCloghrie and M. Rose, Editors, "Management
        Information Base for Network Management of TCP/IP-based
        internets", RFC 1213, Performance Systems International,
        March 1991.

   [3]  Galvin, J., and K. McCloghrie, "Administrative Model for version
        2 of the Simple Network Management Protocol (SNMPv2)", RFC 1445,
        Trusted Information Systems, Hughes LAN Systems, April 1993.

   [4]  Case, J., McCloghrie, K., Rose, M., and S. Waldbusser, "Protocol
        Operations for version 2 of the Simple Network Management
        Protocol (SNMPv2)", RFC 1448, SNMP Research, Inc., Hughes LAN
        Systems, Dover Beach Consulting, Inc., Carnegie Mellon
        University, April 1993.

   [5]  GR-1430-CORE, "Generic Requirements for Initial Frame Relay 
        PVC Exchange Access Operations Management (XA-OM) Service",
        Bellcore, Issue 1, June 1994.

   [6]  T. A. Cox and K. Tesink, "Definitions of Managed Objects
        for Frame Relay Service", RFC 1604, Bellcore, March 1994.

   [7]  T. A. Cox and K. Tesink, "Definitions of Managed Objects
        for the DS3 and E3 Interface Type", RFC 1407, Bellcore,
        January 1993.

   [8]  F. Baker, "Definitions of Managed Objects for the DS1
        and E1 Interface Type", RFC 1406, Advanced Computer
        Communications, January 1993.

   [9] T. A. Brown and K. Tesink, "Definitions of Managed Objects for
        Threshold Crossing Alerts", Bellcore Enterprise-specific MIB
        (posted on venera.isi.edu as bellcore-tcav2-01.txt, SNMPv2
        MIB, and bellcore-tcav1-00.mib, SNMPv1 MIB), Version
        1.1, June 1994.

   [10] Brown, C., Baker, F., and C. Carvalho, "Management Information
        Base for Frame Relay DTEs", RFC 1315, Wellfleet Communications,
        Inc., Advanced Computer Communications, April 1992.





A. J. Mayer (editor)                                               [Page 11]

Bellcore                Intercarrier Frame Relay MIB          September 1994


   [11] ANSI T1.617-1991, American National Standard for
        Telecommunications - Integrated Services Digital Network (ISDN) -
        Digital Subscriber Signaling System No. 1 (DSS1) - Signaling
        Specification for Frame Relay Bearer Service.

   [12] Bradley, T., Brown, C., and A. Malis, "Multi-Protocol
        Interconnect over Frame Relay", RFC 1490, Wellfleet
        Communications, Inc., Ascom Timeplex, Inc., July 1993.












































A. J. Mayer (editor)                                               [Page 12]

Bellcore                Intercarrier Frame Relay MIB          September 1994


6.  Security Considerations

   Security issues are not discussed in this memo.


7.  Authors' Address

   Andrew J. Mayer                         Robert M. Davenport
   Bellcore                                Bellcore
   331 Newman Springs Road                 331 Newman Springs Road
   Room 1C342                              Room 1C326
   Red Bank, NJ  07701                     Red Bank, NJ  07701

   Phone: (908) 758-2148                   Phone: (908) 758-2194
   Fax:   (908) 758-4177                   Fax:   (908) 758-4177

   E-mail:ajm2@cc.bellcore.com             E-mail: rmd2@cc.bellcore.com



































A. J. Mayer (editor)                                               [Page 13]
