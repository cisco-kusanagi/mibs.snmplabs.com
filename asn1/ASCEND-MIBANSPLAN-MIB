--			Ascend mibansplan MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBANSPLAN-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibanswerPlanProfile  OBJECT IDENTIFIER ::= { configuration 34}

	-- The mibanswerPlanProfile table
	--
	-- This table contains parameters for the mibanswerPlanProfile profile
	--

    mibanswerPlanProfileTable	OBJECT-TYPE
	SYNTAX		SEQUENCE OF MibanswerPlanProfileEntry
	ACCESS		not-accessible
	STATUS		mandatory
	DESCRIPTION	"A list of mibanswerPlanProfile profile entries."
	::= { mibanswerPlanProfile 1 }

    mibanswerPlanProfileEntry	OBJECT-TYPE
	SYNTAX		MibanswerPlanProfileEntry
	ACCESS		not-accessible
	STATUS		mandatory
	DESCRIPTION	"A mibanswerPlanProfile entry containing objects that
			 maps to the parameters of mibanswerPlanProfile profile."
	INDEX		{ answerPlanProfile-Name }
	::= { mibanswerPlanProfileTable 1 }

    MibanswerPlanProfileEntry ::=
	SEQUENCE {
	    answerPlanProfile-Name
		DisplayString,
	    answerPlanProfile-AnswerNumber
		DisplayString,
	    answerPlanProfile-AnswerCallType
		INTEGER,
	    answerPlanProfile-DestChanGroup
		INTEGER,
	    answerPlanProfile-DialPlanNumber
		INTEGER,
	    answerPlanProfile-Action-o
		INTEGER
	}

    answerPlanProfile-Name	OBJECT-TYPE
	SYNTAX	DisplayString
	ACCESS	read-only
	STATUS	mandatory
	DESCRIPTION	""
	::= { mibanswerPlanProfileEntry 1 }

    answerPlanProfile-AnswerNumber	OBJECT-TYPE
	SYNTAX	DisplayString
	ACCESS	read-write
	STATUS	mandatory
	DESCRIPTION	"Phone number to match when routing by incoming phone number."
	::= { mibanswerPlanProfileEntry 2 }

    answerPlanProfile-AnswerCallType	OBJECT-TYPE
	SYNTAX	INTEGER {
		    voice (1),
		    n-56kRestricted (2),
		    n-64kClear (3),
		    n-64kRestricted (4),
		    n-56kClear (5),
		    n-384kRestricted (6),
		    n-384kClear (7),
		    n-1536kClear (8),
		    n-1536kRestricted (9),
		    n-128kClear (10),
		    n-192kClear (11),
		    n-256kClear (12),
		    n-320kClear (13),
		    dws384Clear (14),
		    n-448Clear (15),
		    n-512Clear (16),
		    n-576Clear (17),
		    n-640Clear (18),
		    n-704Clear (19),
		    n-768Clear (20),
		    n-832Clear (21),
		    n-896Clear (22),
		    n-960Clear (23),
		    n-1024Clear (24),
		    n-1088Clear (25),
		    n-1152Clear (26),
		    n-1216Clear (27),
		    n-1280Clear (28),
		    n-1344Clear (29),
		    n-1408Clear (30),
		    n-1472Clear (31),
		    n-1600Clear (32),
		    n-1664Clear (33),
		    n-1728Clear (34),
		    n-1792Clear (35),
		    n-1856Clear (36),
		    n-1920Clear (37),
		    x30RestrictedBearer (39),
		    v110ClearBearer (40),
		    n-64kX30Restricted (41),
		    n-56kV110Clear (42),
		    modem (43),
		    atmodem (44),
		    n-2456kV110 (46),
		    n-4856kV110 (47),
		    n-9656kV110 (48),
		    n-19256kV110 (49),
		    n-38456kV110 (50),
		    n-2456krV110 (51),
		    n-4856krV110 (52),
		    n-9656krV110 (53),
		    n-19256krV110 (54),
		    n-38456krV110 (55),
		    n-2464kV110 (56),
		    n-4864kV110 (57),
		    n-9664kV110 (58),
		    n-19264kV110 (59),
		    n-38464kV110 (60),
		    n-2464krV110 (61),
		    n-4864krV110 (62),
		    n-9664krV110 (63),
		    n-19264krV110 (64),
		    n-38464krV110 (65),
		    v32 (66),
		    phs64k (67),
		    voiceOverIp (68),
		    atmSvc (70),
		    frameRelaySvc (71),
		    vpnTunnel (72),
		    wormarq (73),
		    n-14456kV110 (74),
		    n-28856kV110 (75),
		    n-14456krV110 (76),
		    n-28856krV110 (77),
		    n-14464kV110 (78),
		    n-28864kV110 (79),
		    n-14464krV110 (80),
		    n-28864krV110 (81),
		    modem31khzAudio (82),
		    x25Svc (83),
		    n-144kClear (255),
		    iptoip (263)
		}
	ACCESS	read-write
	STATUS	mandatory
	DESCRIPTION	"The switched call type (or any) that is used to map a network call to a destChanGroup."
	::= { mibanswerPlanProfileEntry 3 }

    answerPlanProfile-DestChanGroup	OBJECT-TYPE
	SYNTAX	INTEGER
	ACCESS	read-write
	STATUS	mandatory
	DESCRIPTION	"A number that identifies the channel-group to which incoming calls that match these criteria will be directed."
	::= { mibanswerPlanProfileEntry 4 }

    answerPlanProfile-DialPlanNumber	OBJECT-TYPE
	SYNTAX	INTEGER
	ACCESS	read-write
	STATUS	mandatory
	DESCRIPTION	"A number that identifies the dial plan from the dial plan menu. Priority: net/t1(dialPlan#, Select-Digits), answerPlan(dialPlan#)"
	::= { mibanswerPlanProfileEntry 5 }

    answerPlanProfile-Action-o	OBJECT-TYPE
	SYNTAX	INTEGER {
		    noAction (1),
		    createProfile (2),
		    deleteProfile (3)
		}
	ACCESS	read-write
	STATUS	mandatory
	DESCRIPTION	""
	::= { mibanswerPlanProfileEntry 6 }

END
