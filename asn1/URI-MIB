-- extracted from draft-mcwalter-uri-mib-02.txt
-- at Thu Feb  8 06:08:15 2007

URI-MIB DEFINITIONS ::= BEGIN

IMPORTS
    MODULE-IDENTITY, mib-2             FROM SNMPv2-SMI      -- [RFC2578]
    TEXTUAL-CONVENTION                 FROM SNMPv2-TC;      -- [RFC2579]

uriMIB MODULE-IDENTITY
    LAST-UPDATED "200702050000Z" -- 5 February 2007
    ORGANIZATION "IETF Operations and Management (OPS) Area"
    CONTACT-INFO "EMail: ops-area@ietf.org
                  Home page: http://www.ops.ietf.org/"
    DESCRIPTION
            "This MIB module defines textual conventions for
            representing URIs, as defined by RFC 3986 STD 66.

            Copyright (C) The IETF Trust (2007).  This version of this
            MIB module is part of RFC yyyy; see the RFC itself for full
            legal notices."
    REVISION     "200702050000Z" -- 5 February 2007
    DESCRIPTION
           "Initial revision, published as RFC yyyy."

-- RFC Ed.: replace yyyy with actual RFC number & remove this note
    ::= { mib-2 XXX }
-- RFC Ed.: replace XXX with IANA-assigned number & remove this note

Uri ::= TEXTUAL-CONVENTION
   DISPLAY-HINT "255a"
   STATUS      current
   DESCRIPTION
            "A Uniform Resource Identifier (URI) as defined by STD 66.

            This URI MUST be a normalized as defined in section 6 of
            RFC 3986 STD 66.  STD 66 defines that some parts of a URI
            are case-insensitive, but objects using this textual
            convention MUST use normalized URIs.  The purpose of this
            restriction is to help provide unique URIs for use as MIB
            table indexes.  Note that normalization of URIs does not
            by itself provide uniqueness: Two textually distinct
            normalized URIs may be equivalent."
   REFERENCE "RFC 3986 STD 66 and RFC 3305"
   SYNTAX      OCTET STRING

Uri255 ::= TEXTUAL-CONVENTION
   DISPLAY-HINT "255a"
   STATUS      current
   DESCRIPTION
            "A Uniform Resource Identifier (URI) as defined by STD 66.

            This URI MUST be a normalized as defined in section 6 of
            RFC 3986 STD 66.  STD 66 defines that some parts of a URI
            are case-insensitive, but objects using this textual
            convention MUST use normalized URIs.  The purpose of this
            restriction is to help provide unique URIs for use as MIB
            table indexes.  Note that normalization of URIs does not
            by itself provide uniqueness: Two textually distinct
            normalized URIs may be equivalent.

            STD 66 URIs are of unlimited length.  Objects using this
            textual convention impose an arbitrary length limit on the
            URIs that they can represent.  If no length restriction is
            required, then objects SHOULD use the 'Uri' textual
            convention instead."
   REFERENCE "RFC 3986 STD 66 and RFC 3305"
   SYNTAX      OCTET STRING (SIZE (0..255))

Uri1024 ::= TEXTUAL-CONVENTION
   DISPLAY-HINT "1024a"
   STATUS      current
   DESCRIPTION
            "A Uniform Resource Identifier (URI) as defined by STD 66.

            This URI MUST be a normalized as defined in section 6 of
            RFC 3986 STD 66.  STD 66 defines that some parts of a URI
            are case-insensitive, but objects using this textual
            convention MUST use normalized URIs.  The purpose of this
            restriction is to help provide unique URIs for use as MIB
            table indexes.  Note that normalization of URIs does not
            by itself provide uniqueness: Two textually distinct
            normalized URIs may be equivalent.

            STD 66 URIs are of unlimited length.  Objects using this
            textual convention impose an arbitrary length limit on the
            URIs that they can represent.  If no length restriction is
            required, then objects SHOULD use the 'Uri' textual
            convention instead."
   REFERENCE "RFC 3986 STD 66 and RFC 3305"
   SYNTAX      OCTET STRING (SIZE (0..1024))

END

-- 
--    Copyright (C) The IETF Trust (2007).  This document is subject to the
--    rights, licenses and restrictions contained in BCP 78, and except as
--    set forth therein, the authors retain all their rights.
-- 
-- 
-- Acknowledgment
-- 
--    Funding for the RFC Editor function is currently provided by the
--    Internet Society.
