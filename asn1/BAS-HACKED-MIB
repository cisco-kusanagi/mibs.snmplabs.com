BAS-HACKED-MIB DEFINITIONS ::= BEGIN

IMPORTS
	MODULE-IDENTITY, OBJECT-TYPE,
        IpAddress,
	Integer32						FROM SNMPv2-SMI
	RowStatus						FROM SNMPv2-TC
	basHackedInfo, BasChassisId,
	BasSlotId, BasInterfaceId,
	BasLogicalPortId, BasCardClass	FROM BAS-MIB;


basHackedInfoMib MODULE-IDENTITY
	LAST-UPDATED "9901180900Z"
	ORGANIZATION "Broadband Access Systems"
	CONTACT-INFO
		" Tech Support
		  Broadband Access Systems
		  201 Forest Street
		  Marlboro, MA  01752
		  U.S.A.
		  
		  508-485-8200
		  support@basystems.com"
	DESCRIPTION
		"This MIB module defines the configuration MIB objects
		 for a Broadband Access System Chassis cards."
	::= { basHackedInfo 1 }


basHackedObjects	OBJECT IDENTIFIER ::= { basHackedInfoMib 1 }

--
-- ----------------------------------------------------------------------
--
-- Bas Mgr Configuration Object
--
-- ----------------------------------------------------------------------
--

basHackedInfoTable OBJECT-TYPE
	SYNTAX		SEQUENCE OF BasHackedInfoEntry
	MAX-ACCESS	not-accessible
	STATUS		current
	DESCRIPTION
		"Info about this slot."
	::= { basHackedObjects 1 }

basHackedInfoEntry OBJECT-TYPE
	SYNTAX		BasHackedInfoEntry
	MAX-ACCESS	not-accessible
	STATUS		current
	DESCRIPTION
		"Chassis and slot and Agent information."
	INDEX		{ 
					basHackedCardInfoChassis,
					basHackedCardInfoSlot,
					basHackedCardInfoIf,
					basHackedCardInfoLPort
				}
	::= { basHackedInfoTable 1 }

BasHackedInfoEntry ::= SEQUENCE {
		basHackedCardInfoChassis				BasChassisId,
		basHackedCardInfoSlot					BasSlotId,
		basHackedCardInfoIf					BasInterfaceId,
		basHackedCardInfoLPort					BasLogicalPortId,
		basHackedCardInfoChassisNumber				Integer32,
		basHackedCardInfoClass					BasCardClass,
		basHackedAgentConfigSave				INTEGER,
		basHackedAgentConfigSaveStatus				INTEGER,
		basHackedBcmIpAddress					IpAddress,
		basHackedCardReset					INTEGER,	
		basHackedAgentSharedKey					OCTET STRING,
		basHackedAgentUdpPort					INTEGER,
		basHackedAgentTcpPort					INTEGER,
		basHackedCardResetState					INTEGER
	}

basHackedCardInfoChassis OBJECT-TYPE
	SYNTAX		BasChassisId
	MAX-ACCESS	not-accessible
	STATUS		current
	DESCRIPTION
		"The BAS Chassis ID of this card."
	::= { basHackedInfoEntry 1 }

basHackedCardInfoSlot OBJECT-TYPE
	SYNTAX		BasSlotId
	MAX-ACCESS	not-accessible
	STATUS		current
	DESCRIPTION
		"The BAS Slot ID of this card."
	::= { basHackedInfoEntry 2 }

basHackedCardInfoIf OBJECT-TYPE
	SYNTAX		BasInterfaceId
	MAX-ACCESS	not-accessible
	STATUS		current
	DESCRIPTION
		"The BAS interface ID of this card."
	::= { basHackedInfoEntry 3 }

basHackedCardInfoLPort OBJECT-TYPE
	SYNTAX		BasLogicalPortId
	MAX-ACCESS	not-accessible
	STATUS		current
	DESCRIPTION
		"The BAS logical port ID of this card."
	::= { basHackedInfoEntry 4 }

basHackedCardInfoChassisNumber OBJECT-TYPE
    SYNTAX		Integer32
    MAX-ACCESS	read-only
    STATUS		current
    DESCRIPTION
		"The BAS Chassis serial number of this card."
    ::= { basHackedInfoEntry 5 }

basHackedCardInfoClass OBJECT-TYPE
    SYNTAX		BasCardClass
    MAX-ACCESS	read-only
    STATUS		current
    DESCRIPTION
		"The BAS card class of this card."
    ::= { basHackedInfoEntry 6 }

basHackedAgentConfigSave OBJECT-TYPE
    SYNTAX		INTEGER {
                        normal(1),
                        save(2),
                        saving(3)
			}
    MAX-ACCESS	        read-write
    STATUS		current
    DESCRIPTION
		"The BAS save configuration Object"
    ::= { basHackedInfoEntry 7 }

basHackedAgentConfigSaveStatus OBJECT-TYPE
    SYNTAX		INTEGER {
                        none(1),
                        passed(2),
                        failed(3)
			}	
    MAX-ACCESS	read-only
    STATUS		current
    DESCRIPTION
		"The BAS save configuration status Object"
    ::= { basHackedInfoEntry 8}

basHackedBcmIpAddress OBJECT-TYPE
    SYNTAX		IpAddress
    MAX-ACCESS	        read-write
    STATUS		current
    DESCRIPTION
		"The BCM IP Address Object"
    ::= { basHackedInfoEntry 9 }


basHackedCardReset OBJECT-TYPE
    SYNTAX		INTEGER {
                        normal(1),
                        reset(2)
			}
    MAX-ACCESS	        read-write
    STATUS		current
    DESCRIPTION
		"The BAS Card Reset Object. In order to set this object to reset(2),
                 the object basHackedCardResetState must first be set to unlocked(2)."
    ::= { basHackedInfoEntry 10 }


basHackedAgentSharedKey OBJECT-TYPE
    SYNTAX		OCTET STRING (SIZE (0..256))
    MAX-ACCESS	        read-write
    STATUS		current
    DESCRIPTION
		"The Agent Shared Key Object"
    ::= { basHackedInfoEntry 11 }


basHackedAgentUdpPort OBJECT-TYPE
    SYNTAX		INTEGER(0..65535)
    MAX-ACCESS	        read-write
    STATUS		current
    DESCRIPTION
		"The BAS Agent SNMP UDP Port Object"
    ::= { basHackedInfoEntry 12 }


basHackedAgentTcpPort OBJECT-TYPE
    SYNTAX		INTEGER(0..65535)
    MAX-ACCESS	        read-write
    STATUS		current
    DESCRIPTION
		"The BAS Agentx Tcp Port Object"
    ::= { basHackedInfoEntry 13 }

basHackedCardResetState OBJECT-TYPE
    SYNTAX		INTEGER {
                        locked(1),
                        unlocked(2)
                        }
    MAX-ACCESS	        read-write
    STATUS		current
    DESCRIPTION
		"The state of the basHackedCardReset object. If this object
                is set to locked(1), then the card cannot be reset without
                first setting this object to unlocked(2)."
    ::= { basHackedInfoEntry 14 }

--
-- ----------------------------------------------------------------------
--
-- End
--
-- ----------------------------------------------------------------------
--

END
