Wellfleet-XNS-MIB DEFINITIONS ::= BEGIN

-- Created by mdl2asn version 3.1
-- Creation date: Wed Aug 30 16:50:22 EDT 1995


    IMPORTS

      Counter, Opaque
        FROM RFC1155-SMI
      OBJECT-TYPE
        FROM RFC-1212
      DisplayString
        FROM RFC1213-MIB
      wfXnsGroup
        FROM Wellfleet-COMMON-MIB;


    wfXnsBase	OBJECT IDENTIFIER ::= { wfXnsGroup 1 }

    wfXnsBaseDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete XNS."
        DEFVAL	{ created }
        ::= { wfXnsBase 1 }

    wfXnsBaseDisable OBJECT-TYPE
        SYNTAX	INTEGER {
    		    enabled(1),
    		    disabled(2)
    		}
        ACCESS	read-write
        STATUS	mandatory
        DESCRIPTION
                "Enable/Disable parameter. Default is enabled.
                Users perform an SNMP SET operation on this
                object in order to enable/disable XNS."
        DEFVAL	{ enabled }
        ::= { wfXnsBase 2 }

    wfXnsBaseState OBJECT-TYPE
        SYNTAX	INTEGER {
    		    up(1),
    		    down(2),
    		    init(3),
    		    notpresent(4)
    		}
        ACCESS	read-only
        STATUS	mandatory
        DESCRIPTION
                "The current state of the entire XNS."
        DEFVAL	{ notpresent }
        ::= { wfXnsBase 3 }

    wfXnsBaseCfgHostNumber OBJECT-TYPE
        SYNTAX	OCTET STRING
        ACCESS	read-write
        STATUS	mandatory
        DESCRIPTION
                "Host Number of Router and potential MAC address of box."
        ::= { wfXnsBase 4 }

    wfXnsBaseActiveHostNumber OBJECT-TYPE
        SYNTAX	OCTET STRING
        ACCESS	read-only
        STATUS	mandatory
        DESCRIPTION
                "a legal input, else takes on a self generated unique number"
        ::= { wfXnsBase 5 }

    wfXnsBaseImplement OBJECT-TYPE
        SYNTAX	INTEGER {
    		    xerox(1),
    		    ungb(2)
    		}
        ACCESS	read-write
        STATUS	mandatory
        DESCRIPTION
                "Implementation method.  UB_XNS/XNS concurrent functionality or
                Vanilla XNS functionality only."
        DEFVAL	{ xerox }
        ::= { wfXnsBase 6 }

    wfXnsBaseNetCount OBJECT-TYPE
        SYNTAX	Counter
        ACCESS	read-only
        STATUS	mandatory
        DESCRIPTION
                "Count the total number of nets in the box."
        ::= { wfXnsBase 7 }

    wfXnsBaseHostCount OBJECT-TYPE
        SYNTAX	Counter
        ACCESS	read-only
        STATUS	mandatory
        DESCRIPTION
                "Count the total number of hosts in the box."
        ::= { wfXnsBase 8 }

    wfXnsBaseLogFilter OBJECT-TYPE
        SYNTAX	INTEGER {
    		    debug(1),
    		    info(2),
    		    trace(16),
    		    debuginfo(3),
    		    debugtrace(17),
    		    infotrace(18),
    		    debuginfotrace(19)
    		}
        ACCESS	read-write
        STATUS	mandatory
        DESCRIPTION
                "Filter out some log messages, Default filters out
                debugs, info, and trace messages."
        DEFVAL	{ trace }
        ::= { wfXnsBase 9 }

    wfXnsBaseAdjEntryTable OBJECT-TYPE
        SYNTAX	SEQUENCE OF WfXnsBaseAdjEntry
        ACCESS	not-accessible
        STATUS	mandatory
        DESCRIPTION
                "This is used by Ungermann-Bass functionality only."
        ::= { wfXnsGroup 8 }

    wfXnsBaseAdjEntry OBJECT-TYPE
        SYNTAX	WfXnsBaseAdjEntry
        ACCESS	not-accessible
        STATUS	mandatory
        DESCRIPTION
                "An entry in the Adjacency Table"
        INDEX	{ wfXnsBaseAdjacencyNetwork,
    		  wfXnsBaseAdjacencyHostid }
        ::= { wfXnsBaseAdjEntryTable 1 }

    WfXnsBaseAdjEntry ::= SEQUENCE {
    	    wfXnsBaseAdjacencyNetwork
    		OCTET STRING,
    	    wfXnsBaseAdjacencyHostid
    		OCTET STRING,
    	    wfXnsBaseAdjacencyCost
    		INTEGER,
    	    wfXnsBaseAdjacencyAge
    		INTEGER,
    	    wfXnsBaseAdjacencyIntf
    		OCTET STRING,
    	    wfXnsBaseAdjacencyCct
    		INTEGER
        }

    wfXnsBaseAdjacencyNetwork OBJECT-TYPE
        SYNTAX	OCTET STRING (SIZE (4))
        ACCESS	read-only
        STATUS	mandatory
        DESCRIPTION
                "Adjacent Router's/Host's network address for which a hello has been
                received."
        ::= { wfXnsBaseAdjEntry 1 }

    wfXnsBaseAdjacencyHostid OBJECT-TYPE
        SYNTAX	OCTET STRING (SIZE (6))
        ACCESS	read-only
        STATUS	mandatory
        DESCRIPTION
                "Adjacent Router's/Host's hostid for which a hello has been received."
        ::= { wfXnsBaseAdjEntry 2 }

    wfXnsBaseAdjacencyCost OBJECT-TYPE
        SYNTAX	INTEGER
        ACCESS	read-only
        STATUS	mandatory
        DESCRIPTION
                "Cost associated with reaching this adjacency."
        ::= { wfXnsBaseAdjEntry 3 }

    wfXnsBaseAdjacencyAge OBJECT-TYPE
        SYNTAX	INTEGER
        ACCESS	read-only
        STATUS	mandatory
        DESCRIPTION
                "Adjacent Router/Host for which a hello has been received."
        ::= { wfXnsBaseAdjEntry 4 }

    wfXnsBaseAdjacencyIntf OBJECT-TYPE
        SYNTAX	OCTET STRING
        ACCESS	read-only
        STATUS	mandatory
        DESCRIPTION
                "XNS Network interface."
        ::= { wfXnsBaseAdjEntry 5 }

    wfXnsBaseAdjacencyCct OBJECT-TYPE
        SYNTAX	INTEGER
        ACCESS	read-only
        STATUS	mandatory
        DESCRIPTION
                "Circuit on which hello was received."
        ::= { wfXnsBaseAdjEntry 6 }

    wfXnsBaseRtEntryTable OBJECT-TYPE
        SYNTAX	SEQUENCE OF WfXnsBaseRtEntry
        ACCESS	not-accessible
        STATUS	mandatory
        DESCRIPTION
                "The table of Elements in XNS's routing table"
        ::= { wfXnsGroup 2 }

    wfXnsBaseRtEntry OBJECT-TYPE
        SYNTAX	WfXnsBaseRtEntry
        ACCESS	not-accessible
        STATUS	mandatory
        DESCRIPTION
                "An entry in the Routing Table"
        INDEX	{ wfXnsBaseRouteDest }
        ::= { wfXnsBaseRtEntryTable 1 }

    WfXnsBaseRtEntry ::= SEQUENCE {
    	    wfXnsBaseRouteDest
    		OCTET STRING,
    	    wfXnsBaseRouteIfIndex
    		INTEGER,
    	    wfXnsBaseRouteMetric
    		INTEGER,
    	    wfXnsBaseRouteNextHopNetwork
    		OCTET STRING,
    	    wfXnsBaseRouteNextHopHost
    		OCTET STRING,
    	    wfXnsBaseRouteType
    		INTEGER,
    	    wfXnsBaseRouteProto
    		INTEGER,
    	    wfXnsBaseRouteAge
    		INTEGER,
    	    wfXnsBaseRouteInfo
    		OCTET STRING
        }

    wfXnsBaseRouteDest OBJECT-TYPE
        SYNTAX	OCTET STRING (SIZE (4))
        ACCESS	read-only
        STATUS	mandatory
        DESCRIPTION
                "The destination XNS address of this route.  An
                entry with a value of 0.0.0.0 is considered a
                default route.  Multiple routes to a single
                destination can appear in the table, but access to
                such multiple entries is dependent on the table-
                access mechanisms defined by the network
                management protocol in use."
        ::= { wfXnsBaseRtEntry 1 }

    wfXnsBaseRouteIfIndex OBJECT-TYPE
        SYNTAX	INTEGER
        ACCESS	read-only
        STATUS	mandatory
        DESCRIPTION
                "The index value which uniquely identifies the
                local interface through which the next hop of this
                route should be reached.  The interface identified
                by a particular value of this index is the same
                interface as identified by the same value of
                ifIndex."
        ::= { wfXnsBaseRtEntry 2 }

    wfXnsBaseRouteMetric OBJECT-TYPE
        SYNTAX	INTEGER
        ACCESS	read-only
        STATUS	mandatory
        DESCRIPTION
                "The primary routing metric for this route.  The
                semantics of this metric are determined by the
                routing-protocol specified in the route's
                XnsBaseRouteProto value.  If this metric is not used,
                its value should be set to -1."
        ::= { wfXnsBaseRtEntry 3 }

    wfXnsBaseRouteNextHopNetwork OBJECT-TYPE
        SYNTAX	OCTET STRING
        ACCESS	read-only
        STATUS	mandatory
        DESCRIPTION
                "(In the case of a route bound to an interface
                which is realized via a broadcast media, the value
                of this field is the agent's XNS address on that
                interface.)"
        ::= { wfXnsBaseRtEntry 4 }

    wfXnsBaseRouteNextHopHost OBJECT-TYPE
        SYNTAX	OCTET STRING
        ACCESS	read-only
        STATUS	mandatory
        DESCRIPTION
                "Full network.host_id address of nexthop host for
                this network."
        ::= { wfXnsBaseRtEntry 5 }

    wfXnsBaseRouteType OBJECT-TYPE
        SYNTAX	INTEGER {
    		    other(1),
    		    invalid(2),
    		    direct(3),
    		    indirect(4),
    		    static(5)
    		}
        ACCESS	read-only
        STATUS	mandatory
        DESCRIPTION
                "The type of route.  Note that the values
                direct(3) and indirect(4) refer to the notion of
                direct and indirect routing in the XNS
                architecture.
                "
        ::= { wfXnsBaseRtEntry 6 }

    wfXnsBaseRouteProto OBJECT-TYPE
        SYNTAX	INTEGER {
    		    other(1),
    		    local(2),
    		    netmgmt(3),
    		    rip(4)
    		}
        ACCESS	read-only
        STATUS	mandatory
        DESCRIPTION
                "The routing mechanism via which this route was
                learned.  Inclusion of values for gateway routing
                protocols is not intended to imply that hosts
                should support those protocols."
        ::= { wfXnsBaseRtEntry 7 }

    wfXnsBaseRouteAge OBJECT-TYPE
        SYNTAX	INTEGER
        ACCESS	read-only
        STATUS	mandatory
        DESCRIPTION
                "The number of seconds since this route was last
                updated or otherwise determined to be correct.
                Note that no semantics of `too old' can be implied
                except through knowledge of the routing protocol
                by which the route was learned."
        ::= { wfXnsBaseRtEntry 8 }

    wfXnsBaseRouteInfo OBJECT-TYPE
        SYNTAX	OCTET STRING
        ACCESS	read-only
        STATUS	mandatory
        DESCRIPTION
                "A user-defined string which describes this Route entry"
        ::= { wfXnsBaseRtEntry 9 }

    wfXnsInterfaceTable OBJECT-TYPE
        SYNTAX	SEQUENCE OF WfXnsInterfaceEntry
        ACCESS	not-accessible
        STATUS	mandatory
        DESCRIPTION
                "The network interface record"
        ::= { wfXnsGroup 3 }

    wfXnsInterfaceEntry OBJECT-TYPE
        SYNTAX	WfXnsInterfaceEntry
        ACCESS	not-accessible
        STATUS	mandatory
        DESCRIPTION
                "An entry in the Routing Table"
        INDEX	{ wfXnsInterfaceNetworkNumber,
    		  wfXnsInterfaceCircuit }
        ::= { wfXnsInterfaceTable 1 }

    WfXnsInterfaceEntry ::= SEQUENCE {
    	    wfXnsInterfaceIndex
    		INTEGER,
    	    wfXnsInterfaceDelete
    		INTEGER,
    	    wfXnsInterfaceDisable
    		INTEGER,
    	    wfXnsInterfaceState
    		INTEGER,
    	    wfXnsInterfaceCircuit
    		INTEGER,
    	    wfXnsInterfaceNetworkNumber
    		OCTET STRING,
    	    wfXnsInterfaceCost
    		INTEGER,
    	    wfXnsInterfaceXsumOn
    		INTEGER,
    	    wfXnsInterfaceEncaps
    		INTEGER,
    	    wfXnsInterfaceMacAddress
    		OCTET STRING,
    	    wfXnsInterfaceSMDSGroupAddress
    		OCTET STRING,
    	    wfXnsInterfaceMaxInfo
    		INTEGER,
    	    wfXnsInterfaceExtServer
    		INTEGER,
    	    wfXnsInterfaceExServNetwork
    		OCTET STRING,
    	    wfXnsInterfaceExServHostId
    		OCTET STRING,
    	    wfXnsInterfaceExServPktType
    		OCTET STRING,
    	    wfXnsInterfaceExServSockNm
    		OCTET STRING,
    	    wfXnsInterfaceInReceives
    		Counter,
    	    wfXnsInterfaceInHdrErrors
    		Counter,
    	    wfXnsInterfaceInAddrErrors
    		Counter,
    	    wfXnsInterfaceForwDatagrams
    		Counter,
    	    wfXnsInterfaceInUnknownProtos
    		Counter,
    	    wfXnsInterfaceInDiscards
    		Counter,
    	    wfXnsInterfaceInDelivers
    		Counter,
    	    wfXnsInterfaceOutRequests
    		Counter,
    	    wfXnsInterfaceOutDiscards
    		Counter,
    	    wfXnsInterfaceOutNoRoutes
    		Counter,
    	    wfXnsInterfaceFRBcast
    		OCTET STRING,
    	    wfXnsInterfaceFRMcast
    		OCTET STRING,
    	    wfXnsInterfaceSplit
    		INTEGER
        }

    wfXnsInterfaceIndex OBJECT-TYPE
        SYNTAX	INTEGER
        ACCESS	read-only
        STATUS	mandatory
        DESCRIPTION
                "A unique value for each XNS interface.  Its value
                ranges between 1 and the value of MAXCIRCUITS."
        ::= { wfXnsInterfaceEntry 1 }

    wfXnsInterfaceDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete an XNS interface."
        DEFVAL	{ created }
        ::= { wfXnsInterfaceEntry 2 }

    wfXnsInterfaceDisable OBJECT-TYPE
        SYNTAX	INTEGER {
    		    enabled(1),
    		    disabled(2)
    		}
        ACCESS	read-write
        STATUS	mandatory
        DESCRIPTION
                "Enable/Disable parameter. Default is enabled.
                Users perform an SNMP SET operation on this
                object in order to enable/disable an XNS interface."
        DEFVAL	{ enabled }
        ::= { wfXnsInterfaceEntry 3 }

    wfXnsInterfaceState OBJECT-TYPE
        SYNTAX	INTEGER {
    		    up(1),
    		    down(2),
    		    init(3),
    		    notpresent(4)
    		}
        ACCESS	read-only
        STATUS	mandatory
        DESCRIPTION
                "The current state of the XNS interface"
        DEFVAL	{ notpresent }
        ::= { wfXnsInterfaceEntry 4 }

    wfXnsInterfaceCircuit OBJECT-TYPE
        SYNTAX	INTEGER
        ACCESS	read-only
        STATUS	mandatory
        DESCRIPTION
                "The Circuit Number that this interface runs over"
        ::= { wfXnsInterfaceEntry 5 }

    wfXnsInterfaceNetworkNumber OBJECT-TYPE
        SYNTAX	OCTET STRING (SIZE (4))
        ACCESS	read-only
        STATUS	mandatory
        DESCRIPTION
                "The XNS Address to which this entry's addressing
                information pertains."
        ::= { wfXnsInterfaceEntry 6 }

    wfXnsInterfaceCost OBJECT-TYPE
        SYNTAX	INTEGER
        ACCESS	read-write
        STATUS	mandatory
        DESCRIPTION
                "The Cost associated with the XNS Address of this entry"
        ::= { wfXnsInterfaceEntry 7 }

    wfXnsInterfaceXsumOn OBJECT-TYPE
        SYNTAX	INTEGER {
    		    enabled(1),
    		    disabled(2)
    		}
        ACCESS	read-write
        STATUS	mandatory
        DESCRIPTION
                "Flag for checksums"
        DEFVAL	{ enabled }
        ::= { wfXnsInterfaceEntry 8 }

    wfXnsInterfaceEncaps OBJECT-TYPE
        SYNTAX	INTEGER {
    		    ethernet(1),
    		    snap(2)
    		}
        ACCESS	read-only
        STATUS	mandatory
        DESCRIPTION
                "chosen by the XNS implementation according to underlying media."
        DEFVAL	{ ethernet }
        ::= { wfXnsInterfaceEntry 9 }

    wfXnsInterfaceMacAddress OBJECT-TYPE
        SYNTAX	OCTET STRING
        ACCESS	read-write
        STATUS	mandatory
        DESCRIPTION
                "The MacAddress of this interface
                this port will receive or transmit."
        ::= { wfXnsInterfaceEntry 10 }

    wfXnsInterfaceSMDSGroupAddress OBJECT-TYPE
        SYNTAX	OCTET STRING
        ACCESS	read-write
        STATUS	mandatory
        DESCRIPTION
                "The SMDS Group Address of this interface
                this port will receive or transmit."
        ::= { wfXnsInterfaceEntry 11 }

    wfXnsInterfaceMaxInfo OBJECT-TYPE
        SYNTAX	INTEGER
        ACCESS	read-only
        STATUS	mandatory
        DESCRIPTION
                "The maximum size of the INFO (non-MAC) field
                that this port will receive or transmit."
        ::= { wfXnsInterfaceEntry 12 }

    wfXnsInterfaceExtServer OBJECT-TYPE
        SYNTAX	INTEGER {
    		    enabled(1),
    		    disabled(2)
    		}
        ACCESS	read-write
        STATUS	mandatory
        DESCRIPTION
                "Flag indicating if this interface has External server
                capabilities turned on. Allows interface to pass on
                defined packets, such as PEP/TP requests, to a
                remote server not located on local network."
        DEFVAL	{ disabled }
        ::= { wfXnsInterfaceEntry 13 }

    wfXnsInterfaceExServNetwork OBJECT-TYPE
        SYNTAX	OCTET STRING
        ACCESS	read-write
        STATUS	mandatory
        DESCRIPTION
                "The Network address of the remote server."
        ::= { wfXnsInterfaceEntry 14 }

    wfXnsInterfaceExServHostId OBJECT-TYPE
        SYNTAX	OCTET STRING
        ACCESS	read-write
        STATUS	mandatory
        DESCRIPTION
                "The Host ID of the remote server."
        ::= { wfXnsInterfaceEntry 15 }

    wfXnsInterfaceExServPktType OBJECT-TYPE
        SYNTAX	OCTET STRING
        ACCESS	read-write
        STATUS	mandatory
        DESCRIPTION
                "The packet type of the requests which are to be
                passed on to the specified remote server."
        ::= { wfXnsInterfaceEntry 16 }

    wfXnsInterfaceExServSockNm OBJECT-TYPE
        SYNTAX	OCTET STRING
        ACCESS	read-write
        STATUS	mandatory
        DESCRIPTION
                "The destination socket number of the requests which
                are to be passed on to the specified remote server.
                If no socket number is specified then all packets
                of the specified type that this interface receives
                will be forwarded to specified remote server.
                "
        ::= { wfXnsInterfaceEntry 17 }

    wfXnsInterfaceInReceives OBJECT-TYPE
        SYNTAX	Counter
        ACCESS	read-only
        STATUS	mandatory
        DESCRIPTION
                "The total number of input datagrams received from
                interfaces, including those received in error."
        ::= { wfXnsInterfaceEntry 18 }

    wfXnsInterfaceInHdrErrors OBJECT-TYPE
        SYNTAX	Counter
        ACCESS	read-only
        STATUS	mandatory
        DESCRIPTION
                "The number of input datagrams discarded due to
                errors in their XNS headers, including bad
                checksums, version number mismatch, other format
                errors, time-to-live exceeded, errors discovered
                in processing their XNS options, etc."
        ::= { wfXnsInterfaceEntry 19 }

    wfXnsInterfaceInAddrErrors OBJECT-TYPE
        SYNTAX	Counter
        ACCESS	read-only
        STATUS	mandatory
        DESCRIPTION
                "The number of input datagrams discarded because
                the XNS address in their XNS header's destination
                field was not a valid address to be received at
                this entity.This counter includes datagrams
                discarded because the destination address was not
                a local address."
        ::= { wfXnsInterfaceEntry 20 }

    wfXnsInterfaceForwDatagrams OBJECT-TYPE
        SYNTAX	Counter
        ACCESS	read-only
        STATUS	mandatory
        DESCRIPTION
                "The number of input datagrams for which this
                entity was not their final XNS destination, as a
                result of which an attempt was made to find a
                route to forward them to that final destination.
                In entities which do not act as XNS Gateways, this
                counter will include only those packets which were
                Source-Routed via this entity, and the Source-
                Route option processing was successful."
        ::= { wfXnsInterfaceEntry 21 }

    wfXnsInterfaceInUnknownProtos OBJECT-TYPE
        SYNTAX	Counter
        ACCESS	read-only
        STATUS	mandatory
        DESCRIPTION
                "The number of locally-addressed datagrams
                received successfully but discarded because of an
                unknown or unsupported protocol."
        ::= { wfXnsInterfaceEntry 22 }

    wfXnsInterfaceInDiscards OBJECT-TYPE
        SYNTAX	Counter
        ACCESS	read-only
        STATUS	mandatory
        DESCRIPTION
                "The number of input XNS datagrams for which no
                problems were encountered to prevent their
                continued processing, but which were discarded
                (e.g., for lack of buffer space).  Note that this
                counter does not include any datagrams discarded
                while awaiting re-assembly."
        ::= { wfXnsInterfaceEntry 23 }

    wfXnsInterfaceInDelivers OBJECT-TYPE
        SYNTAX	Counter
        ACCESS	read-only
        STATUS	mandatory
        DESCRIPTION
                "The total number of input datagrams successfully
                delivered to XNS user-protocols (including ECHO)"
        ::= { wfXnsInterfaceEntry 24 }

    wfXnsInterfaceOutRequests OBJECT-TYPE
        SYNTAX	Counter
        ACCESS	read-only
        STATUS	mandatory
        DESCRIPTION
                "The total number of XNS datagrams which local XNS
                user-protocols supplied to XNS in
                requests for transmission.  Note that this counter
                does not include any datagrams counted in
                XnsInteraceFwdDatagrams."
        ::= { wfXnsInterfaceEntry 25 }

    wfXnsInterfaceOutDiscards OBJECT-TYPE
        SYNTAX	Counter
        ACCESS	read-only
        STATUS	mandatory
        DESCRIPTION
                "The number of output XNS datagrams for which no
                problem was encountered to prevent their
                transmission to their destination, but which were
                discarded (e.g., for lack of buffer space).  Note
                that this counter would include datagrams counted
                in XnsForwDatagrams if any such packets met this
                (discretionary) discard criterion."
        ::= { wfXnsInterfaceEntry 26 }

    wfXnsInterfaceOutNoRoutes OBJECT-TYPE
        SYNTAX	Counter
        ACCESS	read-only
        STATUS	mandatory
        DESCRIPTION
                "The number of XNS datagrams discarded because no
                route could be found to transmit them to their
                destination.  Note that this counter includes any
                packets counted in ForwDatagrams which meet this
                `no-route' criterion.  Note that this includes any
                datagarms which a host cannot route because all of
                its default gateways are down."
        ::= { wfXnsInterfaceEntry 27 }

    wfXnsInterfaceFRBcast OBJECT-TYPE
        SYNTAX	OCTET STRING
        ACCESS	read-write
        STATUS	mandatory
        DESCRIPTION
                "Configurable Frame Relay broadcast address"
        ::= { wfXnsInterfaceEntry 28 }

    wfXnsInterfaceFRMcast OBJECT-TYPE
        SYNTAX	OCTET STRING
        ACCESS	read-write
        STATUS	mandatory
        DESCRIPTION
                "Configurable Frame Relay multicast address"
        ::= { wfXnsInterfaceEntry 29 }

    wfXnsInterfaceSplit OBJECT-TYPE
        SYNTAX	INTEGER {
    		    enabled(1),
    		    disabled(2)
    		}
        ACCESS	read-write
        STATUS	mandatory
        DESCRIPTION
                "Enable or Disable Split Horizon algorithm for this interface
                Comes into to play for non full-meshed WAN networks (Frame Relay) "
        DEFVAL	{ enabled }
        ::= { wfXnsInterfaceEntry 30 }

    wfXnsRipIntfTable OBJECT-TYPE
        SYNTAX	SEQUENCE OF WfXnsRipIntfEntry
        ACCESS	not-accessible
        STATUS	mandatory
        DESCRIPTION
                "The list of RIP interfaces"
        ::= { wfXnsGroup 4 }

    wfXnsRipIntfEntry OBJECT-TYPE
        SYNTAX	WfXnsRipIntfEntry
        ACCESS	not-accessible
        STATUS	mandatory
        DESCRIPTION
                "An entry in the Routing Table"
        INDEX	{ wfXnsRipInterfaceIndex }
        ::= { wfXnsRipIntfTable 1 }

    WfXnsRipIntfEntry ::= SEQUENCE {
    	    wfXnsRipInterfaceDelete
    		INTEGER,
    	    wfXnsRipInterfaceDisable
    		INTEGER,
    	    wfXnsRipInterfaceState
    		INTEGER,
    	    wfXnsRipInterfaceIndex
    		OCTET STRING,
    	    wfXnsRipInterfaceSupply
    		INTEGER,
    	    wfXnsRipInterfaceListen
    		INTEGER
        }

    wfXnsRipInterfaceDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete an RIP Interface instance."
        DEFVAL	{ created }
        ::= { wfXnsRipIntfEntry 1 }

    wfXnsRipInterfaceDisable OBJECT-TYPE
        SYNTAX	INTEGER {
    		    enabled(1),
    		    disabled(2)
    		}
        ACCESS	read-write
        STATUS	mandatory
        DESCRIPTION
                "Enable/Disable parameter. Default is enabled.
                Users perform an SNMP SET operation on this
                object in order to enable/disable a RIP instance."
        DEFVAL	{ enabled }
        ::= { wfXnsRipIntfEntry 2 }

    wfXnsRipInterfaceState OBJECT-TYPE
        SYNTAX	INTEGER {
    		    up(1),
    		    down(2),
    		    init(3),
    		    notpresent(4)
    		}
        ACCESS	read-only
        STATUS	mandatory
        DESCRIPTION
                "The current state of RIP on this interface."
        DEFVAL	{ notpresent }
        ::= { wfXnsRipIntfEntry 3 }

    wfXnsRipInterfaceIndex OBJECT-TYPE
        SYNTAX	OCTET STRING (SIZE (4))
        ACCESS	read-only
        STATUS	mandatory
        DESCRIPTION
                "The XNS interface to run RIP on."
        ::= { wfXnsRipIntfEntry 4 }

    wfXnsRipInterfaceSupply OBJECT-TYPE
        SYNTAX	INTEGER {
    		    enabled(1),
    		    disabled(2)
    		}
        ACCESS	read-write
        STATUS	mandatory
        DESCRIPTION
                "Transmit RIP packets."
        DEFVAL	{ enabled }
        ::= { wfXnsRipIntfEntry 5 }

    wfXnsRipInterfaceListen OBJECT-TYPE
        SYNTAX	INTEGER {
    		    enabled(1),
    		    disabled(2)
    		}
        ACCESS	read-write
        STATUS	mandatory
        DESCRIPTION
                "Receive RIP packets."
        DEFVAL	{ enabled }
        ::= { wfXnsRipIntfEntry 6 }

    wfXnsAdjacentHostTable OBJECT-TYPE
        SYNTAX	SEQUENCE OF WfXnsAdjacentHostEntry
        ACCESS	not-accessible
        STATUS	mandatory
        DESCRIPTION
                "must be configured for a nexthop host."
        ::= { wfXnsGroup 5 }

    wfXnsAdjacentHostEntry OBJECT-TYPE
        SYNTAX	WfXnsAdjacentHostEntry
        ACCESS	not-accessible
        STATUS	mandatory
        DESCRIPTION
                "An entry in the Adjacent Host Table"
        INDEX	{ wfXnsAhTargHostNetwork,
    		  wfXnsAhTargHostId }
        ::= { wfXnsAdjacentHostTable 1 }

    WfXnsAdjacentHostEntry ::= SEQUENCE {
    	    wfXnsAhDelete
    		INTEGER,
    	    wfXnsAhDisable
    		INTEGER,
    	    wfXnsAhTargHostNetwork
    		OCTET STRING,
    	    wfXnsAhTargHostId
    		OCTET STRING,
    	    wfXnsAhNextHopIntf
    		OCTET STRING,
    	    wfXnsAhDlci
    		OCTET STRING
        }

    wfXnsAhDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete the XNS
                Static Host."
        DEFVAL	{ created }
        ::= { wfXnsAdjacentHostEntry 1 }

    wfXnsAhDisable OBJECT-TYPE
        SYNTAX	INTEGER {
    		    enabled(1),
    		    disabled(2)
    		}
        ACCESS	read-write
        STATUS	mandatory
        DESCRIPTION
                "Enable/Disable parameter. Default is enabled.
                Users perform an SNMP SET operation on this
                object in order to enable/disable this XNS
                Static Route."
        DEFVAL	{ enabled }
        ::= { wfXnsAdjacentHostEntry 2 }

    wfXnsAhTargHostNetwork OBJECT-TYPE
        SYNTAX	OCTET STRING (SIZE (4))
        ACCESS	read-only
        STATUS	mandatory
        DESCRIPTION
                "The network address of the static host."
        ::= { wfXnsAdjacentHostEntry 3 }

    wfXnsAhTargHostId OBJECT-TYPE
        SYNTAX	OCTET STRING (SIZE (6))
        ACCESS	read-only
        STATUS	mandatory
        DESCRIPTION
                "The Address of this static host."
        ::= { wfXnsAdjacentHostEntry 4 }

    wfXnsAhNextHopIntf OBJECT-TYPE
        SYNTAX	OCTET STRING
        ACCESS	read-write
        STATUS	mandatory
        DESCRIPTION
                "The Next Hop Interface Network Address"
        ::= { wfXnsAdjacentHostEntry 5 }

    wfXnsAhDlci OBJECT-TYPE
        SYNTAX	OCTET STRING
        ACCESS	read-write
        STATUS	mandatory
        DESCRIPTION
                "The next Hop Host address"
        ::= { wfXnsAdjacentHostEntry 6 }

    wfXnsStaticRouteTable OBJECT-TYPE
        SYNTAX	SEQUENCE OF WfXnsStaticRouteEntry
        ACCESS	not-accessible
        STATUS	mandatory
        DESCRIPTION
                "The list of Adjacent Hosts used for Configuring XNS"
        ::= { wfXnsGroup 6 }

    wfXnsStaticRouteEntry OBJECT-TYPE
        SYNTAX	WfXnsStaticRouteEntry
        ACCESS	not-accessible
        STATUS	mandatory
        DESCRIPTION
                "An entry in the Host Table"
        INDEX	{ wfXnsSrTargNetwork,
    		  wfXnsSrNextHopNetwork }
        ::= { wfXnsStaticRouteTable 1 }

    WfXnsStaticRouteEntry ::= SEQUENCE {
    	    wfXnsSrDelete
    		INTEGER,
    	    wfXnsSrDisable
    		INTEGER,
    	    wfXnsSrTargNetwork
    		OCTET STRING,
    	    wfXnsSrCost
    		INTEGER,
    	    wfXnsSrNextHopNetwork
    		OCTET STRING,
    	    wfXnsSrNextHopHost
    		OCTET STRING,
    	    wfXnsSrTargNetworkRt
    		INTEGER
        }

    wfXnsSrDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete the XNS
                Static Route."
        DEFVAL	{ created }
        ::= { wfXnsStaticRouteEntry 1 }

    wfXnsSrDisable OBJECT-TYPE
        SYNTAX	INTEGER {
    		    enabled(1),
    		    disabled(2)
    		}
        ACCESS	read-write
        STATUS	mandatory
        DESCRIPTION
                "Enable/Disable parameter. Default is enabled.
                Users perform an SNMP SET operation on this
                object in order to enable/disable this XNS
                Static Route."
        DEFVAL	{ enabled }
        ::= { wfXnsStaticRouteEntry 2 }

    wfXnsSrTargNetwork OBJECT-TYPE
        SYNTAX	OCTET STRING (SIZE (4))
        ACCESS	read-only
        STATUS	mandatory
        DESCRIPTION
                "The Address of this static route"
        ::= { wfXnsStaticRouteEntry 3 }

    wfXnsSrCost OBJECT-TYPE
        SYNTAX	INTEGER
        ACCESS	read-write
        STATUS	mandatory
        DESCRIPTION
                "The Cost of this Static Route"
        ::= { wfXnsStaticRouteEntry 4 }

    wfXnsSrNextHopNetwork OBJECT-TYPE
        SYNTAX	OCTET STRING (SIZE (4))
        ACCESS	read-only
        STATUS	mandatory
        DESCRIPTION
                "The Next Hop XNS Address"
        ::= { wfXnsStaticRouteEntry 5 }

    wfXnsSrNextHopHost OBJECT-TYPE
        SYNTAX	OCTET STRING
        ACCESS	read-write
        STATUS	mandatory
        DESCRIPTION
                "The next Hop Host address"
        ::= { wfXnsStaticRouteEntry 6 }

    wfXnsSrTargNetworkRt OBJECT-TYPE
        SYNTAX	INTEGER
        ACCESS	read-only
        STATUS	mandatory
        DESCRIPTION
                "The Route Identifier Which numbered route this is to be"
        ::= { wfXnsStaticRouteEntry 7 }

    wfXnsTrafficFilterTable OBJECT-TYPE
        SYNTAX	SEQUENCE OF WfXnsTrafficFilterEntry
        ACCESS	not-accessible
        STATUS	mandatory
        DESCRIPTION
                "XNS Traffic Filters"
        ::= { wfXnsGroup 7 }

    wfXnsTrafficFilterEntry OBJECT-TYPE
        SYNTAX	WfXnsTrafficFilterEntry
        ACCESS	not-accessible
        STATUS	mandatory
        DESCRIPTION
                "A traffic filter definition"
        INDEX	{ wfXnsTrafficFilterInterface,
    		  wfXnsTrafficFilterCircuit,
    		  wfXnsTrafficFilterRuleNumber,
    		  wfXnsTrafficFilterFragment }
        ::= { wfXnsTrafficFilterTable 1 }

    WfXnsTrafficFilterEntry ::= SEQUENCE {
    	    wfXnsTrafficFilterCreate
    		INTEGER,
    	    wfXnsTrafficFilterEnable
    		INTEGER,
    	    wfXnsTrafficFilterStatus
    		INTEGER,
    	    wfXnsTrafficFilterCounter
    		Counter,
    	    wfXnsTrafficFilterDefinition
    		Opaque,
    	    wfXnsTrafficFilterReserved
    		INTEGER,
    	    wfXnsTrafficFilterInterface
    		OCTET STRING,
    	    wfXnsTrafficFilterCircuit
    		INTEGER,
    	    wfXnsTrafficFilterRuleNumber
    		INTEGER,
    	    wfXnsTrafficFilterFragment
    		INTEGER,
    	    wfXnsTrafficFilterName
    		DisplayString
        }

    wfXnsTrafficFilterCreate OBJECT-TYPE
        SYNTAX	INTEGER {
    		    created(1),
    		    deleted(2)
    		}
        ACCESS	read-write
        STATUS	mandatory
        DESCRIPTION
                "Defines the existence of the traffic filter rule:
                created - traffic filter exists
                delete - traffic filter does not exist and can be deleted."
        DEFVAL	{ created }
        ::= { wfXnsTrafficFilterEntry 1 }

    wfXnsTrafficFilterEnable OBJECT-TYPE
        SYNTAX	INTEGER {
    		    enabled(1),
    		    disabled(2)
    		}
        ACCESS	read-write
        STATUS	mandatory
        DESCRIPTION
                "Defines whether or not the traffic filter rule should be used:
                enabled - activate the rule.
                disabled - inactivate the rule."
        DEFVAL	{ enabled }
        ::= { wfXnsTrafficFilterEntry 2 }

    wfXnsTrafficFilterStatus OBJECT-TYPE
        SYNTAX	INTEGER {
    		    active(1),
    		    error(2),
    		    inactive(3)
    		}
        ACCESS	read-only
        STATUS	mandatory
        DESCRIPTION
                "Defines the current status of the traffic filter:
                inactive - the rule is not in use.
                active - the rule is being used.
                error - the application detected an error in the rule."
        DEFVAL	{ inactive }
        ::= { wfXnsTrafficFilterEntry 3 }

    wfXnsTrafficFilterCounter OBJECT-TYPE
        SYNTAX	Counter
        ACCESS	read-only
        STATUS	mandatory
        DESCRIPTION
                "The number of received packets that have
                matched this rule."
        ::= { wfXnsTrafficFilterEntry 4 }

    wfXnsTrafficFilterDefinition OBJECT-TYPE
        SYNTAX	Opaque
        ACCESS	read-write
        STATUS	mandatory
        DESCRIPTION
                "The filter rule definition."
        ::= { wfXnsTrafficFilterEntry 5 }

    wfXnsTrafficFilterReserved OBJECT-TYPE
        SYNTAX	INTEGER
        ACCESS	read-only
        STATUS	mandatory
        DESCRIPTION
                "Reserved field."
        ::= { wfXnsTrafficFilterEntry 6 }

    wfXnsTrafficFilterInterface OBJECT-TYPE
        SYNTAX	OCTET STRING (SIZE (4))
        ACCESS	read-only
        STATUS	mandatory
        DESCRIPTION
                "The network address of the XNS
                interface to which this filter is applied."
        ::= { wfXnsTrafficFilterEntry 7 }

    wfXnsTrafficFilterCircuit OBJECT-TYPE
        SYNTAX	INTEGER
        ACCESS	read-only
        STATUS	mandatory
        DESCRIPTION
                "The ID of the Circuit to which the
                filter is applied."
        ::= { wfXnsTrafficFilterEntry 8 }

    wfXnsTrafficFilterRuleNumber OBJECT-TYPE
        SYNTAX	INTEGER
        ACCESS	read-only
        STATUS	mandatory
        DESCRIPTION
                "ID for the rule."
        ::= { wfXnsTrafficFilterEntry 9 }

    wfXnsTrafficFilterFragment OBJECT-TYPE
        SYNTAX	INTEGER
        ACCESS	read-only
        STATUS	mandatory
        DESCRIPTION
                "Fragment number - for large rules."
        ::= { wfXnsTrafficFilterEntry 10 }

    wfXnsTrafficFilterName OBJECT-TYPE
        SYNTAX	DisplayString
        ACCESS	read-write
        STATUS	mandatory
        DESCRIPTION
                "Name of the rule number."
        ::= { wfXnsTrafficFilterEntry 11 }

    wfXnsAggrStats	OBJECT IDENTIFIER ::= { wfXnsGroup 9 }

    wfXnsAggrInDatagrams OBJECT-TYPE
        SYNTAX	Counter
        ACCESS	read-only
        STATUS	mandatory
        DESCRIPTION
                "The total number of datagrams received"
        ::= { wfXnsAggrStats 1 }

    wfXnsAggrOutDatagrams OBJECT-TYPE
        SYNTAX	Counter
        ACCESS	read-only
        STATUS	mandatory
        DESCRIPTION
                "The total number of datagrams sent (includes datagrams
                forwarded)"
        ::= { wfXnsAggrStats 2 }

    wfXnsAggrFwdDatagrams OBJECT-TYPE
        SYNTAX	Counter
        ACCESS	read-only
        STATUS	mandatory
        DESCRIPTION
                "The total number of datagrams forwarded"
        ::= { wfXnsAggrStats 3 }

    wfXnsAggrInDiscards OBJECT-TYPE
        SYNTAX	Counter
        ACCESS	read-only
        STATUS	mandatory
        DESCRIPTION
                "The total number of datagrams queued for reception that
                were discarded for resource reasons"
        ::= { wfXnsAggrStats 4 }

    wfXnsAggrInHdrErrs OBJECT-TYPE
        SYNTAX	Counter
        ACCESS	read-only
        STATUS	mandatory
        DESCRIPTION
                "The total number of datagrams discarded because of errors
                in the XNS header."
        ::= { wfXnsAggrStats 5 }

    wfXnsAggrInAddrErrs OBJECT-TYPE
        SYNTAX	Counter
        ACCESS	read-only
        STATUS	mandatory
        DESCRIPTION
                "The total nmber of datagrams received whose destination
                address was invalid for this entity."
        ::= { wfXnsAggrStats 6 }

    wfXnsAggrInUnknownProtos OBJECT-TYPE
        SYNTAX	Counter
        ACCESS	read-only
        STATUS	mandatory
        DESCRIPTION
                "The total number of datagrams received locally which
                specified an unknown or unsupported protocol."
        ::= { wfXnsAggrStats 7 }

    wfXnsAggrOutDiscards OBJECT-TYPE
        SYNTAX	Counter
        ACCESS	read-only
        STATUS	mandatory
        DESCRIPTION
                "The total number of datagrams queued for transmission
                that were discarded for resource reasons."
        ::= { wfXnsAggrStats 8 }

    wfXnsAggrOutNoRoutes OBJECT-TYPE
        SYNTAX	Counter
        ACCESS	read-only
        STATUS	mandatory
        DESCRIPTION
                "The total number of datagrams queued for transmission thet
                were discarded because the destination was unreachable."
        ::= { wfXnsAggrStats 9 }

    END  -- Wellfleet-XNS-MIB
