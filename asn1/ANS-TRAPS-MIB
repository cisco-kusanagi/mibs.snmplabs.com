--*********************************************************************
-- Copyright: Ericsson Telecom AB 1997-2000
-- Doc no: 122/190 55-CAA 134 74 Uen
--
-- Copyright: Ericsson Lab Italy S.p.A 2000
-- Doc no: 122/190 55-CAA 134 0238 Uen
--
--
-- NAME ANS-TRAPS-MIB.mib
--
-- REVISION HISTORY
--
-- Revision: PA1, 97-02-11, new traps added for the ADSL application.
-- Revision: PA2, 97-02-26, new traps added, incorrectSWVersion,
--	 		    loopBackFailure, vpAIS and vpRDI
--
-- REV	Date	Name	Reason
-- PA3	970603	etxtpet	Some definitions only concerning traps
--			moved in from equipment and alarm mibs.
-- PA4	970616	etxtpet	Trap names changed to fit the MRI spec.
--			eventTime added in all events.
--			Some warning alarms added.
-- PA5	970623	etxtpet	Variables access changed to not-accessible.
-- PA6	970626	etxtpet	softwareDownloadInProgress and
--			softwareDownloadDone added.
-- PA7	970821	etxtpet	The ansIdentifierString and the alarmingObjString
--			removed. The display string is from now on assembled
--			in the manager. ansIdentifier added to the
--			ntDisconnected and signOnComplete variables.
-- PA8	970918	etxtpet	cellbusPortDefect removed.
-- PA9	971016	etxtpet	msAis, msRdi, pathRdi, pathAis added.
-- PA10	980123	etxtpet	los15minuteThreshold, los24hourThreshold,
--			lof15minuteThreshold, lof24hourThreshold,
--			es15minuteThreshold, es24hourThreshold,
--			locd15minuteThreshold, locd24hourThreshold, snrMargin
--			changed from alarm to event.
--			losEvent, lofEvent, lossOfCellDelineationEvent,
--			sesEvent, powerLossEvent added.
-- PB1  980427  etxsnma los15minuteThreshold, los24hourThreshold,
--			lof15minuteThreshold, lof24hourThreshold,
--			es15minuteThreshold, es24hourThreshold,
--			locd15minuteThreshold, locd24hourThreshold
--			and snrMargin changed from event to alarm.
--			ntMismatch, lol, minimumRateNotReached,
--			lol15minuteThreshold, lol24hourThreshold,
--			lopwr15minuteThreshold and lopwr24hourThreshold
--			alarm added.
--			lolEvent event added.
-- PB2  980610  etxtpet NtId added to all events. NewLedState removed.
-- PB3  980615  etxanlg subrackCreated, systemNodeCreated, 
--			systemNodeDeleted, subrackDeleted and 
--			cbrQueueFull events added.
--			subrackMismatch alarm added. 
-- PC1  980826  etxanlg Wbas specific; signOnComplete event added
-- 			signOnFailure, berThreshold, radioFailure
--			and modemFailure added
-- PC2  980902 etxanlg Changed size on  ntId from 10 to 20 in order to be able
--                     to send wbas terminal_ids.
--                     Removed event ntDisconnected and alarm batteryFailure
-- PC3  981116 etxkake Gemini CNI 2.2: Changed size on  ntId from 20 to 32
-- PC4  981116 etxanlg Wbas specific signOnFailure alarm changed to common 
--		       signOnFailed. New specific Wbas events alarmDisturbance,
--		       ethernetCableRemoved and ethernetCableReplaced. New 
--		       common event systemAudit
-- PC5  981230 etxanlg CNI-additions for IMA - Alarms added:
--		       lif,t1loop,lods,misconn,blocked,feTxUnus,feRxUnus,
--                     feStartUp,neAborted,feAborted,neInsufficientLinks,
-- 		       feInsufficientLinks,neBlocked,feBlocked.
--PD1   990311 etxanlg Dual1 adaptions - Alarms added: powerUnitFailed, power
--                     UnitAbsent,subrackMismatch,mcnError,fanFailureA,
--                     fanFailureB,externalAlarm1..3,pvcFailure
--		       Alarms removed:  fanFailure, doorOpen, powerFailure,
--                     powerLoss, mcnWarning, cellbusPortFailure, interface-
--                     Failure, mcnError,subrackMismatch
--                     Events removed:  linkUp, linkDown, boardReinserted,
--                     cellbusDefect, losEvent, lofEvent,
--			lossOfCellDelineationEvent
--			lolEvent, sesEvent, powerLossEvent
--PE1   990406 etxanlg WBAS R1 adaptions - Events removed: ethernetCableRemoved,
--                     ethernetCableReplaced. Events added: selfTestOk,
--                     selfTestFailedOnRadio, selfTestFailedOnModem	
--PF1	990616 etxdaos According to MRI Core Rev PK1 (Gemini) and MRI WBAS Rev
--		       PB2 (MLBAS R1), removed ADSL alarms
--PF2   990913 etxanlg According to MRI WBAS Rev PB5.
--PF3   991130 etxanlg According to MRI CORE Rev PA3; remove matchingBoardInserted,
--                     boardUp,boardDown,boardReinserted,ledStateChange,
--                     boardRemoved,linkUp,linkDown
--PF4	000124	etxdaos Changed modem_eber to modem_eber_up and modem_eber_down, and 	
--                      modem_rxl_fin to modem_rxl_fin_up and modem_rxl_fin_down
--PF5   000215  etxdaos Added alarm: radioTxVco
--PF6   000315  etxlaaa HB88982: Removed alarm: mac_sw_download
--                               Added alarm: radio_sw_download
--PF7   001020  teies75 CR15: Added alarm: communication_lost (for slot).
--PF8   001220  teies75 Updated alarm list according to MRI (core) for R1.1 and to
--                      MRI WBAS for R1.15 .
--PF8   010219  teigaba Updated alarm list according to MRI (core) rev. F for R1.15 and to
--                      MRI WBAS rev. L for R1.15 .
--PF9   010326  teigaba Updated for Sw Keys.
--PF10  010521  teigaba According to MRI Core rev.H. Alarms added: externalAlarm1 (62), 
--                      externalAlarm2 (64).
--PF11  010521  teigaba According to MRI Wbas rev.N. Alarms changed: macModemRestart.
--                      Event added: modemRestart (89).
--PF12  010806  teigaba Added hostid_mismatch event(110).
--PF13  010913  teigaba Added radio_frequency_mismatch(111).
--PF14  011015  teigaba Changed branch.

ANS-TRAPS-MIB DEFINITIONS ::= BEGIN

IMPORTS
	TRAP-TYPE FROM RFC-1215
	OBJECT-TYPE FROM RFC1155-SMI
	DisplayString, sysName, sysDescr, sysLocation, sysContact
		FROM RFC1213-MIB
	RowPointer, RowStatus, DateAndTime, mlpmpR115, common
		FROM ANS-COMMON-MIB
	InstancePointer, AlarmSeverity, AlarmType
		FROM ANS-ALARM-MIB
	slot, subrack, board, systemNode
		FROM ANS-EQUIPMENT-MIB;

traps		OBJECT IDENTIFIER ::= {mlpmpR115 7}


ansIdentifier OBJECT-TYPE
	SYNTAX	RowPointer
	ACCESS	not-accessible
	STATUS	mandatory
	DESCRIPTION
		"A reference to the affected entity. "

	::= { traps  1 }

alarmingObject OBJECT-TYPE
	SYNTAX	InstancePointer
	ACCESS	not-accessible
	STATUS	mandatory
	DESCRIPTION
		"The alarming object. Identifies either a variable in 
		the group of variables belonging to the alarming object, 
		or a row in a table representing the alarming object."
	::= { traps  11 }

alarmType OBJECT-TYPE
	SYNTAX	AlarmType
	ACCESS	not-accessible
	STATUS	mandatory
	DESCRIPTION
		"The type of the alarm."
	::= { traps  12 }

alarmSeverity OBJECT-TYPE
	SYNTAX	AlarmSeverity
	ACCESS	not-accessible
	STATUS	mandatory
	DESCRIPTION
		"The perceived severity of the fault."
	::= { traps  13 }

alarmTime OBJECT-TYPE
	SYNTAX	DateAndTime
	ACCESS	not-accessible
	STATUS	mandatory
	DESCRIPTION
		"The time the fault was detected."
	::= { traps  14 }

alarmInformation OBJECT-TYPE
	SYNTAX	DisplayString
	ACCESS	not-accessible
	STATUS	mandatory
	DESCRIPTION
		"Additional information pin-pointing the problem. If
		not provided, this string shall be of zero length."
	::= { traps  15 }

eventTime OBJECT-TYPE
	SYNTAX	DateAndTime
	ACCESS	not-accessible
	STATUS	mandatory
	DESCRIPTION
		"The time the event occured."
	::= { traps  17 }

ntId OBJECT-TYPE
	SYNTAX	DisplayString(SIZE(0..32))
	ACCESS	not-accessible
	STATUS	mandatory
	DESCRIPTION
		"Customer id or network terminal id or radio terminal id"
	::= { traps  18 }


--***************************************
--
-- Alarm traps on a subrack
--


cellbusFailure TRAP-TYPE
        ENTERPRISE subrack
        VARIABLES {
                alarmingObject,
                alarmType,
                alarmSeverity,
                alarmTime,
                alarmInformation,
		ntId
                }
        DESCRIPTION
                "This is sent when a Cellbus has a defect
                 that is longer than 2.5+/-0.5 seconds."
        ::= 5

fanFailure TRAP-TYPE
        ENTERPRISE subrack
        VARIABLES {
                alarmingObject,
                alarmType,
                alarmSeverity,
                alarmTime,
                alarmInformation,
		ntId
                }
        DESCRIPTION
                "Is sent when a fan failure has been detected in the subrack (this could be based on detection of over_temperature in the subrack) An alarm ceasing report (alarm severity ='cleared') will be sent when an indication that the fan is back in operation has been detected."
        ::= 6

powerFailure TRAP-TYPE
        ENTERPRISE subrack
        VARIABLES {
                alarmingObject,
                alarmType,
                alarmSeverity,
                alarmTime,
                alarmInformation,
		ntId
                }
        DESCRIPTION
                "Is sent when a power failure has been detected in the subrack. An alarm ceasing report (alarm severity = 'cleared') will be sent when an indication that the power is back on has been detected."
        ::= 7


--*************************************
--
-- Event traps on a slot
--


communicationLost TRAP-TYPE
	ENTERPRISE slot
	VARIABLES {
		alarmingObject,
		alarmType,
		alarmSeverity,
		alarmTime,
		alarmInformation,
		ntId
		}
	DESCRIPTION
		"Is sent when a the communication to a subrack 
		has been lost. An alarm ceasing report (alarm 
		severity = 'cleared') will be sent when the 
		communication has been re-established.
		The alarm type is by default 'communication alarm'."
	::= 1



boardReplaced TRAP-TYPE
	ENTERPRISE slot
	VARIABLES {
		ansIdentifier,
		eventTime,
		ntId
		}
	DESCRIPTION
		"Is sent when the insertion of a circuit board
		that matches the configured data for the slot
		(but not the serial number) has been detected."
	::= 2


--********************************************
--
-- Alarm traps on a slot
--

boardRemovedAlarm TRAP-TYPE
	ENTERPRISE slot
	VARIABLES {
		alarmingObject,
		alarmType,
		alarmSeverity,
		alarmTime,
		alarmInformation,
		ntId
		}
	DESCRIPTION
		"Is sent when the removal of a matching circuit board
		from a slot has been detected. An alarm ceasing report 
		(alarm severity = 'cleared') will be sent when a board 
		is inserted in the slot, or when the configuration data 
		is cleared for the slot. 
		The alarm type is by default 'equipment alarm'."
	::= 4

boardMismatch TRAP-TYPE
	ENTERPRISE slot
	VARIABLES {
		alarmingObject,
		alarmType,
		alarmSeverity,
		alarmTime,
		alarmInformation,
		ntId
		}
	DESCRIPTION
		"Is sent when the insertion of a circuit board
		that does not match the configured data for the
		slot has been detected. An alarm ceasing report 
		(alarm severity = 'cleared') will be sent when 
		matching configuration data is set for the slot, 
		when the configuration data is cleared for
		the slot, or when the board is removed.
		The alarm type is by default 'equipment alarm'."
	::= 6

boardUnrecognized TRAP-TYPE
	ENTERPRISE slot
	VARIABLES {
		alarmingObject,
		alarmType,
		alarmSeverity,
		alarmTime,
		alarmInformation,
		ntId
		}
	DESCRIPTION
		"Is sent when the insertion of a circuit board
		in a slot has been detected, but the board ID 
		is not recognizable (or not valid for this system).
		An alarm ceasing report (alarm severity = 'cleared')
		will be sent when the board is removed.
		The alarm type is by default 'equipment alarm'."
	::= 7

powerLoss TRAP-TYPE
	ENTERPRISE slot
	VARIABLES {
		alarmingObject,
		alarmType,
		alarmSeverity,
		alarmTime,
		alarmInformation,
		ntId
		}
	DESCRIPTION
		"Is sent when a power loss occurs at a board."
	::= 8

interfaceFailure TRAP-TYPE
	ENTERPRISE slot
	VARIABLES {
		alarmingObject,
		alarmType,
		alarmSeverity,
		alarmTime,
		alarmInformation,
		ntId
		}
	DESCRIPTION
		"Is sent when an interface on a board has failed."
	::= 9



--*****************************************
--
-- Event traps on a board
--



softwareDownloadInProgress TRAP-TYPE
        ENTERPRISE board
        VARIABLES {
		ansIdentifier,
		eventTime,
		ntId
                }
        DESCRIPTION
                "Sent when the board software is being downloaded"
        ::= 25

softwareDownloadDone TRAP-TYPE
        ENTERPRISE board
        VARIABLES {
		ansIdentifier,
		eventTime,
		ntId
                }
        DESCRIPTION
                "This is sent when the software is downloaded"
        ::= 26

atRollbacked TRAP-TYPE
        ENTERPRISE board
        VARIABLES {
                ansIdentifier,
                eventTime,
                ntId
                }
        DESCRIPTION
                "This is sent when the software is downloaded"
        ::= 46

--************************************
--
-- Alarm traps on a board
--

communicationError TRAP-TYPE
	ENTERPRISE board
	VARIABLES {
		alarmingObject,
		alarmType,
		alarmSeverity,
		alarmTime,
		alarmInformation,
		ntId
		}
	DESCRIPTION
		"Is sent when a communication error condition has been
		entered (or ceased) on a circuit board.
		The alarm type is by default 'equipment alarm'."
	::= 9


startError TRAP-TYPE
	ENTERPRISE board
	VARIABLES {
		alarmingObject,
		alarmType,
		alarmSeverity,
		alarmTime,
		alarmInformation,
		ntId
		}
	DESCRIPTION
		"Is sent when a start error condition has been
		entered (or ceased) on a circuit board.
		The alarm type is by default 'equipment alarm'."
	::= 12


laserPower TRAP-TYPE
	ENTERPRISE board
	VARIABLES {
		alarmingObject,
		alarmType,
		alarmSeverity,
		alarmTime,
		alarmInformation,
		ntId
		}
	DESCRIPTION
		"This is sent when a failure of the laser power occurs."
	::= 13

dpSoftwareFailure TRAP-TYPE
	ENTERPRISE board
	VARIABLES {
		alarmingObject,
		alarmType,
		alarmSeverity,
		alarmTime,
		alarmInformation,
		ntId
		}
	DESCRIPTION
		"This is sent if the DP software fails."
	::= 15

bufferOverflow TRAP-TYPE
	ENTERPRISE board
	VARIABLES {
		alarmingObject,
		alarmType,
		alarmSeverity,
		alarmTime,
		alarmInformation,
		ntId
		}
	DESCRIPTION
		"This is sent when a buffer overflows for a while"
	::= 16

bufferUnderflow TRAP-TYPE
	ENTERPRISE board
	VARIABLES {
		alarmingObject,
		alarmType,
		alarmSeverity,
		alarmTime,
		alarmInformation,
		ntId
		}
	DESCRIPTION
		"This is sent when a buffer underflows for a while"
	::= 17

downLoadLmFailed TRAP-TYPE
	ENTERPRISE board
	VARIABLES {
		alarmingObject,
		alarmType,
		alarmSeverity,
		alarmTime,
		alarmInformation,
		ntId
		}
	DESCRIPTION
		"This is sent when the downloading of a new Load Module (LM)
		to a Device Processor (DP) fails"
	::= 19


incorrectSwVersion TRAP-TYPE
        ENTERPRISE board
        VARIABLES {
                alarmingObject,
                alarmType,
                alarmSeverity,
                alarmTime,
                alarmInformation,
		ntId
                }
        DESCRIPTION
                "This is sent when a board has been loaded with
                 the incorrect version of software." 
        ::= 21

loopBackFailure TRAP-TYPE
        ENTERPRISE board
        VARIABLES {
                alarmingObject,
                alarmType,
                alarmSeverity,
                alarmTime,
                alarmInformation,
		ntId
                }
        DESCRIPTION
                "This is sent when a loopback has failed." 
        ::= 22

vpAis TRAP-TYPE
        ENTERPRISE board
        VARIABLES {
                alarmingObject,
                alarmType,
                alarmSeverity,
                alarmTime,
                alarmInformation,
		ntId
                }
        DESCRIPTION
                "This is sent when a VP AIS alarm occurs." 
        ::= 23

vpRdi TRAP-TYPE
        ENTERPRISE board
        VARIABLES {
                alarmingObject,
                alarmType,
                alarmSeverity,
                alarmTime,
                alarmInformation,
		ntId
                }
        DESCRIPTION
                "This is sent when a VP RDI alarm occurs." 
        ::= 24

msAis TRAP-TYPE
        ENTERPRISE board
        VARIABLES {
                alarmingObject,
                alarmType,
                alarmSeverity,
                alarmTime,
                alarmInformation,
		ntId
                }
        DESCRIPTION
                "This is sent when Alarm Indication Signal
		is received for more than 2.5 seconds on a 
		Multiplexer Section." 
        ::= 27

msRdi TRAP-TYPE
        ENTERPRISE board
        VARIABLES {
                alarmingObject,
                alarmType,
                alarmSeverity,
                alarmTime,
                alarmInformation,
		ntId
                }
        DESCRIPTION
                "This is sent when Remote Defect Indication
		is received for more than 2.5 seconds on a 
		Multiplexer Section." 
        ::= 28

pathRdi TRAP-TYPE
        ENTERPRISE board
        VARIABLES {
                alarmingObject,
                alarmType,
                alarmSeverity,
                alarmTime,
                alarmInformation,
		ntId
                }
        DESCRIPTION
                "This is sent when Remote Defect Indication
		is received for more than 2.5 seconds on a 
		Path." 
        ::= 29

pathAis TRAP-TYPE
        ENTERPRISE board
        VARIABLES {
                alarmingObject,
                alarmType,
                alarmSeverity,
                alarmTime,
                alarmInformation,
		ntId
                }
        DESCRIPTION
                "This is sent when Alarm Indication Signal
		is received for more than 2.5 seconds on a 
		Path." 
        ::= 30


--***********************************
--
-- Wbas alarms from wbas_rn (board)
--
  
macModemSwDownloadFailure TRAP-TYPE
        ENTERPRISE board
        VARIABLES {
                alarmingObject,
                alarmType,
                alarmSeverity,
                alarmTime,
                alarmInformation,
		ntId
                }
        DESCRIPTION
                "the download from the MAC EPROM active or passive towards the passive area of modem has failed"
        ::= 18

macRadioSwDownloadFailure TRAP-TYPE
        ENTERPRISE board
        VARIABLES {
                alarmingObject,
                alarmType,
                alarmSeverity,
                alarmTime,
                alarmInformation,
		ntId
                }
        DESCRIPTION
                "the download from the MAC EPROM active or passive towards the passive area of radio has failed"
        ::= 20

macIncorrSwVersModem TRAP-TYPE
        ENTERPRISE board
        VARIABLES {
                alarmingObject,
                alarmType,
                alarmSeverity,
                alarmTime,
                alarmInformation,
		ntId
                }
        DESCRIPTION
                "The active loadmodule in the modem contains an incorrect SW version."
        ::= 42

macIncorrSwVersRadio TRAP-TYPE
        ENTERPRISE board
        VARIABLES {
                alarmingObject,
                alarmType,
                alarmSeverity,
                alarmTime,
                alarmInformation,
		ntId
                }
        DESCRIPTION
                "The active loadmodule in the radio contains an incorrect SW version."
        ::= 43

macSwdlFromActiveToModemInProgress TRAP-TYPE
        ENTERPRISE board
        VARIABLES {
                alarmingObject,
                alarmType,
                alarmSeverity,
                alarmTime,
                alarmInformation,
		ntId
                }
        DESCRIPTION
                "the download from the MAC FPROM active towards the passive area of modem is in progress (in Background)"
        ::= 44

macSwdlFromActiveToRadioInProgress TRAP-TYPE
        ENTERPRISE board
        VARIABLES {
                alarmingObject,
                alarmType,
                alarmSeverity,
                alarmTime,
                alarmInformation,
		ntId
                }
        DESCRIPTION
                "the download from the MAC FPROM active towards the passive area of modem is in progress (in Background)"
        ::= 45

macSwdlFromPassiveToModemInProgress TRAP-TYPE
        ENTERPRISE board
        VARIABLES {
                alarmingObject,
                alarmType,
                alarmSeverity,
                alarmTime,
                alarmInformation,
		ntId
                }
        DESCRIPTION
                "the download from the MAC FPROM passive towards the active area of modem is in progress (in Background)"
        ::= 47

macSwdlFromPassiveToRadioInProgress TRAP-TYPE
        ENTERPRISE board
        VARIABLES {
                alarmingObject,
                alarmType,
                alarmSeverity,
                alarmTime,
                alarmInformation,
		ntId
                }
        DESCRIPTION
                "the download from the MAC FPROM passive towards the active area of radio is in progress (in Background)"
        ::= 48

macKeepAliveFail TRAP-TYPE
        ENTERPRISE board
        VARIABLES {
                alarmingObject,
                alarmType,
                alarmSeverity,
                alarmTime,
                alarmInformation,
		ntId
                }
        DESCRIPTION
                "MAC-Radio Control Communication  Link Failure. The ping toward the radio doesn't come back to the mac three consecutive times"
        ::= 49

macRestart TRAP-TYPE
        ENTERPRISE board
        VARIABLES {
                alarmingObject,
                alarmType,
                alarmSeverity,
                alarmTime,
                alarmInformation,
		ntId
                }
        DESCRIPTION
                "MAC DP Restarted"
        ::= 50

macModemRestart TRAP-TYPE
        ENTERPRISE board
        VARIABLES {
                alarmingObject,
                alarmType,
                alarmSeverity,
                alarmTime,
                alarmInformation,
		ntId
                }
        DESCRIPTION
                "Modem DP Restarted"
        ::= 51

macControlChannel TRAP-TYPE
        ENTERPRISE board
        VARIABLES {
                alarmingObject,
                alarmType,
                alarmSeverity,
                alarmTime,
                alarmInformation,
		ntId
                }
        DESCRIPTION
                "No communication with modem processor." 			 			   
        ::= 37

macRclFailure TRAP-TYPE
        ENTERPRISE board
        VARIABLES {
                alarmingObject,
                alarmType,
                alarmSeverity,
                alarmTime,
                alarmInformation,
		ntId
                }
        DESCRIPTION
                "Unknown RCL command from de-framer." 			 			   
        ::= 38

macCbrOverflow TRAP-TYPE
        ENTERPRISE board
        VARIABLES {
                alarmingObject,
                alarmType,
                alarmSeverity,
                alarmTime,
                alarmInformation,
		ntId
                }
        DESCRIPTION
                "CBR buffer overflow." 			 			   
        ::= 39

macSwException TRAP-TYPE
        ENTERPRISE board
        VARIABLES {
                alarmingObject,
                alarmType,
                alarmSeverity,
                alarmTime,
                alarmInformation,
		ntId
                }
        DESCRIPTION
                "Software exception on MAC DP." 			 			   
        ::= 40

macHwException TRAP-TYPE
        ENTERPRISE board
        VARIABLES {
                alarmingObject,
                alarmType,
                alarmSeverity,
                alarmTime,
                alarmInformation,
		ntId
                }
        DESCRIPTION
                "Hardware exception." 			 			   
        ::= 41

--***********************************
--
-- Wbas alarms from wbas_at_slot (slot)
--


macSignonFailed TRAP-TYPE
        ENTERPRISE slot
        VARIABLES {
                alarmingObject,
                alarmType,
                alarmSeverity,
                alarmTime,
                alarmInformation,
		ntId
                }
        DESCRIPTION
                "Sent when the AT which should be signed on is lost." 			 			   
        ::= 12


--***********************************
--
-- Wbas alarms from wbas_at

atControlChannel TRAP-TYPE
        ENTERPRISE common
        VARIABLES {
                alarmingObject,
                alarmType,
                alarmSeverity,
                alarmTime,
                alarmInformation,
		ntId
                }
        DESCRIPTION
                "No communication with modem processor." 			 			   
        ::= 63


radioTxOn TRAP-TYPE
        ENTERPRISE common
        VARIABLES {
                alarmingObject,
                alarmType,
                alarmSeverity,
                alarmTime,
                alarmInformation,
		ntId
                }
        DESCRIPTION
                "Transmitter always on." 			 			   
        ::= 77

radioVco TRAP-TYPE
        ENTERPRISE common
        VARIABLES {
                alarmingObject,
                alarmType,
                alarmSeverity,
                alarmTime,
                alarmInformation,
		ntId
                }
        DESCRIPTION
                "Radio VCO has a reduced margin." 			 			   
        ::= 78

radioTxLevel TRAP-TYPE
        ENTERPRISE common
        VARIABLES {
                alarmingObject,
                alarmType,
                alarmSeverity,
                alarmTime,
                alarmInformation,
		ntId
                }
        DESCRIPTION
                "Unable to adjust radio output power level." 			 			   
        ::= 79

radioTxVco TRAP-TYPE
        ENTERPRISE common
        VARIABLES {
                alarmingObject,
                alarmType,
                alarmSeverity,
                alarmTime,
                alarmInformation,
		ntId
                }
        DESCRIPTION
                "The TX VCO has reached a reduced action margin in the Radio Unit." 			 			   
        ::= 104


modemLofTdm TRAP-TYPE
        ENTERPRISE common
        VARIABLES {
                alarmingObject,
                alarmType,
                alarmSeverity,
                alarmTime,
                alarmInformation,
		ntId
                }
        DESCRIPTION
                "Loss of synchronization." 			 			   
        ::= 83



--***********************************
--
-- Wbas alarms from wbas_siu

suMismatch TRAP-TYPE
        ENTERPRISE common
        VARIABLES {
                alarmingObject,
                alarmType,
                alarmSeverity,
                alarmTime,
                alarmInformation,
		ntId
                }
        DESCRIPTION
                "A SU of wrong type has been inserted in a configured SU slot." 			 			   
        ::= 65

suPowerFailure TRAP-TYPE
        ENTERPRISE common
        VARIABLES {
                alarmingObject,
                alarmType,
                alarmSeverity,
                alarmTime,
                alarmInformation,
		ntId
                }
        DESCRIPTION
                "Power failure on a SU." 			 			   
        ::= 66

suInitFailure TRAP-TYPE
        ENTERPRISE common
        VARIABLES {
                alarmingObject,
                alarmType,
                alarmSeverity,
                alarmTime,
                alarmInformation,
		ntId
                }
        DESCRIPTION
                "Initialization of a SU failed." 			 			   
        ::= 67

suUnsupportedType TRAP-TYPE
        ENTERPRISE common
        VARIABLES {
                alarmingObject,
                alarmType,
                alarmSeverity,
                alarmTime,
                alarmInformation,
		ntId
                }
        DESCRIPTION
                "SU of a type which is not supported was inserted." 			 			   
        ::= 68

suHwFailure TRAP-TYPE
        ENTERPRISE common
        VARIABLES {
                alarmingObject,
                alarmType,
                alarmSeverity,
                alarmTime,
                alarmInformation,
		ntId
                }
        DESCRIPTION
                "HW failure on a SU." 			 			   
        ::= 69

aal1SarFailure TRAP-TYPE
        ENTERPRISE common
        VARIABLES {
                alarmingObject,
                alarmType,
                alarmSeverity,
                alarmTime,
                alarmInformation,
                ntId
                }
        DESCRIPTION
                "Sent when a temporary loss of traffic due to AAL1 device failure is detected."
        ::= 106

--***********************************
--
-- Alarms from wbas_rn / wbas_at


radioTxLos TRAP-TYPE
        ENTERPRISE common
        VARIABLES {
                alarmingObject,
                alarmType,
                alarmSeverity,
                alarmTime,
                alarmInformation,
		ntId
                }
        DESCRIPTION
                "IF input level from modem too low." 			 			   
        ::= 70

radioRfOut TRAP-TYPE
        ENTERPRISE common
        VARIABLES {
                alarmingObject,
                alarmType,
                alarmSeverity,
                alarmTime,
                alarmInformation,
		ntId
                }
        DESCRIPTION
                "RF output level to antenna too low." 			 			   
        ::= 71

radioTxFreq TRAP-TYPE
        ENTERPRISE common
        VARIABLES {
                alarmingObject,
                alarmType,
                alarmSeverity,
                alarmTime,
                alarmInformation,
		ntId
                }
        DESCRIPTION
                "Transmit frequency incorrect." 			 			   
        ::= 72

radioTxOffFail TRAP-TYPE
        ENTERPRISE common
        VARIABLES {
                alarmingObject,
                alarmType,
                alarmSeverity,
                alarmTime,
                alarmInformation,
		ntId
                }
        DESCRIPTION
                "The radio is set off but is still trasmitting"
        ::= 52

radioRxIfc TRAP-TYPE
        ENTERPRISE common
        VARIABLES {
                alarmingObject,
                alarmType,
                alarmSeverity,
                alarmTime,
                alarmInformation,
		ntId
                }
        DESCRIPTION
                "Rx intermediate IF PLL unlocked." 			 			   
        ::= 73

radioRxFreq TRAP-TYPE
        ENTERPRISE common
        VARIABLES {
                alarmingObject,
                alarmType,
                alarmSeverity,
                alarmTime,
                alarmInformation,
		ntId
                }
        DESCRIPTION
                "Receive frequency incorrect." 			 			   
        ::= 74


radioHighTemperature TRAP-TYPE
        ENTERPRISE common
        VARIABLES {
                alarmingObject,
                alarmType,
                alarmSeverity,
                alarmTime,
                alarmInformation,
		ntId
                }
        DESCRIPTION
                "Outdoor temperature above limit." 			 			   
        ::= 76

radioRestart TRAP-TYPE
        ENTERPRISE common
        VARIABLES {
                alarmingObject,
                alarmType,
                alarmSeverity,
                alarmTime,
                alarmInformation,
		ntId
                }
        DESCRIPTION
                "Restart of the Radio DP"
        ::= 53


radioIrsLoss TRAP-TYPE
        ENTERPRISE common
        VARIABLES {
                alarmingObject,
                alarmType,
                alarmSeverity,
                alarmTime,
                alarmInformation,
		ntId
                }
        DESCRIPTION
                "RF input power level too low on average on all the transmitting terminals"
        ::= 94


modemEberUp TRAP-TYPE
        ENTERPRISE common
        VARIABLES {
                alarmingObject,
                alarmType,
                alarmSeverity,
                alarmTime,
                alarmInformation,
		ntId
                }
        DESCRIPTION
                "Uplink Eber received in modem is above limit." 			 			   
        ::= 100

modemEberDown TRAP-TYPE
        ENTERPRISE common
        VARIABLES {
                alarmingObject,
                alarmType,
                alarmSeverity,
                alarmTime,
                alarmInformation,
		ntId
                }
        DESCRIPTION
                "Downlink Eber received in modem is above limit." 			 			   
        ::= 101

modemRxlFinUp TRAP-TYPE
        ENTERPRISE common
        VARIABLES {
                alarmingObject,
                alarmType,
                alarmSeverity,
                alarmTime,
                alarmInformation,
		ntId
                }
        DESCRIPTION
                "Uplink IF input level from RAU too low." 			 			   
        ::= 102

modemRxlFinDown TRAP-TYPE
        ENTERPRISE common
        VARIABLES {
                alarmingObject,
                alarmType,
                alarmSeverity,
                alarmTime,
                alarmInformation,
		ntId
                }
        DESCRIPTION
                "Downlink IF input level from RAU too low." 			 			   
        ::= 103

modemRauPow TRAP-TYPE
        ENTERPRISE common
        VARIABLES {
                alarmingObject,
                alarmType,
                alarmSeverity,
                alarmTime,
                alarmInformation,
		ntId
                }
        DESCRIPTION
                "RAU power supply failure." 			 			   
        ::= 82

modemModInd TRAP-TYPE
        ENTERPRISE common
        VARIABLES {
                alarmingObject,
                alarmType,
                alarmSeverity,
                alarmTime,
                alarmInformation,
		ntId
                }
        DESCRIPTION
                "Unable to adjust modulation index." 			 			   
        ::= 85

modemSwException TRAP-TYPE
        ENTERPRISE common
        VARIABLES {
                alarmingObject,
                alarmType,
                alarmSeverity,
                alarmTime,
                alarmInformation,
		ntId
                }
        DESCRIPTION
                "Software exception." 			 			   
        ::= 86

modemHwException TRAP-TYPE
        ENTERPRISE common
        VARIABLES {
                alarmingObject,
                alarmType,
                alarmSeverity,
                alarmTime,
                alarmInformation,
		ntId
                }
        DESCRIPTION
                "Hardware error." 			 			   
        ::= 87

modemControlChannel TRAP-TYPE
        ENTERPRISE common
        VARIABLES {
                alarmingObject,
                alarmType,
                alarmSeverity,
                alarmTime,
                alarmInformation,
		ntId
                }
        DESCRIPTION
                "No communication with radio unit processor." 			 			   
        ::= 88

swDownloadFailureRadio TRAP-TYPE
        ENTERPRISE common
        VARIABLES {
                alarmingObject,
                alarmType,
                alarmSeverity,
                alarmTime,
                alarmInformation,
		ntId
                }
        DESCRIPTION
                "the download from the NU FPROM active or passive towards the passive area of radio has failed"
        ::= 54

swDownloadFailureModem TRAP-TYPE
        ENTERPRISE common
        VARIABLES {
                alarmingObject,
                alarmType,
                alarmSeverity,
                alarmTime,
                alarmInformation,
		ntId
                }
        DESCRIPTION
                "the download from the NU FPROM active or passive towards the passive area of modem has failed"
        ::= 55

incorrectSwVersModem TRAP-TYPE
        ENTERPRISE common
        VARIABLES {
                alarmingObject,
                alarmType,
                alarmSeverity,
                alarmTime,
                alarmInformation,
		ntId
                }
        DESCRIPTION
                "the active LM in the modem contains an incorrect SW version"
        ::= 56

incorrectSwVersRadio TRAP-TYPE
        ENTERPRISE common
        VARIABLES {
                alarmingObject,
                alarmType,
                alarmSeverity,
                alarmTime,
                alarmInformation,
		ntId
                }
        DESCRIPTION
                "the active LM in the radio contains an incorrect SW version"
        ::= 58

swdlFromActiveToModemInProgress TRAP-TYPE
        ENTERPRISE common
        VARIABLES {
                alarmingObject,
                alarmType,
                alarmSeverity,
                alarmTime,
                alarmInformation,
		ntId
                }
        DESCRIPTION
                "the download from the NU FPROM active towards the passive area of modem is in progress (in Background)"
        ::= 59

swdlFromActiveToRadioInProgress TRAP-TYPE
        ENTERPRISE common
        VARIABLES {
                alarmingObject,
                alarmType,
                alarmSeverity,
                alarmTime,
                alarmInformation,
		ntId
                }
        DESCRIPTION
                "the download from the NU FPROM active towards the passive area of radio is in progress (in Background)"
        ::= 75

swdlFromPassiveToModemInProgress TRAP-TYPE
        ENTERPRISE common
        VARIABLES {
                alarmingObject,
                alarmType,
                alarmSeverity,
                alarmTime,
                alarmInformation,
		ntId
                }
        DESCRIPTION
                "the download from the NU FPROM passive towards the active area of modem is in progress (in Background)"
        ::= 80

swdlFromPassiveToRadioInProgress TRAP-TYPE
        ENTERPRISE common
        VARIABLES {
                alarmingObject,
                alarmType,
                alarmSeverity,
                alarmTime,
                alarmInformation,
		ntId
                }
        DESCRIPTION
                "the download from the NU FPROM passive towards the active area of radio is in progress (in Background)"
        ::= 81

radioMismatch TRAP-TYPE
        ENTERPRISE common
        VARIABLES {
                alarmingObject,
                alarmType,
                alarmSeverity,
                alarmTime,
                alarmInformation,
		ntId
                }
        DESCRIPTION
                "UKL received different from UKL configured"
        ::= 84

radioFrequencyMismatch TRAP-TYPE
        ENTERPRISE common
        VARIABLES {
                alarmingObject,
                alarmType,
                alarmSeverity,
                alarmTime,
                alarmInformation,
		ntId
                }
        DESCRIPTION
                "Configured Frequency is not within the restricted frequency range of the installed Radio Unit"
        ::= 111

--***********************************
--
-- Alarms from ethernet_port
--

ethernetLossOfCarrier TRAP-TYPE
        ENTERPRISE common
        VARIABLES {
                alarmingObject,
                alarmType,
                alarmSeverity,
                alarmTime,
                alarmInformation,
		ntId
                }
        DESCRIPTION
                "Sent if ethernet port detects loss of carrier." 			 			   
        ::= 90


--***********************************
--
-- Alarms from pdh_port
--

aal1Starvation TRAP-TYPE
        ENTERPRISE common
        VARIABLES {
                alarmingObject,
                alarmType,
                alarmSeverity,
                alarmTime,
                alarmInformation,
		ntId
                }
        DESCRIPTION
                "Sent when a buffer-underflow condition is detected." 			 			   
        ::= 91

lossOfRefClock TRAP-TYPE
        ENTERPRISE common
        VARIABLES {
                alarmingObject,
                alarmType,
                alarmSeverity,
                alarmTime,
                alarmInformation,
		ntId
                }
        DESCRIPTION
                "Sent when the 8 kHz clock is lost." 			 			   
        ::= 92



--***********************************
--
-- Common events
--

systemUp TRAP-TYPE
	ENTERPRISE common
	VARIABLES {
		sysName, 
		sysDescr, 
		sysLocation, 
		sysContact,
		eventTime
		}
	DESCRIPTION
		"This is sent when the CP has initialised."
	::= 0


systemAudit TRAP-TYPE
	ENTERPRISE common
	VARIABLES {
		sysName, 
		sysDescr, 
		sysLocation, 
		sysContact,
		eventTime
		}
	DESCRIPTION
		"Generated by the  CP to notify that a CP start/restart is ongoing."
	::= 57

protectionSchemeNotRespected TRAP-TYPE
	ENTERPRISE common
	VARIABLES {
		sysName, 
		sysDescr, 
		sysLocation, 
		sysContact,
		eventTime
		}
	DESCRIPTION
                "his is sent when boards not respecting the protection scheme are present in the subrack."
	::= 10

rnSwitched TRAP-TYPE
	ENTERPRISE common
	VARIABLES {
		sysName, 
		sysDescr, 
		sysLocation, 
		sysContact,
		eventTime
		}
	DESCRIPTION
                "A switch between a providing_service RN board with a cold_standby one has been performed."
	::= 11

masterLinkSwitched TRAP-TYPE
	ENTERPRISE common
	VARIABLES {
		sysName, 
		sysDescr, 
		sysLocation, 
		sysContact,
		eventTime
		}
	DESCRIPTION
                "A switch between the link that is giving the synchronization at the system node."
	::= 107

licenseCapacityEvent TRAP-TYPE
	ENTERPRISE common
	VARIABLES {
		sysName, 
		sysDescr, 
		sysLocation, 
		sysContact,
		eventTime
		}
	DESCRIPTION
                "This event is sent when 85%, 90% or 95% of license capacity is reached."
	::= 108

licenseExpirationEvent TRAP-TYPE
	ENTERPRISE common
	VARIABLES {
		sysName, 
		sysDescr, 
		sysLocation, 
		sysContact,
		eventTime
		}
	DESCRIPTION
                "This event is sent once a day starting from 10 days before expiration date."
	::= 109

hostidMismatch TRAP-TYPE
	ENTERPRISE common
	VARIABLES {
		sysName, 
		sysDescr, 
		sysLocation, 
		sysContact,
		eventTime
		}
	DESCRIPTION
                "This event is sent at System Restart if a hostid mismatch exists."
	::= 110

subrackCreated TRAP-TYPE
	ENTERPRISE common
	VARIABLES {
		ansIdentifier,
		eventTime,
		ntId
		}
	DESCRIPTION
		"A new subrack is created."
	::= 32

systemNodeCreated TRAP-TYPE
	ENTERPRISE common
	VARIABLES {
		ansIdentifier,
		eventTime,
		ntId
		}
	DESCRIPTION
		"A new system node is created."
	::= 33

systemNodeDeleted TRAP-TYPE
	ENTERPRISE common
	VARIABLES {
		ansIdentifier,
		eventTime,
		ntId
		}
	DESCRIPTION
		"A system node is deleted."
	::= 34

subrackDeleted TRAP-TYPE
	ENTERPRISE common
	VARIABLES {
		ansIdentifier,
		eventTime,
		ntId
		}
	DESCRIPTION
		"A subrack is deleted."
	::= 35

cbrQueueFull TRAP-TYPE
	ENTERPRISE common
	VARIABLES {
		ansIdentifier,
		eventTime,
		ntId
		}
	DESCRIPTION
		"Temporary buffer overflow."
	::= 36

--***********************************
--
-- Wbas/Adsl trap 
--

signOnComplete TRAP-TYPE
	ENTERPRISE common
	VARIABLES {
		ansIdentifier,
		eventTime,
		ntId
		}
	DESCRIPTION
		"This is a notification that the sign on of an NT/AT
		is completed."
	::= 37

modemRestart TRAP-TYPE
        ENTERPRISE common
        VARIABLES {
                ansIdentifier,
                eventTime,
                ntId
                }
        DESCRIPTION
                "This is a notification that the sign on of an NT/AT
                is completed."
        ::= 89 

--***********************************
--
-- Only Wbas traps 
--
alarmDisturbance TRAP-TYPE
	ENTERPRISE common
	VARIABLES {
		ansIdentifier,
		eventTime,
		ntId
		}
	DESCRIPTION
		"This notification is sent if an alarm state changes
		frequently."
	::= 38

selfTestOk TRAP-TYPE
	ENTERPRISE common
	VARIABLES {
		ansIdentifier,
		eventTime,
		ntId
		}
	DESCRIPTION
		"Loop on radio is working, i.e. mac, modem and radio have no faults."
	::= 39

selfTestFailedOnRadio TRAP-TYPE
	ENTERPRISE common
	VARIABLES {
		ansIdentifier,
		eventTime,
		ntId
		}
	DESCRIPTION
		"Loop on radio does not work, i.e. mac or modem or radio faulty."
	::= 40

selfTestFailedOnModem TRAP-TYPE
	ENTERPRISE common
	VARIABLES {
		ansIdentifier,
		eventTime,
		ntId
		}
	DESCRIPTION
		"Loop on modem does not work, i.e. mac or modem faulty."
	::= 96

--***********************************
--
-- Common traps, continued 
--


--***********************************
--
-- Common alarms
--

los TRAP-TYPE
	ENTERPRISE common
	VARIABLES {
		alarmingObject,
		alarmType,
		alarmSeverity,
		alarmTime,
		alarmInformation,
		ntId
		}
	DESCRIPTION
		"This is sent when a Loss Of Signal has been detected."
	::= 1

lof TRAP-TYPE
	ENTERPRISE common
	VARIABLES {
		alarmingObject,
		alarmType,
		alarmSeverity,
		alarmTime,
		alarmInformation,
		ntId
		}
	DESCRIPTION
		"This is sent when a Loss Of Frame has been detected."
	::= 2

lop TRAP-TYPE
	ENTERPRISE common
	VARIABLES {
		alarmingObject,
		alarmType,
		alarmSeverity,
		alarmTime,
		alarmInformation,
		ntId
		}
	DESCRIPTION
		"This is sent when a Loss Of Pointer has been detected."
	::= 3

ais TRAP-TYPE
	ENTERPRISE common
	VARIABLES {
		alarmingObject,
		alarmType,
		alarmSeverity,
		alarmTime,
		alarmInformation,
		ntId
		}
	DESCRIPTION
		"This is sent when an Alarm Indication Signal
		 has been detected."
	::= 4

lofMf TRAP-TYPE
	ENTERPRISE common
	VARIABLES {
		alarmingObject,
		alarmType,
		alarmSeverity,
		alarmTime,
		alarmInformation,
		ntId
		}
	DESCRIPTION
		"This is sent when a Loss Of MultiFrame has been detected."
	::= 95

rai TRAP-TYPE
	ENTERPRISE common
	VARIABLES {
		alarmingObject,
		alarmType,
		alarmSeverity,
		alarmTime,
		alarmInformation,
		ntId
		}
	DESCRIPTION
		"This is sent when a Remote Alarm Indication has been detected."
	::= 6

lossOfCellDelineation TRAP-TYPE
	ENTERPRISE common
	VARIABLES {
		alarmingObject,
		alarmType,
		alarmSeverity,
		alarmTime,
		alarmInformation,
		ntId
		}
	DESCRIPTION
		"This is sent when loss of cell delineation has been detected."
	::= 8

subrackMismatch TRAP-TYPE
	ENTERPRISE common
	VARIABLES {
		alarmingObject,
		alarmType,
		alarmSeverity,
		alarmTime,
		alarmInformation,
		ntId
		}
	DESCRIPTION
		"The subrack is wrongly configured in the configuration files.
		Power Management enabled even if no check in the hardware is 
		performed."
	::= 31

externalAlarm1 TRAP-TYPE
        ENTERPRISE common
        VARIABLES {
                alarmingObject,
                alarmType,
                alarmSeverity,
                alarmTime,
                alarmInformation,
                ntId
                }
        DESCRIPTION
                "Is sent when an external alarm has been detected in the subrack 
                 (this is based on detection of relay alarm on input MISC 1 of 
                 the subrack ). An alarm ceasing report (alarm severity = 'cleared') 
                 will be sent when an indication that the external alarm is ceased 
                 has been detected."
        ::= 62

externalAlarm2 TRAP-TYPE
        ENTERPRISE common
        VARIABLES {
                alarmingObject,
                alarmType,
                alarmSeverity,
                alarmTime,
                alarmInformation,
                ntId
                }
        DESCRIPTION
                "Is sent when an external alarm has been detected in the subrack 
                 (this is based on detection of relay alarm on input MISC 2 of 
                 the subrack ). An alarm ceasing report (alarm severity = 'cleared') 
                 will be sent when an indication that the external alarm is ceased 
                 has been detected."
        ::= 64

mcnWarning TRAP-TYPE
	ENTERPRISE common
	VARIABLES {
		alarmingObject,
		alarmType,
		alarmSeverity,
		alarmTime,
		alarmInformation,
		ntId
		}
	DESCRIPTION
		""
	::= 60

lossOfNetSync  TRAP-TYPE
        ENTERPRISE common
        VARIABLES {
                alarmingObject,
                alarmType,
                alarmSeverity,
                alarmTime,
                alarmInformation,
		ntId
                }
        DESCRIPTION
                "This is sent when critical alarms are detected 
		 at DPSW level on a specific board (ET/CE), 
		 which is master for the network." 			 			   
        ::= 61

diskFull TRAP-TYPE
        ENTERPRISE common
        VARIABLES {
                alarmingObject,
                alarmType,
                alarmSeverity,
                alarmTime,
                alarmInformation,
		ntId
                }
        DESCRIPTION
                "The filesystem on a disk in the CP is almost full." 			 			   
        ::= 97

hwFailure TRAP-TYPE
        ENTERPRISE common
        VARIABLES {
                alarmingObject,
                alarmType,
                alarmSeverity,
                alarmTime,
                alarmInformation,
		ntId
                }
        DESCRIPTION
                "Sent when DP has reported faulty HW." 			 			   
        ::= 98

suRemoved TRAP-TYPE
        ENTERPRISE common
        VARIABLES {
                alarmingObject,
                alarmType,
                alarmSeverity,
                alarmTime,
                alarmInformation,
		ntId
                }
        DESCRIPTION
                "Sent when SU has been removed." 			 			   
        ::= 99



END
