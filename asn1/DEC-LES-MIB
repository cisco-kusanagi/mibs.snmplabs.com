--
--  This is a SNMPv1 translation of Digital Equipment Corporation's LAN
--  Emulation Server MIB.
--
--  Initial translation was done by the tool
--          SMIC (the next generation) version 1.6.31
--
--  The machine-generated MIB was then modified to remove all remaining
--  SNMP version 2 constructs.
--

DEC-LES-MIB DEFINITIONS ::= BEGIN

IMPORTS

    Counter, TimeTicks
            FROM RFC1155-SMI
    OBJECT-TYPE
            FROM RFC-1212
    decMIBextension
            FROM DECATM-MIB;

decLesMIB OBJECT IDENTIFIER ::= { decMIBextension 28 }

-- MODULE-IDENTITY
--  LastUpdated
--    9509120000Z
--  OrgName
--    Digital Equipment Corporation
--  ContactInfo
--    
--      Thomas Newton
--      Digital Equipment Corporation
--      550 King Street
--      Littleton, MA  01460
--      United States of America
--      Tel: 508-486-5293
--      E-mail: newton@school.enet.dec.com
--  Descr
--    This module defines a portion of the management 
--     information base (MIB) for managing ATM LAN Emulation
--     Servers.

decLesMIBObjects OBJECT IDENTIFIER ::= { decLesMIB 1 }
decLesMIBConformance OBJECT IDENTIFIER ::= { decLesMIB 2 }
decLesMIBGroups OBJECT IDENTIFIER ::= { decLesMIBConformance 1 }
decLesMIBCompliances OBJECT IDENTIFIER ::= { decLesMIBConformance 2 }

-- AtmLaneAddress ::= OCTET STRING(SIZE(0..20))
-- TEXTUAL-CONVENTION
--  Status
--    mandatory
--  Descr
--    A twenty-octet binary string, containing a standard
--     ATM Forum address == or the zero-length string,
--     indicating the absence of an address.
--    
--     For LAN Emulation purposes, the eight-octet address
--     format is not used.

-- VpiInteger ::= INTEGER(0..255)
-- TEXTUAL-CONVENTION
--  Status
--    mandatory
--  Descr
--    An integer large enough to hold a VPI.

-- VciInteger ::= INTEGER(0..65535)
-- TEXTUAL-CONVENTION
--  Status
--    mandatory
--  Descr
--    An integer large enough to hold a VCI.

-- LesConnectionInterface ::= INTEGER(0..2147483647)
-- TEXTUAL-CONVENTION
--  Status
--    mandatory
--  Descr
--    A combination flag and ifTable index, indicating
--     whether a LAN Emulation circuit exists - and, if
--     so, which interface is associated with it at the
--     point where it connects to a server.
--    
--     Objects of this type are always defined as part of
--     a set that includes
--    
--             fooInterface   LesConnectionInterface
--             fooVpi         VpiInteger
--             fooVci         VciInteger
--    
--     The interpretation of these objects is as follows.
--    
--     1.  If no connection exists, 'fooInterface' has a
--         value of 0.  Because Interfaces table entries
--         always have 'ifIndex' values larger than 0,
--         'fooInterface' reliably serves as a 'connection
--         exists' flag.
--    
--         In this case, 'fooVpi' and 'fooVci' are
--         meaningless, and have the value 0.
--    
--     2.  If a PVC or SVC exists, 'fooInterface' is defined
--         to have the value of the MIB-II/RFC 1573 'ifIndex'
--         of the 'atm' interface associated with the VCC.
--         'fooVpi' and 'fooVci' will contain its VPI/VCI.
--         Therefore, ('fooInterface', 'fooVpi', 'fooVci')
--         give you an index into the AToM MIB which allows
--         you to examine and play with the circuit further.

-- LesDataFrameFormat ::= INTEGER {
--        aflane8023(2),
--        aflane8025(3)
--        }
-- TEXTUAL-CONVENTION
--  Status
--    mandatory
--  Descr
--    A 'LAN Type' value.
--    
--     S2  LAN Type.  The type of this ATM Emulated LAN,
--         either Ethernet/IEEE 802.3 or IEEE 802.5.
--  Refer
--    ATM Forum LAN Emulation Over ATM Specification, V1.0,
--     Section 5.1.2

-- LesDataFrameSize ::= INTEGER {
--        max1516(2),
--        max4544(3),
--        max9234(4),
--        max18190(5)
--        }
-- TEXTUAL-CONVENTION
--  Status
--    mandatory
--  Descr
--    A 'Maximum Data Frame Size' value.
--    
--     S3  Maximum Data Frame Size.  The maximum AAL-5 SDU
--         size of a data frame that the LE Service can
--         guarantee not to drop because it is too large.
--         Also the minimum AAL-5 SDU size that every LE
--         Client must be able to receive.  MUST be either
--         1516, 4544, 9234, or 18190 octets.
--  Refer
--    ATM Forum LAN Emulation Over ATM Specification, V1.0,
--     Section 5.1.2

-- LesLecState ::= INTEGER {
--        other(1),
--        noLesConnect(2),
--        lesConnect(3),
--        joining(4),
--        operational(5),
--        deleting(6)
--        }
-- TEXTUAL-CONVENTION
--  Status
--    mandatory
--  Descr
--    Indicates the status of a LAN Emulation Client from
--     the server's perspective.
--    
--         other
--             The LEC state is unknown.
--    
--         noLesConnect
--             The LEC has not initiated a Control Direct
--             connection to the LES (i.e., it isn't part
--             of the emulated LAN).
--    
--         lesConnect
--             The Control Direct connection from the LEC
--             to the LES has been established.
--    
--         joining
--             The LES has gotten the LEC's Join request,
--             and is processing it (for instance, it may
--             be waiting for a Control Distribute VCC to
--             be established).
--    
--         operational
--             The LEC has successfully joined the ELAN.
--    
--         deleting
--             The LEC is being removed from the ELAN.

-- LeServiceEventReason ::= INTEGER {
--        versionNotSupported(1),
--        invalidRequestParameters(2),
--        duplicateLanDestination(4),
--        duplicateAtmAddress(5),
--        insufficientResources(6),
--        accessDenied(7),
--        invalidRequestorId(8),
--        invalidLanDestination(9),
--        invalidAtmAddress(10),
--        wrongLanType(50),
--        wrongMaxFrameSize(51),
--        wrongJoinMaxFrameSize(52),
--        nonDuplicateRequest(53),
--        controlDistributeFailure(54),
--        multicastForwardFailure(55),
--        joinNotCompleted(56),
--        joinTimeout(57),
--        busConnectTimeout(58),
--        clientNotConnectedToLes(59),
--        missingInformationElement(70),
--        noAalParameters(71),
--        noAtmTrafficDescriptor(72),
--        noBroadbandBearerCapability(73),
--        noBlli(74),
--        noCallingPartyNumber(75),
--        noCalledPartyNumber(76),
--        noConnectionIdentifier(77),
--        noQosParameter(78),
--        invalidInformationElement(80),
--        invalidAalParameters(81),
--        invalidAtmTrafficDescriptor(82),
--        invalidBroadbandBearerCapability(83),
--        invalidBlli(84),
--        invalidCallingPartyNumber(85),
--        invalidCalledPartyNumber(86),
--        invalidConnectionIdentifier(87),
--        invalidQosParameter(88),
--        invalidAalMode(90),
--        invalidAalSccs(91),
--        insecureAtmAddress(100),
--        unverifiedAtmAddress(101)
--        }
-- TEXTUAL-CONVENTION
--  Status
--    mandatory
--  Descr
--    A code in a LAN Emulation Server log, or Broadcast
--     and Unknown Server log, indicating why an operation
--     failed.
--    
--         versionNotSupported(1)
--             An operation failed because the client used a
--             version of the LAN Emulation protocol that is
--             not supported by the server.
--    
--         invalidRequestParameters(2)
--             An operation failed because the client
--             specified parameters that were incompatible
--             with the emulated LAN.
--    
--         duplicateLanDestination(4)
--             The LAN destination that a client tried to
--             register was already taken.
--    
--         duplicateAtmAddress(5)
--             The ATM address that a client tried to use
--             was already taken.
--    
--         insufficientResources(6)
--              An operation failed because the server ran
--              out of resources.
--    
--         accessDenied(7)
--              A request was denied for security reasons,
--              or an incoming Control Direct / Multicast
--              Send VCC was rejected for security reasons.
--    
--         invalidRequestorId(8)
--              'LECID field is not zero (Configure or Join)
--              or is not LE Client's LECID (others)'
--    
--         invalidLanDestination(9)
--             A Join or Registration attempt failed because
--             the client tried to register an 'illegal' LAN
--             destination (such as a multicast MAC address).
--    
--         invalidAtmAddress(10)
--             A Join attempt failed because the would-be
--             client specified an illegal ATM address in
--             the Join Request control frame.
--    
--         wrongLanType(50)
--             Lan Emulation Server:
--                 A Join attempt failed because the client
--                 specified a LAN Type that was incompatible
--                 with the emulated LAN.
--    
--             Broadcast and Unknown Server:
--                 A BUS Connect attempt failed because the
--                 client specified a LAN Type that was
--                 incompatible with the emulated LAN.
--    
--                 In normal operation, the most likely
--                 cause for this error is that the LES and
--                 the BUS are configured inconsistently.
--    
--        wrongMaxFrameSize(51)
--             Lan Emulation Server:
--                 A Join attempt failed because the caller
--                 specified incorrect Forward and/or
--                 Backward Maximum CPCS-SDU sizes for the
--                 Control Direct VCC.
--    
--             Broadcast and Unknown Server:
--                 A BUS connect attempt failed because the
--                 caller specified Forward and/or Backward
--                 Maximum CPCS-SDU sizes for the Multicast
--                 Send VCC which were incompatible with the
--                 emulated LAN.
--    
--                 In normal operation, the most likely
--                 cause for this error is that the LES and
--                 the BUS are configured inconsistently.
--    
--         wrongJoinMaxFrameSize(52)
--             A Join attempt failed because the caller
--             specified a maximum data frame size which
--             was incompatible with the emulated LAN.
--    
--         nonDuplicateRequest(53)
--             A Join attempt failed because the client
--             sent a Join request whose parameters did
--             not match the ones in its first request.
--    
--         controlDistributeFailure(54)
--             A Join attempt failed because the server
--             could not establish a Control Distribute
--             VCC to the would-be client.
--    
--         multicastForwardFailure(55)
--             A client's attempt to connect to a BUS
--             failed, because the BUS could not establish
--             a Multicast Forward VCC to the client.
--    
--         joinNotCompleted(56)
--             A Registration request failed because the
--             client had not completed the Join process.
--    
--         joinTimeout(57)
--             The server disconnected a Control Direct
--             VCC because a Join request was not seen
--             within some timeout period.
--    
--         busConnectTimeout(58)
--             [Reserved for future use]
--             A client was terminated by the LES because
--             it failed to connect to the BUS within a
--             reasonable time period.
--    
--         clientNotConnectedToLes(59)
--             [Reserved for future use]
--             A client's attempt to connect to a BUS
--             failed, because the BUS and LES, working
--             together, determined that the client was
--             not connected to the LES.
--    
--         missingInformationElement(70)
--             An incoming SVC was rejected because the
--             SETUP message was missing one or more of
--             the information elements required to
--             establish a Control Direct (or Multicast
--             Send) VCC.  This is a catch-all code that
--             can be used if more specific details are
--             not available.
--    
--         noAalParameters(71)
--             An incoming SVC was rejected because the
--             SETUP message did not include an AAL
--             Parameters information element.
--    
--         noAtmTrafficDescriptor(72)
--             An incoming SVC was rejected because the
--             SETUP message did not include an ATM User
--             Cell Rate / ATM Traffic Descriptor
--             information element.
--    
--         noBroadbandBearerCapability(73)
--             An incoming SVC was rejected because the
--             SETUP message did not include a Broadband
--             Bearer Capability information element.
--    
--         noBlli(74)
--             An incoming SVC was rejected because the
--             SETUP message did not include a Broadband
--             Low Layer Information information element.
--    
--         noCallingPartyNumber(75)
--             An incoming SVC was rejected because the
--             SETUP message did not include a Calling
--             Party Number information element.
--    
--         noCalledPartyNumber(76)
--             An incoming SVC was rejected because the
--             SETUP message did not include a Called
--             Party Number information element.
--    
--         noConnectionIdentifier(77)
--             An incoming SVC was rejected because the
--             SETUP message did not include a Connection
--             Identifier information element.
--    
--         noQosParameter(78)
--             An incoming SVC was rejected because the
--             SETUP message did not include a QoS
--             Parameter information element.
--    
--         invalidInformationElement(80)
--             An incoming SVC was rejected because the
--             server could not accept the values in one
--             or more of its information elements.  This
--             is a catch-all code that can be used if more
--             specific details are not available.
--    
--         invalidAalParameters(81)
--             An incoming SVC was rejected because the
--             server could not accept the values in its
--             AAL Parameters information element.
--    
--         invalidAtmTrafficDescriptor(82)
--             An incoming SVC was rejected because the
--             server could not accept the values in its
--             ATM User Cell Rate / ATM Traffic Descriptor
--             information element.
--    
--         invalidBroadbandBearerCapability(83)
--             An incoming SVC was rejected because the
--             server could not accept the values in its
--             Broadband Bearer Capability information
--             element.
--    
--         invalidBlli(84)
--             An incoming SVC was rejected because the
--             server could not accept the values in its
--             Broadband Low Layer Information information
--             element.
--    
--         invalidCallingPartyNumber(85)
--             An incoming SVC was rejected because the
--             server could not accept the values in its
--             Calling Party Number information element.
--    
--         invalidCalledPartyNumber(86)
--             An incoming SVC was rejected because the
--             server could not accept the values in its
--             Called Party Number information element.
--    
--         invalidConnectionIdentifier(87)
--             An incoming SVC was rejected because the
--             server could not accept the values in its
--             Connection Identifier information element.
--    
--         invalidQosParameter(88)
--             An incoming SVC was rejected because the
--             server could not accept the values in its
--             QoS Parameter information element.
--    
--         invalidAalMode(90)
--             An incoming SVC was rejected because it
--             had an invalid AAL Parameters 'Mode'.
--             For UNI 3.0, this field must be present
--             and must have a value of 1.  For UNI 3.1,
--             this field must not be present.
--    
--         invalidAAlSccs(91)
--             An incoming SVC was rejected because it
--             had an invalid AAL Parameters 'SCCS Type'.
--             This type must be 0 (Null SCCS).
--    
--         insecureAtmAddress(100)
--             [Reserved for future use]
--             An incoming SVC was rejected because its
--             Screening Indicator was 'User-supplied,
--             verified and failed'.
--    
--         unverifiedAtmAddress(101)
--             [Reserved for future use]
--             An incoming SVC was rejected because its
--             Screening Indicator was 'User-supplied,
--             not verified'.                               

decLesConfigTable OBJECT-TYPE
    SYNTAX SEQUENCE OF DecLesConfigEntry
    ACCESS not-accessible
    STATUS mandatory
    DESCRIPTION
        "A table describing all the LES components which this
         managed device supports."
    ::= { decLesMIBObjects 1 }

decLesConfigEntry OBJECT-TYPE
    SYNTAX DecLesConfigEntry
    ACCESS not-accessible
    STATUS mandatory
    DESCRIPTION
        "Each row describes one LES component, which might be
         either a standalone LES or part of a distributed LES."
    INDEX { decLesIndex }
    ::= { decLesConfigTable 1 }

DecLesConfigEntry ::= SEQUENCE {
    decLesIndex INTEGER,
    decLesRowStatus INTEGER,
    decLesAdminStatus INTEGER,
    decLesOperStatus INTEGER,
    decLesLastChange TimeTicks,
    decLesAtmAddress OCTET STRING,
    decLesDescription OCTET STRING,
    decLesLanName OCTET STRING,
    decLesLanType INTEGER,
    decLesMaxDataFrameSize INTEGER,
    decLesAtmAddressOfBUS OCTET STRING,
    decLesControlTimeout INTEGER,
    decLesArpResponsePolicy INTEGER,
    decLesNarpRequestPolicy INTEGER,
    decLesTopologyChangeMode INTEGER,
    decLesLastTcModeChange TimeTicks,
    decLesTopologyChangeTimeout INTEGER
    }

decLesIndex OBJECT-TYPE
    SYNTAX INTEGER
    ACCESS read-only
    STATUS mandatory
    DESCRIPTION
        "A unique number greater than zero which identifies
         this table row."
    ::= { decLesConfigEntry 1 }

decLesRowStatus OBJECT-TYPE
    SYNTAX INTEGER {
        active(1),
        notInService(2),
        notReady(3),
        createAndGo(4),
        createAndWait(5),
        destroy(6)
        }
    ACCESS read-write
    STATUS mandatory
    DESCRIPTION
        "This object is used to create and delete LAN Emulation
         Server components.
        
         If this object is writable, it will accept the values
             'createAndGo'
             'destroy'
         under suitable conditions.
        
         Use decLesAdminStatus to enable and disable service."
    ::= { decLesConfigEntry 2 }

decLesAdminStatus OBJECT-TYPE
    SYNTAX INTEGER {
        up(1),
        down(2)
        }
    ACCESS read-write
    STATUS mandatory
    DESCRIPTION
        "The desired state of this LES component.
        
         When a LES is distributed, this object controls the
         'local' server component, as opposed to the overall
         state of the LES.
        
         If a BUS is connected to the LES, enabling/disabling
         either server may affect both of them.  Otherwise it
         is up to the network manager to coordinate the state
         of the servers."
    DEFVAL { down }
    ::= { decLesConfigEntry 3 }

decLesOperStatus OBJECT-TYPE
    SYNTAX INTEGER {
        up(1),
        down(2),
        disabling(3),
        deleting(4)
        }
    ACCESS read-only
    STATUS mandatory
    DESCRIPTION
        "The operational state of this LES component.
        
         A LES component may not become operational until it
         has been configured with values for
        
                 LAN Type
                 Maximum Data Frame Size
                 Control Time-out
                 BUS ATM Address
        
         When a LES is in the 'disabling' or 'deleting' state,
         attempts to set decLesAdminStatus to 'up' will fail."
    ::= { decLesConfigEntry 4 }

decLesLastChange OBJECT-TYPE
    SYNTAX TimeTicks
    ACCESS read-only
    STATUS mandatory
    DESCRIPTION
        "The value of sysUpTime at the time that this server
         last entered its current operational state.  If the
         current state was entered prior to the last
         re-initialization of the local network management
         subsystem, then this object contains a zero value."
    ::= { decLesConfigEntry 5 }

decLesAtmAddress OBJECT-TYPE
    SYNTAX OCTET STRING(SIZE(0..20))
    ACCESS read-only
    STATUS mandatory
    DESCRIPTION
        "The ATM address of this LAN Emulation Server, or LAN
         Emulation Server component.
        
         Clients establish Control Direct VCCs to this address
         to initiate the process of Joining the emulated LAN."
    ::= { decLesConfigEntry 6 }

decLesDescription OBJECT-TYPE
    SYNTAX OCTET STRING(SIZE(0..80))
    ACCESS read-write
    STATUS mandatory
    DESCRIPTION
        "A human-readable string which can contain anything the
         network manager wants."
    ::= { decLesConfigEntry 7 }

decLesLanName OBJECT-TYPE
    SYNTAX OCTET STRING(SIZE(0..32))
    ACCESS read-write
    STATUS mandatory
    DESCRIPTION
        "The name of this emulated LAN.  This can be any string
         that the network manager would like this LES component
         to pass out to new clients.
        
         This string is not guaranteed to uniquely identify the
         emulated LAN."
    REFERENCE
        "ATM Forum LAN Emulation Over ATM Specification, V1.0,
         Section 5.1.1"
    ::= { decLesConfigEntry 8 }

decLesLanType OBJECT-TYPE
    SYNTAX INTEGER {
        aflane8023(2),
        aflane8025(3)
        }
    ACCESS read-write
    STATUS mandatory
    DESCRIPTION
        "The data frame format for this emulated LAN.
        
         In an active emulated LAN, this parameter MUST have a
         consistent value in all of the LES and BUS components
         serving the emulated LAN.  Otherwise various problems
         may result.
        
         The value of this columnar object may only be changed
         when this LAN Emulation Server has no active clients,
         and 'decLes[Admin,Oper]Status' are 'down'."
    REFERENCE
        "ATM Forum LAN Emulation Over ATM Specification, V1.0,
         Section 5.1.2"
    DEFVAL { aflane8023 }
    ::= { decLesConfigEntry 9 }

decLesMaxDataFrameSize OBJECT-TYPE
    SYNTAX INTEGER {
        max1516(2),
        max4544(3),
        max9234(4),
        max18190(5)
        }
    ACCESS read-write
    STATUS mandatory
    DESCRIPTION
        "The maximum AAL-5 SDU size for data frames sent over
         this emulated LAN.  This must be one of the standard
         sizes defined in the LAN Emulation specification.
        
         In an active emulated LAN, this parameter MUST have a
         consistent value in all of the LES and BUS components
         serving the emulated LAN.  Otherwise various problems
         may result.
        
         The value of this columnar object may only be changed
         when this LAN Emulation Server has no active clients,
         and 'decLes[Admin,Oper]Status' are 'down'."
    REFERENCE
        "ATM Forum LAN Emulation Over ATM Specification, V1.0,
         Section 5.1.2"
    DEFVAL { max1516 }
    ::= { decLesConfigEntry 10 }

decLesAtmAddressOfBUS OBJECT-TYPE
    SYNTAX OCTET STRING(SIZE(0..20))
    ACCESS read-write
    STATUS mandatory
    DESCRIPTION
        "The ATM address of the Broadcast and Unknown Server
         component associated with this LES component.
        
         Unless otherwise stated in product documentation, the
         value of this columnar object may only be changed when
         this LAN Emulation Server has no active clients, and
         'decLes[Admin,Oper]Status' are 'down'."
    ::= { decLesConfigEntry 11 }

decLesControlTimeout OBJECT-TYPE
    SYNTAX INTEGER(10..300)
--  Units
--    seconds
    ACCESS read-write
    STATUS mandatory
    DESCRIPTION
        "S4  Control Time-out.  Time out period used for
             timing out most request/response control frame
             interactions, as specified elsewhere.  Once a
             LE Client establishes a Control Direct VCC to
             the LE Server, the Join phase must complete
             within the Join Time-out time.  If not, the
             LE Service SHOULD release any Control VCCs to
             that LE Client, terminating the Join phase.
        
         If a LES is distributed, each of its servers should
         have the same value for this parameter."
    REFERENCE
        "ATM Forum LAN Emulation Over ATM Specification, V1.0,
         Section 5.1.2"
    DEFVAL { 120 }
    ::= { decLesConfigEntry 12 }

decLesArpResponsePolicy OBJECT-TYPE
    SYNTAX INTEGER {
        unspecified(1),
        direct(2),
        broadcast(3)
        }
    ACCESS read-write
    STATUS mandatory
    DESCRIPTION
        "Lets you fine-tune the performance of an emulated LAN
         by controlling the distribution of LE_ARP_RESPONSEs.
        
         You can choose from one of three policies:
        
             unspecified(1)
                 Leave everything up to the implementation.
        
             direct(2)
                 The LES sends responses only to the client
                 to which they are directed.  This reduces
                 the amount of overhead per response packet,
                 but may result in more LE_ARP traffic.
        
             broadcast(3)
                 The LES sends responses to all clients via
                 the Control Direct VCC.  This lets clients
                 learn LE_ARP information by eavesdropping,
                 but also increases per-packet overhead."
    DEFVAL { unspecified }
    ::= { decLesConfigEntry 13 }

decLesNarpRequestPolicy OBJECT-TYPE
    SYNTAX INTEGER {
        forward(1),
        filter(2)
        }
    ACCESS read-write
    STATUS mandatory
    DESCRIPTION
        "Controls whether this LES forwards LE_NARP_REQUESTs."
    DEFVAL { forward }
    ::= { decLesConfigEntry 14 }

decLesTopologyChangeMode OBJECT-TYPE
    SYNTAX INTEGER {
        true(1),
        false(2)
        }
    ACCESS read-only
    STATUS mandatory
    DESCRIPTION
        "The Topology Change mode which this LE Server believes
         the emulated LAN is in, based upon the Topology Change
         requests it has seen and/or generated.
        
         The value 'true' indicates accelerated aging mode - as
         opposed to normal aging mode."
    ::= { decLesConfigEntry 15 }

decLesLastTcModeChange OBJECT-TYPE
    SYNTAX TimeTicks
    ACCESS read-only
    STATUS mandatory
    DESCRIPTION
        "The value of sysUpTime at the time that the object
         'decLesTopologyChangeMode' last acquired its current
         value.  If the current value was acquired prior to
         the last re-initialization of the local network
         management subsystem, then this object contains a
         zero value."
    ::= { decLesConfigEntry 16 }

decLesTopologyChangeTimeout OBJECT-TYPE
    SYNTAX INTEGER(10..600)
--  Units
--    seconds
    ACCESS read-write
    STATUS mandatory
    DESCRIPTION
        "Provides a guard against an emulated LAN remaining in
         accelerated aging mode forever.
        
         If an emulated LAN remains in the accelerated aging
         state for more than 'decLesTopologyChangeTimeout'
         seconds following the last Topology Request, the LE
         Server will automatically issue a Topology Request
         frame to reset all the clients to normal aging mode.
        
         This value is measured in seconds, and should be set
         higher than the normal time between bridge BPDUs."
    DEFVAL { 120 }
    ::= { decLesConfigEntry 17 }

decLesClientStatesTable OBJECT-TYPE
    SYNTAX SEQUENCE OF DecLesClientStatesEntry
    ACCESS not-accessible
    STATUS mandatory
    DESCRIPTION
        "A table describing how many clients are in various
         membership states."
    ::= { decLesMIBObjects 2 }

decLesClientStatesEntry OBJECT-TYPE
    SYNTAX DecLesClientStatesEntry
    ACCESS not-accessible
    STATUS mandatory
    DESCRIPTION
        "Each row contains counters for one LES component."
    INDEX { decLesIndex }
-- Augments decLesConfigEntry
    ::= { decLesClientStatesTable 1 }

DecLesClientStatesEntry ::= SEQUENCE {
    decLesActiveClients INTEGER,
    decLesActiveProxyClients INTEGER,
    decLesAwaitingJoinRequest INTEGER,
    decLesCtlDistributeInProgress INTEGER,
    decLesTerminating INTEGER
    }

decLesActiveClients OBJECT-TYPE
    SYNTAX INTEGER
    ACCESS read-only
    STATUS mandatory
    DESCRIPTION
        "The number of active clients of this LES component."
    ::= { decLesClientStatesEntry 1 }

decLesActiveProxyClients OBJECT-TYPE
    SYNTAX INTEGER
    ACCESS read-only
    STATUS mandatory
    DESCRIPTION
        "The number of active proxy clients of this LES
         component."
    ::= { decLesClientStatesEntry 2 }

decLesAwaitingJoinRequest OBJECT-TYPE
    SYNTAX INTEGER
    ACCESS read-only
    STATUS mandatory
    DESCRIPTION
        "The number of Control Direct VCCs on which this
         LES component is waiting for a Join request."
    ::= { decLesClientStatesEntry 3 }

decLesCtlDistributeInProgress OBJECT-TYPE
    SYNTAX INTEGER
    ACCESS read-only
    STATUS mandatory
    DESCRIPTION
        "The number of clients to which this LES component
         is currently establishing Control Distribute VCCs."
    ::= { decLesClientStatesEntry 4 }

decLesTerminating OBJECT-TYPE
    SYNTAX INTEGER
    ACCESS read-only
    STATUS mandatory
    DESCRIPTION
        "The number of clients whose memberships this LES
         component is in the process of terminating."
    ::= { decLesClientStatesEntry 5 }

decLesClientTable OBJECT-TYPE
    SYNTAX SEQUENCE OF DecLesClientEntry
    ACCESS not-accessible
    STATUS mandatory
    DESCRIPTION
        "A table listing clients which belong to the emulated
         LANs that this node serves.  This table reflects the
         actual state of each emulated LAN, as opposed to the
         way the network manager would like to see LE clients
         and servers configured.
        
         This table contains only local clients - that is, to
         say, clients connected directly to one of the server
         components which this agent manages."
    ::= { decLesMIBObjects 3 }

decLesClientEntry OBJECT-TYPE
    SYNTAX DecLesClientEntry
    ACCESS not-accessible
    STATUS mandatory
    DESCRIPTION
        "Each entry describes an active LAN Emulation Client,
         from the perspective of the LES."
    INDEX { decLesIndex, decLesClientID }
    ::= { decLesClientTable 1 }

DecLesClientEntry ::= SEQUENCE {
    decLesClientID INTEGER,
    decLesClientAtmAddress OCTET STRING,
    decLesClientIsProxy INTEGER,
    decLesClientState INTEGER,
    decLesClientRowStatus INTEGER
    }

decLesClientID OBJECT-TYPE
    SYNTAX INTEGER(1..65279)
    ACCESS read-only
    STATUS mandatory
    DESCRIPTION
        "The LEC-ID which the LES handed to the LAN Emulation
         Client as part of the Join process."
    ::= { decLesClientEntry 1 }

decLesClientAtmAddress OBJECT-TYPE
    SYNTAX OCTET STRING(SIZE(0..20))
    ACCESS read-only
    STATUS mandatory
    DESCRIPTION
        "The primary ATM address of the LAN Emulation Client."
    ::= { decLesClientEntry 2 }

decLesClientIsProxy OBJECT-TYPE
    SYNTAX INTEGER {
        true(1),
        false(2)
        }
    ACCESS read-only
    STATUS mandatory
    DESCRIPTION
        "Indicates whether this client is a proxy client."
    ::= { decLesClientEntry 3 }

decLesClientState OBJECT-TYPE
    SYNTAX INTEGER {
        other(1),
        noLesConnect(2),
        lesConnect(3),
        joining(4),
        operational(5),
        deleting(6)
        }
    ACCESS read-only
    STATUS mandatory
    DESCRIPTION
        "Indicates the status of this LEC from the server's
         perspective."
    ::= { decLesClientEntry 4 }

decLesClientRowStatus OBJECT-TYPE
    SYNTAX INTEGER {
        active(1),
        notInService(2),
        notReady(3),
        createAndGo(4),
        createAndWait(5),
        destroy(6)
        }
    ACCESS read-write
    STATUS mandatory
    DESCRIPTION
        "Provides a way to disconnect a LEC from the emulated
         LAN.
        
         When read, this object has the value 'active'.  When
         written, it accepts the value 'destroy'.
        
         Because the ability to disconnect clients could lead
         to denial-of-service attacks, support for this
         feature is strictly optional."
    ::= { decLesClientEntry 5 }

decLesLecTable OBJECT-TYPE
    SYNTAX SEQUENCE OF DecLesLecEntry
    ACCESS not-accessible
    STATUS mandatory
    DESCRIPTION
        "A table listing clients which belong to the emulated
         LANs that this node serves."
    ::= { decLesMIBObjects 4 }

decLesLecEntry OBJECT-TYPE
    SYNTAX DecLesLecEntry
    ACCESS not-accessible
    STATUS mandatory
    DESCRIPTION
        "Each entry describes a LAN Emulation Client from the
         perspective of the LES."
    INDEX { decLesIndex, decLesLecAtmAddress }
    ::= { decLesLecTable 1 }

DecLesLecEntry ::= SEQUENCE {
    decLesLecAtmAddress OCTET STRING,
    decLesLecID INTEGER,
    decLesLecIsProxy INTEGER,
    decLesLecState INTEGER,
    decLesLecRowStatus INTEGER
    }

decLesLecAtmAddress OBJECT-TYPE
    SYNTAX OCTET STRING(SIZE(0..20))
    ACCESS read-only
    STATUS mandatory
    DESCRIPTION
        "The primary ATM address of the LAN Emulation Client."
    ::= { decLesLecEntry 1 }

decLesLecID OBJECT-TYPE
    SYNTAX INTEGER(0..65279)
    ACCESS read-only
    STATUS mandatory
    DESCRIPTION
        "For an active client, the LEC-ID that the LES handed
         to the client as part of the Join process.
        
         For an inactive client, the value zero."
    ::= { decLesLecEntry 2 }

decLesLecIsProxy OBJECT-TYPE
    SYNTAX INTEGER {
        true(1),
        false(2)
        }
    ACCESS read-only
    STATUS mandatory
    DESCRIPTION
        "Indicates whether this client is a proxy client."
    ::= { decLesLecEntry 3 }

decLesLecState OBJECT-TYPE
    SYNTAX INTEGER {
        other(1),
        noLesConnect(2),
        lesConnect(3),
        joining(4),
        operational(5),
        deleting(6)
        }
    ACCESS read-only
    STATUS mandatory
    DESCRIPTION
        "Indicates the status of this LEC from the server's
         perspective."
    ::= { decLesLecEntry 4 }

decLesLecRowStatus OBJECT-TYPE
    SYNTAX INTEGER {
        active(1),
        notInService(2),
        notReady(3),
        createAndGo(4),
        createAndWait(5),
        destroy(6)
        }
    ACCESS read-write
    STATUS mandatory
    DESCRIPTION
        "Provides a way to disconnect a LEC from the emulated
         LAN.
        
         When read, this object has the value 'active'.  When
         written, it only accepts the value 'destroy'.
        
         Because the ability to disconnect clients could lead
         to denial-of-service attacks, support for this
         feature is strictly optional."
    ::= { decLesLecEntry 5 }

decLesCtlDirectTable OBJECT-TYPE
    SYNTAX SEQUENCE OF DecLesCtlDirectEntry
    ACCESS not-accessible
    STATUS mandatory
    DESCRIPTION
        "This optional table identifies Control Direct VCCs
         at the place where they attach to the LES.
        
         In a SVC implementation, the objects in this table
         will be read-only.
        
         In a PVC implementation, this table can be used to
         tell the LES about the creation or the deletion of
         Control Direct VCCs."
    ::= { decLesMIBObjects 5 }

decLesCtlDirectEntry OBJECT-TYPE
    SYNTAX DecLesCtlDirectEntry
    ACCESS not-accessible
    STATUS mandatory
    DESCRIPTION
        "Each entry describes the circuits going to one LAN
         Emulation Client."
    INDEX { decLesIndex, decLesLecAtmAddress }
-- Augments decLesLecEntry
    ::= { decLesCtlDirectTable 1 }

DecLesCtlDirectEntry ::= SEQUENCE {
    decLesControlDirectInterface INTEGER,
    decLesControlDirectVpi INTEGER,
    decLesControlDirectVci INTEGER,
    decLesControlDirectRowStatus INTEGER
    }

decLesControlDirectInterface OBJECT-TYPE
    SYNTAX INTEGER(0..2147483647)
    ACCESS read-write
    STATUS mandatory
    DESCRIPTION
        "If a Control Direct VCC exists, this object contains
         the 'ifIndex' of the ATM port which terminates that
         circuit at the LES.
        
         Otherwise, its value is 0."
    ::= { decLesCtlDirectEntry 1 }

decLesControlDirectVpi OBJECT-TYPE
    SYNTAX INTEGER(0..255)
    ACCESS read-write
    STATUS mandatory
    DESCRIPTION
        "If a Control Direct VCC exists, this object contains
         the VPI of the Control Direct VCC at the point where
         it connects to the LES.
        
         Otherwise, its value is 0."
    ::= { decLesCtlDirectEntry 2 }

decLesControlDirectVci OBJECT-TYPE
    SYNTAX INTEGER(0..65535)
    ACCESS read-write
    STATUS mandatory
    DESCRIPTION
        "If a Control Direct VCC exists, this object contains
         the VCI of the Control Direct VCC at the point where
         it connects to the LES.
        
         Otherwise, its value is 0."
    ::= { decLesCtlDirectEntry 3 }

decLesControlDirectRowStatus OBJECT-TYPE
    SYNTAX INTEGER {
        active(1),
        notInService(2),
        notReady(3),
        createAndGo(4),
        createAndWait(5),
        destroy(6)
        }
    ACCESS read-write
    STATUS mandatory
    DESCRIPTION
        "Used to create and delete rows in the table."
    ::= { decLesCtlDirectEntry 4 }

decLesCtlDistTable OBJECT-TYPE
    SYNTAX SEQUENCE OF DecLesCtlDistEntry
    ACCESS not-accessible
    STATUS mandatory
    DESCRIPTION
        "This optional table identifies Control Distribute
         VCCs at the place where they attach to the LES.
        
         In a SVC implementation, this table will be read-
         only.
        
         In a PVC implementation, this table can be used to
         tell the LES about the creation or the deletion of
         Control Distribute VCCs."
    ::= { decLesMIBObjects 6 }

decLesCtlDistEntry OBJECT-TYPE
    SYNTAX DecLesCtlDistEntry
    ACCESS not-accessible
    STATUS mandatory
    DESCRIPTION
        "Each entry describes one Control Distribute VCC."
    INDEX { decLesIndex, decLesControlDistInterface, decLesControlDistVpi,
            decLesControlDistVci }
    ::= { decLesCtlDistTable 1 }

DecLesCtlDistEntry ::= SEQUENCE {
    decLesControlDistInterface INTEGER,
    decLesControlDistVpi INTEGER,
    decLesControlDistVci INTEGER,
    decLesControlDistRowStatus INTEGER
    }

decLesControlDistInterface OBJECT-TYPE
    SYNTAX INTEGER(0..2147483647)
    ACCESS read-only
    STATUS mandatory
    DESCRIPTION
        "The 'ifIndex' of the ATM port which terminates the
         Control Distribute VCC at the LES."
    ::= { decLesCtlDistEntry 1 }

decLesControlDistVpi OBJECT-TYPE
    SYNTAX INTEGER(0..255)
    ACCESS read-only
    STATUS mandatory
    DESCRIPTION
        "The VPI of the Control Distribute VCC at the point
         where this VCC connects to the LES."
    ::= { decLesCtlDistEntry 2 }

decLesControlDistVci OBJECT-TYPE
    SYNTAX INTEGER(0..65535)
    ACCESS read-only
    STATUS mandatory
    DESCRIPTION
        "The VCI of the Control Distribute VCC at the point
         where this VCC connects to the LES."
    ::= { decLesCtlDistEntry 3 }

decLesControlDistRowStatus OBJECT-TYPE
    SYNTAX INTEGER {
        active(1),
        notInService(2),
        notReady(3),
        createAndGo(4),
        createAndWait(5),
        destroy(6)
        }
    ACCESS read-write
    STATUS mandatory
    DESCRIPTION
        "An object provided to satisfy the requirement that
         all tables have at least one accessible object; in
         the future, it may also be extended to provide PVC
         support."
    ::= { decLesCtlDistEntry 4 }

decLesMacAddressTable OBJECT-TYPE
    SYNTAX SEQUENCE OF DecLesMacAddressEntry
    ACCESS not-accessible
    STATUS mandatory
    DESCRIPTION
        "A table of unicast MAC addresses registered with this
         host's LES components by their local clients."
    ::= { decLesMIBObjects 7 }

decLesMacAddressEntry OBJECT-TYPE
    SYNTAX DecLesMacAddressEntry
    ACCESS not-accessible
    STATUS mandatory
    DESCRIPTION
        "Each entry describes one registered (MAC address, ATM
         address) pair."
    INDEX { decLesIndex, decLesMacAddress }
    ::= { decLesMacAddressTable 1 }

DecLesMacAddressEntry ::= SEQUENCE {
    decLesMacAddress OCTET STRING,
    decLesMacAddressOwner INTEGER,
    decLesMacAddressAtmBinding OCTET STRING
    }

decLesMacAddress OBJECT-TYPE
    SYNTAX OCTET STRING(SIZE(6))
    ACCESS read-only
    STATUS mandatory
    DESCRIPTION
        "One of the MAC addresses registered with the LAN
         Emulation Server 'decLesIndex'."
    ::= { decLesMacAddressEntry 1 }

decLesMacAddressOwner OBJECT-TYPE
    SYNTAX INTEGER
    ACCESS read-only
    STATUS mandatory
    DESCRIPTION
        "The LECID of the client that registered this MAC
         address."
    ::= { decLesMacAddressEntry 2 }

decLesMacAddressAtmBinding OBJECT-TYPE
    SYNTAX OCTET STRING(SIZE(0..20))
    ACCESS read-only
    STATUS mandatory
    DESCRIPTION
        "The ATM address associated with this MAC address."
    ::= { decLesMacAddressEntry 3 }

decLesRouteDescrTable OBJECT-TYPE
    SYNTAX SEQUENCE OF DecLesRouteDescrEntry
    ACCESS not-accessible
    STATUS mandatory
    DESCRIPTION
        "A table of IEEE 802.5 Route Descriptors registered
         with this host's LES components by their local
         clients."
    ::= { decLesMIBObjects 8 }

decLesRouteDescrEntry OBJECT-TYPE
    SYNTAX DecLesRouteDescrEntry
    ACCESS not-accessible
    STATUS mandatory
    DESCRIPTION
        "Each table row describes a (Route Descriptor, ATM
         address) pair registered for a particular client."
    INDEX { decLesIndex, decLesRouteDescrSegmentID,
            decLesRouteDescrBridgeNumber }
    ::= { decLesRouteDescrTable 1 }

DecLesRouteDescrEntry ::= SEQUENCE {
    decLesRouteDescrSegmentID INTEGER,
    decLesRouteDescrBridgeNumber INTEGER,
    decLesRouteDescrOwner INTEGER,
    decLesRouteDescrAtmBinding OCTET STRING
    }

decLesRouteDescrSegmentID OBJECT-TYPE
    SYNTAX INTEGER(0..4095)
    ACCESS read-only
    STATUS mandatory
    DESCRIPTION
        "The LAN ID portion of the IEEE 802.5 route descriptor
         associated with this conceptual row."
    ::= { decLesRouteDescrEntry 1 }

decLesRouteDescrBridgeNumber OBJECT-TYPE
    SYNTAX INTEGER(0..15)
    ACCESS read-only
    STATUS mandatory
    DESCRIPTION
        "The Bridge Number portion of the IEEE 802.5 route
         descriptor associated with this conceptual row."
    ::= { decLesRouteDescrEntry 2 }

decLesRouteDescrOwner OBJECT-TYPE
    SYNTAX INTEGER
    ACCESS read-only
    STATUS mandatory
    DESCRIPTION
        "The LECID of the client that registered this route
         descriptor."
    ::= { decLesRouteDescrEntry 3 }

decLesRouteDescrAtmBinding OBJECT-TYPE
    SYNTAX OCTET STRING(SIZE(0..20))
    ACCESS read-only
    STATUS mandatory
    DESCRIPTION
        "The ATM address registered for the IEEE 802.5 route
         descriptor ('decLesRouteDescrSegmentID',
         'decLesRouteDescrBridgeNumber')."
    ::= { decLesRouteDescrEntry 4 }

decLesTrafficTable OBJECT-TYPE
    SYNTAX SEQUENCE OF DecLesTrafficEntry
    ACCESS not-accessible
    STATUS mandatory
    DESCRIPTION
        "A table of traffic statistics, with one row for each
         Broadcast and Unknown Server."
    ::= { decLesMIBObjects 9 }

decLesTrafficEntry OBJECT-TYPE
    SYNTAX DecLesTrafficEntry
    ACCESS not-accessible
    STATUS mandatory
    DESCRIPTION
        "A set of traffic statistics for one BUS component."
    INDEX { decLesIndex }
    ::= { decLesTrafficTable 1 }

DecLesTrafficEntry ::= SEQUENCE {
    decLesControlFramesIn Counter,
    decLesShortFrames Counter,
    decLesUnjoinedClientFrames Counter,
    decLesVersionsNotSupported Counter,
    decLesInvalidFrames Counter,
    decLesReceiveQueueDiscards Counter,
    decLesMiscDiscards Counter
    }

decLesControlFramesIn OBJECT-TYPE
    SYNTAX Counter
    ACCESS read-only
    STATUS mandatory
    DESCRIPTION
        "The total number of control frames received by this
         LES component.  This includes invalid frames."
    ::= { decLesTrafficEntry 1 }

decLesShortFrames OBJECT-TYPE
    SYNTAX Counter
    ACCESS read-only
    STATUS mandatory
    DESCRIPTION
        "The number of frames which were discarded because
         they were too short, and which are not included in
         any other error count."
    ::= { decLesTrafficEntry 2 }

decLesUnjoinedClientFrames OBJECT-TYPE
    SYNTAX Counter
    ACCESS read-only
    STATUS mandatory
    DESCRIPTION
        "The number of frames which were discarded because a
         client had not completed the Join process, and which
         are not included in any other error count."
    ::= { decLesTrafficEntry 3 }

decLesVersionsNotSupported OBJECT-TYPE
    SYNTAX Counter
    ACCESS read-only
    STATUS mandatory
    DESCRIPTION
        "The number of frames which were discarded because
         they specified a version of the LAN Emulation protocol
         which the server does not support.
        
         This count does not include Join frames counted by the
         MIB object 'decLesJoinVersionsNotSupported'."
    ::= { decLesTrafficEntry 4 }

decLesInvalidFrames OBJECT-TYPE
    SYNTAX Counter
    ACCESS read-only
    STATUS mandatory
    DESCRIPTION
        "The number of frames which were discarded because of
         invalid frame formats, and which are not included in
         any other error count.  This counter includes frames
         with invalid MARKERs and OPCODEs."
    ::= { decLesTrafficEntry 5 }

decLesReceiveQueueDiscards OBJECT-TYPE
    SYNTAX Counter
    ACCESS read-only
    STATUS mandatory
    DESCRIPTION
        "The number of frames discarded due to receive queue
         overflows, and not included in other discard counts."
    ::= { decLesTrafficEntry 6 }

decLesMiscDiscards OBJECT-TYPE
    SYNTAX Counter
    ACCESS read-only
    STATUS mandatory
    DESCRIPTION
        "The number of incoming frames which were discarded
         due to no fault of their own, and which are not
         included in any other discard count or error count."
    ::= { decLesTrafficEntry 7 }

decLesCallStatsTable OBJECT-TYPE
    SYNTAX SEQUENCE OF DecLesCallStatsEntry
    ACCESS not-accessible
    STATUS mandatory
    DESCRIPTION
        "This table holds statistics on virtual circuit/leaf
         establishment attempts.
        
         It contains one row for each LAN Emulation Server,
         and acts as an extension to 'decLesServicesTable'."
    ::= { decLesMIBObjects 10 }

decLesCallStatsEntry OBJECT-TYPE
    SYNTAX DecLesCallStatsEntry
    ACCESS not-accessible
    STATUS mandatory
    DESCRIPTION
        "Each row contains connection statistics for one LAN
         Emulation Server."
    INDEX { decLesIndex }
-- Augments decLesConfigEntry
    ::= { decLesCallStatsTable 1 }

DecLesCallStatsEntry ::= SEQUENCE {
    decLesCtlDirectCalls Counter,
    decLesCtlDirectFailures Counter,
    decLesCtlDirectOutOfResources Counter,
    decLesCtlDirectInvalidInfoElements Counter,
    decLesCtlDistributeCalls Counter,
    decLesCtlDistributeFailures Counter,
    decLesCtlDistribOutOfResources Counter
    }

decLesCtlDirectCalls OBJECT-TYPE
    SYNTAX Counter
    ACCESS read-only
    STATUS mandatory
    DESCRIPTION
        "The total number of Control Direct VCC establishment
         attempts for this LES component."
    ::= { decLesCallStatsEntry 1 }

decLesCtlDirectFailures OBJECT-TYPE
    SYNTAX Counter
    ACCESS read-only
    STATUS mandatory
    DESCRIPTION
        "The number of Control Direct establishment attempts
         for this LES component which were not accepted.
        
         This includes failures counted in
        
                 decLesCtlDirectOutOfResources
                 decLesCtlDirectInvalidInfoElements
        
         and any miscellaneous failures."
    ::= { decLesCallStatsEntry 2 }

decLesCtlDirectOutOfResources OBJECT-TYPE
    SYNTAX Counter
    ACCESS read-only
    STATUS mandatory
    DESCRIPTION
        "The number of Control Direct establishment attempts
         for this LES component which failed for lack of
         resources."
    ::= { decLesCallStatsEntry 3 }

decLesCtlDirectInvalidInfoElements OBJECT-TYPE
    SYNTAX Counter
    ACCESS read-only
    STATUS mandatory
    DESCRIPTION
        "The number of Control Direct establishment attempts
         for this LES component which failed because required
         information elements were missing or contained
         invalid information.
        
         The optional Event Log group can help you determine
         which information elements were invalid or missing."
    ::= { decLesCallStatsEntry 4 }

decLesCtlDistributeCalls OBJECT-TYPE
    SYNTAX Counter
    ACCESS read-only
    STATUS mandatory
    DESCRIPTION
        "The total number of Control Distribute connections
         which this LES component tried to establish to
         clients."
    ::= { decLesCallStatsEntry 5 }

decLesCtlDistributeFailures OBJECT-TYPE
    SYNTAX Counter
    ACCESS read-only
    STATUS mandatory
    DESCRIPTION
        "The number of Control Distribute connections which
         this LES component was unable to establish.
        
         This includes failures counted in
        
                 decLesCtlDistribOutOfResources
                 decLesJoinCtlDistributeRejects
        
         and any miscellaneous failures."
    ::= { decLesCallStatsEntry 6 }

decLesCtlDistribOutOfResources OBJECT-TYPE
    SYNTAX Counter
    ACCESS read-only
    STATUS mandatory
    DESCRIPTION
        "The number of Control Distribute connections which
         this LES component could not establish due to lack
         of resources."
    ::= { decLesCallStatsEntry 7 }

decLesJoinTable OBJECT-TYPE
    SYNTAX SEQUENCE OF DecLesJoinEntry
    ACCESS not-accessible
    STATUS mandatory
    DESCRIPTION
        "This table holds statistics on Join attempts.  It
         contains one row for each managed LES component."
    REFERENCE
        "ATM Forum LAN Emulation Over ATM Specification, V1.0,
         Section 5.4"
    ::= { decLesMIBObjects 11 }

decLesJoinEntry OBJECT-TYPE
    SYNTAX DecLesJoinEntry
    ACCESS not-accessible
    STATUS mandatory
    DESCRIPTION
        "Each row contains Join statistics for one LES."
    INDEX { decLesIndex }
-- Augments decLesConfigEntry
    ::= { decLesJoinTable 1 }

DecLesJoinEntry ::= SEQUENCE {
    decLesJoinRequests Counter,
    decLesJoinSuccesses Counter,
    decLesJoinFailures Counter,
    decLesJoinDuplicates Counter,
    decLesJoinNonDuplicates Counter,
    decLesJoinDiscards Counter,
    decLesJoinTimeouts Counter,
    decLesJoinVersionsNotSupported Counter,
    decLesJoinInvalidParameters Counter,
    decLesJoinDuplicateAtmAddresses Counter,
    decLesJoinDuplicateLanDestinations Counter,
    decLesJoinInvalidAtmAddresses Counter,
    decLesJoinInvalidLanDestinations Counter,
    decLesJoinWrongLanTypes Counter,
    decLesJoinMaxFrameSizesTooSmall Counter,
    decLesJoinInvalidLECIDs Counter,
    decLesJoinCtlDistributeRejects Counter,
    decLesJoinOutOfResources Counter,
    decLesJoinRcvQueueDiscards Counter,
    decLesJoinLecRcvQueueDiscards Counter,
    decLesJoinResourceDiscards Counter
    }

decLesJoinRequests OBJECT-TYPE
    SYNTAX Counter
    ACCESS read-only
    STATUS mandatory
    DESCRIPTION
        "The total number of Join requests received by this
         LES component."
    ::= { decLesJoinEntry 1 }

decLesJoinSuccesses OBJECT-TYPE
    SYNTAX Counter
    ACCESS read-only
    STATUS mandatory
    DESCRIPTION
        "The number of first-time Join requests accepted by
         this LES component."
    ::= { decLesJoinEntry 2 }

decLesJoinFailures OBJECT-TYPE
    SYNTAX Counter
    ACCESS read-only
    STATUS mandatory
    DESCRIPTION
        "The number of first-time Join requests rejected by
         this LES component.
        
         This includes requests counted in
        
                 decLesJoinInvalidParameters
                 decLesJoinDuplicateAtmAddresses
                 decLesJoinDuplicateLanDestinations
                 decLesJoinInvalidAtmAddresses
                 decLesJoinInvalidLanDestinations
                 decLesJoinWrongLanTypes
                 decLesJoinMaxFrameSizesTooSmall
                 decLesJoinInvalidLECIDs
                 decLesJoinCtlDistributeRejects
                 decLesJoinOutOfResources
        
         This value does not include failures counted in
        
                 decLesJoinDuplicates
                 decLesJoinNonDuplicates
                 decLesJoinDiscards
                 decLesJoinTimeouts
                 decLesJoinVersionsNotSupported            "
    ::= { decLesJoinEntry 3 }

decLesJoinDuplicates OBJECT-TYPE
    SYNTAX Counter
    ACCESS read-only
    STATUS mandatory
    DESCRIPTION
        "The number of duplicate Join requests received by
         this LES component.  Each duplicate Join request is
         answered with a duplicate Join response.  These do
         not count towards the various 'successful Join' and
         'failed Join' statistics."
    REFERENCE
        "ATM Forum LAN Emulation Over ATM Specification, V1.0,
         Section 5.4.2.14"
    ::= { decLesJoinEntry 4 }

decLesJoinNonDuplicates OBJECT-TYPE
    SYNTAX Counter
    ACCESS read-only
    STATUS mandatory
    DESCRIPTION
        "The number of Join requests which were rejected by
         this LES component because they differed from
         previous Join requests received over the same Control
         Direct VCCs.  Clients which send such requests are
         terminated."
    REFERENCE
        "ATM Forum LAN Emulation Over ATM Specification, V1.0,
         Section 5.4.2.14"
    ::= { decLesJoinEntry 5 }

decLesJoinDiscards OBJECT-TYPE
    SYNTAX Counter
    ACCESS read-only
    STATUS mandatory
    DESCRIPTION
        "The number of Join requests which were discarded
         due to no fault of their own, and for which this
         LES component sent no Join response."
    ::= { decLesJoinEntry 6 }

decLesJoinTimeouts OBJECT-TYPE
    SYNTAX Counter
    ACCESS read-only
    STATUS mandatory
    DESCRIPTION
        "The number of Control Direct VCCs which this LES
         closed because their callers failed to send Join
         requests within a reasonable time-out period."
    REFERENCE
        "ATM Forum LAN Emulation Over ATM Specification, V1.0,
         Section 5.4.2.2"
    ::= { decLesJoinEntry 7 }

decLesJoinVersionsNotSupported OBJECT-TYPE
    SYNTAX Counter
    ACCESS read-only
    STATUS mandatory
    DESCRIPTION
        "The number of Join requests which were ignored by
         this LES component because they specified a version
         of the LAN Emulation protocol which the server does
         not support.  As per the specification, such requests
         are not answered with response frames."
    ::= { decLesJoinEntry 8 }

decLesJoinInvalidParameters OBJECT-TYPE
    SYNTAX Counter
    ACCESS read-only
    STATUS mandatory
    DESCRIPTION
        "The number of Join requests which were rejected by
         this LES component due to invalid parameters (such
         as a non-zero STATUS in the Join request frame)."
    ::= { decLesJoinEntry 9 }

decLesJoinDuplicateAtmAddresses OBJECT-TYPE
    SYNTAX Counter
    ACCESS read-only
    STATUS mandatory
    DESCRIPTION
        "The number of Join requests which were rejected
         by this LES component because they specified a
         duplicate ATM address."
    REFERENCE
        "ATM Forum LAN Emulation Over ATM Specification, V1.0,
         Section 5.4.2.6"
    ::= { decLesJoinEntry 10 }

decLesJoinDuplicateLanDestinations OBJECT-TYPE
    SYNTAX Counter
    ACCESS read-only
    STATUS mandatory
    DESCRIPTION
        "The number of Join requests which were rejected
         by this LES component because they specified a
         duplicate LAN destination."
    REFERENCE
        "ATM Forum LAN Emulation Over ATM Specification, V1.0,
         Section 5.4.2.5"
    ::= { decLesJoinEntry 11 }

decLesJoinInvalidAtmAddresses OBJECT-TYPE
    SYNTAX Counter
    ACCESS read-only
    STATUS mandatory
    DESCRIPTION
        "The number of Join requests which were rejected by
         this LES component because they specified an invalid
         ATM address, or because the would-be clients violated
         the rules concerning primary ATM addresses."
    REFERENCE
        "ATM Forum LAN Emulation Over ATM Specification, V1.0,
         Sections 4.2, 5.1.1"
    ::= { decLesJoinEntry 12 }

decLesJoinInvalidLanDestinations OBJECT-TYPE
    SYNTAX Counter
    ACCESS read-only
    STATUS mandatory
    DESCRIPTION
        "The number of Join requests which were rejected
         by this LES component because they specified an
         illegal LAN destination, such as a multicast or
         broadcast MAC address."
    REFERENCE
        "ATM Forum LAN Emulation Over ATM Specification, V1.0,
         Section 5.4.2.4"
    ::= { decLesJoinEntry 13 }

decLesJoinWrongLanTypes OBJECT-TYPE
    SYNTAX Counter
    ACCESS read-only
    STATUS mandatory
    DESCRIPTION
        "The number of Join requests which were rejected
         by this LES component because they specified the
         wrong LAN Type."
    REFERENCE
        "ATM Forum LAN Emulation Over ATM Specification, V1.0,
         Section 5.4.2.4"
    ::= { decLesJoinEntry 14 }

decLesJoinMaxFrameSizesTooSmall OBJECT-TYPE
    SYNTAX Counter
    ACCESS read-only
    STATUS mandatory
    DESCRIPTION
        "The number of Join requests which were rejected
         by this LES component because they specified a
         maximum frame size smaller than the one configured
         for the emulated LAN."
    REFERENCE
        "ATM Forum LAN Emulation Over ATM Specification, V1.0,
         Section 5.4.2.4"
    ::= { decLesJoinEntry 15 }

decLesJoinInvalidLECIDs OBJECT-TYPE
    SYNTAX Counter
    ACCESS read-only
    STATUS mandatory
    DESCRIPTION
        "The number of Join requests which were rejected
         by this LES component because they specified a
         REQUESTER-LECID other than zero."
    REFERENCE
        "ATM Forum LAN Emulation Over ATM Specification, V1.0,
         Section 5.4.2.6"
    ::= { decLesJoinEntry 16 }

decLesJoinCtlDistributeRejects OBJECT-TYPE
    SYNTAX Counter
    ACCESS read-only
    STATUS mandatory
    DESCRIPTION
        "The number of Join requests which were rejected
         by this LES component because the client failed
         to accept a Control Distribute VCC connection."
    REFERENCE
        "ATM Forum LAN Emulation Over ATM Specification, V1.0,
         Section 5.4.2.7"
    ::= { decLesJoinEntry 17 }

decLesJoinOutOfResources OBJECT-TYPE
    SYNTAX Counter
    ACCESS read-only
    STATUS mandatory
    DESCRIPTION
        "The number of Join requests which were rejected
         by this LES component because the LES ran out
         of resources."
    ::= { decLesJoinEntry 18 }

decLesJoinRcvQueueDiscards OBJECT-TYPE
    SYNTAX Counter
    ACCESS read-only
    STATUS mandatory
    DESCRIPTION
        "The number of Join request discards which were due
         to running out of space in Join receive queues."
    ::= { decLesJoinEntry 19 }

decLesJoinLecRcvQueueDiscards OBJECT-TYPE
    SYNTAX Counter
    ACCESS read-only
    STATUS mandatory
    DESCRIPTION
        "The number of Join request discards which were due
         to running out of space in per-LEC receive queues."
    ::= { decLesJoinEntry 20 }

decLesJoinResourceDiscards OBJECT-TYPE
    SYNTAX Counter
    ACCESS read-only
    STATUS mandatory
    DESCRIPTION
        "The number of Join request discards which were due
         to the server running out of other resources."
    ::= { decLesJoinEntry 21 }

decLesRegisterTable OBJECT-TYPE
    SYNTAX SEQUENCE OF DecLesRegisterEntry
    ACCESS not-accessible
    STATUS mandatory
    DESCRIPTION
        "This table holds statistics on Registration attempts.
         It contains one row for each managed LES component."
    REFERENCE
        "ATM Forum LAN Emulation Over ATM Specification, V1.0,
         Chapter 6"
    ::= { decLesMIBObjects 12 }

decLesRegisterEntry OBJECT-TYPE
    SYNTAX DecLesRegisterEntry
    ACCESS not-accessible
    STATUS mandatory
    DESCRIPTION
        "Each row contains registration statistics for one
         LES."
    INDEX { decLesIndex }
-- Augments decLesConfigEntry
    ::= { decLesRegisterTable 1 }

DecLesRegisterEntry ::= SEQUENCE {
    decLesRegisterRequests Counter,
    decLesRegisterSuccesses Counter,
    decLesRegisterFailures Counter,
    decLesRegisterDiscards Counter,
    decLesUnregisterRequests Counter,
    decLesUnregisterSuccesses Counter,
    decLesUnregisterFailures Counter,
    decLesUnregisterDiscards Counter,
    decLesRegDuplicateAtmAddresses Counter,
    decLesRegDuplicateLanDestinations Counter,
    decLesRegInvalidAtmAddresses Counter,
    decLesRegInvalidLanDestinations Counter,
    decLesRegInvalidLECIDs Counter,
    decLesRegOutOfResources Counter,
    decLesRegRcvQueueDiscards Counter,
    decLesRegLecRcvQueueDiscards Counter,
    decLesRegResourceDiscards Counter,
    decLesUnRegInvalidLanDestinations Counter,
    decLesUnRegInvalidLECIDs Counter,
    decLesUnRegRcvQueueDiscards Counter,
    decLesUnRegLecRcvQueueDiscards Counter,
    decLesUnRegResourceDiscards Counter,
    decLesRegAlreadyRegistered Counter,
    decLesUnRegNoSuchLanDestinations Counter,
    decLesUnRegNoSuchAddressPairs Counter,
    decLesUnRegOwnedByOthers Counter
    }

decLesRegisterRequests OBJECT-TYPE
    SYNTAX Counter
    ACCESS read-only
    STATUS mandatory
    DESCRIPTION
        "The total number of Register requests received by
         this LAN Emulation Server component."
    ::= { decLesRegisterEntry 1 }

decLesRegisterSuccesses OBJECT-TYPE
    SYNTAX Counter
    ACCESS read-only
    STATUS mandatory
    DESCRIPTION
        "The total number of valid registration requests
         received by this LAN Emulation Server component."
    ::= { decLesRegisterEntry 2 }

decLesRegisterFailures OBJECT-TYPE
    SYNTAX Counter
    ACCESS read-only
    STATUS mandatory
    DESCRIPTION
        "The total number of invalid registration requests
         received by this LAN Emulation Server component."
    ::= { decLesRegisterEntry 3 }

decLesRegisterDiscards OBJECT-TYPE
    SYNTAX Counter
    ACCESS read-only
    STATUS mandatory
    DESCRIPTION
        "The number of Register requests which were discarded
         due to no fault of their own, and for which this LES
         component sent no Register response."
    ::= { decLesRegisterEntry 4 }

decLesUnregisterRequests OBJECT-TYPE
    SYNTAX Counter
    ACCESS read-only
    STATUS mandatory
    DESCRIPTION
        "The total number of Unregister requests received by
         this LAN Emulation Server component."
    ::= { decLesRegisterEntry 5 }

decLesUnregisterSuccesses OBJECT-TYPE
    SYNTAX Counter
    ACCESS read-only
    STATUS mandatory
    DESCRIPTION
        "The total number of valid unregister requests
         received by this LAN Emulation Server component."
    ::= { decLesRegisterEntry 6 }

decLesUnregisterFailures OBJECT-TYPE
    SYNTAX Counter
    ACCESS read-only
    STATUS mandatory
    DESCRIPTION
        "The total number of invalid unregister requests
         received by this LAN Emulation Server component."
    ::= { decLesRegisterEntry 7 }

decLesUnregisterDiscards OBJECT-TYPE
    SYNTAX Counter
    ACCESS read-only
    STATUS mandatory
    DESCRIPTION
        "The number of Unregister requests which were discarded
         due to no fault of their own, and for which this LES
         component sent no Unregister response."
    ::= { decLesRegisterEntry 8 }

decLesRegDuplicateAtmAddresses OBJECT-TYPE
    SYNTAX Counter
    ACCESS read-only
    STATUS mandatory
    DESCRIPTION
        "The number of Register requests that failed because
         they specified an ATM address already registered to
         another client."
    ::= { decLesRegisterEntry 9 }

decLesRegDuplicateLanDestinations OBJECT-TYPE
    SYNTAX Counter
    ACCESS read-only
    STATUS mandatory
    DESCRIPTION
        "The number of Register requests that failed because
         they specified a LAN Destination already registered
         to another client."
    ::= { decLesRegisterEntry 10 }

decLesRegInvalidAtmAddresses OBJECT-TYPE
    SYNTAX Counter
    ACCESS read-only
    STATUS mandatory
    DESCRIPTION
        "The number of Register requests that failed because
         they contained an invalid ATM address."
    ::= { decLesRegisterEntry 11 }

decLesRegInvalidLanDestinations OBJECT-TYPE
    SYNTAX Counter
    ACCESS read-only
    STATUS mandatory
    DESCRIPTION
        "The number of Register requests that failed because
         they specified an invalid LAN Destination - such as
         a broadcast or multicast MAC address."
    ::= { decLesRegisterEntry 12 }

decLesRegInvalidLECIDs OBJECT-TYPE
    SYNTAX Counter
    ACCESS read-only
    STATUS mandatory
    DESCRIPTION
        "The number of Register requests that failed because
         they contained an invalid LEC ID."
    ::= { decLesRegisterEntry 13 }

decLesRegOutOfResources OBJECT-TYPE
    SYNTAX Counter
    ACCESS read-only
    STATUS mandatory
    DESCRIPTION
        "The number of Register requests that failed because
         the server ran out of resources."
    ::= { decLesRegisterEntry 14 }

decLesRegRcvQueueDiscards OBJECT-TYPE
    SYNTAX Counter
    ACCESS read-only
    STATUS mandatory
    DESCRIPTION
        "The number of Register requests which were discarded
         by this LES component because one of its receive
         queues was full."
    ::= { decLesRegisterEntry 15 }

decLesRegLecRcvQueueDiscards OBJECT-TYPE
    SYNTAX Counter
    ACCESS read-only
    STATUS mandatory
    DESCRIPTION
        "The number of Register requests which were discarded
         by this LES component because one of its per-LEC
         receive queues was full."
    ::= { decLesRegisterEntry 16 }

decLesRegResourceDiscards OBJECT-TYPE
    SYNTAX Counter
    ACCESS read-only
    STATUS mandatory
    DESCRIPTION
        "The number of Register requests which were discarded
         by this LES component because the server ran out of
         resources."
    ::= { decLesRegisterEntry 17 }

decLesUnRegInvalidLanDestinations OBJECT-TYPE
    SYNTAX Counter
    ACCESS read-only
    STATUS mandatory
    DESCRIPTION
        "The number of Unregister requests that failed because
         they specified an invalid LAN Destination - such as
         a broadcast or multicast MAC address."
    ::= { decLesRegisterEntry 18 }

decLesUnRegInvalidLECIDs OBJECT-TYPE
    SYNTAX Counter
    ACCESS read-only
    STATUS mandatory
    DESCRIPTION
        "The number of Unregister requests that failed because
         they contained an invalid LEC ID."
    ::= { decLesRegisterEntry 19 }

decLesUnRegRcvQueueDiscards OBJECT-TYPE
    SYNTAX Counter
    ACCESS read-only
    STATUS mandatory
    DESCRIPTION
        "The number of Unregister requests which were discarded
         by this LES component because one of its receive
         queues was full."
    ::= { decLesRegisterEntry 20 }

decLesUnRegLecRcvQueueDiscards OBJECT-TYPE
    SYNTAX Counter
    ACCESS read-only
    STATUS mandatory
    DESCRIPTION
        "The number of Unregister requests which were discarded
         by this LES component because one of its per-LEC
         receive queues was full."
    ::= { decLesRegisterEntry 21 }

decLesUnRegResourceDiscards OBJECT-TYPE
    SYNTAX Counter
    ACCESS read-only
    STATUS mandatory
    DESCRIPTION
        "The number of Unregister requests which were discarded
         by this LES component because the server ran out of
         resources."
    ::= { decLesRegisterEntry 22 }

decLesRegAlreadyRegistered OBJECT-TYPE
    SYNTAX Counter
    ACCESS read-only
    STATUS mandatory
    DESCRIPTION
        "The number of successful Register requests which had
         no effect, because the address pairs they specified
         were already registered to the requesting clients."
    ::= { decLesRegisterEntry 23 }

decLesUnRegNoSuchLanDestinations OBJECT-TYPE
    SYNTAX Counter
    ACCESS read-only
    STATUS mandatory
    DESCRIPTION
        "The number of successful Unregister requests which
         had no effect, because the LAN Destinations that they
         specified were already unregistered."
    ::= { decLesRegisterEntry 24 }

decLesUnRegNoSuchAddressPairs OBJECT-TYPE
    SYNTAX Counter
    ACCESS read-only
    STATUS mandatory
    DESCRIPTION
        "The number of successful Unregister requests which
         had no effect, because the ATM addresses that they
         specified did not match the registered ones."
    ::= { decLesRegisterEntry 25 }

decLesUnRegOwnedByOthers OBJECT-TYPE
    SYNTAX Counter
    ACCESS read-only
    STATUS mandatory
    DESCRIPTION
        "The number of successful Unregister requests which
         had no effect, because they attempted to unregister
         LAN Destinations belonging to other clients."
    ::= { decLesRegisterEntry 26 }

decLesArpTable OBJECT-TYPE
    SYNTAX SEQUENCE OF DecLesArpEntry
    ACCESS not-accessible
    STATUS mandatory
    DESCRIPTION
        "This table holds statistics on LE_ARP_REQUESTs and
         related LAN Emulation control frames.  It contains
         one row for each managed LES component."
    REFERENCE
        "ATM Forum LAN Emulation Over ATM Specification, V1.0,
         Chapter 7"
    ::= { decLesMIBObjects 13 }

decLesArpEntry OBJECT-TYPE
    SYNTAX DecLesArpEntry
    ACCESS not-accessible
    STATUS mandatory
    DESCRIPTION
        "Each row contains LE-ARP statistics for one LES."
    INDEX { decLesIndex }
-- Augments decLesConfigEntry
    ::= { decLesArpTable 1 }

DecLesArpEntry ::= SEQUENCE {
    decLesArpRequestsAnswered Counter,
    decLesArpRequestsForwarded Counter,
    decLesArpRequestsRejected Counter,
    decLesArpRequestsDiscarded Counter,
    decLesArpResponsesForwarded Counter,
    decLesArpResponsesRejected Counter,
    decLesArpResponsesDiscarded Counter,
    decLesNarpRequestsForwarded Counter,
    decLesNarpRequestsFiltered Counter,
    decLesNarpRequestsRejected Counter,
    decLesNarpRequestsDiscarded Counter,
    decLesTopologyRequestsForwarded Counter,
    decLesTopologyRequestsGenerated Counter,
    decLesTopologyRequestsRejected Counter,
    decLesTopologyRequestsDiscarded Counter,
    decLesTopologyRequestGenFailures Counter,
    decLesArpReqInvalidAtmAddresses Counter,
    decLesArpReqInvalidLanDestinations Counter,
    decLesArpReqInvalidLECIDs Counter,
    decLesArpReqReceiveQueueDiscards Counter,
    decLesArpReqResourceDiscards Counter,
    decLesArpRespInvalidLECIDs Counter,
    decLesArpRespReceiveQueueDiscards Counter,
    decLesArpRespResourceDiscards Counter,
    decLesNarpReqInvalidAtmAddresses Counter,
    decLesNarpReqInvalidLanDestinations Counter,
    decLesNarpReqInvalidLECIDs Counter,
    decLesNarpReqReceiveQueueDiscards Counter,
    decLesNarpReqResourceDiscards Counter,
    decLesTopoReqReceiveQueueDiscards Counter,
    decLesTopoReqResourceDiscards Counter
    }

decLesArpRequestsAnswered OBJECT-TYPE
    SYNTAX Counter
    ACCESS read-only
    STATUS mandatory
    DESCRIPTION
        "The number of LE_ARP_REQUESTs which this LES component
         has answered directly with a Success code."
    ::= { decLesArpEntry 1 }

decLesArpRequestsForwarded OBJECT-TYPE
    SYNTAX Counter
    ACCESS read-only
    STATUS mandatory
    DESCRIPTION
        "The number of LE_ARP_REQUESTs which this LES component
         has forwarded to clients or other server components."
    ::= { decLesArpEntry 2 }

decLesArpRequestsRejected OBJECT-TYPE
    SYNTAX Counter
    ACCESS read-only
    STATUS mandatory
    DESCRIPTION
        "The number of LE_ARP_REQUESTs which this LES component
         has rejected.  This includes frames counted in
        
                decLesArpReqInvalidAtmAddresses
                decLesArpReqInvalidLanDestinations
                decLesArpReqInvalidLECIDs                     "
    ::= { decLesArpEntry 3 }

decLesArpRequestsDiscarded OBJECT-TYPE
    SYNTAX Counter
    ACCESS read-only
    STATUS mandatory
    DESCRIPTION
        "The number of LE_ARP_REQUESTs which this LES component
         has discarded, due to no fault of their own."
    ::= { decLesArpEntry 4 }

decLesArpResponsesForwarded OBJECT-TYPE
    SYNTAX Counter
    ACCESS read-only
    STATUS mandatory
    DESCRIPTION
        "The number of LE_ARP_RESPONSEs which this LES
         component has forwarded to one or more clients.
        
         This count does not include any LE_ARP_RESPONSE
         which is counted in 'decLesArpRequestsAnswered'."
    ::= { decLesArpEntry 5 }

decLesArpResponsesRejected OBJECT-TYPE
    SYNTAX Counter
    ACCESS read-only
    STATUS mandatory
    DESCRIPTION
        "The number of LE_ARP_RESPONSEs which this LES
         component has discarded due to errors.  This includes
         frames counted in
        
                decLesArpRespInvalidLECIDs                   "
    ::= { decLesArpEntry 6 }

decLesArpResponsesDiscarded OBJECT-TYPE
    SYNTAX Counter
    ACCESS read-only
    STATUS mandatory
    DESCRIPTION
        "The number of LE_ARP_RESPONSEs which this LES
         component has discarded due to no fault of their own."
    ::= { decLesArpEntry 7 }

decLesNarpRequestsForwarded OBJECT-TYPE
    SYNTAX Counter
    ACCESS read-only
    STATUS mandatory
    DESCRIPTION
        "The number of LE_NARP_REQUESTs which this LES
         component has forwarded to clients."
    ::= { decLesArpEntry 8 }

decLesNarpRequestsFiltered OBJECT-TYPE
    SYNTAX Counter
    ACCESS read-only
    STATUS mandatory
    DESCRIPTION
        "The number of LE_NARP_REQUESTs which this LES has
         filtered (discarded) to enforce management policy.
         See 'decLesNarpRequestPolicy'."
    ::= { decLesArpEntry 9 }

decLesNarpRequestsRejected OBJECT-TYPE
    SYNTAX Counter
    ACCESS read-only
    STATUS mandatory
    DESCRIPTION
        "The number of LE_NARP_REQUESTs which this LES
         component has rejected.  This includes frames
         counted in
        
                decLesNarpReqInvalidAtmAddresses
                decLesNarpReqInvalidLanDestinations
                decLesNarpReqInvalidLECIDs            "
    ::= { decLesArpEntry 10 }

decLesNarpRequestsDiscarded OBJECT-TYPE
    SYNTAX Counter
    ACCESS read-only
    STATUS mandatory
    DESCRIPTION
        "The number of LE_NARP_REQUESTs which this LES has
         discarded through no fault of their own, and which
         are not counted in decLesNarpRequestsFiltered."
    ::= { decLesArpEntry 11 }

decLesTopologyRequestsForwarded OBJECT-TYPE
    SYNTAX Counter
    ACCESS read-only
    STATUS mandatory
    DESCRIPTION
        "The number of LE_TOPOLOGY_REQUESTs which this LES
         component has forwarded to clients."
    ::= { decLesArpEntry 12 }

decLesTopologyRequestsGenerated OBJECT-TYPE
    SYNTAX Counter
    ACCESS read-only
    STATUS mandatory
    DESCRIPTION
        "The number of LE_TOPOLOGY_REQUESTs which this LES
         component has generated to take the emulated LAN
         out of accelerated aging mode."
    ::= { decLesArpEntry 13 }

decLesTopologyRequestsRejected OBJECT-TYPE
    SYNTAX Counter
    ACCESS read-only
    STATUS mandatory
    DESCRIPTION
        "The number of LE_TOPOLOGY_REQUESTs which this LES
         component has rejected."
    ::= { decLesArpEntry 14 }

decLesTopologyRequestsDiscarded OBJECT-TYPE
    SYNTAX Counter
    ACCESS read-only
    STATUS mandatory
    DESCRIPTION
        "The number of LE_TOPOLOGY_REQUESTs which this LES
         component has discarded due to no fault of their own."
    ::= { decLesArpEntry 15 }

decLesTopologyRequestGenFailures OBJECT-TYPE
    SYNTAX Counter
    ACCESS read-only
    STATUS mandatory
    DESCRIPTION
        "The number of LE_TOPOLOGY_REQUESTs which this LES
         component has tried, but failed, to generate."
    ::= { decLesArpEntry 16 }

decLesArpReqInvalidAtmAddresses OBJECT-TYPE
    SYNTAX Counter
    ACCESS read-only
    STATUS mandatory
    DESCRIPTION
        "The number of LE_ARP_REQUESTs which were rejected
         because their ATM addresses were in unrecognizable
         formats."
    ::= { decLesArpEntry 17 }

decLesArpReqInvalidLanDestinations OBJECT-TYPE
    SYNTAX Counter
    ACCESS read-only
    STATUS mandatory
    DESCRIPTION
        "The number of LE_ARP_REQUESTs which were rejected
         because they specified invalid LAN Destinations -
         such as multicast MAC addresses."
    ::= { decLesArpEntry 18 }

decLesArpReqInvalidLECIDs OBJECT-TYPE
    SYNTAX Counter
    ACCESS read-only
    STATUS mandatory
    DESCRIPTION
        "The number of LE_ARP_REQUESTs that were discarded
         because they contained an invalid LEC ID."
    ::= { decLesArpEntry 19 }

decLesArpReqReceiveQueueDiscards OBJECT-TYPE
    SYNTAX Counter
    ACCESS read-only
    STATUS mandatory
    DESCRIPTION
        "The number of LE_ARP requests which were discarded
         by this LES component because one of its receive
         queues was full."
    ::= { decLesArpEntry 20 }

decLesArpReqResourceDiscards OBJECT-TYPE
    SYNTAX Counter
    ACCESS read-only
    STATUS mandatory
    DESCRIPTION
        "The number of LE_ARP requests which were discarded
         by this LES component because the server ran out of
         resources."
    ::= { decLesArpEntry 21 }

decLesArpRespInvalidLECIDs OBJECT-TYPE
    SYNTAX Counter
    ACCESS read-only
    STATUS mandatory
    DESCRIPTION
        "The number of LE_ARP_RESPONSEs which this LES
         component has discarded because
        
           *  they specify invalid LECIDs,
        
           *  their REQUESTER-LECIDs and SOURCE-ATM-ADDRESSes
              indicate two different clients, or
        
           *  the clients to which they were directed are no
              longer part of the emulated LAN."
    ::= { decLesArpEntry 22 }

decLesArpRespReceiveQueueDiscards OBJECT-TYPE
    SYNTAX Counter
    ACCESS read-only
    STATUS mandatory
    DESCRIPTION
        "The number of LE_ARP responses which were discarded
         by this LES component because one of its receive
         queues was full."
    ::= { decLesArpEntry 23 }

decLesArpRespResourceDiscards OBJECT-TYPE
    SYNTAX Counter
    ACCESS read-only
    STATUS mandatory
    DESCRIPTION
        "The number of LE_ARP responses which were discarded
         by this LES component because the server ran out of
         resources."
    ::= { decLesArpEntry 24 }

decLesNarpReqInvalidAtmAddresses OBJECT-TYPE
    SYNTAX Counter
    ACCESS read-only
    STATUS mandatory
    DESCRIPTION
        "The number of LE_NARP_REQUESTs which were rejected
         because their ATM addresses were in unrecognizable
         formats."
    ::= { decLesArpEntry 25 }

decLesNarpReqInvalidLanDestinations OBJECT-TYPE
    SYNTAX Counter
    ACCESS read-only
    STATUS mandatory
    DESCRIPTION
        "The number of LE_NARP_REQUESTs that were rejected
         because they specified invalid LAN Destinations -
         such as multicast MAC addresses."
    ::= { decLesArpEntry 26 }

decLesNarpReqInvalidLECIDs OBJECT-TYPE
    SYNTAX Counter
    ACCESS read-only
    STATUS mandatory
    DESCRIPTION
        "The number of LE_NARP_REQUESTs that were rejected
         because they contained an invalid LEC ID."
    ::= { decLesArpEntry 27 }

decLesNarpReqReceiveQueueDiscards OBJECT-TYPE
    SYNTAX Counter
    ACCESS read-only
    STATUS mandatory
    DESCRIPTION
        "The number of LE_NARP requests which were discarded
         by this LES component because one of its receive
         queues was full."
    ::= { decLesArpEntry 28 }

decLesNarpReqResourceDiscards OBJECT-TYPE
    SYNTAX Counter
    ACCESS read-only
    STATUS mandatory
    DESCRIPTION
        "The number of LE_NARP requests which were discarded
         by this LES component because the server ran out of
         resources."
    ::= { decLesArpEntry 29 }

decLesTopoReqReceiveQueueDiscards OBJECT-TYPE
    SYNTAX Counter
    ACCESS read-only
    STATUS mandatory
    DESCRIPTION
        "The number of LE_TOPOLOGY requests which were
         discarded by this LES component because one of its
         receive queues was full."
    ::= { decLesArpEntry 30 }

decLesTopoReqResourceDiscards OBJECT-TYPE
    SYNTAX Counter
    ACCESS read-only
    STATUS mandatory
    DESCRIPTION
        "The number of LE_TOPOLOGY requests which were
         discarded by this LES component because the server
         ran out of resources."
    ::= { decLesArpEntry 31 }

decLesFlushTable OBJECT-TYPE
    SYNTAX SEQUENCE OF DecLesFlushEntry
    ACCESS not-accessible
    STATUS mandatory
    DESCRIPTION
        "This table holds statistics on LE_FLUSH_RESPONSE
         frames.  It contains one row for each managed LES
         component."
    REFERENCE
        "ATM Forum LAN Emulation Over ATM Specification, V1.0,
         Chapter 9"
    ::= { decLesMIBObjects 14 }

decLesFlushEntry OBJECT-TYPE
    SYNTAX DecLesFlushEntry
    ACCESS not-accessible
    STATUS mandatory
    DESCRIPTION
        "Each row contains Flush statistics for one LES."
    INDEX { decLesIndex }
-- Augments decLesConfigEntry
    ::= { decLesFlushTable 1 }

DecLesFlushEntry ::= SEQUENCE {
    decLesFlushResponsesForwarded Counter,
    decLesFlushResponsesRejected Counter,
    decLesFlushResponsesDiscarded Counter
    }

decLesFlushResponsesForwarded OBJECT-TYPE
    SYNTAX Counter
    ACCESS read-only
    STATUS mandatory
    DESCRIPTION
        "The number of LE_FLUSH_RESPONSES which this LES
         component has forwarded."
    ::= { decLesFlushEntry 1 }

decLesFlushResponsesRejected OBJECT-TYPE
    SYNTAX Counter
    ACCESS read-only
    STATUS mandatory
    DESCRIPTION
        "The number of LE_FLUSH_RESPONSES which this LES
         component has rejected."
    ::= { decLesFlushEntry 2 }

decLesFlushResponsesDiscarded OBJECT-TYPE
    SYNTAX Counter
    ACCESS read-only
    STATUS mandatory
    DESCRIPTION
        "The number of LE_FLUSH_RESPONSES which this LES
         component has discarded due to no fault of their own."
    ::= { decLesFlushEntry 3 }

decLesEventLogMaximumSize OBJECT-TYPE
    SYNTAX INTEGER
    ACCESS read-write
    STATUS mandatory
    DESCRIPTION
        "The minimum number of events which the agent should
         remember before purging old log entries to make way
         for new ones."
    ::= { decLesMIBObjects 15 }

decLesEventLogTable OBJECT-TYPE
    SYNTAX SEQUENCE OF DecLesEventLogEntry
    ACCESS not-accessible
    STATUS mandatory
    DESCRIPTION
        "A table of event log entries for the emulated
         LANs that this node serves."
    ::= { decLesMIBObjects 16 }

decLesEventLogEntry OBJECT-TYPE
    SYNTAX DecLesEventLogEntry
    ACCESS not-accessible
    STATUS mandatory
    DESCRIPTION
        "An entry describing a significant event."
    INDEX { decLesEventIndex }
    ::= { decLesEventLogTable 1 }

DecLesEventLogEntry ::= SEQUENCE {
    decLesEventIndex INTEGER,
    decLesEventType INTEGER,
    decLesEventReason INTEGER,
    decLesEventServer INTEGER,
    decLesEventServerAtmAddress OCTET STRING,
    decLesEventClientAtmAddress OCTET STRING,
    decLesEventClientMacAddress OCTET STRING,
    decLesEventTimestamp TimeTicks
    }

decLesEventIndex OBJECT-TYPE
    SYNTAX INTEGER
    ACCESS read-only
    STATUS mandatory
    DESCRIPTION
        "A unique number greater than zero which identifies
         this table row."
    ::= { decLesEventLogEntry 1 }

decLesEventType OBJECT-TYPE
    SYNTAX INTEGER {
        joinFailed(1),
        registrationFailed(2)
        }
    ACCESS read-only
    STATUS mandatory
    DESCRIPTION
        "The event which triggered this log entry.
        
             joinFailed(1) - A client tried to join one of the
                 LANs this host serves, but the attempt failed.
        
             registrationFailed(2) - A client was not able to
                 register a new LAN Destination.              "
    ::= { decLesEventLogEntry 2 }

decLesEventReason OBJECT-TYPE
    SYNTAX INTEGER {
        versionNotSupported(1),
        invalidRequestParameters(2),
        duplicateLanDestination(4),
        duplicateAtmAddress(5),
        insufficientResources(6),
        accessDenied(7),
        invalidRequestorId(8),
        invalidLanDestination(9),
        invalidAtmAddress(10),
        wrongLanType(50),
        wrongMaxFrameSize(51),
        wrongJoinMaxFrameSize(52),
        nonDuplicateRequest(53),
        controlDistributeFailure(54),
        multicastForwardFailure(55),
        joinNotCompleted(56),
        joinTimeout(57),
        busConnectTimeout(58),
        clientNotConnectedToLes(59),
        missingInformationElement(70),
        noAalParameters(71),
        noAtmTrafficDescriptor(72),
        noBroadbandBearerCapability(73),
        noBlli(74),
        noCallingPartyNumber(75),
        noCalledPartyNumber(76),
        noConnectionIdentifier(77),
        noQosParameter(78),
        invalidInformationElement(80),
        invalidAalParameters(81),
        invalidAtmTrafficDescriptor(82),
        invalidBroadbandBearerCapability(83),
        invalidBlli(84),
        invalidCallingPartyNumber(85),
        invalidCalledPartyNumber(86),
        invalidConnectionIdentifier(87),
        invalidQosParameter(88),
        invalidAalMode(90),
        invalidAalSccs(91),
        insecureAtmAddress(100),
        unverifiedAtmAddress(101)
        }
    ACCESS read-only
    STATUS mandatory
    DESCRIPTION
        "The cause of the failure."
    ::= { decLesEventLogEntry 3 }

decLesEventServer OBJECT-TYPE
    SYNTAX INTEGER
    ACCESS read-only
    STATUS mandatory
    DESCRIPTION
        "The 'decLesIndex' of the LAN Emulation Server that
         was involved in this incident.
        
         If the value of this object is zero, it indicates
         that the server no longer exists."
    ::= { decLesEventLogEntry 4 }

decLesEventServerAtmAddress OBJECT-TYPE
    SYNTAX OCTET STRING(SIZE(0..20))
    ACCESS read-only
    STATUS mandatory
    DESCRIPTION
        "The ATM address of the LAN Emulation server that was
         involved in this incident."
    ::= { decLesEventLogEntry 5 }

decLesEventClientAtmAddress OBJECT-TYPE
    SYNTAX OCTET STRING(SIZE(0..20))
    ACCESS read-only
    STATUS mandatory
    DESCRIPTION
        "If known, the ATM address of the LAN Emulation Client
         that was involved in this incident."
    ::= { decLesEventLogEntry 6 }

decLesEventClientMacAddress OBJECT-TYPE
    SYNTAX OCTET STRING(SIZE(6))
    ACCESS read-only
    STATUS mandatory
    DESCRIPTION
        "If known, one of the MAC addresses of the client that
         was involved in this incident.
        
         If 'decLesEventReason' is 'duplicateLanDestination'
         or 'invalidLanDestination', the value of this object
         will be the MAC address in question."
    ::= { decLesEventLogEntry 7 }

decLesEventTimestamp OBJECT-TYPE
    SYNTAX TimeTicks
    ACCESS read-only
    STATUS mandatory
    DESCRIPTION
        "The value of sysUpTime at the time that the event
         occurred.  If the event occurred prior to the last
         re-initialization of the local network management
         subsystem, this object contains a zero value."
    ::= { decLesEventLogEntry 8 }

decLesConfigGroup OBJECT IDENTIFIER ::= { decLesMIBGroups 1 }
-- OBJECT-GROUP
--  Status
--    mandatory
--  Descr
--    A collection of objects for identifying and
--     configuring LAN Emulation Server components.
--  objects
--    decLesRowStatus, decLesAdminStatus, decLesOperStatus, 
--    decLesAtmAddress, decLesLastChange, decLesDescription, 
--    decLesLanName, decLesLanType, decLesMaxDataFrameSize, 
--    decLesAtmAddressOfBUS, decLesControlTimeout, 
--    decLesArpResponsePolicy, decLesNarpRequestPolicy, 
--    decLesTopologyChangeMode, decLesLastTcModeChange, 
--    decLesTopologyChangeTimeout

decLesClientStatesGroup OBJECT IDENTIFIER ::= { decLesMIBGroups 2 }
-- OBJECT-GROUP
--  Status
--    mandatory
--  Descr
--    A collection of objects describing the number
--     of LES clients in various membership states.
--  objects
--    decLesActiveClients, decLesActiveProxyClients, 
--    decLesAwaitingJoinRequest, decLesCtlDistributeInProgress, 
--    decLesTerminating

decLesClientGroup OBJECT IDENTIFIER ::= { decLesMIBGroups 3 }
-- OBJECT-GROUP
--  Status
--    mandatory
--  Descr
--    A collection of objects describing the current
--     clients of each managed LES component.
--  objects
--    decLesClientAtmAddress, decLesClientIsProxy, 
--    decLesClientState, decLesClientRowStatus

decLesLecGroup OBJECT IDENTIFIER ::= { decLesMIBGroups 4 }
-- OBJECT-GROUP
--  Status
--    mandatory
--  Descr
--    A collection of objects describing the clients
--     of each managed LES component.
--  objects
--    decLesLecID, decLesLecIsProxy, decLesLecState, 
--    decLesLecRowStatus

decLesCircuitGroup OBJECT IDENTIFIER ::= { decLesMIBGroups 5 }
-- OBJECT-GROUP
--  Status
--    mandatory
--  Descr
--    A optional collection of objects describing
--     Control Direct and Control Distribute VCCs.
--  objects
--    decLesControlDirectInterface, decLesControlDirectVpi, 
--    decLesControlDirectVci, decLesControlDirectRowStatus, 
--    decLesControlDistRowStatus

decLesMacAddressGroup OBJECT IDENTIFIER ::= { decLesMIBGroups 6 }
-- OBJECT-GROUP
--  Status
--    mandatory
--  Descr
--    A collection of objects describing registered
--     MAC addresses for each managed LES component.
--  objects
--    decLesMacAddressOwner, decLesMacAddressAtmBinding

decLesRouteDescrGroup OBJECT IDENTIFIER ::= { decLesMIBGroups 7 }
-- OBJECT-GROUP
--  Status
--    mandatory
--  Descr
--    A collection of objects describing registered
--     route descriptors for each managed LES component.
--  objects
--    decLesRouteDescrOwner, decLesRouteDescrAtmBinding

decLesTrafficGroup OBJECT IDENTIFIER ::= { decLesMIBGroups 8 }
-- OBJECT-GROUP
--  Status
--    mandatory
--  Descr
--    A collection of objects describing the amount
--     of traffic seen by each managed LES component.
--  objects
--    decLesControlFramesIn, decLesShortFrames, 
--    decLesUnjoinedClientFrames, decLesVersionsNotSupported, 
--    decLesInvalidFrames, decLesReceiveQueueDiscards, 
--    decLesMiscDiscards

decLesCallStatsGroup OBJECT IDENTIFIER ::= { decLesMIBGroups 9 }
-- OBJECT-GROUP
--  Status
--    mandatory
--  Descr
--    A collection of objects providing statistics on
--     LE Control VCC establishments.
--  objects
--    decLesCtlDirectCalls, decLesCtlDirectFailures, 
--    decLesCtlDirectOutOfResources, 
--    decLesCtlDirectInvalidInfoElements, decLesCtlDistributeCalls, 
--    decLesCtlDistributeFailures, decLesCtlDistribOutOfResources

decLesJoinStatsGroup OBJECT IDENTIFIER ::= { decLesMIBGroups 10 }
-- OBJECT-GROUP
--  Status
--    mandatory
--  Descr
--    A collection of objects providing statistics on
--     LAN Emulation Join requests.
--  objects
--    decLesJoinRequests, decLesJoinSuccesses, decLesJoinFailures, 
--    decLesJoinDuplicates, decLesJoinNonDuplicates, 
--    decLesJoinDiscards, decLesJoinTimeouts, 
--    decLesJoinVersionsNotSupported, decLesJoinInvalidParameters, 
--    decLesJoinDuplicateAtmAddresses, 
--    decLesJoinDuplicateLanDestinations, 
--    decLesJoinInvalidAtmAddresses, 
--    decLesJoinInvalidLanDestinations, decLesJoinWrongLanTypes, 
--    decLesJoinMaxFrameSizesTooSmall, decLesJoinInvalidLECIDs, 
--    decLesJoinCtlDistributeRejects, decLesJoinOutOfResources, 
--    decLesJoinRcvQueueDiscards, decLesJoinLecRcvQueueDiscards, 
--    decLesJoinResourceDiscards

decLesRegisterStatsGroup OBJECT IDENTIFIER ::= { decLesMIBGroups 11 }
-- OBJECT-GROUP
--  Status
--    mandatory
--  Descr
--    A collection of objects providing statistics on
--     LAN Emulation Register and Unregister requests.
--  objects
--    decLesRegisterRequests, decLesRegisterSuccesses, 
--    decLesRegisterFailures, decLesRegisterDiscards, 
--    decLesUnregisterRequests, decLesUnregisterSuccesses, 
--    decLesUnregisterFailures, decLesUnregisterDiscards, 
--    decLesRegDuplicateAtmAddresses, 
--    decLesRegDuplicateLanDestinations, 
--    decLesRegInvalidAtmAddresses, decLesRegInvalidLanDestinations, 
--    decLesRegInvalidLECIDs, decLesRegOutOfResources, 
--    decLesRegRcvQueueDiscards, decLesRegLecRcvQueueDiscards, 
--    decLesRegResourceDiscards, decLesUnRegInvalidLanDestinations, 
--    decLesUnRegInvalidLECIDs, decLesUnRegRcvQueueDiscards, 
--    decLesUnRegLecRcvQueueDiscards, decLesUnRegResourceDiscards, 
--    decLesRegAlreadyRegistered, decLesUnRegNoSuchLanDestinations, 
--    decLesUnRegNoSuchAddressPairs, decLesUnRegOwnedByOthers

decLesArpStatsGroup OBJECT IDENTIFIER ::= { decLesMIBGroups 12 }
-- OBJECT-GROUP
--  Status
--    mandatory
--  Descr
--    A collection of objects providing statistics on
--     LE_ARP requests.
--  objects
--    decLesArpRequestsAnswered, decLesArpRequestsForwarded, 
--    decLesArpRequestsRejected, decLesArpRequestsDiscarded, 
--    decLesArpReqInvalidAtmAddresses, 
--    decLesArpReqInvalidLanDestinations, decLesArpReqInvalidLECIDs, 
--    decLesArpResponsesForwarded, decLesArpResponsesRejected, 
--    decLesArpResponsesDiscarded, decLesArpRespInvalidLECIDs, 
--    decLesNarpRequestsForwarded, decLesNarpRequestsFiltered, 
--    decLesNarpRequestsRejected, decLesNarpRequestsDiscarded, 
--    decLesNarpReqInvalidAtmAddresses, 
--    decLesNarpReqInvalidLanDestinations, 
--    decLesNarpReqInvalidLECIDs, decLesTopologyRequestsForwarded, 
--    decLesTopologyRequestsGenerated, 
--    decLesTopologyRequestsRejected, 
--    decLesTopologyRequestsDiscarded, 
--    decLesTopologyRequestGenFailures, 
--    decLesArpReqReceiveQueueDiscards, 
--    decLesArpReqResourceDiscards, 
--    decLesArpRespReceiveQueueDiscards, 
--    decLesArpRespResourceDiscards, 
--    decLesNarpReqReceiveQueueDiscards, 
--    decLesNarpReqResourceDiscards, 
--    decLesTopoReqReceiveQueueDiscards, 
--    decLesTopoReqResourceDiscards

decLesFlushStatsGroup OBJECT IDENTIFIER ::= { decLesMIBGroups 13 }
-- OBJECT-GROUP
--  Status
--    mandatory
--  Descr
--    A collection of objects providing statistics on
--     LE_FLUSH_RESPONSEs.
--  objects
--    decLesFlushResponsesForwarded, decLesFlushResponsesRejected, 
--    decLesFlushResponsesDiscarded

decLesEventLogGroup OBJECT IDENTIFIER ::= { decLesMIBGroups 14 }
-- OBJECT-GROUP
--  Status
--    mandatory
--  Descr
--    A collection of objects implementing an optional
--     troubleshooting log.
--  objects
--    decLesEventLogMaximumSize, decLesEventType, decLesEventReason, 
--    decLesEventServer, decLesEventServerAtmAddress, 
--    decLesEventClientAtmAddress, decLesEventClientMacAddress, 
--    decLesEventTimestamp

decLesMIBCompliance OBJECT IDENTIFIER ::= { decLesMIBCompliances 1 }
-- MODULE-COMPLIANCE
--  Status
--    mandatory
--  Descr
--    The compliance statement for SNMP agents
--     which implement the DEC-LES-MIB.
--  Module
--    >>current<<
--   MandGroup
--    decLesConfigGroup
--   MandGroup
--    decLesClientStatesGroup
--   MandGroup
--    decLesClientGroup
--   MandGroup
--    decLesLecGroup
--   MandGroup
--    decLesMacAddressGroup
--   MandGroup
--    decLesTrafficGroup
--   MandGroup
--    decLesCallStatsGroup
--   MandGroup
--    decLesJoinStatsGroup
--   MandGroup
--    decLesRegisterStatsGroup
--   MandGroup
--    decLesArpStatsGroup
--   MandGroup
--    decLesFlushStatsGroup
--   OptGroup
--    decLesRouteDescrGroup
--   OptGroup
--    decLesCircuitGroup
--   OptGroup
--    decLesEventLogGroup
--   ObjVar
--    decLesRowStatus
--   ObjVar
--    decLesAdminStatus
--   ObjVar
--    decLesLanName
--   ObjVar
--    decLesLanType
--   ObjVar
--    decLesMaxDataFrameSize
--   ObjVar
--    decLesAtmAddressOfBUS
--   ObjVar
--    decLesControlTimeout
--   ObjVar
--    decLesArpResponsePolicy
--   ObjVar
--    decLesNarpRequestPolicy
--   ObjVar
--    decLesTopologyChangeTimeout
--   ObjVar
--    decLesClientRowStatus
--   ObjVar
--    decLesEventLogMaximumSize


END
