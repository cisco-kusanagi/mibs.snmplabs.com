--
-- This SMIv2 module has been generated by smidump 0.2-cvs. Do not edit.
--

SONUS-IP-FORWARDING-MIB DEFINITIONS ::= BEGIN

IMPORTS
    Gauge32, Integer32, IpAddress, MODULE-IDENTITY, OBJECT-TYPE
        FROM SNMPv2-SMI
    RowStatus
        FROM SNMPv2-TC
    sonusPacketMIBs
        FROM SONUS-SMI;

sonusIpForwardingMIB MODULE-IDENTITY
    LAST-UPDATED    "200004230000Z"
    ORGANIZATION    
            "Sonus Networks, Inc."
    CONTACT-INFO    
            "   Customer Support    
             Sonus Networks, Inc,
             5 carlisle Road
             Westford, MA 01886
             USA
             
             Tel: 978-692-8999
             Fax: 978-392-9118
             E-mail: cs.snmp@sonusnet.com"
    DESCRIPTION     
            "The MIB Module for IP Forwarding management."
    ::= { sonusPacketMIBs 3 }


sonusIpForwardGeneralGroupTable OBJECT-TYPE
    SYNTAX          SEQUENCE OF SonusIpForwardGeneralGroupEntry
    MAX-ACCESS      not-accessible
    STATUS          current
    DESCRIPTION     
            "The collection of IP Forward General Group information
             for the specified instance."
    ::= { sonusIpForwardingMIB 1 }

sonusIpForwardGeneralGroupEntry OBJECT-TYPE
    SYNTAX          SonusIpForwardGeneralGroupEntry
    MAX-ACCESS      not-accessible
    STATUS          current
    DESCRIPTION     
            "The collection of IP Forward General Group information
             for the specified instance."
    INDEX           { sonusIpForwardGeneralGroupShelf, 
                      sonusIpForwardGeneralGroupSlot, 
                      sonusIpForwardGeneralGroupInstance }
    ::= { sonusIpForwardGeneralGroupTable 1 }

SonusIpForwardGeneralGroupEntry ::=
    SEQUENCE {
        sonusIpCidrRouteNumber          Gauge32,
        sonusIpForwardGeneralGroupShelf Integer32,
        sonusIpForwardGeneralGroupSlot  Integer32,
        sonusIpForwardGeneralGroupInstance  Integer32
    }

sonusIpCidrRouteNumber OBJECT-TYPE
    SYNTAX          Gauge32
    MAX-ACCESS      read-only
    STATUS          current
    DESCRIPTION     
            "The number of current ipCidrRouteTable entries
             that are not invalid."
    ::= { sonusIpForwardGeneralGroupEntry 3 }

sonusIpForwardGeneralGroupShelf OBJECT-TYPE
    SYNTAX          Integer32
    MAX-ACCESS      read-only
    STATUS          current
    DESCRIPTION     
            "A 32-bit integer identifying the shelf
             that the IP Forward General Group table applies to"
    ::= { sonusIpForwardGeneralGroupEntry 4 }

sonusIpForwardGeneralGroupSlot OBJECT-TYPE
    SYNTAX          Integer32
    MAX-ACCESS      read-only
    STATUS          current
    DESCRIPTION     
            "A 32-bit integer identifying the slot
             that the IP Forward General Group table applies to"
    ::= { sonusIpForwardGeneralGroupEntry 5 }

sonusIpForwardGeneralGroupInstance OBJECT-TYPE
    SYNTAX          Integer32
    MAX-ACCESS      read-only
    STATUS          current
    DESCRIPTION     
            "A 32-bit integer identifying the instance
             that the IP Forward General Group table applies to"
    ::= { sonusIpForwardGeneralGroupEntry 6 }

sonusIpCidrRouteTable OBJECT-TYPE
    SYNTAX          SEQUENCE OF SonusIpCidrRouteEntry
    MAX-ACCESS      not-accessible
    STATUS          current
    DESCRIPTION     
            "This entity's IP Routing table."
    REFERENCE       
            "RFC 1213 Section 6.6, The IP Group"
    ::= { sonusIpForwardingMIB 2 }

sonusIpCidrRouteEntry OBJECT-TYPE
    SYNTAX          SonusIpCidrRouteEntry
    MAX-ACCESS      not-accessible
    STATUS          current
    DESCRIPTION     
            "A particular route to  a  particular  destina-
             tion, under a particular policy."
    INDEX           { sonusIpCidrRouteShelf, sonusIpCidrRouteSlot, 
                      sonusIpCidrRouteInstance, sonusIpCidrRouteDest, 
                      sonusIpCidrRouteMask, sonusIpCidrRouteTos, 
                      sonusIpCidrRouteNextHop }
    ::= { sonusIpCidrRouteTable 1 }

SonusIpCidrRouteEntry ::=
    SEQUENCE {
        sonusIpCidrRouteDest            IpAddress,
        sonusIpCidrRouteMask            IpAddress,
        sonusIpCidrRouteTos             Integer32,
        sonusIpCidrRouteNextHop         IpAddress,
        sonusIpCidrRouteIfIndex         Integer32,
        sonusIpCidrRouteType            INTEGER,
        sonusIpCidrRouteProto           INTEGER,
        sonusIpCidrRouteAge             Integer32,
        sonusIpCidrRouteInfo            OBJECT IDENTIFIER,
        sonusIpCidrRouteNextHopAS       Integer32,
        sonusIpCidrRouteMetric1         Integer32,
        sonusIpCidrRouteMetric2         Integer32,
        sonusIpCidrRouteMetric3         Integer32,
        sonusIpCidrRouteMetric4         Integer32,
        sonusIpCidrRouteMetric5         Integer32,
        sonusIpCidrRouteStatus          RowStatus,
        sonusIpCidrRouteShelf           Integer32,
        sonusIpCidrRouteSlot            Integer32,
        sonusIpCidrRouteInstance        Integer32
    }

sonusIpCidrRouteDest OBJECT-TYPE
    SYNTAX          IpAddress
    MAX-ACCESS      read-only
    STATUS          current
    DESCRIPTION     
            "The destination IP address of this route.
             
             This object may not take a Multicast (Class  D)
             address value.
             
             Any assignment (implicit or  otherwise)  of  an
             instance  of  this  object to a value x must be
             rejected if the bitwise logical-AND of  x  with
             the  value of the corresponding instance of the
             ipCidrRouteMask object is not equal to x."
    ::= { sonusIpCidrRouteEntry 1 }

sonusIpCidrRouteMask OBJECT-TYPE
    SYNTAX          IpAddress
    MAX-ACCESS      read-only
    STATUS          current
    DESCRIPTION     
            "Indicate the mask to be logical-ANDed with the
             destination  address  before  being compared to
             the value  in  the  ipCidrRouteDest  field.   For
             those  systems  that  do  not support arbitrary
             subnet masks, an agent constructs the value  of
             the  ipCidrRouteMask  by  reference to the IP Ad-
             dress Class.
             
             Any assignment (implicit or  otherwise)  of  an
             instance  of  this  object to a value x must be
             rejected if the bitwise logical-AND of  x  with
             the  value of the corresponding instance of the
             ipCidrRouteDest object is not equal to ipCidrRoute-
             Dest."
    ::= { sonusIpCidrRouteEntry 2 }

sonusIpCidrRouteTos OBJECT-TYPE
    SYNTAX          Integer32
    MAX-ACCESS      read-only
    STATUS          current
    DESCRIPTION     
            "The policy specifier is the IP TOS Field.  The encoding
             of IP TOS is as specified  by  the  following convention.
             Zero indicates the default path if no more  specific
             policy applies.
             
             +-----+-----+-----+-----+-----+-----+-----+-----+
             |                 |                       |     |
             |   PRECEDENCE    |    TYPE OF SERVICE    |  0  |
             |                 |                       |     |
             +-----+-----+-----+-----+-----+-----+-----+-----+
             
                      IP TOS                IP TOS
                 Field     Policy      Field     Policy
                 Contents    Code      Contents    Code
                 0 0 0 0  ==>   0      0 0 0 1  ==>   2
                 0 0 1 0  ==>   4      0 0 1 1  ==>   6
                 0 1 0 0  ==>   8      0 1 0 1  ==>  10
                 0 1 1 0  ==>  12      0 1 1 1  ==>  14
                 1 0 0 0  ==>  16      1 0 0 1  ==>  18
                 1 0 1 0  ==>  20      1 0 1 1  ==>  22
                 1 1 0 0  ==>  24      1 1 0 1  ==>  26
                 1 1 1 0  ==>  28      1 1 1 1  ==>  30"
    ::= { sonusIpCidrRouteEntry 3 }

sonusIpCidrRouteNextHop OBJECT-TYPE
    SYNTAX          IpAddress
    MAX-ACCESS      read-only
    STATUS          current
    DESCRIPTION     
            "On remote routes, the address of the next sys-
             tem en route; Otherwise, 0.0.0.0."
    ::= { sonusIpCidrRouteEntry 4 }

sonusIpCidrRouteIfIndex OBJECT-TYPE
    SYNTAX          Integer32
    MAX-ACCESS      read-only
    STATUS          current
    DESCRIPTION     
            "The ifIndex value which identifies  the  local
             interface  through  which  the next hop of this
             route should be reached."
    DEFVAL          { 0 }
    ::= { sonusIpCidrRouteEntry 5 }

sonusIpCidrRouteType OBJECT-TYPE
    SYNTAX          INTEGER { other(1), reject(2), local(3), remote(4) }
    MAX-ACCESS      read-only
    STATUS          current
    DESCRIPTION     
            "The type of route.  Note that local(3)  refers
             to  a route for which the next hop is the final
             destination; remote(4) refers to  a  route  for
             which  the  next  hop is not the final destina-
             tion.
             
             Routes which do not result in traffic forwarding or
             rejection should not be displayed even if the
             implementation keeps them stored internally.
             
             
             reject (2) refers to a route which, if matched, discards
             the message as unreachable. This is used in some
             protocols as a means of correctly aggregating routes."
    ::= { sonusIpCidrRouteEntry 6 }

sonusIpCidrRouteProto OBJECT-TYPE
    SYNTAX          INTEGER { other(1), local(2), netmgmt(3), icmp(4), 
                        egp(5), ggp(6), hello(7), rip(8), isIs(9), 
                        esIs(10), ciscoIgrp(11), bbnSpfIgp(12), ospf(13), 
                        bgp(14), idpr(15), ciscoEigrp(16) }
    MAX-ACCESS      read-only
    STATUS          current
    DESCRIPTION     
            "The routing mechanism via which this route was
             learned.  Inclusion of values for gateway rout-
             ing protocols is not  intended  to  imply  that
             hosts should support those protocols."
    ::= { sonusIpCidrRouteEntry 7 }

sonusIpCidrRouteAge OBJECT-TYPE
    SYNTAX          Integer32
    MAX-ACCESS      read-only
    STATUS          current
    DESCRIPTION     
            "The number of seconds  since  this  route  was
             last  updated  or  otherwise  determined  to be
             correct.  Note that no semantics of  `too  old'
             can  be implied except through knowledge of the
             routing  protocol  by  which  the   route   was
             learned."
    DEFVAL          { 0 }
    ::= { sonusIpCidrRouteEntry 8 }

sonusIpCidrRouteInfo OBJECT-TYPE
    SYNTAX          OBJECT IDENTIFIER
    MAX-ACCESS      read-only
    STATUS          current
    DESCRIPTION     
            "A reference to MIB definitions specific to the
             particular  routing protocol which is responsi-
             ble for this route, as determined by the  value
             specified  in the route's ipCidrRouteProto value.
             If this information is not present,  its  value
             should be set to the OBJECT IDENTIFIER { 0 0 },
             which is a syntactically valid object  identif-
             ier, and any implementation conforming to ASN.1
             and the Basic Encoding Rules must  be  able  to
             generate and recognize this value."
    ::= { sonusIpCidrRouteEntry 9 }

sonusIpCidrRouteNextHopAS OBJECT-TYPE
    SYNTAX          Integer32
    MAX-ACCESS      read-only
    STATUS          current
    DESCRIPTION     
            "The Autonomous System Number of the Next  Hop.
             The  semantics of this object are determined by
             the routing-protocol specified in  the  route's
             ipCidrRouteProto  value. When  this object is
             unknown or not relevant its value should be set
             to zero."
    DEFVAL          { 0 }
    ::= { sonusIpCidrRouteEntry 10 }

sonusIpCidrRouteMetric1 OBJECT-TYPE
    SYNTAX          Integer32
    MAX-ACCESS      read-only
    STATUS          current
    DESCRIPTION     
            "The primary routing  metric  for  this  route.
             The  semantics of this metric are determined by
             the routing-protocol specified in  the  route's
             ipCidrRouteProto  value.   If  this metric is not
             used, its value should be set to -1."
    DEFVAL          { -1 }
    ::= { sonusIpCidrRouteEntry 11 }

sonusIpCidrRouteMetric2 OBJECT-TYPE
    SYNTAX          Integer32
    MAX-ACCESS      read-only
    STATUS          current
    DESCRIPTION     
            "An alternate routing metric  for  this  route.
             The  semantics of this metric are determined by
             the routing-protocol specified in  the  route's
             ipCidrRouteProto  value.   If  this metric is not
             used, its value should be set to -1."
    DEFVAL          { -1 }
    ::= { sonusIpCidrRouteEntry 12 }

sonusIpCidrRouteMetric3 OBJECT-TYPE
    SYNTAX          Integer32
    MAX-ACCESS      read-only
    STATUS          current
    DESCRIPTION     
            "An alternate routing metric  for  this  route.
             The  semantics of this metric are determined by
             the routing-protocol specified in  the  route's
             ipCidrRouteProto  value.   If  this metric is not
             used, its value should be set to -1."
    DEFVAL          { -1 }
    ::= { sonusIpCidrRouteEntry 13 }

sonusIpCidrRouteMetric4 OBJECT-TYPE
    SYNTAX          Integer32
    MAX-ACCESS      read-only
    STATUS          current
    DESCRIPTION     
            "An alternate routing metric  for  this  route.
             The  semantics of this metric are determined by
             the routing-protocol specified in  the  route's
             ipCidrRouteProto  value.   If  this metric is not
             used, its value should be set to -1."
    DEFVAL          { -1 }
    ::= { sonusIpCidrRouteEntry 14 }

sonusIpCidrRouteMetric5 OBJECT-TYPE
    SYNTAX          Integer32
    MAX-ACCESS      read-only
    STATUS          current
    DESCRIPTION     
            "An alternate routing metric  for  this  route.
             The  semantics of this metric are determined by
             the routing-protocol specified in  the  route's
             ipCidrRouteProto  value.   If  this metric is not
             used, its value should be set to -1."
    DEFVAL          { -1 }
    ::= { sonusIpCidrRouteEntry 15 }

sonusIpCidrRouteStatus OBJECT-TYPE
    SYNTAX          RowStatus
    MAX-ACCESS      read-only
    STATUS          current
    DESCRIPTION     
            "The row status variable, used according to
             row installation and removal conventions."
    ::= { sonusIpCidrRouteEntry 16 }

sonusIpCidrRouteShelf OBJECT-TYPE
    SYNTAX          Integer32
    MAX-ACCESS      read-only
    STATUS          current
    DESCRIPTION     
            "A 32-bit integer identifying the shelf
             that the IP CIDR Route table applies to"
    ::= { sonusIpCidrRouteEntry 17 }

sonusIpCidrRouteSlot OBJECT-TYPE
    SYNTAX          Integer32
    MAX-ACCESS      read-only
    STATUS          current
    DESCRIPTION     
            "A 32-bit integer identifying the slot
             that the IP CIDR Route table applies to"
    ::= { sonusIpCidrRouteEntry 18 }

sonusIpCidrRouteInstance OBJECT-TYPE
    SYNTAX          Integer32
    MAX-ACCESS      read-only
    STATUS          current
    DESCRIPTION     
            "A 32-bit integer identifying the instance
             that the IP CIDR Route table applies to"
    ::= { sonusIpCidrRouteEntry 19 }

sonusIpCidrAdminRouteTable OBJECT-TYPE
    SYNTAX          SEQUENCE OF SonusIpCidrAdminRouteEntry
    MAX-ACCESS      not-accessible
    STATUS          current
    DESCRIPTION     
            "This entity's administratively configured IP Routing table."
    ::= { sonusIpForwardingMIB 3 }

sonusIpCidrAdminRouteEntry OBJECT-TYPE
    SYNTAX          SonusIpCidrAdminRouteEntry
    MAX-ACCESS      not-accessible
    STATUS          current
    DESCRIPTION     
            "A particular route to  a  particular  destina-
             tion, under a particular policy."
    INDEX           { sonusIpCidrAdminRouteDest, 
                      sonusIpCidrAdminRouteMask, 
                      sonusIpCidrAdminRouteNextHop, 
                      sonusIpCidrAdminRouteIfIndex }
    ::= { sonusIpCidrAdminRouteTable 1 }

SonusIpCidrAdminRouteEntry ::=
    SEQUENCE {
        sonusIpCidrAdminRouteDest       IpAddress,
        sonusIpCidrAdminRouteMask       IpAddress,
        sonusIpCidrAdminRouteNextHop    IpAddress,
        sonusIpCidrAdminRouteIfIndex    Integer32,
        sonusIpCidrAdminRouteStatus     RowStatus
    }

sonusIpCidrAdminRouteDest OBJECT-TYPE
    SYNTAX          IpAddress
    MAX-ACCESS      read-create
    STATUS          current
    DESCRIPTION     
            "The destination IP address of this route.
             
             This object may not take a Multicast (Class  D)
             address value.
             
             Any assignment (implicit or  otherwise)  of  an
             instance  of  this  object to a value x must be
             rejected if the bitwise logical-AND of  x  with
             the  value of the corresponding instance of the
             ipCidrRouteMask object is not equal to x."
    ::= { sonusIpCidrAdminRouteEntry 1 }

sonusIpCidrAdminRouteMask OBJECT-TYPE
    SYNTAX          IpAddress
    MAX-ACCESS      read-create
    STATUS          current
    DESCRIPTION     
            "Indicate the mask to be logical-ANDed with the
             destination  address  before  being compared to
             the value  in  the  ipCidrRouteDest  field.   For
             those  systems  that  do  not support arbitrary
             subnet masks, an agent constructs the value  of
             the  ipCidrRouteMask  by  reference to the IP Ad-
             dress Class.
             
             Any assignment (implicit or  otherwise)  of  an
             instance  of  this  object to a value x must be
             rejected if the bitwise logical-AND of  x  with
             the  value of the corresponding instance of the
             ipCidrRouteDest object is not equal to ipCidrRoute-
             Dest."
    ::= { sonusIpCidrAdminRouteEntry 2 }

sonusIpCidrAdminRouteNextHop OBJECT-TYPE
    SYNTAX          IpAddress
    MAX-ACCESS      read-create
    STATUS          current
    DESCRIPTION     
            "On remote routes, the address of the next sys-
             tem en route; Otherwise, 0.0.0.0."
    ::= { sonusIpCidrAdminRouteEntry 3 }

sonusIpCidrAdminRouteIfIndex OBJECT-TYPE
    SYNTAX          Integer32
    MAX-ACCESS      read-create
    STATUS          current
    DESCRIPTION     
            "The interface  through  which  the next hop of this
             route should be reached."
    ::= { sonusIpCidrAdminRouteEntry 4 }

sonusIpCidrAdminRouteStatus OBJECT-TYPE
    SYNTAX          RowStatus
    MAX-ACCESS      read-create
    STATUS          current
    DESCRIPTION     
            "The row status variable, used according to
             row installation and removal conventions."
    ::= { sonusIpCidrAdminRouteEntry 5 }

END -- end of module SONUS-IP-FORWARDING-MIB.
