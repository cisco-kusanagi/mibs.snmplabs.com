-- *****************************************************************
-- ciscoWanVismXgcpCapabilities MIB
--
-- AGENT-CAPABILITIES mib for XGCP-MIB in the VISM product
--
-- Copyright(c) 2000 by Cisco Systems,Inc.
--
-- Author: Ganga Purlupady
--
-- Modified: Mike Manley
-- 2002/02/27 Fix bug CSCdw32263 where xgcpRestartDelay returns illegal value,
--            but the MIB object is not used. 
--
-- *****************************************************************

CISCO-WAN-VISM-XGCP-CAPABILITY DEFINITIONS ::= BEGIN

IMPORTS
        MODULE-IDENTITY
                FROM SNMPv2-SMI
        AGENT-CAPABILITIES
                FROM SNMPv2-CONF
        ciscoWanAgentCapability
                FROM CISCOWAN-SMI;   

ciscoWanVismXgcpCapability MODULE-IDENTITY
        LAST-UPDATED    "200202270000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"
        DESCRIPTION
                "The Agent Capabilities for XGCP-MIB."


 REVISION "200202270000Z"
 DESCRIPTION
     "Fix bug CSCdw32263 where xgcpRestartDelay returns illegal value"


 REVISION "200201210000Z"
 DESCRIPTION
     "Changed INCLUDES fields in order to pass SMIC compiler"


 REVISION "200108090000Z"
 DESCRIPTION
     "Added ciscoWanVismXgcpCapabilityV2R01 AGENT-CAPABILITIES."


        ::= { ciscoWanAgentCapability 322 }



ciscoWanVismXgcpCapabilityV2R00 AGENT-CAPABILITIES
    PRODUCT-RELEASE      "VISM Release1.5,VISM Release2.0"
    STATUS               current
    DESCRIPTION          "XGCP MIB Capabilities"

    SUPPORTS XGCP-MIB
    INCLUDES { xgcpCoreGroup, xgcpExtensionGroup, 
               xgcpPackageGroup
             }

	VARIATION   xgcpAdminStatus
	ACCESS      not-implemented
	DESCRIPTION "This is replaced by mgAdminiStrativeStateControl of MG-MIB."

	VARIATION   xgcpOperStatus
	ACCESS      not-implemented
	DESCRIPTION "This is replaced by mgAdminiStrativeState of MG-MIB."

	VARIATION   xgcpCapabilityPackageName
	DESCRIPTION "T is the only package supported."

    ::= { ciscoWanVismXgcpCapability 1 }



ciscoWanVismXgcpCapabilityV2R01 AGENT-CAPABILITIES
    PRODUCT-RELEASE      "VISM Release2.2"
    STATUS               current
    DESCRIPTION          "XGCP MIB Capabilities"

    SUPPORTS XGCP-MIB
    INCLUDES { xgcpCoreGroup, xgcpExtensionGroup, 
               xgcpPackageGroup
             }

	VARIATION   xgcpAdminStatus
	ACCESS      not-implemented
	DESCRIPTION "This is replaced by mgAdminiStrativeStateControl of MG-MIB."

	VARIATION   xgcpOperStatus
	ACCESS      not-implemented
	DESCRIPTION "This is replaced by mgAdminiStrativeState of MG-MIB."

	VARIATION   xgcpCapabilityPackageName
	DESCRIPTION "The packages supported are :
                         G  (generic),
                         D  (DTMF), 
                         M  (MF), 
                         T  (trunk), 
                         L  (line), 
                         H  (handset), 
                         R  (RTP), 
                         MS (RFC-3064 package to support MF (wink-start, immediate-start and
                             delay-dial) trunks), 
                         DT (RFC-3064 package to support DTMF (wink-start, immediate-start and
                             delay-dial) trunks),
                         MO (RFC-3064 package to support Feature Group D Operator Services Signaling,                               outgoing trunks), 
                         BL (RFC-3064 package to support DTMF loop-start and DTMF ground start
                             trunks), 
                         MD (RFC-3064 package to support North American MF Feature Group D EANA and
                            EAIN"

    ::= { ciscoWanVismXgcpCapability 2 }






ciscoWanVismXgcpCapabilityV3R00 AGENT-CAPABILITIES
    PRODUCT-RELEASE      "VISM Release3.0"
    STATUS               current
    DESCRIPTION          "XGCP MIB Capabilities"

    SUPPORTS XGCP-MIB
    INCLUDES { xgcpCoreGroup,
               xgcpExtensionGroup, 
               xgcpPackageGroup
             }

	VARIATION   xgcpRequestTimeOut
	ACCESS      not-implemented
	DESCRIPTION "This MIB object is not used by VISM."

	VARIATION   xgcpAdminStatus
	ACCESS      not-implemented
	DESCRIPTION "This is replaced by mgAdminiStrativeStateControl of MG-MIB."

	VARIATION   xgcpOperStatus
	ACCESS      not-implemented
	DESCRIPTION "This is replaced by mgAdminiStrativeState of MG-MIB."

	VARIATION   xgcpRestartDelay
	ACCESS      not-implemented
	DESCRIPTION "This MIB object is not used by VISM."

	VARIATION   xgcpCapabilityPackageName
	DESCRIPTION "The packages supported are :
                         G  (generic),
                         D  (DTMF), 
                         M  (MF), 
                         T  (trunk), 
                         L  (line), 
                         H  (handset), 
                         R  (RTP), 
                         MS (RFC-3064 package to support MF (wink-start, immediate-start and
                             delay-dial) trunks), 
                         DT (RFC-3064 package to support DTMF (wink-start, immediate-start and
                             delay-dial) trunks),
                         MO (RFC-3064 package to support Feature Group D Operator Services Signaling,                               outgoing trunks), 
                         BL (RFC-3064 package to support DTMF loop-start and DTMF ground start
                             trunks), 
                         MD (RFC-3064 package to support North American MF Feature Group D EANA and
                            EAIN"

    ::= { ciscoWanVismXgcpCapability 3 }



END
