-- ****************************************************************************
--
--              Dialogic Shared RAM Performance Information
--         Management Information Base for SNMP Network Management
--
--
--      Copyright 1997, Dialogic Corporation.
--      All Rights Reserved.
--
--      The information in this document is subject to change without notice.
--
--      The Dialogic Enterprise number is 3028.
--      The ASN.1 prefix to, and including the Dialogic Enterprise is:
--           1.3.6.1.4.1.3028
--
-- ****************************************************************************

DLGSRPRF-MIB DEFINITIONS ::= BEGIN

    IMPORTS
        Counter                 FROM RFC1155-SMI
        OBJECT-TYPE             FROM RFC1155-SMI
        dlgPerformanceInfo      FROM DLGC-GLOBAL-REG;


    dlgPiSram            OBJECT IDENTIFIER ::= { dlgPerformanceInfo 1 }
    dlgPsCurrentStats    OBJECT IDENTIFIER ::= { dlgPiSram 4 }
    dlgPsTotalStats      OBJECT IDENTIFIER ::= { dlgPiSram 5 }

-- ****************************************************************************
-- SRAM Performance MIB Revision
-- =========================
--
-- The dialogic enterprise              (1.3.6.1.4.1.3028)
--      dlgHardware Group               (1.3.6.1.4.1.3028.1)
--        dlgPerformanceInfo Group      (1.3.6.1.4.1.3028.1.2)
--         dlgPiSram Group              (1.3.6.1.4.1.3028.1.2.1)
--
--
--     An Agent conforming to this document will return a mibRevMajor
--     of one (1) and a mibRevMinor of zero (1).
--
--
-- ****************************************************************************

    dlgPiSramMibRev       OBJECT IDENTIFIER ::= { dlgPiSram 6 }

    dlgPiSramMibRevMajor OBJECT-TYPE
       SYNTAX  INTEGER (1..65535)
       ACCESS  read-only
       STATUS  mandatory
       DESCRIPTION
           "The Major Revision level.

            A change in the major revision level represents a major change
            in the architecture of the MIB.  A change in the major revision
            level may indicate a significant change in the information
            supported and/or the meaning of the supported information,
            correct interpretation of data may require a MIB document with
            the same major revision level."
       ::= { dlgPiSramMibRev 1 }

    dlgPiSramMibRevMinor OBJECT-TYPE
       SYNTAX  INTEGER (0..65535)
       ACCESS  read-only
       STATUS  mandatory
       DESCRIPTION
           "The Minor Revision level.

            A change in the minor revision level may represent some minor
            additional support. no changes to any pre-existing information
            has occurred."
       ::= { dlgPiSramMibRev 2 }

-- ****************************************************************************
--    SramPerformanceInfo Group
--    =========================
--
-- The dialogic enterprise              (1.3.6.1.4.1.3028)
--      dlgHardware Group               (1.3.6.1.4.1.3028.1)
--        dlgPerformanceInfo Group      (1.3.6.1.4.1.3028.1.2)
--         dlgPiSram Group              (1.3.6.1.4.1.3028.1.2.1)
--
--  The SramPerf group contains Performance related information about the
--  Dialogic Shared RAM (Voice and Network) cards in the system.
--
-- ****************************************************************************

    dlgPsStatsEnableMask OBJECT-TYPE
       SYNTAX  INTEGER 
       ACCESS  read-write
       STATUS  mandatory
       DESCRIPTION
           "Statistics Collection Enable mask. This mask enables or disables all statistics
		defined in this MIB.

            0 - Disables statistics collection.
            1 - Enables statistics collection.
            2 - Clear existing statistics (resets all stats to zero)

            Default value is 1 - statistics collection enabled"

       ::= { dlgPiSram 1 }

    dlgPsPollingInterval OBJECT-TYPE
        SYNTAX  INTEGER (0..65535)
        ACCESS  read-write
        STATUS  mandatory
        DESCRIPTION
            "The Agent's polling interval in seconds.

             This is the length of time that the Agent will keeps stats
             within the Current Stats group. By default, this value
             is 3600 seconds (1 hour). At the end of each interval the
             statistics are reset to zero and the counters begin counting
             up again. The dlgPsElapsedTime variable provides an indication
             how long into the current interval the agent has been 
             collecting statistics."

       ::= { dlgPiSram 2 }

    dlgPsElapsedTime OBJECT-TYPE
        SYNTAX  INTEGER
        ACCESS  read-only
        STATUS  mandatory
        DESCRIPTION
           "Number of Elapsed seconds since the start of the current
            polling interval." 

        ::= { dlgPiSram 3 }

-- ****************************************************************************
--    SRAM CurrentInterval Perfomance Table
--    ======================================
--
-- The dialogic enterprise              (1.3.6.1.4.1.3028)
--      dlgHardware Group               (1.3.6.1.4.1.3028.1)
--        dlgPerformanceInfo Group      (1.3.6.1.4.1.3028.1.2)
--         dlgPiSram Group              (1.3.6.1.4.1.3028.1.2.1)
--          dlgPsCurrentStats Group     (1.3.6.1.4.1.3028.1.2.1.4)
--
--
--  The Shared RAM current performance group provides a snap shot
--  of performance counters for the current polling interval.
--
-- ****************************************************************************
   
    dlgPsCurrentInterrupts OBJECT-TYPE
        SYNTAX  Counter
        ACCESS  read-only
        STATUS  mandatory
        DESCRIPTION
           "Number of hardware interrupts generated by Span or D4x based 
            boards for the current interval."
        ::= { dlgPsCurrentStats 1 }

    dlgPsCurrentDrvCommands OBJECT-TYPE
        SYNTAX  Counter
        ACCESS  read-only
        STATUS  mandatory
        DESCRIPTION
           "Number of commands sent to the driver for the current
            interval."
        ::= { dlgPsCurrentStats 2 }

    dlgPsCurrentFWCommands OBJECT-TYPE
        SYNTAX  Counter
        ACCESS  read-only
        STATUS  mandatory
        DESCRIPTION
           "Number of commands sent to the Firmware for the current 
            interval."
        ::= { dlgPsCurrentStats 3 }

    dlgPsCurrentUnSolEvents OBJECT-TYPE
        SYNTAX  Counter
        ACCESS  read-only
        STATUS  mandatory
        DESCRIPTION
           "Number of unsolicited events from the Firmware for the current 
            interval."
        ::= { dlgPsCurrentStats 4 }

    dlgPsCurrentBytesRead  OBJECT-TYPE
        SYNTAX  Counter
        ACCESS  read-only
        STATUS  mandatory
        DESCRIPTION
           "Number of bytes read from the Firmware during record
            for the current interval."
        ::= { dlgPsCurrentStats 5 }

    dlgPsCurrentBytesWritten OBJECT-TYPE
        SYNTAX  Counter
        ACCESS  read-only
        STATUS  mandatory
        DESCRIPTION
           "Number of bytes written to the Firmware during playback
            for the current interval."
        ::= { dlgPsCurrentStats 6 }

    dlgPsCurrentLostMsgToFW OBJECT-TYPE
        SYNTAX  Counter
        ACCESS  read-only
        STATUS  mandatory
        DESCRIPTION
           "Number of lost messages (commands) to the Firmware
            for the current interval. This value should always
            be zero. A non zero value typically indicates a Firmware
            or hardware failure."
        ::= { dlgPsCurrentStats 7 }

    dlgPsCurrentLostMsgFromFW OBJECT-TYPE
        SYNTAX  Counter
        ACCESS  read-only
        STATUS  mandatory
        DESCRIPTION
           "Number of lost messages (events) from the Firmware
            for the current interval. This value should typically be
            zero. A non zero value indicates the host cannot service
            all the messages being generated by the firmware."
        ::= { dlgPsCurrentStats 8 }

    dlgPsCurrentFWErrorMsgs OBJECT-TYPE
        SYNTAX  Counter
        ACCESS  read-only
        STATUS  mandatory
        DESCRIPTION
           "Number of error message packets generated by the Firmware
            for the current interval. This should typically be zero."
        ::= { dlgPsCurrentStats 9 }

    dlgPsCurrentDrvErrorMsgs OBJECT-TYPE
        SYNTAX  Counter
        ACCESS  read-only
        STATUS  mandatory
        DESCRIPTION
           "Number of error message packets generated by the Driver
            for the current interval. This should tpyically be zero."
        ::= { dlgPsCurrentStats 10 }


-- ****************************************************************************
--    SRAM Total Perfomance Table
--    ===========================
--
-- The dialogic enterprise              (1.3.6.1.4.1.3028)
--      dlgHardware Group               (1.3.6.1.4.1.3028.1)
--        dlgPerformanceInfo Group      (1.3.6.1.4.1.3028.1.2)
--         dlgPiSram Group              (1.3.6.1.4.1.3028.1.2.1)
--          dlgPsTotalStats Group       (1.3.6.1.4.1.3028.1.2.1.5)
--
--
--  The Shared RAM total performance group provides a snap shot
--  of performance counters since the driver\agent started keeping
--  the statistics.
--
-- ****************************************************************************

    dlgPsTotalInterrupts OBJECT-TYPE
        SYNTAX  Counter
        ACCESS  read-only
        STATUS  mandatory
        DESCRIPTION
           "Total Number of hardware interrupts generated by the 
            Span or D4x based boards."
        ::= { dlgPsTotalStats 1 }

    dlgPsTotalDrvCommands OBJECT-TYPE
        SYNTAX  Counter
        ACCESS  read-only
        STATUS  mandatory
        DESCRIPTION
           "Total Number of commands sent to the driver."
        ::= { dlgPsTotalStats 2 }

    dlgPsTotalFWCommands OBJECT-TYPE
        SYNTAX  Counter
        ACCESS  read-only
        STATUS  mandatory
        DESCRIPTION
           "Total Number of commands sent to the Firmware."
        ::= { dlgPsTotalStats 3 }

    dlgPsTotalUnSolEvents OBJECT-TYPE
        SYNTAX  Counter
        ACCESS  read-only
        STATUS  mandatory
        DESCRIPTION
           "Total Number of unsolicited events from the Firmware."
        ::= { dlgPsTotalStats 4 }

    dlgPsTotalBytesRead  OBJECT-TYPE
        SYNTAX  Counter
        ACCESS  read-only
        STATUS  mandatory
        DESCRIPTION
           "Total Number of bytes Read from the Firmware during record."
        ::= { dlgPsTotalStats 5 }

    dlgPsTotalBytesWritten OBJECT-TYPE
        SYNTAX  Counter
        ACCESS  read-only
        STATUS  mandatory
        DESCRIPTION
           "Total Number of bytes written to the Firmware during 
            playback."
        ::= { dlgPsTotalStats 6 }

    dlgPsTotalLostMsgToFW OBJECT-TYPE
        SYNTAX  Counter
        ACCESS  read-only
        STATUS  mandatory
        DESCRIPTION
           "Total Number of lost messages (commands) to the Firmware.
            This value should always be zero. A non zero value typically 
            indicates a Firmware or Hardware failure."
        ::= { dlgPsTotalStats 7 }

    dlgPsTotalLostMsgFromFW OBJECT-TYPE
        SYNTAX  Counter
        ACCESS  read-only
        STATUS  mandatory
        DESCRIPTION
           "Total Number of lost messages (events) from the Firmware.
            This value should typically be zero. A non zero value 
            indicates the host cannot service all the messages being 
            generated by the firmware."
        ::= { dlgPsTotalStats 8 }

    dlgPsTotalFWErrorMsgs OBJECT-TYPE
        SYNTAX  Counter
        ACCESS  read-only
        STATUS  mandatory
        DESCRIPTION
           "Total Number of error message packets gernerated by the 
            Firmware. This should typically be zero."
        ::= { dlgPsTotalStats 9 }

    dlgPsTotalDrvErrorMsgs OBJECT-TYPE
        SYNTAX  Counter
        ACCESS  read-only
        STATUS  mandatory
        DESCRIPTION
           "Total Number of error message packets generated by the Driver.
            This should typically be zero."
        ::= { dlgPsTotalStats 10 }


END
