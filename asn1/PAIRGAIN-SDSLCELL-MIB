PAIRGAIN-SDSLCELL-MIB
-- PairGain SDSL MIB Release 1.0(6)
-- Revision Date:  05/16/2000
--
-- Copyright 2000 PairGain Technologies, Inc.  All Rights
-- Reserved.  Reproduction of this document is authorized on
-- condition that the foregoing copyright notice is included.
-- This PairGain SNMP Management Information Base Specification
-- (Specification) embodies PairGain's confidential and
-- proprietary intellectual property.  PairGain retains all
-- title and ownership in the Specification, including any
-- revisions.
--
-- It is PairGain's intent to encourage the widespread use of
-- this Specification in connection with the management of
-- PairGain products. PairGain grants vendors, end-users,
-- and other interested parties a non-exclusive license to
-- use this Specification in connection with the management
-- of PairGain products.
--
-- This Specification is supplied "AS IS," and PairGain makes
-- no warranty, either expressed or implied, as to the use,
-- operation, condition, or performance of the Specification.
--
-- Revision History
--------------------------------------------------------------
-- Date     Ver     Programmer      Description
--------------------------------------------------------------
-- 03/01/00 1.0     Chirag Barot    Initial Checkin
-- 03/16/00 1.0(2)  R. Wada 		Added Clear, running counters, nextindex,
--                                  removed TC layer.
-- 03/23/00 1.0(3)  R. Wada			Added profile in use flag, alarm status
--                                  table, hardware alarm trap.
-- 04/04/00 1.0(4)  R. Wada		    Added enumeration for hardware cause,
--                                  renamed AlarmLastCleared to
--                                  AlarmLastChanged.
-- 04/07/00 1.0(5)  R. Wada		    Made changes per MIB Review. Added Pg to
--                                  SdslcellLineProfileType and
--                                  SdslcellAlarmProfileType. Moved RowStatus
--                                  objects right after Index objects instead
--                                  of being at the end.  Added "Cell" to
--                                  IndexNext objects, changed inuse object to
--                                  read only.  Changed enumerated type
--                                  inactive from 0 to 1, active from 1 to 2,
--                                  enumerations of pgSdslCellCurrStatus.
-- 05/16/00 1.0(6)  R. Wada		    Changed VarBind contents of trap.
--------------------------------------------------------------

DEFINITIONS ::= BEGIN

-- SECTION 1: Top Level Definitions

IMPORTS
    Counter32, Integer32, MODULE-IDENTITY, OBJECT-TYPE, NOTIFICATION-TYPE
        FROM SNMPv2-SMI
	OBJECT-TYPE
        FROM RFC-1212
    pgainSDSLCell
        FROM PAIRGAIN-COMMON-HD-MIB
    ifIndex
        FROM RFC1213-MIB
    DisplayString, RowStatus, TruthValue, TimeStamp
        FROM SNMPv2-TC;

    PgSdslcellLineProfileType ::= INTEGER(0..65535)
    PgSdslcellAlarmProfileType ::= INTEGER(0..65535)

-- Module Identity SDSL (required for SNMP v2)
pgsdslCellMIB MODULE-IDENTITY
    LAST-UPDATED    "0003170000Z"
    ORGANIZATION    "PairGain Technologies Inc."
        CONTACT-INFO    "
                    14402 Franklin Avenue
                    Tustin, CA  92780
                    "
    DESCRIPTION "The module defines the SDSL CELL  MIB "
    ::= {pgainSDSLCell 1}

pgsdslCellMibObjects        OBJECT IDENTIFIER ::= { pgsdslCellMIB 1 }




    ----------------------------------------------------
    -- SDSL Cell Line Table -
	-- Assigns line and alarm profile indexes which are used to configure
	-- each physical line/port of the SDSL Cell card.
    ----------------------------------------------------

	pgSdslCellLineTable  OBJECT-TYPE
        SYNTAX      SEQUENCE OF PgSdslCellLineEntry
        MAX-ACCESS  not-accessible
        STATUS      current
        DESCRIPTION
            "This table contains the information pointers used to configure
			 each physical line/port of the SDSL Cell card.
			 Each line/port is assigned the index of a Line Profile which
			 characterizes the speed and other characteristics of the line/port.
			 Each line/port is also assigned the index of an Alarm Profile
			 which characterizes the alarm settings of the line/port.
			 "
        ::= { pgsdslCellMibObjects 1 }

    pgSdslCellLineEntry  OBJECT-TYPE
        SYNTAX      PgSdslCellLineEntry
        MAX-ACCESS  not-accessible
        STATUS      current
        DESCRIPTION
            "This entry contains the indexes of the Line and Alarm Profiles
			that are assigned to the physical interface indexed by the ifIndex.
			"
        INDEX       {ifIndex }
        ::= { pgSdslCellLineTable 1 }

    PgSdslCellLineEntry ::= SEQUENCE {
        pgSdslCellLineProfile                  PgSdslcellLineProfileType,
        pgSdslCellAlarmProfile                 PgSdslcellAlarmProfileType

        }


    pgSdslCellLineProfile OBJECT-TYPE
        SYNTAX      PgSdslcellLineProfileType
        MAX-ACCESS  read-write
        STATUS      current
        DESCRIPTION
            "The value of this object identifies the row
             in the Cell SDSL Line Configuration Profile Table,
             (pgSdslCellLineProfileTable), which applies for this
             Cell SDSL line.   In the case which the configuration
             profile has not been set, the value will be set to '0'.

             If the implementator of this MIB has choosen not
             to implement 'dynamic assignment' of profiles, this
             object is not useful and should return noSuchName
             upon SNMP request."

        ::= { pgSdslCellLineEntry 1}

    pgSdslCellAlarmProfile OBJECT-TYPE
        SYNTAX      PgSdslcellAlarmProfileType
        MAX-ACCESS  read-write
        STATUS      current
        DESCRIPTION
            "The value of this object identifies the row
             in the Cell SDSL Line Alarm Configuration Profile Table,
             (pgSdslCellLineAlarmProfileTable), which applies to this
             Cell SDSL line.  In the case which the configuration profile
             has not been set, the value will be set to '0'.

             If the implementator of this MIB has choosen not
             to implement 'dynamic assignment' of profiles, this
             object is not useful and should return noSuchName
             upon SNMP request."

        ::= { pgSdslCellLineEntry 2}


    ----------------------------------------------------
    -- SDSL Cell Physical Table
	-- This table contains information about the physical
	-- line/port indexed by ifIndex.
    ----------------------------------------------------

   pgSdslCellPhysTable  OBJECT-TYPE
        SYNTAX      SEQUENCE OF PgSdslCellPhysEntry
        MAX-ACCESS  not-accessible
        STATUS      current
        DESCRIPTION
            "This table provides one row for each port.
             Each row contains the Physical Layer Parameters
             table for that port."
        ::= {pgsdslCellMibObjects 2}

   pgSdslCellPhysEntry       OBJECT-TYPE
                SYNTAX          PgSdslCellPhysEntry
                MAX-ACCESS      not-accessible
                STATUS          current
                DESCRIPTION     "An entry in the pgSdslCellPhysTable."
                INDEX           { ifIndex }
        ::= { pgSdslCellPhysTable 1 }


  PgSdslCellPhysEntry ::=    SEQUENCE {
                pgSdslCellInvSerialNumber         DisplayString,
                pgSdslCellInvVendorID             Integer32,
                pgSdslCellInvVersionNumber        Integer32,
                pgSdslCellCurrSnrMgn              INTEGER,
                pgSdslCellCurrAtn                 INTEGER,
                pgSdslCellCurrStatus              INTEGER
				}

                pgSdslCellInvSerialNumber OBJECT-TYPE
                    SYNTAX      DisplayString (SIZE(1..32))
                    MAX-ACCESS  read-only
                    STATUS      current
                    DESCRIPTION
                        "Vendor specific string that identifies the vendor
                        equipment."
                ::= { pgSdslCellPhysEntry 1 }

                pgSdslCellInvVendorID OBJECT-TYPE
                    SYNTAX      Integer32
                    MAX-ACCESS  read-only
                    STATUS      current
                    DESCRIPTION
                        "The vendor ID assigned by T1E1.413 according to its
                        Annex D."
                ::= { pgSdslCellPhysEntry 2 }

                pgSdslCellInvVersionNumber OBJECT-TYPE
                    SYNTAX      Integer32
                    MAX-ACCESS  read-only
                    STATUS      current
                    DESCRIPTION
                        "Vendor specific Version number "
                ::= { pgSdslCellPhysEntry 3 }

                       -- current status group
                       --
                pgSdslCellCurrSnrMgn OBJECT-TYPE
                    SYNTAX      INTEGER(0..310)
                    UNITS       "tenth dB"
                    MAX-ACCESS  read-only
                    STATUS      current
                    DESCRIPTION
                        "Noise Margin as seen by this ATU with respect to its
                        received signal in tenth dB."
                ::= { pgSdslCellPhysEntry 4 }

                pgSdslCellCurrAtn OBJECT-TYPE
                    SYNTAX      INTEGER(0..630)
                    UNITS       "tenth dB"
                    MAX-ACCESS  read-only
                    STATUS      current
                    DESCRIPTION
                        "Measured difference in the total power transmitted by
                        the peer  and the total power received by this end.
                        This is measured in in tenth dB."
                ::= { pgSdslCellPhysEntry 5 }

               pgSdslCellCurrStatus OBJECT-TYPE
                    SYNTAX      INTEGER {
						  up (1),
						down (2),
						hand (3),
						test (4),
						fail (5)
						}
                    MAX-ACCESS  read-only
                    STATUS      current
                    DESCRIPTION
                        "Status indicates the state of the Port. This value is
						intended to give more detail than is currently available
						through the ifOperStatus.
						UP   (1) - SDSL line is in data mode, it is
						                synchronized.
						DOWN (2) - SDSL is down and no CPE has been
						                recognized
						HAND (3) - SDSL is down but a CPE has been
						                recognized and SDSL training is in
										progress (handshake phase)
						TEST (4) - SDSL line is in a test mode
						FAIL (5) - SDSL line is down and had some
										unrecoverable hardware failure or
										transceiver is missing
                        This is intended to supplement ifOperStatus."

				::= { pgSdslCellPhysEntry 6 }


    ----------------------------------------------------
    -- SDSL Cell Profile Index Next
	-- This object is used to get the next available index
	-- for creating a new entry in the pgSdslCellLineProfile table.
    ----------------------------------------------------
	pgSdslCellLineProfileIndexNext OBJECT-TYPE
        SYNTAX          INTEGER(0..65535)
        MAX-ACCESS      read-only
        STATUS          current
        DESCRIPTION
            " This object contains an appropriate value to
            be used for pgSdslCellLineProfileIndex when creating
            entries in the pgSdslCellLineProfileTable. The value
            '0' indicates that no unassigned entries are
            available. To obtain the pgSdslCellLineProfileIndexNext
            value for a new entry, the manager issues a
            management protocol retrieval operation to obtain
            the current value of this object.  After each
            retrieval, the agent should modify the value to
            the next unassigned index.

            If the implementator of this MIB has choosen not
            to implement 'dynamic assignment' of profiles, this
            object is not useful and should return noSuchName
            upon SNMP request."
        ::= { pgsdslCellMibObjects 3}

    ----------------------------------------------------
    -- SDSL Cell Line Profile Table -
    ----------------------------------------------------

	pgSdslCellLineProfileTable  OBJECT-TYPE
        SYNTAX      SEQUENCE OF PgSdslCellLineProfileEntry
        MAX-ACCESS  not-accessible
        STATUS      current
        DESCRIPTION
            "This table contains information on the Cell-SDSL line
            configuration.  One entry in this table reflects a
            profile defined by a manager which can be used to
            configure the Cell-SDSL line."

        ::= {pgsdslCellMibObjects 4 }

    pgSdslCellLineProfileEntry  OBJECT-TYPE
        SYNTAX      PgSdslCellLineProfileEntry
        MAX-ACCESS  not-accessible
        STATUS      current
        DESCRIPTION
            "Each entry consists of a list of parameters that
            represents the configuration of an SDSL Cell.  A
            profile is created in one step with all necessary
            parameter values and pgSdslCellLineProfileRowStatus set to
            createAndGo.  This RowStatus object is also used
            to delete destroy profiles."
        INDEX       {pgSdslCellLineProfileIndex }
        ::= {pgSdslCellLineProfileTable 1}

    PgSdslCellLineProfileEntry ::= SEQUENCE {
        pgSdslCellLineProfileIndex     PgSdslcellLineProfileType,
        pgSdslCellLineProfileRowStatus RowStatus,
        pgSdslCellLineCode             INTEGER,
        pgSdslCellLineRateMode         INTEGER,
        pgSdslCellLineRate             INTEGER,
        pgSdslCellLineTermType         INTEGER,
		pgSdslCellLineProfileInUse	   INTEGER
        }


	pgSdslCellLineProfileIndex OBJECT-TYPE
        SYNTAX      PgSdslcellLineProfileType
        MAX-ACCESS  read-write
        STATUS      current
        DESCRIPTION
                "This object is used by the line  configuration
                        table in order to identify a row of this table"
        ::= { pgSdslCellLineProfileEntry 1 }

    pgSdslCellLineProfileRowStatus OBJECT-TYPE
        SYNTAX      RowStatus
        MAX-ACCESS  read-write
        STATUS      current
        DESCRIPTION
                 "This object is used to create a new row or modify or
                 delete an existing row in this table.
                 A profile activated by setting this object to
                 `active'.  When `active' is set, the system
                 will validate the profile.

                 Before a profile can be deleted or taken out of
                 service, (by setting this object to `destroy' or
                 `outOfService') it must be first unreferenced
                 from all associated ports.

                 If the implementator of this MIB has chosen not
                 to implement `dynamic assignment' of profiles, this
                 object's MIN-ACCESS is read-only and its value
                 is always to be `active'."

        ::= { pgSdslCellLineProfileEntry 2 }

    pgSdslCellLineCode OBJECT-TYPE
        SYNTAX      INTEGER {
        other (1),
        twoB1Q  (2) -- 2B1Q legacy code
        }
        MAX-ACCESS  read-write
        STATUS      current
        DESCRIPTION
                "Specifies the  SDSL coding type used on this line.
                    Other types may be added in the future."
        ::= { pgSdslCellLineProfileEntry 3}

    pgSdslCellLineRateMode OBJECT-TYPE
        SYNTAX      INTEGER {
        other     (1),
        autoBaud  (2), -- autoBaud
        autoConex (3), -- conexant proprietary
        fixed     (4)  -- Fixed Rate
        }
        MAX-ACCESS  read-write
        STATUS      current
        DESCRIPTION
                   "Defines what form of transmit rate adaptation is
                    configured on this port.  See chipset description for more
                    information."
        ::= { pgSdslCellLineProfileEntry 4}

    pgSdslCellLineRate OBJECT-TYPE
        SYNTAX      INTEGER(64..2320)
        UNITS       "kbps"
        MAX-ACCESS  read-write
        STATUS      current
        DESCRIPTION
                "Defines the rate of this port , if RateMode is set to fixed"
        ::= { pgSdslCellLineProfileEntry 5 }

    pgSdslCellLineTermType OBJECT-TYPE
        SYNTAX      INTEGER {
        co     (1), -- central office
        rt     (2) -- remote terminal
        }
        MAX-ACCESS  read-write
        STATUS      current
        DESCRIPTION
                   "Defines the mode of the transceiver ,intend for testing only"
        ::= { pgSdslCellLineProfileEntry 6}

    pgSdslCellLineProfileInUse OBJECT-TYPE
        SYNTAX      INTEGER {
        	notused   (1), -- not currently assigned to any lines
        	inuse     (2)  -- assigned to 1 or more lines
        }
        MAX-ACCESS  read-only
        STATUS      current
        DESCRIPTION
                   "Defines whether this profile is in use.  The agent must insure that
				   this object is up to date whenever the line table is updated.

				   If the implementator of this MIB has choosen not
            	   to implement this feature, this object
            	   should return noSuchName upon SNMP request."
        ::= { pgSdslCellLineProfileEntry 7}


    ----------------------------------------------------
    -- SDSL Cell Alarm Profile Index Next
	-- This object is used to get the next available index
	-- for creating a new entry in the pgSdslCellAlarmProfile table.
    ----------------------------------------------------

	pgSdslCellAlarmProfileIndexNext OBJECT-TYPE
        SYNTAX          INTEGER(0..65535)
        MAX-ACCESS      read-only
        STATUS          current
        DESCRIPTION
            " This object contains an appropriate value to
            be used for pgSdslCellAlarmProfileIndex when creating
            entries in the pgSdslCellAlarmProfileTable. The value
            '0' indicates that no unassigned entries are
            available. To obtain the pgSdslCellAlarmProfileIndexNext
            value for a new entry, the manager issues a
            management protocol retrieval operation to obtain
            the current value of this object.  After each
            retrieval, the agent should modify the value to
            the next unassigned index.

            If the implementator of this MIB has choosen not
            to implement 'dynamic assignment' of profiles, this
            object is not useful and should return noSuchName
            upon SNMP request."
        ::= { pgsdslCellMibObjects 5}


    ----------------------------------------------------
    -- Cell SDSL Alarm Profile Table -
    ----------------------------------------------------

	pgSdslCellAlarmProfileTable  OBJECT-TYPE
        SYNTAX      SEQUENCE OF PgSdslCellAlarmProfileEntry
        MAX-ACCESS  not-accessible
        STATUS      current
        DESCRIPTION
            "This table contains information on the Cell-SDSL Alarm
            configuration.  One entry in this table reflects a
            profile defined by a manager which can be used to
            configure the Cell-SDSL line Alarms."

        ::= { pgsdslCellMibObjects 6 }

    pgSdslCellAlarmProfileEntry  OBJECT-TYPE
        SYNTAX      PgSdslCellAlarmProfileEntry
        MAX-ACCESS  not-accessible
        STATUS      current
        DESCRIPTION
            "Each entry consists of a list of parameters that
            represents the Alarm configuration of an Cell SDSL port.  A
            profile is created in one step with all necessary
            parameter values and pgSdslCellAlarmProfileRowStatus set to
            createAndGo.  This RowStatus object is also used
            to delete destroy profiles."
        INDEX       {pgSdslCellAlarmProfileIndex }
        ::= { pgSdslCellAlarmProfileTable 1}


   PgSdslCellAlarmProfileEntry ::= SEQUENCE {
		pgSdslCellAlarmProfileRowStatus RowStatus,
        pgSdslCellAlarmProfileIndex     PgSdslcellAlarmProfileType,
        pgSdslCellThresh15MinLOSS       INTEGER,
        pgSdslCellThresh15MinLOCD       INTEGER,
        pgSdslCellThresh15MinSLOCD      INTEGER,
        pgSdslCellThreshSNR             INTEGER,
		pgSdslCellAlarmProfileInUse		INTEGER
        }


    pgSdslCellAlarmProfileIndex OBJECT-TYPE
        SYNTAX      PgSdslcellAlarmProfileType
        MAX-ACCESS  read-write
        STATUS      current
        DESCRIPTION
                "This object is used by the line alarm  configuration
                        table in order to identify a row of this table"
        ::= { pgSdslCellAlarmProfileEntry 1}

    pgSdslCellAlarmProfileRowStatus OBJECT-TYPE
        SYNTAX      RowStatus
        MAX-ACCESS  read-write
        STATUS      current
        DESCRIPTION
                 "This object is used to create a new row or modify or
                 delete an existing row in this table.
                 A profile activated by setting this object to
                 `active'.  When `active' is set, the system
                 will validate the profile.

                 Before a profile can be deleted or taken out of
                 service, (by setting this object to `destroy' or
                 `outOfService') it must be first unreferenced
                 from all associated ports.

                 If the implementator of this MIB has chosen not
                 to implement `dynamic assignment' of profiles, this
                 object's MIN-ACCESS is read-only and its value
                 is always to be `active'."

        ::= { pgSdslCellAlarmProfileEntry 2 }



    pgSdslCellThresh15MinLOSS OBJECT-TYPE
        SYNTAX      INTEGER(0..900)
        MAX-ACCESS  read-write
        STATUS      current
        DESCRIPTION
                "The number of Loss of Signal Seconds,
                encountered by an Cell SDSL interface within any given 15
                minutes performance data collection period, which causes
                the SNMP agent to send an pgSdslCellLOSSThreshTrap.
                Limit of one trap will be sent for any one interval.
                A value of '0' will disable the trap."
        ::= { pgSdslCellAlarmProfileEntry 3}

    pgSdslCellThresh15MinLOCD OBJECT-TYPE
        SYNTAX      Integer32
        MAX-ACCESS  read-write
        STATUS      current
        DESCRIPTION
                "The number of Loss of Cell Delineation,
                encountered by an Cell SDSL interface within any given 15
                minutes performance data collection period, which causes
                the SNMP agent to send an pgSdslCellLOCDThreshTrap.
                Limit of one trap will be sent for any one interval.
                A value of '0' will disable the trap."
        ::= { pgSdslCellAlarmProfileEntry 4}

    pgSdslCellThresh15MinSLOCD OBJECT-TYPE
        SYNTAX      Integer32
        MAX-ACCESS  read-write
        STATUS      current
        DESCRIPTION
                "The number of Severe Loss of Cell Delineation,
                encountered by an Cell SDSL interface within any given 15
                minutes performance data collection period, which causes
                the SNMP agent to send an pgSdslCellSLOCDThreshTrap.
                Limit of one trap will be sent for any one interval.
                A value of '0' will disable the trap."
        ::= { pgSdslCellAlarmProfileEntry 5}

    pgSdslCellThreshSNR OBJECT-TYPE
        SYNTAX      Integer32
        MAX-ACCESS  read-write
        STATUS      current
        DESCRIPTION
                "The SNR value below which causes
                the SNMP agent to send a pgSdslCellSNRThreshTrap.
                Limit of one trap will be sent for any TBD interval.
                A value of '0' will disable the trap."
        ::= { pgSdslCellAlarmProfileEntry 6}

    pgSdslCellAlarmProfileInUse OBJECT-TYPE
        SYNTAX      INTEGER {
        	notused   (1), -- not currently assigned to any lines
        	inuse     (2)  -- assigned to 1 or more lines
        }
        MAX-ACCESS  read-only
        STATUS      current
        DESCRIPTION
                   "Defines whether this profile is in use.  The agent must insure that
				   this object is up to date whenever the line table is updated.

				   If the implementator of this MIB has choosen not
            	   to implement this feature, this object
            	   should return noSuchName upon SNMP request."
        ::= { pgSdslCellAlarmProfileEntry 7}


    ------------------------------------------------------------
    -- SDSL Cell Performance                                   -
	-- Running Counters Table                                  -
	-- NOTE:  Running counters are provided for manufacturing  -
	-- and provide redundant information to what is already    -
	-- available in the Current 15 minute, Previous 96 15      -
	-- minute, Current 24 Hour, and Previous 7 24 Hour interval-
	-- tables.                                                 -
	------------------------------------------------------------

    pgSdslCellPerfCurrTable  OBJECT-TYPE
        SYNTAX      SEQUENCE OF PgSdslCellPerfCurrEntry
        MAX-ACCESS  not-accessible
        STATUS      current
        DESCRIPTION
            "This table contains running counters on the Cell-SDSL Line
             performance data.  These counters will rollover after overflow.
			 These counters are used internally for testing and production
			 purposes and need not be displayed to the end-user since all of
			 the information is available in other history tables.
			 These counters are only cleared by explicitly calling the
			 pgSdslCellClearStats function. "

        ::= {pgsdslCellMibObjects 7 }

    pgSdslCellPerfCurrEntry  OBJECT-TYPE
        SYNTAX      PgSdslCellPerfCurrEntry
        MAX-ACCESS  not-accessible
        STATUS      current
        DESCRIPTION
                "An Entry in pgSdslCellPerfCurrTable "
        INDEX       { ifIndex }
        ::= { pgSdslCellPerfCurrTable 1}

    PgSdslCellPerfCurrEntry ::= SEQUENCE {
        pgSdslCellPerfCurrLOSS       INTEGER,
        pgSdslCellPerfCurrLOCD       INTEGER,
        pgSdslCellPerfCurrSLOCD      INTEGER,
		pgSdslCellClearStats         INTEGER,
        pgSdslCellStatsLastCleared   TimeStamp
		}

    pgSdslCellPerfCurrLOSS OBJECT-TYPE
        SYNTAX      Counter32
        MAX-ACCESS  read-only
        STATUS      current
        DESCRIPTION
                "The number of  Loss of Signal seconds, encountered
                by an Cell SDSL interface since powered up or since last
                cleared with a clear command"
        ::= { pgSdslCellPerfCurrEntry 1}

    pgSdslCellPerfCurrLOCD OBJECT-TYPE
        SYNTAX      Counter32
        MAX-ACCESS  read-only
        STATUS      current
        DESCRIPTION
                "The number of Loss of Cell Delineation, encountered
                by an Cell SDSL interface since powered up or since last
                cleared with a clear command"
        ::= { pgSdslCellPerfCurrEntry 2}

    pgSdslCellPerfCurrSLOCD OBJECT-TYPE
        SYNTAX      Counter32
        MAX-ACCESS  read-only
        STATUS      current
        DESCRIPTION
                "The number of  Severe Loss of Cell Delineation, encountered
                by an Cell SDSL interface since powered up or since last
                cleared with a clear command"
        ::= { pgSdslCellPerfCurrEntry 3}

	pgSdslCellClearStats OBJECT-TYPE
		SYNTAX  INTEGER {
			clear(1)
		}
		MAX-ACCESS  read-write
		STATUS  	current
		DESCRIPTION
			"Clear running statistics counters to zero on this particular port.
			Writing a '1' to this MIB object only clears the counters present in
			pgSdslCellPerfCurrTable with the matching ifIndex."
		::= {  pgSdslCellPerfCurrEntry 4 }


     pgSdslCellStatsLastCleared OBJECT-TYPE
          SYNTAX  TimeStamp
          MAX-ACCESS  read-only
          STATUS  current
          DESCRIPTION
                 "The value of MIB II's sysUpTime object at the
                 last time these statistics were cleared.
                 At power on, this value should contain 0.
                 "
          ::= { pgSdslCellPerfCurrEntry 5 }



    ----------------------------------------------------
    -- SDSL Cell Performance                           -
	-- Current 15 Minute Table                         -
    ----------------------------------------------------

	pgSdslCellPerfCurr15MinTable  OBJECT-TYPE
        SYNTAX      SEQUENCE OF PgSdslCellPerfCurr15MinEntry
        MAX-ACCESS  not-accessible
        STATUS      current
        DESCRIPTION
            "This table contains information on the Cell-SDSL Line
             performance data for the current 15 minute period"

        ::= {pgsdslCellMibObjects 8 }

    pgSdslCellPerfCurr15MinEntry  OBJECT-TYPE
        SYNTAX      PgSdslCellPerfCurr15MinEntry
        MAX-ACCESS  not-accessible
        STATUS      current
        DESCRIPTION
                "An Entry in pgSdslCellPerfCurr15MinTable "
        INDEX       { ifIndex }
        ::= { pgSdslCellPerfCurr15MinTable 1}

    PgSdslCellPerfCurr15MinEntry ::= SEQUENCE {
        pgSdslCellPerfCurr15MinLOSS       INTEGER,
        pgSdslCellPerfCurr15MinLOCD       INTEGER,
        pgSdslCellPerfCurr15MinSLOCD      INTEGER,
		pgSdslCellClearHistory			  INTEGER,
		pgSdslCellHistoryLastCleared	  TimeStamp
		}

    pgSdslCellPerfCurr15MinLOSS OBJECT-TYPE
        SYNTAX      Counter32
        MAX-ACCESS  read-only
        STATUS      current
        DESCRIPTION
                "The number of  Loss of Signal seconds, encountered
                by an Cell SDSL interface within current  15
                minutes performance data collection interval"
        ::= { pgSdslCellPerfCurr15MinEntry 1}

    pgSdslCellPerfCurr15MinLOCD OBJECT-TYPE
        SYNTAX      Counter32
        MAX-ACCESS  read-only
        STATUS      current
        DESCRIPTION
                "The number of Loss of Cell Delineation, encountered
                by an Cell SDSL interface within current  15
                minutes performance data collection interval"
        ::= { pgSdslCellPerfCurr15MinEntry 2}

    pgSdslCellPerfCurr15MinSLOCD OBJECT-TYPE
        SYNTAX      Counter32
        MAX-ACCESS  read-only
        STATUS      current
        DESCRIPTION
                "The number of  Severe Loss of Cell Delineation, encountered
                by an Cell SDSL interface within current  15
                minutes performance data collection interval"
        ::= { pgSdslCellPerfCurr15MinEntry 3}

	pgSdslCellClearHistory OBJECT-TYPE
		SYNTAX  INTEGER {
			clear(1)
		}
		MAX-ACCESS  read-write
		STATUS  	current
		DESCRIPTION
			"Writing a '1' to this object clears all of the statistics and history counters
			related to this port (ifIndex) except for the running counters stored in
			pgSdslCellPerfCurrTable.
			The following table entries indexed by ifIndex will be cleared by setting this object:
			pgSdslCellPerfCurr15MinTable,
			pgSdslCellPerf15MinIntervalTable,
			pgSdslCellPerfCurr24hTable,
			pgSdslCellPerf24hIntervalTable.
			"
		::= {  pgSdslCellPerfCurr15MinEntry 4 }


   	pgSdslCellHistoryLastCleared OBJECT-TYPE
        SYNTAX  TimeStamp
        MAX-ACCESS  read-only
        STATUS  current
        DESCRIPTION
            "The value of MIB II's sysUpTime object at the
            last time the history was cleared.
            At power on, this value should contain 0.
            "
        ::= { pgSdslCellPerfCurr15MinEntry 5 }


    ----------------------------------------------------
    -- SDSL Cell Performance Previous 96               -
	-- 15 Minute Intervals Table                       -
    ----------------------------------------------------

	pgSdslCellPerf15MinIntervalTable  OBJECT-TYPE
        SYNTAX      SEQUENCE OF PgSdslCellPerf15MinIntervalEntry
        MAX-ACCESS  not-accessible
        STATUS      current
        DESCRIPTION
            "This table contains information on the Cell-SDSL Line
             performance data for the previous (0-96) 15 minute Interval"

        ::= {pgsdslCellMibObjects 9 }

    pgSdslCellPerf15MinIntervalEntry  OBJECT-TYPE
        SYNTAX      PgSdslCellPerf15MinIntervalEntry
        MAX-ACCESS  not-accessible
        STATUS      current
        DESCRIPTION
                "An Entry in pgSdslCellPerf15MinIntervalTable "
        INDEX       { ifIndex, pgSdslCellPerf15MinIntervalIndex }
        ::= { pgSdslCellPerf15MinIntervalTable 1}

     PgSdslCellPerf15MinIntervalEntry ::= SEQUENCE {
        pgSdslCellPerf15MinIntervalIndex    INTEGER,
        pgSdslCellPerf15MinIntervalLOSS     Counter32,
        pgSdslCellPerf15MinIntervalLOCD     Counter32,
        pgSdslCellPerf15MinIntervalSLOCD    Counter32
        }

    pgSdslCellPerf15MinIntervalIndex OBJECT-TYPE
        SYNTAX      INTEGER(0..96)
        MAX-ACCESS  read-only
        STATUS      current
        DESCRIPTION
                 "A number between 1 and 96, where 1 is the most
                 recently completed 15 minute interval and 96 is
                 the 15 minutes interval completed 23 hours and 45
                 minutes prior to interval 1."
        ::= { pgSdslCellPerf15MinIntervalEntry 1}

    pgSdslCellPerf15MinIntervalLOSS OBJECT-TYPE
        SYNTAX      Counter32
        MAX-ACCESS  read-only
        STATUS      current
        DESCRIPTION
                "The number of   Loss of Signal seconds , encountered
                 by an Cell SDSL interface within this 15 minutes performance
                 data collection interval"
        ::= { pgSdslCellPerf15MinIntervalEntry 2}

    pgSdslCellPerf15MinIntervalLOCD OBJECT-TYPE
        SYNTAX      Counter32
        MAX-ACCESS  read-only
        STATUS      current
        DESCRIPTION
                "The number of   Loss of Cell Delineation , encountered
                 by an Cell SDSL interface within this 15 minutes performance
                 data collection interval"
        ::= { pgSdslCellPerf15MinIntervalEntry 3 }

    pgSdslCellPerf15MinIntervalSLOCD OBJECT-TYPE
        SYNTAX      Counter32
        MAX-ACCESS  read-only
        STATUS      current
        DESCRIPTION
                "The number of severe Loss of Cell Delineation , encountered
                 by an Cell SDSL interface within this 15 minutes performance
                 data collection interval"
        ::= { pgSdslCellPerf15MinIntervalEntry 4 }

    ----------------------------------------------------
    -- SDSL Cell Performance Current  				   -
	-- 24 Hour Table                                   -
    ----------------------------------------------------

	pgSdslCellPerfCurr24hTable  OBJECT-TYPE
        SYNTAX      SEQUENCE OF PgSdslCellPerfCurr24hEntry
        MAX-ACCESS  not-accessible
        STATUS      current
        DESCRIPTION
            "This table contains information on the Cell-SDSL Line
             performance data for the current 24 hour  period"

        ::= {pgsdslCellMibObjects 10 }

    pgSdslCellPerfCurr24hEntry  OBJECT-TYPE
        SYNTAX      PgSdslCellPerfCurr24hEntry
        MAX-ACCESS  not-accessible
        STATUS      current
        DESCRIPTION
                "An Entry in pgSdslCellPerfCurr24hTable "
        INDEX       { ifIndex }
        ::= { pgSdslCellPerfCurr24hTable 1}



     PgSdslCellPerfCurr24hEntry ::= SEQUENCE {
        pgSdslCellPerfCurr24hLOSS           Counter32,
        pgSdslCellPerfCurr24hLOCD           Counter32,
        pgSdslCellPerfCurr24hSLOCD          Counter32
        }

    pgSdslCellPerfCurr24hLOSS OBJECT-TYPE
        SYNTAX      Counter32
        MAX-ACCESS  read-only
        STATUS      current
        DESCRIPTION
                "The number of  Loss of Signal seconds, encountered
                by an Cell SDSL interface within current  24
                hour performance data collection interval"
        ::= { pgSdslCellPerfCurr24hEntry 1}

    pgSdslCellPerfCurr24hLOCD OBJECT-TYPE
        SYNTAX      Counter32
        MAX-ACCESS  read-only
        STATUS      current
        DESCRIPTION
                "The number of Loss of Cell Delineation, encountered
                by an Cell SDSL interface within current  24
                hour performance data collection interval"
        ::= { pgSdslCellPerfCurr24hEntry 2}

    pgSdslCellPerfCurr24hSLOCD OBJECT-TYPE
        SYNTAX      Counter32
        MAX-ACCESS  read-only
        STATUS      current
        DESCRIPTION
                "The number of  Severe Loss of Cell Delineation, encountered
                by an Cell SDSL interface within current  24
                hour performance data collection interval"
        ::= { pgSdslCellPerfCurr24hEntry 3}

    -------------------------------------------------------
    -- SDSL Cell Performance Previous 7                   -
	-- 24 Hour Intervals Table                            -
    -------------------------------------------------------

	pgSdslCellPerf24hIntervalTable  OBJECT-TYPE
        SYNTAX      SEQUENCE OF PgSdslCellPerf24hIntervalEntry
        MAX-ACCESS  not-accessible
        STATUS      current
        DESCRIPTION
            "This table contains information on the Cell-SDSL Line
             performance data for the previous 7 24 hour Interval"

        ::= {pgsdslCellMibObjects 11 }

    pgSdslCellPerf24hIntervalEntry  OBJECT-TYPE
        SYNTAX      PgSdslCellPerf24hIntervalEntry
        MAX-ACCESS  not-accessible
        STATUS      current
        DESCRIPTION
                "An Entry in pgSdslCellPerf24hIntervalTable "
        INDEX       { ifIndex, pgSdslCellPerf24hIntervalIndex }
        ::= { pgSdslCellPerf24hIntervalTable 1}


     PgSdslCellPerf24hIntervalEntry ::= SEQUENCE {
        pgSdslCellPerf24hIntervalIndex      INTEGER,
        pgSdslCellPerf24hIntervalLOSS       Counter32,
        pgSdslCellPerf24hIntervalLOCD       Counter32,
        pgSdslCellPerf24hIntervalSLOCD      Counter32

        }

    pgSdslCellPerf24hIntervalIndex OBJECT-TYPE
        SYNTAX      INTEGER(0..7)
        MAX-ACCESS  read-only
        STATUS      current
        DESCRIPTION
                 "A number between 1 and 7, where 1 is the most
                 recently completed 24 hour interval"
        ::= { pgSdslCellPerf24hIntervalEntry 1}

    pgSdslCellPerf24hIntervalLOSS OBJECT-TYPE
        SYNTAX      Counter32
        MAX-ACCESS  read-only
        STATUS      current
        DESCRIPTION
                "The number of   Loss of Signal seconds , encountered
                 by an Cell SDSL interface within this 24 hour performance
                 data collection interval"
        ::= { pgSdslCellPerf24hIntervalEntry 2}

    pgSdslCellPerf24hIntervalLOCD OBJECT-TYPE
        SYNTAX      Counter32
        MAX-ACCESS  read-only
        STATUS      current
        DESCRIPTION
                "The number of   Loss of Cell Delineation , encountered
                 by an Cell SDSL interface within this 24 hour performance
                 data collection interval"
        ::= { pgSdslCellPerf24hIntervalEntry 3 }

    pgSdslCellPerf24hIntervalSLOCD OBJECT-TYPE
        SYNTAX      Counter32
        MAX-ACCESS  read-only
        STATUS      current
        DESCRIPTION
                "The number of severe Loss of Cell Delineation , encountered
                 by an Cell SDSL interface within this 24 hour performance
                 data collection interval"
        ::= { pgSdslCellPerf24hIntervalEntry 4 }


    ----------------------------------------------------
    -- SDSL Cell Alarm Status Table -
    ----------------------------------------------------

     pgSdslCellAlarmTable  OBJECT-TYPE
          SYNTAX      SEQUENCE OF PgSdslCellAlarmEntry
          MAX-ACCESS  not-accessible
          STATUS      current
          DESCRIPTION
              "This table provides the SDSL Cell  alarm indications."
          ::= {pgsdslCellMibObjects 12}

     pgSdslCellAlarmEntry  OBJECT-TYPE
          SYNTAX      PgSdslCellAlarmEntry
          MAX-ACCESS  not-accessible
          STATUS      current
          DESCRIPTION
              "Entries of the SDSL Cell alarm table "
          INDEX       {ifIndex}
          ::= {pgSdslCellAlarmTable 1}

     PgSdslCellAlarmEntry ::= SEQUENCE {
        pgSdslCellCrossThreshLOSS   	INTEGER,
        pgSdslCellCrossThreshLOCD       INTEGER,
        pgSdslCellCrossThreshSLOCD      INTEGER,
        pgSdslCellCrossThreshSNR        INTEGER,
		pgSdslCellHardwareCause         INTEGER,
		pgSdslCellAlarmLastChanged		TimeStamp
      }

      pgSdslCellCrossThreshLOSS OBJECT-TYPE
           SYNTAX      INTEGER {
			inactive (1),
			active   (2)
		   }
           MAX-ACCESS  read-only
           STATUS      current
           DESCRIPTION
               "When active the LOSS Threshold was crossed during the previous
			   15 minute interval and the condition has not yet been cleared."
           ::= {pgSdslCellAlarmEntry 1}

      pgSdslCellCrossThreshLOCD OBJECT-TYPE
           SYNTAX      INTEGER {
			inactive (1),
			active   (2)
		   }
           MAX-ACCESS  read-only
           STATUS      current
           DESCRIPTION
               "When active the LOCD Threshold was crossed during the previous
			   15 minute interval and the condition has not yet been cleared."
           ::= {pgSdslCellAlarmEntry 2}

      pgSdslCellCrossThreshSLOCD OBJECT-TYPE
           SYNTAX      INTEGER {
			inactive (1),
			active   (2)
		   }
           MAX-ACCESS  read-only
           STATUS      current
           DESCRIPTION
               "When active the SLOCD Threshold was crossed during the previous
			   15 minute interval and the condition has not yet been cleared."
           ::= {pgSdslCellAlarmEntry 3}

      pgSdslCellCrossThreshSNR OBJECT-TYPE
           SYNTAX      INTEGER {
			inactive (1),
			active   (2)
		   }
           MAX-ACCESS  read-only
           STATUS      current
           DESCRIPTION
               "When active the current SNR is below the SNR Threshold."
           ::= {pgSdslCellAlarmEntry 4}

      pgSdslCellHardwareCause OBJECT-TYPE
           SYNTAX      INTEGER {
			ok       (1),
			xcvrfail (2),
			otherfail(3)
		   }
           MAX-ACCESS  read-only
           STATUS      current
           DESCRIPTION
               "This MIB object is used to communicate a port based hardware
			   failure.
			   1 = no failure detected
			   2 = transceiver failure detected.  e.g. failure to communicate
			       with the transceiver.
			   3 = other port based hardware failure
			   "
           ::= {pgSdslCellAlarmEntry 5}

     pgSdslCellAlarmLastChanged OBJECT-TYPE
          SYNTAX  TimeStamp
          MAX-ACCESS  read-only
          STATUS  current
          DESCRIPTION
                 "The value of MIB II's sysUpTime object at the
                 last time the alarm status changed.
                 At power on, this value should contain 0.
                 "
          ::= { pgSdslCellAlarmEntry 6 }


	---------------------------------------
    -- SDSL CELL TRAPS                    -
	---------------------------------------

pgSdslCellTraps OBJECT IDENTIFIER ::= { pgsdslCellMIB 2 }
pgSdslCellTrap  OBJECT IDENTIFIER ::= { pgSdslCellTraps 0 }



pgSdslCellThreshLOSSTrap NOTIFICATION-TYPE
    OBJECTS      { ifIndex,pgSdslCellCrossThreshLOSS, pgSdslCellAlarmLastChanged}
    STATUS       current
    DESCRIPTION
        "Loss of Signal 15-minute interval threshold exceeded"
    ::= { pgSdslCellTrap 1 }

pgSdslCellThreshLOCDTrap NOTIFICATION-TYPE
    OBJECTS      { ifIndex,pgSdslCellCrossThreshLOCD, pgSdslCellAlarmLastChanged}
    STATUS       current
    DESCRIPTION
        "Loss of Cell Delineation  15-minute interval threshold exceeded"
    ::= { pgSdslCellTrap 2 }

pgSdslCellThreshSLOCDTrap NOTIFICATION-TYPE
    OBJECTS      { ifIndex,pgSdslCellCrossThreshSLOCD, pgSdslCellAlarmLastChanged}
    STATUS       current
    DESCRIPTION
        "Severe Loss of Cell Delination 15-minute interval threshold exceeded"
    ::= { pgSdslCellTrap 3 }

pgSdslCellThreshSNRTrap NOTIFICATION-TYPE
    OBJECTS      { ifIndex,pgSdslCellCrossThreshSNR, pgSdslCellAlarmLastChanged}
    STATUS       current
    DESCRIPTION
        "SNR 15-minute interval threshold exceeded"
    ::= { pgSdslCellTrap 4 }

pgSdslCellHardwareFaultTrap NOTIFICATION-TYPE
    OBJECTS      { ifIndex,pgSdslCellHardwareCause, pgSdslCellAlarmLastChanged }
    STATUS       current
    DESCRIPTION
        "A hardware fault on this ifIndex has occurred.  The pgSdslCellHardware Cause provides
		a description of the type of the failure."
    ::= { pgSdslCellTrap 5 }


END
