-- extracted from draft-otani-ccamp-gmpls-ospf-mib-02.txt
-- at Tue Mar  7 06:10:55 2006

   OSPF-TE-DRAFT00-MIB DEFINITIONS ::= BEGIN  
    
   IMPORTS 
      MODULE-IDENTITY, OBJECT-TYPE, Integer32, Unsigned32 
        FROM SNMPv2-SMI                            --[RFC2578] 
      MODULE-COMPLIANCE, OBJECT-GROUP 
        FROM SNMPv2-CONF                           --[RFC2580] 
      InetAddressType, InetAddress 
        FROM INET-ADDRESS-MIB 
      transmission       
        FROM SNMPv2-SMI                            --[RFC2578] 
      ospfLsdbLsid, ospfRouterId  
        FROM OSPF-MIB;                             --[OSPFMIB UPDATE] 
    
   ospfTeMIB MODULE-IDENTITY 
      LAST-UPDATED "200510240000Z"  -- 04 July 2005 00:00:00 GMT 
      ORGANIZATION "IETF CCAMP Working Group." 
      CONTACT-INFO 
         "          Tomohiro Otani 
                     otani@kddilabs.jp 
    
                     Masanori Miyazawa 
                     ma-miyazawa@kddilabs.jp 
    
                     Thomas D. Nadeau 
                     tnadeau@cisco.com 
    
                     Kenji Kumaki 
                     ke-kumaki@kddi.com 
    
                     Comments and discussion to ccamp@ietf.org" 
      DESCRIPTION 
           "This MIB contains managed object definitions for  
            extensions to the OSPF MIB in support of Traffic 
            Engienering (TE). 
    
           Copyright (C) The Internet Society (2006).  This 
           version of this MIB module is part of RFCXXX; see 
           the RFC itself for full legal notices." 
     -- Revision history. 
      REVISION 
         "200506041200Z"  -- 04 July 2005 12:00:00 GMT 
      DESCRIPTION 
        "Initial version. Published as RFC xxxx." -- RFC-editor pls fill 
        in xxx" 
      ::= { transmission 9988 } -- assigned by IANA, see section 7.1 for  
                                -- details 
    
   -- Textual Conventions. 
    
   -- Top level components of this MIB. 
    
   ospfTeNotifications OBJECT IDENTIFIER ::= { ospfTeMIB 0 } 
   ospfTeObjects       OBJECT IDENTIFIER ::= { ospfTeMIB 1 } 
     
   T. Otani et al.          Expires Sept. 30, 2006                   5 
   Internet Drafts draft-otani-ccamp-gmpls-ospf-mib-02.txt  March 2006 
    
   ospfTeScalars       OBJECT IDENTIFIER ::= { ospfTeObjects 1 } 
   ospfTeTables        OBJECT IDENTIFIER ::= { ospfTeObjects 2 } 
   ospfTeConformance   OBJECT IDENTIFIER ::= { ospfTeMIB 2 } 
    
   -- MIB Definitions 
    
   -- 
   -- Scalar Objects 
   -- 
    
    
   -- 
   --  OSPF TE LSDB Table 
   -- 
    
   ospfTeLsdbTable OBJECT-TYPE  
   SYNTAX       SEQUENCE OF OspfTeLsdbEntry  
   MAX-ACCESS   not-accessible  
   STATUS       current  
   DESCRIPTION  
        "This table indicates multiple sub-TLVs information in opaque 
   LSA which have been supported by [OSPF-TE].  " 
   ::= { ospfTeTables 1 }  
    
   ospfTeLsdbEntry OBJECT-TYPE  
      SYNTAX       OspfTeLsdbEntry  
      MAX-ACCESS   not-accessible  
      STATUS       current  
      DESCRIPTION  
      "This entry contains each sub-TLVs information commonly utilized 
   in both MPLS and GMPLS"  
      INDEX { ospfLsdbLsid, ospflsdbRouterId }  
   ::= { ospfTeLsdbTable 1 }  
    
   OspfTeLsdbEntry ::= SEQUENCE {  
      ospfTeLinkType                  INTEGER, 
      ospfTeLinkIdAddr                InetAddress, 
      ospfTeLinkIdAddrType            InetAddressType, 
      ospfTeMetric                    Integer32, 
      ospfTeMaxBandwidth              Unsigned32, 
      ospfTeMaxReservableBandwidth    Unsigned32, 
      ospfTeUnreservedBandwidthPri0   Unsigned32, 
      ospfTeUnreservedBandwidthPri1   Unsigned32, 
      ospfTeUnreservedBandwidthPri2   Unsigned32, 
      ospfTeUnreservedBandwidthPri3   Unsigned32, 
      ospfTeUnreservedBandwidthPri4   Unsigned32, 
      ospfTeUnreservedBandwidthPri5   Unsigned32, 
      ospfTeUnreservedBandwidthPri6   Unsigned32, 
      ospfTeUnreservedBandwidthPri7   Unsigned32, 
      ospfTeAdministrativeGroup       Integer32, 
      ospfTeLocalId                   Integer32, 
      ospfTeRemoteId                  Integer32, 
      ospfTeLinkProtectionType        INTEGER, 
   }  
     
   T. Otani et al.          Expires Sept. 30, 2006                   6 
   Internet Drafts draft-otani-ccamp-gmpls-ospf-mib-02.txt  March 2006 
    
    
   ospfTeLinkType OBJECT-TYPE  
       SYNTAX    INTEGER {  
                           pointToPoint (1),  
                           multiAccess (2) 
                        } 
       MAX-ACCESS   read-only  
       STATUS       current  
       DESCRIPTION  
           "This indicates the type of the link such as point-to-point 
   or multi-access"  
   ::= { ospfTeLsdbEntry 1 }  
    
   ospfTeLinkIdAddr OBJECT-TYPE  
       SYNTAX       InetAddress  
       MAX-ACCESS   read-only  
       STATUS       current  
       DESCRIPTION  
               "This indicates the Router ID of the neighbor in the case 
   of point-to-point links.  This also indicates the interface address 
   of the designated router in the case of multi-access links."  
   ::= { ospfTeLsdbEntry 2 }  
    
   ospfTeLinkIdAddrType OBJECT-TYPE  
       SYNTAX       InetAddressType 
       MAX-ACCESS   read-only  
       STATUS       current  
       DESCRIPTION  
               "This object indicates the type of TE link ID address."  
   ::= { ospfTeLsdbEntry 3 }  
    
   ospfTeMetric OBJECT-TYPE  
       SYNTAX       Integer32  
       MAX-ACCESS   read-only  
       STATUS       current  
       DESCRIPTION  
           "This indicates the traffic engineering metric value of the 
   TE link."  
   ::= { ospfTeLsdbEntry 4 }  
    
   ospfTeMaxBandwidth OBJECT-TYPE  
       SYNTAX       Unsigned32  
       MAX-ACCESS   read-only  
       STATUS       current  
       DESCRIPTION  
           "This indicates the maximum bandwidth that 
      can be used on this link in this direction"  
   ::= { ospfTeLsdbEntry 5 }  
    
   ospfTeMaxReservableBandwidth OBJECT-TYPE  
       SYNTAX       Unsigned32  
       MAX-ACCESS   read-only  
       STATUS       current  
       DESCRIPTION  
     
   T. Otani et al.          Expires Sept. 30, 2006                   7 
   Internet Drafts draft-otani-ccamp-gmpls-ospf-mib-02.txt  March 2006 
    
           "This indicates the maximum bandwidth that may be reserved on 
   this link in this direction"  
   ::= { ospfTeLsdbEntry 6 }  
    
   ospfTeUnreservedBandwidthPri0 OBJECT-TYPE  
       SYNTAX       Unsigned32  
       MAX-ACCESS   read-only  
       STATUS       current  
       DESCRIPTION  
           "This indicates the amount of bandwidth not yet reserved at 
   the priority 0"  
   ::= { ospfTeLsdbEntry 7 }  
    
   ospfTeUnreservedBandwidthPri1 OBJECT-TYPE  
       SYNTAX       Unsigned32  
       MAX-ACCESS   read-only  
       STATUS       current  
       DESCRIPTION  
           "This indicates the amount of bandwidth not yet reserved at 
   the priority 1"  
   ::= { ospfTeLsdbEntry 8 } 
    
   ospfTeUnreservedBandwidthPri2 OBJECT-TYPE  
       SYNTAX       Unsigned32  
       MAX-ACCESS   read-only  
       STATUS       current  
       DESCRIPTION  
           "This indicates the amount of bandwidth not yet reserved at 
   the priority 2"  
   ::= { ospfTeLsdbEntry 9 } 
    
   ospfTeUnreservedBandwidthPri3 OBJECT-TYPE  
       SYNTAX       Unsigned32  
       MAX-ACCESS   read-only  
       STATUS       current  
       DESCRIPTION 
           "This indicates the amount of bandwidth not yet reserved at 
   the priority 3"  
   ::= { ospfTeLsdbEntry 10 } 
    
   ospfTeUnreservedBandwidthPri4 OBJECT-TYPE  
       SYNTAX       Unsigned32  
       MAX-ACCESS   read-only  
       STATUS       current  
       DESCRIPTION  
           "This indicates the amount of bandwidth not yet reserved at 
   the priority 4"  
   ::= { ospfTeLsdbEntry 11 } 
    
   ospfTeUnreservedBandwidthPri5 OBJECT-TYPE  
       SYNTAX       Unsigned32  
       MAX-ACCESS   read-only  
       STATUS       current  
       DESCRIPTION  
     
   T. Otani et al.          Expires Sept. 30, 2006                   8 
   Internet Drafts draft-otani-ccamp-gmpls-ospf-mib-02.txt  March 2006 
    
           "This indicates the amount of bandwidth not yet reserved at 
   the priority 5"  
   ::= { ospfTeLsdbEntry 12 } 
    
   ospfTeUnreservedBandwidthPri6 OBJECT-TYPE  
       SYNTAX       Unsigned32  
       MAX-ACCESS   read-only  
       STATUS       current  
       DESCRIPTION  
           "This indicates the amount of bandwidth not yet reserved at 
   the priority 6"  
   ::= { ospfTeLsdbEntry 13 } 
    
   ospfTeUnreservedBandwidthPri7 OBJECT-TYPE  
       SYNTAX       Unsigned32  
       MAX-ACCESS   read-only  
       STATUS       current  
       DESCRIPTION  
           "This indicates the amount of bandwidth not yet reserved at 
   the priority 7"  
   ::= { ospfTeLsdbEntry 14 } 
    
   ospfTeAdministrativeGroup OBJECT-TYPE  
       SYNTAX       Integer32 
       MAX-ACCESS   read-only  
       STATUS       current  
       DESCRIPTION  
           "This indicates the Administrative Group which the link 
   belong to.  Since the value is a bit mask, the link can belong to 
   multiple groups.  This is also called Resource Class/Color."  
   ::= { ospfTeLsdbEntry 15 } 
    
   ospfTeLocalId OBJECT-TYPE  
       SYNTAX       Unsigned32  
       MAX-ACCESS   read-only  
       STATUS       current  
       DESCRIPTION  
           "This indicates the Link local identifier of an unnumbered 
   link." 
   ::= { ospfTeLsdbEntry 16 } 
    
   ospfTeRemoteId OBJECT-TYPE  
       SYNTAX       Unsigned32  
       MAX-ACCESS   read-only  
       STATUS       current  
       DESCRIPTION  
           " This indicates the Link remote identifier of an unnumbered 
   link."  
   ::= { ospfTeLsdbEntry 17 } 
    
   ospfTeLinkProtectionType OBJECT-TYPE 
       SYNTAX  INTEGER { 
               extraTraffic(0), 
               unprotected(1), 
     
   T. Otani et al.          Expires Sept. 30, 2006                   9 
   Internet Drafts draft-otani-ccamp-gmpls-ospf-mib-02.txt  March 2006 
    
               shared (2), 
               dedicatedOneToOne (3), 
               dedicatedOnePlusOne(4), 
               enhanced(5) 
       } 
       MAX-ACCESS read-only 
       STATUS  current 
       DESCRIPTION 
           "This object indicates the protection type of the TE link" 
   ::= { ospfTeLsdbEntry 18 } 
 
 
   -- 
   --  OSPF TE Local Interface IP Address Table 
   -- 
    
   ospfTeLocalIntAddrTable OBJECT-TYPE 
       SYNTAX       SEQUENCE OF OspfTeLocalIntAddrEntry  
       MAX-ACCESS   not-accessible  
       STATUS       current  
       DESCRIPTION  
           "This table contains the IP address information of a local TE 
   link."  
   ::= { ospfTeTables 2 }       
    
   ospfTeLocalIntAddrEntry OBJECT-TYPE  
       SYNTAX       OspfTeLocalIntAddrEntry  
       MAX-ACCESS   not-accessible  
       STATUS       current  
       DESCRIPTION  
           "This entry contains the IP address information of the local 
   TE link."  
       INDEX { ospfLsdbLsid, ospflsdbRouterId, ospfTeLocalIntAddrIndex }  
   ::= { ospfTeLocalIntAddrTable 1 }  
    
   OspfTeLocalIntAddrEntry ::= SEQUENCE { 
           ospfTeLocalIntAddrIndex Unsigned32, 
           ospfTeLocalIntAddr      InetAddress, 
           ospfTeLocalIntAddrType  InetAddressType 
       }  
    
   ospfTeLocalIntAddrIndex OBJECT-TYPE  
       SYNTAX       Unsigned32 
       MAX-ACCESS   not-accessible  
       STATUS       current  
       DESCRIPTION  
       "This indicates the index to identify multiple local TE links"  
   ::= { ospfTeLocalIntAddrEntry 1 } 
    
   ospfTeLocalIntAddr OBJECT-TYPE  
       SYNTAX       InetAddress  
       MAX-ACCESS   read-only  
       STATUS       current  
       DESCRIPTION  
     
   T. Otani et al.          Expires Sept. 30, 2006                  10 
   Internet Drafts draft-otani-ccamp-gmpls-ospf-mib-02.txt  March 2006 
    
       "This object indicates the address of the local TE link."  
   ::= { ospfTeLocalIntAddrEntry 2 } 
    
   ospfTeLocalIntAddrType OBJECT-TYPE  
       SYNTAX       InetAddressType  
       MAX-ACCESS   read-only  
       STATUS       current  
       DESCRIPTION  
       "This object indicates the type of local TE link address."  
   ::= { ospfTeLocalIntAddrEntry 3 } 
    
    
   -- 
   --  OSPF TE Remote Interface IP Address Table 
   -- 
    
   ospfTeRemoteIntAddrTable OBJECT-TYPE 
       SYNTAX       SEQUENCE OF OspfTeRemoteIntAddrEntry  
       MAX-ACCESS   not-accessible  
       STATUS       current  
       DESCRIPTION  
           "This table contains the IP address information of a remote 
   TE link."  
   ::= { ospfTeTables 3 }       
    
   ospfTeRemoteIntAddrEntry OBJECT-TYPE  
       SYNTAX       OspfTeRemoteIntAddrEntry  
       MAX-ACCESS   not-accessible  
       STATUS       current  
       DESCRIPTION  
           "This entry contains the IP address information of the remote 
   TE link."  
   INDEX { ospfLsdbLsid, ospflsdbRouterId, ospfTeRemoteIntAddrIndex }  
       ::= { ospfTeRemoteIntAddrTable 1 }  
    
   OspfTeRemoteIntAddrEntry ::= SEQUENCE {  
       ospfTeRemoteIntAddrIndex Unsigned32, 
       ospfTeRemoteIntAddr      InetAddress, 
       ospfTeRemoteIntAddrType  InetAddressType 
   }  
    
   ospfTeRemoteIntAddrIndex OBJECT-TYPE  
       SYNTAX       Unsigned32 
       MAX-ACCESS   not-accessible 
       STATUS       current  
       DESCRIPTION  
           "This indicates the index to identify multiple remote TE 
   links."  
   ::= { ospfTeRemoteIntAddrEntry 1 } 
    
   ospfTeRemoteIntAddr OBJECT-TYPE  
       SYNTAX       InetAddress 
       MAX-ACCESS   read-only 
       STATUS       current  
     
   T. Otani et al.          Expires Sept. 30, 2006                  11 
   Internet Drafts draft-otani-ccamp-gmpls-ospf-mib-02.txt  March 2006 
    
       DESCRIPTION  
           "This object indicates the address of the remote TE link."  
   ::= { ospfTeRemoteIntAddrEntry 2 } 
    
   ospfTeRemoteIntAddrType OBJECT-TYPE  
       SYNTAX       InetAddressType 
       MAX-ACCESS   read-only 
       STATUS       current  
       DESCRIPTION  
           "This object indicates the type of the remote TE link 
   address."  
   ::= { ospfTeRemoteIntAddrEntry 3 } 
    
    
   -- 
   --  OSPF TE Switch Capable Table 
   -- 
    
   ospfTeSwCapTable OBJECT-TYPE  
       SYNTAX       SEQUENCE OF OspfTeSwCapEntry  
       MAX-ACCESS   not-accessible  
       STATUS       current  
       DESCRIPTION  
           "This table contains the GMPLS OSPF TE switching capability 
   information." 
   ::= { ospfTeTables 4 }  
    
   ospfTeSwCapEntry OBJECT-TYPE  
       SYNTAX       OspfTeSwCapEntry  
       MAX-ACCESS   not-accessible  
       STATUS       current  
       DESCRIPTION  
           "This entry relates each TE link with its GMPLS TE switching 
   capability information. IF the MIB deals with only OSPF-TE 
   information, the value of each object related with GMPLS TE 
   extensions should be null." 
       INDEX { ospfLsdbLsid, ospflsdbRouterId, ospfTeSwCapIndex }  
   ::= { ospfTeSwCapTable 1 }  
      
   OspfTeSwCapEntry ::= SEQUENCE { 
       ospfTeSwCapIndex            Unsigned32, 
       ospfTeSwitchingType         INTEGER, 
       ospfTeEncoding              INTEGER, 
       ospfTeMaxLspBandwidthPri0   Unsigned32, 
       ospfTeMaxLspBandwidthPri1   Unsigned32, 
       ospfTeMaxLspBandwidthPri2   Unsigned32, 
       ospfTeMaxLspBandwidthPri3   Unsigned32, 
       ospfTeMaxLspBandwidthPri4   Unsigned32, 
       ospfTeMaxLspBandwidthPri5   Unsigned32, 
       ospfTeMaxLspBandwidthPri6   Unsigned32, 
       ospfTeMaxLspBandwidthPri7   Unsigned32, 
       ospfTeMinLspBandwidth       Unsigned32, 
       ospfTeIntMtu                Integer32, 
       ospfTeIndication            INTEGER 
     
   T. Otani et al.          Expires Sept. 30, 2006                  12 
   Internet Drafts draft-otani-ccamp-gmpls-ospf-mib-02.txt  March 2006 
    
   }  
    
   ospfTeSwCapIndex OBJECT-TYPE  
       SYNTAX       Unsigned32 
       MAX-ACCESS   not-accessible  
       STATUS       current  
       DESCRIPTION  
           "This index is utilized to identify multiple switching 
   functions on a local or remote TE link."  
   ::= { ospfTeSwCapEntry 1 } 
    
   ospfTeSwitchingType OBJECT-TYPE 
      SYNTAX  INTEGER { 
                 unknown (0), 
                 psc1    (1), 
                 psc2    (2), 
                 psc3    (3), 
                 psc4    (4), 
                 l2sc   (51), 
                 tdm   (100), 
                 lsc   (150), 
                 fsc   (200) 
           } 
           MAX-ACCESS read-only 
           STATUS  current 
           DESCRIPTION 
               "This object indicates the GMPLS switching capability 
   assigned to the TE link." 
           ::= { ospfTeSwCapEntry 2 } 
    
   ospfTeEncoding OBJECT-TYPE 
           SYNTAX  INTEGER { 
                 packet         (1), 
                 ethernet       (2), 
                 ansiEtsiPdh    (3), 
                 sdhSonet       (5), 
                 digitalWrapper (7), 
                 lambda         (8), 
                 fiber          (9), 
                 fiberChannel  (11) 
               } 
       MAX-ACCESS read-only 
       STATUS  current 
       DESCRIPTION 
           "This object indicates the GMPLS encoding type assigned to 
   the TE link." 
   ::= { ospfTeSwCapEntry 3 } 
    
   ospfTeMaxLspBandwidthPri0 OBJECT-TYPE 
       SYNTAX       Unsigned32 
       MAX-ACCESS   read-only 
       STATUS       current 
       DESCRIPTION 
     
   T. Otani et al.          Expires Sept. 30, 2006                  13 
   Internet Drafts draft-otani-ccamp-gmpls-ospf-mib-02.txt  March 2006 
    
           "This object indicates the maximum bandwidth of the TE link 
   at the priority 0 for GMPLS LSP creation." 
   ::= { ospfTeSwCapEntry 4 } 
    
   ospfTeMaxLspBandwidthPri1 OBJECT-TYPE 
       SYNTAX       Unsigned32 
       MAX-ACCESS   read-only 
       STATUS       current 
       DESCRIPTION 
           "This object indicates the maximum bandwidth of the TE link 
   at the priority 1 for GMPLS LSP creation." 
   ::= { ospfTeSwCapEntry 5 } 
    
   ospfTeMaxLspBandwidthPri2  OBJECT-TYPE 
       SYNTAX       Unsigned32 
       MAX-ACCESS   read-only 
       STATUS       current 
       DESCRIPTION 
           "This object indicates the maximum bandwidth of the TE link 
   at the priority 2 for GMPLS LSP creation." 
   ::= { ospfTeSwCapEntry 6 } 
    
   ospfTeMaxLspBandwidthPri3 OBJECT-TYPE 
       SYNTAX       Unsigned32 
       MAX-ACCESS   read-only 
       STATUS       current 
       DESCRIPTION 
           "This object indicates the maximum bandwidth of the TE link 
   at the priority 3 for GMPLS LSP creation." 
   ::= { ospfTeSwCapEntry 7 } 
    
   ospfTeMaxLspBandwidthPri4 OBJECT-TYPE 
       SYNTAX       Unsigned32 
       MAX-ACCESS   read-only 
       STATUS       current 
       DESCRIPTION 
           "This object indicates the maximum bandwidth of the TE link 
   at the priority 4 for GMPLS LSP creation." 
   ::= { ospfTeSwCapEntry 8 } 
    
   ospfTeMaxLspBandwidthPri5  OBJECT-TYPE 
       SYNTAX       Unsigned32 
       MAX-ACCESS   read-only 
       STATUS       current 
       DESCRIPTION 
           "This object indicates the maximum bandwidth of the TE link 
   at the priority 5 for GMPLS LSP creation." 
   ::= { ospfTeSwCapEntry 9 } 
        
   ospfTeMaxLspBandwidthPri6 OBJECT-TYPE 
       SYNTAX       Unsigned32 
       MAX-ACCESS   read-only 
       STATUS       current 
       DESCRIPTION 
     
   T. Otani et al.          Expires Sept. 30, 2006                  14 
   Internet Drafts draft-otani-ccamp-gmpls-ospf-mib-02.txt  March 2006 
    
           "This object indicates the maximum bandwidth of the TE link 
   at the priority 6 for GMPLS LSP creation." 
   ::= { ospfTeSwCapEntry 10 } 
    
   ospfTeMaxLspBandwidthPri7 OBJECT-TYPE 
       SYNTAX       Unsigned32 
       MAX-ACCESS   read-only 
       STATUS       current 
       DESCRIPTION 
           "This object indicates the maximum bandwidth of the TE link 
   at the priority 7 for GMPLS LSP creation." 
   ::= { ospfTeSwCapEntry 11 } 
    
   ospfTeLspMinBandwidth OBJECT-TYPE 
       SYNTAX       Unsigned32 
       MAX-ACCESS   read-only 
       STATUS       current 
       DESCRIPTION 
           "This object indicates the minimum bandwidth of the TE link 
   for GMPLS LSP creation if the switching capability field is TDM, PSC-
   1, PSC-2, PSC-3, or PSC-4." 
   ::= { ospfTeSwCapEntry 12 } 
    
   ospfTeIntMtu OBJECT-TYPE 
       SYNTAX       Integer32 
       MAX-ACCESS   read-write 
       STATUS       current 
       DESCRIPTION 
           "This object indicates the MTU of the local or remote TE 
   link" 
   ::= { ospfTeSwCapEntry 13 } 
    
   ospfTeIndication OBJECT-TYPE 
       SYNTAX       INTEGER { 
                      standard (0), 
                      arbitrary (1) 
                      } 
       MAX-ACCESS   read-only 
       STATUS       current 
       DESCRIPTION 
           "This object indicates whether the interface supports 
   Standard or Arbitrary SONET/SDH." 
   ::= { ospfTeSwCapEntry 14 } 
    
   -- 
   --  OSPF TE SRLG Table 
   -- 
    
   ospfTeSrlgTable OBJECT-TYPE 
       SYNTAX       SEQUENCE OF OspfTeSrlgEntry  
       MAX-ACCESS   not-accessible  
       STATUS       current  
       DESCRIPTION  
           "This table contains the SRLG information of the TE link."  
     
   T. Otani et al.          Expires Sept. 30, 2006                  15 
   Internet Drafts draft-otani-ccamp-gmpls-ospf-mib-02.txt  March 2006 
    
   ::= { ospfTeTables 5 }       
    
   ospfTeSrlgEntry OBJECT-TYPE  
       SYNTAX       OspfTeSrlgEntry  
       MAX-ACCESS   not-accessible  
       STATUS       current  
       DESCRIPTION  
           "This entry relates each TE link with its SRLG information."  
       INDEX { ospfLsdbLsid, ospflsdbRouterId, ospfTeSrlgIndex }  
   ::= { ospfTeSrlgTable 1 }  
    
   OspfTeSrlgEntry ::= SEQUENCE { 
       ospfTeSrlgIndex Unsigned32 
       ospfTeSrlg      Integer32 
       }  
    
   ospfTeSrlgIndex OBJECT-TYPE  
       SYNTAX       Unsigned32 
       MAX-ACCESS   not-accessible  
       STATUS       current  
       DESCRIPTION  
           "This index is utilized to identify multiple SRLG values on a 
   local or remote TE link."  
   ::= { ospfTeLsdbEntry 1 } 
    
   ospfTeSrlg OBJECT-TYPE  
       SYNTAX       Integer32  
       MAX-ACCESS   read-only  
       STATUS       current  
       DESCRIPTION  
           "This object indicate the SRLG value assigned to a local or 
   remote TE link"  
   ::= { ospfTeSrlgEntry 2 } 
    
   -- Conformance Statement 
   ospfTeGroups 
         OBJECT IDENTIFIER ::= { ospfTeConformance 1 } 
    
   ospfTeCompliances 
         OBJECT IDENTIFIER ::= { ospfTeConformance 2 } 
    
   -- Module Compliance 
    
   ospfTeModuleFullCompliance MODULE-COMPLIANCE 
         STATUS current 
         DESCRIPTION 
            "Compliance statement for agents provides full support  
             for the OSPF-TE MIB" 
         MODULE -- this module 
            MANDATORY-GROUPS    { ospfTeMainGroup 
                                } 
    
      ::= { ospfTeCompliances 1 } 
    
     
   T. Otani et al.          Expires Sept. 30, 2006                  16 
   Internet Drafts draft-otani-ccamp-gmpls-ospf-mib-02.txt  March 2006 
    
   -- 
   -- ReadOnly Compliance 
   -- 
    
   ospfTeModuleReadOnlyCompliance MODULE-COMPLIANCE 
         STATUS current 
         DESCRIPTION  
           "Compliance requirement for implementations only provide 
           read-only support for OSPF-TE. Such devices can then be 
           monitored but cannot be configured using this MIB module. 
           " 
         MODULE -- this module 
            MANDATORY-GROUPS    { ospfTeMainGroup 
                                } 
    
      ::= { ospfTeCompliances 2 } 
    
    
      -- Units of conformance. 
      ospfTeMainGroup OBJECT-GROUP 
         OBJECTS {  
               ospfTeLinkType                  , 
               ospfTeLinkIdAddr                , 
               ospfTeLinkIdAddrType            , 
               ospfTeMetric                    , 
               ospfTeMaxBandwidth              , 
               ospfTeMaxReservableBandwidth    , 
               ospfTeUnreservedBandwidthPri0   , 
               ospfTeUnreservedBandwidthPri1   , 
               ospfTeUnreservedBandwidthPri2   , 
               ospfTeUnreservedBandwidthPri3   , 
               ospfTeUnreservedBandwidthPri4   , 
               ospfTeUnreservedBandwidthPri5   , 
               ospfTeUnreservedBandwidthPri6   , 
               ospfTeUnreservedBandwidthPri7   , 
               ospfTeAdministrativeGroup       , 
               ospfTeLocalId                   , 
               ospfTeRemoteId                  , 
               ospfTeLinkProtectionType        , 
               ospfTeLocalIntAddrIndex         , 
               ospfTeLocalIntAddr              , 
               ospfTeLocalIntAddrType          , 
               ospfTeRemoteIntAddrIndex        , 
               ospfTeRemoteIntAddr             , 
               ospfTeRemoteIntAddrType         , 
               ospfTeSwCapIndex                , 
               ospfTeSwitchingType             , 
               ospfTeEncoding                  , 
               ospfTeMaxLspBandwidthPri0       , 
               ospfTeMaxLspBandwidthPri1       , 
               ospfTeMaxLspBandwidthPri2       , 
               ospfTeMaxLspBandwidthPri3       , 
               ospfTeMaxLspBandwidthPri4       , 
               ospfTeMaxLspBandwidthPri5       , 
     
   T. Otani et al.          Expires Sept. 30, 2006                  17 
   Internet Drafts draft-otani-ccamp-gmpls-ospf-mib-02.txt  March 2006 
    
               ospfTeMaxLspBandwidthPri6       , 
               ospfTeMaxLspBandwidthPri7       , 
               ospfTeIntMtu                    , 
               ospfTeIndication                , 
               ospfTeSrlgIndex                 , 
               ospfTeSrlg 
              } 
         STATUS  current 
         DESCRIPTION 
                "Collection of objects for OSPF-TE management" 
       ::= { ospfTeGroups 1 } 
    
   END 

--     
--    "Copyright (C) The Internet Society (2006).  This document is subject 
--    to the rights, licenses and restrictions contained in BCP 78, and 
--    except as set forth therein, the authors retain all their rights." 
--     
--    "This document and the information contained herein are provided on 
--    an "AS IS" basis and THE CONTRIBUTOR, THE ORGANIZATION HE/SHE 
--    REPRESENTS OR IS SPONSORED BY (IF ANY), THE INTERNET SOCIETY AND THE 
--    INTERNET ENGINEERING TASK FORCE DISCLAIM ALL WARRANTIES, EXPRESS OR 
--    IMPLIED, INCLUDING BUT NOT LIMITED TO ANY WARRANTY THAT THE USE OF 
--      
--    T. Otani et al.          Expires Sept. 30, 2006                  20 
--    Internet Drafts draft-otani-ccamp-gmpls-ospf-mib-02.txt  March 2006 
--     
--    THE INFORMATION HEREIN WILL NOT INFRINGE ANY RIGHTS OR ANY IMPLIED 
--    WARRANTIES OF MERCHANTABILITY OR FITNESS FOR A PARTICULAR PURPOSE." 
--      
--    T. Otani et al.          Expires Sept. 30, 2006                  21
