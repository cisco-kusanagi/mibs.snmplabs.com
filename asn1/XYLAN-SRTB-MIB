XYLAN-SRTB-MIB DEFINITIONS ::= BEGIN

	--  Revision: 1.00
	--  Date: March 22, 1999

	--  Alcatel Internetworking, Inc.

	--  This module provides authoritative definitions for Alcatel Internetworking,
	--  Inc. enterprise-specific Source Route Transparent Bridging MIB.

	--  This module will be extended, as needed.

	--  Alcatel Internetworking, Inc. reserves the right to make changes in 
	--  specification and other information contained in this document 
	--  without prior notice.  The reader should consult Alcatel Internetworking,
	--  Inc. to determine whether any such changes have been made.
	--  Current MIBs are availible from the following URLs:
	--		ftp://ftp.ind.alcatel.com/pub/products/mibs
	--		http://www.ind.alcatel.com

	--  In no event shall Alcatel Internetworking, Inc. be liable for any incidental, 
	--  indirect, special, or consequential damages whatsoever (including 
	--  but not limited to lost profits) arising out of or related to this
	--  document or the information contained in it, even if Alcatel Internetworking,
	--  Inc. has been advised of, known, or should have known, the 
	--  possibility of such damages.

	--  Alcatel Internetworking, Inc. grants vendors, end-users, and other interested
	--  parties a non-exclusive license to use this Specification in connection
	--  with the management of Alcatel Internetworking, Inc. products.

	--  Copyright (C) 1994, Alcatel Internetworking, Inc. All Rights Reserved.

	IMPORTS
		OBJECT-TYPE
			FROM RFC-1212
		MacAddress
			FROM BRIDGE-MIB
		xylanSrtbArch
			FROM XYLAN-BASE-MIB
			;

	--  This MIB module uses the extended OBJECT-TYPE macro as defined in
	--  RFC 1212 (but known in the epilog files under RFC1213-SMI...)


	--  groups within the xylanSrtbArch mib

	xylanSRTB		OBJECT IDENTIFIER ::= { xylanSrtbArch 1 }
	
	--  type codes

	--  SRTBConfig group.  This group contains the SRTB
	--  Configuration information data.
	--  Implementation of this group is mandatory.

	srtbConfigTable  OBJECT-TYPE
	    SYNTAX  SEQUENCE OF SrtbConfigEntry
            ACCESS  not-accessible
	    STATUS  mandatory
            DESCRIPTION
		"This table contains information related to
		 SRTB configuration for the groups in the switch."
	    ::= { xylanSRTB 1 }


	srtbConfigEntry  OBJECT-TYPE
	    SYNTAX  SrtbConfigEntry
	    ACCESS  not-accessible
	    STATUS  mandatory
	    DESCRIPTION
		"An entry in the SRTB configuration table.  Each entry
		 represents a group for which SRTB has been configured."
	    INDEX { srtbGroupID }
	    ::= { srtbConfigTable 1 }

	SrtbConfigEntry ::= SEQUENCE {
	    srtbGroupID
		INTEGER (1..65535),
	    srtbOperStatus
		INTEGER,
            srtbEthernetRingId
		INTEGER (0..4095),
	    srtbExplorerTypeToSend
		INTEGER
	   }

	srtbGroupID  OBJECT-TYPE
	    SYNTAX  INTEGER (1..65535)
	    ACCESS  read-only 
	    STATUS  mandatory
	    DESCRIPTION
		"This object contains the group ID for SRTB is being
		 configured.  This object uniquely identifies the
		 group in the switch."
	    ::= { srtbConfigEntry 1 }

	srtbOperStatus  OBJECT-TYPE
	    SYNTAX  INTEGER {
			off (1),
			on  (2)
			}
	    ACCESS  read-write
	    STATUS  mandatory
	    DESCRIPTION
		"This is used to enable/disable SRTB for the group and
		 report on status of SRTB for the group."
	    ::= { srtbConfigEntry 2 }

	srtbEthernetRingId  OBJECT-TYPE
	    SYNTAX  INTEGER (0..4095)
	    ACCESS  read-write
	    STATUS  mandatory
	    DESCRIPTION
		"Ring ID to be assigned to the Ethernet segment.
                 Valid ring-id is from 0x001(1) to 0xFFF(4095).
                 Users can set EthRingID from 1 to 4095. But for 0 
                 which is read-only, is not avaliable for user to set. 
                 If 0 is returned (from GET), meaning SRTB is OFF,
                 hence not available for users to configure.
                 "
	    ::= { srtbConfigEntry 3 }
	
	srtbExplorerTypeToSend  OBJECT-TYPE
	    SYNTAX  INTEGER {
                        notAvailable (3),
			typeSTE (2),
			typeARE (1)
			}
	    ACCESS  read-write
	    STATUS  mandatory
	    DESCRIPTION
		"The value of this object specifies which explorer type to
		 send when unknown destination, multicast or broadcast
		 frame is forwarded from Ethernet to Token Ring.
                 If notAvailable is returned (from GET), meaning SRTB is 
                 OFF, hence not available for users to configure.
                 "
	    ::= { srtbConfigEntry 4 }


	-- The srtbRIFTable is used to display the cached RIF values and
	-- to purge the RIF value that has been learned."

	srtbRIFTable  OBJECT-TYPE
	    SYNTAX  SEQUENCE OF SrtbRIFEntry
            ACCESS  not-accessible
	    STATUS  mandatory
            DESCRIPTION
		"This table is used to display the RIF values cached
		 in the switch and to purge the value stored."
	    ::= { xylanSRTB 2 }


	srtbRIFEntry  OBJECT-TYPE
	    SYNTAX  SrtbRIFEntry
	    ACCESS  not-accessible
	    STATUS  mandatory
	    DESCRIPTION
		"An entry in the srtbRIF table."
	    INDEX { srtbRIFMac,  srtbRIFGroupID }
	    ::= { srtbRIFTable 1 }

	SrtbRIFEntry ::= SEQUENCE {
	    srtbRIFMac
		MacAddress,
	    srtbRIFGroupID
		INTEGER (1..65535),
	    srtbRIFString
		OCTET STRING,
	    srtbRIFPurge
		INTEGER
	   }

	srtbRIFMac  OBJECT-TYPE
	    SYNTAX  MacAddress
	    ACCESS  read-only 
	    STATUS  mandatory
	    DESCRIPTION
		"This object contains the MAC address associated with the RIF."
	    ::= { srtbRIFEntry 1 }


	srtbRIFGroupID  OBJECT-TYPE
	    SYNTAX  INTEGER (1..65535)
	    ACCESS  read-only
	    STATUS  mandatory
	    DESCRIPTION
		"This object uniquely identifies the group in the
		 Xylan switch."
	    ::= { srtbRIFEntry 2 }

	srtbRIFString  OBJECT-TYPE
	    SYNTAX  OCTET STRING
	    ACCESS  read-only
	    STATUS  mandatory
	    DESCRIPTION
		"This object contains the RIF that has been cached for
		 MAC address associated with the entry."
	    ::= { srtbRIFEntry 3 }

	srtbRIFPurge  OBJECT-TYPE
	    SYNTAX  INTEGER {
			noAction (1),
			purgeRif (2)
			}
	    ACCESS  read-write
	    STATUS  mandatory
	    DESCRIPTION
		"This object when set to 2 causes the RIF associated
		 with the MAC address to be purged."
	    ::= { srtbRIFEntry 4 }

END
