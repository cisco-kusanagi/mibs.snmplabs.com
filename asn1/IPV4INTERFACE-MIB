IPV4INTERFACE-MIB

   --FORCE-INCLUDE <mib.h>
   --FORCE-INCLUDE <snmpdefs.h>
   --FORCE-INCLUDE <snmpstat.h>
   --FORCE-INCLUDE "mibproto.h"
 
   DEFINITIONS ::= BEGIN

	IMPORTS
		MODULE-IDENTITY, OBJECT-TYPE, Integer32,IpAddress
			FROM SNMPv2-SMI
		RowStatus, TruthValue
			FROM SNMPv2-TC
		apIpv4Interface
			FROM APENT-MIB;


    apIpv4InterfaceMib MODULE-IDENTITY
	   LAST-UPDATED "9711192000Z" -- Wed November 19 20:00:00 EST 1997
	   ORGANIZATION "ArrowPoint Communications Inc."
	   CONTACT-INFO
	   "Postal:               ArrowPoint Communications Inc.
				                 50 Nagog Park
				                 Acton, Massachusetts 01720
	   Tel:                   +1 978-206-3000  option 1
	   E-Mail:                support@arrowpoint.com"
       DESCRIPTION
	"This MIB module describes the ArrowPoint enterprise
	 MIB support for IPv4 Interfaces"
      ::= { apIpv4Interface 1}

--arrowpoint
-- apmgmt
--  ipv4Ext
--   apIpv4Interface
--     apIpv4InterfaceTable

-- per-interface IPv4 configuration information

apIpv4InterfaceTable OBJECT-TYPE
	SYNTAX      SEQUENCE OF ApIpv4InterfaceEntry
	MAX-ACCESS  not-accessible
	STATUS      current
	DESCRIPTION
		"A table of IP Interfaces."
	::= {apIpv4Interface 2}

apIpv4InterfaceEntry OBJECT-TYPE
	SYNTAX      ApIpv4InterfaceEntry
	MAX-ACCESS  not-accessible
	STATUS      current
	DESCRIPTION
	       "ArrowPoint interface table extensions"
	INDEX  {apIpv4IfAddress,apIpv4IfCircuitIfIndex}
	--DEFAULT apjam-group apIpv4IfInst, apIpv4IfAddress
	--DEFAULT apjam-popup-def apIpv4IfInst, Properties, local, Advanced
	--DEFAULT apjam-popup-def apIpv4IfInst, Delete, special, apIpv4IfStatus
	--DEFAULT apjam-popup-def apIpv4IfInst, RipEnable, coderef, Enable Rip, RipEnableMenuItemAction, !ripEnabled()
	--DEFAULT apjam-popup-def apIpv4IfInst, RipDisable, coderef, Disable Rip, RipDisableMenuItemAction, ripEnabled()
	--DEFAULT apjam-popup-def apIpv4IfInst, Rip, coderef, Rip Properties, RipMenuItemAction, ripEnabled()
	--DEFAULT apjam-wizard	Ip Interface Wizard, 1, images/arrowlogo.gif, "An ip interface allows access to the web farm"
	--DEFAULT apjam-wizard	Ip Interface Wizard, 2, images/arrowlogo.gif, ""
	--DEFAULT apjam-group-code  // special mib added routine
	--DEFAULT apjam-group-code  public void RipMenuItemAction( java.awt.event.ActionEvent event )
	--DEFAULT apjam-group-code  {
	--DEFAULT apjam-group-code		ccp = new composerConnectionProtocol();
	--DEFAULT apjam-group-code		arrowIpAddress ipAddr = new arrowIpAddress( get_apIpv4IfAddress());
	--DEFAULT apjam-group-code		arrowIndex ripIndex = new arrowIndex( ipAddr );
	--DEFAULT apjam-group-code		arrowValue val = new arrowValue( 0 );
	--DEFAULT apjam-group-code		arrowResponse fakeResp = new arrowResponse( "", ripIndex, val );
	--DEFAULT apjam-group-code        apRipIfConfInst ripIfData = new apRipIfConfInst( parentFrame, 
	--DEFAULT apjam-group-code														 ourComponent,
	--DEFAULT apjam-group-code														 fakeResp);
	--DEFAULT apjam-group-code        try {
	--DEFAULT apjam-group-code			ripIfData.Properties.getValues( ripIndex );
	--DEFAULT apjam-group-code			(new arrowPropertiesDialog( parentFrame, "Properties", true, 
	--DEFAULT apjam-group-code										ripIfData.Properties)).show();
	--DEFAULT apjam-group-code        }
	--DEFAULT apjam-group-code        catch( IOException  e) { }
	--DEFAULT apjam-group-code	}
	--DEFAULT apjam-group-code
	--DEFAULT apjam-group-code  public void RipEnableMenuItemAction( java.awt.event.ActionEvent event )
	--DEFAULT apjam-group-code	{
	--DEFAULT apjam-group-code		RipHitStatusButton( CREATE_AND_GO );
	--DEFAULT apjam-group-code	}
	--DEFAULT apjam-group-code
	--DEFAULT apjam-group-code  public void RipDisableMenuItemAction( java.awt.event.ActionEvent event )
	--DEFAULT apjam-group-code	{
	--DEFAULT apjam-group-code		RipHitStatusButton( DESTROY );
	--DEFAULT apjam-group-code	}
	--DEFAULT apjam-group-code
	--DEFAULT apjam-group-code	public void RipHitStatusButton( int statusValue )
	--DEFAULT apjam-group-code	{
	--DEFAULT apjam-group-code		ccp = new composerConnectionProtocol();
	--DEFAULT apjam-group-code		java.util.Vector createObjs = new java.util.Vector( 1, 1);
	--DEFAULT apjam-group-code
	--DEFAULT apjam-group-code		// let's actually hit the rip status button.
	--DEFAULT apjam-group-code		arrowValue value = new arrowValue( statusValue ); // set the createandgo value 
	--DEFAULT apjam-group-code		arrowIpAddress ipAddr = new arrowIpAddress( get_apIpv4IfAddress() );
	--DEFAULT apjam-group-code		arrowIndex ripIndex = new arrowIndex( ipAddr );
	--DEFAULT apjam-group-code		arrowResponse resp = new arrowResponse( "rip2IfConfStatus", ripIndex, value );
	--DEFAULT apjam-group-code		createObjs.addElement( resp );
	--DEFAULT apjam-group-code		try	{
	--DEFAULT apjam-group-code			ccp.setBulkObjectValue( createObjs );
	--DEFAULT apjam-group-code		}
	--DEFAULT apjam-group-code		catch (IOException e) {
	--DEFAULT apjam-group-code			arrowErrorDialog errDlg = new arrowErrorDialog( parentFrame, 
	--DEFAULT apjam-group-code										"Set Error", 
	--DEFAULT apjam-group-code						  "An Error Occurred while performing the set operation");
	--DEFAULT apjam-group-code			return;
	--DEFAULT apjam-group-code		}
	--DEFAULT apjam-group-code	}
	--DEFAULT apjam-group-code
	--DEFAULT apjam-group-code	public boolean ripEnabled()
	--DEFAULT apjam-group-code	{
	--DEFAULT apjam-group-code		ccp = new composerConnectionProtocol();
	--DEFAULT apjam-group-code		arrowIpAddress ipAddr = new arrowIpAddress( get_apIpv4IfAddress() );
	--DEFAULT apjam-group-code		arrowIndex ripIndex = new arrowIndex( ipAddr );
	--DEFAULT apjam-group-code        try {
	--DEFAULT apjam-group-code			if( ccp.getObjectValue( "rip2IfConfAddress", ripIndex ) != null )
	--DEFAULT apjam-group-code				return( true );
	--DEFAULT apjam-group-code			else
	--DEFAULT apjam-group-code				return( false );
	--DEFAULT apjam-group-code        }
	--DEFAULT apjam-group-code        catch( IOException  e) {
	--DEFAULT apjam-group-code			return( false );
	--DEFAULT apjam-group-code		}
	--DEFAULT apjam-group-code	}
	::= {apIpv4InterfaceTable 1}

ApIpv4InterfaceEntry ::=
	SEQUENCE {
	       apIpv4IfAddress              IpAddress,
	       apIpv4IfCircuitIfIndex       Integer32, -- Should be InterfaceIndex
	       apIpv4IfNetPrefixLen         Integer32,
	       apIpv4IfDisable              INTEGER,
	       apIpv4IfState                INTEGER,
	       apIpv4IfBroadcastIpAddress   IpAddress,
	       apIpv4IfRedirects            INTEGER,
	       apIpv4IfUnreachables         INTEGER,
	       apIpv4IfIrdp                 INTEGER,
	       apIpv4IfIrdpUseMulticast     INTEGER,
	       apIpv4IfIrdpMax              INTEGER,
	       apIpv4IfIrdpMin              INTEGER,
	       apIpv4IfIrdpPref             INTEGER,
           apIpv4IfStatus               RowStatus,
		   apIpv4IfRunRedundancyProto   TruthValue
		 }

apIpv4IfAddress OBJECT-TYPE
	SYNTAX      IpAddress
	MAX-ACCESS  read-only
	STATUS      current
	DESCRIPTION
	       "The Local Interface IP Address"
	--DEFAULT ap-display-name	IP Address
	--DEFAULT apjam-popup-ref apIpv4IfInst, Properties
	--DEFAULT apjam-wizard-field	1, normal
	::= {apIpv4InterfaceEntry 1}

apIpv4IfCircuitIfIndex OBJECT-TYPE
	SYNTAX      Integer32  -- LOOK!! InterfaceIndex
	MAX-ACCESS  read-only
	STATUS      current
	DESCRIPTION
	       "The Circuit ifIndex associated with the local interface"
	--DEFAULT ap-display-name	If Index
	--DEFAULT apjam-popup-ref apIpv4IfInst, Properties
	--DEFAULT apjam-wizard-field 1, doublechoice, apCctIfIndex( ), apCctName
	::= {apIpv4InterfaceEntry 2}

apIpv4IfNetPrefixLen OBJECT-TYPE
	SYNTAX      Integer32 (8..31)
	MAX-ACCESS  read-create
	STATUS      current
	DESCRIPTION
	       "The network prefix length associated with this entry"
	--DEFAULT ap-display-name	Prefix Length
	--DEFAULT apjam-popup-ref apIpv4IfInst, Properties
	--DEFAULT ap-create-requires Yes
	--DEFAULT apjam-wizard-field	1, normal
	::= {apIpv4InterfaceEntry 3}

apIpv4IfDisable OBJECT-TYPE
	SYNTAX      INTEGER {
			    enable (1),
			    disable (2)
			    } 
	MAX-ACCESS  read-create
	STATUS      current
	DESCRIPTION
	       "Used to disable or enable an interface."
	DEFVAL {1}
	--DEFAULT ap-display-name	State
	--DEFAULT apjam-popup-ref apIpv4IfInst, Properties
	--DEFAULT apjam-wizard-field	1, normal
	::= {apIpv4InterfaceEntry 4}

apIpv4IfState OBJECT-TYPE
	SYNTAX      INTEGER {
			    active (1),   -- interface is up
			    disabled (2), -- interface is disabled
                noCircuit (3) -- interface is waiting for underlying circuit
			    } 
	MAX-ACCESS  read-only
	STATUS      current
	DESCRIPTION
	       "Current state of the interface."
	--DEFAULT ap-display-name	Status
	::= {apIpv4InterfaceEntry 5}

apIpv4IfBroadcastIpAddress OBJECT-TYPE
	SYNTAX      IpAddress
	MAX-ACCESS  read-create
	STATUS      current
	DESCRIPTION
	       "The broadcast IP Address associated with this entry.
            If left zero, the all-ones host is used for numbered
            interfaces.  255.255.255.255 is always used for unnumbered."
	DEFVAL {0}
	--DEFAULT ap-display-name	Broadcast Address
	--DEFAULT apjam-popup-ref apIpv4IfInst, Properties
	--DEFAULT apjam-wizard-field	2, normal
	::= {apIpv4InterfaceEntry 6}

apIpv4IfRedirects OBJECT-TYPE
	SYNTAX      INTEGER {
			    enabled (1),
			    disabled (2)
			    }
	MAX-ACCESS  read-create
	STATUS      current
	DESCRIPTION
	       "Enable/disable the transmission of ICMP redirect packets."
	DEFVAL {1}
	--DEFAULT ap-display-name	Redirects
	--DEFAULT apjam-popup-ref apIpv4IfInst, Properties
	--DEFAULT apjam-wizard-field	2, normal
	::= {apIpv4InterfaceEntry 7}

apIpv4IfUnreachables OBJECT-TYPE
	SYNTAX      INTEGER {
			    enabled (1),
			    disabled (2)
			    }
	MAX-ACCESS  read-create
	STATUS      current
	DESCRIPTION
	       "Enable/disable the transmission of ICMP unreachable packets."
	DEFVAL {1}
	--DEFAULT ap-display-name	Unreachables
	--DEFAULT apjam-popup-ref apIpv4IfInst, Properties
	--DEFAULT apjam-wizard-field	2, normal
	::= {apIpv4InterfaceEntry 8}

apIpv4IfIrdp OBJECT-TYPE
	SYNTAX      INTEGER {
			    enabled (1),
			    disabled (2)
			    }
	MAX-ACCESS  read-create
	STATUS      current
	DESCRIPTION
	       "Enable/disable router discovery."
	DEFVAL {2}
	--DEFAULT ap-display-name	Irdp State
	--DEFAULT apjam-popup-ref apIpv4IfInst, Properties, Advanced
	::= {apIpv4InterfaceEntry 9}

apIpv4IfIrdpUseMulticast OBJECT-TYPE
	SYNTAX      INTEGER {
			    enabled (1),
			    disabled (2)
			    }
	MAX-ACCESS  read-create
	STATUS      obsolete
	DESCRIPTION
	       "Enable/disable the use of the multicast address 224.0.0.1 for
            transmission of router discovery packets.  Default is disabled
            (use 255.255.255.255)."
	DEFVAL {2}
	--DEFAULT ap-display-name	Irdp Multicast
	--DEFAULT apjam-popup-ref apIpv4IfInst, Properties, Advanced
	::= {apIpv4InterfaceEntry 10}

apIpv4IfIrdpMax OBJECT-TYPE
	SYNTAX      INTEGER
	MAX-ACCESS  read-create
	STATUS      obsolete
	DESCRIPTION
	       "Maximum interval between advertisements (seconds).  Default is
            600 seconds."
	DEFVAL {600}
	--DEFAULT ap-display-name	Irdp Max
	--DEFAULT apjam-popup-ref apIpv4IfInst, Properties, Advanced
	::= {apIpv4InterfaceEntry 11}

apIpv4IfIrdpMin OBJECT-TYPE
	SYNTAX      INTEGER
	MAX-ACCESS  read-create
	STATUS      obsolete
	DESCRIPTION
	       "Minimum interval between advertisements (seconds).  Default (0) is
            means use 0.75 times max.  If non-zero, this value must be less
            than apIpv4IfIrdpMax."
	DEFVAL {0}
	--DEFAULT ap-display-name	Irdp Min
	--DEFAULT apjam-popup-ref apIpv4IfInst, Properties, Advanced
	::= {apIpv4InterfaceEntry 12}

apIpv4IfIrdpPref OBJECT-TYPE
	SYNTAX      INTEGER
	MAX-ACCESS  read-create
	STATUS      current
	DESCRIPTION
	       "Router preference value to advertise.  Default is 0."
	DEFVAL {0}
	--DEFAULT ap-display-name	Irdp Preference
	--DEFAULT apjam-popup-ref apIpv4IfInst, Properties, Advanced
	::= {apIpv4InterfaceEntry 13}

apIpv4IfStatus OBJECT-TYPE
	SYNTAX      RowStatus
	MAX-ACCESS  read-create
	STATUS      current
	DESCRIPTION
	       "(fill in later)"
	::= {apIpv4InterfaceEntry 14}

apIpv4IfRunRedundancyProto OBJECT-TYPE
    SYNTAX      TruthValue
    MAX-ACCESS  read-create
    STATUS      current
    DESCRIPTION
           "Indicates whether a redundancy protocol is run on this interface."
    DEFVAL { false }
    ::= { apIpv4InterfaceEntry 15 }

END
