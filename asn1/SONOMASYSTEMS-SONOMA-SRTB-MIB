-- |**********************************************************************|
 -- | Copyright 1998 - Sonoma Systems, Inc. Marina del Rey, CA 90292       |
 -- |    Unpublished software - All rights reserved.                       |
 -- |                                                                      |
 -- | The information in this software is subject to change without notice |
 -- | and should not be construed as a commitment by Sonoma Systems, Inc.  |
 -- |                                                                      |
 -- | Sonoma Systems, Inc. assumes no responsibility for the use or        |
 -- | reliability of its software on equipment which is not supplied by    |
 -- | Sonoma Systems, Inc.                                                 |
 -- |                                                                      |
 -- | This software is furnished under a license and may be copied only    |
 -- | under the terms of that license and with the inclusion of this       |
 -- | notice. This software, or any other copies thereof, may not be       |
 -- | provided or otherwise made available to any other person except to   |
 -- | one who agrees to these license terms. Title to and ownership of the |
 -- | software shall at all times remain with Sonoma Systems, Inc.         |
 -- |**********************************************************************|
 --
 -- Sonoma Systems Inc.,
 -- 4640 Admiralty Way, Suite #600,
 -- Marina Del Rey,
 -- California 90292-6695.
 --
 -- Web : www.sonoma-systems.com
 -- Phone:  310.827.8000
 --
 -- NAME        : srtbmib.def
 --
 -- DESCRIPTION : 
 --
 -- This is the MIB for the Source Routing and Translational bridging
 -- objects for the Sonoma product line.
 --
 -- ARCHIVE : $Archive:   M:\pvcs\pvcsproj\sonoma3\src\mib\srtbmib.dev  $
 -- REVISION: $Revision:   1.6  $
 -- AUTHOR  : $Author:   FREEVE  $
 -- DATE    : $Date:   Nov 13 1998 10:33:52  $
 
 SONOMASYSTEMS-SONOMA-SRTB-MIB      DEFINITIONS ::= BEGIN
 
      IMPORTS
        Counter
        FROM RFC1155-SMI
        OBJECT-TYPE
        FROM RFC-1212
        sonomaBridging
        FROM SONOMASYSTEMS-SONOMA-MIB;        
       --
        -- Hierarchy for these groups
        -- enterprises OBJECT IDENTIFIER ::= { private 4 }
        -- sonomaSystems OBJECT IDENTIFIER ::= {  enterprises 2926 }
        -- sonomaSeries OBJECT IDENTIFIER ::= { sonomaSystems 25 }
        -- sonomaBridging OBJECT IDENTIFIER ::= { sonomaSeries 3 }
        srtBridging OBJECT IDENTIFIER ::= { sonomaBridging 2 }
 
      -- Proprietary Source Routing Objects

      srtBridgeNumber  OBJECT-TYPE
         SYNTAX  INTEGER 
         ACCESS  read-write
         STATUS  obsolete
         DESCRIPTION
            "Obsoleted by vlanConfigBrNumber. Was:
             A bridge number uniquely identifies a bridge when more than
             one bridge is used to span the same segments. This object
             can have values between 0..15 inclusive and also a value
             65535. When set to 65535, source routing on the unit is
             DISABLED."
         DEFVAL  { 65535 }
         ::= { srtBridging 1 }

      srtSourceRouteAgingTime  OBJECT-TYPE
         SYNTAX  INTEGER (10..3600)
         ACCESS  read-write
         STATUS  mandatory
         DESCRIPTION
            "If no frames from a source are received for this time, 
             any associated routing information in the Source Route
             Table is purged. The granularity is seconds."
         DEFVAL { 300 }
         ::= { srtBridging 2 }

      srtPortTable  OBJECT-TYPE
         SYNTAX  SEQUENCE OF SrtPortEntry 
         ACCESS  not-accessible
         STATUS  mandatory
         DESCRIPTION
            "Table of Source Routing per Port parameters. "
         ::= { srtBridging 3 }
          
      srtPortEntry OBJECT-TYPE
         SYNTAX  SrtPortEntry 
         ACCESS  not-accessible
         STATUS  mandatory
          DESCRIPTION
             "An entry in the logical port instanced SRT
              Port Table. "
          INDEX  { srtPortIfIndex }
          ::= { srtPortTable 1 }

      SrtPortEntry  ::= SEQUENCE {
         srtPortIfIndex          INTEGER,
         srtPortHopCount         INTEGER,
         srtPortLocalSegment     INTEGER,
         srtPortLargestFrame     INTEGER,
         srtPortSTESpanMode      INTEGER,
         srtPortSpecInFrames     Counter,
         srtPortSpecOutFrames    Counter,
         srtPortAREInFrames      Counter,
         srtPortAREOutFrames     Counter,
         srtPortSteInFrames      Counter,
         srtPortSteOutFrames     Counter,                  
         srtPortSegmentMismatchDiscards   Counter,
         srtPortDuplicateSegmentDiscards  Counter,
         srtPortHopCountExceededDiscards  Counter
         }

      srtPortIfIndex OBJECT-TYPE
         SYNTAX  INTEGER
         ACCESS  read-only
         STATUS  mandatory
         DESCRIPTION
             "The port number of the port for which this entry
              contains Source Route management information."
         ::= { srtPortEntry 1 }

      srtPortHopCount OBJECT-TYPE
         SYNTAX  INTEGER
         ACCESS  read-write
         STATUS  mandatory
         DESCRIPTION
             "The maximum number of routing descriptors allowed
              in an All Paths or Spanning Tree Explorer frames."
         ::= { srtPortEntry 2 }

      srtPortLocalSegment OBJECT-TYPE
         SYNTAX  INTEGER
         ACCESS  read-write
         STATUS  mandatory
         DESCRIPTION
             "The segment number that uniquely identifies the
              segment to which this port is connected. Current
              source routing protocols limit this value to the
              range: 0 through 4095. A value of 65535 signifies
              that no segment number is assigned to this port."
         ::= { srtPortEntry 3 }

       -- It would be nice if we could use ifMtu as the size of the
       -- largest frame, but we can't because ifMtu is defined to be
       -- the size that the (inter-)network layer can use which can
       -- differ from the MAC layer (especially if several layers of
       -- encapsulation are used).

      srtPortLargestFrame OBJECT-TYPE
         SYNTAX  INTEGER {
                  srtMtu516   (1),
                  srtMtu1500  (2),
                  srtMtu2052  (3),
                  srtMtu4472  (4),
                  srtMtu8144  (5),
                  srtMtu11407 (6), -- yes this is correct don't
                  srtMtu17800 (7), -- ask me where it came from.
                  srtMtu65535 (8)
                  }
          ACCESS  read-write
          STATUS  mandatory
          DESCRIPTION
             "The maximum size of the INFO field (LLC and
              above) that this port can send/receive.  It does
              not include any MAC level (framing) octets.  The
              value of this object is used by this bridge to
              determine whether a modification of the
              LargestFrame (LF, see [14]) field of the Routing
              Control field of the Routing Information Field is
              necessary.  Valid values as defined by the 802.5
              source routing bridging specification[14] are 516,
              1500, 2052, 4472, 8144, 11407, 17800, and 65535
              octets.  Behavior of the port when an illegal
              value is written is implementation specific.  It
              is recommended that a reasonable legal value be
              chosen."
          ::= { srtPortEntry 4 }

      srtPortSTESpanMode OBJECT-TYPE
         SYNTAX  INTEGER {
                     auto-span (1),
                     disabled (2),
                     forced (3)
                 }
         ACCESS  read-write
         STATUS  mandatory
         DESCRIPTION
             "Determines how this port behaves when presented
              with a Spanning Tree Explorer frame.  The value
              'disabled(2)' indicates that the port will not
               accept or send Spanning Tree Explorer packets; any
               STE packets received will be silently discarded.
               The value 'forced(3)' indicates the port will
               always accept and propagate Spanning Tree Explorer
               frames.  This allows a manually configured
               Spanning Tree for this class of packet to be
               configured.  Note that unlike transparent bridging
               this is not catastrophic to the network if there
               are loops.  The value 'auto-span(1)' can only be
               returned by a bridge that both implements the
               Spanning Tree Protocol and has use of the protocol
               enabled on this port. The behavior of the port for
               Spanning Tree Explorer frames is determined by the
               state of dot1dStpPortState.  If the port is in the
               'forwarding' state, the frame will be accepted or
               propagated.  Otherwise it will be silently
               discarded."
          ::= { srtPortEntry 5 }

      srtPortSpecInFrames OBJECT-TYPE
         SYNTAX  Counter
         ACCESS  read-only
         STATUS  mandatory
         DESCRIPTION
             "The number of specifically routed frames that
              have been received from this port's segment."
         ::= { srtPortEntry 6 }

      srtPortSpecOutFrames OBJECT-TYPE
         SYNTAX  Counter
         ACCESS  read-only
         STATUS  mandatory
         DESCRIPTION
             "The number of specifically routed frames that
              this port has transmitted on its segment."
         ::= { srtPortEntry 7 }

      srtPortAREInFrames OBJECT-TYPE
         SYNTAX  Counter
         ACCESS  read-only
         STATUS  mandatory
         DESCRIPTION
             "The number of all paths explorer frames that have
              been received by this port from its segment."
         ::= { srtPortEntry 8 }

      srtPortAREOutFrames OBJECT-TYPE
         SYNTAX  Counter
         ACCESS  read-only
         STATUS  mandatory
         DESCRIPTION
             "The number of all paths explorer frames that have
              been transmitted by this port on its segment."
         ::= { srtPortEntry 9 }

      srtPortSteInFrames OBJECT-TYPE
         SYNTAX  Counter
         ACCESS  read-only
         STATUS  mandatory
         DESCRIPTION
             "The number of spanning tree explorer frames that
               have been received by this port from its segment."
         ::= { srtPortEntry 10 }

      srtPortSteOutFrames OBJECT-TYPE
         SYNTAX  Counter
         ACCESS  read-only
         STATUS  mandatory
         DESCRIPTION
             "The number of spanning tree explorer frames that
              have been transmitted by this port on its
              segment."
         ::= { srtPortEntry 11 }

      srtPortSegmentMismatchDiscards OBJECT-TYPE
         SYNTAX  Counter
         ACCESS  read-only
         STATUS  mandatory
         DESCRIPTION
             "The number of explorer frames that have been
              discarded by this port because the routing
              descriptor field contained an invalid adjacent
              segment value."
         ::= { srtPortEntry 12 }

      srtPortDuplicateSegmentDiscards OBJECT-TYPE
         SYNTAX  Counter
         ACCESS  read-only
         STATUS  mandatory
         DESCRIPTION
             "The number of frames that have been discarded by
              this port because the routing descriptor field
              contained a duplicate segment identifier."
         ::= { srtPortEntry 13 }

     srtPortHopCountExceededDiscards OBJECT-TYPE
        SYNTAX  Counter
        ACCESS  read-only
        STATUS  mandatory
        DESCRIPTION
            "The number of explorer frames that have been
             discarded by this port because the Routing
             Information Field has exceeded the maximum route
             descriptor length."
        ::= { srtPortEntry 14 }

   
     srtSourceRouteTable  OBJECT-TYPE
        SYNTAX  SEQUENCE OF SrtSourceRouteEntry
        ACCESS  not-accessible
        STATUS  mandatory
        DESCRIPTION
            "This table contains a list of stored destination address
             and the routing information fields which will be inserted
             in frames sent to those destinations."
        ::= { srtBridging 4 }

      srtSourceRouteEntry  OBJECT-TYPE
         SYNTAX  SrtSourceRouteEntry
         ACCESS  not-accessible
         STATUS  mandatory
         DESCRIPTION
             "An source route entry."
         INDEX  { srtSourceRouteVlanID, srtSourceRouteAddress }
         ::= { srtSourceRouteTable 1 }
                                     
    SrtSourceRouteEntry  ::= SEQUENCE {
       srtSourceRouteVlanID      INTEGER,
       srtSourceRouteAddress     OCTET STRING (SIZE(6)),
       srtSourceRouteRIF         OCTET STRING (SIZE(0..18)),
       srtSourceRouteType        INTEGER,
       srtSourceRouteDirection   INTEGER              
       }
    
    srtSourceRouteVlanID  OBJECT-TYPE
       SYNTAX  INTEGER
       ACCESS  read-only
       STATUS  mandatory
       DESCRIPTION
           "This is the ID of the Vlan on which the address
            corresponding to this entry was learnt."
       ::= { srtSourceRouteEntry 1 }

    srtSourceRouteAddress  OBJECT-TYPE
       SYNTAX  OCTET STRING (SIZE(6))
       ACCESS  read-only
       STATUS  mandatory
       DESCRIPTION
           "This is the source address which was stored when the
            Source Routing frame which contained it was processed by the
            SRTB. The address is in the form it was 
            received from the ring network."
       ::= { srtSourceRouteEntry 2 }

    srtSourceRouteRIF  OBJECT-TYPE
       SYNTAX  OCTET STRING (SIZE(0..18))
       ACCESS  read-only
       STATUS  mandatory
       DESCRIPTION
           "This object contains all the routing information which was
            extracted from the received Source Routed frame. The data
            is in the form it was received from the ring network"
       ::= { srtSourceRouteEntry 3 }

    srtSourceRouteType  OBJECT-TYPE
       SYNTAX  INTEGER {
                         permanent (1),
                         temporary (2),
                         respondWithARE (3),
                         other (4)
                        } 
       ACCESS  read-only
       STATUS  mandatory
       DESCRIPTION
           "This object represents the type of the entry. If the value
            returned is sameRing (1), then this indicates that the
            frame from which this entry was taken originated on our
            local ring. A value of locked (2) is used for entries which
            have been learned from ARE type frames. 
            The value provisional(3)is used for frames which have been
            learned from STE frames and the responsWithARE (4) values is
            used to indicate that when a response is sent to this 
            entry's address is should be sent as an ARE frame."
       ::= { srtSourceRouteEntry 4 }

    srtSourceRouteDirection  OBJECT-TYPE
       SYNTAX  INTEGER {
                         inOrder(1),
                         reverseOrder(2)
                        }
       ACCESS  read-only
       STATUS  mandatory
       DESCRIPTION
           "If this object returns a value of inOrder(0), then this
            means that the D bit is zero and that the frame traverses
            the LANs in the order in which they are specified in the 
            routing information field.
            Conversely, if the D bit is set to 1 the frame will traverse 
            the LANs in the reverse order. The D bit is meaningful only 
            or source routed frames (SRF). For STE and ARE frames the
            D bit is ignored and is not altered by the unit."
       ::= { srtSourceRouteEntry 5 }

 END
