-- ****************************************************************************
--                             sc553.mib
-- ****************************************************************************

-- Copyright 1997 General DataComm Inc., All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.

-- This MIB module uses the extended OBJECT-TYPE macro as
-- defined in RFC 1212.

-- Note:  All rows in all tables defined within this MIB module are
-- virtual.  They can neither be created or deleted by management
-- operations.



-- ****************************************************************************
--                        Revision History
-- ****************************************************************************

-- Version   Date	Name

-- 1.00A     20-Dec-96  D. Baylis     	Initial Revision
--           07-Jan-97  D. Baylis     	1) removed enums (1) and (2) on  sc553ConfigurationSave
--				      	2) changed spelling of enums (1) and (5) on 
--					sc553AlarmCountWindow 
-- 1.00B     09-Jan-97  D. Baylis       Added firmware download support to sc553VersionTable:
-- 1.00C     09-Jan-97  D. Baylis	Added sc553DiagResetTestResults object
-- 1.00D     10-Jan-97  D. Baylis       Chagned module name to GDC-SC553 and added sc553TotalFarEndTable
-- 1.00E     20-Jan-97  D. Baylis       1) Changed Clock invert to sc553ChannelAdminClkInvert and
--						sc553ChannelOperClkInvert
--					2) Deleted sc553ChannelFlowControl
--       				3) Deleted none(1) on sc553NetworkPreequalization
--					4) Reordered enums on sc553NetworkAdminLineType, sc553NetworkOperLineType
--					   sc553NetworkAdminLineBuildout, sc553NetworkOperLineBuildout,
--					   and sc553NetworkTransmitClockSource
-- 1.00F     22-Jan-97  D. Baylis       1) deleted sc553DteStatus {sc553 3} and moved others up
--					2) Modified description on sc553LedStatus
--					3) Modified enum names on:
--						sc553ChannelDataInvert
--						sc553ChannelAdminClkInvert
--						sc553ChannelOperClkInvert
--					4) Reordered sc553NetworkAdminLineType, sc553NetworkOperLineType enums
--					5) Removed enums 2-5 on sc553ProductType and renamed enum 1
-- 1.00G     03-Feb-97  D. Baylis       1) Chagned sc553ReceiveLevel to enum type 
--                                      2) Added -7.5db to sc553NetworkAdminLineType and sc553NetworkOperLineType 
-- 1.00H     05-Feb-97  D. Baylis       1) Modified/ added sc553ChannelAdminClkInvert enums:
--						autoTxnormRx(5) and autoTxinvertRx(6)
-- 1.00J     11-Feb-97  D. Baylis       1) Added CRC's to all performance statistics.
-- 1.00K     18-Feb-97  D. Baylis       1) Added sc553DownloadingMode to sc553VersionTable
--					2) Added % complete to Network and Far End perf.
-- 1.00M     20-Feb-97  D. baylis       1) Changed sc553UserIntervals into three objects:sc553ValidUserIntervals
--        				   sc553ValidNetworkIntervals, and sc553ValidFarEndIntervals		
--        				   sc553ValidNetworkIntervals, and sc553ValidFarEndIntervals		
-- 1.00N     30-May-97  C. Amorossi     1) Added Statistics Collection objects
--        				   sc553ValidNetworkIntervals, and sc553ValidFarEndIntervals		
-- 1.00P     17-Jun-97  D. Baylis       1) Added enum testTimeInfinite(16)			
--			
-- 1.00Q     17-Oct-97  D. Baylis       1) Added enum testTimeInfinite(16)		
--					2) Added statDownloadAborted(7) to object sc553StoredFirmwareStatus
--					3) Added objects to s553ChannelConfigtable for redundancy
--						sc553ChannelNetworkNumber
--						sc553ChannelActivePort
--						sc553channelRedundancy
--						sc553ChannelActivePort
--					4) Cascade support:
--						a) Added sc553CasReceiveLevel to sc553MaintenanceTable
--						b) Added casDigitalLoopback(9), casLineLoop(10), and casPayloadLoop(1)
--							to object sc553DiagT1Test	
--						c) Added sc553CascadeConfigTable 
--						d) Added cascade(2) to object sc553NetworkTransmitClockSource
--						e) Added sc553ChannelInService to sc553ChannelConfigTable
--					5) Twin Pack support:
--						a) Added sc553ShelfType: spectracom(1), twinPack(2).
--						b) Added sc553TwinPackPowerSupplyInstalled bottom(1), top(2), both(3).	
--   	      22-Oct-97 D. Baylis       6) Added Alarms: 	sc553RedundancyOn
--							 	sc553RemoteNotResponding 
--								sc553TopPowerSupplyFail
--								sc553BottomPowerSupplyFail
--	      19-Dec-97 D. Baylis       7) Added sc553TestAllLeds to sc553MaintenanceTable
-- 	      06-Jan-98 D. Baylis       1) Added cascade enums to sc553DiagTestStatus and
--					2) Reorded sc553DiagT1Test enums
--					
--	      07-Jan-98 D. Baylis	Changed sc553DiagT1Test enum # 10 name
-- 1.00R      22-Jan-98 C. Amorossi     1) Added sc553DiagT1TestDirection
--					   and sc553DiagDS0TestDirection to
--					   sc553DiagTable
--					2) Added sc553CascadeAISLoopdown
--					   and sc553CascadeLoopbackConfig to
--					   sc553CascadeConfigTable
-- 1.00S      06-Feb-98 C. Amorossi     Changed OID of sc553ConfigurationSave
-- 1.00T      07-May-98 C. Amorossi     1) Obsolete sc553ChannelNetworkPosition
--                                         and sc553ChannelNetworkNumber.
--                                      2) Add cascade (2) to sc553NetworkFallbackClockSource.
--
--
--
--
-- ****************************************************************************


-- ****************************************************************************
--                       mib definitions begin
-- ****************************************************************************


GDC-SC553-MIB DEFINITIONS ::= BEGIN

IMPORTS	
        Gauge				FROM RFC1155-SMI
	OBJECT-TYPE			FROM RFC-1212
	DisplayString			FROM RFC1213-MIB
	gdc				FROM GDCCMN-MIB
	SCinstance			FROM GDCMACRO-MIB;

dsx1                   OBJECT IDENTIFIER ::= { gdc 6 }
sc553                 OBJECT IDENTIFIER ::= { dsx1 11}

sc553Version          OBJECT IDENTIFIER ::= { sc553 1 }
sc553Configuration    OBJECT IDENTIFIER ::= { sc553 2 }
sc553Diagnostics      OBJECT IDENTIFIER ::= { sc553 3 }
sc553Maintenance      OBJECT IDENTIFIER ::= { sc553 4 }
sc553Alarms           OBJECT IDENTIFIER ::= { sc553 5 }
sc553Performance      OBJECT IDENTIFIER ::= { sc553 6 }


sc553MIBversion OBJECT-TYPE
    SYNTAX DisplayString (SIZE (5))
    ACCESS read-only
    STATUS mandatory
    DESCRIPTION
        "Identifies the version of the MIB. The format of the version
        is x.yzT, where 'x' identifies the major revision number, 'y'
        identifies the minor revision number, 'z' identifies the
        typographical revision, and T identifies the test revision.
        Upon formal release, no designation for the test revision will
        be present. Acceptable values for the individual revision
        components are as follows:
        x: 1 - 9,    y: 0 - 9,    z: 0 - 9,    T: A - Z"
    ::= { sc553Version 1 }




-- ****************************************************************************
--                                Version Table
-- ****************************************************************************


sc553VersionTable OBJECT-TYPE
    SYNTAX SEQUENCE OF Sc553VersionEntry
    ACCESS not-accessible
    STATUS mandatory
    DESCRIPTION " "
    ::= { sc553Version 2  }

sc553VersionEntry OBJECT-TYPE
    SYNTAX Sc553VersionEntry
    ACCESS not-accessible
    STATUS mandatory
    DESCRIPTION
        "An entry in the GDC SC553 Version Table."
    INDEX	{ sc553VersionIndex }
    ::= { sc553VersionTable 1 }

Sc553VersionEntry ::=
    SEQUENCE {
	sc553VersionIndex    		SCinstance,
	sc553ActiveFirmwareRev 		DisplayString,
	sc553StoredFirmwareRev		DisplayString,
	sc553BootRev			DisplayString,
	sc553StoredFirmwareStatus	INTEGER,
	sc553SwitchActiveFirmware	INTEGER,
	sc553DownloadingMode          	INTEGER
    }

sc553VersionIndex OBJECT-TYPE
    SYNTAX SCinstance
    ACCESS read-only
    STATUS mandatory
    DESCRIPTION
        "Identifies Version parameters associated with the managed object."
    ::= { sc553VersionEntry 1 }


sc553ActiveFirmwareRev OBJECT-TYPE
    SYNTAX DisplayString (SIZE(8))
    ACCESS read-only
    STATUS mandatory
    DESCRIPTION
        "The version number of the firmware currently executing.

	The format is MM.NN.BB where:
	
		MM: Major Revision (0-99)
		NN: Minor Revision (0-99)
		BB: Bug Fix Revision (0-99)

 	 	"
    ::= { sc553VersionEntry 2 }

sc553StoredFirmwareRev OBJECT-TYPE
    SYNTAX DisplayString (SIZE(8))
    ACCESS read-only
    STATUS mandatory
    DESCRIPTION
        "The version number of the firmware stored (in a compressed format) 
         but not currently executing.

	
		MM: Major Revision (0-99)
		NN: Minor Revision (0-99)
		BB: Bug Fix Revision (0-99)

	"
    ::= { sc553VersionEntry 3 }

sc553BootRev OBJECT-TYPE
    SYNTAX DisplayString (SIZE(2))
    ACCESS read-only
    STATUS mandatory
    DESCRIPTION
        "The version number of the bootstrap firmware. 

    	The version number of the firmware, to allow products to know which
    	revision is installed.  The released version number is sequenced from
    	--, A-, ... AA, ... ZZ.  
	"
    ::= { sc553VersionEntry 4 }


sc553StoredFirmwareStatus OBJECT-TYPE
    SYNTAX INTEGER {
        statBlank(1),                       
        statDownLoading(2),
	statOK(3),
	statCheckSumBad(4),    
	statUnZipping(5),
	statBadUnZip(6),
	statDownloadAborted(7)
                    
    }
    ACCESS read-only
    STATUS mandatory
    DESCRIPTION
        "This object represents the state of the Non-Active or Stored firmware:

        statBlank(1)    	Factory Default                  
        statDownLoading(2)	In process of downloading firmware

	statOK(3)		Zipped version checksum succesful (OK to switch)
				(can set sc553SwitchActive to switchActive(2))
				
	statCheckSumBad(4)    	Failed checksum after download
	statUnZipping(5)	In process of uncompressing into active area
	statBadUnZip(6)      	Failed last uncompress 
	statDownloadAborted(7)  Download aborted by user             


	The object is read only.
	 "
    ::= { sc553VersionEntry 5 }


sc553SwitchActiveFirmware OBJECT-TYPE
    SYNTAX INTEGER {
        switchNorm(1),                  -- Read only
        switchActive(2)			-- Write only
    }
    ACCESS read-write
    STATUS mandatory
    DESCRIPTION
        "This object is used to switch the active executing firmware from the version 
	in sc553ActiveRev to the version in sc553StoredRev.

	When a  switchActive(2) is set (write only) the element will:
		1) reboot
		2) uncompress stored code into active area
		3) perform checksum on active area
		4) Set sc553StoredStatus object to indicate results
		5) If succesfull:
			update sc553ActiveFirmwareRev and sc553StoredFirmwareRev
			and begin executing
		   If failed: 
			replace active area with previous revision


	The switchNorm(1) enumeration will always be read. 

	Setting switchActive(2) when the sc553StoredStatus is not statOK(3) will
	result in an error.
	"
    ::= { sc553VersionEntry 6 }


sc553DownloadingMode OBJECT-TYPE
    SYNTAX INTEGER {
        disableAll(1),
        enableAndWait(2),
	enableAndSwitch(3)
    }
    ACCESS read-write
    STATUS mandatory
    DESCRIPTION
        "This object is used to configure the download mode:

        disableAll(1)		Prevents any firmware downloading to SC553

        enableAndWait(2)        Allows downloading zipped code to be stored only!
								
	enableAndSwitch(3)	Allows downloading and then unzips and begins executing
				the new code

	"
    ::= { sc553VersionEntry 7 }











-- ****************************************************************************
--                        Configuration table
-- ****************************************************************************


--
--
--                     Channel Configuration table
-- 


sc553ChannelConfigTable OBJECT-TYPE
    SYNTAX SEQUENCE OF Sc553ChannelConfigEntry
    ACCESS not-accessible
    STATUS mandatory
    DESCRIPTION
    "The GDC 553 Channel Configuration table."
    ::= { sc553Configuration 1 }


sc553ChannelConfigEntry OBJECT-TYPE
    SYNTAX Sc553ChannelConfigEntry
    ACCESS not-accessible
    STATUS mandatory
    DESCRIPTION
    "The sc553 Channel Configuration table entry."
    INDEX { sc553ChannelConfigIndex }
    ::= { sc553ChannelConfigTable 1 }


Sc553ChannelConfigEntry ::=
    SEQUENCE {
        sc553ChannelConfigIndex       	SCinstance,
        sc553ChannelDS0AllocationScheme INTEGER,
        sc553ChannelBaseRate 		INTEGER,
        sc553ChannelStartingDS0 	INTEGER,
        sc553ChannelNumberOfDS0s 	INTEGER,
        sc553ChannelInbandDccMode 	INTEGER,
        sc553ChannelSplitTiming 	INTEGER,
        sc553ChannelChannelType 	INTEGER,
        sc553ChannelAdminClkInvert 	INTEGER,
        sc553ChannelOperClkInvert 	INTEGER,
        sc553ChannelDataInvert 		INTEGER,
        sc553ChannelLocalDCD 		INTEGER,
        sc553ChannelLocalDSR 		INTEGER,
        sc553ChannelRTSCTSControl 	INTEGER,
        sc553ChannelEIAtestLeads 	INTEGER,
        sc553ChannelInbandLoop 		INTEGER,
        sc553ChannelInbandLoopdown 	INTEGER,
  	sc553channelRedundancy		INTEGER,
  	sc553ChannelActivePort		INTEGER,
  	sc553ChannelNetworkNumber	INTEGER,
  	sc553ChannelNetworkPosition	INTEGER,
        sc553WakeUpRemote      		DisplayString,
	sc553ChannelInService		INTEGER
    }


sc553ChannelConfigIndex OBJECT-TYPE
    SYNTAX SCinstance
    ACCESS read-only
    STATUS mandatory
    DESCRIPTION
        "The index value which uniquely identifies the channel to
        which this entry is applicable.  This has the form of a
        SCinstance which defines the slot, line, drop, and
        sub-identifier.
 
        The sub-indentifier for this SCinstance is the channel."
    ::= { sc553ChannelConfigEntry 1 }


sc553ChannelDS0AllocationScheme OBJECT-TYPE
    SYNTAX INTEGER {
        consecutive(1),                 -- consecutive DS0's allocation scheme
        alternate(2)                    -- alternate DS0's allocation scheme
    }
    ACCESS read-write
    STATUS mandatory
    DESCRIPTION
        "Identifies the DSU DS0 allocation scheme.The value consecutive(2) 
        indicates that bundles of DS0s are allocated to channels consecutively 
        from the starting DS0. The value of alternate(3) indicates that bundles 
        of DS0s are allocated to channels alternatly, or every other DS0 from
        the starting DS0. The unused DS0s are forced to marks.
 
        Note that DS0 bundles cannot be split across frames (wrap around
        from the highest numbered DS0 of one frame to DS0 1 of the next
        frame. For example, on a T1 frame using consecutive DS0 allocation,
        a channel configuration of starting DS0 = 20 and number of
        DS0s = 5 is an illegal channel configuration because the DS0 bundle
        wraps from DS0 #24 of 1 frame to DS0 #1 of the next."
    ::= { sc553ChannelConfigEntry 2 }

sc553ChannelBaseRate OBJECT-TYPE
    SYNTAX INTEGER {
        nx56k(1),                       -- N X 56K rate
        nx64k(2)                        -- N X 64K rate
    }
    ACCESS read-write
    STATUS mandatory
    DESCRIPTION
        "Indicates the DS0 base rate: either 56K or 64K bits per second.
        This is used in conjunction with the number of DS0s to determine
        the bandwidth of the channel.
 
        Note that base rate of 64K defines the DS0 as clear channel in
        which all 8 bits of the DS0 are used. A base rate of 56K defines
        the DS0 as non-clear in which bits 1-7 are used for channel data
        and the 8th bit is either unused and forced to marks or used to
        pass signaling information."
    ::= { sc553ChannelConfigEntry 3 }
 
sc553ChannelStartingDS0 OBJECT-TYPE
    SYNTAX INTEGER (0..24)
    ACCESS read-write
    STATUS mandatory
    DESCRIPTION
        "Indicates the starting DS0 number for the bundle of DS0s used for
        the channel. DS0 bundles are allocated starting at the DS0 defined by
        this integer.
 
        When this integer is set to 0, the channel is disabled and no DS0s
        are allocated to the channel.
 
        Note that DS0 bundles cannot be split across frames (wrap around
        from the highest numbered DS0 of one frame to DS0 1 of the next
        frame. For example, on a T1 frame using consecutive DS0 allocation,
        a channel configuration of starting DS0 = 20 and number of
        DS0s = 5 is an illegal channel configuration because the DS0 bundle
        wraps from DS0 #24 of 1 frame to DS0 #1 of the next."
    ::= { sc553ChannelConfigEntry 4 }
 
sc553ChannelNumberOfDS0s OBJECT-TYPE
    SYNTAX INTEGER (1..24)
    ACCESS read-write
    STATUS mandatory
    DESCRIPTION
        "Indicates the number of DS0s for the bundle allocated to the
        channel. The number of DS0s, in conjunction with the DS0 base
        rate, also determines the bandwidth of the channel.
 
        Note that DS0 bundles cannot be split across frames (wrap around
        from the highest numbered DS0 of one frame to DS0 1 of the next
        frame. For example, on a T1 frame using consecutive DS0 allocation,
        a channel configuration of starting DS0 = 20 and number of
        DS0s = 5 is an illegal channel configuration because the DS0 bundle
        wraps from DS0 #24 of 1 frame to DS0 #1 of the next."
    ::= { sc553ChannelConfigEntry 5 }
 
 
sc553ChannelInbandDccMode OBJECT-TYPE
    SYNTAX INTEGER {
	none(1),
        embedded(2),
        dccDs0(3)
    }
    ACCESS read-write
    STATUS mandatory
    DESCRIPTION
        "The mode of propagation of inband Diagnostics Communication Channel to
        the dedicated remote sc553 unit. None specifies no inband DCC. Embedded
        is an allowed value when the mib object sc553DS0BaseRate is set to Nx56K,
        and specifies that DCC is propagated in the 8th bit of the assigned DS0's.
        dccDs0 specifies that a DS0 is used for propagation of DCC, this value
        would be selected if the sc553DS0BaseRate is Nx64k (clear channel) since
        all data bits are used for user data,  a minimum of two DS0's must be
        assigned to this device in this mode, the last ds0 should be set as the
        sc553DccDs0 when using this mode."
    ::= { sc553ChannelConfigEntry 6 }



sc553ChannelSplitTiming OBJECT-TYPE
    SYNTAX INTEGER {
        disabled(1),                    -- split timing disabled
        enabled(2)                      -- split timing enabled
    }
    ACCESS read-write
    STATUS mandatory
    DESCRIPTION
        "Indicates whether or not to use split timing. The value disabled(1)
        indicates that channel's transmit timing is provided by the DSU.
        The value enabled(2) indicates that the channel's transmit timing
        is provided by the customer business equipment (ext Tx Clk).
 
        Split timing refers to the activation of elastic storage to allow
        the channel interface to receive data using the customer business
        equipment's timing source (ext Tx Clk) and transmit that same data
        to the network using the networks timing source."
    ::= { sc553ChannelConfigEntry 7 }
 
sc553ChannelChannelType OBJECT-TYPE
    SYNTAX INTEGER {
        none(1),                        -- no channel interface
        v35(2),                         -- V.35 interface
        eia530(3)                       -- 530 EIA interface
    }
    ACCESS read-only
    STATUS mandatory
    DESCRIPTION
        "The channel interface type. The value none(1) indicates that 
        there is no channel interface for the index. The value v35(2) 
        indicates the channel interface is standard V.35 and the value 
        eia530(3) indicates the channel interface is standard EIA 530."
    ::= { sc553ChannelConfigEntry 8 }

sc553ChannelAdminClkInvert OBJECT-TYPE
    SYNTAX INTEGER {
        none(1),      		-- Tx and Rx clock normal
        invertRx(2),    	-- Tx clock normal, Rx clock inverted
        invertTx(3),    	-- Tx clock inv, Rx clock normal
        both(4),  		-- Tx and Rx clock inverted
	autoTxnormRx(5),	-- Auto select Tx clock Rx clock normal
	autoTxinvertRx(6)	-- Auto select Tx clock Rx clock inverted
     }
    ACCESS read-write
    STATUS mandatory
    DESCRIPTION
    "Clock invert option for manual settings ( 1-4).
     Options autoTxnormRx(5) and autoTxinvertRx(6) allow auto selection of
     Tx clock with Rx clock normal, or inverted.		
	    "		
    ::= { sc553ChannelConfigEntry 9 }
 
sc553ChannelOperClkInvert OBJECT-TYPE
    SYNTAX INTEGER {
        none(1),      	-- Tx and Rx clock normal
        invertRx(2),    -- Tx clock normal, Rx clock inverted
        invertTx(3),    -- Tx clock inv, Rx clock normal
        both(4)  	-- Tx and Rx clock inverted
     }
    ACCESS read-only
    STATUS mandatory
    DESCRIPTION
    "Clock invert option. Read Only."
    ::= { sc553ChannelConfigEntry 10 }
 
sc553ChannelDataInvert OBJECT-TYPE
    SYNTAX INTEGER {
        none(1),        -- Tx and Rx data normal
        invertRx(2),    -- Tx data normal, Rx data inverted
        invertTx(3),    -- Tx data inverted, Rx data normal
        both(4)    	-- Tx and Rx data inverted
    }
    ACCESS read-write
    STATUS mandatory
    DESCRIPTION
    "Data invert option"
    ::= { sc553ChannelConfigEntry 11}
 
sc553ChannelLocalDCD OBJECT-TYPE
    SYNTAX INTEGER {
        followsSignal(1),               -- local DCD follows inband CMI
        forcedOn(2)                     -- local DCD forced on
    }
    ACCESS read-write
    STATUS mandatory
    DESCRIPTION
        "Controls the operation of Data Carrier Detect (DCD) signal.
        The value followsSignal(1) indicates that the channel's DCD follows
        the inband control mode idle (CMI). The value forcedOn(2) indicates
        that DCD is forced on."
    ::= { sc553ChannelConfigEntry 12}
 
sc553ChannelLocalDSR OBJECT-TYPE
    SYNTAX INTEGER {
        followsSignal(1),               -- local DSR follows inband CMI
        forcedOn(2)                     -- local DSR forced on
    }
    ACCESS read-write
    STATUS mandatory
    DESCRIPTION
        "Controls the operation of the Data Set Ready (DSR) signal.
        The value followsSignal(1) indicates that the channel's DSR follows
        the inband control mode idle (CMI). The value forcedOn(2) indicates
        that DSR is forced on."
    ::= { sc553ChannelConfigEntry 13}
 
 
sc553ChannelRTSCTSControl OBJECT-TYPE
    SYNTAX INTEGER {
        ctrl(1),                	-- CTS 
        ctsForcedOn(2)                  -- CTS forced on
    }
    ACCESS read-write
    STATUS mandatory
    DESCRIPTION
        "
	?
	"
    ::= { sc553ChannelConfigEntry 14}
 
sc553ChannelEIAtestLeads OBJECT-TYPE
    SYNTAX INTEGER {
        disabled(1),                    -- EIA test leads disabled
        enabled(2)                      -- EIA test leads enabled
    }
    ACCESS read-write
    STATUS mandatory
    DESCRIPTION
        "Controls the channel's EIA test leads. The EIA test leads allow
        customer business equipment to initiate diagnostic tests through
        the assertion of the EIA test leads RDL, LL, and ST.
 
        When this object is enabled(1), then the assertion of these leads
        is recognized and acted upon by the DSU.  When this object is
        disabled(2), then the assertion of these leads is ignored by the DSU."
    ::= { sc553ChannelConfigEntry 15 }
 
sc553ChannelInbandLoop OBJECT-TYPE
    SYNTAX INTEGER {
        disable(1),                     -- disable detection of in-band loop code
        enabled(2)                      -- enable detection of in-band loop code
    }
    ACCESS read-write
    STATUS mandatory
    DESCRIPTION
        "In-band loopcode enable/disable. The value disabled(1) indicates
        the channel does not enter an RDL loop when an inband RDL code is detected.
        The value enable(2) indicates the channel does enter an RDL loop when
        an inband RDL code is detected."
    ::= { sc553ChannelConfigEntry 16 }
 
sc553ChannelInbandLoopdown OBJECT-TYPE
    SYNTAX INTEGER {
        inhibit(1),                    -- timeout disabled
        enable10Min(2)                 -- timeout value of 10 minutes
    }
    ACCESS read-write
    STATUS mandatory
    DESCRIPTION
        "The time limit in seconds before terminating a channel's RDL.
        The value inhibit(1) indicates that the loopdown time is disabled and
        the loopback will only terminate by the in-band loopdown code.

        The value enable10Min(2) indicates the time before terminating
        the RDL in the event the loopdown code is never received."
    ::= { sc553ChannelConfigEntry 17 }


sc553channelRedundancy OBJECT-TYPE
    SYNTAX INTEGER {
        on(1),                    
        off(2)                 
    }
    ACCESS read-write
    STATUS mandatory
    DESCRIPTION
        "
	"
    ::= { sc553ChannelConfigEntry 18 }

sc553ChannelActivePort OBJECT-TYPE
    SYNTAX INTEGER {
        network(1),                    
        cascade(2)                 
    }
    ACCESS read-write
    STATUS mandatory
    DESCRIPTION
        "
	This option routes the Channel bundle through either the network
	or cascade port.  When a port becomes active the other port
	is automatically defined as the standby port.
	"
    ::= { sc553ChannelConfigEntry 19 }



sc553ChannelNetworkNumber OBJECT-TYPE
    SYNTAX INTEGER {
        networkOne(1),                 
        networkTwo(2)           
    }
    ACCESS read-write
    STATUS obsolete
    DESCRIPTION
        "
	In redundant T1 applications, there are two (2) networks employed.
	The are arbitrarily labeled Network 1 and Network 2.  This option
	designates which of these redundant T1 networks is used for
	transmission over the SC553's Active T1 port.
	"
    ::= { sc553ChannelConfigEntry 20 }



sc553ChannelNetworkPosition OBJECT-TYPE
    SYNTAX INTEGER {
        network(1),                    
        cascade(2)                 
    }
    ACCESS read-write
    STATUS obsolete
    DESCRIPTION
        "
	In redundant T1 applications, this option defines the network position of the DSU.
	Network position indicates that the DSU is connected directly to the network.
	Cascade position indicates that the DSU is connected to the network as a cascaded
	DSU through at least one ther DSU.
	"
    ::= { sc553ChannelConfigEntry 21 }



sc553WakeUpRemote OBJECT-TYPE
	SYNTAX	  DisplayString (SIZE (16))
	ACCESS	  read-only
	STATUS	  mandatory
	DESCRIPTION
	"This object is requested to initiate the add remote process. The serial number
         of the associated remote is returned." 
	::= { sc553ChannelConfigEntry 22}


sc553ChannelInService OBJECT-TYPE
    SYNTAX  INTEGER {
        on(1),
        off(2)
    }
    ACCESS  read-write
    STATUS  mandatory
    DESCRIPTION
        ""
     ::= { sc553ChannelConfigEntry 23 }
 


  

-- 
--
--                     Network Configuration table
-- 


sc553NetworkConfigTable OBJECT-TYPE
    SYNTAX SEQUENCE OF Sc553NetworkConfigEntry
    ACCESS not-accessible
    STATUS mandatory
    DESCRIPTION
    "The GDC 553 Network Configuration table."
    ::= { sc553Configuration 2 }
 
 
sc553NetworkConfigEntry OBJECT-TYPE
    SYNTAX Sc553NetworkConfigEntry
    ACCESS not-accessible
    STATUS mandatory
    DESCRIPTION
    "The sc553 Network Configuration table entry."
    INDEX { sc553NetworkConfigIndex }
    ::= { sc553NetworkConfigTable 1 }
 
 
Sc553NetworkConfigEntry ::=
    SEQUENCE {
        sc553NetworkConfigIndex 	SCinstance,
        sc553NetworkAdminLineType 	INTEGER,
        sc553NetworkOperLineType 	INTEGER,
        sc553NetworkInterfaceType 	INTEGER,
        sc553NetworkPreequalization 	INTEGER,
        sc553NetworkAdminLineBuildout 	INTEGER,
        sc553NetworkOperLineBuildout 	INTEGER,
        sc553NetworkOnesDensity 	INTEGER,
        sc553NetworkTransmitClockSource INTEGER,
        sc553NetworkFallbackClockSource INTEGER,
        sc553NetworkFDLdcc 		INTEGER,
        sc553NetworkAISLoopdown 	INTEGER,
        sc553NetworkLoopbackConfig 	INTEGER,
        sc553NetworkLineCoding 		INTEGER,
        sc553NetworkFdl 		INTEGER 
    }





sc553NetworkConfigIndex OBJECT-TYPE
     SYNTAX SCinstance
     ACCESS read-only
     STATUS mandatory
     DESCRIPTION
         "The index value which uniquely identifies the interface to
         which this entry is applicable.  This has the form of a
         SCinstance which defines the slot, line, drop, and sub-identifier."
     ::= { sc553NetworkConfigEntry 1 }
 
sc553NetworkAdminLineType OBJECT-TYPE
    SYNTAX INTEGER {
        unframed(1),
        manEsf(2),
        manD4(3),
        auto(4)
    }
    ACCESS  read-write
    STATUS  mandatory
    DESCRIPTION
        "The values describe:
 
        'auto' indicates the unit will determine framing.
 
        'manEsf' indicates manual selection of extended superframe format.
 
        'manD4'indicates manual selection of D4 framing format.
 
        'unframed' indicates manual selection of unframed format."
    ::= { sc553NetworkConfigEntry 2 }

sc553NetworkOperLineType OBJECT-TYPE
    SYNTAX INTEGER {
        unframed(1),
        esf(2),
        d4(3)
    }
    ACCESS  read-only
    STATUS  mandatory
    DESCRIPTION
        "The values describe:
 
        'manEsf' indicates the current setting of Line type.
 
        'manD4'indicates the current setting of Line type.
 
        'unframed' indicates the current setting of Line type."
    ::= { sc553NetworkConfigEntry 3 }
 
sc553NetworkInterfaceType OBJECT-TYPE
     SYNTAX INTEGER {
         ds1(1),                        -- DS1 mode
         dsx1(2)                        -- DSX-1 mode
     }
     ACCESS read-write
     STATUS mandatory
     DESCRIPTION
         "The operating mode of the interface.  Setting the value of
         this object to ds1(1) configures the interface as
         standard DS1.  Setting the value of this object to
         dsx1(2) configures the interface to operate as a standard
         cross-connect DSX-1.
 
         This object interoperates with the sc553NetworkPreequalization
         object.  When this object is set to ds1(1), then the value of
         sc553NetworkPreequalization does not apply.
 
         This object interoperates with the sc553NetworkAdminLineBuildout object.
         When this object is set to dsx1(2), then the value of
         sc553NetworkLineBuildout does not apply."
     ::= { sc553NetworkConfigEntry 4 }
 
sc553NetworkPreequalization OBJECT-TYPE
     SYNTAX INTEGER {
         preeq130(1),           -- preequalization for 0 < 130 feet
         preeq260(2),           -- preequalization for 130 < 260 feet
         preeq390(3),           -- preequalization for 260 < 390 feet
         preeq530(4),           -- preequalization for 390 < 530 feet
         preeq655(5)            -- preequalization for 530 < 655 feet
     }
     ACCESS read-write
     STATUS mandatory
     DESCRIPTION
         "Is the preequalization of the transmitter of the interface.
 
         This object interoperates with the object
         sc553NetworkInterfaceType.  When the value of sc553NetworkInterfaceType
         is ds1(2) then this value is not applicable."
     ::= { sc553NetworkConfigEntry 5 }
 
sc553NetworkAdminLineBuildout OBJECT-TYPE
    SYNTAX INTEGER {
        man00dB(10),
        man75dB(11),
        man150dB(12),
        man225dB(13),
        auto(16)
    }
    ACCESS read-write
    STATUS mandatory
    DESCRIPTION
        "This variable is used to set the Transmit Ntwk
        Build-Out value on the network side and is only
        valid if the sc553NetworkInterfaceType is set for ds1(1).
        The values, in sequence, describe:

        auto(16) indicates auto detection of receive level to
        determine the appropriate Ntwk build out without controller intervention

        man00dB(10) indicates manual selection of 0.0 dB transmit Ntwk build out

        man75dB(11) indicates manual selection of -7.5 dB transmit Ntwk build out

        man150dB(12) indicates manual selection of -15.0 dB transmit Ntwk build out

        man225B(13) indicates manual selection of -22.5 dB transmit Ntwk build out"
    ::= { sc553NetworkConfigEntry 6 }
 
sc553NetworkOperLineBuildout OBJECT-TYPE
    SYNTAX INTEGER {
        tx00dB(2),
        tx75dB(3),
        tx150dB(4),
        tx225dB(5)
    }
    ACCESS read-only
    STATUS mandatory
    DESCRIPTION
        "This variable is used to report the current Ntwk
        build-out setting if the sc553NetworkInterfaceType is set for ds1(1).
 
       tx00dB(2) indicates the unit is set for 0.0 dB of attenuation
       when the sc553NetworkAdminLineBuildout is set for auto (16) or man00dB (10)

       tx75dB(3) indicates the unit is set for 7.5 dB of attenuation
       when the sc553NetworkAdminLineBuildout is set for auto (16) or man75dB (11)

       tx150dB(4) indicates the unit is set for -15.0 dB of attenuation
       when the sc553NetworkAdminLineBuildout is set for auto (16) or man150dB (12)

       tx225dB(5) indicates the unit is set for -22.5 dB of attenuation
       when the sc553NetworkAdminLineBuildout is set for auto (16) or man225dB (13)"
    ::= { sc553NetworkConfigEntry 7 }

sc553NetworkOnesDensity OBJECT-TYPE
     SYNTAX INTEGER {
         inhibit(1),                    -- no minimum ones density
         restrict8XNplus1(4),           -- minimum of N ones per 8(N+1) bits
         min1in8(5)                     -- minimum of 1 one per 8 bits
     }
     ACCESS read-write
     STATUS mandatory
     DESCRIPTION
         "The ones density restriction for the interface.  The values
         of this object define the ones density restriction that is
         enforced on the interface.
 
         The value inhibit(1) indicates that no ones density restriction
         is enforced.
 
         The value restrict8nX1(4) indicates a minimum of N ones per
         8(N+1) bits, where N is in the range 1 to 24.
 
         The value min1in8(5) indicates a minimum of 1 one per 8 bits.
         With this value, pulse density violations are enforced but not
         recorded."
     ::= { sc553NetworkConfigEntry 8 }
 
sc553NetworkTransmitClockSource OBJECT-TYPE
     SYNTAX INTEGER {
         receive(1),                    -- receive  transmit clock source
	 cascade(2),			-- cascade  transmit clock source
         internal(4),                   -- internal transmit clock source
         station(5),                    -- station  transmit clock source
         extChannelClkPPL(6)            -- channel  transmit clock source, ClockPPL
     }
     ACCESS read-write
     STATUS mandatory
     DESCRIPTION
         ""
     ::= { sc553NetworkConfigEntry 9 }
 
sc553NetworkFallbackClockSource OBJECT-TYPE
     SYNTAX INTEGER {
         receive   (1),                 -- receive  fallback clock source
	 cascade   (2),			-- cascade  fallback clock source
         internal  (4)                  -- internal fallback clock source
     }
     ACCESS read-write
     STATUS mandatory
     DESCRIPTION
         ""
    ::= { sc553NetworkConfigEntry 10 }
 
sc553NetworkFDLdcc OBJECT-TYPE
     SYNTAX INTEGER {
         enabled(1),
         disabled(2)
     }
     ACCESS read-write
     STATUS mandatory
     DESCRIPTION
         "Controls whether or not the DCC uses the FDL as its
         transport.  The FDL is only available when the DS1 line type
         is ESF, a full DS1 interface is being used, and transportation
         of the FDL completely through the network is supported.
 
         The value enabled(1) enables the transportation of the DCC
         using the FDL.  The value disabled(2) disables the use of the
         FDL to transport the DCC, which implies that the DCC is
         transported by some other means.
 
         This object interoperates with the sc553NetworkLineType object.  The
         value of this object can be set to enabled(1) only when the
         value of the sc553NetworkLineType is one of the ESF values."
     ::= { sc553NetworkConfigEntry 11 }
 
sc553NetworkAISLoopdown OBJECT-TYPE
     SYNTAX INTEGER (4..60)             -- 4, 5..60 seconds
     ACCESS read-write
     STATUS mandatory
     DESCRIPTION
         "The time in seconds when receiving a continuous AIS signal
         before a remotely initiated loopback is terminated.  When this
         object has the value 4, then there is no time limit and the
         loop must be terminated by remotely issued in-band loopdown
         codes.  When the object has a value between 5 and 60, then
         this is time in seconds of continuous AIS signal before
         the loopback is terminated."
     ::= { sc553NetworkConfigEntry 12 }
 
 
sc553NetworkLoopbackConfig OBJECT-TYPE
    SYNTAX INTEGER {
        none(1),
        payload(2),
        lineloop(3)
    }
    ACCESS read-write
    STATUS mandatory
    DESCRIPTION
        "This variable is used to set the
        In-Band DS1 Loopback Code Detection.
 
        none(1) refers to when the in-band
        loopback codes are ignored.
 
        payload(2) designates a payload loopback is done 
	upon recognition of the inband loopback code.
 
        lineloop(3) designates a line loopback is done 
	upon recognition of the inband loopback code."

    ::= { sc553NetworkConfigEntry 13 }
 


sc553NetworkLineCoding OBJECT-TYPE
    SYNTAX  INTEGER {
        sc553B8ZS (1),
        sc553AMI (2)
    }
    ACCESS  read-write
    STATUS  mandatory
    DESCRIPTION
        "This variable describes the  variety  of  Zero
        Code  Suppression  used  on  the link, which in
        turn affects a number of its characteristics.

        sc553B8ZS refers to the use of a specified  pat-
        tern  of  normal  bits  and  bipolar violations
        which are used to replace a sequence  of  eight
        zero bits.

        sc553AMI refers to a mode wherein no  zero  code
        suppression  is  present  and the line encoding
        does not solve the problem directly.   In  this
        application, the higher layer must provide data
        which meets or exceeds the  pulse  density  re-
        quirements, such as inverting HDLC data."
    ::= { sc553NetworkConfigEntry 14 }

sc553NetworkFdl OBJECT-TYPE
    SYNTAX  INTEGER {
        sc553Fdl-none(1),
        sc553Ansi-T1-403(2),
        sc553Att-54016(3)
    }
    ACCESS  read-write
    STATUS  mandatory
    DESCRIPTION
        "This bitmap describes the use of  the  facili-
        ties data link, and is the sum of the capabili-
        ties:

        sc553Fdl-none(1) indicates that the device  does
        not use the FDL.
 
        sc553Ansi-T1-403(2) refers to the  FDL  exchange
        recommended by ANSI.
 
        sc553Att-54016(3) refers to ESF FDL exchanges."
     ::= { sc553NetworkConfigEntry 15 }
 

-- 
--
--                     Cascade Configuration table
-- 


sc553CascadeConfigTable OBJECT-TYPE
    SYNTAX SEQUENCE OF Sc553CascadeConfigEntry
    ACCESS not-accessible
    STATUS mandatory
    DESCRIPTION
    "The GDC 553 Cascade Configuration table."
    ::= { sc553Configuration 4 }
 
 
sc553CascadeConfigEntry OBJECT-TYPE
    SYNTAX Sc553CascadeConfigEntry
    ACCESS not-accessible
    STATUS mandatory
    DESCRIPTION
    "The sc553 Cascade Configuration table entry."
    INDEX { sc553CascadeConfigIndex }
    ::= { sc553CascadeConfigTable 1 }
 
 
Sc553CascadeConfigEntry ::=
    SEQUENCE {
        sc553CascadeConfigIndex 	SCinstance,
        sc553CascadeAdminLineType 	INTEGER,
        sc553CascadeOperLineType 	INTEGER,
        sc553CascadeInterfaceType 	INTEGER,
        sc553CascadePreequalization 	INTEGER,
        sc553CascadeAdminLineBuildout 	INTEGER,
        sc553CascadeOperLineBuildout 	INTEGER,
        sc553CascadeFDLdcc 		INTEGER,
        sc553CascadeLineCoding 		INTEGER,
        sc553CascadeFdl 		INTEGER, 
	sc553CascadeInService		INTEGER,
        sc553CascadeAISLoopdown		INTEGER, 
	sc553CascadeLoopbackConfig	INTEGER
    }

sc553CascadeConfigIndex OBJECT-TYPE
     SYNTAX SCinstance
     ACCESS read-only
     STATUS mandatory
     DESCRIPTION
         "The index value which uniquely identifies the interface to
         which this entry is applicable.  This has the form of a
         SCinstance which defines the slot, line, drop, and sub-identifier."
     ::= { sc553CascadeConfigEntry 1 }
 
sc553CascadeAdminLineType OBJECT-TYPE
    SYNTAX INTEGER {
        unframed(1),
        manEsf(2),
        manD4(3),
        auto(4)
    }
    ACCESS  read-write
    STATUS  mandatory
    DESCRIPTION
        "The values describe:
 
        'auto' indicates the unit will determine framing.
 
        'manEsf' indicates manual selection of extended superframe format.
 
        'manD4'indicates manual selection of D4 framing format.
 
        'unframed' indicates manual selection of unframed format."
    ::= { sc553CascadeConfigEntry 2 }

sc553CascadeOperLineType OBJECT-TYPE
    SYNTAX INTEGER {
        unframed(1),
        esf(2),
        d4(3)
    }
    ACCESS  read-only
    STATUS  mandatory
    DESCRIPTION
        "The values describe:
 
        'manEsf' indicates the current setting of Line type.
 
        'manD4'indicates the current setting of Line type.
 
        'unframed' indicates the current setting of Line type."
    ::= { sc553CascadeConfigEntry 3 }
 
sc553CascadeInterfaceType OBJECT-TYPE
     SYNTAX INTEGER {
         ds1(1),                        -- DS1 mode
         dsx1(2)                        -- DSX-1 mode
     }
     ACCESS read-write
     STATUS mandatory
     DESCRIPTION
         "The operating mode of the interface.  Setting the value of
         this object to ds1(1) configures the interface as
         standard DS1.  Setting the value of this object to
         dsx1(2) configures the interface to operate as a standard
         cross-connect DSX-1.
 
         This object interoperates with the sc553CascadePreequalization
         object.  When this object is set to ds1(1), then the value of
         sc553CascadePreequalization does not apply.
 
         This object interoperates with the sc553CascadeAdminLineBuildout object.
         When this object is set to dsx1(2), then the value of
         sc553CascadeLineBuildout does not apply."
     ::= { sc553CascadeConfigEntry 4 }
 
sc553CascadePreequalization OBJECT-TYPE
     SYNTAX INTEGER {
         preeq130(1),           -- preequalization for 0 < 130 feet
         preeq260(2),           -- preequalization for 130 < 260 feet
         preeq390(3),           -- preequalization for 260 < 390 feet
         preeq530(4),           -- preequalization for 390 < 530 feet
         preeq655(5)            -- preequalization for 530 < 655 feet
     }
     ACCESS read-write
     STATUS mandatory
     DESCRIPTION
         "Is the preequalization of the transmitter of the interface.
 
         This object interoperates with the object
         sc553CascadeInterfaceType.  When the value of sc553CascadeInterfaceType
         is ds1(2) then this value is not applicable."
     ::= { sc553CascadeConfigEntry 5 }
 
sc553CascadeAdminLineBuildout OBJECT-TYPE
    SYNTAX INTEGER {
        man00dB(10),
        man75dB(11),
        man150dB(12),
        man225dB(13),
        auto(16)
    }
    ACCESS read-write
    STATUS mandatory
    DESCRIPTION
        "This variable is used to set the Transmit Ntwk
        Build-Out value on the cascade side and is only
        valid if the sc553CascadeInterfaceType is set for ds1(1).
        The values, in sequence, describe:

        auto(16) indicates auto detection of receive level to
        determine the appropriate Ntwk build out without controller intervention

        man00dB(10) indicates manual selection of 0.0 dB transmit Ntwk build out

        man75dB(11) indicates manual selection of -7.5 dB transmit Ntwk build out

        man150dB(12) indicates manual selection of -15.0 dB transmit Ntwk build out

        man225B(13) indicates manual selection of -22.5 dB transmit Ntwk build out"
    ::= { sc553CascadeConfigEntry 6 }
 
sc553CascadeOperLineBuildout OBJECT-TYPE
    SYNTAX INTEGER {
        tx00dB(2),
        tx75dB(3),
        tx150dB(4),
        tx225dB(5)
    }
    ACCESS read-only
    STATUS mandatory
    DESCRIPTION
        "This variable is used to report the current Ntwk
        build-out setting if the sc553CascadeInterfaceType is set for ds1(1).
 
       tx00dB(2) indicates the unit is set for 0.0 dB of attenuation
       when the sc553CascadeAdminLineBuildout is set for auto (16) or man00dB (10)

       tx75dB(3) indicates the unit is set for 7.5 dB of attenuation
       when the sc553CascadeAdminLineBuildout is set for auto (16) or man75dB (11)

       tx150dB(4) indicates the unit is set for -15.0 dB of attenuation
       when the sc553CascadeAdminLineBuildout is set for auto (16) or man150dB (12)

       tx225dB(5) indicates the unit is set for -22.5 dB of attenuation
       when the sc553CascadeAdminLineBuildout is set for auto (16) or man225dB (13)"
    ::= { sc553CascadeConfigEntry 7 }

  
 
sc553CascadeFDLdcc OBJECT-TYPE
     SYNTAX INTEGER {
         enabled(1),
         disabled(2)
     }
     ACCESS read-write
     STATUS mandatory
     DESCRIPTION
         "Controls whether or not the DCC uses the FDL as its
         transport.  The FDL is only available when the DS1 line type
         is ESF, a full DS1 interface is being used, and transportation
         of the FDL completely through the cascade is supported.
 
         The value enabled(1) enables the transportation of the DCC
         using the FDL.  The value disabled(2) disables the use of the
         FDL to transport the DCC, which implies that the DCC is
         transported by some other means.
 
         This object interoperates with the sc553CascadeLineType object.  The
         value of this object can be set to enabled(1) only when the
         value of the sc553CascadeLineType is one of the ESF values."
     ::= { sc553CascadeConfigEntry 8  }
 
 

sc553CascadeLineCoding OBJECT-TYPE
    SYNTAX  INTEGER {
        sc553B8ZS (1),
        sc553AMI (2)
    }
    ACCESS  read-write
    STATUS  mandatory
    DESCRIPTION
        "This variable describes the  variety  of  Zero
        Code  Suppression  used  on  the link, which in
        turn affects a number of its characteristics.

        sc553B8ZS refers to the use of a specified  pat-
        tern  of  normal  bits  and  bipolar violations
        which are used to replace a sequence  of  eight
        zero bits.

        sc553AMI refers to a mode wherein no  zero  code
        suppression  is  present  and the line encoding
        does not solve the problem directly.   In  this
        application, the higher layer must provide data
        which meets or exceeds the  pulse  density  re-
        quirements, such as inverting HDLC data."
    ::= { sc553CascadeConfigEntry  9 }

sc553CascadeFdl OBJECT-TYPE
    SYNTAX  INTEGER {
        sc553Fdl-none(1),
        sc553Ansi-T1-403(2),
        sc553Att-54016(3)
    }
    ACCESS  read-write
    STATUS  mandatory
    DESCRIPTION
        "This bitmap describes the use of  the  facili-
        ties data link, and is the sum of the capabili-
        ties:

        sc553Fdl-none(1) indicates that the device  does
        not use the FDL.
 
        sc553Ansi-T1-403(2) refers to the  FDL  exchange
        recommended by ANSI.
 
        sc553Att-54016(3) refers to ESF FDL exchanges."
     ::= { sc553CascadeConfigEntry 10 }
 
sc553CascadeInService OBJECT-TYPE
    SYNTAX  INTEGER {
        on(1),
        off(2)
    }
    ACCESS  read-write
    STATUS  mandatory
    DESCRIPTION
        ""
     ::= { sc553CascadeConfigEntry 11 }
 
sc553CascadeAISLoopdown OBJECT-TYPE
     SYNTAX INTEGER (4..60)             -- 4, 5..60 seconds
     ACCESS read-write
     STATUS mandatory
     DESCRIPTION
         "The time in seconds when receiving a continuous AIS signal
         before a remotely initiated loopback is terminated.  When this
         object has the value 4, then there is no time limit and the
         loop must be terminated by remotely issued in-band loopdown
         codes.  When the object has a value between 5 and 60, then
         this is time in seconds of continuous AIS signal before
         the loopback is terminated."
     ::= { sc553CascadeConfigEntry 12 }
 
 
sc553CascadeLoopbackConfig OBJECT-TYPE
    SYNTAX INTEGER {
        none(1),
        payload(2),
        lineloop(3)
    }
    ACCESS read-write
    STATUS mandatory
    DESCRIPTION
        "This variable is used to set the
        In-Band DS1 Loopback Code Detection.
 
        none(1) refers to when the in-band
        loopback codes are ignored.
 
        payload(2) designates a payload loopback is done 
	upon recognition of the inband loopback code.
 
        lineloop(3) designates a line loopback is done 
	upon recognition of the inband loopback code."

    ::= { sc553CascadeConfigEntry 13 }
 

 

-- 
--
--                    Network/ Channel Save
-- 





sc553ConfigurationSave OBJECT-TYPE
    SYNTAX INTEGER {
          norm(1),		-- read-only
          saveall(2)        	-- write-only
    }
    ACCESS read-write
    STATUS mandatory
    DESCRIPTION
        "This variable is used to set the update status flag for saving 
	network and channel configuration settings.
        
	Management can only set a saveall(2).

	A norm(1) will always be read.
	
	Configuration settings are not saved to network element by default.
	This permits the configuration of several objects before saving.  
	After all objects are set-up, a (2) must be sent.  This will
	enable and save the new configuration(s).
	
 	"

    ::= { sc553Configuration 3 }
 











-- ****************************************************************************
--                        Diagnostics table
-- ****************************************************************************

sc553DiagTable OBJECT-TYPE
    SYNTAX SEQUENCE OF Sc553DiagEntry
    ACCESS not-accessible
    STATUS mandatory
    DESCRIPTION
        "The SC553 Diagnostics table."
    ::= { sc553Diagnostics 1 }
 
sc553DiagEntry OBJECT-TYPE
    SYNTAX Sc553DiagEntry
    ACCESS not-accessible
    STATUS mandatory
    DESCRIPTION
        "The SNMP553S Diagnostics table entry."
    INDEX { sc553DiagIndex }
    ::= { sc553DiagTable 1 }
 
Sc553DiagEntry ::=
    SEQUENCE {
        sc553DiagIndex 			SCinstance,
        sc553DiagTestDuration 		INTEGER,
        sc553DiagProgPattern 		INTEGER,
        sc553InsertBitError 		INTEGER,
        sc553DiagDS0Number 		INTEGER,
        sc553DiagT1SelfTestPattern 	INTEGER,
        sc553DiagT1Test 		INTEGER,
        sc553DiagDS0SelfTestPattern 	INTEGER,
        sc553DiagDS0Test 		INTEGER,
        sc553DiagChannelSelfTestPattern INTEGER,
        sc553DiagChannelTest 		INTEGER,
        sc553DiagTestResults  		OCTET STRING,
	sc553DiagTestStatus 		INTEGER,
	sc553DiagResetTestToNormal 	INTEGER,
	sc553DiagResetTestResults	INTEGER,
	sc553DiagT1TestDirection 	INTEGER,
	sc553DiagDS0TestDirection	INTEGER
	
 }

sc553DiagIndex OBJECT-TYPE
    SYNTAX SCinstance
    ACCESS read-only
    STATUS mandatory
    DESCRIPTION
        "The index value which uniquely identifies the interface to
        which this entry is applicable.  This has the form of a
        SCinstance which defines the slot, line, drop, and sub-identifier,
        which in this case is a network interface."
    ::= { sc553DiagEntry 1 }
 
sc553DiagTestDuration OBJECT-TYPE
    SYNTAX INTEGER     {
	testTime30Secs(1),
        testTime1Min(2),
        testTime2Mins(3),
        testTime3Mins(4),
        testTime4Mins(5),
        testTime5Mins(6),
        testTime6Mins(7),
        testTime7Mins(8),
        testTime8Mins(9),
        testTime9Mins(10),
        testTime10Mins(11),
        testTime15Mins(12),
        testTime20Mins(13),
        testTime25Mins(14),
        testTime30Mins(15),
	testTimeInfinite(16)
    }
    ACCESS read-write
    STATUS mandatory
    DESCRIPTION
        "Selects the duration to run a diagnostic test.  
	"

    ::= { sc553DiagEntry 2 }




sc553DiagProgPattern OBJECT-TYPE
     SYNTAX INTEGER (0..'ffff'h)
     ACCESS read-write
     STATUS mandatory
     DESCRIPTION
        "The 16 bit user programmable test pattern.  This object
        works with the  sc553DiagT1SelfTestPattern object in that when it
        is set to t1ProgPattern(4), the the value of this object is
        used as the 16 bit user programmable test pattern.
 
        This object is used for all tests defined in both the GDC
        dsx1 mib."
 
     ::= { sc553DiagEntry 3}




sc553InsertBitError OBJECT-TYPE
    SYNTAX INTEGER {

	insertBitErrorNorm(1),		-- Read Only
	insertOneBitError(2)		         	

    }
    ACCESS read-write
    STATUS mandatory
    DESCRIPTION "A set of 2 will insert one bit error for test.
		Management may only write a 2.  A 1 will always be read.
	"
    ::= { sc553DiagEntry 4 }




sc553DiagDS0Number OBJECT-TYPE
    SYNTAX INTEGER (1..24)
    ACCESS read-write
    STATUS mandatory
    DESCRIPTION
        "Indicates the DS0 number for the test.  The valid range is between
	one (1) and twenty-four (24)."
    ::= { sc553DiagEntry 5 }
 

sc553DiagT1SelfTestPattern OBJECT-TYPE
    SYNTAX INTEGER {

	t1511Pattern(1),		 
	t12047Pattern(2),		 
	t1QRSPattern(3),		 
	t1ProgPattern(4),		 
	t13in24(5)     		         
   }
    ACCESS read-write
    STATUS mandatory
    DESCRIPTION "The selected option is used when a sc553DiagT1Test is performed.
                 
	"
    ::= { sc553DiagEntry 6 }


sc553DiagT1Test OBJECT-TYPE
    SYNTAX INTEGER {

	t1SelfTest(1),			-- Network:  	Self Tests
	t1LocalSelfTest(2),		--
	t1RemoteSelfTest(3),		--
	t1LocalTest(4),		        -- 		Loopbacks
	t1RemoteTest(5),		-- 
	t1NetworkInterface(6),		--
	t1LineLoopback(7),		--
	t1PayLoadLoopback(8),		--
	t1NoTest(9)		        -- No T1 Test Running
    }
    ACCESS read-write
    STATUS mandatory
    DESCRIPTION "


	"
    ::= { sc553DiagEntry 7 }

sc553DiagDS0SelfTestPattern OBJECT-TYPE
    SYNTAX INTEGER {

	ds0511Pattern(1),		
	ds02047Pattern(2) 		
   }
    ACCESS read-write
    STATUS mandatory
    DESCRIPTION "The selected option is used when a sc553DiagDS0Test is performed.
                
	"
    ::= { sc553DiagEntry 8 }



sc553DiagDS0Test OBJECT-TYPE
    SYNTAX INTEGER {

	ds0SelfTest(1),			-- DS0 Self Test
	ds0CircuitDelay(2),		-- Circuit Delay
	ds0Loopback(3),  		-- Loopback
	ds0NoDS0Test(4)			-- No DS0 Test Running
    }
    ACCESS read-write
    STATUS mandatory
    DESCRIPTION "


	"
    ::= { sc553DiagEntry 9 }

sc553DiagChannelSelfTestPattern OBJECT-TYPE
    SYNTAX INTEGER {

	chan511Pattern(1),		
	chan2047Pattern(2) 		 
   }
    ACCESS read-write
    STATUS mandatory
    DESCRIPTION "The selected option is used when a sc553DiagChannelTest is performed.
                 
	"
    ::= { sc553DiagEntry 10 }


sc553DiagChannelTest OBJECT-TYPE
    SYNTAX INTEGER {

	chanSelfTest(1),		-- Channel Self Test
	chanLocalSelfTest(2),		--
	chanRemoteSelfTest(3),		--
	chandigitalLoop(4),		-- Loopbacks
	chanLocalLoop(5),  		-- 
	chanRemoteDataLoop(6),          --
	chanNoTest(7) 			-- No Channel Test 
    }
    ACCESS read-write
    STATUS mandatory
    DESCRIPTION " Reading will indicate the 


	"
    ::= { sc553DiagEntry 11 }


sc553DiagTestResults OBJECT-TYPE
    SYNTAX OCTET STRING (SIZE(4))
    ACCESS read-only
    STATUS mandatory
    DESCRIPTION
   "Returns a the folowing bytes.
 		Octet 1         bit 7 - parity
				bit 6 - f/u           
				bit 5 - 1: Circuit Delay Results or 0: for Bit Error Count	
				bit 4 - 1: Test is in Progress, 0: Test not in progress
				bit 3 - 1: Remote Test did not loop
				bit 2 - 1: Remote Digital Loop did not loop
				bit 1 - 1: No Sync
				bit 0 - 1: Bit Over Range

		Octet 2         bit 7 - parity
				bit 6 - f/u       
				bit 5 - 2^19	Bit Error Count	/ Circuit Delay ms
				bit 4 - 2^18
				bit 3 - 2^17
				bit 2 - 2^16
				bit 1 - 2^15
				bit 0 - 2^14

		Octet 3         bit 7 - parity
				bit 6 - 2^13
				bit 5 - 2^12
				bit 4 - 2^11
				bit 3 - 2^10
				bit 2 - 2^9
				bit 1 - 2^8
				bit 0 - 2^7

		Octet 4         bit 7 - parity
				bit 6 - 2^6
				bit 5 - 2^5
				bit 4 - 2^4
				bit 3 - 2^3
				bit 2 - 2^2
				bit 1 - 2^1
				bit 0 - 2^0
	"
    ::= { sc553DiagEntry 12 }



sc553DiagTestStatus OBJECT-TYPE
    SYNTAX INTEGER {
	statNoTestinProgress(1),		-- No test in progress

	statT1SelfTest(2),			-- Self Tests
	statT1LocalSelfTest(3),			--
	statT1RemoteSelfTest(4),		--
	statT1LocalTest(5),		        -- Loopbacks
	statT1RemoteTest(6),			-- 
	statT1NetworkInterface(7),		--
	statT1LineLoopback(8),			--
	statT1PayLoadLoopback(9),		--

	statChanSelfTest(10),			-- Channel Self Test
	statChanLocalSelfTest(11),		--
	statChanRemoteSelfTest(12),		--
	statChandigitalLoop(13),		-- Loopbacks
	statChanLocalLoop(14),  		-- 
	statChanRemoteDataLoop(15),          	--

	statDS0SelfTest(16),			-- DS0 Self Test
	statDS0CircuitDelay(17),		-- Loopbacks
	statDS0Loopback(18)			-- 
   }
    ACCESS read-only
    STATUS mandatory
    DESCRIPTION
        "This object will return the test current test in progress, if any."
    ::= { sc553DiagEntry 13}



sc553DiagResetTestToNormal OBJECT-TYPE
    SYNTAX INTEGER {
        normal(1),      -- read only
        resetTest(2)    -- write only
    }
    ACCESS read-write
    STATUS mandatory
    DESCRIPTION
        "This object will halt the execution of any and all
        diagnostic test that may be running with the exception
        of the Network Delay Test."
    ::= { sc553DiagEntry 14 }




sc553DiagResetTestResults OBJECT-TYPE
    SYNTAX INTEGER {
        normal(1),            -- read only
        resetTestResult(2)    -- write only
    }
    ACCESS read-write
    STATUS mandatory
    DESCRIPTION
        "This object will clear the results register while 
	running any test except for Network Delay.
	
 	Starting a new test will automatically zero out
	the register. 

	A normal(1) will always be read.  Management will set a
	resetTestResult(2) to reset the test results.
	"
    ::= { sc553DiagEntry 15 }


sc553DiagT1TestDirection OBJECT-TYPE
    SYNTAX INTEGER {
        toNetwork(1),    
        toCascade(2)     
    }
    ACCESS read-write
    STATUS mandatory
    DESCRIPTION
        "Selects the test direction for T1 tests."
    ::= { sc553DiagEntry 16}


sc553DiagDS0TestDirection OBJECT-TYPE
    SYNTAX INTEGER {
        toNetwork(1),    
        toCascade(2)     
    }
    ACCESS read-write
    STATUS mandatory
    DESCRIPTION
        "Selects the test direction for DS0 tests."
    ::= { sc553DiagEntry 17}



-- ****************************************************************************
--                        Maintenance Table
-- ****************************************************************************


sc553MaintenanceTable OBJECT-TYPE
    SYNTAX SEQUENCE OF Sc553MaintenanceEntry
    ACCESS not-accessible
    STATUS mandatory
    DESCRIPTION
    "The table describes the maintenance functions for the sc553. "
    ::= { sc553Maintenance 1 }


sc553MaintenanceEntry OBJECT-TYPE
    SYNTAX Sc553MaintenanceEntry
    ACCESS not-accessible
    STATUS mandatory
    DESCRIPTION
    "An entry in the GDC maintenance Table"
    INDEX { sc553MaintenanceIndex }
    ::= { sc553MaintenanceTable 1 }


Sc553MaintenanceEntry ::=
SEQUENCE {
	sc553MaintenanceIndex      SCinstance,
	sc553LedStatus             OCTET STRING,
        sc553SoftReset             INTEGER,
	sc553DefaultInit           INTEGER,
	sc553FrontPanel            INTEGER,
        sc553ProductType           INTEGER,
        sc553ResetStatistics       INTEGER,
        sc553ValidUserIntervals    INTEGER,
        sc553ValidNetworkIntervals INTEGER,
        sc553ValidFarEndIntervals  INTEGER,
        sc553CascadePresent        INTEGER,
        sc553ReceiveLevel          INTEGER,
	sc553DteStat		   OCTET STRING,		
        sc553CasReceiveLevel       INTEGER,
	sc553ShelfType		   INTEGER,
	sc553TwinPackPowerSupply   INTEGER,
	sc553TestAllLeds	   INTEGER		
 }

sc553MaintenanceIndex OBJECT-TYPE
    SYNTAX SCinstance
    ACCESS read-only
    STATUS mandatory
    DESCRIPTION
     "The index value: slot, line, drop, and interface"
    ::= { sc553MaintenanceEntry 1 }


sc553LedStatus OBJECT-TYPE
    SYNTAX OCTET STRING (SIZE(3))
    ACCESS read-only
    STATUS mandatory
    DESCRIPTION
   "Returns a bitwise snapshot of the front panel LED state and front panel switches.
 		Octet 1         bit 7 - not used
				bit 6 - ON           (0:LED inactive   1:LED active)
				bit 5 - f/u   
				bit 4 - RSP   
				bit 3 - f/u   
				bit 2 - f/u
				bit 1 - f/u    
				bit 0 - f/u    

		Octet 2         bit 7 - not used
				bit 6 - NET OOF
				bit 5 - NET NS 
				bit 4 - NET BPV
				bit 3 - NET AIS
				bit 2 - TM     
				bit 1 - ALM
				bit 0 - f/u       

		Octet 3         bit 7 - not used
				bit 6 - CHA SD
				bit 5 - CHA RD
				bit 4 - INS   
				bit 3 - CH     
				bit 2 - T1     
				bit 1 - RL    
				bit 0 - EQP        
	"
    ::= { sc553MaintenanceEntry 2 }


sc553SoftReset	OBJECT-TYPE
     SYNTAX INTEGER
     {
          norm(1),          		-- read-only
          reset(2) 			-- write-only
     }
     ACCESS read-write
     STATUS mandatory
     DESCRIPTION
     "Supports the action of soft resetting the unit.  When this
     object is set to reset(1), then the unit performs a soft reset.
     The value norm will be returned when the reset is complete.
     The value of norm can not be set by management."
     ::= { sc553MaintenanceEntry 3 }

sc553DefaultInit OBJECT-TYPE
     SYNTAX INTEGER
     {
         normal(1),			-- read-only
         factoryDefault(2) 		-- write-only
     }
     ACCESS read-write
     STATUS mandatory
     DESCRIPTION
     "This is used to allow the NonVolatile Configuration to be set to
     a factory default state.  When this value is set to factoryDefault,
     the unit will reset to the default configuration. The value of normal
     will be returned when the initialization is complete. The value normal
     can not be set by management."
     ::= { sc553MaintenanceEntry 4 }


sc553FrontPanel OBJECT-TYPE
     SYNTAX INTEGER
     {
         inhibit(1),
         enable(2)
     }
     ACCESS read-write
     STATUS mandatory
     DESCRIPTION
     "This variable is used to indicate whether the front
     panel switches are operational or not."
     ::= { sc553MaintenanceEntry 5 }

sc553ProductType OBJECT-TYPE
    SYNTAX INTEGER {
        sc553(1)
    }
    ACCESS read-only
    STATUS mandatory
    DESCRIPTION
        "Indicates the product type of the unit."
    ::= { sc553MaintenanceEntry 6 }

sc553ResetStatistics OBJECT-TYPE
    SYNTAX  INTEGER {
        norm(1),   -- read only
        reset(2)   -- write only
    }
    ACCESS  read-write
    STATUS  mandatory
    DESCRIPTION
        "Supports the action of soft resetting the sc553ValidIntervals
        object.  When this object is set to reset(2), then the unit
        will reset the sc553ValidIntervals object to zero.
        The value of norm(1) can not be set by management."
    ::= { sc553MaintenanceEntry 7 }

sc553ValidUserIntervals OBJECT-TYPE
    SYNTAX  INTEGER (0..96)
    ACCESS  read-only
    STATUS  mandatory
    DESCRIPTION
        "The number of  previous  User intervals  for  which
        valid data was collected.  The value will be 96
        unless the interface was brought on-line within
        the last 24 hours, in which case the value will
        be the number of complete 15  minute  intervals
        the since interface has been online."
    ::= { sc553MaintenanceEntry 8 }
 
sc553ValidNetworkIntervals OBJECT-TYPE
    SYNTAX  INTEGER (0..96)
    ACCESS  read-only
    STATUS  mandatory
    DESCRIPTION
        "The number of  previous  Network intervals  for  which
        valid data was collected.  The value will be 96
        unless the interface was brought on-line within
        the last 24 hours, in which case the value will
        be the number of complete 15  minute  intervals
        the since interface has been online."
    ::= { sc553MaintenanceEntry 9 }
 
sc553ValidFarEndIntervals OBJECT-TYPE
    SYNTAX  INTEGER (0..96)
    ACCESS  read-only
    STATUS  mandatory
    DESCRIPTION
        "The number of  previous  Far End intervals  for  which
        valid data was collected.  The value will be 96
        unless the interface was brought on-line within
        the last 24 hours, in which case the value will
        be the number of complete 15  minute  intervals
        the since interface has been online."
    ::= { sc553MaintenanceEntry 10}
 
sc553CascadePresent OBJECT-TYPE
    SYNTAX INTEGER {
        notPresent(1),                  -- cascade interface not present
        present(2)                      -- cascade interface present
    }
    ACCESS read-only
    STATUS mandatory
    DESCRIPTION
        "Identifies whether or not the cascade interface cards
        are installed."
    ::= { sc553MaintenanceEntry 11}

sc553ReceiveLevel    OBJECT-TYPE
    SYNTAX INTEGER {
	invalidNiDSX1(1),
	noSignal(2),
	pos2toNeg7andOneHalf(3),
	neg7andOneHalftoNeg15(4),
	neg15toNeg22andOneHalf(5),
	lessThanNeg22andOneHalf(6)				
     }
    ACCESS read-only
    STATUS mandatory
    DESCRIPTION
        " invalidNiDSX1(1) indicates an invalid request because the Network Interface
	  is configured as DSX-1.  noSignal(2) is present when there is no T1 signal
	  detected (NS led on front panel will be on).

	  The last 4 options (3) - (6) indicate the ranges for receive level:

		(3):	+2db   to -7.5db
		(4):	-7.5db to -15db
		(5):	-15db  to -22.5db
		(6):	less than -22.5db

		"

      ::= { sc553MaintenanceEntry 12 }

sc553DteStat OBJECT-TYPE
        SYNTAX  OCTET STRING (SIZE(2))
        ACCESS  read-only
        STATUS  mandatory
        DESCRIPTION
        "Returns a bitwise snapshot of the DTE signals.

        Octet 1 bit 7 - not used
                bit 6 - CTS     (1:ON; 0:OFF)
                bit 5 - RTS     (1:ON; 0:OFF)
                bit 4 - DTR     (1:ON; 0:OFF)
                bit 3 - DSR     (1:ON; 0:OFF)
                bit 2 - future use 
                bit 1 - DCD     (1:ON; 0:OFF)
                bit 0 - future use
 
        Octet 2 bit 7 - not used
                bit 6 - RXC     (1:Transitions)
                bit 5 - DCD     (1:Transitions)
                bit 4 - RTS     (1:Transitions)
                bit 3 - CTS     (1:Transitions)
                bit 2 - RXD     (1:Transitions)
                bit 1 - TXC     (1:Transitions)
                bit 0 - TXD     (1:Transitions)"
    ::= { sc553MaintenanceEntry 13 }
 




sc553CasReceiveLevel    OBJECT-TYPE
    SYNTAX INTEGER {
	invalidNiDSX1(1),
	noSignal(2),
	pos2toNeg7andOneHalf(3),
	neg7andOneHalftoNeg15(4),
	neg15toNeg22andOneHalf(5),
	lessThanNeg22andOneHalf(6)				
     }
    ACCESS read-only
    STATUS mandatory
    DESCRIPTION
        " invalidNiDSX1(1) indicates an invalid request because the Cascade Interface
	  is configured as DSX-1.  noSignal(2) is present when there is no T1 signal
	  detected (NS led on front panel will be on).

	  The last 4 options (3) - (6) indicate the ranges for receive level:

		(3):	+2db   to -7.5db
		(4):	-7.5db to -15db
		(5):	-15db  to -22.5db
		(6):	less than -22.5db

		"

      ::= { sc553MaintenanceEntry 14 }
 

sc553ShelfType OBJECT-TYPE
     SYNTAX INTEGER
     {
         spectracomm(1),
         twinPack(2)
     }
     ACCESS read-only
     STATUS mandatory
     DESCRIPTION
     "Type of shelf the sc553 is located in."
     ::= { sc553MaintenanceEntry 15 }

sc553TwinPackPowerSupply OBJECT-TYPE
     SYNTAX INTEGER
     {
	 none(1),
         bottomOnly(2),
         topOnly(3),
	 both(4)
     }
     ACCESS read-only
     STATUS mandatory
     DESCRIPTION
     "Power supplies currently installed in Twin Pack. When the sc553 is located in
      a Spectracomm shelf none(1) will always be returned."
     ::= { sc553MaintenanceEntry 16 }


sc553TestAllLeds OBJECT-TYPE
     SYNTAX INTEGER
     {
         allLedsON(1),
         allLedsOFF(2)
     }
     ACCESS read-write
     STATUS mandatory
     DESCRIPTION
     "This variable is used to test the front panel leds and individual 
      segments of the display.  A one (1) will turn all leds and display 
      segments on.  They will remain on until a two (2) is set or the card is 
      rebooted" 
     ::= { sc553MaintenanceEntry 17 }




-- ****************************************************************************
--                     Alarm Tables
-- ****************************************************************************

-- 
--
--                     Alarm Object Identifier Definitions
-- 


sc553AlarmData	             	OBJECT IDENTIFIER ::= { sc553Alarms 1 }

sc553NoResponseAlm           	OBJECT IDENTIFIER ::= { sc553AlarmData 1 }
sc553DiagRxErrAlm            	OBJECT IDENTIFIER ::= { sc553AlarmData 2 }
sc553PowerUpAlm              	OBJECT IDENTIFIER ::= { sc553AlarmData 3 }
sc553NvRamCorruptAlm         	OBJECT IDENTIFIER ::= { sc553AlarmData 4 }
sc553UnitFailureAlm          	OBJECT IDENTIFIER ::= { sc553AlarmData 5 }
sc553StatusChangeAlm         	OBJECT IDENTIFIER ::= { sc553AlarmData 6 }
sc553UnsolicitedTestAlm      	OBJECT IDENTIFIER ::= { sc553AlarmData 7  }
sc553FrontPanelTestAlm       	OBJECT IDENTIFIER ::= { sc553AlarmData 8  }
sc553ConfigChangeAlm         	OBJECT IDENTIFIER ::= { sc553AlarmData 9  }
sc553TimingLossAlm           	OBJECT IDENTIFIER ::= { sc553AlarmData 10 }
sc553LossOfSignalAlm         	OBJECT IDENTIFIER ::= { sc553AlarmData 11 }
sc553LossOfFrameAlm          	OBJECT IDENTIFIER ::= { sc553AlarmData 12 }
sc553AlarmIndicationSignalAlm 	OBJECT IDENTIFIER ::= { sc553AlarmData 13 }
sc553ReceivedYellowAlm       	OBJECT IDENTIFIER ::= { sc553AlarmData 14 }
sc553UnavailableSignalStateAlm	OBJECT IDENTIFIER ::= { sc553AlarmData 15 }
sc553CrcErrorsAlm    	     	OBJECT IDENTIFIER ::= { sc553AlarmData 16 }
sc553BipolarViolationsAlm    	OBJECT IDENTIFIER ::= { sc553AlarmData 17 }
sc553LowAverageDensityAlm    	OBJECT IDENTIFIER ::= { sc553AlarmData 18 }
sc553ExternalTXClockLossAlm  	OBJECT IDENTIFIER ::= { sc553AlarmData 19 }
sc553DCDLossAlm              	OBJECT IDENTIFIER ::= { sc553AlarmData 20 }
sc553DSRLossAlm              	OBJECT IDENTIFIER ::= { sc553AlarmData 21 }
sc553DTRLossAlm              	OBJECT IDENTIFIER ::= { sc553AlarmData 22 }
sc553RXDNoTransitionsAlm     	OBJECT IDENTIFIER ::= { sc553AlarmData 23 }
sc553TXDNoTransitionsAlm     	OBJECT IDENTIFIER ::= { sc553AlarmData 24 }
sc553RedundancyOn     		OBJECT IDENTIFIER ::= { sc553AlarmData 25 }
sc553RemoteNotResponding     	OBJECT IDENTIFIER ::= { sc553AlarmData 26 }
sc553TopPowerSupplyFail     	OBJECT IDENTIFIER ::= { sc553AlarmData 27 }
sc553BottomPowerSupplyFail     	OBJECT IDENTIFIER ::= { sc553AlarmData 28 }










 -- The following Table provides a description of the alarms on the sc553.

 -- The index sub-identifier for each alarm on an interface basis is:
 --
 --                     system sub-identifier = 0
 --                     net    sub-identifier = 1
 --                     casc   sub-identifier = 2
 --                     chan   sub-identifier = 3
 --
 -- ALARM                       Maskable   Valid interfaces   thres      Type
 -- ============================================================================
 -- sc553NoResponseAlm           no         system             no        major
 -- sc553DiagRxErrAlm            ?????????????????????????????????????????????
 -- sc553PowerUpAlm              no         system             no/no        Informational
 -- sc553NvRamCorrupt            no         system             no/no        major
 -- sc553UnitFailure             no         system             no/no        major
 -- sc553StatusChange            yes        system             no/no        other
 -- sc553UnsolicitedTest         yes        system             no/no        other
 -- sc553FrontPanelTest          yes        system             no/no        other
 -- sc553ConfigChage             Yes        system             no/no        other
 -- sc553TimingLoss              yes        net/only           no/no        major
 -- sc553LossofSignal            yes        net/casc           no/no        major
 -- sc553LossOfFrame             yes        net/casc           yes/yes      major
 -- sc553AlarmIndicationSignal   yes        net/casc           no/no        major
 -- sc553ReceivedYellow          yes        net/casc           no/no        minor
 -- sc553UnavailableSignalstate  yes        net/casc           no/no        major
 -- sc553BipolarViolations       yes        net/casc           yes/yes      minor
 -- sc553CrcErrors               yes        net/casc           yes/yes      minor
 -- sc553LowAverageDensity       yes        net/casc           yes/no       minor
 -- sc553ExternalTXClockLoss     yes	    chan	       no/no        minor	
 -- sc553DCDLoss                 yes	    chan	       no/no        minor	
 -- sc553DSRLoss                 yes	    chan	       no/no        minor	
 -- sc553DTRLoss                 yes	    chan	       no/no        minor	
 -- sc553RXDNoTransitions        yes	    chan	       no/no        minor	
 -- sc553TXDNoTransitions        yes	    chan	       no/no        minor	
 -- sc553RedundancyOn            yes	    chan	       no/no        minor	
 -- sc553RemoteNotResponding     yes	    system	       no/no        minor	
 -- sc553TopPowerSupplyFail      yes	    system	       no/no        minor	
 -- sc553BottomPowerSupplyFail   yes	    system	       no/no        minor	



--	Alarm Status octet String (scmNodeCurrentAlarms in scmNodeTable from GDCSCM-MIB)
--
--
--
--	1.7	parity
--	1.6	LOS	(1: Loss Of Signal 		[Network])
--	1.5	OOF	(1: Out Of Frame 		[Network])
--	1.4	AIS	(1: Alarm Indication Signal 	[Network])
--	1.3	BPV	(1: BiPolar Violations 		[Network])
--	1.2	RY	(1: Received Yellow 		[Network])
--	1.1	RDON    (1: Redundancy On               [Channel])
--	1.0	LAD	(1: Low Average Density		[Network])	
--
--
--	2.7	parity
--	2.6	FPT	(1: Front Panel Test 		[System ])
--	2.5	CRC	(1: Cycle Redundance Check 	[Network])
--	2.4	CC	(1: Config Change 		[System ])
--	2.3	USS	(1: Unavailable Signal State 	[Network])
--	2.2	SC	(1: Status Change		[System ])
--	2.1	TL	(1: Timing Loss			[Network])
--	2.0	UF	(1: Unit Failure		[System ])
--
--
--	3.7	parity
--	3.6	LOS	(1: Loss Of Signal 		[Cascade])
--	3.5	OOF	(1: Out Of Frame 		[Cascade])
--	3.4	AIS	(1: Alarm Indication Signal 	[Cascade])
--	3.3	TPSF    (1: Top PS Failed               [System])
--	3.2	RY	(1: Received Yellow 		[Cascade])
--	3.1	f/u
--	3.0	LAD	(1: Low Average Density		[Cascade])	
--
--
--	4.7	parity
--	4.6	BPV	(1: BiPolar Violations 		[Cascade])
--	4.5	CRC	(1: Cycle Redundance Check 	[Cascade])
--	4.4	BPSF    (1: Bottom PS Failed            [System])
--	4.3	USS	(1: Unavailable Signal State	[Cascade])
--	4.2	UT	(1: Unsolicited Test		[System ])
--	4.1	NVRC	(1: EE prom Checksum		[System ])
--	4.0	PRUP	(1: Power-up			[System ]) 
--
--
--	5.7	parity
--	5.6 	RNR     (1: Remote Not Responding       [System])
--	5.5	ETXC	(1: External Transmit Clock Loss[Channel])
--	5.4	DCD	(1: DCD Loss              	[Channel])
--	5.3	DSR	(1: DSR Loss           		[Channel])
--	5.2	DTR	(1: DTR Loss             	[Channel])
--	5.1	RXD	(1: RXD No Transition   	[Channel])
--	5.0	TXD	(1: TXD No Transition  		[Channel])
--
--







-- 
--
--   			 Alarm Thresholds
-- 

 
sc553AlarmConfigTable OBJECT-TYPE
     SYNTAX SEQUENCE OF Sc553AlarmConfigEntry
     ACCESS not-accessible
     STATUS mandatory
     DESCRIPTION
         "The sc553AlarmConfigTable contains entries that configure alarm
         reporting.  The structure of the table is such that alarm
         configuration is supported on a unit and interface basis, and
         then on an alarm type basis within the interface.  For
         simplicity sake alarms, be they unit or interface
         related, are represented in one table."
     ::= { sc553Alarms 2 }
 
sc553AlarmConfigEntry OBJECT-TYPE
     SYNTAX Sc553AlarmConfigEntry
     ACCESS not-accessible
     STATUS mandatory
     DESCRIPTION
         "An entry in the GDC Alarm Configuration table."
     INDEX { sc553AlarmConfigIndex, sc553AlarmConfigIdentifier }
     ::= { sc553AlarmConfigTable 1 }
 
Sc553AlarmConfigEntry ::=
     SEQUENCE {
         sc553AlarmConfigIndex
             SCinstance,
         sc553AlarmConfigIdentifier
             OBJECT IDENTIFIER,
         sc553AlarmCountWindow
             INTEGER,
         sc553AlarmCountThreshold
             INTEGER
     }
 
sc553AlarmConfigIndex OBJECT-TYPE
     SYNTAX SCinstance
     ACCESS read-only
     STATUS mandatory
     DESCRIPTION
         "The index value which uniquely identifies the interface to
         which this entry is applicable."
     ::= { sc553AlarmConfigEntry 1 }
 
sc553AlarmConfigIdentifier OBJECT-TYPE
     SYNTAX OBJECT IDENTIFIER
     ACCESS read-only
     STATUS mandatory
     DESCRIPTION
         "The unique alarm identifier assigned to this alarm type.
         The format of this identifier is an OBJECT IDENTIFIER that has
         the following format: {iso(1) org(3) dod(6) internet(1)
         private(4) enterprises(1) gdc(498) xxx(x) alarm(z) yyy(y)
         where xxx(x) is the administratively assigned family object
         identifier (z) is the object identifier for alarms in the family
         defined MIB and yyy(y) is the administratively assigned alarm
         type identifier for this alarm."
     ::= { sc553AlarmConfigEntry 2 }
 
sc553AlarmCountWindow OBJECT-TYPE
    SYNTAX INTEGER{
        reportAll(1),
        last1sec(2),
        last1min(3),
        last1hr(4),
        reportWhen(5)
    }
    ACCESS  read-write
    STATUS  mandatory
    DESCRIPTION
    "This variable sets/reads the alarm window.
 
    This window is used with the alarm threshold to determine
    how long the alarm should be active before reporting."
    ::= { sc553AlarmConfigEntry 3 }
 
sc553AlarmCountThreshold OBJECT-TYPE
    SYNTAX INTEGER {
        thresGT10(1),
        thresGT100(2),
        thresGT1000(3),
        thresGT10000(4)
    }
    ACCESS  read-write
    STATUS  mandatory
    DESCRIPTION
    "This function sets/reads the alarm threshold criteria.
 
    This threshold is used along with the the alarm window to
    determine the number of instances in a given time frame for
    an alarm to occur before the alarm is considered active."
    ::= { sc553AlarmConfigEntry 4 }



-- ********************************************************************
--  			Performance Tables
-- ********************************************************************



-- 
--
--                     ATT CurrentUser Performance Table
-- 


sc553CurrentUserTable 	OBJECT-TYPE
	 SYNTAX  SEQUENCE OF Sc553CurrentUserEntry
	 ACCESS  not-accessible
	 STATUS  mandatory
	 DESCRIPTION
		 "The sc553 CurrentUser table.  This table supplements the
		 entries in the DS1 AT&T performance table of the DS1
		 MIB defined in RFC1406."
	 ::= { sc553Performance 1 }


sc553CurrentUserEntry 	OBJECT-TYPE
	 SYNTAX  Sc553CurrentUserEntry
	 ACCESS  not-accessible
	 STATUS  mandatory
	 DESCRIPTION
		 "An entry in the sc553 CurrentUser table."
	 INDEX   { sc553CurrentUserIndex }
	 ::= { sc553CurrentUserTable 1 }

Sc553CurrentUserEntry ::=
    SEQUENCE {
        sc553CurrentUserIndex  	SCinstance,
        sc553CurrentUserStat	OCTET STRING
 	  }

sc553CurrentUserIndex 	OBJECT-TYPE
    SYNTAX  SCinstance
    ACCESS  read-only
    STATUS  mandatory
    DESCRIPTION
        "The index value which uniquely identifies the interface to
        which this entry is applicable.  This has the form of a
        SCinstance which defines the slot, line, drop, and interface,
        which in this case is a network interface."
    ::= { sc553CurrentUserEntry 1 }

sc553CurrentUserStat OBJECT-TYPE
	 SYNTAX OCTET STRING (SIZE (15))
	 ACCESS read-only
	 STATUS mandatory
	 DESCRIPTION
		"Returns a bitwise snapshot of the  statistics.

		 Octet 1 bit 7 - parity   
			 bit 6 - 2^15	Errored Seconds 
			 bit 5 - 2^14
			 bit 4 - 2^15	Severely Errored Seconds
			 bit 3 - 2^14
			 bit 2 - 2^15	Bursty Errored Seconds
			 bit 1 - 2^14
			 bit 0 - 1: 	New Interval

		 Octet 2 bit 7 - parity   
			 bit 6 - 2^13   Errored Seconds
			 bit 5 - 2^12
			 bit 4 - 2^11
			 bit 3 - 2^10
			 bit 2 - 2^9
			 bit 1 - 2^8
			 bit 0 - 2^7

		 Octet 3 bit 7 - parity   
			 bit 6 - 2^6	Errored Seconds
			 bit 5 - 2^5
			 bit 4 - 2^4
			 bit 3 - 2^3
			 bit 2 - 2^2
			 bit 1 - 2^1
			 bit 0 - 2^0

		 Octet 4 bit 7 - parity   
			 bit 6 - 2^13 	Severely Errored Seconds
			 bit 5 - 2^12
			 bit 4 - 2^11
			 bit 3 - 2^10
			 bit 2 - 2^9
			 bit 1 - 2^8
			 bit 0 - 2^7

		 Octet 5 bit 7 - parity   
			 bit 6 - 2^6 	Severely Errored Seconds	
			 bit 5 - 2^5
			 bit 4 - 2^4
			 bit 3 - 2^3
			 bit 2 - 2^2
			 bit 1 - 2^1
			 bit 0 - 2^0

		 Octet 6 bit 7 - parity   
			 bit 6 - 2^13 	Bursty Errored Seconds	
			 bit 5 - 2^12
			 bit 4 - 2^11
			 bit 3 - 2^10
			 bit 2 - 2^9
			 bit 1 - 2^8
			 bit 0 - 2^7

		 Octet 7 bit 7 - parity   
			 bit 6 - 2^6 	Bursty Errored Seconds
			 bit 5 - 2^5
			 bit 4 - 2^4
			 bit 3 - 2^3
			 bit 2 - 2^2
			 bit 1 - 2^1
			 bit 0 - 2^0

		 Octet 8 bit 7 - parity   
			 bit 6 - 2^15 	CRC's
			 bit 5 - 2^14	
			 bit 4 - 2^15	Unavailable Seconds
			 bit 3 - 2^14
			 bit 2 - f/u
			 bit 1 - 2^7 	Loss of Frame Count
			 bit 0 - 2^7	Controlled Slip Seconds

		 Octet 9 bit 7 - parity   
			 bit 6 - 2^13 	Unavailable Seconds
			 bit 5 - 2^12
			 bit 4 - 2^11
			 bit 3 - 2^10
			 bit 2 - 2^9
			 bit 1 - 2^8
			 bit 0 - 2^7

	        Octet 10 bit 7 - parity   
			 bit 6 - 2^6 	Unavailable Seconds
			 bit 5 - 2^5
			 bit 4 - 2^4
			 bit 3 - 2^3
			 bit 2 - 2^2
			 bit 1 - 2^1
			 bit 0 - 2^0

		Octet 11 bit 7 - parity   
			 bit 6 - 2^6  	Controlled Slip Second
			 bit 5 - 2^5
			 bit 4 - 2^4
			 bit 3 - 2^3
			 bit 2 - 2^2
			 bit 1 - 2^1
			 bit 0 - 2^0

		Octet 12 bit 7 - parity   
			 bit 6 - 2^6 	Loss of Frame Count
			 bit 5 - 2^5
			 bit 4 - 2^4
			 bit 3 - 2^3
			 bit 2 - 2^2
			 bit 1 - 2^1
			 bit 0 - 2^0

		Octet 13 bit 7 - parity   
			 bit 6 - 2^13	CRC's
			 bit 5 - 2^12
			 bit 4 - 2^11
			 bit 3 - 2^10
			 bit 2 - 2^9
			 bit 1 - 2^8
			 bit 0 - 2^7

		Octet 14 bit 7 - parity   
			 bit 6 - 2^6 	CRC's
			 bit 5 - 2^5
			 bit 4 - 2^4
			 bit 3 - 2^3
			 bit 2 - 2^2
			 bit 1 - 2^1
			 bit 0 - 2^0

		Octet 15 bit 7 - parity   
			 bit 6 - 2^6 	Percent Complete
			 bit 5 - 2^5
			 bit 4 - 2^4
			 bit 3 - 2^3
			 bit 2 - 2^2
			 bit 1 - 2^1
			 bit 0 - 2^0
		"

    ::= { sc553CurrentUserEntry 2 }
 


-- 
--
--                     ATT CurrentNetwork Performance Table
-- 


sc553CurrentNetworkTable 	OBJECT-TYPE
	 SYNTAX  SEQUENCE OF Sc553CurrentNetworkEntry
	 ACCESS  not-accessible
	 STATUS  mandatory
	 DESCRIPTION
		 "The sc553 CurrentNetwork table.  This table supplements the
		 entries in the DS1 AT&T performance table of the DS1
		 MIB defined in RFC1406."
	 ::= { sc553Performance 2 }


sc553CurrentNetworkEntry 	OBJECT-TYPE
	 SYNTAX  Sc553CurrentNetworkEntry
	 ACCESS  not-accessible
	 STATUS  mandatory
	 DESCRIPTION
		 "An entry in the sc553 CurrentNetwork table."
	 INDEX   { sc553CurrentNetworkIndex }
	 ::= { sc553CurrentNetworkTable 1 }

Sc553CurrentNetworkEntry ::=
    SEQUENCE {
        sc553CurrentNetworkIndex  	SCinstance,
        sc553CurrentNetworkStat	OCTET STRING
 	  }

sc553CurrentNetworkIndex 	OBJECT-TYPE
    SYNTAX  SCinstance
    ACCESS  read-only
    STATUS  mandatory
    DESCRIPTION
        "The index value which uniquely identifies the interface to
        which this entry is applicable.  This has the form of a
        SCinstance which defines the slot, line, drop, and interface,
        which in this case is a network interface."
    ::= { sc553CurrentNetworkEntry 1 }

sc553CurrentNetworkStat OBJECT-TYPE
	 SYNTAX OCTET STRING (SIZE (15))
	 ACCESS read-only
	 STATUS mandatory
	 DESCRIPTION
		"Returns a bitwise snapshot of the  statistics.

		 Octet 1 bit 7 - parity   
			 bit 6 - 2^15	Errored Seconds 
			 bit 5 - 2^14
			 bit 4 - 2^15	Severely Errored Seconds
			 bit 3 - 2^14
			 bit 2 - 2^15	Bursty Errored Seconds
			 bit 1 - 2^14
			 bit 0 - 1: 	New Interval

		 Octet 2 bit 7 - parity   
			 bit 6 - 2^13   Errored Seconds
			 bit 5 - 2^12
			 bit 4 - 2^11
			 bit 3 - 2^10
			 bit 2 - 2^9
			 bit 1 - 2^8
			 bit 0 - 2^7

		 Octet 3 bit 7 - parity   
			 bit 6 - 2^6	Errored Seconds
			 bit 5 - 2^5
			 bit 4 - 2^4
			 bit 3 - 2^3
			 bit 2 - 2^2
			 bit 1 - 2^1
			 bit 0 - 2^0

		 Octet 4 bit 7 - parity   
			 bit 6 - 2^13 	Severely Errored Seconds
			 bit 5 - 2^12
			 bit 4 - 2^11
			 bit 3 - 2^10
			 bit 2 - 2^9
			 bit 1 - 2^8
			 bit 0 - 2^7

		 Octet 5 bit 7 - parity   
			 bit 6 - 2^6 	Severely Errored Seconds	
			 bit 5 - 2^5
			 bit 4 - 2^4
			 bit 3 - 2^3
			 bit 2 - 2^2
			 bit 1 - 2^1
			 bit 0 - 2^0

		 Octet 6 bit 7 - parity   
			 bit 6 - 2^13 	Bursty Errored Seconds	
			 bit 5 - 2^12
			 bit 4 - 2^11
			 bit 3 - 2^10
			 bit 2 - 2^9
			 bit 1 - 2^8
			 bit 0 - 2^7

		 Octet 7 bit 7 - parity   
			 bit 6 - 2^6 	Bursty Errored Seconds
			 bit 5 - 2^5
			 bit 4 - 2^4
			 bit 3 - 2^3
			 bit 2 - 2^2
			 bit 1 - 2^1
			 bit 0 - 2^0

		 Octet 8 bit 7 - parity   
			 bit 6 - 2^15 	CRC's
			 bit 5 - 2^14	
			 bit 4 - 2^15	Unavailable Seconds
			 bit 3 - 2^14
			 bit 2 - f/u
			 bit 1 - 2^7 	Loss of Frame Count
			 bit 0 - 2^7	Controlled Slip Seconds

		 Octet 9 bit 7 - parity   
			 bit 6 - 2^13 	Unavailable Seconds
			 bit 5 - 2^12
			 bit 4 - 2^11
			 bit 3 - 2^10
			 bit 2 - 2^9
			 bit 1 - 2^8
			 bit 0 - 2^7

	        Octet 10 bit 7 - parity   
			 bit 6 - 2^6 	Unavailable Seconds
			 bit 5 - 2^5
			 bit 4 - 2^4
			 bit 3 - 2^3
			 bit 2 - 2^2
			 bit 1 - 2^1
			 bit 0 - 2^0

		Octet 11 bit 7 - parity   
			 bit 6 - 2^6  	Controlled Slip Second
			 bit 5 - 2^5
			 bit 4 - 2^4
			 bit 3 - 2^3
			 bit 2 - 2^2
			 bit 1 - 2^1
			 bit 0 - 2^0

		Octet 12 bit 7 - parity   
			 bit 6 - 2^6 	Loss of Frame Count
			 bit 5 - 2^5
			 bit 4 - 2^4
			 bit 3 - 2^3
			 bit 2 - 2^2
			 bit 1 - 2^1
			 bit 0 - 2^0

		Octet 13 bit 7 - parity   
			 bit 6 - 2^13	CRC's
			 bit 5 - 2^12
			 bit 4 - 2^11
			 bit 3 - 2^10
			 bit 2 - 2^9
			 bit 1 - 2^8
			 bit 0 - 2^7

		Octet 14 bit 7 - parity   
			 bit 6 - 2^6 	CRC's
			 bit 5 - 2^5
			 bit 4 - 2^4
			 bit 3 - 2^3
			 bit 2 - 2^2
			 bit 1 - 2^1
			 bit 0 - 2^0

		Octet 15 bit 7 - parity   
			 bit 6 - 2^6 	Percent Complete
			 bit 5 - 2^5
			 bit 4 - 2^4
			 bit 3 - 2^3
			 bit 2 - 2^2
			 bit 1 - 2^1
			 bit 0 - 2^0

				"

    ::= { sc553CurrentNetworkEntry 2 }
 

-- 
--
--                     ATT CurrentFarEnd Performance Table
-- 


sc553CurrentFarEndTable 	OBJECT-TYPE
	 SYNTAX  SEQUENCE OF Sc553CurrentFarEndEntry
	 ACCESS  not-accessible
	 STATUS  mandatory
	 DESCRIPTION
		 "The sc553 CurrentFarEnd table.  This table supplements the
		 entries in the DS1 AT&T performance table of the DS1
		 MIB defined in RFC1406."
	 ::= { sc553Performance 3 }


sc553CurrentFarEndEntry 	OBJECT-TYPE
	 SYNTAX  Sc553CurrentFarEndEntry
	 ACCESS  not-accessible
	 STATUS  mandatory
	 DESCRIPTION
		 "An entry in the sc553 CurrentFarEnd table."
	 INDEX   { sc553CurrentFarEndIndex }
	 ::= { sc553CurrentFarEndTable 1 }

Sc553CurrentFarEndEntry ::=
    SEQUENCE {
        sc553CurrentFarEndIndex  	SCinstance,
        sc553CurrentFarEndStat	OCTET STRING
 	  }

sc553CurrentFarEndIndex 	OBJECT-TYPE
    SYNTAX  SCinstance
    ACCESS  read-only
    STATUS  mandatory
    DESCRIPTION
        "The index value which uniquely identifies the interface to
        which this entry is applicable.  This has the form of a
        SCinstance which defines the slot, line, drop, and interface,
        which in this case is a network interface."
    ::= { sc553CurrentFarEndEntry 1 }

sc553CurrentFarEndStat OBJECT-TYPE
	 SYNTAX OCTET STRING (SIZE (15))
	 ACCESS read-only
	 STATUS mandatory
	 DESCRIPTION
		"Returns a bitwise snapshot of the  statistics.

		 Octet 1 bit 7 - parity   
			 bit 6 - 2^15	Errored Seconds 
			 bit 5 - 2^14
			 bit 4 - 2^15	Severely Errored Seconds
			 bit 3 - 2^14
			 bit 2 - 2^15	Bursty Errored Seconds
			 bit 1 - 2^14
			 bit 0 - 1: 	New Interval

		 Octet 2 bit 7 - parity   
			 bit 6 - 2^13   Errored Seconds
			 bit 5 - 2^12
			 bit 4 - 2^11
			 bit 3 - 2^10
			 bit 2 - 2^9
			 bit 1 - 2^8
			 bit 0 - 2^7

		 Octet 3 bit 7 - parity   
			 bit 6 - 2^6	Errored Seconds
			 bit 5 - 2^5
			 bit 4 - 2^4
			 bit 3 - 2^3
			 bit 2 - 2^2
			 bit 1 - 2^1
			 bit 0 - 2^0

		 Octet 4 bit 7 - parity   
			 bit 6 - 2^13 	Severely Errored Seconds
			 bit 5 - 2^12
			 bit 4 - 2^11
			 bit 3 - 2^10
			 bit 2 - 2^9
			 bit 1 - 2^8
			 bit 0 - 2^7

		 Octet 5 bit 7 - parity   
			 bit 6 - 2^6 	Severely Errored Seconds	
			 bit 5 - 2^5
			 bit 4 - 2^4
			 bit 3 - 2^3
			 bit 2 - 2^2
			 bit 1 - 2^1
			 bit 0 - 2^0

		 Octet 6 bit 7 - parity   
			 bit 6 - 2^13 	Bursty Errored Seconds	
			 bit 5 - 2^12
			 bit 4 - 2^11
			 bit 3 - 2^10
			 bit 2 - 2^9
			 bit 1 - 2^8
			 bit 0 - 2^7

		 Octet 7 bit 7 - parity   
			 bit 6 - 2^6 	Bursty Errored Seconds
			 bit 5 - 2^5
			 bit 4 - 2^4
			 bit 3 - 2^3
			 bit 2 - 2^2
			 bit 1 - 2^1
			 bit 0 - 2^0

		 Octet 8 bit 7 - parity   
			 bit 6 - 2^15 	CRC's
			 bit 5 - 2^14	
			 bit 4 - 2^15	Unavailable Seconds
			 bit 3 - 2^14
			 bit 2 - f/u
			 bit 1 - 2^7 	Loss of Frame Count
			 bit 0 - 2^7	Controlled Slip Seconds

		 Octet 9 bit 7 - parity   
			 bit 6 - 2^13 	Unavailable Seconds
			 bit 5 - 2^12
			 bit 4 - 2^11
			 bit 3 - 2^10
			 bit 2 - 2^9
			 bit 1 - 2^8
			 bit 0 - 2^7

	        Octet 10 bit 7 - parity   
			 bit 6 - 2^6 	Unavailable Seconds
			 bit 5 - 2^5
			 bit 4 - 2^4
			 bit 3 - 2^3
			 bit 2 - 2^2
			 bit 1 - 2^1
			 bit 0 - 2^0

		Octet 11 bit 7 - parity   
			 bit 6 - 2^6  	Controlled Slip Second
			 bit 5 - 2^5
			 bit 4 - 2^4
			 bit 3 - 2^3
			 bit 2 - 2^2
			 bit 1 - 2^1
			 bit 0 - 2^0

		Octet 12 bit 7 - parity   
			 bit 6 - 2^6 	Loss of Frame Count
			 bit 5 - 2^5
			 bit 4 - 2^4
			 bit 3 - 2^3
			 bit 2 - 2^2
			 bit 1 - 2^1
			 bit 0 - 2^0
		Octet 13 bit 7 - parity   
			 bit 6 - 2^13	CRC's
			 bit 5 - 2^12
			 bit 4 - 2^11
			 bit 3 - 2^10
			 bit 2 - 2^9
			 bit 1 - 2^8
			 bit 0 - 2^7

		Octet 14 bit 7 - parity   
			 bit 6 - 2^6 	CRC's
			 bit 5 - 2^5
			 bit 4 - 2^4
			 bit 3 - 2^3
			 bit 2 - 2^2
			 bit 1 - 2^1
			 bit 0 - 2^0

		Octet 15 bit 7 - parity   
			 bit 6 - 2^6 	Percent Complete
			 bit 5 - 2^5
			 bit 4 - 2^4
			 bit 3 - 2^3
			 bit 2 - 2^2
			 bit 1 - 2^1
			 bit 0 - 2^0


		"

    ::= { sc553CurrentFarEndEntry 2 }
 





-- 
--
--                     ATT TotalUser Performance Table
-- 


sc553TotalUserTable 	OBJECT-TYPE
	 SYNTAX  SEQUENCE OF Sc553TotalUserEntry
	 ACCESS  not-accessible
	 STATUS  mandatory
	 DESCRIPTION
		 "The sc553 TotalUser table.  This table supplements the
		 entries in the DS1 AT&T performance table of the DS1
		 MIB defined in RFC1406."
	 ::= { sc553Performance 4 }


sc553TotalUserEntry 	OBJECT-TYPE
	 SYNTAX  Sc553TotalUserEntry
	 ACCESS  not-accessible
	 STATUS  mandatory
	 DESCRIPTION
		 "An entry in the sc553 TotalUser table."
	 INDEX   { sc553TotalUserIndex }
	 ::= { sc553TotalUserTable 1 }

Sc553TotalUserEntry ::=
    SEQUENCE {
        sc553TotalUserIndex  	SCinstance,
        sc553TotalUserStat	OCTET STRING
 	  }

sc553TotalUserIndex 	OBJECT-TYPE
    SYNTAX  SCinstance
    ACCESS  read-only
    STATUS  mandatory
    DESCRIPTION
        "The index value which uniquely identifies the interface to
        which this entry is applicable.  This has the form of a
        SCinstance which defines the slot, line, drop, and interface,
        which in this case is a network interface."
    ::= { sc553TotalUserEntry 1 }

sc553TotalUserStat OBJECT-TYPE
	 SYNTAX OCTET STRING (SIZE (15))
	 ACCESS read-only
	 STATUS mandatory
	 DESCRIPTION
		"Returns a bitwise snapshot of the  statistics.

		 Octet 1 bit 7 - parity   
			 bit 6 - 2^15	Errored Seconds 
			 bit 5 - 2^14
			 bit 4 - 2^15	Severely Errored Seconds
			 bit 3 - 2^14
			 bit 2 - 2^15	Bursty Errored Seconds
			 bit 1 - 2^14
			 bit 0 - 1: 	New Interval

		 Octet 2 bit 7 - parity   
			 bit 6 - 2^13   Errored Seconds
			 bit 5 - 2^12
			 bit 4 - 2^11
			 bit 3 - 2^10
			 bit 2 - 2^9
			 bit 1 - 2^8
			 bit 0 - 2^7

		 Octet 3 bit 7 - parity   
			 bit 6 - 2^6	Errored Seconds
			 bit 5 - 2^5
			 bit 4 - 2^4
			 bit 3 - 2^3
			 bit 2 - 2^2
			 bit 1 - 2^1
			 bit 0 - 2^0

		 Octet 4 bit 7 - parity   
			 bit 6 - 2^13 	Severely Errored Seconds
			 bit 5 - 2^12
			 bit 4 - 2^11
			 bit 3 - 2^10
			 bit 2 - 2^9
			 bit 1 - 2^8
			 bit 0 - 2^7

		 Octet 5 bit 7 - parity   
			 bit 6 - 2^6 	Severely Errored Seconds	
			 bit 5 - 2^5
			 bit 4 - 2^4
			 bit 3 - 2^3
			 bit 2 - 2^2
			 bit 1 - 2^1
			 bit 0 - 2^0

		 Octet 6 bit 7 - parity   
			 bit 6 - 2^13 	Bursty Errored Seconds	
			 bit 5 - 2^12
			 bit 4 - 2^11
			 bit 3 - 2^10
			 bit 2 - 2^9
			 bit 1 - 2^8
			 bit 0 - 2^7

		 Octet 7 bit 7 - parity   
			 bit 6 - 2^6 	Bursty Errored Seconds
			 bit 5 - 2^5
			 bit 4 - 2^4
			 bit 3 - 2^3
			 bit 2 - 2^2
			 bit 1 - 2^1
			 bit 0 - 2^0

		 Octet 8 bit 7 - parity   
			 bit 6 - 2^15 	CRC's
			 bit 5 - 2^14	
			 bit 4 - 2^15	Unavailable Seconds
			 bit 3 - 2^14
			 bit 2 - f/u
			 bit 1 - 2^7 	Loss of Frame Count
			 bit 0 - 2^7	Controlled Slip Seconds

		 Octet 9 bit 7 - parity   
			 bit 6 - 2^13 	Unavailable Seconds
			 bit 5 - 2^12
			 bit 4 - 2^11
			 bit 3 - 2^10
			 bit 2 - 2^9
			 bit 1 - 2^8
			 bit 0 - 2^7

	        Octet 10 bit 7 - parity   
			 bit 6 - 2^6 	Unavailable Seconds
			 bit 5 - 2^5
			 bit 4 - 2^4
			 bit 3 - 2^3
			 bit 2 - 2^2
			 bit 1 - 2^1
			 bit 0 - 2^0

		Octet 11 bit 7 - parity   
			 bit 6 - 2^6  	Controlled Slip Second
			 bit 5 - 2^5
			 bit 4 - 2^4
			 bit 3 - 2^3
			 bit 2 - 2^2
			 bit 1 - 2^1
			 bit 0 - 2^0

		Octet 12 bit 7 - parity   
			 bit 6 - 2^6 	Loss of Frame Count
			 bit 5 - 2^5
			 bit 4 - 2^4
			 bit 3 - 2^3
			 bit 2 - 2^2
			 bit 1 - 2^1
			 bit 0 - 2^0

		Octet 13 bit 7 - parity   
			 bit 6 - 2^13	CRC's
			 bit 5 - 2^12
			 bit 4 - 2^11
			 bit 3 - 2^10
			 bit 2 - 2^9
			 bit 1 - 2^8
			 bit 0 - 2^7

		Octet 14 bit 7 - parity   
			 bit 6 - 2^6 	CRC's
			 bit 5 - 2^5
			 bit 4 - 2^4
			 bit 3 - 2^3
			 bit 2 - 2^2
			 bit 1 - 2^1
			 bit 0 - 2^0

		Octet 15 bit 7 - parity   
			 bit 6 - 2^6 	Percent Complete
			 bit 5 - 2^5
			 bit 4 - 2^4
			 bit 3 - 2^3
			 bit 2 - 2^2
			 bit 1 - 2^1
			 bit 0 - 2^0

		"

    ::= { sc553TotalUserEntry 2 }
 


-- 
--
--                     ATT TotalNetwork Performance Table
-- 


sc553TotalNetworkTable 	OBJECT-TYPE
	 SYNTAX  SEQUENCE OF Sc553TotalNetworkEntry
	 ACCESS  not-accessible
	 STATUS  mandatory
	 DESCRIPTION
		 "The sc553 TotalNetwork table.  This table supplements the
		 entries in the DS1 AT&T performance table of the DS1
		 MIB defined in RFC1406."
	 ::= { sc553Performance 5 }


sc553TotalNetworkEntry 	OBJECT-TYPE
	 SYNTAX  Sc553TotalNetworkEntry
	 ACCESS  not-accessible
	 STATUS  mandatory
	 DESCRIPTION
		 "An entry in the sc553 TotalNetwork table."
	 INDEX   { sc553TotalNetworkIndex }
	 ::= { sc553TotalNetworkTable 1 }

Sc553TotalNetworkEntry ::=
    SEQUENCE {
        sc553TotalNetworkIndex  	SCinstance,
        sc553TotalNetworkStat	OCTET STRING
 	  }

sc553TotalNetworkIndex 	OBJECT-TYPE
    SYNTAX  SCinstance
    ACCESS  read-only
    STATUS  mandatory
    DESCRIPTION
        "The index value which uniquely identifies the interface to
        which this entry is applicable.  This has the form of a
        SCinstance which defines the slot, line, drop, and interface,
        which in this case is a network interface."
    ::= { sc553TotalNetworkEntry 1 }

sc553TotalNetworkStat OBJECT-TYPE
	 SYNTAX OCTET STRING (SIZE (15))
	 ACCESS read-only
	 STATUS mandatory
	 DESCRIPTION
		"Returns a bitwise snapshot of the  statistics.

		 Octet 1 bit 7 - parity   
			 bit 6 - 2^15	Errored Seconds 
			 bit 5 - 2^14
			 bit 4 - 2^15	Severely Errored Seconds
			 bit 3 - 2^14
			 bit 2 - 2^15	Bursty Errored Seconds
			 bit 1 - 2^14
			 bit 0 - 1: 	New Interval

		 Octet 2 bit 7 - parity   
			 bit 6 - 2^13   Errored Seconds
			 bit 5 - 2^12
			 bit 4 - 2^11
			 bit 3 - 2^10
			 bit 2 - 2^9
			 bit 1 - 2^8
			 bit 0 - 2^7

		 Octet 3 bit 7 - parity   
			 bit 6 - 2^6	Errored Seconds
			 bit 5 - 2^5
			 bit 4 - 2^4
			 bit 3 - 2^3
			 bit 2 - 2^2
			 bit 1 - 2^1
			 bit 0 - 2^0

		 Octet 4 bit 7 - parity   
			 bit 6 - 2^13 	Severely Errored Seconds
			 bit 5 - 2^12
			 bit 4 - 2^11
			 bit 3 - 2^10
			 bit 2 - 2^9
			 bit 1 - 2^8
			 bit 0 - 2^7

		 Octet 5 bit 7 - parity   
			 bit 6 - 2^6 	Severely Errored Seconds	
			 bit 5 - 2^5
			 bit 4 - 2^4
			 bit 3 - 2^3
			 bit 2 - 2^2
			 bit 1 - 2^1
			 bit 0 - 2^0

		 Octet 6 bit 7 - parity   
			 bit 6 - 2^13 	Bursty Errored Seconds	
			 bit 5 - 2^12
			 bit 4 - 2^11
			 bit 3 - 2^10
			 bit 2 - 2^9
			 bit 1 - 2^8
			 bit 0 - 2^7

		 Octet 7 bit 7 - parity   
			 bit 6 - 2^6 	Bursty Errored Seconds
			 bit 5 - 2^5
			 bit 4 - 2^4
			 bit 3 - 2^3
			 bit 2 - 2^2
			 bit 1 - 2^1
			 bit 0 - 2^0

		 Octet 8 bit 7 - parity   
			 bit 6 - fu           
			 bit 5 - fu     
			 bit 4 - 2^15	Unavailable Seconds
			 bit 3 - 2^14
			 bit 2 - f/u
			 bit 1 - 2^7 	Loss of Frame Count
			 bit 0 - 2^7	Controlled Slip Seconds

		 Octet 9 bit 7 - parity   
			 bit 6 - 2^13 	Unavailable Seconds
			 bit 5 - 2^12
			 bit 4 - 2^11
			 bit 3 - 2^10
			 bit 2 - 2^9
			 bit 1 - 2^8
			 bit 0 - 2^7

	        Octet 10 bit 7 - parity   
			 bit 6 - 2^6 	Unavailable Seconds
			 bit 5 - 2^5
			 bit 4 - 2^4
			 bit 3 - 2^3
			 bit 2 - 2^2
			 bit 1 - 2^1
			 bit 0 - 2^0

		Octet 11 bit 7 - parity   
			 bit 6 - 2^6  	Controlled Slip Second
			 bit 5 - 2^5
			 bit 4 - 2^4
			 bit 3 - 2^3
			 bit 2 - 2^2
			 bit 1 - 2^1
			 bit 0 - 2^0

		Octet 12 bit 7 - parity   
			 bit 6 - 2^6 	Loss of Frame Count
			 bit 5 - 2^5
			 bit 4 - 2^4
			 bit 3 - 2^3
			 bit 2 - 2^2
			 bit 1 - 2^1
			 bit 0 - 2^0
		Octet 13 bit 7 - parity   
			 bit 6 - fu           
			 bit 5 - fu  
			 bit 4 - fu
			 bit 3 - fu  
			 bit 2 - fu  
			 bit 1 - fu  
			 bit 0 - fu 

		Octet 14 bit 7 - parity   
			 bit 6 - fu           
			 bit 5 - fu  
			 bit 4 - fu
			 bit 3 - fu  
			 bit 2 - fu  
			 bit 1 - fu  
			 bit 0 - fu 

		Octet 15 bit 7 - parity   
			 bit 6 - 2^6 	Percent Complete
			 bit 5 - 2^5
			 bit 4 - 2^4
			 bit 3 - 2^3
			 bit 2 - 2^2
			 bit 1 - 2^1
			 bit 0 - 2^0


		"

    ::= { sc553TotalNetworkEntry 2 }
 



-- 
--
--                     ATT Total FarEnd Performance Table
-- 


sc553TotalFarEndTable 	OBJECT-TYPE
	 SYNTAX  SEQUENCE OF Sc553TotalFarEndEntry
	 ACCESS  not-accessible
	 STATUS  mandatory
	 DESCRIPTION
		 "The sc553 TotalFarEnd table.  This table supplements the
		 entries in the DS1 AT&T performance table of the DS1
		 MIB defined in RFC1406."
	 ::= { sc553Performance 6 }


sc553TotalFarEndEntry 	OBJECT-TYPE
	 SYNTAX  Sc553TotalFarEndEntry
	 ACCESS  not-accessible
	 STATUS  mandatory
	 DESCRIPTION
		 "An entry in the sc553 TotalFarEnd table."
	 INDEX   { sc553TotalFarEndIndex }
	 ::= { sc553TotalFarEndTable 1 }

Sc553TotalFarEndEntry ::=
    SEQUENCE {
        sc553TotalFarEndIndex  	SCinstance,
        sc553TotalFarEndStat	OCTET STRING
 	  }

sc553TotalFarEndIndex 	OBJECT-TYPE
    SYNTAX  SCinstance
    ACCESS  read-only
    STATUS  mandatory
    DESCRIPTION
        "The index value which uniquely identifies the interface to
        which this entry is applicable.  This has the form of a
        SCinstance which defines the slot, line, drop, and interface,
        which in this case is a network interface."
    ::= { sc553TotalFarEndEntry 1 }

sc553TotalFarEndStat OBJECT-TYPE
	 SYNTAX OCTET STRING (SIZE (15))
	 ACCESS read-only
	 STATUS mandatory
	 DESCRIPTION
		"Returns a bitwise snapshot of the  statistics.

		 Octet 1 bit 7 - parity   
			 bit 6 - 2^15	Errored Seconds 
			 bit 5 - 2^14
			 bit 4 - 2^15	Severely Errored Seconds
			 bit 3 - 2^14
			 bit 2 - 2^15	Bursty Errored Seconds
			 bit 1 - 2^14
			 bit 0 - 1: 	New Interval

		 Octet 2 bit 7 - parity   
			 bit 6 - 2^13   Errored Seconds
			 bit 5 - 2^12
			 bit 4 - 2^11
			 bit 3 - 2^10
			 bit 2 - 2^9
			 bit 1 - 2^8
			 bit 0 - 2^7

		 Octet 3 bit 7 - parity   
			 bit 6 - 2^6	Errored Seconds
			 bit 5 - 2^5
			 bit 4 - 2^4
			 bit 3 - 2^3
			 bit 2 - 2^2
			 bit 1 - 2^1
			 bit 0 - 2^0

		 Octet 4 bit 7 - parity   
			 bit 6 - 2^13 	Severely Errored Seconds
			 bit 5 - 2^12
			 bit 4 - 2^11
			 bit 3 - 2^10
			 bit 2 - 2^9
			 bit 1 - 2^8
			 bit 0 - 2^7

		 Octet 5 bit 7 - parity   
			 bit 6 - 2^6 	Severely Errored Seconds	
			 bit 5 - 2^5
			 bit 4 - 2^4
			 bit 3 - 2^3
			 bit 2 - 2^2
			 bit 1 - 2^1
			 bit 0 - 2^0

		 Octet 6 bit 7 - parity   
			 bit 6 - 2^13 	Bursty Errored Seconds	
			 bit 5 - 2^12
			 bit 4 - 2^11
			 bit 3 - 2^10
			 bit 2 - 2^9
			 bit 1 - 2^8
			 bit 0 - 2^7

		 Octet 7 bit 7 - parity   
			 bit 6 - 2^6 	Bursty Errored Seconds
			 bit 5 - 2^5
			 bit 4 - 2^4
			 bit 3 - 2^3
			 bit 2 - 2^2
			 bit 1 - 2^1
			 bit 0 - 2^0

		 Octet 8 bit 7 - parity   
			 bit 6 - fu           
			 bit 5 - fu       
			 bit 4 - 2^15	Unavailable Seconds
			 bit 3 - 2^14
			 bit 2 - f/u
			 bit 1 - 2^7 	Loss of Frame Count
			 bit 0 - 2^7	Controlled Slip Seconds

		 Octet 9 bit 7 - parity   
			 bit 6 - 2^13 	Unavailable Seconds
			 bit 5 - 2^12
			 bit 4 - 2^11
			 bit 3 - 2^10
			 bit 2 - 2^9
			 bit 1 - 2^8
			 bit 0 - 2^7

	        Octet 10 bit 7 - parity   
			 bit 6 - 2^6 	Unavailable Seconds
			 bit 5 - 2^5
			 bit 4 - 2^4
			 bit 3 - 2^3
			 bit 2 - 2^2
			 bit 1 - 2^1
			 bit 0 - 2^0

		Octet 11 bit 7 - parity   
			 bit 6 - 2^6  	Controlled Slip Second
			 bit 5 - 2^5
			 bit 4 - 2^4
			 bit 3 - 2^3
			 bit 2 - 2^2
			 bit 1 - 2^1
			 bit 0 - 2^0

		Octet 12 bit 7 - parity   
			 bit 6 - 2^6 	Loss of Frame Count
			 bit 5 - 2^5
			 bit 4 - 2^4
			 bit 3 - 2^3
			 bit 2 - 2^2
			 bit 1 - 2^1
			 bit 0 - 2^0

		Octet 13 bit 7 - parity   
			 bit 6 - fu           
			 bit 5 - fu  
			 bit 4 - fu
			 bit 3 - fu  
			 bit 2 - fu  
			 bit 1 - fu  
			 bit 0 - fu 

		Octet 14 bit 7 - parity   
			 bit 6 - fu           
			 bit 5 - fu  
			 bit 4 - fu
			 bit 3 - fu  
			 bit 2 - fu  
			 bit 1 - fu  
			 bit 0 - fu 

		Octet 15 bit 7 - parity   
			 bit 6 - 2^6 	Percent Complete
			 bit 5 - 2^5
			 bit 4 - 2^4
			 bit 3 - 2^3
			 bit 2 - 2^2
			 bit 1 - 2^1
			 bit 0 - 2^0


		"

    ::= { sc553TotalFarEndEntry 2 }
 








-- 
--
--                     ATT User Interval Performance Table
-- 



sc553UserIntervalTable 	OBJECT-TYPE
    SYNTAX  SEQUENCE OF Sc553UserIntervalEntry
    ACCESS  not-accessible
    STATUS  mandatory
    DESCRIPTION
        "The sc553 User Interval table.  This table supplements the
        entries in the DS1 AT&T performance table of the DS1
        MIB defined in RFC1406."
    ::= { sc553Performance 7 }

sc553UserIntervalEntry 	OBJECT-TYPE
    SYNTAX  Sc553UserIntervalEntry
    ACCESS  not-accessible
    STATUS  mandatory
    DESCRIPTION
        "An entry in the DS1 Interval table."
    INDEX   { sc553UserIntervalIndex, sc553UserIntervalNumber }
    ::= { sc553UserIntervalTable 1 }

Sc553UserIntervalEntry ::=
    SEQUENCE {
        sc553UserIntervalIndex		SCinstance,
        sc553UserIntervalNumber		INTEGER,
        sc553UserIntervalStats		OCTET STRING
}

sc553UserIntervalIndex OBJECT-TYPE
    SYNTAX  SCinstance
    ACCESS  read-only
    STATUS  mandatory
    DESCRIPTION
        "The index value which uniquely identifies the interface to
        which this entry is applicable.  This has the form of a
        SCinstance which defines the slot, line, drop, and interface,
        which in this case is a network interface."
    ::= { sc553UserIntervalEntry 1 }

sc553UserIntervalNumber 	OBJECT-TYPE
    SYNTAX  INTEGER (1..96)
    ACCESS  read-only
    STATUS  mandatory
    DESCRIPTION
        "A number between 1 and 96, where 1 is the most recently completed 
        minute interval and 96 is the least recently completed 15 minutes  
        interval   (assuming   that  all  96  intervals  are valid)."
    ::= { sc553UserIntervalEntry 2 }

sc553UserIntervalStats OBJECT-TYPE
	 SYNTAX OCTET STRING (SIZE (15))
	 ACCESS read-only
	 STATUS mandatory
	 DESCRIPTION
		"Returns a bitwise snapshot of the  statistics.

		 Octet 1 bit 7 - parity   
			 bit 6 - 2^15	Errored Seconds 
			 bit 5 - 2^14
			 bit 4 - 2^15	Severely Errored Seconds
			 bit 3 - 2^14
			 bit 2 - 2^15	Bursty Errored Seconds
			 bit 1 - 2^14
			 bit 0 - 1: 	New Interval

		 Octet 2 bit 7 - parity   
			 bit 6 - 2^13   Errored Seconds
			 bit 5 - 2^12
			 bit 4 - 2^11
			 bit 3 - 2^10
			 bit 2 - 2^9
			 bit 1 - 2^8
			 bit 0 - 2^7

		 Octet 3 bit 7 - parity   
			 bit 6 - 2^6	Errored Seconds
			 bit 5 - 2^5
			 bit 4 - 2^4
			 bit 3 - 2^3
			 bit 2 - 2^2
			 bit 1 - 2^1
			 bit 0 - 2^0

		 Octet 4 bit 7 - parity   
			 bit 6 - 2^13 	Severely Errored Seconds
			 bit 5 - 2^12
			 bit 4 - 2^11
			 bit 3 - 2^10
			 bit 2 - 2^9
			 bit 1 - 2^8
			 bit 0 - 2^7

		 Octet 5 bit 7 - parity   
			 bit 6 - 2^6 	Severely Errored Seconds	
			 bit 5 - 2^5
			 bit 4 - 2^4
			 bit 3 - 2^3
			 bit 2 - 2^2
			 bit 1 - 2^1
			 bit 0 - 2^0

		 Octet 6 bit 7 - parity   
			 bit 6 - 2^13 	Bursty Errored Seconds	
			 bit 5 - 2^12
			 bit 4 - 2^11
			 bit 3 - 2^10
			 bit 2 - 2^9
			 bit 1 - 2^8
			 bit 0 - 2^7

		 Octet 7 bit 7 - parity   
			 bit 6 - 2^6 	Bursty Errored Seconds
			 bit 5 - 2^5
			 bit 4 - 2^4
			 bit 3 - 2^3
			 bit 2 - 2^2
			 bit 1 - 2^1
			 bit 0 - 2^0

		 Octet 8 bit 7 - parity   
			 bit 6 - 2^15 	CRC's
			 bit 5 - 2^14	
			 bit 4 - 2^15	Unavailable Seconds
			 bit 3 - 2^14
			 bit 2 - f/u
			 bit 1 - 2^7 	Loss of Frame Count
			 bit 0 - 2^7	Controlled Slip Seconds

		 Octet 9 bit 7 - parity   
			 bit 6 - 2^13 	Unavailable Seconds
			 bit 5 - 2^12
			 bit 4 - 2^11
			 bit 3 - 2^10
			 bit 2 - 2^9
			 bit 1 - 2^8
			 bit 0 - 2^7

	        Octet 10 bit 7 - parity   
			 bit 6 - 2^6 	Unavailable Seconds
			 bit 5 - 2^5
			 bit 4 - 2^4
			 bit 3 - 2^3
			 bit 2 - 2^2
			 bit 1 - 2^1
			 bit 0 - 2^0

		Octet 11 bit 7 - parity   
			 bit 6 - 2^6  	Controlled Slip Second
			 bit 5 - 2^5
			 bit 4 - 2^4
			 bit 3 - 2^3
			 bit 2 - 2^2
			 bit 1 - 2^1
			 bit 0 - 2^0

		Octet 12 bit 7 - parity   
			 bit 6 - 2^6 	Loss of Frame Count
			 bit 5 - 2^5
			 bit 4 - 2^4
			 bit 3 - 2^3
			 bit 2 - 2^2
			 bit 1 - 2^1
			 bit 0 - 2^0

		Octet 13 bit 7 - parity   
			 bit 6 - 2^13	CRC's
			 bit 5 - 2^12
			 bit 4 - 2^11
			 bit 3 - 2^10
			 bit 2 - 2^9
			 bit 1 - 2^8
			 bit 0 - 2^7

		Octet 14 bit 7 - parity   
			 bit 6 - 2^6 	CRC's
			 bit 5 - 2^5
			 bit 4 - 2^4
			 bit 3 - 2^3
			 bit 2 - 2^2
			 bit 1 - 2^1
			 bit 0 - 2^0

		Octet 15 bit 7 - parity   
			 bit 6 - 2^6 	Interval 1 thru 96
			 bit 5 - 2^5
			 bit 4 - 2^4
			 bit 3 - 2^3
			 bit 2 - 2^2
			 bit 1 - 2^1
			 bit 0 - 2^0

		"    ::= { sc553UserIntervalEntry 3 }


-- 
--
--                     ATT Network Interval Performance Table
-- 



sc553NetworkIntervalTable 	OBJECT-TYPE
    SYNTAX  SEQUENCE OF Sc553NetworkIntervalEntry
    ACCESS  not-accessible
    STATUS  mandatory
    DESCRIPTION
        "The sc553 Network Interval table.  This table supplements the
        entries in the DS1 AT&T performance table of the DS1
        MIB defined in RFC1406."
    ::= { sc553Performance 8 }

sc553NetworkIntervalEntry 	OBJECT-TYPE
    SYNTAX  Sc553NetworkIntervalEntry
    ACCESS  not-accessible
    STATUS  mandatory
    DESCRIPTION
        "An entry in the DS1 Interval table."
    INDEX   { sc553NetworkIntervalIndex, sc553NetworkIntervalNumber }
    ::= { sc553NetworkIntervalTable 1 }

Sc553NetworkIntervalEntry ::=
    SEQUENCE {
        sc553NetworkIntervalIndex		SCinstance,
        sc553NetworkIntervalNumber		INTEGER,
        sc553NetworkIntervalStats		OCTET STRING
}

sc553NetworkIntervalIndex OBJECT-TYPE
    SYNTAX  SCinstance
    ACCESS  read-only
    STATUS  mandatory
    DESCRIPTION
        "The index value which uniquely identifies the interface to
        which this entry is applicable.  This has the form of a
        SCinstance which defines the slot, line, drop, and interface,
        which in this case is a network interface."
    ::= { sc553NetworkIntervalEntry 1 }

sc553NetworkIntervalNumber 	OBJECT-TYPE
    SYNTAX  INTEGER (1..96)
    ACCESS  read-only
    STATUS  mandatory
    DESCRIPTION
        "A number between 1 and 96, where 1 is the most recently completed 
        minute interval and 96 is the least recently completed 15 minutes  
        interval   (assuming   that  all  96  intervals  are valid)."
    ::= { sc553NetworkIntervalEntry 2 }

sc553NetworkIntervalStats OBJECT-TYPE
	 SYNTAX OCTET STRING (SIZE (15))
	 ACCESS read-only
	 STATUS mandatory
	 DESCRIPTION
		"Returns a bitwise snapshot of the statistics.

		 Octet 1 bit 7 - parity   
			 bit 6 - 2^15	Errored Seconds 
			 bit 5 - 2^14
			 bit 4 - 2^15	Severely Errored Seconds
			 bit 3 - 2^14
			 bit 2 - 2^15	Bursty Errored Seconds
			 bit 1 - 2^14
			 bit 0 - 1: 	New Interval

		 Octet 2 bit 7 - parity   
			 bit 6 - 2^13   Errored Seconds
			 bit 5 - 2^12
			 bit 4 - 2^11
			 bit 3 - 2^10
			 bit 2 - 2^9
			 bit 1 - 2^8
			 bit 0 - 2^7

		 Octet 3 bit 7 - parity   
			 bit 6 - 2^6	Errored Seconds
			 bit 5 - 2^5
			 bit 4 - 2^4
			 bit 3 - 2^3
			 bit 2 - 2^2
			 bit 1 - 2^1
			 bit 0 - 2^0

		 Octet 4 bit 7 - parity   
			 bit 6 - 2^13 	Severely Errored Seconds
			 bit 5 - 2^12
			 bit 4 - 2^11
			 bit 3 - 2^10
			 bit 2 - 2^9
			 bit 1 - 2^8
			 bit 0 - 2^7

		 Octet 5 bit 7 - parity   
			 bit 6 - 2^6 	Severely Errored Seconds	
			 bit 5 - 2^5
			 bit 4 - 2^4
			 bit 3 - 2^3
			 bit 2 - 2^2
			 bit 1 - 2^1
			 bit 0 - 2^0

		 Octet 6 bit 7 - parity   
			 bit 6 - 2^13 	Bursty Errored Seconds	
			 bit 5 - 2^12
			 bit 4 - 2^11
			 bit 3 - 2^10
			 bit 2 - 2^9
			 bit 1 - 2^8
			 bit 0 - 2^7

		 Octet 7 bit 7 - parity   
			 bit 6 - 2^6 	Bursty Errored Seconds
			 bit 5 - 2^5
			 bit 4 - 2^4
			 bit 3 - 2^3
			 bit 2 - 2^2
			 bit 1 - 2^1
			 bit 0 - 2^0

		 Octet 8 bit 7 - parity   
			 bit 6 - fu           
			 bit 5 - fu
			 bit 4 - 2^15	Unavailable Seconds
			 bit 3 - 2^14
			 bit 2 - f/u
			 bit 1 - 2^7 	Loss of Frame Count
			 bit 0 - 2^7	Controlled Slip Seconds

		 Octet 9 bit 7 - parity   
			 bit 6 - 2^13 	Unavailable Seconds
			 bit 5 - 2^12
			 bit 4 - 2^11
			 bit 3 - 2^10
			 bit 2 - 2^9
			 bit 1 - 2^8
			 bit 0 - 2^7

	        Octet 10 bit 7 - parity   
			 bit 6 - 2^6 	Unavailable Seconds
			 bit 5 - 2^5
			 bit 4 - 2^4
			 bit 3 - 2^3
			 bit 2 - 2^2
			 bit 1 - 2^1
			 bit 0 - 2^0

		Octet 11 bit 7 - parity   
			 bit 6 - 2^6  	Controlled Slip Second
			 bit 5 - 2^5
			 bit 4 - 2^4
			 bit 3 - 2^3
			 bit 2 - 2^2
			 bit 1 - 2^1
			 bit 0 - 2^0

		Octet 12 bit 7 - parity   
			 bit 6 - 2^6 	Loss of Frame Count
			 bit 5 - 2^5
			 bit 4 - 2^4
			 bit 3 - 2^3
			 bit 2 - 2^2
			 bit 1 - 2^1
			 bit 0 - 2^0

		Octet 13 bit 7 - parity   
			 bit 6 - fu           
			 bit 5 - fu  
			 bit 4 - fu
			 bit 3 - fu  
			 bit 2 - fu  
			 bit 1 - fu  
			 bit 0 - fu 

		Octet 14 bit 7 - parity   
			 bit 6 - fu           
			 bit 5 - fu  
			 bit 4 - fu
			 bit 3 - fu  
			 bit 2 - fu  
			 bit 1 - fu  
			 bit 0 - fu 


		Octet 15 bit 7 - parity   
			 bit 6 - 2^6 	Interval 1 thru 96
			 bit 5 - 2^5
			 bit 4 - 2^4
			 bit 3 - 2^3
			 bit 2 - 2^2
			 bit 1 - 2^1
			 bit 0 - 2^0

		"    ::= { sc553NetworkIntervalEntry 3 }


 -- 
--
--                     ATT FarEnd Interval Performance Table
-- 



sc553FarEndIntervalTable 	OBJECT-TYPE
    SYNTAX  SEQUENCE OF Sc553FarEndIntervalEntry
    ACCESS  not-accessible
    STATUS  mandatory
    DESCRIPTION
        "The sc553 FarEnd Interval table.  This table supplements the
        entries in the DS1 AT&T performance table of the DS1
        MIB defined in RFC1406."
    ::= { sc553Performance 9 }

sc553FarEndIntervalEntry 	OBJECT-TYPE
    SYNTAX  Sc553FarEndIntervalEntry
    ACCESS  not-accessible
    STATUS  mandatory
    DESCRIPTION
        "An entry in the DS1 Interval table."
    INDEX   { sc553FarEndIntervalIndex, sc553FarEndIntervalNumber }
    ::= { sc553FarEndIntervalTable 1 }

Sc553FarEndIntervalEntry ::=
    SEQUENCE {
        sc553FarEndIntervalIndex		SCinstance,
        sc553FarEndIntervalNumber		INTEGER,
        sc553FarEndIntervalStats		OCTET STRING
}

sc553FarEndIntervalIndex OBJECT-TYPE
    SYNTAX  SCinstance
    ACCESS  read-only
    STATUS  mandatory
    DESCRIPTION
        "The index value which uniquely identifies the interface to
        which this entry is applicable.  This has the form of a
        SCinstance which defines the slot, line, drop, and interface,
        which in this case is a network interface."
    ::= { sc553FarEndIntervalEntry 1 }

sc553FarEndIntervalNumber 	OBJECT-TYPE
    SYNTAX  INTEGER (1..96)
    ACCESS  read-only
    STATUS  mandatory
    DESCRIPTION
        "A number between 1 and 96, where 1 is the most recently completed 
        minute interval and 96 is the least recently completed 15 minutes  
        interval   (assuming   that  all  96  intervals  are valid)."
    ::= { sc553FarEndIntervalEntry 2 }

sc553FarEndIntervalStats OBJECT-TYPE
	 SYNTAX OCTET STRING (SIZE (15))
	 ACCESS read-only
	 STATUS mandatory
	 DESCRIPTION
		"Returns a bitwise snapshot of the statistics.

		 Octet 1 bit 7 - parity   
			 bit 6 - 2^15	Errored Seconds 
			 bit 5 - 2^14
			 bit 4 - 2^15	Severely Errored Seconds
			 bit 3 - 2^14
			 bit 2 - 2^15	Bursty Errored Seconds
			 bit 1 - 2^14
			 bit 0 - 1: 	New Interval

		 Octet 2 bit 7 - parity   
			 bit 6 - 2^13   Errored Seconds
			 bit 5 - 2^12
			 bit 4 - 2^11
			 bit 3 - 2^10
			 bit 2 - 2^9
			 bit 1 - 2^8
			 bit 0 - 2^7

		 Octet 3 bit 7 - parity   
			 bit 6 - 2^6	Errored Seconds
			 bit 5 - 2^5
			 bit 4 - 2^4
			 bit 3 - 2^3
			 bit 2 - 2^2
			 bit 1 - 2^1
			 bit 0 - 2^0

		 Octet 4 bit 7 - parity   
			 bit 6 - 2^13 	Severely Errored Seconds
			 bit 5 - 2^12
			 bit 4 - 2^11
			 bit 3 - 2^10
			 bit 2 - 2^9
			 bit 1 - 2^8
			 bit 0 - 2^7

		 Octet 5 bit 7 - parity   
			 bit 6 - 2^6 	Severely Errored Seconds	
			 bit 5 - 2^5
			 bit 4 - 2^4
			 bit 3 - 2^3
			 bit 2 - 2^2
			 bit 1 - 2^1
			 bit 0 - 2^0

		 Octet 6 bit 7 - parity   
			 bit 6 - 2^13 	Bursty Errored Seconds	
			 bit 5 - 2^12
			 bit 4 - 2^11
			 bit 3 - 2^10
			 bit 2 - 2^9
			 bit 1 - 2^8
			 bit 0 - 2^7

		 Octet 7 bit 7 - parity   
			 bit 6 - 2^6 	Bursty Errored Seconds
			 bit 5 - 2^5
			 bit 4 - 2^4
			 bit 3 - 2^3
			 bit 2 - 2^2
			 bit 1 - 2^1
			 bit 0 - 2^0

		 Octet 8 bit 7 - parity   
			 bit 6 - fu    	
			 bit 5 - fu   	
			 bit 4 - 2^15	Unavailable Seconds
			 bit 3 - 2^14
			 bit 2 - f/u
			 bit 1 - 2^7 	Loss of Frame Count
			 bit 0 - 2^7	Controlled Slip Seconds

		 Octet 9 bit 7 - parity   
			 bit 6 - 2^13 	Unavailable Seconds
			 bit 5 - 2^12
			 bit 4 - 2^11
			 bit 3 - 2^10
			 bit 2 - 2^9
			 bit 1 - 2^8
			 bit 0 - 2^7

	        Octet 10 bit 7 - parity   
			 bit 6 - 2^6 	Unavailable Seconds
			 bit 5 - 2^5
			 bit 4 - 2^4
			 bit 3 - 2^3
			 bit 2 - 2^2
			 bit 1 - 2^1
			 bit 0 - 2^0

		Octet 11 bit 7 - parity   
			 bit 6 - 2^6  	Controlled Slip Second
			 bit 5 - 2^5
			 bit 4 - 2^4
			 bit 3 - 2^3
			 bit 2 - 2^2
			 bit 1 - 2^1
			 bit 0 - 2^0

		Octet 12 bit 7 - parity   
			 bit 6 - 2^6 	Loss of Frame Count
			 bit 5 - 2^5
			 bit 4 - 2^4
			 bit 3 - 2^3
			 bit 2 - 2^2
			 bit 1 - 2^1
			 bit 0 - 2^0


		Octet 13 bit 7 - parity   
			 bit 6 - fu           
			 bit 5 - fu  
			 bit 4 - fu
			 bit 3 - fu  
			 bit 2 - fu  
			 bit 1 - fu  
			 bit 0 - fu 

		Octet 14 bit 7 - parity   
			 bit 6 - fu           
			 bit 5 - fu  
			 bit 4 - fu
			 bit 3 - fu  
			 bit 2 - fu  
			 bit 1 - fu  
			 bit 0 - fu 

		Octet 15 bit 7 - parity   
			 bit 6 - 2^6 	Interval 1 thru 96
			 bit 5 - 2^5
			 bit 4 - 2^4
			 bit 3 - 2^3
			 bit 2 - 2^2
			 bit 1 - 2^1
			 bit 0 - 2^0

		"    ::= { sc553FarEndIntervalEntry 3}




--*****************************************************************************
--                   Statistics Collection
--*****************************************************************************

sc553StoreUserTotals OBJECT-TYPE
	SYNTAX INTEGER {
		   normal(1),  -- read-only
		   store(2)    -- write-only
	       }
	ACCESS  read-write
	STATUS  mandatory
	DESCRIPTION
		 "A set of this object will be broadcasted to every
		 sc553 in the shelf.  Upon receiving the broadcast,
		 the sc553 will write the contents of sc553TotalUserStat
		 to memory for collection at a later time.
		 A get of this object will always return a 1."
	::= { sc553Performance 10 }


sc553StoreUserIntervals OBJECT-TYPE
	SYNTAX INTEGER {
		   normal(1),  -- read-only
		   store(2)    -- write-only
	       }
	ACCESS  read-write
	STATUS  mandatory
	DESCRIPTION
		 "A set of this object will be broadcasted to every
		 sc553 in the shelf.  Upon receiving the broadcast,
		 the sc553 will write the contents of sc553UserIntervalStats
		 for each interval to memory for collection at a later time.
		 A get of this object will always return a 1."
	::= { sc553Performance 11 }


sc553ShelfUserTotals OBJECT-TYPE
	 SYNTAX OCTET STRING (SIZE (0..465))
	 ACCESS read-only
	 STATUS mandatory
	 DESCRIPTION
	 "Collects the User Totals that were stored by the set 
	  of sc553StoreUserTotals for all sc553s in the shelf.
          The data for each sc553 is contained in 15 octet groupings
          where each grouping is encoded in the following way:

	  Octet 1:     Control Octet containing the slot (1-32) of the sc553 
	               and an invalid/valid data flag. The data in the following
		       14 octets is invalid if the MSB is set.
          Octet 2,3:   Errored Seconds Total
	  Octet 4,5:   Bursty Errored Seconds Total
	  Octet 6,7:   Severely Errored Seconds Total
	  Octet 8,9:   Unavailable Seconds Total
	  Octet 10,11: CRC Errors Total
	  Octet 12,13: Loss of Frame Total
	  Octet 14,15: Controlled Slip Seconds Total

	  If there are no sc553s in the shelf then a null string is returned."
	
	::= { sc553Performance 12 }
 

sc553ShelfUserIntvlsTable OBJECT-TYPE
    SYNTAX  SEQUENCE OF Sc553ShelfUserIntervalsEntry
    ACCESS  not-accessible
    STATUS  mandatory
    DESCRIPTION
          "The sc553ShelfUserIntvlsTable contains the user statistics
	   for all sc553s in the shelf."
        ::= { sc553Performance 13 }

sc553ShelfUserIntervalsEntry 	OBJECT-TYPE
    SYNTAX  Sc553ShelfUserIntervalsEntry
    ACCESS  not-accessible
    STATUS  mandatory
    DESCRIPTION
        "An entry in the  Shelf User Intervals table."
    INDEX   { sc553ShelfUserIntvlsIndex }
    ::= { sc553ShelfUserIntvlsTable 1 }

Sc553ShelfUserIntervalsEntry ::=
    SEQUENCE {
        sc553ShelfUserIntvlsIndex		INTEGER,
        sc553ShelfUserIntervals  		OCTET STRING
}

sc553ShelfUserIntvlsIndex OBJECT-TYPE
    SYNTAX  INTEGER (1..96)
    ACCESS  read-only
    STATUS  mandatory
    DESCRIPTION
        "The index value which uniquely determines the interval."
    ::= { sc553ShelfUserIntervalsEntry 1 }

sc553ShelfUserIntervals OBJECT-TYPE
	 SYNTAX OCTET STRING (SIZE (0..465))
	 ACCESS read-only
	 STATUS mandatory
	 DESCRIPTION
	 "Collects the User Statistics that were stored by the set of 
	  sc553StoreUserIntervals for the interval given by
          sc553ShelfUserIntervalsIndex for all sc553s in the shelf.
          The data for each sc553 is contained in 15 octet groupings
          where each grouping is encoded in the following way:

	  Octet 1:     Control Octet containing the slot (1-32) of the sc553 
	               and an invalid/valid data flag. The data in the following
		       14 octets is invalid if the MSB is set.
          Octet 2,3:   Errored Seconds 
	  Octet 4,5:   Bursty Errored Seconds
	  Octet 6,7:   Severely Errored Seconds
	  Octet 8,9:   Unavailable Seconds
	  Octet 10,11: CRC Errors
	  Octet 12,13: Loss of Frame
	  Octet 14,15: Controlled Slip Seconds

	  If there are no sc553s in the shelf then a null string is returned."
	
	::= { sc553ShelfUserIntervalsEntry 2 }
 

END
