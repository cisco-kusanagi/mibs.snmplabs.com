-- Copyright 1994 General DataComm Inc., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.

-- Revision History
-- Version   Date	Name		Description
-- 1.00A     10-Feb-95  E. Moreno-Leon  Initial Revision
-- 1.00B     01-Sep-95	C. Amorossi	Added Interface Comments
-- 1.00C     12-Mar-96	E. Moreno-Leon	Added Major and Minor BER Alarms

HDSL700G2-MIB DEFINITIONS ::= BEGIN

IMPORTS
	OBJECT-TYPE			FROM RFC-1212
	DisplayString			FROM RFC1213-MIB
	hdsl700G2                       FROM GDCHDSL-MIB;

hdsl700G2System          OBJECT IDENTIFIER ::= { hdsl700G2 1 }
hdsl700G2Version         OBJECT IDENTIFIER ::= { hdsl700G2System 1 }

-- This mib is a subset of the HDSL mib for the 700G2 product.

-- ***************************************************************************
-- The interfaces are defined as follows:
--	Unit	0
--	E1	1
--	Loop1	2
--	Loop2	3
-- ***************************************************************************

 gdc700G2SystemMIBversion OBJECT-TYPE
     	SYNTAX DisplayString (SIZE (5))
     	ACCESS read-only
     	STATUS mandatory
     	DESCRIPTION
     		"Identifies the version of the MIB. The format of the version
     		is x.yzT, where 'x' identifies the major revision number, 'y'
     		identifies the minor revision number, 'z' identifies the
     		typographical revision, and T identifies the test revision.
     		Acceptable values for the individual revision components are
     		as follows:
 
     		x: 1 - 9
     		y: 0 - 9
     		z: 0 - 9
     		T: A - Z
 
     		Upon formal release, no designation for the test revision will
     		be present."
     	::= { hdsl700G2Version 1 }

-- ********************************************************************
-- GDC Hdsl Alarm Object Identifier Definitions
-- ********************************************************************
 hdsl700G2Alarms          OBJECT IDENTIFIER ::= { hdsl700G2 2 }

 hdsl700G2NoResponseAlm		OBJECT IDENTIFIER ::= { hdsl700G2Alarms 1 }
 hdsl700G2DiagRxErrAlm		OBJECT IDENTIFIER ::= { hdsl700G2Alarms 2 }
 hdsl700G2PowerUpAlm		OBJECT IDENTIFIER ::= { hdsl700G2Alarms 3 }
 hdsl700G2UnitFailure           OBJECT IDENTIFIER ::= { hdsl700G2Alarms 4 }
 hdsl700G2ChecksumCorrupt       OBJECT IDENTIFIER ::= { hdsl700G2Alarms 5 }
 hdsl700G2LossofSignal		OBJECT IDENTIFIER ::= { hdsl700G2Alarms 6 }
 hdsl700G2UnavailableSec	OBJECT IDENTIFIER ::= { hdsl700G2Alarms 7 }
 hdsl700G2ErrorSec		OBJECT IDENTIFIER ::= { hdsl700G2Alarms 8 }
 hdsl700G2LossofSyncWord	OBJECT IDENTIFIER ::= { hdsl700G2Alarms 9 }
 hdsl700G2LossofFrameAlign	OBJECT IDENTIFIER ::= { hdsl700G2Alarms 10 }
 hdsl700G2AllOnes		OBJECT IDENTIFIER ::= { hdsl700G2Alarms 11 }
 hdsl700G2RemoteLossofSig	OBJECT IDENTIFIER ::= { hdsl700G2Alarms 12 }
 hdsl700G2RemoteAlarmInd	OBJECT IDENTIFIER ::= { hdsl700G2Alarms 13 }
 hdsl700G2MajorBER      	OBJECT IDENTIFIER ::= { hdsl700G2Alarms 14 }
 hdsl700G2MinorBER		OBJECT IDENTIFIER ::= { hdsl700G2Alarms 15 }
 
 


-- ALARM			Maskable	Valid Interfaces
--===============================================================
--hdslNoResponseAlm		No		Unit
--hdslDiagRxErrAlm              No              Unit
--hdslPowerUpAlm		No		Unit
--hdslUnitFailure               No              Unit
--hdslChecksumCorrupt           No              Unit
--hdslLossofSignal		Yes		E1, L1, L2 
--hdslUnavailableSec		Yes		E1, L1, L2
--hdslErrorSec			Yes		E1, L1, L2
--hdslLossofSyncWord		Yes		L1, L2
--hdslLossofFrameAlign		Yes		E1
--hdslAllOnes			Yes		E1
--hdslRemoteLossofSig		Yes		E1
--hdslRemoteAlarmInd		Yes		E1 
--hdsl700G2MajorBER		Yes		L1, L2
--hdsl700G2MinorBER		Yes		L1, L2





END
