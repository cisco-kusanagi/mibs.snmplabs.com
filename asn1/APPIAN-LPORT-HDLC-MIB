--
--      Title:  Appian HDLC MIB
--
--      Dated:  01/02/2000
--      Author: Brian Johnson
--
--      Description:
--
--      This MIB file contains the definitions and support for the Appian
--      Optical Services Access Platform(s).
-- 
--

APPIAN-LPORT-HDLC-MIB DEFINITIONS ::= BEGIN

    IMPORTS
        acLport, AcNodeId, AcSlotNumber             FROM APPIAN-SMI-MIB
        MODULE-IDENTITY, OBJECT-TYPE, Counter64     FROM SNMPv2-SMI
        TruthValue                                  FROM SNMPv2-TC;

acLogicalHdlc   MODULE-IDENTITY
    LAST-UPDATED        "0003190000Z"
    ORGANIZATION        "Appian Communications, Inc."
    CONTACT-INFO        "Brian Johnson"
    DESCRIPTION
        "Appian Communications HDLC Configuration and Statistics MIB."
    REVISION
        "0002010000Z"
    DESCRIPTION
        "Initial release"

    ::= { acLport 4 }

acLogicalHdlcTable      OBJECT-TYPE
    SYNTAX              SEQUENCE OF AcLogicalHdlcEntry
    MAX-ACCESS          not-accessible
    STATUS              current
    DESCRIPTION
        "A table containing the statistics parameters for HDLC data streams
        on the SONET board.  The index key used is type.channel."

    ::= { acLogicalHdlc 1 }

acLogicalHdlcEntry      OBJECT-TYPE
    SYNTAX              AcLogicalHdlcEntry
    MAX-ACCESS          not-accessible
    STATUS              current
    DESCRIPTION
        "A row in the HDLC table containing all HDLC level statistics and
        configuration for a specific HDLC data stream on the SONET board."

    INDEX { acLogicalHdlcNodeId, 
            acLogicalHdlcSlot, 
            acLogicalHdlcType, 
            acLogicalHdlcIndex }

    ::= { acLogicalHdlcTable 1 }

    AcLogicalHdlcEntry ::=
        SEQUENCE {
            acLogicalHdlcNodeId                         AcNodeId,
            acLogicalHdlcSlot                           AcSlotNumber,
            acLogicalHdlcType                           INTEGER,
            acLogicalHdlcIndex                          INTEGER,
            acLogicalHdlcStatsReset                     TruthValue,
            acLogicalHdlcRxFifoOverrun                  Counter64,
            acLogicalHdlcRxMaxPktLenViolation           Counter64,
            acLogicalHdlcRxFCSError                     Counter64,
            acLogicalHdlcRxNonOctetAligned              Counter64,
            acLogicalHdlcRxHdlcPktAbort                 Counter64,
            acLogicalHdlcRxBufferStarvation             Counter64,
            acLogicalHdlcTxFifoUnderrun                 Counter64,
            acLogicalHdlcRxBundleDiscardDupSeq          Counter64,
            acLogicalHdlcRxBundleDiscardMissSeq         Counter64,
            acLogicalHdlcRxBundleDiscardQDepth          Counter64,
            acLogicalHdlcIngressRxFrames                Counter64,
            acLogicalHdlcEgressTxFrames                 Counter64
        }

acLogicalHdlcNodeId       OBJECT-TYPE
    SYNTAX  AcNodeId
    MAX-ACCESS  accessible-for-notify
    STATUS  current
    DESCRIPTION
    "The node id is the id for this specific node in the OSAP ring."

    ::= { acLogicalHdlcEntry 1 }

acLogicalHdlcSlot       OBJECT-TYPE
    SYNTAX  AcSlotNumber
    MAX-ACCESS  accessible-for-notify
    STATUS  current
    DESCRIPTION
    "The slot number within the chassis where the stats reside."

    ::= { acLogicalHdlcEntry 2 }


acLogicalHdlcType       OBJECT-TYPE
    SYNTAX      INTEGER {
                    ds1(1), 
                    ds3(2), 
                    dcc(3) 
                }
    MAX-ACCESS  accessible-for-notify
    STATUS      current
    DESCRIPTION
    "The type of data stream that this hdlc channel is framing. The
    current options are DS1, DS3, or DCC."
        
    ::= { acLogicalHdlcEntry 3 }

acLogicalHdlcIndex    OBJECT-TYPE
    SYNTAX      INTEGER
    MAX-ACCESS  accessible-for-notify
    STATUS      current
    DESCRIPTION
    "The acLogicalHdlcIndex is the index for this table for the specified
    type.  For DS1 and DS3, the index is the same as the index in the
    timeslot table that this entity corresponds.  For the case of Appian
    DCC, the index simply a number from 1-4."

    ::= { acLogicalHdlcEntry 4 }

acLogicalHdlcStatsReset OBJECT-TYPE
    SYNTAX      TruthValue
    MAX-ACCESS  read-write
    STATUS      current
    DESCRIPTION
    "Setting this attribute to True(1) will force all statistics for this
    row to be cleared and set to zero (0) values.  Used for debugging, 
    clearing statistics can trouble with trending and long term statistics
    collection by AppianVista or 3rd party trending tools."

    ::= { acLogicalHdlcEntry 5 }

acLogicalHdlcRxFifoOverrun      OBJECT-TYPE
    SYNTAX       Counter64
    MAX-ACCESS   read-only
    STATUS       current
    DESCRIPTION
    "The total number of receive FIFO overruns that occurred in the 
    hdlc controller for this specified channel number.  This error
    occurs when attemps are made to write data to a channel which
    is already full."

    ::= { acLogicalHdlcEntry 6 }

acLogicalHdlcRxMaxPktLenViolation       OBJECT-TYPE
    SYNTAX      Counter64
    MAX-ACCESS  read-only
    STATUS      current
    DESCRIPTION
    "The total number of receive max packet packet length violations
    that occurred in the hdcl controller for the specified channel
    number.  This error occurs when an hdlc packet is received that
    is greater than the maximum packet length which is programmed to
    be 2048 bytes. "

    ::= { acLogicalHdlcEntry 7 }

acLogicalHdlcRxFCSError OBJECT-TYPE
    SYNTAX      Counter64
    MAX-ACCESS  read-only
    STATUS      current
    DESCRIPTION
    "The total number of receive FCS errors that occurred in the 
    hdlc controller for this specified channel number. The FCS error
    is generated when the FCS from HDLC packet receieved differs from
    the FCS that is computed by the HDLC controller."

    ::= { acLogicalHdlcEntry 8 }

acLogicalHdlcRxNonOctetAligned  OBJECT-TYPE
    SYNTAX      Counter64
    MAX-ACCESS  read-only
    STATUS      current
    DESCRIPTION
    "The total number of receive non-octet aligned errors that occurred 
    in the hdlc controller for this specified channel number. This 
    error occurs when the receieved data stream is not octet aligned." 

    ::= { acLogicalHdlcEntry 9 }

acLogicalHdlcRxHdlcPktAbort     OBJECT-TYPE
    SYNTAX      Counter64
    MAX-ACCESS  read-only
    STATUS      current
    DESCRIPTION
    "The total number of receive hdlc abort errors that occurred 
    in the hdlc controller for this specified channel number.  This
    error occurs when and abort code (at least 7 contiguous 1's)
    is received."

    ::= { acLogicalHdlcEntry 10 }

acLogicalHdlcRxBufferStarvation         OBJECT-TYPE
    SYNTAX      Counter64
    MAX-ACCESS  read-only
    STATUS      current
    DESCRIPTION
    "The total number of receive buffer starvation errors that occurred 
    in the hdlc controller for this specified channel number. "

    ::= { acLogicalHdlcEntry 11 }

acLogicalHdlcTxFifoUnderrun      OBJECT-TYPE
    SYNTAX      Counter64
    MAX-ACCESS  read-only
    STATUS      current
    DESCRIPTION
    "The total number of transmit FIFO underrun errors that occurred 
    in the hdlc controller for this specified channel number.  This
    error occurs when attempts are made to read data from a channel
    that does not have any data ready to send."

    ::= { acLogicalHdlcEntry 12 }

acLogicalHdlcRxBundleDiscardDupSeq       OBJECT-TYPE
    SYNTAX      Counter64
    MAX-ACCESS  read-only
    STATUS      current
    DESCRIPTION
    "The total number of receive bundle discard duplicate sequence errors that 
     occurred in the hdlc controller for this specified channel number. "

    ::= { acLogicalHdlcEntry 13 }


acLogicalHdlcRxBundleDiscardMissSeq       OBJECT-TYPE
    SYNTAX      Counter64
    MAX-ACCESS  read-only
    STATUS      current
    DESCRIPTION
    "The total number of receive bundle discard missed sequence errors that 
     occurred in the hdlc controller for this specified channel number. "

    ::= { acLogicalHdlcEntry 14 }

acLogicalHdlcRxBundleDiscardQDepth       OBJECT-TYPE
    SYNTAX      Counter64
    MAX-ACCESS  read-only
    STATUS      current
    DESCRIPTION
    "The total number of receive bundle discard queue depth errors that 
     occurred in the hdlc controller for this specified channel number. "

    ::= { acLogicalHdlcEntry 15 }

acLogicalHdlcIngressRxFrames       OBJECT-TYPE
    SYNTAX      Counter64
    MAX-ACCESS  read-only
    STATUS      current
    DESCRIPTION
    "The total number of ingress receive frames that the MLC has received 
     from the hdlc controller for this specified channel number. "

    ::= { acLogicalHdlcEntry 16 }

acLogicalHdlcEgressTxFrames       OBJECT-TYPE
    SYNTAX      Counter64
    MAX-ACCESS  read-only
    STATUS      current
    DESCRIPTION
    "The total number of egress transmit frames that the MLC has transmitted 
     to the hdlc controller for this specified channel number. "

    ::= { acLogicalHdlcEntry 17 }




END
