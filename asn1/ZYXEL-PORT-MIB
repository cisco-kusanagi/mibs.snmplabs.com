-- ZyXEL Communications Corporation
-- Private Enterprise MIB definition 
  
-- This file describes the ZyXEL Communications Corporation Enterprise MIB.
-- It contains ZyXEL products OIDs, and common managed objects.

-- $Log: ZYXEL-PORT-MIB.mib $
-- Revision 1.13  2014/09/23 01:18:46  MandyLi
-- support auto port speed
-- Revision 1.12  2013/12/06 07:07:58  ccho
-- remove uncessary imports
-- Revision 1.11  2013/11/20 06:54:14  ccho
-- renaming identifier name for SMI.V2
-- Revision 1.10  2013/11/06 05:42:20  ccho
-- fix mib style
-- Revision 1.9  2013/08/01 06:53:40  Aga
-- bug fix: for clear silverCreek faild message
-- Revision 1.8  2013/06/26 07:14:11  Mandy
-- Support notified trap for error recovered
-- Revision 1.7  2013/06/26 07:00:22  Aga
-- merge 
--      Revision 1.7  2013/03/22 10:01:47  Neng
--      Support 10GBase Media Type.
-- Revision 1.6  2012/12/25 07:19:22  Aga
-- Revision 1.5  2012/09/19 07:44:19  Kevin
-- if it's leaf node, revise the vender name from zyxel to zy
-- Revision 1.4  2012/08/22 09:47:40  Kevin
-- clean warning for SNMPc
-- Revision 1.3  2012/08/09 03:41:48  shobi
-- Support speed-duplex 40G
-- Revision 1.2  2012/07/05 06:24:18  Kevin
-- 1. upgrade from SNMP to SNMPv2 
-- 2. clean warning
-- Revision 1.1  2012/05/30 07:50:25  Kevin
-- Initial revision

ZYXEL-PORT-MIB DEFINITIONS ::= BEGIN
    IMPORTS
	OBJECT-TYPE
		FROM SNMPv2-SMI			-- RFC2578	
		
	MODULE-IDENTITY
		FROM SNMPv2-SMI
		
	DisplayString                                          
	  	FROM SNMPv2-TC
	  	
	EnabledStatus
		FROM  P-BRIDGE-MIB
		
	dot1dBasePort
       	FROM BRIDGE-MIB

    ifIndex
    	FROM IF-MIB					-- RFC2863
    	
    NOTIFICATION-TYPE
        FROM SNMPv2-SMI
       
	esMgmt			
		FROM ZYXEL-ES-SMI;

	zyxelPort MODULE-IDENTITY
		LAST-UPDATED	"201207010000Z"    
		ORGANIZATION "Enterprise Solution ZyXEL"     
		CONTACT-INFO
			""	   
		DESCRIPTION
			"The subtree for port"
		::= { esMgmt 61 }

	zyxelPortSetup 			OBJECT IDENTIFIER ::= { zyxelPort 1 }
	zyxelPortStatus 		OBJECT IDENTIFIER ::= { zyxelPort 2 }
	zyxelPortNotifications 	OBJECT IDENTIFIER ::= { zyxelPort 3 }
	
	  
-- *******************************************************************
-- *
-- * zyxelPortSetup
-- *
-- *******************************************************************

-- zyxelPortTable
        zyxelPortTable  OBJECT-TYPE
        SYNTAX	SEQUENCE OF ZyxelPortEntry 
        MAX-ACCESS  not-accessible
        STATUS  current
        DESCRIPTION
                 	"The table contains port configuration. "
        ::= { zyxelPortSetup 1 }
        
		zyxelPortEntry  OBJECT-TYPE
        SYNTAX	ZyxelPortEntry 
        MAX-ACCESS	not-accessible
        STATUS	current
        DESCRIPTION    	
					"An entry contains port configuration. "
        INDEX          	{ dot1dBasePort }
        ::= { zyxelPortTable 1 }

        ZyxelPortEntry ::=
          SEQUENCE {
        	zyPortSpeedDuplex			INTEGER,
        	zyPortFlowControlState		INTEGER,
        	zyPortName					DisplayString,
         	zyPortIntrusionLockState	EnabledStatus,
        	zyPortCX4CableLength		INTEGER,
			zyPort10GMediaType			INTEGER
           }

        zyPortSpeedDuplex OBJECT-TYPE
        SYNTAX  INTEGER {
            auto(0),
        	speed10Half(1),
        	speed10Full(2),
        	speed100Half(3),
        	speed100Full(4),
        	speed1000Full(5),
        	speed10000Full(6),
        	speed12000Full(7),
        	speed40000Full(8),
			speed1000Auto(9),
			speedAuto1000(10),
			speedAuto10000(11)
			
        }
        MAX-ACCESS  read-write
        STATUS  current
        DESCRIPTION
			"Select The speed and the duplex mode of the Ethernet connection on this port. Selecting Auto 
			(auto-negotiation) allows one port to negotiate with a peer port automatically to obtain the 
			connection speed and duplex mode that both ends support. When auto-negotiation is turned on, 
			a port on the Switch negotiates with the peer automatically to determine the connection speed 
			and duplex mode. If the peer port does not support auto-negotiation or turns off this feature, 
			the Switch determines the connection speed by detecting the signal on the cable and using half 
			duplex mode. Thus requiring you to make sure that the settings of the peer port are the same in 
			order to connect."
        ::= { zyxelPortEntry 1 }

        zyPortFlowControlState OBJECT-TYPE
        SYNTAX  EnabledStatus
        MAX-ACCESS  read-write
        STATUS  current
        DESCRIPTION
			"Enable/Disable the flow control on this port. A concentration of traffic on a port decreases port 
			bandwidth and overflows buffer memory causing packet discards and frame losses. Flow control is used 
			to regulate transmission of signals to match the bandwidth of the receiving port."
        ::= { zyxelPortEntry 2 }

        zyPortName  OBJECT-TYPE
        SYNTAX  DisplayString
        MAX-ACCESS  read-write
        STATUS  current
        DESCRIPTION
			"Enter a descriptive name that identifies this port."
        ::= { zyxelPortEntry 3 }

		zyPortIntrusionLockState OBJECT-TYPE
        SYNTAX  EnabledStatus
        MAX-ACCESS  read-write
        STATUS  current
        DESCRIPTION
			"Enable/Disable intrusion lock on the port(s) and the port cannot be connected again after you 
			disconnected the cable."
        ::= { zyxelPortEntry 4 }
        
        zyPortCX4CableLength OBJECT-TYPE
        SYNTAX  INTEGER {
        	halfMeters(0),
        	oneMeters(1),
        	threeMeters(2),
        	fiveMeters(3),
        	tenMeters(4),
        	fifteenMeters(5)
        }
        MAX-ACCESS  read-write
        STATUS  current
        DESCRIPTION
			"Set the number of meters for the length of the 10GBASE-CX4 cable you use to connect between the swtich 
			and another switch for stacking."
        ::= { zyxelPortEntry 5}    

        zyPort10GMediaType OBJECT-TYPE
        SYNTAX  INTEGER {
        	sfpPlus(0),
        	dac10g(1)
        }
        MAX-ACCESS  read-write
        STATUS  current
        DESCRIPTION
			"Set the 10GBase media type."
        ::= { zyxelPortEntry 6}

-- *******************************************************************
-- *
-- * zyxelPortStatus
-- *
-- *******************************************************************

-- zyxelPortInfoTable
        zyxelPortInfoTable  OBJECT-TYPE
        SYNTAX	SEQUENCE OF ZyxelPortInfoEntry 
        MAX-ACCESS  not-accessible
        STATUS  current
        DESCRIPTION
                 	"The table contains port information. "
        ::= { zyxelPortStatus 1 }
        
		zyxelPortInfoEntry  OBJECT-TYPE
        SYNTAX	ZyxelPortInfoEntry 
        MAX-ACCESS	not-accessible
        STATUS	current
        DESCRIPTION    	
					"An entry contains port information. "
        INDEX          	{ dot1dBasePort }
        ::= { zyxelPortInfoTable 1 }
        ZyxelPortInfoEntry ::=
           SEQUENCE {
        	zyPortModuleType		INTEGER,
        	zyPortLinkUpType		INTEGER,
        	zyPortTestStatus		INTEGER,
        	zyPortCounterReset		INTEGER
           }
		   
		zyPortModuleType  OBJECT-TYPE
        SYNTAX  INTEGER {
        	fastEthernet(0),
        	gigabitEthernet(1),
        	xgEthernet10000(2),
        	x1Ethernet40000(3)
        }
        MAX-ACCESS  read-only
        STATUS  current
        DESCRIPTION
			"This entry displays the speed type of modular."
        ::= { zyxelPortInfoEntry 1 }
		
		zyPortLinkUpType  OBJECT-TYPE
        SYNTAX  INTEGER { 	
       		down(0),
        	copper(1),
        	fiber(2),
        	xfp(3),
        	cx4(4)
        }
        MAX-ACCESS  read-only
        STATUS  current
        DESCRIPTION
			"The entry shows the linkUp cable type (copper, fiber, xfp or cx4) for the combo ports."
        ::= { zyxelPortInfoEntry 2 }
		
		zyPortTestStatus OBJECT-TYPE
        SYNTAX  INTEGER {
        	none(0),
        	underTesting(1),
        	success(2),
        	fail(3)
        }
        MAX-ACCESS  read-only
        STATUS  current
        DESCRIPTION
			"This entry displays latest loopback test status of port while performing loopback test."
        ::= { zyxelPortInfoEntry 3 } 

       
		zyPortCounterReset OBJECT-TYPE
        SYNTAX  EnabledStatus
        MAX-ACCESS  read-write
        STATUS  current
        DESCRIPTION
			"Enable this entry can reset port counter record."
        ::= { zyxelPortInfoEntry 4 } 

	   zyPortAutonegotiationFailed NOTIFICATION-TYPE
       OBJECTS {
				ifIndex
         }       
	   STATUS  current
       DESCRIPTION
               "Link speed and duplex mode autonegotiation has failed."
       ::= { zyxelPortNotifications 1 }
       
	   zyPortIntrusionLock NOTIFICATION-TYPE
       OBJECTS {
				ifIndex
         }       
	   STATUS  current
       DESCRIPTION
               "The cable is disconnected and the port cannot be connected again."
       ::= { zyxelPortNotifications 2 }               
        
	   zyPortAutonegotiationFailedRecovered NOTIFICATION-TYPE
       OBJECTS {
				ifIndex
         }       
	   STATUS  current
       DESCRIPTION
               "Link speed and duplex mode autonegotiation has recovered from failed."
       ::= { zyxelPortNotifications 3 }
        
		
END
