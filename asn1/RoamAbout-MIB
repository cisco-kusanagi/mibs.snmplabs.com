-- 
-- @DEC-COPYRIGHT@
-- 
-- RoamAbout MIB
--
--

RoamAbout-MIB

DEFINITIONS ::= BEGIN

IMPORTS
	enterprises, Counter, IpAddress FROM RFC1155-SMI
	OBJECT-TYPE FROM RFC-1212
	DisplayString, PhysAddress FROM RFC1213-MIB;

dec               OBJECT IDENTIFIER ::= { enterprises 36 }
ema               OBJECT IDENTIFIER ::= { dec 2 }
decMIBextension   OBJECT IDENTIFIER ::= { ema 18 }
roamabout         OBJECT IDENTIFIER ::= { decMIBextension 35 }


rabtPCCardType OBJECT-TYPE
        SYNTAX  INTEGER  {
                        none(1),
                        ds915(2),    -- 915Mhz DS card
                        ds2400(3),   -- non-IEEE 2.4Ghz DS card
                        fh2400(4),   -- non-IEEE 2.4Ghz FH card
			ds80211(5),   -- IEEE 802.11 2.4Ghz DS card
                        unknown(15)
                }
        ACCESS  read-only
        STATUS  mandatory
        DESCRIPTION
                "The type of PC card inserted in the Access Point."
        ::= { roamabout 1 }


rabtIPAddressState OBJECT-TYPE
        SYNTAX  INTEGER  {
                        volatile(1),
                        non-volatile(2)
                }
        ACCESS  read-write
        STATUS  mandatory
        DESCRIPTION
                "Determines the state of IP Address storage.
                 A value of 2 causes the current IP address
                 to be stored in NVRAM."
        ::= { roamabout 2 }


rabtBridgeMode OBJECT-TYPE
        SYNTAX  INTEGER  {
                        workgroup(1),
                        lan-to-lan(2),
                        lan-to-lan-hub(3)
                }
        ACCESS  read-write
        STATUS  mandatory
        DESCRIPTION
                "CURRENT Access Point bridge mode state.  LAN-to-LAN mode is
                 the improved name for 802.11.  LAN-to-LAN used to be called
                 full-bridge pre-802.11."
        ::= { roamabout 3 }

rabtUplineDumpMode OBJECT-TYPE
        SYNTAX  INTEGER  {
                        enabled(1),
                        disabled(2)
                }
        ACCESS  read-write
        STATUS  mandatory
        DESCRIPTION
                "Determines whether or not a dump file
                 is created on an Access Point crash."
        ::= { roamabout 4 }

rabtMemorySize OBJECT-TYPE
        SYNTAX  INTEGER
        ACCESS  read-only
        STATUS  mandatory
        DESCRIPTION
                "The size of the memory in the Access Point in Mbytes."
        ::= { roamabout 5 }

rabtUpgradeFlash OBJECT-TYPE
        SYNTAX  INTEGER  {
                upgrade-flash(1)
        }
        ACCESS  write-only
        STATUS  mandatory
        DESCRIPTION
                "Causes the Access Point to attempt a flash upgrade.
                 Be aware that this causes the Access Point to reset."
        ::= { roamabout 6 }

rabtForceUplineDump OBJECT-TYPE
        SYNTAX  INTEGER  {
                force-dump(1)
        }
        ACCESS  write-only
        STATUS  mandatory
        DESCRIPTION
                "Causes the Access Point to attempt a upline dump.
                 Be aware that this causes the Access Point to reset."
        ::= { roamabout 7 }

rabtStationName OBJECT-TYPE
        SYNTAX  DisplayString (SIZE (0..20))
        ACCESS  read-write
        STATUS  mandatory
        DESCRIPTION
                "The wireless station name sent out as part of
                 the beacon messages.  Valid only when a DS card
                 is inserted in the Access Point."
        ::= { roamabout 8 }

rabtIPSubnetMask OBJECT-TYPE
        SYNTAX  IpAddress
        ACCESS  read-write
        STATUS  mandatory
        DESCRIPTION
                "The IP subnet mask for this access Point."
        ::= { roamabout 9 }

rabtDSChannel OBJECT-TYPE
	SYNTAX  INTEGER  {
			typeA-f2425Mhz(2),
			typeB-f2460Mhz(3),
			typeC-f2484Mhz(4),
			typeD-f2430Mhz(5),	-- actually 2430.5 MHz
			ieee1-f2412Mhz(6),
			ieee3-f2422Mhz(7),
			ieee5-f2432Mhz(8),
			ieee2-f2442Mhz(9),
			ieee4-f2452Mhz(10),
			ieee6-f2462Mhz(11)
		}
	ACCESS  read-write
	STATUS  mandatory
	DESCRIPTION
		"The channel number for the wireless non-IEEE 2400DS card.
                 This value is only valid currently if a 2400DS card
                 is installed.  After changing this value, it will not
                 be loaded onto the card until reset is performed."
	::= { roamabout 10 }

rabtDSCountryVariant OBJECT-TYPE
	SYNTAX  INTEGER  {
                        unknown(1),
			north-america(2),
			europe(3),
			france(4),
			japan(5)
		}
	ACCESS  read-only
	STATUS  mandatory
	DESCRIPTION
		"Describes the country variant of the 2400DS card.
                 This value is only valid currently if a 2400DS card
                 is installed."
	::= { roamabout 11 }

rabtDSCurrentNWID OBJECT-TYPE
	SYNTAX  OCTET STRING  (SIZE  (2))
	ACCESS  read-only
	STATUS  mandatory
	DESCRIPTION
		"The WaveLAN Network ID (NWID) this RF-modem
		 is currently operating with."
	::= { roamabout 12 }


rabtEncryptionEnable OBJECT-TYPE
	SYNTAX  INTEGER  {
                        disable(1),
			enable(2)
		}
	ACCESS  read-write
	STATUS  mandatory
	DESCRIPTION
		"Used to enable or disable encryption of the wireless radio
                 signals if the installed PC Card supports encryption, and
                 the Access Point is in the 'trusted' security mode.  After
                 changing this value, it will not be loaded onto the card
                 until reset is performed.

                 This value varies from wliEncSelect in that it shows the
                 future value of the encryption mode after the next reset,
                 and wliEncSelect is read-only.

                 If the Access Point is in the 'non-trusted' security mode,
                 this parameter cannot be set via SNMP, only through the
                 console port." 

	::= { roamabout 13 }

--
-- This is the new PTP Diagnostic section.  It only applies to non-IEEE DS
-- cards.
--

rabtPTPDiag		  OBJECT IDENTIFIER ::= { roamabout 14 }

rabtPTPRemoteStationMAC OBJECT-TYPE
        SYNTAX  PhysAddress
        ACCESS  read-write
        STATUS  mandatory
        DESCRIPTION
                "The MAC address for the remote station to participate
                 in the Point-to-Point diagnostic test.

                 To initiate a search for a participating station, write the
                 broadcast address (FF-FF-FF-FF-FF-FF) to this variable."

        ::= { rabtPTPDiag 1 }

rabtPTPRemoteStationName OBJECT-TYPE
        SYNTAX  DisplayString (SIZE (0..20))
        ACCESS  read-only
        STATUS  mandatory
        DESCRIPTION
                "The wireless station name of the remote station
                 participating in the Point-to-Point diagnostic test."

        ::= { rabtPTPDiag 2 }

rabtPTPRemoteSignalLevel OBJECT-TYPE
        SYNTAX  INTEGER (0..36)
        ACCESS  read-only
        STATUS  mandatory
        DESCRIPTION
                "The last remote signal level value obtained from the 
                 Point-to-Point diagnostic test.

                 A value of 0 is returned if the last sample was not valid."

        ::= { rabtPTPDiag 3 }

rabtPTPRemoteNoiseLevel OBJECT-TYPE
        SYNTAX  INTEGER (0..36)
        ACCESS  read-only
        STATUS  mandatory
        DESCRIPTION
                "The last remote noise level value obtained from the
                 Point-to-Point diagnostic test.

                 A value of 0 is returned if the last sample was not valid."

        ::= { rabtPTPDiag 4 }

rabtPTPRemoteSignalQuality OBJECT-TYPE
        SYNTAX  INTEGER (0..15)
        ACCESS  read-only
        STATUS  mandatory
        DESCRIPTION
                "The last remote signal quality value obtained from the
                 Point-to-Point diagnostic test.

                 A value of 0 is returned if the PTP Diagnostic testing is
                 not currently active."

        ::= { rabtPTPDiag 5 }

rabtPTPInterval OBJECT-TYPE
        SYNTAX  INTEGER (0..1000)
        ACCESS  read-write
        STATUS  mandatory
        DESCRIPTION
                "Writing a 1 to this variable causes a single PTP sample to
                 be performed."

        ::= { rabtPTPDiag 6 }

rabtPTPLocalSignalLevel OBJECT-TYPE
        SYNTAX  INTEGER (0..36)
        ACCESS  read-only
        STATUS  mandatory
        DESCRIPTION
                "The last LOCAL Signal Level value obtained from the 
                 Point-to-Point diagnostic test.

                 A value of 0 is returned if the last sample was not valid."

        ::= { rabtPTPDiag 7 }

rabtPTPLocalNoiseLevel OBJECT-TYPE
        SYNTAX  INTEGER (0..36)
        ACCESS  read-only
        STATUS  mandatory
        DESCRIPTION
                "The last LOCAL Noise Level value obtained from the
                 Point-to-Point diagnostic test.

                 A value of 0 is returned if the last sample was not valid."

        ::= { rabtPTPDiag 8 }

rabtPTPLocalSignalQuality OBJECT-TYPE
        SYNTAX  INTEGER (0..15)
        ACCESS  read-only
        STATUS  mandatory
        DESCRIPTION
                "The last LOCAL signal quality value obtained from the 
                 Point-to-Point diagnostic test.

                 A value of 0 is returned if the last sample was not valid."

        ::= { rabtPTPDiag 9 }


--
-- This is the new IEEE 802.11 section.  It only applies to IEEE 802.11 DS
-- cards.
--

		rabtDot11	  OBJECT IDENTIFIER ::= { roamabout 15 }

		rabtDot11Current  OBJECT IDENTIFIER ::= { rabtDot11 1 }
		rabtDot11Future   OBJECT IDENTIFIER ::= { rabtDot11 2 }
		rabtDot11General  OBJECT IDENTIFIER ::= { rabtDot11 3 }
		rabtDot11Bldg	  OBJECT IDENTIFIER ::= { rabtDot11 4 }
		rabtDot11WEP	  OBJECT IDENTIFIER ::= { rabtDot11 5 }


rabtDot11CurrentChannel OBJECT-TYPE
        SYNTAX  INTEGER (1..14)
        ACCESS  read-only
        STATUS  mandatory
        DESCRIPTION
                "The CURRENT channel."

        ::= { rabtDot11Current 1 }

rabtDot11CurrentNetworkName OBJECT-TYPE
        SYNTAX  DisplayString (SIZE (1..32))
        ACCESS  read-only
        STATUS  mandatory
        DESCRIPTION
                "The CURRENT network name."

        ::= { rabtDot11Current 2 }


rabtDot11CurrentStationName OBJECT-TYPE
        SYNTAX  DisplayString (SIZE (1..20))
        ACCESS  read-only
        STATUS  mandatory
        DESCRIPTION
                "Defines the CURRENT station name of the radio interface,
                 used by client utilities."

        ::= { rabtDot11Current 3 }

rabtDot11CurrentOperationalRate OBJECT-TYPE
		SYNTAX OCTET STRING (SIZE(1..126))
		ACCESS read-only
		STATUS mandatory
		DESCRIPTION
			"This attribute shall specify the set of data rates
			 at which the station may transmit data.  Each octet
                         contains a value representing a rate.  Each rate
			 shall be within the range from 2 to 127,
			 corresponding to data rates in increments of
			 500 kb/s from 1 Mb/s to 63.5 Mb/s, and shall be
			 supported (as indicated in the supported rates
			 table) for receiving data. This value is reported in
			 transmitted Beacon, Probe Request, Probe Response,
			 Association Request, Association Response,
			 Reassociation Request, and Reassociation Response
			 frames, and is used to determine whether a BSS
			 with which the station desires to synchronize is
			 suitable. It is also used when starting a BSS,
			 as specified in  10.3."
        ::= { rabtDot11Current 4 }

rabtDot11CurrentSystemScale OBJECT-TYPE
        SYNTAX  INTEGER  {
                        low(1),
                        medium(2),
			high(3)
                }
        ACCESS  read-only
        STATUS  mandatory
        DESCRIPTION
                "Specifies the CURRENT Access Point density in the ESS."

        ::= { rabtDot11Current 5 }

rabtDot11CurrentDTIMPeriod OBJECT-TYPE
        SYNTAX  INTEGER (1..255)
        ACCESS  read-only
        STATUS  mandatory
        DESCRIPTION
                "Defines the CURRENT number of beacon intervals between
		 successive DTIMs."

        ::= { rabtDot11Current 6 }

rabtDot11CurrentFragmentationThreshold OBJECT-TYPE
        SYNTAX INTEGER (256..2346)
        ACCESS read-only
        STATUS mandatory
        DESCRIPTION

        "This attribute shall specify the mandatory maximum size, in
         octets, of the MPDU that may be delivered to the PHY. An MSDU
         shall be broken into fragments if its size exceeds the value
	 of this attribute after adding MAC headers and trailers. An MSDU
	 or MMPDU shall be fragmented when the resulting frame has an 
	 individual address in the Address1 field, and the length of the 
	 frame is larger than this threshold. The default value for this
	 attribute shall be the lesser of 2346 or the aMPDUMaxLength of 
	 the attached PHY and shall never exceed the lesser of 2346 or 
	 the aMPDUMaxLength of the attached PHY. The value of this
	 attribute shall never be less than 256. "

        ::= { rabtDot11Current 7 }

rabtDot11CurrentRTSThreshold OBJECT-TYPE
        SYNTAX INTEGER (0..2347)
        ACCESS read-only
        STATUS mandatory
        DESCRIPTION

        "This attribute shall indicate the number of octets in an MPDU,
         below which an RTS/CTS handshake shall not be performed. An
         RTS/CTS handshake shall be performed at the beginning of any
         frame exchange sequence where the MPDU is of type Data or
         Management, the MPDU has an individual address in the Address1
         field, and the length of the MPDU is greater than
         this threshold. (For additional details, refer to Table 21 in
         9.7.) Setting this attribute to be larger than the maximum
         MSDU size shall have the effect of turning off the RTS/CTS
         handshake for frames of Data or Management type transmitted by
         this STA. Setting this attribute to zero shall have the effect
         of turning on the RTS/CTS handshake for all frames of Data or
         Management type transmitted by this STA. The default value of
         this attribute shall be 2347."

        ::= { rabtDot11Current 8 }



rabtDot11CurrentMulticastPMBuffering OBJECT-TYPE
        SYNTAX  INTEGER  {
                        enabled(1),
                        disabled(2)
                }
        ACCESS  read-only
        STATUS  mandatory
        DESCRIPTION
                "Defines if multicast MAC frames are CURRENTLY buffered for
	 	 transmission after DTIM.  If disabled, MAC frames are
                 immediately placed in the output queue for transmission."

        ::= { rabtDot11Current 9 }

rabtDot11CurrentSecureAccess OBJECT-TYPE
        SYNTAX  INTEGER  {
                        enabled(1),
                        disabled(2)
                }
        ACCESS  read-only
        STATUS  mandatory
        DESCRIPTION
                "When this mode is set to enabled, the AP will only associate
                 with stations that have the same network name as the AP.
                 When this mode is set to disabled, a station with the
                 network name of ANY is allowed to associate."

        ::= { rabtDot11Current 10 }


rabtDot11CurrentTransmitRate OBJECT-TYPE
        SYNTAX  INTEGER  {
                        fixed1Mbit(1),
                        fixed2Mbit(2),
			autoFallback(3),
			fixedMediumRate(4),
			fixedHighRate(5),
			autoFallbackStd(6),
			autoFallbackMedium(7)
                }
        ACCESS  read-only
        STATUS  mandatory
        DESCRIPTION
                "This value specifies the transmission rate of the AP. It is
                 implemented when cards that operate faster than the 2Mbit
                 802.11 standard are inserted."

        ::= { rabtDot11Current 11 }

rabtDot11CurrentPrivacyInvoked OBJECT-TYPE
        SYNTAX  INTEGER  {
                        true(1),
			false(2)
                }
        ACCESS  read-only
        STATUS  mandatory
        DESCRIPTION
                "When this attribute is true, it shall indicate that the AP
                 is currently using the 802.11 WEP mechanism for transmitting
                 frames of type Data."

        ::= { rabtDot11Current 12 }

rabtDot11CurrentExcludeUnencrypted OBJECT-TYPE
        SYNTAX  INTEGER  {
                        true(1),
			false(2)
                }
        ACCESS  read-only
        STATUS  mandatory
        DESCRIPTION
                "This value indicates the current setting of the dot11ExcludeUnencrypted
                 attribute in the AP."

        ::= { rabtDot11Current 13 }

rabtDot11FutureChannel OBJECT-TYPE
        SYNTAX  INTEGER (1..14)
        ACCESS  read-write
        STATUS  mandatory
        DESCRIPTION
                "Defines the FUTURE channel (communication frequency) to be
                 used for creating a BSS.  
				 
	         Note that different subsets of channels are valid for
                 different registration domains.  The current domain can be
                 found at dot11CurrentRegDomain.  The valid channels per
                 domain are listed in the IEEE 802.11 specification.  Setting
		 an invalid channel will result in a SNMP BAD-VALUE error.

		 The term future means that a change takes effect after the
		 next reset of the Access Point.  The current channel can be
		 obtained from dot11CurrentChannel."

        ::= { rabtDot11Future 1 }


rabtDot11FutureNetworkName OBJECT-TYPE
        SYNTAX  DisplayString (SIZE (1..32))
        ACCESS  read-write
        STATUS  mandatory
        DESCRIPTION
                "Defines the FUTURE Service Set IDentifier to be used for the
                 BSS.
				 			
		 The term future means that a change takes effect after the
		 next reset of the Access Point.  The current BSSID can be
                 obtained from dot11DesiredSSID."

        ::= { rabtDot11Future 2 }

rabtDot11FutureStationName OBJECT-TYPE
        SYNTAX  DisplayString (SIZE (1..20))
        ACCESS  read-write
        STATUS  mandatory
        DESCRIPTION
                "Defines the FUTURE station name of the radio interface,
                 used by client utilities.

		 The term future means that a change takes effect after the
		 next reset of the Access Point.  The current station name
		 can be read from rabtStationName."

        ::= { rabtDot11Future 3 }

rabtDot11FutureOperationalRate OBJECT-TYPE
		SYNTAX OCTET STRING (SIZE(1..126))
		ACCESS read-write
		STATUS mandatory
		DESCRIPTION
			"This attribute shall specify the set of data rates
			 at which the station may transmit data.  Each octet
                         contains a value representing a rate.  Each rate
			 shall be within the range from 2 to 127,
			 corresponding to data rates in increments of
			 500 kb/s from 1 Mb/s to 63.5 Mb/s, and shall be
			 supported (as indicated in the supported rates
			 table) for receiving data. This value is reported in
			 transmitted Beacon, Probe Request, Probe Response,
			 Association Request, Association Response,
			 Reassociation Request, and Reassociation Response
			 frames, and is used to determine whether a BSS
			 with which the station desires to synchronize is
			 suitable. It is also used when starting a BSS,
			 as specified in  10.3."

        ::= { rabtDot11Future 4 }

rabtDot11FutureSystemScale OBJECT-TYPE
        SYNTAX  INTEGER  {
                        low(1),
                        medium(2),
			high(3)
                }
        ACCESS  read-write
        STATUS  mandatory
        DESCRIPTION
                "Specifies the FUTURE Access Point density in the ESS.  

		 The term future means that the change takes effect after the
		 next reset of the Access Point.  The current system scale is
		 found above at rabtDot11CurrentSystemScale."

        ::= { rabtDot11Future 5 }


rabtDot11FutureDTIMPeriod OBJECT-TYPE
        SYNTAX  INTEGER (1..255)
        ACCESS  read-write
        STATUS  mandatory
        DESCRIPTION
                "Defines the FUTURE number of beacon intervals between
		 successive DTIMs. 
				
		 The term future means that a change takes effect after the
		 next reset of the Access Point.   The current DTIM period
		 is at dot11DTIMPeriod."

        ::= { rabtDot11Future 6 }

rabtDot11FutureFragmentationThreshold OBJECT-TYPE
        SYNTAX INTEGER (256..2346)
        ACCESS read-write
        STATUS mandatory
        DESCRIPTION

        "This attribute shall specify the mandatory maximum size, in
         octets, of the MPDU that may be delivered to the PHY. An MSDU
         shall be broken into fragments if its size exceeds the value
 	 of this attribute after adding MAC headers and trailers. An MSDU
	 or MMPDU shall be fragmented when the resulting frame has an 
	 individual address in the Address1 field, and the length of the 
	 frame is larger than this threshold. The default value for this
	 attribute shall be the lesser of 2346 or the aMPDUMaxLength of 
	 the attached PHY and shall never exceed the lesser of 2346 or 
	 the aMPDUMaxLength of the attached PHY. The value of this
	 attribute shall never be less than 256. "

        ::= { rabtDot11Future 7 }

rabtDot11FutureRTSThreshold OBJECT-TYPE
        SYNTAX INTEGER (0..2347)
        ACCESS read-write
        STATUS mandatory
        DESCRIPTION

        "This attribute shall indicate the number of octets in an MPDU,
         below which an RTS/CTS handshake shall not be performed. An
         RTS/CTS handshake shall be performed at the beginning of any
         frame exchange sequence where the MPDU is of type Data or
         Management, the MPDU has an individual address in the Address1
         field, and the length of the MPDU is greater than
         this threshold. (For additional details, refer to Table 21 in
         9.7.) Setting this attribute to be larger than the maximum
         MSDU size shall have the effect of turning off the RTS/CTS
         handshake for frames of Data or Management type transmitted by
         this STA. Setting this attribute to zero shall have the effect
         of turning on the RTS/CTS handshake for all frames of Data or
         Management type transmitted by this STA. The default value of
         this attribute shall be 2347."

        ::= { rabtDot11Future 8 }

rabtDot11FutureMulticastPMBuffering OBJECT-TYPE
        SYNTAX  INTEGER  {
                        enabled(1),
                        disabled(2)
                }
        ACCESS  read-write
        STATUS  mandatory
        DESCRIPTION
                "Defines if multicast MAC frames are to be buffered for
		 transmission after DTIM in the FUTURE.  If disabled, MAC
		 frames will be immediately placed in the output queue for
		 transmission.

		 The term future means that a change takes effect after the
		 next reset of the Access Point.  The current multicast PM
		 buffering state is read from
                 rabtDot11CurrentMulticastPMBuffering."

        ::= { rabtDot11Future 9 }


rabtDot11FutureSecureAccess OBJECT-TYPE
        SYNTAX  INTEGER  {
                        enabled(1),
                        disabled(2)
                }
        ACCESS  read-write
        STATUS  mandatory
        DESCRIPTION
                "When this mode is set to enabled, the AP will only associate
                 with stations that have the same network name as the AP.
                 When this mode is set to disabled, a station with the
                 network name of ANY is allowed to associate.

		 The term future means that a change takes effect after the
		 next reset of the Access Point.  The current multicast PM
		 buffering state is read from
                 rabtDot11CurrentMulticastPMBuffering."

        ::= { rabtDot11Future 10 }


rabtDot11FutureTransmitRate OBJECT-TYPE
        SYNTAX  INTEGER  {
                        fixed1Mbit(1),
                        fixed2Mbit(2),
			autoFallback(3),
			fixedMediumRate(4),
			fixedHighRate(5),
			autoFallbackStd(6),
			autoFallbackMedium(7)
                }
        ACCESS  read-write
        STATUS  mandatory
        DESCRIPTION
                "This value specifies the transmission rate of the AP. It is
                 implemented when cards that operate faster than the 2Mbit
                 802.11 standard are inserted."

        ::= { rabtDot11Future 11 }

rabtDot11FuturePrivacyInvoked OBJECT-TYPE
        SYNTAX  INTEGER  {
                        true(1),
			false(2)
                }
        ACCESS  read-write
        STATUS  mandatory
        DESCRIPTION
                "This value specifies the future setting of the
                 dot11PrivacyInvoked attribute in the AP."

        ::= { rabtDot11Future 12 }

rabtDot11FutureExcludeUnencrypted OBJECT-TYPE
        SYNTAX  INTEGER  {
                        true(1),
			false(2)
                }
        ACCESS  read-write
        STATUS  mandatory
        DESCRIPTION
                "This value specifies the future value of the
                 dot11ExcludeUnencrypted attribute in the AP."

        ::= { rabtDot11Future 13 }

--
-- 802.11 General Information
--

rabtDot11PCCardVersions OBJECT-TYPE
        SYNTAX  DisplayString (SIZE (1..80))
        ACCESS  read-only
        STATUS  mandatory
        DESCRIPTION
                "Specifies the version identifiers for the PC card."

        ::= { rabtDot11General 1 }


--
-- This is the 802.11 Building-to-Building section.
--

rabtDot11BldgRemoteMAC OBJECT-TYPE
        SYNTAX  PhysAddress
        ACCESS  read-only
        STATUS  mandatory
        DESCRIPTION
            "The CURRENT MAC address for the remote station participating
            in a 802.11 Building-to-Building link."

        ::= { rabtDot11Bldg 1 }

rabtDot11FutureBldgRemoteMAC OBJECT-TYPE
        SYNTAX  PhysAddress
        ACCESS  read-write
        STATUS  mandatory
        DESCRIPTION
            "The FUTURE MAC address for the remote station participating
             in a 802.11 Building-to-Building link.

             Setting this MAC address and then ISSUING A RESET
             places the AP in the Building-to-Building mode."

        ::= { rabtDot11Bldg 2 }


rabtFutureBridgeMode OBJECT-TYPE
        SYNTAX  INTEGER  {
                        workgroup(1),
                        lan-to-lan(2),
                        lan-to-lan-hub(3)
                }
        ACCESS  read-write
        STATUS  mandatory
        DESCRIPTION
                "FUTURE Access Point bridge mode state.  LAN-to-LAN mode is
                 the improved name for 802.11.  LAN-to-LAN used to be called
                 full-bridge pre-802.11.  pre-802.11 was dynamic.  It now
                 requires a reset to implement."

        ::= { rabtDot11Bldg 3 }


-- **********************************************************************
-- *    rabtDot11BldgExt Extensions
-- **********************************************************************
rabtDot11BldgExt	OBJECT IDENTIFIER ::= { rabtDot11Bldg 4 }
rabtDot11BldgExtCurrent	OBJECT IDENTIFIER ::= { rabtDot11BldgExt 1 }
rabtDot11BldgExtFuture	OBJECT IDENTIFIER ::= { rabtDot11BldgExt 2 }

rabtDot11BldgRelayMode OBJECT-TYPE
        SYNTAX  INTEGER  {
                        enabled(1),
                        disabled(2)
                }
        ACCESS  read-write
        STATUS  mandatory
        DESCRIPTION
                "Enabling relay mode allows the Access Point in a point to
                 multi-point configuration to relay broadcast messages to
                 other wireless AP's."

        ::= { rabtDot11BldgExtCurrent 1 }

rabtDot11BldgRemoteMAC2 OBJECT-TYPE
        SYNTAX  PhysAddress
        ACCESS  read-only
        STATUS  mandatory
        DESCRIPTION
            "The CURRENT MAC address for the remote station participating
            in a 802.11 Building-to-Building link."

        ::= { rabtDot11BldgExtCurrent 2 }

rabtDot11BldgRemoteMAC3 OBJECT-TYPE
        SYNTAX  PhysAddress
        ACCESS  read-only
        STATUS  mandatory
        DESCRIPTION
            "The CURRENT MAC address for the remote station participating
            in a 802.11 Building-to-Building link."

        ::= { rabtDot11BldgExtCurrent 3 }

rabtDot11BldgRemoteMAC4 OBJECT-TYPE
        SYNTAX  PhysAddress
        ACCESS  read-only
        STATUS  mandatory
        DESCRIPTION
            "The CURRENT MAC address for the remote station participating
            in a 802.11 Building-to-Building link."

        ::= { rabtDot11BldgExtCurrent 4 }

rabtDot11BldgRemoteMAC5 OBJECT-TYPE
        SYNTAX  PhysAddress
        ACCESS  read-only
        STATUS  mandatory
        DESCRIPTION
            "The CURRENT MAC address for the remote station participating
            in a 802.11 Building-to-Building link."

        ::= { rabtDot11BldgExtCurrent 5 }

rabtDot11BldgRemoteMAC6 OBJECT-TYPE
        SYNTAX  PhysAddress
        ACCESS  read-only
        STATUS  mandatory
        DESCRIPTION
            "The CURRENT MAC address for the remote station participating
            in a 802.11 Building-to-Building link."

        ::= { rabtDot11BldgExtCurrent 6 }

rabtDot11BldgFutureRelayMode OBJECT-TYPE
        SYNTAX  INTEGER  {
                        enabled(1),
                        disabled(2)
                }
        ACCESS  read-write
        STATUS  mandatory
        DESCRIPTION
                "Enabling relay mode allows the Access Point in a point to
                 multi-point configuration to relay broadcast messages to
                 other wireless AP's."

        ::= { rabtDot11BldgExtFuture 1 }

rabtDot11BldgFutureRemoteMAC2 OBJECT-TYPE
        SYNTAX  PhysAddress
        ACCESS  read-write
        STATUS  mandatory
        DESCRIPTION
            "The FUTURE MAC address for the remote station participating
            in a 802.11 Building-to-Building link."

        ::= { rabtDot11BldgExtFuture 2 }

rabtDot11BldgFutureRemoteMAC3 OBJECT-TYPE
        SYNTAX  PhysAddress
        ACCESS  read-write
        STATUS  mandatory
        DESCRIPTION
            "The FUTURE MAC address for the remote station participating
            in a 802.11 Building-to-Building link."

        ::= { rabtDot11BldgExtFuture 3 }

rabtDot11BldgFutureRemoteMAC4 OBJECT-TYPE
        SYNTAX  PhysAddress
        ACCESS  read-write
        STATUS  mandatory
        DESCRIPTION
            "The FUTURE MAC address for the remote station participating
            in a 802.11 Building-to-Building link."

        ::= { rabtDot11BldgExtFuture 4 }

rabtDot11BldgFutureRemoteMAC5 OBJECT-TYPE
        SYNTAX  PhysAddress
        ACCESS  read-write
        STATUS  mandatory
        DESCRIPTION
            "The FUTURE MAC address for the remote station participating
            in a 802.11 Building-to-Building link."

        ::= { rabtDot11BldgExtFuture 5 }

rabtDot11BldgFutureRemoteMAC6 OBJECT-TYPE
        SYNTAX  PhysAddress
        ACCESS  read-write
        STATUS  mandatory
        DESCRIPTION
            "The FUTURE MAC address for the remote station participating
            in a 802.11 Building-to-Building link."

        ::= { rabtDot11BldgExtFuture 6 }


-- **********************************************************************
-- *    End rabtDot11BldgExt Extensions
-- **********************************************************************


rabtDot11WEPEnhancedImplemented OBJECT-TYPE
        SYNTAX  INTEGER  {
                        true(1),
                        false(2)
                }
        ACCESS  read-only
        STATUS  mandatory
        DESCRIPTION
                "This value indicates whether the AP is capable of Enhanced
                 Wireless Equivalent Privacy (WEP), using 128-bit keys."

        ::= { rabtDot11WEP 1 }

rabtDot11WEPExcludeSNMP OBJECT-TYPE
        SYNTAX  INTEGER  {
                        true(1),
                        false(2)
                }
        ACCESS  read-only
        STATUS  mandatory
        DESCRIPTION
                "This value indicates that SNMP management of WEP attributes
                 is disabled in the AP."

        ::= { rabtDot11WEP 2 }

-- **********************************************************************
-- *    Key State  TABLE
-- **********************************************************************

rabtdot11KeyStateTable OBJECT-TYPE
        SYNTAX SEQUENCE OF RabtDot11KeyStateEntry
        ACCESS not-accessible
        STATUS mandatory
        DESCRIPTION
            "A conceptual table containing a set of booleans
            identifying if an encryption key has been set or not."

    ::= {  rabtDot11WEP 3 }

rabtdot11KeyStateEntry OBJECT-TYPE
        SYNTAX RabtDot11KeyStateEntry
        ACCESS not-accessible
        STATUS mandatory
        DESCRIPTION
            "An Entry (conceptual row) in the Key State Table.

            ifIndex - Each 802.11 interface is represented by an
            ifEntry.  Interface tables in this MIB module are indexed
            by ifIndex."
        INDEX {ifIndex, rabtdot11KeyStateIndex}

    ::= {  rabtdot11KeyStateTable  1 }

RabtDot11KeyStateEntry ::= SEQUENCE {
            rabtdot11KeyStateIndex    INTEGER,
            rabtDot11KeyState         INTEGER
}

rabtdot11KeyStateIndex OBJECT-TYPE
        SYNTAX INTEGER
        ACCESS not-accessible
        STATUS mandatory
        DESCRIPTION
            "The auxiliary variable used to identify instances
             of the columnar objects in the Key State Table."
    ::= { rabtdot11KeyStateEntry 1 }

rabtDot11KeyState OBJECT-TYPE
		SYNTAX INTEGER { set(1), notset(2) }
        ACCESS read-only
        STATUS mandatory
        DESCRIPTION

            "The state column used for determining if an
             encryption key is set or not."

        DEFVAL {notset}
    ::= {  rabtdot11KeyStateEntry 2 }

-- **********************************************************************
-- *    End Of Key State  TABLE
-- **********************************************************************


-- ***********************************************************************
-- *    Objects to support manual configuration of the primitive loader.
-- *
-- *    These objects make it possible to do firmware upgrades and crash
-- *    dump uploads even if there is no BootP server on the same subnet
-- *    as the AccessPoint.
-- *
-- *    Note that you MUST configure the AccessPoint's IP address if you
-- *    want a manually-configured TFTP transfer to work.  (You may also
-- *    need to specify a subnet mask and default gateway IP address.)
-- ***********************************************************************

roamaboutLoader OBJECT IDENTIFIER ::= { roamabout 16 }

rabtFirmwareUseBootp OBJECT-TYPE
        SYNTAX  INTEGER { true(1), false(2) }
        ACCESS  read-write
        STATUS  mandatory
        DESCRIPTION
                "Controls where the AccessPoint gets the information that
                 it needs to download new firmware.

                 When true(1), indicates that the AP should use the BootP
                 protocol to auto-configure parameters such as its own IP
                 address, gateway IP, subnet, TFTP server IP address, and
                 file name.

                 When false(2), indicates that the AccessPoint should use
                 locally-configured parameters stored in NVRAM."
        ::= { roamaboutLoader 1 }

rabtFirmwareServerIP OBJECT-TYPE
        SYNTAX  IpAddress
        ACCESS  read-write
        STATUS  mandatory
        DESCRIPTION
                "The IP address of the TFTP server that should be used for
                 firmware downloads.

                 This value will be ignored when 'rabtFirmwareUseBootp' is
                 'false(2)'."
        ::= { roamaboutLoader 2 }

rabtFirmwareFilename OBJECT-TYPE
        SYNTAX  OCTET STRING( 0..128 )
        ACCESS  read-write
        STATUS  mandatory
        DESCRIPTION
                "The name of the remote file that contains the firmware to
                 be downloaded.

                 This value will be ignored when 'rabtFirmwareUseBootp' is
                 'false(2)'."
        ::= { roamaboutLoader 3 }

rabtFirmwareStatus OBJECT-TYPE
        SYNTAX  INTEGER {
                --
                -- Generic status codes
                --
                         none(1),
                             -- The AccessPoint hasn't tried to load firmware
                             -- since the last time parameters were cleared.

                         success(2),
                             -- The last firmware load attempt succeeded.

                         flashStatusUnknown(3),
                             -- Indicates that the TFTP file transfer appears
                             -- to have succeeded, but that the Flash Blaster
                             -- status is unknown.
                             --
                             -- This can happen if the Flash Blaster computes
                             -- that the action of programming the flash will
                             -- overwrite the routines that called it.  Flash
                             -- Blaster may choose to reset the AP itself, in
                             -- a "controlled" fashion, in such circumstances.

                         unspecifiedFailure(4),
                             -- The last firmware load attempt failed for some
                             -- reason other than those called out below.


                --
                -- Flash Blaster codes.
                --
                         flashInvalidSize(51),
                             -- Flash Blaster was asked to write an image that
                             -- was too large - or to write an image partially
                             -- or completely outside the supposed destination
                             -- area of flash.

                         flashByteCopyFailure(52),
                             -- A flash write failed.  (Currently returned for
                             -- the case where writing the CRC failed.)

                         flashUnknownFlashType(53),
                             -- Flash Blaster couldn't identify the flash chip
                             -- (i.e., the firmware you tried to load probably
                             -- is not the right firmware for your equipment).

                         flashFatalError(54),
                             -- Generally signals a programming error.

			 flashEraseFailure(55),
			 flashWriteFailure(56),
			 flashVppFailure(57),
			 flashCmdSequenceError(58),

			 flashOperationTimeout(59),
                             -- The flash chip did not respond in a timely way
                             -- to an operation (e.g., programming or erasing)

			 flashCrcFailure(60),
                             -- The CRC of freshly-written flash doesn't match
                             -- the expected value, indicating data corruption

                --
                -- Primitive Loader codes
                --
                         modeError(101),
                             -- Generally signals a programming error.  The
                             -- program was asked to do an undefined task.

                         headerOffsetError(102),
                             -- The downloaded firmware image isn't aligned
                             -- properly.

                         headerSizeError(103),
                             -- The primitive loader thinks the firmware is
                             -- too big to fit in the target area of flash.

                         imageSizeError(104),
                             -- The new firmware image was too large to fit
                             -- into the "landing pad" area.

                         imageCrcError(105),
                             -- According to CRC tests, the just-downloaded
                             -- firmware is corrupt.  (Generally the loader
                             -- will retry the TFTP transfer a few times if
                             -- it runs into this sort of trouble; when you
                             -- get this error, it probably means that your
                             -- network is really messed up or that there's
                             -- corrupt firmware on your TFTP server.)

                         wrongImage(106),
                             -- The downloaded file does not hold firmware,
                             -- or at least not firmware that's appropriate
                             -- for this AccessPoint unit.

                         retriesExceeded(107),
                             -- The AccessPoint got tired of failed upload/
                             -- download attempts, and gave up.

                         tftpTimeout(108),
                         unknownXferId(109),
                         portUnreachable(110),

                         loadStateError(111),
                             -- The primitive loader's state machine got out
                             -- of sync.  Probably indicates a bug.

                         filterError(112),
                         wrongTidReceived(113),
                         wrongBlockNumber(114),

                         landingPadError(116),
                              -- Indicates that, due to a bug (or some other
                              -- unexpected condition), the "landing pad" is
                              -- outside of DRAM.

                         noIpAddress(117),
                               -- No IP address was set for the AccessPoint.

                         tftpErrFileNotFound(201),
                         tftpErrAccessViolation(202),
                         tftpErrDiskFull(203),
                         tftpErrIllegalOperation(204),
                         tftpErrUnknownXferId(205),
                         tftpErrFileAlreadyExists(206),
                         tftpErrNoSuchUser(207)
                             -- These seven error codes indicate that the
                             -- AccessPoint received various kinds of TFTP
                             -- errors from the server.
                        }
        ACCESS  read-only
        STATUS  mandatory
        DESCRIPTION
                "Indicates the success or failure of the AccessPoint's most
                 recent attempt to download new firmware.  In the case of a
                 failure, the value of this object may provide some clue as
                 to what caused the failure.

                 This MIB object does not distinguish 'managment-initiated'
                 reloads from reloads that the AccessPoint initiates."
        ::= { roamaboutLoader 4 }

rabtCrashUploadUseBootp OBJECT-TYPE
        SYNTAX  INTEGER { true(1), false(2) }
        ACCESS  read-write
        STATUS  mandatory
        DESCRIPTION
                "Controls where the AccessPoint gets the information that
                 it needs to upload crash dumps.

                 When true(1), indicates that the AP should use the BootP
                 protocol to auto-configure parameters such as its own IP
                 address, gateway IP, subnet, TFTP server IP address, and
                 directory name.

                 When false(2), indicates that the AccessPoint should use
                 locally-configured parameters stored in NVRAM."
        ::= { roamaboutLoader 5 }

rabtCrashUploadServerIP OBJECT-TYPE
        SYNTAX  IpAddress
        ACCESS  read-write
        STATUS  mandatory
        DESCRIPTION
                "The IP address of the TFTP server that should be used for
                 crash dump uploads.

                 This value will be ignored when 'rabtCrashUploadUseBootp'
                 is 'false(2)'."
        ::= { roamaboutLoader 6 }

rabtCrashUploadDirectory OBJECT-TYPE
        SYNTAX  OCTET STRING( 0..128 )
        ACCESS  read-write
        STATUS  mandatory
        DESCRIPTION
                "The name of the remote directory to which all crash dumps
                 should be uploaded.

                 This value will be ignored when 'rabtCrashUploadUseBootp'
                 is 'false(2)'."
        ::= { roamaboutLoader 7 }

-- ***********************************************************************
-- *    End of primitive loader objects
-- ***********************************************************************


-- ***********************************************************************
-- *    Miscellaneous console objects
-- ***********************************************************************

roamaboutConsole OBJECT IDENTIFIER ::= { roamabout 17 }

rabtUseConsolePassword OBJECT-TYPE
        SYNTAX  INTEGER { true(1), false(2) }
        ACCESS  read-write
        STATUS  mandatory
        DESCRIPTION
                "Indicates whether the AccessPoint console (command line
                 interface) should be password-protected.

                 ------------------------ NOTE -------------------------

                 Currently, password protection won't take effect unless
                 the read-write community string is something OTHER than
                 'public'.  This could change, though it's unlikely.

                 -------------------------------------------------------"
        ::= { roamaboutConsole 1 }


END
