-- This file is the MIB file for a DSUCSU.
-- This file, and the associated dsucsu.cdl file, 
-- were created to manage the internal DSUCSU for NEPTUNE.
-- Last Modified 12/19/96 PCK
Wellfleet-DSUCSU-MIB DEFINITIONS ::= BEGIN

   IMPORTS

      Counter
        FROM RFC1155-SMI
      OBJECT-TYPE
        FROM RFC-1212
      DisplayString
        FROM RFC1213-MIB
      TRAP-TYPE
        FROM RFC-1215
      wfDsuCsuGroup
        FROM Wellfleet-COMMON-MIB;

      
      wfDsuCsuIfTable OBJECT-TYPE
          SYNTAX      SEQUENCE OF WfDsuCsuIfEntry
          ACCESS      not-accessible
          STATUS      mandatory
          DESCRIPTION
             "DSU CSU line record."
          ::= { wfDsuCsuGroup 1 }

      wfDsuCsuIfEntry OBJECT-TYPE
          SYNTAX      WfDsuCsuIfEntry
          ACCESS      not-accessible
          STATUS      mandatory
          DESCRIPTION
             "An entry in the DSU CSU IF table"
          INDEX       { wfDsuCsuIfSlot,
                        wfDsuCsuIfConnector }
          ::= { wfDsuCsuIfTable 1 }

      WfDsuCsuIfEntry ::= SEQUENCE {
    	  wfDsuCsuIfDelete
              INTEGER,
          wfDsuCsuIfSlot
              INTEGER,
          wfDsuCsuIfConnector
              INTEGER,
          wfDsuCsuSoftRev
              DisplayString,
          wfDsuCsuHardRev
              DisplayString,
          wfDsuCsuOpMode
              INTEGER,
          wfDsuCsuTxClkSelect
              INTEGER,
          wfDsuCsuUnitReset
              INTEGER,
          wfDsuCsu64KTxMonitor
              INTEGER,
          wfDsuCsuOpState
              INTEGER,
          wfDsuCsuServiceStatus
              INTEGER,
          wfDsuCsuV54Lpbk
              INTEGER,
          wfDsuCsuV54Timer
              INTEGER,
          wfDsuCsuV54Errors
              Counter,
          wfDsuCsuCqmsLaWindow
              INTEGER,
          wfDsuCsuCqmsLaErrors
              Counter,
          wfDsuCsuCqmsLaPollRate
              INTEGER,
          wfDsuCsuCqmsReset
              INTEGER,
          wfDsuCsuOOSErrors
              Counter,
          wfDsuCsuFrameErrors
              Counter,
          wfDsuCsuLOLErrors
              Counter,
          wfDsuCsuInitState
              INTEGER
      }
      wfDsuCsuIfDelete OBJECT-TYPE
        SYNTAX	INTEGER {
    		    created(1),
    		    deleted(2)
    		}
        ACCESS	read-write
        STATUS	mandatory
        DESCRIPTION
                "Create/Delete parameter"
        DEFVAL	{ created }
        ::= { wfDsuCsuIfEntry 1 }

      wfDsuCsuIfSlot OBJECT-TYPE
          SYNTAX  INTEGER
          ACCESS  read-only
          STATUS  mandatory
          DESCRIPTION
             "Instance ID Slot, filled in by driver"
          ::= { wfDsuCsuIfEntry 2}

      wfDsuCsuIfConnector OBJECT-TYPE
          SYNTAX  INTEGER
          ACCESS  read-only
          STATUS  mandatory
          DESCRIPTION
             "Instance ID Connector, filled in by the driver."
          ::= { wfDsuCsuIfEntry 3 }

      wfDsuCsuSoftRev OBJECT-TYPE
          SYNTAX  DisplayString (SIZE (0..10))
          ACCESS  read-only
          STATUS  mandatory
          DESCRIPTION
             "Displays the Software Revision of the DSU CSU card."
          ::= {  wfDsuCsuIfEntry 4 }

      wfDsuCsuHardRev    OBJECT-TYPE
          SYNTAX  DisplayString (SIZE (0..10))
          ACCESS  read-only
          STATUS  mandatory
          DESCRIPTION
             "Displays the Hardware Revision of the DSU CSU card."
          ::= { wfDsuCsuIfEntry 5 } 

      wfDsuCsuOpMode     OBJECT-TYPE
          SYNTAX  INTEGER {
                      dds156kbps(1),
                      cc64kbps(2)
                  }
          ACCESS  read-write
          STATUS  mandatory
          DESCRIPTION
             "Identifies the type of telco service that the
              DSU CSU is connected to. Opmode should be set
              to dds1-56kbps (1) when connected to a DDS1 56 Kbps
              line. Opmode should be set to cc-64kbps (2) when
              connected to a Clear Channel 64Kbps line."
          DEFVAL { dds156kbps }
          ::= { wfDsuCsuIfEntry 6 }          

      wfDsuCsuTxClkSelect OBJECT-TYPE
          SYNTAX  INTEGER {
                      slave(1),
                      master(2)
                  }
          ACCESS  read-write
          STATUS  mandatory
          DESCRIPTION
             "Default timing, or clock, source for transmiting data to the
              network.  There must be only one source on a DDS line.  
              Timing should always be slave (1) when connected to a
              network. Timing should be set to master (2) on either
              end of a private-wire configuration, with the other end
              being set to slave (1)."
          DEFVAL { slave }
          ::= { wfDsuCsuIfEntry 7 }

      wfDsuCsuUnitReset OBJECT-TYPE
          SYNTAX  INTEGER {
                      resetUnit(1)
                  }
          ACCESS  read-write
          STATUS  mandatory
          DESCRIPTION
             "Enables the operator to remotely reset the unit.
              Using this command will cause the unit to terminate
              all its connections and drop data."
          ::= { wfDsuCsuIfEntry 8 }

      wfDsuCsu64KTxMonitor OBJECT-TYPE
          SYNTAX  INTEGER {
                      enabled(1),
                      disabled(2)
                  }
          ACCESS  read-write
          STATUS  mandatory
          DESCRIPTION
             "This signal is used in 64K Clear Channel mode to suppress 
              customer data in the event that the data duplicates a 
              network control code. A setting of enabled(1) suppresses 
              customer data. A setting of disabled(2) allows all customer
              data through, which could
              potentially put the other end into a loop if the data
              duplicates a network control code."
          DEFVAL { disabled }
          ::= { wfDsuCsuIfEntry 9 }

      wfDsuCsuOpState OBJECT-TYPE
          SYNTAX  INTEGER
          {
               normal(1),
               localLpbk(2),
               digitalLpbk(3),
               remDigitalLpbk(4),
               telcoLpbk(5),
               remDigLpbkWPattern(6),
               localAnlgLpbkWPattern(7),
               pattern2047Gen(8)
          }
          ACCESS  read-only
          STATUS  mandatory
          DESCRIPTION
             "Indicates the current operating state of the DSU CSU card."
          DEFVAL { normal }
          ::= { wfDsuCsuIfEntry 10 }

      wfDsuCsuServiceStatus   OBJECT-TYPE
          SYNTAX  INTEGER 
          {
               inService(1),
               outOfService(2),
               frameError(3),
               lossOfLine(5),
               telcoLpbk(6)
          }
          ACCESS  read-only
          STATUS  mandatory
          DESCRIPTION
             "The Current status of the physical interface.
              Your network carrier can send Out-of-Service 
              or Maintenance Mode codes."
          DEFVAL { inService }
          ::= { wfDsuCsuIfEntry 11 }

      wfDsuCsuV54Lpbk OBJECT-TYPE
          SYNTAX  INTEGER 
          {
               noLoop(1),
               localAnlgLpbk(2),
               localDigLpbk(3),
               remDigLpbk(4),
               remDigLpbkWPattern(5),
               localAnlgLpbkWPattern(6),
               pattern2047Gen(7)
          }
          ACCESS  read-write
          STATUS  mandatory
          DESCRIPTION
             "Enables the operator to control, and examine the 
             state of, V.54 loopbacks within the DSU CSU."
          DEFVAL { noLoop }
          ::= { wfDsuCsuIfEntry 12 }

      wfDsuCsuV54Timer OBJECT-TYPE
          SYNTAX  INTEGER (0..255)
          ACCESS  read-write
          STATUS  mandatory
          DESCRIPTION
             "Duration in seconds that a test specified in wfDsuCsuTestLpbk
              is to execute."
          DEFVAL { 0 }
          ::= { wfDsuCsuIfEntry 13 }

      wfDsuCsuV54Errors OBJECT-TYPE
          SYNTAX  Counter
          ACCESS  read-only
          STATUS  mandatory
          DESCRIPTION
             "Indicates the number of errors reported during the last
              loopback test. This count will only be updated for 
              loopbacks with test pattern."
          ::= { wfDsuCsuIfEntry 14 }

      wfDsuCsuCqmsLaWindow OBJECT-TYPE
          SYNTAX  INTEGER (1..15)
          ACCESS  read-write
          STATUS  mandatory
          DESCRIPTION
             "Indicates the number of minutes within the window in which
              the availability of the line (network) is to be calculated. The 
              availability of the line is an indication of the percentage
              of time the line has been in service.
              It is calculated as follows:
              (((wfDsuCsuCqmsLaWindow*60) - (wfDsuCsuCqmsLaErrCnt*wfDsuCsuCqmsLaPollRate))/
                            wfDsuCsuCqmsLaWindow*60)"
          DEFVAL { 15 }
          ::= { wfDsuCsuIfEntry 15 }

      wfDsuCsuCqmsLaErrors OBJECT-TYPE
          SYNTAX  Counter
          ACCESS  read-only
          STATUS  mandatory
          DESCRIPTION
             "Indicates the total number of seconds that the line was not
              in service in the last window of size wfDsuCsuCqmsLaWindow."
          ::= { wfDsuCsuIfEntry 16 }

      wfDsuCsuCqmsLaPollRate OBJECT-TYPE
          SYNTAX  INTEGER (1..60)
          ACCESS  read-write
          STATUS  mandatory
          DESCRIPTION
             "Indicates the number of seconds between polls for line status
              from the DsuCsu. A value of 1 forces polling every second. 
              A value of 60 forces polling every minute."
          DEFVAL { 1 }
          ::= { wfDsuCsuIfEntry 17 }

      wfDsuCsuCqmsReset OBJECT-TYPE
          SYNTAX  INTEGER {
                      resetCqms(1)
                  }
          ACCESS  read-write
          STATUS  mandatory
          DESCRIPTION
             "Resets the CQMS counters to their default values. For
              Line Availability, wfDsuCsuCqmsLaErrCnt is reset."
          ::= { wfDsuCsuIfEntry 18 }

       wfDsuCsuOOSErrors OBJECT-TYPE
          SYNTAX  Counter
          ACCESS  read-only
          STATUS  mandatory
          DESCRIPTION
             "The number of seconds in which Out of Service control codes
              were received from the Telco. The counter is incremented 
              whenever a sample within a second indicated the unit received 
              an out of service control code."
          ::= { wfDsuCsuIfEntry 19 }

       wfDsuCsuFrameErrors OBJECT-TYPE
          SYNTAX  Counter
          ACCESS  read-only
          STATUS  mandatory
          DESCRIPTION
             "The number of seconds in which the unit was out of frame
              with the Telco. This is only applicable in 64K mode. The
              counter is incremented whenever a sample within a second
              indicated the unit was out of frame."
          ::= { wfDsuCsuIfEntry 20 }

       wfDsuCsuLOLErrors OBJECT-TYPE
          SYNTAX  Counter
          ACCESS  read-only
          STATUS  mandatory
          DESCRIPTION
             "The number of seconds in which the unit has detected that no
              signal is present on the line, and/or no line is present."
          ::= { wfDsuCsuIfEntry 21 }

        wfDsuCsuInitState OBJECT-TYPE
          SYNTAX       INTEGER {
                            startup(1),
                            init(2),
                            monitor(3),
                            loopback(4)
                       }
          ACCESS       read-only
          STATUS       mandatory
          DESCRIPTION
             "Indictes the state of the DSU/CSU initialization sequence. The state will
              indicate if the DSU/CSU has been initialized and is in the *monitor*
              state polling the card for line condition, or in the *loopback state
              running a user-initiated loopback"
          ::= {wfDsuCsuIfEntry 22 }

      wfDsuCsuIfTrap TRAP-TYPE
          ENTERPRISE wfDsuCsuGroup
          VARIABLES {
              wfDsuCsuServiceStatus
          }
          DESCRIPTION
             "Indicates a change in the status of the line. The
              value returned in  the trap will indicate the current
              state as defined in wfDsuCsuServiceStatus."
          ::= 1

    END -- Wellfleet-DSUCSU-MIB
