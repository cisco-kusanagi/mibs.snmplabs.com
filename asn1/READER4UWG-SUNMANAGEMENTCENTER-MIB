-- This MIB was created by extracting information from 
-- Sun Mangement Center 3.5 for use in other applications
-- to help determine what is actually listed in the SMC snmp 
-- agent. Sun has/will not release their MIBS for this 
-- information, so I created them from all information that
-- they have released.
--
-- Most all the information should be correct, but
-- if you find a discrepency please let me know. I do not
-- have all available Sun hardware to test with, so not 
-- not all types of support hardware has been tested.
-- These MIBs have only been tested using the utilities
-- from net-snmp. They may or may not work with other
-- applications.
-- 
-- The MIBs are not detailed, they only are useful in 
-- mapping OIDs to names. At some point in time 
-- descriptions may be given.
--
-- Author: Brian T. O'Neill (btoneill@misplaced.net)
-- Date: 7-30-2003 
-- Version: 0.9
--
-- No guarantees are given regarding the accuracy of this
-- data.
--
-- Note: The naming was done in line with the published
-- MIBS from Sun Microsystems.
--
--
READER4UWG-SUNMANAGEMENTCENTER-MIB DEFINITIONS ::= BEGIN

  IMPORTS
        enterprises, NOTIFICATION-TYPE, OBJECT-TYPE, MODULE-IDENTITY
                FROM SNMPv2-SMI;

sun             OBJECT IDENTIFIER ::= { enterprises 42 }
prod            OBJECT IDENTIFIER ::= { sun 2 }
sunsymon        OBJECT IDENTIFIER ::= { prod 12 }
agent           OBJECT IDENTIFIER ::= { sunsymon 2 }
base            OBJECT IDENTIFIER ::= { agent 1 }
modules         OBJECT IDENTIFIER ::= { agent 2 }
hardware        OBJECT IDENTIFIER ::= { modules 1 }
--
--
config          OBJECT IDENTIFIER ::= { hardware 1 }
reader4u        OBJECT IDENTIFIER ::= { config 1 }
reader4udt      OBJECT IDENTIFIER ::= { config 2 }
reader4uwg      OBJECT IDENTIFIER ::= { config 3 }
reader4u1P      OBJECT IDENTIFIER ::= { config 4 }
reader4u1D      OBJECT IDENTIFIER ::= { config 5 }
reader4unt      OBJECT IDENTIFIER ::= { config 6 }
readerSerengeti OBJECT IDENTIFIER ::= { config 7 }
reader4uvh      OBJECT IDENTIFIER ::= { config 8 }
readerECP       OBJECT IDENTIFIER ::= { config 9 }
readerELP       OBJECT IDENTIFIER ::= { config 10 }

system  OBJECT IDENTIFIER ::= { reader4uwg 2 }
system-board    OBJECT IDENTIFIER ::= { reader4uwg 3 }
sunwUltra-1     OBJECT IDENTIFIER ::= { reader4uwg 4 }
sunwUltra-2     OBJECT IDENTIFIER ::= { reader4uwg 5 }
sunwUltra-250   OBJECT IDENTIFIER ::= { reader4uwg 6 }
sunwUltra-5     OBJECT IDENTIFIER ::= { reader4uwg 7 }
sunwUltra-10    OBJECT IDENTIFIER ::= { reader4uwg 8 }
sunwUltra-5-10  OBJECT IDENTIFIER ::= { reader4uwg 9 }
sunwUltra-60    OBJECT IDENTIFIER ::= { reader4uwg 10 }
sunwUltra-80    OBJECT IDENTIFIER ::= { reader4uwg 11 }
sunwUltra-4	OBJECT IDENTIFIER ::= { reader4uwg 12 }
slot		OBJECT IDENTIFIER ::= { reader4uwg 14 }
cpu-unit	OBJECT IDENTIFIER ::= { reader4uwg 15 }
mc		OBJECT IDENTIFIER ::= { reader4uwg 16 }
bank		OBJECT IDENTIFIER ::= { reader4uwg 17 }
memory		OBJECT IDENTIFIER ::= { reader4uwg 20 }
simm		OBJECT IDENTIFIER ::= { reader4uwg 21 }
dimm		OBJECT IDENTIFIER ::= { reader4uwg 22 }
fru-device	OBJECT IDENTIFIER ::= { reader4uwg 23 } 
cpu-fans	OBJECT IDENTIFIER ::= { reader4uwg 24 }
power-supply-fans	OBJECT IDENTIFIER ::= { reader4uwg 25 }
fan		OBJECT IDENTIFIER ::= { reader4uwg 26 }
ffb		OBJECT IDENTIFIER ::= { reader4uwg 27 }
afb		OBJECT IDENTIFIER ::= { reader4uwg 28 }
sunwffb		OBJECT IDENTIFIER ::= { reader4uwg 29 }
keyswitch	OBJECT IDENTIFIER ::= { reader4uwg 30 }
active-led	OBJECT IDENTIFIER ::= { reader4uwg 31 }
disk-error-led	OBJECT IDENTIFIER ::= { reader4uwg 32 }
gen-error-led	OBJECT IDENTIFIER ::= { reader4uwg 33 }
power-led	OBJECT IDENTIFIER ::= { reader4uwg 34 }
ps-error-led	OBJECT IDENTIFIER ::= { reader4uwg 35 }
temp-error-led	OBJECT IDENTIFIER ::= { reader4uwg 36 }	
power-supply	OBJECT IDENTIFIER ::= { reader4uwg 37 }
-- no clue on these two, they might go here....
system-status-panel	OBJECT IDENTIFIER ::= { reader4uwg 38 }
disk-status-leds	OBJECT IDENTIFIER ::= { reader4uwg 39 }
--
rsc		OBJECT IDENTIFIER ::= { reader4uwg 46 }
hardware-rules	OBJECT IDENTIFIER ::= { reader4uwg 47 }
io-controller	OBJECT IDENTIFIER ::= { reader4uwg 49 }
io-device	OBJECT IDENTIFIER ::= { reader4uwg 50 }
disk		OBJECT IDENTIFIER ::= { reader4uwg 51 }
tape		OBJECT IDENTIFIER ::= { reader4uwg 52 }
network		OBJECT IDENTIFIER ::= { reader4uwg 53 }
io-unit		OBJECT IDENTIFIER ::= { reader4uwg 54 }
generic-device	OBJECT IDENTIFIER ::= { reader4uwg 55 }





sunSmTreeProp	OBJECT IDENTIFIER ::= { networkEntry 1 }
sunSmNodeName	OBJECT IDENTIFIER ::= { networkEntry 2 }
entry-no	OBJECT IDENTIFIER ::= { networkEntry 3 }
device-type	OBJECT IDENTIFIER ::= { networkEntry 4 }
fru	OBJECT IDENTIFIER ::= { networkEntry 5 }
ether	OBJECT IDENTIFIER ::= { networkEntry 6 }
inet	OBJECT IDENTIFIER ::= { networkEntry 7 }
interface-name	OBJECT IDENTIFIER ::= { networkEntry 8 }
node-hierarchy	OBJECT IDENTIFIER ::= { networkEntry 9 }
symbolic-name	OBJECT IDENTIFIER ::= { networkEntry 10 }
reg	OBJECT IDENTIFIER ::= { networkEntry 11 }
input-errors	OBJECT IDENTIFIER ::= { networkEntry 12 }
output-errors	OBJECT IDENTIFIER ::= { networkEntry 13 }
cpu-unitTbl	OBJECT IDENTIFIER ::= { cpu-unit 1 }
power-supplyTbl	OBJECT IDENTIFIER ::= { power-supply 1 }
sunSmTreeProp	OBJECT IDENTIFIER ::= { power-supply-entry 1 }
sunSmNodeName	OBJECT IDENTIFIER ::= { power-supply-entry 2 }
entry-no	OBJECT IDENTIFIER ::= { power-supply-entry 3 }
fru	OBJECT IDENTIFIER ::= { power-supply-entry 4 }
state	OBJECT IDENTIFIER ::= { power-supply-entry 5 }
sunSmTreeProp	OBJECT IDENTIFIER ::= { simm-entry 1 }
sunSmNodeName	OBJECT IDENTIFIER ::= { simm-entry 2 }
entry-no	OBJECT IDENTIFIER ::= { simm-entry 3 }
board-reference-number	OBJECT IDENTIFIER ::= { simm-entry 4 }
fru	OBJECT IDENTIFIER ::= { simm-entry 5 }
size	OBJECT IDENTIFIER ::= { simm-entry 6 }
slot	OBJECT IDENTIFIER ::= { simm-entry 7 }
type	OBJECT IDENTIFIER ::= { simm-entry 8 }
ps-fan-entry	OBJECT IDENTIFIER ::= { power-supply-fansTbl 1 }
disk-status-leds-entry	OBJECT IDENTIFIER ::= { disk-status-leds 1 }
sunSmTreeProp	OBJECT IDENTIFIER ::= { ps-fan-entry 1 }
sunSmNodeName	OBJECT IDENTIFIER ::= { ps-fan-entry 2 }
entry-no	OBJECT IDENTIFIER ::= { ps-fan-entry 3 }
status	OBJECT IDENTIFIER ::= { ps-fan-entry 4 }
sunSmTreeProp	OBJECT IDENTIFIER ::= { sunwUltra-10 1 }
sunSmNodeName	OBJECT IDENTIFIER ::= { sunwUltra-10 2 }
generic-deviceTbl	OBJECT IDENTIFIER ::= { generic-device 1 }
sunSmTreeProp	OBJECT IDENTIFIER ::= { dimm-entry 1 }
sunSmNodeName	OBJECT IDENTIFIER ::= { dimm-entry 2 }
entry-no	OBJECT IDENTIFIER ::= { dimm-entry 3 }
device-type	OBJECT IDENTIFIER ::= { dimm-entry 4 }
fru	OBJECT IDENTIFIER ::= { dimm-entry 5 }
fru-device	OBJECT IDENTIFIER ::= { dimm-entry 6 }
module-size	OBJECT IDENTIFIER ::= { dimm-entry 7 }
socket-name	OBJECT IDENTIFIER ::= { dimm-entry 8 }
status	OBJECT IDENTIFIER ::= { dimm-entry 9 }
generic-device-entry	OBJECT IDENTIFIER ::= { generic-deviceTbl 1 }
io-controllerTblEntry	OBJECT IDENTIFIER ::= { io-controllerTbl 1 }
sunwffb-entry	OBJECT IDENTIFIER ::= { sunwffb 1 }
cpu-unit-entry	OBJECT IDENTIFIER ::= { cpu-unitTbl 1 }
simmTbl	OBJECT IDENTIFIER ::= { simm 1 }
bankTbl	OBJECT IDENTIFIER ::= { bank 1 }
dimmTbl	OBJECT IDENTIFIER ::= { dimm 1 }
sunSmTreeProp	OBJECT IDENTIFIER ::= { power-led 1 }
sunSmNodeName	OBJECT IDENTIFIER ::= { power-led 2 }
state	OBJECT IDENTIFIER ::= { power-led 3 }
power-supply-fansTbl	OBJECT IDENTIFIER ::= { power-supply-fans 1 }
sunSmTreeProp	OBJECT IDENTIFIER ::= { io-controllerTblEntry 1 }
sunSmNodeName	OBJECT IDENTIFIER ::= { io-controllerTblEntry 2 }
entry-no	OBJECT IDENTIFIER ::= { io-controllerTblEntry 3 }
board-num	OBJECT IDENTIFIER ::= { io-controllerTblEntry 4 }
clock-frequency	OBJECT IDENTIFIER ::= { io-controllerTblEntry 5 }
device-type	OBJECT IDENTIFIER ::= { io-controllerTblEntry 6 }
instance	OBJECT IDENTIFIER ::= { io-controllerTblEntry 7 }
model	OBJECT IDENTIFIER ::= { io-controllerTblEntry 8 }
reg	OBJECT IDENTIFIER ::= { io-controllerTblEntry 9 }
upa-mid	OBJECT IDENTIFIER ::= { io-controllerTblEntry 10 }
upa-portid	OBJECT IDENTIFIER ::= { io-controllerTblEntry 11 }
version-no	OBJECT IDENTIFIER ::= { io-controllerTblEntry 12 }
tapeTbl	OBJECT IDENTIFIER ::= { tape 1 }
bank-entry	OBJECT IDENTIFIER ::= { bankTbl 1 }
sunSmTreeProp	OBJECT IDENTIFIER ::= { io-unitEntry 1 }
sunSmNodeName	OBJECT IDENTIFIER ::= { io-unitEntry 2 }
entry-no	OBJECT IDENTIFIER ::= { io-unitEntry 3 }
board-num	OBJECT IDENTIFIER ::= { io-unitEntry 4 }
device-id	OBJECT IDENTIFIER ::= { io-unitEntry 5 }
instance	OBJECT IDENTIFIER ::= { io-unitEntry 6 }
reg	OBJECT IDENTIFIER ::= { io-unitEntry 7 }
sunSmTreeProp	OBJECT IDENTIFIER ::= { ssp-entry 1 }
sunSmNodeName	OBJECT IDENTIFIER ::= { ssp-entry 2 }
entry-no	OBJECT IDENTIFIER ::= { ssp-entry 3 }
mc-entry	OBJECT IDENTIFIER ::= { mcTbl 1 }
sunSmTreeProp	OBJECT IDENTIFIER ::= { ffb-entry 1 }
sunSmNodeName	OBJECT IDENTIFIER ::= { ffb-entry 2 }
entry-no	OBJECT IDENTIFIER ::= { ffb-entry 3 }
buffer	OBJECT IDENTIFIER ::= { ffb-entry 4 }
device-type	OBJECT IDENTIFIER ::= { ffb-entry 5 }
model	OBJECT IDENTIFIER ::= { ffb-entry 6 }
pathname-element	OBJECT IDENTIFIER ::= { ffb-entry 7 }
cpu-fansTbl	OBJECT IDENTIFIER ::= { cpu-fans 1 }
sunSmTreeProp	OBJECT IDENTIFIER ::= { keyswitch 1 }
sunSmNodeName	OBJECT IDENTIFIER ::= { keyswitch 2 }
position	OBJECT IDENTIFIER ::= { keyswitch 3 }
sunSmTreeProp	OBJECT IDENTIFIER ::= { bank-entry 1 }
sunSmNodeName	OBJECT IDENTIFIER ::= { bank-entry 2 }
entry-no	OBJECT IDENTIFIER ::= { bank-entry 3 }
bank-size	OBJECT IDENTIFIER ::= { bank-entry 4 }
device-type	OBJECT IDENTIFIER ::= { bank-entry 5 }
fru-device	OBJECT IDENTIFIER ::= { bank-entry 6 }
status	OBJECT IDENTIFIER ::= { bank-entry 7 }
simm-entry	OBJECT IDENTIFIER ::= { simmTbl 1 }
reader4uwg	OBJECT IDENTIFIER ::= { config 3 }
fan-entry	OBJECT IDENTIFIER ::= { cpu-fansTbl 1 }
io-deviceEntry	OBJECT IDENTIFIER ::= { io-deviceTbl 1 }
memory-entry	OBJECT IDENTIFIER ::= { memory 1 }
sunSmTreeProp	OBJECT IDENTIFIER ::= { sunwUltra-60 1 }
sunSmNodeName	OBJECT IDENTIFIER ::= { sunwUltra-60 2 }
sunSmTreeProp	OBJECT IDENTIFIER ::= { disk-status-leds-entry 1 }
sunSmNodeName	OBJECT IDENTIFIER ::= { disk-status-leds-entry 2 }
entry-no	OBJECT IDENTIFIER ::= { disk-status-leds-entry 3 }
sunSmTreeProp	OBJECT IDENTIFIER ::= { system 1 }
sunSmNodeName	OBJECT IDENTIFIER ::= { system 2 }
os	OBJECT IDENTIFIER ::= { system 3 }
os-version	OBJECT IDENTIFIER ::= { system 4 }
system-clock-frequency	OBJECT IDENTIFIER ::= { system 5 }
architecture	OBJECT IDENTIFIER ::= { system 6 }
hostname	OBJECT IDENTIFIER ::= { system 7 }
machine	OBJECT IDENTIFIER ::= { system 8 }
platform	OBJECT IDENTIFIER ::= { system 9 }
sample	OBJECT IDENTIFIER ::= { system 10 }
serial-number	OBJECT IDENTIFIER ::= { system 11 }
timestamp	OBJECT IDENTIFIER ::= { system 12 }
timestamp-raw	OBJECT IDENTIFIER ::= { system 13 }
total-disks	OBJECT IDENTIFIER ::= { system 14 }
total-memory	OBJECT IDENTIFIER ::= { system 15 }
total-processors	OBJECT IDENTIFIER ::= { system 16 }
total-tape-devices	OBJECT IDENTIFIER ::= { system 17 }
total-model-changes	OBJECT IDENTIFIER ::= { system 18 }
total-config-changes	OBJECT IDENTIFIER ::= { system 19 }
sunSmTreeProp	OBJECT IDENTIFIER ::= { sunwffb-entry 1 }
sunSmNodeName	OBJECT IDENTIFIER ::= { sunwffb-entry 2 }
entry-no	OBJECT IDENTIFIER ::= { sunwffb-entry 3 }
dram3	OBJECT IDENTIFIER ::= { sunwffb-entry 4 }
dac	OBJECT IDENTIFIER ::= { sunwffb-entry 5 }
fbc-version	OBJECT IDENTIFIER ::= { sunwffb-entry 6 }
board-type	OBJECT IDENTIFIER ::= { sunwffb-entry 7 }
buffer	OBJECT IDENTIFIER ::= { sunwffb-entry 8 }
device-type	OBJECT IDENTIFIER ::= { sunwffb-entry 9 }
height	OBJECT IDENTIFIER ::= { sunwffb-entry 10 }
model	OBJECT IDENTIFIER ::= { sunwffb-entry 11 }
revision	OBJECT IDENTIFIER ::= { sunwffb-entry 12 }
upa-portid	OBJECT IDENTIFIER ::= { sunwffb-entry 13 }
width	OBJECT IDENTIFIER ::= { sunwffb-entry 14 }
networkEntry	OBJECT IDENTIFIER ::= { networkTbl 1 }
sunSmTreeProp	OBJECT IDENTIFIER ::= { rsc 1 }
sunSmNodeName	OBJECT IDENTIFIER ::= { rsc 2 }
device-type	OBJECT IDENTIFIER ::= { rsc 3 }
fru-device	OBJECT IDENTIFIER ::= { rsc 4 }
name	OBJECT IDENTIFIER ::= { rsc 5 }
rsc-hostname	OBJECT IDENTIFIER ::= { rsc 6 }
sunSmTreeProp	OBJECT IDENTIFIER ::= { io-deviceEntry 1 }
sunSmNodeName	OBJECT IDENTIFIER ::= { io-deviceEntry 2 }
entry-no	OBJECT IDENTIFIER ::= { io-deviceEntry 3 }
device-type	OBJECT IDENTIFIER ::= { io-deviceEntry 4 }
disk-count	OBJECT IDENTIFIER ::= { io-deviceEntry 5 }
instance	OBJECT IDENTIFIER ::= { io-deviceEntry 6 }
model	OBJECT IDENTIFIER ::= { io-deviceEntry 7 }
node-hierarchy	OBJECT IDENTIFIER ::= { io-deviceEntry 8 }
network-count	OBJECT IDENTIFIER ::= { io-deviceEntry 9 }
reg	OBJECT IDENTIFIER ::= { io-deviceEntry 10 }
tape-count	OBJECT IDENTIFIER ::= { io-deviceEntry 11 }
fan-entry	OBJECT IDENTIFIER ::= { fan 1 }
sunSmTreeProp	OBJECT IDENTIFIER ::= { ps-error-led 1 }
sunSmNodeName	OBJECT IDENTIFIER ::= { ps-error-led 2 }
state	OBJECT IDENTIFIER ::= { ps-error-led 3 }
sunSmTreeProp	OBJECT IDENTIFIER ::= { cpu-unit-entry 1 }
sunSmNodeName	OBJECT IDENTIFIER ::= { cpu-unit-entry 2 }
entry-no	OBJECT IDENTIFIER ::= { cpu-unit-entry 3 }
clock-frequency	OBJECT IDENTIFIER ::= { cpu-unit-entry 4 }
cpu-type	OBJECT IDENTIFIER ::= { cpu-unit-entry 5 }
dcache-size	OBJECT IDENTIFIER ::= { cpu-unit-entry 6 }
device-type	OBJECT IDENTIFIER ::= { cpu-unit-entry 7 }
ecache-size	OBJECT IDENTIFIER ::= { cpu-unit-entry 8 }
fru	OBJECT IDENTIFIER ::= { cpu-unit-entry 9 }
icache-size	OBJECT IDENTIFIER ::= { cpu-unit-entry 10 }
model	OBJECT IDENTIFIER ::= { cpu-unit-entry 11 }
pathname-element	OBJECT IDENTIFIER ::= { cpu-unit-entry 12 }
processor-id	OBJECT IDENTIFIER ::= { cpu-unit-entry 13 }
status	OBJECT IDENTIFIER ::= { cpu-unit-entry 14 }
unit	OBJECT IDENTIFIER ::= { cpu-unit-entry 15 }
temperature	OBJECT IDENTIFIER ::= { cpu-unit-entry 16 }
upa-portid	OBJECT IDENTIFIER ::= { cpu-unit-entry 17 }
io-deviceTbl	OBJECT IDENTIFIER ::= { io-device 1 }
sunSmTreeProp	OBJECT IDENTIFIER ::= { sunwUltra-250 1 }
sunSmNodeName	OBJECT IDENTIFIER ::= { sunwUltra-250 2 }
sunSmTreeProp	OBJECT IDENTIFIER ::= { tapeEntry 1 }
sunSmNodeName	OBJECT IDENTIFIER ::= { tapeEntry 2 }
entry-no	OBJECT IDENTIFIER ::= { tapeEntry 3 }
device-type	OBJECT IDENTIFIER ::= { tapeEntry 4 }
fru	OBJECT IDENTIFIER ::= { tapeEntry 5 }
instance	OBJECT IDENTIFIER ::= { tapeEntry 6 }
model	OBJECT IDENTIFIER ::= { tapeEntry 7 }
node-hierarchy	OBJECT IDENTIFIER ::= { tapeEntry 8 }
tape-name	OBJECT IDENTIFIER ::= { tapeEntry 9 }
status	OBJECT IDENTIFIER ::= { tapeEntry 10 }
target	OBJECT IDENTIFIER ::= { tapeEntry 11 }
soft-errors	OBJECT IDENTIFIER ::= { tapeEntry 12 }
hard-errors	OBJECT IDENTIFIER ::= { tapeEntry 13 }
transport-errors	OBJECT IDENTIFIER ::= { tapeEntry 14 }
power-supply-entry	OBJECT IDENTIFIER ::= { power-supplyTbl 1 }
io-controllerTbl	OBJECT IDENTIFIER ::= { io-controller 1 }
sunSmTreeProp	OBJECT IDENTIFIER ::= { fan-entry 1 }
sunSmNodeName	OBJECT IDENTIFIER ::= { fan-entry 2 }
entry-no	OBJECT IDENTIFIER ::= { fan-entry 3 }
status	OBJECT IDENTIFIER ::= { fan-entry 4 }
speed	OBJECT IDENTIFIER ::= { fan-entry 5 }
tapeEntry	OBJECT IDENTIFIER ::= { tapeTbl 1 }
sunSmTreeProp	OBJECT IDENTIFIER ::= { diskEntry 1 }
sunSmNodeName	OBJECT IDENTIFIER ::= { diskEntry 2 }
entry-no	OBJECT IDENTIFIER ::= { diskEntry 3 }
device-type	OBJECT IDENTIFIER ::= { diskEntry 4 }
disk-name	OBJECT IDENTIFIER ::= { diskEntry 5 }
fru	OBJECT IDENTIFIER ::= { diskEntry 6 }
instance	OBJECT IDENTIFIER ::= { diskEntry 7 }
node-hierarchy	OBJECT IDENTIFIER ::= { diskEntry 8 }
target	OBJECT IDENTIFIER ::= { diskEntry 9 }
soft-errors	OBJECT IDENTIFIER ::= { diskEntry 10 }
hard-errors	OBJECT IDENTIFIER ::= { diskEntry 11 }
transport-errors	OBJECT IDENTIFIER ::= { diskEntry 12 }
sunSmTreeProp	OBJECT IDENTIFIER ::= { memory-entry 1 }
sunSmNodeName	OBJECT IDENTIFIER ::= { memory-entry 2 }
entry-no	OBJECT IDENTIFIER ::= { memory-entry 3 }
pathname-element	OBJECT IDENTIFIER ::= { memory-entry 4 }
sunSmTreeProp	OBJECT IDENTIFIER ::= { generic-device-entry 1 }
sunSmNodeName	OBJECT IDENTIFIER ::= { generic-device-entry 2 }
entry-no	OBJECT IDENTIFIER ::= { generic-device-entry 3 }
pathname-element	OBJECT IDENTIFIER ::= { generic-device-entry 4 }
ssp-entry	OBJECT IDENTIFIER ::= { system-status-panel 1 }
mcTbl	OBJECT IDENTIFIER ::= { mc 1 }
sunSmTreeProp	OBJECT IDENTIFIER ::= { active-led 1 }
sunSmNodeName	OBJECT IDENTIFIER ::= { active-led 2 }
state	OBJECT IDENTIFIER ::= { active-led 3 }
sunSmTreeProp	OBJECT IDENTIFIER ::= { temp-error-led 1 }
sunSmNodeName	OBJECT IDENTIFIER ::= { temp-error-led 2 }
state	OBJECT IDENTIFIER ::= { temp-error-led 3 }
dimm-entry	OBJECT IDENTIFIER ::= { dimmTbl 1 }
ffb-entry	OBJECT IDENTIFIER ::= { ffb 1 }
sunSmTreeProp	OBJECT IDENTIFIER ::= { sunwUltra-5-10 1 }
sunSmNodeName	OBJECT IDENTIFIER ::= { sunwUltra-5-10 2 }
diskTbl	OBJECT IDENTIFIER ::= { disk 1 }
sunSmTreeProp	OBJECT IDENTIFIER ::= { sunwUltra-1 1 }
sunSmNodeName	OBJECT IDENTIFIER ::= { sunwUltra-1 2 }
sunSmTreeProp	OBJECT IDENTIFIER ::= { sunwUltra-2 1 }
sunSmNodeName	OBJECT IDENTIFIER ::= { sunwUltra-2 2 }
sunSmTreeProp	OBJECT IDENTIFIER ::= { disk-error-led 1 }
sunSmNodeName	OBJECT IDENTIFIER ::= { disk-error-led 2 }
state	OBJECT IDENTIFIER ::= { disk-error-led 3 }
rcr4u290	OBJECT IDENTIFIER ::= { hardware-rules 2 }
sunSmTreeProp	OBJECT IDENTIFIER ::= { sunwUltra-4 1 }
sunSmNodeName	OBJECT IDENTIFIER ::= { sunwUltra-4 2 }
sunSmTreeProp	OBJECT IDENTIFIER ::= { mc-entry 1 }
sunSmNodeName	OBJECT IDENTIFIER ::= { mc-entry 2 }
entry-no	OBJECT IDENTIFIER ::= { mc-entry 3 }
device-type	OBJECT IDENTIFIER ::= { mc-entry 4 }
fru-device	OBJECT IDENTIFIER ::= { mc-entry 5 }
sunSmTreeProp	OBJECT IDENTIFIER ::= { gen-error-led 1 }
sunSmNodeName	OBJECT IDENTIFIER ::= { gen-error-led 2 }
state	OBJECT IDENTIFIER ::= { gen-error-led 3 }
sunSmTreeProp	OBJECT IDENTIFIER ::= { sunwUltra-5 1 }
sunSmNodeName	OBJECT IDENTIFIER ::= { sunwUltra-5 2 }
sunSmTreeProp	OBJECT IDENTIFIER ::= { system-board 1 }
sunSmNodeName	OBJECT IDENTIFIER ::= { system-board 2 }
fru	OBJECT IDENTIFIER ::= { system-board 3 }
state	OBJECT IDENTIFIER ::= { system-board 4 }
io-unitEntry	OBJECT IDENTIFIER ::= { io-unit 1 }
networkTbl	OBJECT IDENTIFIER ::= { network 1 }
afb-entry	OBJECT IDENTIFIER ::= { afb 1 }
sunSmTreeProp	OBJECT IDENTIFIER ::= { afb-entry 1 }
sunSmNodeName	OBJECT IDENTIFIER ::= { afb-entry 2 }
entry-no	OBJECT IDENTIFIER ::= { afb-entry 3 }
buffer	OBJECT IDENTIFIER ::= { afb-entry 4 }
device-type	OBJECT IDENTIFIER ::= { afb-entry 5 }
model	OBJECT IDENTIFIER ::= { afb-entry 6 }
pathname-element	OBJECT IDENTIFIER ::= { afb-entry 7 }
sunSmTreeProp	OBJECT IDENTIFIER ::= { sunwUltra-80 1 }
sunSmNodeName	OBJECT IDENTIFIER ::= { sunwUltra-80 2 }
diskEntry	OBJECT IDENTIFIER ::= { diskTbl 1 }

END
