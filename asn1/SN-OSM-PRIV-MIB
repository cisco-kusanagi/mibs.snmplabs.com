----------------------------------------------------------------------------------------------------
-- SIEMENS AG   MIB for MIB Compiler OPC SNMP Server SIMATIC NET
-- SN-OSM-PRIV-MIB.mib
-- RFC  
-- Version: 1.1
-- Date: 10.09.2002
-- Comment: Private MIB OSM
----------------------------------------------------------------------------------------------------

-- ----------------------------------------------------------------------
-- snOSM.mib
-- SIMATIC NET Industrial Ethernet 
-- OSM/ESM Private MIB
-- Copyright (c) 2002 Siemens AG
-- ----------------------------------------------------------------------
--
-- MIB Module :   SN-OSM-PRIV-MIB
--
-- Revision   :   V1.2.0.7
-- Date       :	  2002/09/10 
--
-- ----------------------------------------------------------------------

SN-OSM-PRIV-MIB DEFINITIONS ::= BEGIN

  IMPORTS
	TRAP-TYPE FROM RFC-1215
          enterprises,IpAddress,internet,
          TimeTicks,Counter FROM RFC1155-SMI
	  
	  DisplayString, ifIndex
                FROM RFC1213-MIB

          OBJECT-TYPE FROM RFC-1212;

ad                      OBJECT IDENTIFIER ::= { enterprises 4196 }
adProductMibs           OBJECT IDENTIFIER ::= { ad 1 }
simaticNet              OBJECT IDENTIFIER ::= { adProductMibs 1 }
iHub                    OBJECT IDENTIFIER ::= { simaticNet 1 }
iSwitch                 OBJECT IDENTIFIER ::= { simaticNet 2 }

-- -------------------------------------------------------------
-- SIMATIC NET OSM/ESM Products
-- These objects are used as sysObjectID of the products.
-- -------------------------------------------------------------

snOsmItp62				OBJECT IDENTIFIER ::= { iSwitch 1 }
snOsmItp53				OBJECT IDENTIFIER ::= { iSwitch 2 }
snOsmItpLd62				OBJECT IDENTIFIER ::= { iSwitch 3 }
snEsmItp80				OBJECT IDENTIFIER ::= { iSwitch 4 }
snOsmTp62				OBJECT IDENTIFIER ::= { iSwitch 5 }
snEsmTp80				OBJECT IDENTIFIER ::= { iSwitch 6 }
snOsmBC08				OBJECT IDENTIFIER ::= { iSwitch 7 }
snOsmTpLd62				OBJECT IDENTIFIER ::= { iSwitch 8 }
snOsmTp22				OBJECT IDENTIFIER ::= { iSwitch 9 }
snEsmTp40				OBJECT IDENTIFIER ::= { iSwitch 10 }
snOsmTp62-Advanced			OBJECT IDENTIFIER ::= { iSwitch 11 }
snEsmItp80-Advanced			OBJECT IDENTIFIER ::= { iSwitch 12 }
snEsmTp80-Advanced			OBJECT IDENTIFIER ::= { iSwitch 13 }
snOsmItpLd62-Advanced			OBJECT IDENTIFIER ::= { iSwitch 14 }
snOsmItp62-Advanced			OBJECT IDENTIFIER ::= { iSwitch 15 }
snOsmItp53-Advanced			OBJECT IDENTIFIER ::= { iSwitch 16 }
snOsmTp53				OBJECT IDENTIFIER ::= { iSwitch 17 }

-- ************************************************************
--          SIMATIC NET OSM/ESM Private MIB
-- ************************************************************

-- ------------------------------------------------------------
-- SIMATIC NET OSM/ESM Object Identifier Definition
-- ------------------------------------------------------------
iSwitchMib  	OBJECT IDENTIFIER ::= { iSwitch 100 }

-- -------------------------------------------------------------
-- Groups in SN-PRIVATE-MIB
-- -------------------------------------------------------------
-- --------------------------------------------------------------
-- textual conventions
-- --------------------------------------------------------------
          MacAddress ::= OCTET STRING (SIZE (6))    -- a 6 octet address
                                                    -- in the
                                                    -- "canonical"
                                                    -- order
          -- defined by IEEE 802.1a, i.e., as if it were transmitted
          -- least significant bit first, even though 802.5 (in
          -- contrast to other n802.x protocols) requires MAC
          -- addresses to be transmitted most significant bit first.
          --
          -- 16-bit addresses, if needed, are represented by setting
          -- their upper 4 octets to all 0's, i.e., AAFF would be
          -- represented as 00000000AAFF.

-- -------------------------------------------------------------
-- SIMATIC NET OSM/ESM Objects
-- -------------------------------------------------------------
snCommon             OBJECT IDENTIFIER ::= { iSwitchMib 1 }
snProductSpecific    OBJECT IDENTIFIER ::= { iSwitchMib 2 }

-- -------------------------------------------------------------
-- SIMATIC NET OSM/ESM Common Objects
-- -------------------------------------------------------------
snDownload           OBJECT IDENTIFIER ::= { snCommon 5  }
snNvLog              OBJECT IDENTIFIER ::= { snCommon 6  }
snTrapInfo           OBJECT IDENTIFIER ::= { snCommon 7  }
snGen                OBJECT IDENTIFIER ::= { snCommon 8  }
snTcpip              OBJECT IDENTIFIER ::= { snCommon 10 }

-- -------------------------------------------------------------
-- SIMATIC NET OSM/ESM Product Specific Objects
-- -------------------------------------------------------------
snOsm		  OBJECT IDENTIFIER ::= { snProductSpecific 1 } 


-- --------------------------------------------------------------
-- AD-DOWNLOAD-MIB:
-- --------------------------------------------------------------

-- --------------------------------------------------------------
-- Download Sub-Groups
-- --------------------------------------------------------------
snDownloadParams   OBJECT IDENTIFIER ::= {snDownload 1}

-- --------------------------------------------------------------
-- SIMATIC NET OSM/ESM Download Group
-- This group contains all the download related parameters.
-- --------------------------------------------------------------
snDownloadParamsTftpServerHostName OBJECT-TYPE
        SYNTAX  DisplayString  (SIZE(0..64))
        ACCESS  read-write
        STATUS  mandatory
        DESCRIPTION
            "IP address of the TFTP server (x.y.z.w)."
         DEFVAL  {"0.0.0.0"}
        ::= { snDownloadParams 2 }


snDownloadParamsFile       OBJECT-TYPE
        SYNTAX  DisplayString (SIZE(0..32))
        ACCESS  read-write
        STATUS  mandatory
        DESCRIPTION  "Full path name of file to be loaded from the TFTP
            server host. Note that the file name must have the appropriate syntax
            for the TFTP server host.
            E.g., if the TFTP server host is a UNIX machine, the full file name
            might be  /tftp/name.lad, or if the TFTP server host is a Windows
            machine, the full file name might be  C:\tftp\name.lad."
        DEFVAL  {"Not Defined Yet"}
        ::= { snDownloadParams 3 }


snDownloadParamsControl    OBJECT-TYPE
        SYNTAX  INTEGER {
          start-load(2),
          cancel-load(3)
        }
        ACCESS  write-only
        STATUS  mandatory
        DESCRIPTION  "Setting this object to start-load(2) causes the
            system to start a downloading process.
            Setting this object to cancel-load(3) causes the system to abort
            a downloading process.
            If ParamsProtocol is <tftp-server> the object is not writable.
            Reading the object, meaning-less(127) is returned."
        ::= { snDownloadParams 4 }


snDownloadParamsStatus OBJECT-TYPE
        SYNTAX  INTEGER {
	  load-in-progress(2),
          load-inactive(3),
	  load-interrupted(4)
        }
        ACCESS  read-only
        STATUS  mandatory
        DESCRIPTION  "The status of the TFTP client."
        DEFVAL  {load-inactive}
        ::= { snDownloadParams 5 }


snDownloadNextBlockId  OBJECT-TYPE
        SYNTAX  INTEGER
        ACCESS  read-only
        STATUS  mandatory
        DESCRIPTION  "The number of the next block ID expected by the TFTP
        session. Block ID's are numbers starting with 1. "
        DEFVAL  {0}
        ::= { snDownloadParams 6 }

snDownloadParamsError  OBJECT-TYPE
        SYNTAX  DisplayString
        ACCESS  read-only
        STATUS  mandatory
        DESCRIPTION  "The error status of the TFTP client."
        DEFVAL  {""}
        ::= { snDownloadParams 7 }

snDownloadAutoLoad OBJECT-TYPE
      SYNTAX INTEGER {
        enabled(1),
        disabled(2)
      }
      ACCESS read-write
      STATUS    mandatory
      DESCRIPTION "The value enabled(1) will automatically start TFTP when the
                   Operative Program is invalid.
                   The value disabled(2) will inhibit TFTP."
      DEFVAL { disabled }
      ::= {  snDownloadParams 8 }


snDownloadEventLogTableFile       OBJECT-TYPE
        SYNTAX  DisplayString (SIZE(0..32))
        ACCESS  read-write
        STATUS  mandatory
        DESCRIPTION  "Full path name of file to be saved to the TFTP
            server host. Note that the file name must have the appropriate syntax
            for the TFTP server host.
            E.g., if the TFTP server host is a UNIX machine, the full file name
            might be  /tftp/name.txt, or if the TFTP server host is a Windows
            machine, the full file name might be  C:\tftp\name.txt."
        DEFVAL  {"Not Defined Yet"}
        ::= { snDownloadParams 9 }


snDownloadEventLogTableControl    OBJECT-TYPE
        SYNTAX  INTEGER {
          start-load(2),
	  start-save(3),
          cancel(4),
	  continue-process(5),
	  abort-process(6)
        }
        ACCESS  write-only
        STATUS  mandatory
        DESCRIPTION  "Setting this object to start-save(3) causes the
            system to start a uploading process.
            Setting this object to cancel-(4) causes the system to abort
            a uploading process.
            If ParamsProtocol is <tftp-server> the object is not writable.
            Reading the object, meaning-less(127) is returned."
        ::= { snDownloadParams 10 }


snDownloadConfigFile       OBJECT-TYPE
        SYNTAX  DisplayString (SIZE(0..32))
        ACCESS  read-write
        STATUS  mandatory
        DESCRIPTION  "Full path name of file to be saved or loaded from the TFTP
            server host. Note that the file name must have the appropriate syntax
            for the TFTP server host.
            E.g., if the TFTP server host is a UNIX machine, the full file name
            might be  /tftp/name.txt, or if the TFTP server host is a Windows
            machine, the full file name might be  C:\tftp\name.txt."
        DEFVAL  {"Not Defined Yet"}
        ::= { snDownloadParams 11 }

snDownloadConfigControl    OBJECT-TYPE
        SYNTAX  INTEGER {
          start-load(2),
	  start-save(3),
          cancel(4),
	  continue-process(5),
	  abort-process(6)
        }
        ACCESS  write-only
        STATUS  mandatory
        DESCRIPTION  "Setting this object to start-load(2) causes the
            system to start a downloading process.
            Setting this object to start-save(3) causes the
            system to start a uploading process.
            Setting this object to cancel-(4) causes the system to abort
            the process.
            If ParamsProtocol is <tftp-server> the object is not writable.
            Reading the object, meaning-less(127) is returned."
        ::= { snDownloadParams 12 }

-- --------------------------------------------------------------
-- AD-NVLG-MIB:
-- --------------------------------------------------------------
snNvLogMaxEntries  OBJECT-TYPE
  SYNTAX    INTEGER (10..400)
  ACCESS    read-write
  STATUS    mandatory
  DESCRIPTION
    "Maximum number of events that can be kept in 
	Non-Volatile Memory."
        DEFVAL { 200 }
  ::= { snNvLog 1 }

snNvLogCurrentEntries  OBJECT-TYPE
  SYNTAX    INTEGER
  ACCESS    read-only
  STATUS    mandatory
  DESCRIPTION
    "Number of events that are currently kept in 
	Non-Volatile Memory."
        DEFVAL { 0 }
  ::= { snNvLog 2 }

snNvLogNewEntries  OBJECT-TYPE
  SYNTAX    INTEGER
  ACCESS    read-write
  STATUS    mandatory
  DESCRIPTION
    "Counter for events that are logged in Non-Volatile Memory. 
	This counter starts at 0 after each system start. User can reset 
	this counter at any time by writing 0 to this object."
        DEFVAL { 0 }
  ::= { snNvLog 3 }

snNvLogClear   OBJECT-TYPE
  SYNTAX    INTEGER{
    clear(1)
  }
  ACCESS    write-only
  STATUS    mandatory
  DESCRIPTION
    "Setting this object to clear(1) value, clears the
     events that are kept in Non-Volatile Memory."
  ::= { snNvLog 4 }

snNvLogTable   OBJECT-TYPE
  SYNTAX    SEQUENCE OF SnNvLogEntry
  ACCESS    not-accessible
  STATUS    mandatory
  DESCRIPTION
    "The table contains the last events that occurred 
	in the system."
  ::= { snNvLog 5 }

snNvLogEntry   OBJECT-TYPE
  SYNTAX    SnNvLogEntry
  ACCESS    not-accessible
  STATUS    mandatory
  DESCRIPTION
    "The description of an event that occurred in the system,
     and was stored in Non-Volatile memory."
  INDEX { snNvLogPowerUpCount ,
                snNvLogTime ,
                snNvLogSequenceNumber }
  ::= { snNvLogTable 1 }

SnNvLogEntry ::= SEQUENCE {
  snNvLogPowerUpCount
    INTEGER,
  snNvLogTime
      TimeTicks,
  snNvLogSequenceNumber
    INTEGER,
  snNvLogDescr
    DisplayString
  }

snNvLogPowerUpCount       OBJECT-TYPE
        SYNTAX  INTEGER
        ACCESS  read-only
        STATUS  mandatory
        DESCRIPTION
                "The number of times the system was powered up."
        DEFVAL { 0 }
        ::= { snNvLogEntry 1 }

snNvLogTime       OBJECT-TYPE
        SYNTAX  TimeTicks
        ACCESS  read-only
        STATUS  mandatory
        DESCRIPTION
                "The sysUpTime of the system when the event occurred."
        DEFVAL { 0 }
        ::= { snNvLogEntry 2 }

snNvLogSequenceNumber       OBJECT-TYPE
        SYNTAX  INTEGER
        ACCESS  read-only
        STATUS  mandatory
        DESCRIPTION
                "The sequence number of the log entry."
        DEFVAL { 0 }
        ::= { snNvLogEntry 3 }

snNvLogDescr   OBJECT-TYPE
  SYNTAX    DisplayString (SIZE (0..256))
  ACCESS    read-only
  STATUS    mandatory
  DESCRIPTION
    "ASCII description of the event."
        DEFVAL { "" }
  ::= { snNvLogEntry 4 }

snNvLogPositionDescr  OBJECT-TYPE
  SYNTAX    DisplayString (SIZE (0..255))
  ACCESS    read-write
  STATUS    mandatory
  DESCRIPTION
    "Read - find the oid of the entry with spezial number in log table.
	 Write - set the entry number in log table for the read request."
        DEFVAL { "" }
  ::= { snNvLog 6 }

-- --------------------------------------------------------------
-- AD-SNMPv2:
-- --------------------------------------------------------------
snmpV2         OBJECT IDENTIFIER ::= { internet 6 }
snmpModules    OBJECT IDENTIFIER ::= { snmpV2 3 }
snmpMIB        OBJECT IDENTIFIER ::= { snmpModules 1 }
snmpMIBObjects OBJECT IDENTIFIER ::= { snmpMIB 1 }

snmpTraps      OBJECT IDENTIFIER ::= { snmpMIBObjects 5 }

IANAifType ::= INTEGER {
		   other(1),          -- none of the following
		   regular1822(2),
		   hdh1822(3),
		   ddnX25(4),
		   rfc877x25(5),
		   ethernetCsmacd(6),
		   iso88023Csmacd(7),
		   iso88024TokenBus(8),
		   iso88025TokenRing(9),
		   iso88026Man(10),
		   starLan(11),
		   proteon10Mbit(12),
		   proteon80Mbit(13),
		   hyperchannel(14),
		   fddi(15),
		   lapb(16),
		   sdlc(17),
		   ds1(18),           -- DS1/E1 (RFC 1406)
		   e1(19),            -- obsolete
		   basicISDN(20),
		   primaryISDN(21),
		   propPointToPointSerial(22), -- proprietary serial
		   ppp(23),
		   softwareLoopback(24),
		   eon(25),            -- CLNP over IP (RFC 1070)
		   ethernet3Mbit(26),
		   nsip(27),           -- XNS over IP
		   slip(28),           -- generic SLIP
		   ultra(29),          -- ULTRA technologies
		   ds3(30),            -- T-3
		   sip(31),            -- SMDS
		   frameRelay(32),    -- DTE only
		   rs232(33),
		   para(34),           -- parallel-port
		   arcnet(35),         -- arcnet
		   arcnetPlus(36),     -- arcnet plus
		   atm(37),            -- ATM cells
		   miox25(38),
		   sonet(39),          -- SONET or SDH
		   x25ple(40),
		   iso88022llc(41),
		   localTalk(42),
		   smdsDxi(43),
		   frameRelayService(44),  -- Frame relay DCE
		   v35(45),
		   hssi(46),
		   hippi(47),
		   modem(48),          -- Generic modem
		   aal5(49),           -- AAL5 over ATM
		   sonetPath(50),
		   sonetVT(51),
		   smdsIcip(52),       -- SMDS InterCarrier Interface
		   propVirtual(53),    -- proprietary virtual/internal
		   propMultiplexor(54) -- proprietary multiplexing
	       }

-- --------------------------------------------------------------
-- AD-TRAP-MIB:
-- --------------------------------------------------------------
snSwitchTrapsEnable OBJECT-TYPE
    SYNTAX  INTEGER {
      not-supported(10),
      enabled(1),
      disabled(2)
    }
    ACCESS  read-write
    STATUS  mandatory
    DESCRIPTION
       "Determines whether this device will
        transmit traps to SNMP management stations.
        This if this object is set to disable, no traps
        will be sent.  Setting this object to enabled
        is a necessary, but not a sufficient condition for
        transmission of traps."
     DEFVAL { enabled }
    ::= { snTrapInfo 1 }


snTrapTimeLastGenerated OBJECT-TYPE
        SYNTAX TimeTicks
        ACCESS read-only
        STATUS mandatory
        DESCRIPTION
                "The value of sysUpTime at the time the last trap was
     generated."
        DEFVAL { 0 }
        ::= { snTrapInfo 5 }

snTrapMaxManagers  OBJECT-TYPE
  SYNTAX    INTEGER
  ACCESS    read-only
  STATUS    mandatory
  DESCRIPTION
    "The maximum number of managers that can be registered
     for receiving traps."
        DEFVAL { 10 }
  ::= { snTrapInfo 6 }

snTrapTable    OBJECT-TYPE
  SYNTAX  SEQUENCE OF SnTrapEntry
  ACCESS  not-accessible
  STATUS  mandatory
  DESCRIPTION
    "This table contains information about the managers
     to which traps should be directed.

     Setting the snTrapState to inactive(3) removes
     the corresponding entry from the table."
  ::= { snTrapInfo 7 }

snTrapEntry    OBJECT-TYPE
  SYNTAX  SnTrapEntry
  ACCESS  not-accessible
  STATUS  mandatory
        DESCRIPTION
                   "This object contains runtime information about
                    an individual trap destination."
  INDEX   { snTrapIndex }
  ::= { snTrapTable 1 }

SnTrapEntry ::= SEQUENCE {
  snTrapAddress  IpAddress,
  snTrapState    INTEGER,
  snTrapIndex   INTEGER
  }

snTrapAddress  OBJECT-TYPE
  SYNTAX    IpAddress
        ACCESS  read-write
        STATUS  mandatory
  DESCRIPTION
    "The IP address of the network management entity
     to which traps should be sent."
        DEFVAL { 0 }
  ::= { snTrapEntry 1 }

snTrapState    OBJECT-TYPE
  SYNTAX  INTEGER {
        other(1),
        active(2),
        inactive(3)
    }
        ACCESS  read-write
        STATUS  mandatory
  DESCRIPTION
    "The state of this entry in the trap address
     table.  Setting this object to inactive(3)
     removes the corresponding entry from the table."
  DEFVAL { inactive }
  ::= { snTrapEntry 3 }

snTrapIndex    OBJECT-TYPE
  SYNTAX    INTEGER
  ACCESS    read-only
  STATUS    mandatory
  DESCRIPTION
    "The Index of Trap Table."
  REFERENCE
    "snTrapIndex"
	DEFVAL { 0 }
    ::= { snTrapEntry 6 }

-- --------------------------------------------------------------
-- AD-GEN-MIB:
-- --------------------------------------------------------------
snUserDescription  OBJECT-TYPE
  SYNTAX    DisplayString (SIZE (0..255))
  ACCESS    read-write
  STATUS    mandatory
  DESCRIPTION
    "Extended description of the station including user specific
      information. This value is used for the email From-field."
   DEFVAL  {"Not Defined Yet"}
  ::= { snGen 1 }

snHwVersion OBJECT-TYPE
  SYNTAX DisplayString (SIZE (0..20))
  ACCESS read-only
  STATUS mandatory
  DESCRIPTION
    "The hardware version of the system."
  ::= { snGen 2 }

snBootStrapVersion OBJECT-TYPE
  SYNTAX DisplayString (SIZE (0..20))
  ACCESS read-only
  STATUS mandatory
  DESCRIPTION
    "The firmware version of the boot software installed
     in the system."
  ::= { snGen 3 }

snSwVersion OBJECT-TYPE
   SYNTAX  DisplayString (SIZE(0..255))
   ACCESS  read-only
   STATUS  mandatory
   DESCRIPTION
    "The firmware version of the system."
   ::= { snGen 4 }

snInfoOrderNr OBJECT-TYPE
   SYNTAX DisplayString (SIZE(0..20))
   ACCESS read-only
   STATUS mandatory
   DESCRIPTION "The order number of this product."
   ::= { snGen 6 }

snSerialPortSpeed  OBJECT-TYPE
   SYNTAX  INTEGER{
     other(1),
     o9600bps(5),
     o19200bps(6),
     o38400bps(7),
     o115200bps(9)
      }
   ACCESS  read-write
   STATUS  mandatory
   DESCRIPTION
           "The serial port speed in bits per second."
   ::= { snGen 8 }


snSwitchTelnetEnable OBJECT-TYPE
    SYNTAX  INTEGER {
      not-supported(10),
      enabled(1),
      disabled(2)
    }
    ACCESS  read-write
    STATUS  mandatory
    DESCRIPTION   "Enable/Disable TELNET access."
    DEFVAL { enabled }
    ::= { snGen 9 }

snSwitchTelnetTimeOutEnable OBJECT-TYPE
    SYNTAX  INTEGER {
      enabled(1),
      disabled(2)
    }
    ACCESS  read-write
    STATUS  mandatory
    DESCRIPTION   "Enables or disables the time out for a TELNET session."
    DEFVAL { enabled }
    ::= { snGen 10 }

snSwitchTelnetTimeOut OBJECT-TYPE
    SYNTAX  INTEGER (60..600)
    ACCESS  read-write
    STATUS  mandatory
    DESCRIPTION   "Time out for the TELNET session. The time could be set in 
                   steps of 10 seconds. Minimum value is 60 seconds, maximum value is 600 seconds."
    DEFVAL { 300 }
    ::= { snGen 11 }


snSwitchSNMPEnable OBJECT-TYPE
    SYNTAX  INTEGER {
      not-supported(10),
      enabled(1),
      disabled(2)
    }
    ACCESS  read-write
    STATUS  mandatory
    DESCRIPTION
       "Determines whether this device may be
         accessed by SNMP management stations."
    DEFVAL { enabled }
    ::= { snGen 12 }


-- --------------------------------------------------------------
-- SIMATIC NET OSM/ESM System Reset Group
--
-- This group contains Action MIB Objects that perform reset operations.
-- --------------------------------------------------------------
snSysReset  OBJECT-TYPE
  SYNTAX  INTEGER {
        cold-reset(1),
        warm-reset(2)
    }
  ACCESS  write-only
  STATUS  mandatory
  DESCRIPTION
    "Resets the system.
     cold-reset(1) is identical to Power-On-Reset or Watchdog-Reset.
     warm-reset(2) is identical to restart command."
  ::= { snGen 13 }

snResetPowerUpCount OBJECT-TYPE
  SYNTAX INTEGER
  ACCESS read-only
  STATUS  mandatory
  DESCRIPTION 
    "The number of times the sytem was powered up."
  ::= { snGen 14 }

snSetFactoryDefs   OBJECT-TYPE
  SYNTAX    INTEGER {
     set-factory-defaults(1),
     set-factory-defaults-complete(2)
  }
  ACCESS    read-write
  STATUS    mandatory
  DESCRIPTION
    "Restore factory defaults."
  ::= { snGen 15 }

snResetCounters   OBJECT-TYPE
  SYNTAX    INTEGER {
        reset-counters(1)
                }
  ACCESS    write-only
  STATUS    mandatory
  DESCRIPTION
    "Reset all statistic counters."
  ::= { snGen 16 }

snEraseDataStoreFlash   OBJECT-TYPE
  SYNTAX    INTEGER {
        erase-datastore(1)
                }
  ACCESS    write-only
  STATUS    mandatory
  DESCRIPTION
    "Erase all configuration data and log table entries.
	In opposite to reset to factory defaults nothing is saved."
  ::= { snGen 17 }

snSetMemoryDefs   OBJECT-TYPE
  SYNTAX    INTEGER {
     set-memory-defaults(1),
     set-memory-defaults-complete(2)
  }
  ACCESS    read-write
  STATUS    mandatory
  DESCRIPTION
    "Restore memory defaults and restart."
  ::= { snGen 18 }

-- --------------------------------------------------------------
-- Email objects
-- This group includes parameters for the Email.
-- --------------------------------------------------------------
snEmailSMTPIpAddress   OBJECT-TYPE
    SYNTAX  IpAddress
    ACCESS  read-write
    STATUS  mandatory
    DESCRIPTION
        "IP address or host name of SMTP server."
      DEFVAL  {0}
    ::= { snGen 20 }

snEmailSMTPPort    OBJECT-TYPE
    SYNTAX  INTEGER (1..65535)
    ACCESS  read-write
    STATUS  mandatory
    DESCRIPTION
        "Number of TCP port to which the SMTP server will listen."
      DEFVAL  {25}
    ::= { snGen 21 }

snEmailEnable OBJECT-TYPE
    SYNTAX  INTEGER {
      enabled(1),
      disabled(2)
    }
    ACCESS  read-write
    STATUS  mandatory
    DESCRIPTION
          "E-mail functionality for sending a message when an event occurred."
    DEFVAL { disabled }
    ::= { snGen 22 }

snEmailAddress OBJECT-TYPE
    SYNTAX  DisplayString (SIZE (0..255))
    ACCESS  read-write
    STATUS  mandatory
    DESCRIPTION
        "E-mail address to which messages will be sent."
      DEFVAL  {"user@host.domain"}
    ::= { snGen 23 }

-- --------------------------------------------------------------
-- AD-TCPIP-MIB:
-- --------------------------------------------------------------
snIpAddress OBJECT-TYPE
    SYNTAX  IpAddress
    ACCESS  read-write
    STATUS  mandatory
    DESCRIPTION
        "IP address of the agent. Changes become valid after restart."
      DEFVAL  {0}
    ::= { snTcpip 2 }

snIpSubnetMask OBJECT-TYPE
    SYNTAX  IpAddress
    ACCESS  read-write
    STATUS  mandatory
    DESCRIPTION
        "IP subnet mask of the agent. Changes become valid after restart."
      DEFVAL  {0}
    ::= { snTcpip 3 }

snIpDefaultGateway OBJECT-TYPE
    SYNTAX  IpAddress
    ACCESS  read-write
    STATUS  mandatory
    DESCRIPTION
        "IP address of the default gateway. Changes become valid after restart."
      DEFVAL  {0}
      ::= { snTcpip 4 }

snBootP OBJECT-TYPE
      SYNTAX INTEGER {
           enabled(1),
           disabled(2)
       }
      ACCESS read-write
      STATUS    mandatory
      DESCRIPTION "Enable/Disable BOOTP. Changes become valid after restart."
      DEFVAL { enabled }
      ::= { snTcpip 5 }

snMacAddressBase OBJECT-TYPE
      SYNTAX MacAddress
      ACCESS read-only
      STATUS    mandatory
      DESCRIPTION "MAC address of the switch."
      ::= { snTcpip 10 }
-- --------------------------------------------------------------
-- SN-OSM-MIB:
-- --------------------------------------------------------------
snOsmFaultState OBJECT-TYPE
    SYNTAX  INTEGER {
      noFault(1),
      fault(2)
    }
    ACCESS  read-only
    STATUS  mandatory
    DESCRIPTION
          "Indicates OSM/ESM fault state
           (state of fault LED/signaling contact)."
    DEFVAL { noFault }
    ::= { snOsm 2 }

snOsmSignalledFaults OBJECT-TYPE
    SYNTAX  Counter 
    ACCESS  read-only
    STATUS  mandatory
    DESCRIPTION
          "Number of signalled faults."    
    DEFVAL { 0 }
    ::= { snOsm 3 }

snOsmFaultValue OBJECT-TYPE
    SYNTAX  OCTET STRING (SIZE(4))
--  SYNTAX      BITS {
--                      (fault = 0 - no fault )
--                      fault( 0) - FAULT_POWER
--                      fault( 1) - FAULT_LINKDOWN
--                      fault( 2) - FAULT_INTERROR
--                      fault( 3) - FAULT_STANDBY
--                      fault( 4) - FAULT_RM
--                      fault( 5) - FAULT_DIPSW_RM
--                      fault( 6) - FAULT_DIPSW_STBY
--                      fault( 7) - FAULT_NCM
--                      fault( 8) - FAULT_PARTPORT_1
--                      fault( 9) - FAULT_PARTPORT_2
--                      fault(10) - FAULT_PARTPORT_3
--                      fault(11) - FAULT_PARTPORT_4
--                      fault(12) - FAULT_PARTPORT_5
--                      fault(13) - FAULT_PARTPORT_6
--                      fault(14) - FAULT_PARTPORT_7
--                      fault(15) - FAULT_PARTPORT_8
--                      fault(16) - FAULT_OBSERVER
--                      fault(17) - FAULT_RING
--                      fault(18) - FAULT_FACTORY
--                   }
    ACCESS  read-write
    STATUS  mandatory
    DESCRIPTION
         "Fault value:        0  = no fault,
                          bit 0  = power,
                          bit 1  = linkdown,
                          bit 2  = internal error,
                          bit 3  = standby,
                          bit 4  = rm,
                          bit 5  = dip switch rm,
                          bit 6  = dip switch standby,
                          bit 7  = ncm,
                          bit 8  = partition port 1,
			  ...
                          bit 15 = partition port 8,
			  bit 16 = observer error,
			  bit 17 = non-recoverable ring error,
			  bit 18 = reset to factory defaults"
    ::= { snOsm 4 }

snOsmDigitalInputChange OBJECT-TYPE
    SYNTAX  OCTET STRING (SIZE(8))
    ACCESS  read-only
    STATUS  mandatory
    DESCRIPTION
          "Digital Input change"
    DEFVAL { "00000000" }
    ::= { snOsm 5 }

snOsmDigitalInputState OBJECT-TYPE
    SYNTAX  INTEGER 
    ACCESS  read-only
    STATUS  mandatory
    DESCRIPTION
          "Digital Input state"
    DEFVAL { 0 }
    ::= { snOsm 6 }


snOsmRmMode OBJECT-TYPE
    SYNTAX  INTEGER {
        rmOff(1),
        rmOn(2)
    }
    ACCESS  read-only
    STATUS  mandatory
    DESCRIPTION
          "RM mode."
    DEFVAL { rmOff}
    ::= { snOsm 11 }

snOsmRmState OBJECT-TYPE
    SYNTAX  INTEGER {
        rmPassive(1),
        rmActive(2)
    }
    ACCESS  read-only
    STATUS  mandatory
    DESCRIPTION
          "RM State."
    DEFVAL { rmPassive}
    ::= { snOsm 12 }

snOsmRmStateChanges OBJECT-TYPE
    SYNTAX  Counter
    ACCESS  read-only
    STATUS  mandatory
    DESCRIPTION
          "Number of changes to RM active state."
    DEFVAL { 0 }
    ::= { snOsm 13 }

snOsmRmObserverMode OBJECT-TYPE
    SYNTAX  INTEGER {
      enabled(1),
      disabled(2),
      restart(3),
      not-supported(10)
    }
    ACCESS  read-write
    STATUS  mandatory
    DESCRIPTION
          "Reserved for further use."
    DEFVAL { disabled }
    ::= { snOsm 14 }

snOsmStandbyMode OBJECT-TYPE
    SYNTAX  INTEGER {
        standbyOff(1),
        standbyOn(2),
        not-supported(10)
    }
    ACCESS  read-only
    STATUS  mandatory
    DESCRIPTION
          "Standby Mode."
    DEFVAL { standbyOff}
    ::= { snOsm 21 }

snOsmStandbyState OBJECT-TYPE
    SYNTAX  INTEGER {
        standbyPassive(1),
        standbyActive(2),
        not-supported(10)
    }
    ACCESS  read-only
    STATUS  mandatory
    DESCRIPTION
          "Standby State."
    DEFVAL { standbyPassive}
    ::= { snOsm 22 }
              
snOsmStandbyCableState OBJECT-TYPE
    SYNTAX  INTEGER {
        connected(1),
        disconnected(2),
        not-supported(10)
    }
    ACCESS  read-only
    STATUS  mandatory
    DESCRIPTION
          "Standby cable state."
    DEFVAL { connected }
    ::= { snOsm 24 }
                  
snOsmStandbyStateChanges OBJECT-TYPE
    SYNTAX  Counter
    ACCESS  read-only
    STATUS  mandatory
    DESCRIPTION
          "Number of changes to standby active state."
    DEFVAL { 0 }
    ::= { snOsm 25 }

snOsmPort7TestMac    OBJECT-TYPE
    SYNTAX  MacAddress
    ACCESS  read-only
    STATUS  mandatory
    DESCRIPTION 
        "MAC (source) address of test telegrams sent on port 7."
    ::= { snOsm 31 }

snOsmPort8TestMac    OBJECT-TYPE
    SYNTAX  MacAddress
    ACCESS  read-only
    STATUS  mandatory
    DESCRIPTION 
        "MAC (source) address of test telegrams sent on port 8."
    ::= { snOsm 32 }

snOsmMulticastTestMac OBJECT-TYPE
       SYNTAX  MacAddress
       ACCESS  read-only
       STATUS  mandatory
       DESCRIPTION
         "MAC multicast address used for redundancy functions."
       ::= { snOsm 33 }

snOsmMulticastLinkMac OBJECT-TYPE
       SYNTAX  MacAddress
       ACCESS  read-only
       STATUS  mandatory
       DESCRIPTION
         "MAC multicast address used for redundancy functions."
       ::= { snOsm 34 }

snOsmUnicastLinkMac OBJECT-TYPE
       SYNTAX  MacAddress
       ACCESS  read-only
       STATUS  mandatory
       DESCRIPTION
         "MAC unicast address used for redundancy functions."
       ::= { snOsm 35 }

snOsmMulticastSyncMac OBJECT-TYPE
       SYNTAX  MacAddress
       ACCESS  read-only
       STATUS  mandatory
       DESCRIPTION
         "MAC multicast address of time synchronisation packets."
       ::= { snOsm 36 }

snOsmMulticastFlowControlMac OBJECT-TYPE
       SYNTAX  MacAddress
       ACCESS  read-only
       STATUS  mandatory
       DESCRIPTION
         "MAC multicast address of flow control packets."
       ::= { snOsm 37 }

snOsmTestMaxDelay   OBJECT-TYPE
    SYNTAX  INTEGER (0..200)
    ACCESS  read-only
    STATUS  mandatory
    DESCRIPTION
          "Measured maximum delay of RM test telegrams."
    DEFVAL { 0 }
    ::= { snOsm 38 }

snOsmPowerSupply1State OBJECT-TYPE
    SYNTAX  INTEGER {
      inactive(1),
      active(2)
    }
    ACCESS  read-only
    STATUS  mandatory
    DESCRIPTION
          "State of power supply line 1."
    DEFVAL { inactive }
    ::= { snOsm 41 }

snOsmPowerSupply2State OBJECT-TYPE
    SYNTAX  INTEGER {
      inactive(1),
      active(2)
    }
    ACCESS  read-only
    STATUS  mandatory
    DESCRIPTION
          "State of power supply line 2."
    DEFVAL { inactive }
    ::= { snOsm 42 }

snOsmPowerSupply1Mask OBJECT-TYPE
    SYNTAX  INTEGER {
      checked(1),
      notChecked(2)
    }
    ACCESS  read-write
    STATUS  mandatory
    DESCRIPTION
          "Mask of power supply line 1."
    DEFVAL { notChecked }
    ::= { snOsm 43 }

snOsmPowerSupply2Mask OBJECT-TYPE
    SYNTAX  INTEGER {
      checked(1),
      notChecked(2)
    }
    ACCESS  read-write
    STATUS  mandatory
    DESCRIPTION
          "Mask of power supply line 2."
    DEFVAL { notChecked }
    ::= { snOsm 44 }

snOsmChangedPowerLine OBJECT-TYPE
    SYNTAX  INTEGER {
	  nochange(0),
      line1(1),
      line2(2)
    }
    ACCESS  read-write
    STATUS  mandatory
    DESCRIPTION
         "The power line where the last Power-Up or -Down occurred. 
          User can reset to initial value 0 at any time."
    DEFVAL { nochange }
    ::= { snOsm 45 }


snOsmResetCounters OBJECT-TYPE
    SYNTAX  INTEGER {
      reset(1)
    }
    ACCESS  write-only
    STATUS  mandatory
    DESCRIPTION
          "Reset all counters of OSM protocol software."
    ::= { snOsm 51 }


-- --------------------------------------------------------------
-- This group includes additional parameters for the ports.
-- --------------------------------------------------------------
snOsmPortTable OBJECT-TYPE
    SYNTAX  SEQUENCE OF SnOsmPortEntry
    ACCESS  not-accessible
    STATUS  mandatory
    DESCRIPTION
             "Table containing per-port objects in the form of private
              extensions of interface objects."
    ::= { snOsm 61 }

snOsmPortEntry OBJECT-TYPE
    SYNTAX  SnOsmPortEntry
    ACCESS  not-accessible
    STATUS  mandatory
    DESCRIPTION
            "Interface entry containing objects at the
             subnetwork layer and below for a particular
            interface."
    INDEX   { snOsmPortIndex }
    ::= { snOsmPortTable 1 }

SnOsmPortEntry ::=
    SEQUENCE {
        snOsmPortIndex
            INTEGER,
        snOsmPortFaultMaskState
            INTEGER,
        snOsmPortStandbyMaskState
            INTEGER,
        snOsmPortLockState
            INTEGER,
        snOsmPortPartitionState
            INTEGER,
        snOsmPortBackPressure
            INTEGER
    }

snOsmPortIndex OBJECT-TYPE
    SYNTAX  INTEGER
    ACCESS  not-accessible
    STATUS  mandatory
    DESCRIPTION
            "Unique number for each interface. The number is in the range
             1 to ifNumber. The number for each interface must remain
             constant at least from one re-initialization of the entity's
             network management system to the next re-initialization."
    ::= { snOsmPortEntry 1 }


snOsmPortFaultMaskState OBJECT-TYPE
    SYNTAX  INTEGER {
        checked(1),
        notChecked(2)
    }
    ACCESS  read-write
    STATUS  mandatory
    DESCRIPTION
        "Mask for checking link state of the port.
             If a link of a unmasked (checked) port is down then
             a fault will be generated."
    DEFVAL { notChecked }
    ::= { snOsmPortEntry 2 }

snOsmPortStandbyMaskState OBJECT-TYPE
    SYNTAX  INTEGER 
    {
        checked(1),
        notChecked(2)
    }    
    ACCESS  read-write
    STATUS  mandatory
    DESCRIPTION
	"Mask for standby ports." 
    ::= { snOsmPortEntry 3 }

snOsmPortLockState OBJECT-TYPE
    SYNTAX  INTEGER 
    {
        unlocked(1),        
        locked(2)
    }
    ACCESS  read-write
    STATUS  mandatory    
    DESCRIPTION     
        "Lock state of the port."
    DEFVAL { unlocked }
    ::= { snOsmPortEntry 4 }

snOsmPortPartitionState OBJECT-TYPE
    SYNTAX  INTEGER {
        noPartition(1),
        partition(2)
    }
    ACCESS  read-only
    STATUS  mandatory
    DESCRIPTION
        "Partition state of the port."
    DEFVAL { noPartition }

    ::= { snOsmPortEntry 5 }
    
snOsmPortBackPressure OBJECT-TYPE
    SYNTAX  INTEGER {
      enabled(1),
      disabled(2)
    }
    ACCESS  read-write
    STATUS  mandatory
    DESCRIPTION
        "Back pressure mode for the half-duplex port."
    ::= { snOsmPortEntry 6 }

-- --------------------------------------------------------------    
-- Traps for use by OSM
-- --------------------------------------------------------------
    snOsmRmActiveState TRAP-TYPE
        ENTERPRISE  snOsm
        DESCRIPTION
            "Redundancy manager entered active state."
    ::= 11

    snOsmRmPassiveState TRAP-TYPE
        ENTERPRISE  snOsm
        DESCRIPTION
            "Redundancy manager entered passive state."
    ::= 12

    snOsmStandbyActiveState TRAP-TYPE
        ENTERPRISE  snOsm
        DESCRIPTION
            "Device entered standby active state."
    ::= 21
         
    snOsmStandbyPassiveState TRAP-TYPE
        ENTERPRISE  snOsm
        DESCRIPTION
            "Device entered standby passive state."
    ::= 22

    snOsmPowerLineDown TRAP-TYPE
        ENTERPRISE  snOsm
        VARIABLES { snOsmChangedPowerLine }
        DESCRIPTION
            "Power down on line <L1/L2>."
    ::= 31

    snOsmPowerLineUp TRAP-TYPE
        ENTERPRISE  snOsm
        VARIABLES { snOsmChangedPowerLine }
        DESCRIPTION
            "Power up on line <L1/L2>."
    ::= 32

    snOsmFault TRAP-TYPE
        ENTERPRISE  snOsm
        VARIABLES { snOsmFaultValue }
        DESCRIPTION
            "Device entered fault state."
    ::= 41

    snOsmDigitalInput TRAP-TYPE
        ENTERPRISE  snOsm
        VARIABLES { snOsmDigitalInputChange, snOsmDigitalInputState }
        DESCRIPTION
            "Digital Input state changed."
    ::= 51

-- --------------------------------------------------------------
-- This group includes additional parameters for the event table.
-- --------------------------------------------------------------
snOsmEventTable OBJECT-TYPE
    SYNTAX  SEQUENCE OF SnOsmEventEntry
    ACCESS  not-accessible
    STATUS  mandatory
    DESCRIPTION
             "Event configuration table."
    ::= { snOsm 62 }

snOsmEventEntry OBJECT-TYPE
    SYNTAX  SnOsmEventEntry
    ACCESS  not-accessible
    STATUS  mandatory
    DESCRIPTION
            "Events table rows entries."
    INDEX   { snOsmEventIndex }
    ::= { snOsmEventTable 1 }

SnOsmEventEntry ::=
    SEQUENCE {
		snOsmEventIndex
			INTEGER,
        snOsmEventColdWarmStart
            INTEGER,
        snOsmEventLinkChange
            INTEGER,
        snOsmEventAuthenticationFailure
            INTEGER,
        snOsmEventRmonAlarm
            INTEGER,
        snOsmEventPowerChange
            INTEGER,
        snOsmEventRmStateChange
            INTEGER,
        snOsmEventStandbyStateChange
            INTEGER,
		snOsmEventFault
			INTEGER
    }

snOsmEventIndex OBJECT-TYPE
    SYNTAX  INTEGER {
        eMail(1),
        trap(2),
	logTabel(3)
    }
    ACCESS  read-only
    STATUS  mandatory
    DESCRIPTION
        "Index of columns : E-Mail = 1, Traps = 2, LogTable = 3."
    DEFVAL { eMail }
    ::= { snOsmEventEntry 1 }

snOsmEventColdWarmStart OBJECT-TYPE
    SYNTAX  INTEGER {
        checked(1),
        notChecked(2)
    }
    ACCESS  read-write
    STATUS  mandatory
    DESCRIPTION
        "Enables/Disables cold/warm start notification."
    DEFVAL { checked }
    ::= { snOsmEventEntry 2 }

snOsmEventLinkChange OBJECT-TYPE
    SYNTAX  INTEGER {
        checked(1),
        notChecked(2)
    }
    ACCESS  read-write
    STATUS  mandatory
    DESCRIPTION
        "Enables/Disables link change notification."
    DEFVAL { checked }
    ::= { snOsmEventEntry 3 }

snOsmEventAuthenticationFailure OBJECT-TYPE
    SYNTAX  INTEGER {
        checked(1),
        notChecked(2)
    }
    ACCESS  read-write
    STATUS  mandatory
    DESCRIPTION
        "Enables/Disables authentication failure notification."
    DEFVAL { checked }
    ::= { snOsmEventEntry 4 }

snOsmEventRmonAlarm OBJECT-TYPE
    SYNTAX  INTEGER {
        checked(1),
        notChecked(2)
    }
    ACCESS  read-write
    STATUS  mandatory
    DESCRIPTION
        "Enables/Disables RMon alarm notification."
    DEFVAL { checked }
    ::= { snOsmEventEntry 5 }

snOsmEventPowerChange OBJECT-TYPE
    SYNTAX  INTEGER {
        checked(1),
        notChecked(2)
    }
    ACCESS  read-write
    STATUS  mandatory
    DESCRIPTION
        "Enables/Disables power change notification."
    DEFVAL { checked }
    ::= { snOsmEventEntry 6 }

snOsmEventRmStateChange OBJECT-TYPE
    SYNTAX  INTEGER {
        checked(1),
        notChecked(2)
    }
    ACCESS  read-write
    STATUS  mandatory
    DESCRIPTION
        "Enables/Disables RM state change notification."
    DEFVAL { checked }
    ::= { snOsmEventEntry 7 }

snOsmEventStandbyStateChange OBJECT-TYPE
    SYNTAX  INTEGER {
        checked(1),
        notChecked(2)
    }
    ACCESS  read-write
    STATUS  mandatory
    DESCRIPTION
        "Enables/Disables standby state change notification."
    DEFVAL { checked }
    ::= { snOsmEventEntry 8 }

snOsmEventFault OBJECT-TYPE
    SYNTAX  INTEGER {
        checked(1),
        notChecked(2)
    }
    ACCESS  read-write
    STATUS  mandatory
    DESCRIPTION
        "Enables/Disables fault notification."
	DEFVAL { checked }
    ::= { snOsmEventEntry 9 }

-- --------------------------------------------------------------
-- This group includes additional parameters for the digitalIn table.
-- --------------------------------------------------------------
snOsmDigitalInEventTable OBJECT-TYPE
    SYNTAX  SEQUENCE OF SnOsmDigitalInEventEntry
    ACCESS  not-accessible
    STATUS  mandatory
    DESCRIPTION
             "Digital-In event configuration table."
    ::= { snOsm 63 }

snOsmDigitalInEventEntry OBJECT-TYPE
    SYNTAX  SnOsmDigitalInEventEntry
    ACCESS  not-accessible
    STATUS  mandatory
    DESCRIPTION
            "Digital-In events table rows entries."
    INDEX   { snOsmDigitalInIndex }
    ::= { snOsmDigitalInEventTable 1 }

SnOsmDigitalInEventEntry ::=
    SEQUENCE {
        snOsmDigitalInIndex
            INTEGER,
        snOsmDigitalInName
             DisplayString,
        snOsmDigitalInMailEvent
            INTEGER,
        snOsmDigitalInTrapEvent
            INTEGER,
        snOsmDigitalInLogEvent
            INTEGER,
        snOsmDigitalInState
            INTEGER
    }

snOsmDigitalInIndex OBJECT-TYPE
    SYNTAX  INTEGER
    ACCESS  read-only
    STATUS  mandatory
    DESCRIPTION
        "Index of Digital-In."
	DEFVAL { 0 }
    ::= { snOsmDigitalInEventEntry 1 }

snOsmDigitalInName OBJECT-TYPE
    SYNTAX  DisplayString  (SIZE(0..64))
    ACCESS  read-write
    STATUS  mandatory
    DESCRIPTION
        "Name of Digital-In."
	DEFVAL { "Digital XX" }
    ::= { snOsmDigitalInEventEntry 2 }

snOsmDigitalInMailEvent OBJECT-TYPE
    SYNTAX  INTEGER {
        checked(1),
        notChecked(2),
	notSupported(3)
    }
    ACCESS  read-write
    STATUS  mandatory
    DESCRIPTION
        "Enables/Disables Digital-In E-Mail notification."
    DEFVAL {checked}
    ::= { snOsmDigitalInEventEntry 3 }

snOsmDigitalInTrapEvent OBJECT-TYPE
    SYNTAX  INTEGER {
        checked(1),
        notChecked(2),
	notSupported(3)
    }
    ACCESS  read-write
    STATUS  mandatory
    DESCRIPTION
        "Enables/Disables Digital-In Trap notification."
    DEFVAL { checked }
    ::= { snOsmDigitalInEventEntry 4 }

snOsmDigitalInLogEvent OBJECT-TYPE
    SYNTAX  INTEGER {
        checked(1),
        notChecked(2),
	notSupported(3)
    }
    ACCESS  read-write
    STATUS  mandatory
    DESCRIPTION
        "Enables/Disables Digital-In LogTable notification."
    DEFVAL { checked }
    ::= { snOsmDigitalInEventEntry 5 }

snOsmDigitalInState OBJECT-TYPE
    SYNTAX  INTEGER {
        on(1),
        off(2),
	notSupported(3)
    }
    ACCESS  read-only
    STATUS  mandatory
    DESCRIPTION
        "State of the Digital-In."
    ::= { snOsmDigitalInEventEntry 6 }

-- --------------------------------------------------------------
-- AD-SN-MIB:
-- --------------------------------------------------------------
snConfigId OBJECT-TYPE
    SYNTAX  INTEGER {
      osmItp62(0),
      osmItp53(1),
      osmTp62(2),
      esmItp80(3),
      esmTp80(4),
      osmItpLd62(5),
      osmTpLd62(6),
      osmBC08(7),
      osmTp22(8),
      esmTp40(9),
      osmTp62-Advanced(10),
      esmItp80-Advanced(11),
      esmTp80-Advanced(12),
      osmItpLd62-Advanced(13),
      osmItp62-Advanced(14),
      osmItp53-Advanced(15),
      osmTp53(16)
    }
    ACCESS  read-only
    STATUS  mandatory
    DESCRIPTION
		"OSM/ESM hardware type."          
    ::= { snOsm 100 }

snSwitchFlowControl OBJECT-TYPE
    SYNTAX  INTEGER {
      enabled(1),
      disabled(2)
    }
    ACCESS  read-write
    STATUS  mandatory
    DESCRIPTION   
          "Enable/Disable flow control functionality." 
    DEFVAL { disabled }
    ::= { snOsm 101 }

snSwitchSnifferSrc OBJECT-TYPE
    SYNTAX  INTEGER
    ACCESS  read-write
    STATUS  mandatory
    DESCRIPTION   
         "Source port for traffic mirroring."
    DEFVAL { 2 }
    ::= { snOsm 102 }

snSwitchSnifferDest OBJECT-TYPE
    SYNTAX  INTEGER
    ACCESS  read-write
    STATUS  mandatory
    DESCRIPTION   
         "Destination port for traffic mirroring."
    DEFVAL { 1 }
    ::= { snOsm 103 }

snSwitchSnifferEnable OBJECT-TYPE
    SYNTAX  INTEGER {
      enabled(1),
      disabled(2)
    }
    ACCESS  read-write
    STATUS  mandatory
    DESCRIPTION   
          "Enable/Disable mirroring functionality."
    DEFVAL { disabled }
    ::= { snOsm 104 }


snSwitchAgingEnable    OBJECT-TYPE
      SYNTAX  INTEGER {
         enabled(1),
         disabled(2)
         }
      ACCESS  read-write
      STATUS  mandatory
      DESCRIPTION
          "Enable/Disable auto-aging functionality of the learning table."
    DEFVAL  {enabled}
    ::= { snOsm 105 }


snSwitchRmonMode OBJECT-TYPE
    SYNTAX  INTEGER {
      enabled(1),
      disabled(2),
      not-supported(10)
    }
    ACCESS  read-write
    STATUS  mandatory
    DESCRIPTION
          "Enable/Disable RMon functionality (statistics, history, alarm, events)."
    DEFVAL { disabled }
    ::= { snOsm 106 }

snSwitchFdbImagePollTime OBJECT-TYPE
    SYNTAX  INTEGER (10..600)
    ACCESS  read-write
    STATUS  mandatory
    DESCRIPTION
          "Polling time for update of learning table image."
    DEFVAL { 40 }
    ::= { snOsm 107 }

snSwitchLearningTableEntries OBJECT-TYPE
    SYNTAX  INTEGER 
    ACCESS  read-only
    STATUS  mandatory
    DESCRIPTION
          "Number of entries in learning table image."
    DEFVAL { 0 }
    ::= { snOsm 108 }

snSwitchTimeToNextDataStore OBJECT-TYPE
    SYNTAX  INTEGER 
    ACCESS  read-only
    STATUS  mandatory
    DESCRIPTION
          "Time in seconds, when the next saving of configuration data and log entries takes place."
    DEFVAL { 0 }
    ::= { snOsm 109 }

snSwitchFlushDataStore OBJECT-TYPE
    SYNTAX  INTEGER {
      flush(1)
    }
    ACCESS  write-only
    STATUS  mandatory
    DESCRIPTION
          "Force direct saving of configuration data and log entries."
    ::= { snOsm 110 }

-- -------------------------------------------------------------
-- LastObject in SN-PRIVATE-MIB
-- -------------------------------------------------------------
snLastObject     OBJECT-TYPE
        SYNTAX  INTEGER {
                last-object(1)
        }
        ACCESS  read-only
        STATUS  mandatory
        DESCRIPTION
                "This object is defined as a dummy object. The object
                 is used to indicate that no other objects can appear
                 after it in this private MIB.
                 The only purpose of this object is for MIB browsers
                 that need a valid object at the end of a private MIB."
        DEFVAL { last-object }
        ::= { iSwitchMib 999 }


END
