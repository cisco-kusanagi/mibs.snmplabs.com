-- $Id: ir-alarm-mib.mib,v 1.1 2002/06/27 15:49:08 sse Exp $
                    MRV-IN-REACH-ALARM-EXTENSION-MIB DEFINITIONS ::= BEGIN
            
                    IMPORTS
                           sysLocation
                                    FROM RFC1213-MIB
			   TRAP-TYPE
                                    FROM RFC-1215
                           mrvInReachProductDivision
                               FROM MRV-IN-REACH-PRODUCT-DIVISION-MIB
			basicAlarmMasterInputValue,
			basicAlarmMasterInputName,
		        basicAlarmMasterInputPort,
        	        basicAlarmMasterInputStatus,
        		basicAlarmMasterInputSlot,
			basicAlarmMasterInputPoint,
        	        basicAlarmMasterInputZone,
                	basicAlarmMasterInputRelatedEquipment,
	                basicAlarmMasterInputSiteId,
        	        basicAlarmMasterInputManufacturer,
                	basicAlarmMasterInputModel
                                     FROM MRV-IN-REACH-CHARACTER-MIB;



	     xAlarm          OBJECT IDENTIFIER ::= { mrvInReachProductDivision 49 }


	     -- This is a MIB module for all MRV In-Reach systems that
	     -- use high densitity alarm input systems, such as the 7104.
             -- Refer to the MRV-IN-REACH-CHARACTER-MIB to manage low density
             -- alarm inputs.

	     -- Copyright 2002 MRV Communications, Inc. All Rights Reserved.
	     -- Reproduction of this document is authorized on
	     -- condition that this copyright notice is included.
	     -- This MIB document embodies MRV Communications, Inc.'s 
	     -- proprietary intellectual property.  MRV Communications, Inc.
	     -- retains all title and ownership in this MIB, including any
	     -- revisions.
	     --
	     -- It is MRV Communications, Inc.'s intent to encourage the
	     -- widespread use of this MIB in connection with the management of
	     -- MRV Communications, Inc. products. MRV Communications,
	     -- Inc. grants vendors,end-users, and other interested parties a
	     -- non-exclusive license to use this MIB in connection with the
	     -- management of MRV Communications, Inc. products.
	     --
	     -- This MIB document is supplied "AS IS," and MRV 
	     -- Communications, Inc. makes no warranty, either express or
	     -- implied, as to the use operation, condition, or performance of
	     -- the MIB.





--         The following alarm input traps are used with the high density
--         alarm manager products, such as the 7104. The traps below replace
--         the alarmMasterInputStateChanged trap 41 for InReach agents running 
--         IRV3-1 software and above.  

--         The alarm trap numbers have the format 300xx or 400xx, where xx 
--         represents the alarm input index. A leading '3' represents the alarm
--         condition, and a leading '4' represents the normal condition.

           alarmInputHighDensity0001Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 1 from a high density unit
                transitions to the alarm state."
           ::= 30001

           alarmInputHighDensity0001Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 1 from a high density unit 
                transitions to the normal state."
           ::= 40001

           alarmInputHighDensity0002Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 2 from a high density unit
                transitions to the alarm state."
           ::= 30002

           alarmInputHighDensity0002Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 2 from a high density unit 
                transitions to the normal state."
           ::= 40002

           alarmInputHighDensity0003Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 3 from a high density unit
                transitions to the alarm state."
           ::= 30003

           alarmInputHighDensity0003Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 3 from a high density unit 
                transitions to the normal state."
           ::= 40003

           alarmInputHighDensity0004Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 4 from a high density unit
                transitions to the alarm state."
           ::= 30004

           alarmInputHighDensity0004Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 4 from a high density unit 
                transitions to the normal state."
           ::= 40004

           alarmInputHighDensity0005Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 5 from a high density unit
                transitions to the alarm state."
           ::= 30005

           alarmInputHighDensity0005Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 5 from a high density unit 
                transitions to the normal state."
           ::= 40005

           alarmInputHighDensity0006Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 6 from a high density unit
                transitions to the alarm state."
           ::= 30006

           alarmInputHighDensity0006Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 6 from a high density unit 
                transitions to the normal state."
           ::= 40006

           alarmInputHighDensity0007Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 7 from a high density unit
                transitions to the alarm state."
           ::= 30007

           alarmInputHighDensity0007Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 7 from a high density unit 
                transitions to the normal state."
           ::= 40007

           alarmInputHighDensity0008Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 8 from a high density unit
                transitions to the alarm state."
           ::= 30008

           alarmInputHighDensity0008Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 8 from a high density unit 
                transitions to the normal state."
           ::= 40008

           alarmInputHighDensity0009Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 9 from a high density unit
                transitions to the alarm state."
           ::= 30009

           alarmInputHighDensity0009Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 9 from a high density unit 
                transitions to the normal state."
           ::= 40009

           alarmInputHighDensity0010Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 10 from a high density unit
                transitions to the alarm state."
           ::= 30010

           alarmInputHighDensity0010Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 10 from a high density unit 
                transitions to the normal state."
           ::= 40010

           alarmInputHighDensity0011Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 11 from a high density unit
                transitions to the alarm state."
           ::= 30011

           alarmInputHighDensity0011Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 11 from a high density unit 
                transitions to the normal state."
           ::= 40011

           alarmInputHighDensity0012Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 12 from a high density unit
                transitions to the alarm state."
           ::= 30012

           alarmInputHighDensity0012Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 12 from a high density unit 
                transitions to the normal state."
           ::= 40012

           alarmInputHighDensity0013Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 13 from a high density unit
                transitions to the alarm state."
           ::= 30013

           alarmInputHighDensity0013Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 13 from a high density unit 
                transitions to the normal state."
           ::= 40013

           alarmInputHighDensity0014Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 14 from a high density unit
                transitions to the alarm state."
           ::= 30014

           alarmInputHighDensity0014Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 14 from a high density unit 
                transitions to the normal state."
           ::= 40014

           alarmInputHighDensity0015Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 15 from a high density unit
                transitions to the alarm state."
           ::= 30015

           alarmInputHighDensity0015Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 15 from a high density unit 
                transitions to the normal state."
           ::= 40015

           alarmInputHighDensity0016Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 16 from a high density unit
                transitions to the alarm state."
           ::= 30016

           alarmInputHighDensity0016Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 16 from a high density unit 
                transitions to the normal state."
           ::= 40016

           alarmInputHighDensity0017Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 17 from a high density unit
                transitions to the alarm state."
           ::= 30017

           alarmInputHighDensity0017Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 17 from a high density unit 
                transitions to the normal state."
           ::= 40017

           alarmInputHighDensity0018Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 18 from a high density unit
                transitions to the alarm state."
           ::= 30018

           alarmInputHighDensity0018Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 18 from a high density unit 
                transitions to the normal state."
           ::= 40018

           alarmInputHighDensity0019Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 19 from a high density unit
                transitions to the alarm state."
           ::= 30019

           alarmInputHighDensity0019Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 19 from a high density unit 
                transitions to the normal state."
           ::= 40019

           alarmInputHighDensity0020Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 20 from a high density unit
                transitions to the alarm state."
           ::= 30020

           alarmInputHighDensity0020Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 20 from a high density unit 
                transitions to the normal state."
           ::= 40020

           alarmInputHighDensity0021Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 21 from a high density unit
                transitions to the alarm state."
           ::= 30021

           alarmInputHighDensity0021Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 21 from a high density unit 
                transitions to the normal state."
           ::= 40021

           alarmInputHighDensity0022Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 22 from a high density unit
                transitions to the alarm state."
           ::= 30022

           alarmInputHighDensity0022Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 22 from a high density unit 
                transitions to the normal state."
           ::= 40022

           alarmInputHighDensity0023Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 23 from a high density unit
                transitions to the alarm state."
           ::= 30023

           alarmInputHighDensity0023Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 23 from a high density unit 
                transitions to the normal state."
           ::= 40023

           alarmInputHighDensity0024Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 24 from a high density unit
                transitions to the alarm state."
           ::= 30024

           alarmInputHighDensity0024Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 24 from a high density unit 
                transitions to the normal state."
           ::= 40024

           alarmInputHighDensity0025Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 25 from a high density unit
                transitions to the alarm state."
           ::= 30025

           alarmInputHighDensity0025Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 25 from a high density unit 
                transitions to the normal state."
           ::= 40025

           alarmInputHighDensity0026Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 26 from a high density unit
                transitions to the alarm state."
           ::= 30026

           alarmInputHighDensity0026Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 26 from a high density unit 
                transitions to the normal state."
           ::= 40026

           alarmInputHighDensity0027Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 27 from a high density unit
                transitions to the alarm state."
           ::= 30027

           alarmInputHighDensity0027Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 27 from a high density unit 
                transitions to the normal state."
           ::= 40027

           alarmInputHighDensity0028Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 28 from a high density unit
                transitions to the alarm state."
           ::= 30028

           alarmInputHighDensity0028Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 28 from a high density unit 
                transitions to the normal state."
           ::= 40028

           alarmInputHighDensity0029Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 29 from a high density unit
                transitions to the alarm state."
           ::= 30029

           alarmInputHighDensity0029Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 29 from a high density unit 
                transitions to the normal state."
           ::= 40029

           alarmInputHighDensity0030Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 30 from a high density unit
                transitions to the alarm state."
           ::= 30030

           alarmInputHighDensity0030Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 30 from a high density unit 
                transitions to the normal state."
           ::= 40030

           alarmInputHighDensity0031Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 31 from a high density unit
                transitions to the alarm state."
           ::= 30031

           alarmInputHighDensity0031Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 31 from a high density unit 
                transitions to the normal state."
           ::= 40031

           alarmInputHighDensity0032Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 32 from a high density unit
                transitions to the alarm state."
           ::= 30032

           alarmInputHighDensity0032Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 32 from a high density unit 
                transitions to the normal state."
           ::= 40032

           alarmInputHighDensity0033Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 33 from a high density unit
                transitions to the alarm state."
           ::= 30033

           alarmInputHighDensity0033Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 33 from a high density unit 
                transitions to the normal state."
           ::= 40033

           alarmInputHighDensity0034Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 34 from a high density unit
                transitions to the alarm state."
           ::= 30034

           alarmInputHighDensity0034Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 34 from a high density unit 
                transitions to the normal state."
           ::= 40034

           alarmInputHighDensity0035Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 35 from a high density unit
                transitions to the alarm state."
           ::= 30035

           alarmInputHighDensity0035Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 35 from a high density unit 
                transitions to the normal state."
           ::= 40035

           alarmInputHighDensity0036Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 36 from a high density unit
                transitions to the alarm state."
           ::= 30036

           alarmInputHighDensity0036Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 36 from a high density unit 
                transitions to the normal state."
           ::= 40036

           alarmInputHighDensity0037Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 37 from a high density unit
                transitions to the alarm state."
           ::= 30037

           alarmInputHighDensity0037Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 37 from a high density unit 
                transitions to the normal state."
           ::= 40037

           alarmInputHighDensity0038Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 38 from a high density unit
                transitions to the alarm state."
           ::= 30038

           alarmInputHighDensity0038Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 38 from a high density unit 
                transitions to the normal state."
           ::= 40038

           alarmInputHighDensity0039Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 39 from a high density unit
                transitions to the alarm state."
           ::= 30039

           alarmInputHighDensity0039Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 39 from a high density unit 
                transitions to the normal state."
           ::= 40039

           alarmInputHighDensity0040Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 40 from a high density unit
                transitions to the alarm state."
           ::= 30040

           alarmInputHighDensity0040Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 40 from a high density unit 
                transitions to the normal state."
           ::= 40040

           alarmInputHighDensity0041Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 41 from a high density unit
                transitions to the alarm state."
           ::= 30041

           alarmInputHighDensity0041Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 41 from a high density unit 
                transitions to the normal state."
           ::= 40041

           alarmInputHighDensity0042Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 42 from a high density unit
                transitions to the alarm state."
           ::= 30042

           alarmInputHighDensity0042Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 42 from a high density unit 
                transitions to the normal state."
           ::= 40042

           alarmInputHighDensity0043Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 43 from a high density unit
                transitions to the alarm state."
           ::= 30043

           alarmInputHighDensity0043Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 43 from a high density unit 
                transitions to the normal state."
           ::= 40043

           alarmInputHighDensity0044Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 44 from a high density unit
                transitions to the alarm state."
           ::= 30044

           alarmInputHighDensity0044Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 44 from a high density unit 
                transitions to the normal state."
           ::= 40044

           alarmInputHighDensity0045Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 45 from a high density unit
                transitions to the alarm state."
           ::= 30045

           alarmInputHighDensity0045Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 45 from a high density unit 
                transitions to the normal state."
           ::= 40045

           alarmInputHighDensity0046Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 46 from a high density unit
                transitions to the alarm state."
           ::= 30046

           alarmInputHighDensity0046Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 46 from a high density unit 
                transitions to the normal state."
           ::= 40046

           alarmInputHighDensity0047Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 47 from a high density unit
                transitions to the alarm state."
           ::= 30047

           alarmInputHighDensity0047Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 47 from a high density unit 
                transitions to the normal state."
           ::= 40047

           alarmInputHighDensity0048Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 48 from a high density unit
                transitions to the alarm state."
           ::= 30048

           alarmInputHighDensity0048Normal TRAP-TYPE
           ENTERPRISE mrvInReachProductDivision
           VARIABLES {
		basicAlarmMasterInputValue,
		basicAlarmMasterInputName,
		sysLocation,
	        basicAlarmMasterInputPort,
                basicAlarmMasterInputStatus,
                basicAlarmMasterInputZone,
                basicAlarmMasterInputRelatedEquipment,
                basicAlarmMasterInputSiteId,
                basicAlarmMasterInputManufacturer,
                basicAlarmMasterInputModel
		 }
           DESCRIPTION
               "Generated when alarm point 48 from a high density unit 
                transitions to the normal state."
           ::= 40048

           alarmInputHighDensity0049Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 49 from a high density unit
                transitions to the alarm state."
           ::= 30049

           alarmInputHighDensity0049Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 49 from a high density unit 
                transitions to the normal state."
           ::= 40049

           alarmInputHighDensity0050Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 50 from a high density unit
                transitions to the alarm state."
           ::= 30050

           alarmInputHighDensity0050Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 50 from a high density unit 
                transitions to the normal state."
           ::= 40050
           alarmInputHighDensity0051Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 51 from a high density unit
                transitions to the alarm state."
           ::= 30051

           alarmInputHighDensity0051Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 51 from a high density unit 
                transitions to the normal state."
           ::= 40051

           alarmInputHighDensity0052Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 52 from a high density unit
                transitions to the alarm state."
           ::= 30052

           alarmInputHighDensity0052Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 52 from a high density unit 
                transitions to the normal state."
           ::= 40052

           alarmInputHighDensity0053Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 53 from a high density unit
                transitions to the alarm state."
           ::= 30053

           alarmInputHighDensity0053Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 53 from a high density unit 
                transitions to the normal state."
           ::= 40053

           alarmInputHighDensity0054Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 54 from a high density unit
                transitions to the alarm state."
           ::= 30054

           alarmInputHighDensity0054Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 54 from a high density unit 
                transitions to the normal state."
           ::= 40054

           alarmInputHighDensity0055Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 55 from a high density unit
                transitions to the alarm state."
           ::= 30055

           alarmInputHighDensity0055Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 55 from a high density unit 
                transitions to the normal state."
           ::= 40055

           alarmInputHighDensity0056Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 56 from a high density unit
                transitions to the alarm state."
           ::= 30056

           alarmInputHighDensity0056Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 56 from a high density unit 
                transitions to the normal state."
           ::= 40056

           alarmInputHighDensity0057Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 57 from a high density unit
                transitions to the alarm state."
           ::= 30057

           alarmInputHighDensity0057Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 57 from a high density unit 
                transitions to the normal state."
           ::= 40057

           alarmInputHighDensity0058Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 58 from a high density unit
                transitions to the alarm state."
           ::= 30058

           alarmInputHighDensity0058Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 58 from a high density unit 
                transitions to the normal state."
           ::= 40058

           alarmInputHighDensity0059Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 59 from a high density unit
                transitions to the alarm state."
           ::= 30059

           alarmInputHighDensity0059Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 59 from a high density unit 
                transitions to the normal state."
           ::= 40059

           alarmInputHighDensity0060Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 60 from a high density unit
                transitions to the alarm state."
           ::= 30060

           alarmInputHighDensity0060Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 60 from a high density unit 
                transitions to the normal state."
           ::= 40060
           alarmInputHighDensity0061Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 61 from a high density unit
                transitions to the alarm state."
           ::= 30061

           alarmInputHighDensity0061Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 61 from a high density unit 
                transitions to the normal state."
           ::= 40061

           alarmInputHighDensity0062Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 62 from a high density unit
                transitions to the alarm state."
           ::= 30062

           alarmInputHighDensity0062Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 62 from a high density unit 
                transitions to the normal state."
           ::= 40062

           alarmInputHighDensity0063Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 63 from a high density unit
                transitions to the alarm state."
           ::= 30063

           alarmInputHighDensity0063Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 63 from a high density unit 
                transitions to the normal state."
           ::= 40063

           alarmInputHighDensity0064Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 64 from a high density unit
                transitions to the alarm state."
           ::= 30064

           alarmInputHighDensity0064Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 64 from a high density unit 
                transitions to the normal state."
           ::= 40064

           alarmInputHighDensity0065Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 65 from a high density unit
                transitions to the alarm state."
           ::= 30065

           alarmInputHighDensity0065Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 65 from a high density unit 
                transitions to the normal state."
           ::= 40065

           alarmInputHighDensity0066Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 66 from a high density unit
                transitions to the alarm state."
           ::= 30066

           alarmInputHighDensity0066Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 66 from a high density unit 
                transitions to the normal state."
           ::= 40066

           alarmInputHighDensity0067Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 67 from a high density unit
                transitions to the alarm state."
           ::= 30067

           alarmInputHighDensity0067Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 67 from a high density unit 
                transitions to the normal state."
           ::= 40067

           alarmInputHighDensity0068Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 68 from a high density unit
                transitions to the alarm state."
           ::= 30068

           alarmInputHighDensity0068Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 68 from a high density unit 
                transitions to the normal state."
           ::= 40068

           alarmInputHighDensity0069Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 69 from a high density unit
                transitions to the alarm state."
           ::= 30069

           alarmInputHighDensity0069Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 69 from a high density unit 
                transitions to the normal state."
           ::= 40069

           alarmInputHighDensity0070Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 70 from a high density unit
                transitions to the alarm state."
           ::= 30070

           alarmInputHighDensity0070Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 70 from a high density unit 
                transitions to the normal state."
           ::= 40070

           alarmInputHighDensity0071Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 71 from a high density unit
                transitions to the alarm state."
           ::= 30071

           alarmInputHighDensity0071Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 71 from a high density unit 
                transitions to the normal state."
           ::= 40071

           alarmInputHighDensity0072Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 72 from a high density unit
                transitions to the alarm state."
           ::= 30072

           alarmInputHighDensity0072Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 72 from a high density unit 
                transitions to the normal state."
           ::= 40072

           alarmInputHighDensity0073Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 73 from a high density unit
                transitions to the alarm state."
           ::= 30073

           alarmInputHighDensity0073Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 73 from a high density unit 
                transitions to the normal state."
           ::= 40073

           alarmInputHighDensity0074Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 74 from a high density unit
                transitions to the alarm state."
           ::= 30074

           alarmInputHighDensity0074Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 74 from a high density unit 
                transitions to the normal state."
           ::= 40074

           alarmInputHighDensity0075Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 75 from a high density unit
                transitions to the alarm state."
           ::= 30075

           alarmInputHighDensity0075Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 75 from a high density unit 
                transitions to the normal state."
           ::= 40075

           alarmInputHighDensity0076Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 76 from a high density unit
                transitions to the alarm state."
           ::= 30076

           alarmInputHighDensity0076Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 76 from a high density unit 
                transitions to the normal state."
           ::= 40076

           alarmInputHighDensity0077Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 77 from a high density unit
                transitions to the alarm state."
           ::= 30077

           alarmInputHighDensity0077Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 77 from a high density unit 
                transitions to the normal state."
           ::= 40077

           alarmInputHighDensity0078Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 78 from a high density unit
                transitions to the alarm state."
           ::= 30078

           alarmInputHighDensity0078Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 78 from a high density unit 
                transitions to the normal state."
           ::= 40078

           alarmInputHighDensity0079Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 79 from a high density unit
                transitions to the alarm state."
           ::= 30079

           alarmInputHighDensity0079Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 79 from a high density unit 
                transitions to the normal state."
           ::= 40079

           alarmInputHighDensity0080Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 80 from a high density unit
                transitions to the alarm state."
           ::= 30080

           alarmInputHighDensity0080Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 80 from a high density unit 
                transitions to the normal state."
           ::= 40080

           alarmInputHighDensity0081Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 81 from a high density unit
                transitions to the alarm state."
           ::= 30081

           alarmInputHighDensity0081Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 81 from a high density unit 
                transitions to the normal state."
           ::= 40081

           alarmInputHighDensity0082Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 82 from a high density unit
                transitions to the alarm state."
           ::= 30082

           alarmInputHighDensity0082Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 82 from a high density unit 
                transitions to the normal state."
           ::= 40082

           alarmInputHighDensity0083Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 83 from a high density unit
                transitions to the alarm state."
           ::= 30083

           alarmInputHighDensity0083Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 83 from a high density unit 
                transitions to the normal state."
           ::= 40083

           alarmInputHighDensity0084Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 84 from a high density unit
                transitions to the alarm state."
           ::= 30084

           alarmInputHighDensity0084Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 84 from a high density unit 
                transitions to the normal state."
           ::= 40084

           alarmInputHighDensity0085Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 85 from a high density unit
                transitions to the alarm state."
           ::= 30085

           alarmInputHighDensity0085Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 85 from a high density unit 
                transitions to the normal state."
           ::= 40085

           alarmInputHighDensity0086Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 86 from a high density unit
                transitions to the alarm state."
           ::= 30086

           alarmInputHighDensity0086Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 86 from a high density unit 
                transitions to the normal state."
           ::= 40086

           alarmInputHighDensity0087Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 87 from a high density unit
                transitions to the alarm state."
           ::= 30087

           alarmInputHighDensity0087Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 87 from a high density unit 
                transitions to the normal state."
           ::= 40087

           alarmInputHighDensity0088Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 88 from a high density unit
                transitions to the alarm state."
           ::= 30088

           alarmInputHighDensity0088Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 88 from a high density unit 
                transitions to the normal state."
           ::= 40088

           alarmInputHighDensity0089Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 89 from a high density unit
                transitions to the alarm state."
           ::= 30089

           alarmInputHighDensity0089Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 89 from a high density unit 
                transitions to the normal state."
           ::= 40089

           alarmInputHighDensity0090Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 90 from a high density unit
                transitions to the alarm state."
           ::= 30090

           alarmInputHighDensity0090Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 90 from a high density unit 
                transitions to the normal state."
           ::= 40090

           alarmInputHighDensity0091Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 91 from a high density unit
                transitions to the alarm state."
           ::= 30091

           alarmInputHighDensity0091Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 91 from a high density unit 
                transitions to the normal state."
           ::= 40091

           alarmInputHighDensity0092Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 92 from a high density unit
                transitions to the alarm state."
           ::= 30092

           alarmInputHighDensity0092Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 92 from a high density unit 
                transitions to the normal state."
           ::= 40092

           alarmInputHighDensity0093Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 93 from a high density unit
                transitions to the alarm state."
           ::= 30093

           alarmInputHighDensity0093Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 93 from a high density unit 
                transitions to the normal state."
           ::= 40093

           alarmInputHighDensity0094Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 94 from a high density unit
                transitions to the alarm state."
           ::= 30094

           alarmInputHighDensity0094Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 94 from a high density unit 
                transitions to the normal state."
           ::= 40094

           alarmInputHighDensity0095Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 95 from a high density unit
                transitions to the alarm state."
           ::= 30095

           alarmInputHighDensity0095Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 95 from a high density unit 
                transitions to the normal state."
           ::= 40095

           alarmInputHighDensity0096Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 96 from a high density unit
                transitions to the alarm state."
           ::= 30096

           alarmInputHighDensity0096Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 96 from a high density unit 
                transitions to the normal state."
           ::= 40096

           alarmInputHighDensity0097Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 97 from a high density unit
                transitions to the alarm state."
           ::= 30097

           alarmInputHighDensity0097Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 97 from a high density unit 
                transitions to the normal state."
           ::= 40097

           alarmInputHighDensity0098Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 98 from a high density unit
                transitions to the alarm state."
           ::= 30098

           alarmInputHighDensity0098Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 98 from a high density unit 
                transitions to the normal state."
           ::= 40098

           alarmInputHighDensity0099Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 99 from a high density unit
                transitions to the alarm state."
           ::= 30099

           alarmInputHighDensity0099Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 99 from a high density unit 
                transitions to the normal state."
           ::= 40099

           alarmInputHighDensity0100Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 100 from a high density unit
                transitions to the alarm state."
           ::= 30100

           alarmInputHighDensity0100Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 100 from a high density unit 
                transitions to the normal state."
           ::= 40100

           alarmInputHighDensity0101Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 101 from a high density unit
                transitions to the alarm state."
           ::= 30101

           alarmInputHighDensity0101Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 101 from a high density unit 
                transitions to the normal state."
           ::= 40101

           alarmInputHighDensity0102Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 102 from a high density unit
                transitions to the alarm state."
           ::= 30102

           alarmInputHighDensity0102Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 102 from a high density unit 
                transitions to the normal state."
           ::= 40102

           alarmInputHighDensity0103Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 103 from a high density unit
                transitions to the alarm state."
           ::= 30103

           alarmInputHighDensity0103Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 103 from a high density unit 
                transitions to the normal state."
           ::= 40103

           alarmInputHighDensity0104Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 104 from a high density unit
                transitions to the alarm state."
           ::= 30104

           alarmInputHighDensity0104Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 104 from a high density unit 
                transitions to the normal state."
           ::= 40104

           alarmInputHighDensity0105Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 105 from a high density unit
                transitions to the alarm state."
           ::= 30105

           alarmInputHighDensity0105Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 105 from a high density unit 
                transitions to the normal state."
           ::= 40105

           alarmInputHighDensity0106Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 106 from a high density unit
                transitions to the alarm state."
           ::= 30106

           alarmInputHighDensity0106Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 106 from a high density unit 
                transitions to the normal state."
           ::= 40106

           alarmInputHighDensity0107Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 107 from a high density unit
                transitions to the alarm state."
           ::= 30107

           alarmInputHighDensity0107Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 107 from a high density unit 
                transitions to the normal state."
           ::= 40107

           alarmInputHighDensity0108Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 108 from a high density unit
                transitions to the alarm state."
           ::= 30108

           alarmInputHighDensity0108Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 108 from a high density unit 
                transitions to the normal state."
           ::= 40108

           alarmInputHighDensity0109Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 109 from a high density unit
                transitions to the alarm state."
           ::= 30109

           alarmInputHighDensity0109Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 109 from a high density unit 
                transitions to the normal state."
           ::= 40109

           alarmInputHighDensity0110Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 110 from a high density unit
                transitions to the alarm state."
           ::= 30110

           alarmInputHighDensity0110Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 110 from a high density unit 
                transitions to the normal state."
           ::= 40110

           alarmInputHighDensity0111Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 111 from a high density unit
                transitions to the alarm state."
           ::= 30111

           alarmInputHighDensity0111Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 111 from a high density unit 
                transitions to the normal state."
           ::= 40111

           alarmInputHighDensity0112Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 112 from a high density unit
                transitions to the alarm state."
           ::= 30112

           alarmInputHighDensity0112Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 112 from a high density unit 
                transitions to the normal state."
           ::= 40112

           alarmInputHighDensity0113Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 113 from a high density unit
                transitions to the alarm state."
           ::= 30113

           alarmInputHighDensity0113Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 113 from a high density unit 
                transitions to the normal state."
           ::= 40113

           alarmInputHighDensity0114Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 114 from a high density unit
                transitions to the alarm state."
           ::= 30114

           alarmInputHighDensity0114Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 114 from a high density unit 
                transitions to the normal state."
           ::= 40114

           alarmInputHighDensity0115Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 115 from a high density unit
                transitions to the alarm state."
           ::= 30115

           alarmInputHighDensity0115Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 115 from a high density unit 
                transitions to the normal state."
           ::= 40115

           alarmInputHighDensity0116Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 116 from a high density unit
                transitions to the alarm state."
           ::= 30116

           alarmInputHighDensity0116Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 116 from a high density unit 
                transitions to the normal state."
           ::= 40116

           alarmInputHighDensity0117Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 117 from a high density unit
                transitions to the alarm state."
           ::= 30117

           alarmInputHighDensity0117Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 117 from a high density unit 
                transitions to the normal state."
           ::= 40117

           alarmInputHighDensity0118Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 118 from a high density unit
                transitions to the alarm state."
           ::= 30118

           alarmInputHighDensity0118Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 118 from a high density unit 
                transitions to the normal state."
           ::= 40118

           alarmInputHighDensity0119Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 119 from a high density unit
                transitions to the alarm state."
           ::= 30119

           alarmInputHighDensity0119Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 119 from a high density unit 
                transitions to the normal state."
           ::= 40119

           alarmInputHighDensity0120Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 120 from a high density unit
                transitions to the alarm state."
           ::= 30120

           alarmInputHighDensity0120Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 120 from a high density unit 
                transitions to the normal state."
           ::= 40120

           alarmInputHighDensity0121Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 121 from a high density unit
                transitions to the alarm state."
           ::= 30121

           alarmInputHighDensity0121Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 121 from a high density unit 
                transitions to the normal state."
           ::= 40121

           alarmInputHighDensity0122Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 122 from a high density unit
                transitions to the alarm state."
           ::= 30122

           alarmInputHighDensity0122Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 122 from a high density unit 
                transitions to the normal state."
           ::= 40122

           alarmInputHighDensity0123Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 123 from a high density unit
                transitions to the alarm state."
           ::= 30123

           alarmInputHighDensity0123Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 123 from a high density unit 
                transitions to the normal state."
           ::= 40123

           alarmInputHighDensity0124Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 124 from a high density unit
                transitions to the alarm state."
           ::= 30124

           alarmInputHighDensity0124Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 124 from a high density unit 
                transitions to the normal state."
           ::= 40124

           alarmInputHighDensity0125Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 125 from a high density unit
                transitions to the alarm state."
           ::= 30125

           alarmInputHighDensity0125Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 125 from a high density unit 
                transitions to the normal state."
           ::= 40125

           alarmInputHighDensity0126Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 126 from a high density unit
                transitions to the alarm state."
           ::= 30126

           alarmInputHighDensity0126Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 126 from a high density unit 
                transitions to the normal state."
           ::= 40126

           alarmInputHighDensity0127Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 127 from a high density unit
                transitions to the alarm state."
           ::= 30127

           alarmInputHighDensity0127Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 127 from a high density unit 
                transitions to the normal state."
           ::= 40127

           alarmInputHighDensity0128Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 128 from a high density unit
                transitions to the alarm state."
           ::= 30128

           alarmInputHighDensity0128Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 128 from a high density unit 
                transitions to the normal state."
           ::= 40128

           alarmInputHighDensity0129Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 129 from a high density unit
                transitions to the alarm state."
           ::= 30129

           alarmInputHighDensity0129Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 129 from a high density unit 
                transitions to the normal state."
           ::= 40129

           alarmInputHighDensity0130Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 130 from a high density unit
                transitions to the alarm state."
           ::= 30130

           alarmInputHighDensity0130Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 130 from a high density unit 
                transitions to the normal state."
           ::= 40130

           alarmInputHighDensity0131Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 131 from a high density unit
                transitions to the alarm state."
           ::= 30131

           alarmInputHighDensity0131Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 131 from a high density unit 
                transitions to the normal state."
           ::= 40131

           alarmInputHighDensity0132Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 132 from a high density unit
                transitions to the alarm state."
           ::= 30132

           alarmInputHighDensity0132Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 132 from a high density unit 
                transitions to the normal state."
           ::= 40132

           alarmInputHighDensity0133Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 133 from a high density unit
                transitions to the alarm state."
           ::= 30133

           alarmInputHighDensity0133Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 133 from a high density unit 
                transitions to the normal state."
           ::= 40133

           alarmInputHighDensity0134Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 134 from a high density unit
                transitions to the alarm state."
           ::= 30134

           alarmInputHighDensity0134Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 134 from a high density unit 
                transitions to the normal state."
           ::= 40134

           alarmInputHighDensity0135Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 135 from a high density unit
                transitions to the alarm state."
           ::= 30135

           alarmInputHighDensity0135Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 135 from a high density unit 
                transitions to the normal state."
           ::= 40135

           alarmInputHighDensity0136Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 136 from a high density unit
                transitions to the alarm state."
           ::= 30136

           alarmInputHighDensity0136Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 136 from a high density unit 
                transitions to the normal state."
           ::= 40136

           alarmInputHighDensity0137Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 137 from a high density unit
                transitions to the alarm state."
           ::= 30137

           alarmInputHighDensity0137Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 137 from a high density unit 
                transitions to the normal state."
           ::= 40137

           alarmInputHighDensity0138Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 138 from a high density unit
                transitions to the alarm state."
           ::= 30138

           alarmInputHighDensity0138Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 138 from a high density unit 
                transitions to the normal state."
           ::= 40138

           alarmInputHighDensity0139Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 139 from a high density unit
                transitions to the alarm state."
           ::= 30139

           alarmInputHighDensity0139Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 139 from a high density unit 
                transitions to the normal state."
           ::= 40139

           alarmInputHighDensity0140Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 140 from a high density unit
                transitions to the alarm state."
           ::= 30140

           alarmInputHighDensity0140Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 140 from a high density unit 
                transitions to the normal state."
           ::= 40140

           alarmInputHighDensity0141Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 141 from a high density unit
                transitions to the alarm state."
           ::= 30141

           alarmInputHighDensity0141Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 141 from a high density unit 
                transitions to the normal state."
           ::= 40141

           alarmInputHighDensity0142Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 142 from a high density unit
                transitions to the alarm state."
           ::= 30142

           alarmInputHighDensity0142Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 142 from a high density unit 
                transitions to the normal state."
           ::= 40142

           alarmInputHighDensity0143Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 143 from a high density unit
                transitions to the alarm state."
           ::= 30143

           alarmInputHighDensity0143Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 143 from a high density unit 
                transitions to the normal state."
           ::= 40143

           alarmInputHighDensity0144Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 144 from a high density unit
                transitions to the alarm state."
           ::= 30144

           alarmInputHighDensity0144Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 144 from a high density unit 
                transitions to the normal state."
           ::= 40144

           alarmInputHighDensity0145Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 145 from a high density unit
                transitions to the alarm state."
           ::= 30145

           alarmInputHighDensity0145Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 145 from a high density unit 
                transitions to the normal state."
           ::= 40145

           alarmInputHighDensity0146Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 146 from a high density unit
                transitions to the alarm state."
           ::= 30146

           alarmInputHighDensity0146Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 146 from a high density unit 
                transitions to the normal state."
           ::= 40146

           alarmInputHighDensity0147Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 147 from a high density unit
                transitions to the alarm state."
           ::= 30147

           alarmInputHighDensity0147Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 147 from a high density unit 
                transitions to the normal state."
           ::= 40147

           alarmInputHighDensity0148Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 148 from a high density unit
                transitions to the alarm state."
           ::= 30148

           alarmInputHighDensity0148Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 148 from a high density unit 
                transitions to the normal state."
           ::= 40148

           alarmInputHighDensity0149Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 149 from a high density unit
                transitions to the alarm state."
           ::= 30149

           alarmInputHighDensity0149Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 149 from a high density unit 
                transitions to the normal state."
           ::= 40149

           alarmInputHighDensity0150Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 150 from a high density unit
                transitions to the alarm state."
           ::= 30150

           alarmInputHighDensity0150Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 150 from a high density unit 
                transitions to the normal state."
           ::= 40150

           alarmInputHighDensity0151Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 151 from a high density unit
                transitions to the alarm state."
           ::= 30151

           alarmInputHighDensity0151Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 151 from a high density unit 
                transitions to the normal state."
           ::= 40151

           alarmInputHighDensity0152Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 152 from a high density unit
                transitions to the alarm state."
           ::= 30152

           alarmInputHighDensity0152Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 152 from a high density unit 
                transitions to the normal state."
           ::= 40152

           alarmInputHighDensity0153Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 153 from a high density unit
                transitions to the alarm state."
           ::= 30153

           alarmInputHighDensity0153Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 153 from a high density unit 
                transitions to the normal state."
           ::= 40153

           alarmInputHighDensity0154Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 154 from a high density unit
                transitions to the alarm state."
           ::= 30154

           alarmInputHighDensity0154Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 154 from a high density unit 
                transitions to the normal state."
           ::= 40154

           alarmInputHighDensity0155Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 155 from a high density unit
                transitions to the alarm state."
           ::= 30155

           alarmInputHighDensity0155Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 155 from a high density unit 
                transitions to the normal state."
           ::= 40155

           alarmInputHighDensity0156Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 156 from a high density unit
                transitions to the alarm state."
           ::= 30156

           alarmInputHighDensity0156Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 156 from a high density unit 
                transitions to the normal state."
           ::= 40156

           alarmInputHighDensity0157Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 157 from a high density unit
                transitions to the alarm state."
           ::= 30157

           alarmInputHighDensity0157Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 157 from a high density unit 
                transitions to the normal state."
           ::= 40157

           alarmInputHighDensity0158Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 158 from a high density unit
                transitions to the alarm state."
           ::= 30158

           alarmInputHighDensity0158Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 158 from a high density unit 
                transitions to the normal state."
           ::= 40158

           alarmInputHighDensity0159Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 159 from a high density unit
                transitions to the alarm state."
           ::= 30159

           alarmInputHighDensity0159Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 159 from a high density unit 
                transitions to the normal state."
           ::= 40159

           alarmInputHighDensity0160Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 160 from a high density unit
                transitions to the alarm state."
           ::= 30160

           alarmInputHighDensity0160Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 160 from a high density unit 
                transitions to the normal state."
           ::= 40160

           alarmInputHighDensity0161Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 161 from a high density unit
                transitions to the alarm state."
           ::= 30161

           alarmInputHighDensity0161Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 161 from a high density unit 
                transitions to the normal state."
           ::= 40161

           alarmInputHighDensity0162Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 162 from a high density unit
                transitions to the alarm state."
           ::= 30162

           alarmInputHighDensity0162Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 162 from a high density unit 
                transitions to the normal state."
           ::= 40162

           alarmInputHighDensity0163Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 163 from a high density unit
                transitions to the alarm state."
           ::= 30163

           alarmInputHighDensity0163Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 163 from a high density unit 
                transitions to the normal state."
           ::= 40163

           alarmInputHighDensity0164Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 164 from a high density unit
                transitions to the alarm state."
           ::= 30164

           alarmInputHighDensity0164Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 164 from a high density unit 
                transitions to the normal state."
           ::= 40164

           alarmInputHighDensity0165Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 165 from a high density unit
                transitions to the alarm state."
           ::= 30165

           alarmInputHighDensity0165Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 165 from a high density unit 
                transitions to the normal state."
           ::= 40165

           alarmInputHighDensity0166Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 166 from a high density unit
                transitions to the alarm state."
           ::= 30166

           alarmInputHighDensity0166Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 166 from a high density unit 
                transitions to the normal state."
           ::= 40166

           alarmInputHighDensity0167Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 167 from a high density unit
                transitions to the alarm state."
           ::= 30167

           alarmInputHighDensity0167Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 167 from a high density unit 
                transitions to the normal state."
           ::= 40167

           alarmInputHighDensity0168Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 168 from a high density unit
                transitions to the alarm state."
           ::= 30168

           alarmInputHighDensity0168Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 168 from a high density unit 
                transitions to the normal state."
           ::= 40168

           alarmInputHighDensity0169Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 169 from a high density unit
                transitions to the alarm state."
           ::= 30169

           alarmInputHighDensity0169Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 169 from a high density unit 
                transitions to the normal state."
           ::= 40169

           alarmInputHighDensity0170Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 170 from a high density unit
                transitions to the alarm state."
           ::= 30170

           alarmInputHighDensity0170Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 170 from a high density unit 
                transitions to the normal state."
           ::= 40170

           alarmInputHighDensity0171Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 171 from a high density unit
                transitions to the alarm state."
           ::= 30171

           alarmInputHighDensity0171Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 171 from a high density unit 
                transitions to the normal state."
           ::= 40171

           alarmInputHighDensity0172Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 172 from a high density unit
                transitions to the alarm state."
           ::= 30172

           alarmInputHighDensity0172Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 172 from a high density unit 
                transitions to the normal state."
           ::= 40172

           alarmInputHighDensity0173Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 173 from a high density unit
                transitions to the alarm state."
           ::= 30173

           alarmInputHighDensity0173Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 173 from a high density unit 
                transitions to the normal state."
           ::= 40173

           alarmInputHighDensity0174Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 174 from a high density unit
                transitions to the alarm state."
           ::= 30174

           alarmInputHighDensity0174Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 174 from a high density unit 
                transitions to the normal state."
           ::= 40174

           alarmInputHighDensity0175Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 175 from a high density unit
                transitions to the alarm state."
           ::= 30175

           alarmInputHighDensity0175Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 175 from a high density unit 
                transitions to the normal state."
           ::= 40175

           alarmInputHighDensity0176Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 176 from a high density unit
                transitions to the alarm state."
           ::= 30176

           alarmInputHighDensity0176Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 176 from a high density unit 
                transitions to the normal state."
           ::= 40176

           alarmInputHighDensity0177Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 177 from a high density unit
                transitions to the alarm state."
           ::= 30177

           alarmInputHighDensity0177Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 177 from a high density unit 
                transitions to the normal state."
           ::= 40177

           alarmInputHighDensity0178Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 178 from a high density unit
                transitions to the alarm state."
           ::= 30178

           alarmInputHighDensity0178Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 178 from a high density unit 
                transitions to the normal state."
           ::= 40178

           alarmInputHighDensity0179Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 179 from a high density unit
                transitions to the alarm state."
           ::= 30179

           alarmInputHighDensity0179Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 179 from a high density unit 
                transitions to the normal state."
           ::= 40179

           alarmInputHighDensity0180Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 180 from a high density unit
                transitions to the alarm state."
           ::= 30180

           alarmInputHighDensity0180Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 180 from a high density unit 
                transitions to the normal state."
           ::= 40180

           alarmInputHighDensity0181Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 181 from a high density unit
                transitions to the alarm state."
           ::= 30181

           alarmInputHighDensity0181Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 181 from a high density unit 
                transitions to the normal state."
           ::= 40181

           alarmInputHighDensity0182Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 182 from a high density unit
                transitions to the alarm state."
           ::= 30182

           alarmInputHighDensity0182Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 182 from a high density unit 
                transitions to the normal state."
           ::= 40182

           alarmInputHighDensity0183Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 183 from a high density unit
                transitions to the alarm state."
           ::= 30183

           alarmInputHighDensity0183Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 183 from a high density unit 
                transitions to the normal state."
           ::= 40183

           alarmInputHighDensity0184Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 184 from a high density unit
                transitions to the alarm state."
           ::= 30184

           alarmInputHighDensity0184Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 184 from a high density unit 
                transitions to the normal state."
           ::= 40184

           alarmInputHighDensity0185Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 185 from a high density unit
                transitions to the alarm state."
           ::= 30185

           alarmInputHighDensity0185Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 185 from a high density unit 
                transitions to the normal state."
           ::= 40185

           alarmInputHighDensity0186Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 186 from a high density unit
                transitions to the alarm state."
           ::= 30186

           alarmInputHighDensity0186Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 186 from a high density unit 
                transitions to the normal state."
           ::= 40186

           alarmInputHighDensity0187Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 187 from a high density unit
                transitions to the alarm state."
           ::= 30187

           alarmInputHighDensity0187Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 187 from a high density unit 
                transitions to the normal state."
           ::= 40187

           alarmInputHighDensity0188Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 188 from a high density unit
                transitions to the alarm state."
           ::= 30188

           alarmInputHighDensity0188Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 188 from a high density unit 
                transitions to the normal state."
           ::= 40188

           alarmInputHighDensity0189Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 189 from a high density unit
                transitions to the alarm state."
           ::= 30189

           alarmInputHighDensity0189Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 189 from a high density unit 
                transitions to the normal state."
           ::= 40189

           alarmInputHighDensity0190Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 190 from a high density unit
                transitions to the alarm state."
           ::= 30190

           alarmInputHighDensity0190Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 190 from a high density unit 
                transitions to the normal state."
           ::= 40190

           alarmInputHighDensity0191Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 191 from a high density unit
                transitions to the alarm state."
           ::= 30191

           alarmInputHighDensity0191Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 191 from a high density unit 
                transitions to the normal state."
           ::= 40191

           alarmInputHighDensity0192Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 192 from a high density unit
                transitions to the alarm state."
           ::= 30192

           alarmInputHighDensity0192Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 192 from a high density unit 
                transitions to the normal state."
           ::= 40192

           alarmInputHighDensity0193Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 193 from a high density unit
                transitions to the alarm state."
           ::= 30193

           alarmInputHighDensity0193Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 193 from a high density unit 
                transitions to the normal state."
           ::= 40193

           alarmInputHighDensity0194Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 194 from a high density unit
                transitions to the alarm state."
           ::= 30194

           alarmInputHighDensity0194Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 194 from a high density unit 
                transitions to the normal state."
           ::= 40194

           alarmInputHighDensity0195Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 195 from a high density unit
                transitions to the alarm state."
           ::= 30195

           alarmInputHighDensity0195Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 195 from a high density unit 
                transitions to the normal state."
           ::= 40195

           alarmInputHighDensity0196Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 196 from a high density unit
                transitions to the alarm state."
           ::= 30196

           alarmInputHighDensity0196Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 196 from a high density unit 
                transitions to the normal state."
           ::= 40196

           alarmInputHighDensity0197Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 197 from a high density unit
                transitions to the alarm state."
           ::= 30197

           alarmInputHighDensity0197Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 197 from a high density unit 
                transitions to the normal state."
           ::= 40197

           alarmInputHighDensity0198Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 198 from a high density unit
                transitions to the alarm state."
           ::= 30198

           alarmInputHighDensity0198Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 198 from a high density unit 
                transitions to the normal state."
           ::= 40198

           alarmInputHighDensity0199Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 199 from a high density unit
                transitions to the alarm state."
           ::= 30199

           alarmInputHighDensity0199Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 199 from a high density unit 
                transitions to the normal state."
           ::= 40199

           alarmInputHighDensity0200Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 200 from a high density unit
                transitions to the alarm state."
           ::= 30200

           alarmInputHighDensity0200Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 200 from a high density unit 
                transitions to the normal state."
           ::= 40200

           alarmInputHighDensity0201Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 201 from a high density unit
                transitions to the alarm state."
           ::= 30201

           alarmInputHighDensity0201Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 201 from a high density unit 
                transitions to the normal state."
           ::= 40201

           alarmInputHighDensity0202Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 202 from a high density unit
                transitions to the alarm state."
           ::= 30202

           alarmInputHighDensity0202Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 202 from a high density unit 
                transitions to the normal state."
           ::= 40202

           alarmInputHighDensity0203Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 203 from a high density unit
                transitions to the alarm state."
           ::= 30203

           alarmInputHighDensity0203Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 203 from a high density unit 
                transitions to the normal state."
           ::= 40203

           alarmInputHighDensity0204Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 204 from a high density unit
                transitions to the alarm state."
           ::= 30204

           alarmInputHighDensity0204Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 204 from a high density unit 
                transitions to the normal state."
           ::= 40204

           alarmInputHighDensity0205Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 205 from a high density unit
                transitions to the alarm state."
           ::= 30205

           alarmInputHighDensity0205Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 205 from a high density unit 
                transitions to the normal state."
           ::= 40205

           alarmInputHighDensity0206Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 206 from a high density unit
                transitions to the alarm state."
           ::= 30206

           alarmInputHighDensity0206Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 206 from a high density unit 
                transitions to the normal state."
           ::= 40206

           alarmInputHighDensity0207Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 207 from a high density unit
                transitions to the alarm state."
           ::= 30207

           alarmInputHighDensity0207Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 207 from a high density unit 
                transitions to the normal state."
           ::= 40207

           alarmInputHighDensity0208Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 208 from a high density unit
                transitions to the alarm state."
           ::= 30208

           alarmInputHighDensity0208Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 208 from a high density unit 
                transitions to the normal state."
           ::= 40208

           alarmInputHighDensity0209Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 209 from a high density unit
                transitions to the alarm state."
           ::= 30209

           alarmInputHighDensity0209Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 209 from a high density unit 
                transitions to the normal state."
           ::= 40209

           alarmInputHighDensity0210Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 210 from a high density unit
                transitions to the alarm state."
           ::= 30210

           alarmInputHighDensity0210Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 210 from a high density unit 
                transitions to the normal state."
           ::= 40210

           alarmInputHighDensity0211Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 211 from a high density unit
                transitions to the alarm state."
           ::= 30211

           alarmInputHighDensity0211Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 211 from a high density unit 
                transitions to the normal state."
           ::= 40211

           alarmInputHighDensity0212Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 212 from a high density unit
                transitions to the alarm state."
           ::= 30212

           alarmInputHighDensity0212Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 212 from a high density unit 
                transitions to the normal state."
           ::= 40212

           alarmInputHighDensity0213Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 213 from a high density unit
                transitions to the alarm state."
           ::= 30213

           alarmInputHighDensity0213Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 213 from a high density unit 
                transitions to the normal state."
           ::= 40213

           alarmInputHighDensity0214Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 214 from a high density unit
                transitions to the alarm state."
           ::= 30214

           alarmInputHighDensity0214Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 214 from a high density unit 
                transitions to the normal state."
           ::= 40214

           alarmInputHighDensity0215Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 215 from a high density unit
                transitions to the alarm state."
           ::= 30215

           alarmInputHighDensity0215Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 215 from a high density unit 
                transitions to the normal state."
           ::= 40215

           alarmInputHighDensity0216Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 216 from a high density unit
                transitions to the alarm state."
           ::= 30216

           alarmInputHighDensity0216Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 216 from a high density unit 
                transitions to the normal state."
           ::= 40216

           alarmInputHighDensity0217Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 217 from a high density unit
                transitions to the alarm state."
           ::= 30217

           alarmInputHighDensity0217Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 217 from a high density unit 
                transitions to the normal state."
           ::= 40217

           alarmInputHighDensity0218Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 218 from a high density unit
                transitions to the alarm state."
           ::= 30218

           alarmInputHighDensity0218Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 218 from a high density unit 
                transitions to the normal state."
           ::= 40218

           alarmInputHighDensity0219Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 219 from a high density unit
                transitions to the alarm state."
           ::= 30219

           alarmInputHighDensity0219Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 219 from a high density unit 
                transitions to the normal state."
           ::= 40219

           alarmInputHighDensity0220Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 220 from a high density unit
                transitions to the alarm state."
           ::= 30220

           alarmInputHighDensity0220Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 220 from a high density unit 
                transitions to the normal state."
           ::= 40220

           alarmInputHighDensity0221Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 221 from a high density unit
                transitions to the alarm state."
           ::= 30221

           alarmInputHighDensity0221Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 221 from a high density unit 
                transitions to the normal state."
           ::= 40221

           alarmInputHighDensity0222Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 222 from a high density unit
                transitions to the alarm state."
           ::= 30222

           alarmInputHighDensity0222Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 222 from a high density unit 
                transitions to the normal state."
           ::= 40222

           alarmInputHighDensity0223Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 223 from a high density unit
                transitions to the alarm state."
           ::= 30223

           alarmInputHighDensity0223Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 223 from a high density unit 
                transitions to the normal state."
           ::= 40223

           alarmInputHighDensity0224Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 224 from a high density unit
                transitions to the alarm state."
           ::= 30224

           alarmInputHighDensity0224Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 224 from a high density unit 
                transitions to the normal state."
           ::= 40224

           alarmInputHighDensity0225Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 225 from a high density unit
                transitions to the alarm state."
           ::= 30225

           alarmInputHighDensity0225Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 225 from a high density unit 
                transitions to the normal state."
           ::= 40225

           alarmInputHighDensity0226Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 226 from a high density unit
                transitions to the alarm state."
           ::= 30226

           alarmInputHighDensity0226Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 226 from a high density unit 
                transitions to the normal state."
           ::= 40226

           alarmInputHighDensity0227Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 227 from a high density unit
                transitions to the alarm state."
           ::= 30227

           alarmInputHighDensity0227Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 227 from a high density unit 
                transitions to the normal state."
           ::= 40227

           alarmInputHighDensity0228Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 228 from a high density unit
                transitions to the alarm state."
           ::= 30228

           alarmInputHighDensity0228Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 228 from a high density unit 
                transitions to the normal state."
           ::= 40228

           alarmInputHighDensity0229Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 229 from a high density unit
                transitions to the alarm state."
           ::= 30229

           alarmInputHighDensity0229Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 229 from a high density unit 
                transitions to the normal state."
           ::= 40229

           alarmInputHighDensity0230Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 230 from a high density unit
                transitions to the alarm state."
           ::= 30230

           alarmInputHighDensity0230Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 230 from a high density unit 
                transitions to the normal state."
           ::= 40230

           alarmInputHighDensity0231Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 231 from a high density unit
                transitions to the alarm state."
           ::= 30231

           alarmInputHighDensity0231Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 231 from a high density unit 
                transitions to the normal state."
           ::= 40231

           alarmInputHighDensity0232Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 232 from a high density unit
                transitions to the alarm state."
           ::= 30232

           alarmInputHighDensity0232Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 232 from a high density unit 
                transitions to the normal state."
           ::= 40232

           alarmInputHighDensity0233Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 233 from a high density unit
                transitions to the alarm state."
           ::= 30233

           alarmInputHighDensity0233Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 233 from a high density unit 
                transitions to the normal state."
           ::= 40233

           alarmInputHighDensity0234Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 234 from a high density unit
                transitions to the alarm state."
           ::= 30234

           alarmInputHighDensity0234Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 234 from a high density unit 
                transitions to the normal state."
           ::= 40234

           alarmInputHighDensity0235Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 235 from a high density unit
                transitions to the alarm state."
           ::= 30235

           alarmInputHighDensity0235Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 235 from a high density unit 
                transitions to the normal state."
           ::= 40235

           alarmInputHighDensity0236Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 236 from a high density unit
                transitions to the alarm state."
           ::= 30236

           alarmInputHighDensity0236Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 236 from a high density unit 
                transitions to the normal state."
           ::= 40236

           alarmInputHighDensity0237Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 237 from a high density unit
                transitions to the alarm state."
           ::= 30237

           alarmInputHighDensity0237Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 237 from a high density unit 
                transitions to the normal state."
           ::= 40237

           alarmInputHighDensity0238Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 238 from a high density unit
                transitions to the alarm state."
           ::= 30238

           alarmInputHighDensity0238Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 238 from a high density unit 
                transitions to the normal state."
           ::= 40238

           alarmInputHighDensity0239Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 239 from a high density unit
                transitions to the alarm state."
           ::= 30239

           alarmInputHighDensity0239Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 239 from a high density unit 
                transitions to the normal state."
           ::= 40239

           alarmInputHighDensity0240Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 240 from a high density unit
                transitions to the alarm state."
           ::= 30240

           alarmInputHighDensity0240Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 240 from a high density unit 
                transitions to the normal state."
           ::= 40240

           alarmInputHighDensity0241Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 241 from a high density unit
                transitions to the alarm state."
           ::= 30241

           alarmInputHighDensity0241Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 241 from a high density unit 
                transitions to the normal state."
           ::= 40241

           alarmInputHighDensity0242Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 242 from a high density unit
                transitions to the alarm state."
           ::= 30242

           alarmInputHighDensity0242Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 242 from a high density unit 
                transitions to the normal state."
           ::= 40242

           alarmInputHighDensity0243Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 243 from a high density unit
                transitions to the alarm state."
           ::= 30243

           alarmInputHighDensity0243Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 243 from a high density unit 
                transitions to the normal state."
           ::= 40243

           alarmInputHighDensity0244Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 244 from a high density unit
                transitions to the alarm state."
           ::= 30244

           alarmInputHighDensity0244Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 244 from a high density unit 
                transitions to the normal state."
           ::= 40244

           alarmInputHighDensity0245Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 245 from a high density unit
                transitions to the alarm state."
           ::= 30245

           alarmInputHighDensity0245Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 245 from a high density unit 
                transitions to the normal state."
           ::= 40245

           alarmInputHighDensity0246Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 246 from a high density unit
                transitions to the alarm state."
           ::= 30246

           alarmInputHighDensity0246Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 246 from a high density unit 
                transitions to the normal state."
           ::= 40246

           alarmInputHighDensity0247Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 247 from a high density unit
                transitions to the alarm state."
           ::= 30247

           alarmInputHighDensity0247Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 247 from a high density unit 
                transitions to the normal state."
           ::= 40247

           alarmInputHighDensity0248Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 248 from a high density unit
                transitions to the alarm state."
           ::= 30248

           alarmInputHighDensity0248Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 248 from a high density unit 
                transitions to the normal state."
           ::= 40248

           alarmInputHighDensity0249Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 249 from a high density unit
                transitions to the alarm state."
           ::= 30249

           alarmInputHighDensity0249Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 249 from a high density unit 
                transitions to the normal state."
           ::= 40249

           alarmInputHighDensity0250Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 250 from a high density unit
                transitions to the alarm state."
           ::= 30250

           alarmInputHighDensity0250Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 250 from a high density unit 
                transitions to the normal state."
           ::= 40250

           alarmInputHighDensity0251Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 251 from a high density unit
                transitions to the alarm state."
           ::= 30251

           alarmInputHighDensity0251Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 251 from a high density unit 
                transitions to the normal state."
           ::= 40251

           alarmInputHighDensity0252Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 252 from a high density unit
                transitions to the alarm state."
           ::= 30252

           alarmInputHighDensity0252Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 252 from a high density unit 
                transitions to the normal state."
           ::= 40252

           alarmInputHighDensity0253Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 253 from a high density unit
                transitions to the alarm state."
           ::= 30253

           alarmInputHighDensity0253Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 253 from a high density unit 
                transitions to the normal state."
           ::= 40253

           alarmInputHighDensity0254Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 254 from a high density unit
                transitions to the alarm state."
           ::= 30254

           alarmInputHighDensity0254Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 254 from a high density unit 
                transitions to the normal state."
           ::= 40254

           alarmInputHighDensity0255Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 255 from a high density unit
                transitions to the alarm state."
           ::= 30255

           alarmInputHighDensity0255Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 255 from a high density unit 
                transitions to the normal state."
           ::= 40255

           alarmInputHighDensity0256Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 256 from a high density unit
                transitions to the alarm state."
           ::= 30256

           alarmInputHighDensity0256Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 256 from a high density unit 
                transitions to the normal state."
           ::= 40256

           alarmInputHighDensity0257Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 257 from a high density unit
                transitions to the alarm state."
           ::= 30257

           alarmInputHighDensity0257Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 257 from a high density unit 
                transitions to the normal state."
           ::= 40257

           alarmInputHighDensity0258Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 258 from a high density unit
                transitions to the alarm state."
           ::= 30258

           alarmInputHighDensity0258Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 258 from a high density unit 
                transitions to the normal state."
           ::= 40258

           alarmInputHighDensity0259Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 259 from a high density unit
                transitions to the alarm state."
           ::= 30259

           alarmInputHighDensity0259Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 259 from a high density unit 
                transitions to the normal state."
           ::= 40259

           alarmInputHighDensity0260Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 260 from a high density unit
                transitions to the alarm state."
           ::= 30260

           alarmInputHighDensity0260Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 260 from a high density unit 
                transitions to the normal state."
           ::= 40260

           alarmInputHighDensity0261Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 261 from a high density unit
                transitions to the alarm state."
           ::= 30261

           alarmInputHighDensity0261Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 261 from a high density unit 
                transitions to the normal state."
           ::= 40261

           alarmInputHighDensity0262Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 262 from a high density unit
                transitions to the alarm state."
           ::= 30262

           alarmInputHighDensity0262Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 262 from a high density unit 
                transitions to the normal state."
           ::= 40262

           alarmInputHighDensity0263Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 263 from a high density unit
                transitions to the alarm state."
           ::= 30263

           alarmInputHighDensity0263Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 263 from a high density unit 
                transitions to the normal state."
           ::= 40263

           alarmInputHighDensity0264Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 264 from a high density unit
                transitions to the alarm state."
           ::= 30264

           alarmInputHighDensity0264Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 264 from a high density unit 
                transitions to the normal state."
           ::= 40264

           alarmInputHighDensity0265Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 265 from a high density unit
                transitions to the alarm state."
           ::= 30265

           alarmInputHighDensity0265Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 265 from a high density unit 
                transitions to the normal state."
           ::= 40265

           alarmInputHighDensity0266Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 266 from a high density unit
                transitions to the alarm state."
           ::= 30266

           alarmInputHighDensity0266Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 266 from a high density unit 
                transitions to the normal state."
           ::= 40266

           alarmInputHighDensity0267Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 267 from a high density unit
                transitions to the alarm state."
           ::= 30267

           alarmInputHighDensity0267Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 267 from a high density unit 
                transitions to the normal state."
           ::= 40267

           alarmInputHighDensity0268Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 268 from a high density unit
                transitions to the alarm state."
           ::= 30268

           alarmInputHighDensity0268Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 268 from a high density unit 
                transitions to the normal state."
           ::= 40268

           alarmInputHighDensity0269Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 269 from a high density unit
                transitions to the alarm state."
           ::= 30269

           alarmInputHighDensity0269Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 269 from a high density unit 
                transitions to the normal state."
           ::= 40269

           alarmInputHighDensity0270Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 270 from a high density unit
                transitions to the alarm state."
           ::= 30270

           alarmInputHighDensity0270Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 270 from a high density unit 
                transitions to the normal state."
           ::= 40270

           alarmInputHighDensity0271Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 271 from a high density unit
                transitions to the alarm state."
           ::= 30271

           alarmInputHighDensity0271Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 271 from a high density unit 
                transitions to the normal state."
           ::= 40271

           alarmInputHighDensity0272Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 272 from a high density unit
                transitions to the alarm state."
           ::= 30272

           alarmInputHighDensity0272Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 272 from a high density unit 
                transitions to the normal state."
           ::= 40272

           alarmInputHighDensity0273Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 273 from a high density unit
                transitions to the alarm state."
           ::= 30273

           alarmInputHighDensity0273Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 273 from a high density unit 
                transitions to the normal state."
           ::= 40273

           alarmInputHighDensity0274Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 274 from a high density unit
                transitions to the alarm state."
           ::= 30274

           alarmInputHighDensity0274Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 274 from a high density unit 
                transitions to the normal state."
           ::= 40274

           alarmInputHighDensity0275Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 275 from a high density unit
                transitions to the alarm state."
           ::= 30275

           alarmInputHighDensity0275Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 275 from a high density unit 
                transitions to the normal state."
           ::= 40275

           alarmInputHighDensity0276Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 276 from a high density unit
                transitions to the alarm state."
           ::= 30276

           alarmInputHighDensity0276Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 276 from a high density unit 
                transitions to the normal state."
           ::= 40276

           alarmInputHighDensity0277Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 277 from a high density unit
                transitions to the alarm state."
           ::= 30277

           alarmInputHighDensity0277Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 277 from a high density unit 
                transitions to the normal state."
           ::= 40277

           alarmInputHighDensity0278Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 278 from a high density unit
                transitions to the alarm state."
           ::= 30278

           alarmInputHighDensity0278Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 278 from a high density unit 
                transitions to the normal state."
           ::= 40278

           alarmInputHighDensity0279Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 279 from a high density unit
                transitions to the alarm state."
           ::= 30279

           alarmInputHighDensity0279Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 279 from a high density unit 
                transitions to the normal state."
           ::= 40279

           alarmInputHighDensity0280Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 280 from a high density unit
                transitions to the alarm state."
           ::= 30280

           alarmInputHighDensity0280Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 280 from a high density unit 
                transitions to the normal state."
           ::= 40280

           alarmInputHighDensity0281Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 281 from a high density unit
                transitions to the alarm state."
           ::= 30281

           alarmInputHighDensity0281Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 281 from a high density unit 
                transitions to the normal state."
           ::= 40281

           alarmInputHighDensity0282Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 282 from a high density unit
                transitions to the alarm state."
           ::= 30282

           alarmInputHighDensity0282Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 282 from a high density unit 
                transitions to the normal state."
           ::= 40282

           alarmInputHighDensity0283Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 283 from a high density unit
                transitions to the alarm state."
           ::= 30283

           alarmInputHighDensity0283Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 283 from a high density unit 
                transitions to the normal state."
           ::= 40283

           alarmInputHighDensity0284Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 284 from a high density unit
                transitions to the alarm state."
           ::= 30284

           alarmInputHighDensity0284Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 284 from a high density unit 
                transitions to the normal state."
           ::= 40284

           alarmInputHighDensity0285Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 285 from a high density unit
                transitions to the alarm state."
           ::= 30285

           alarmInputHighDensity0285Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 285 from a high density unit 
                transitions to the normal state."
           ::= 40285

           alarmInputHighDensity0286Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 286 from a high density unit
                transitions to the alarm state."
           ::= 30286

           alarmInputHighDensity0286Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 286 from a high density unit 
                transitions to the normal state."
           ::= 40286

           alarmInputHighDensity0287Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 287 from a high density unit
                transitions to the alarm state."
           ::= 30287

           alarmInputHighDensity0287Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 287 from a high density unit 
                transitions to the normal state."
           ::= 40287

           alarmInputHighDensity0288Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 288 from a high density unit
                transitions to the alarm state."
           ::= 30288

           alarmInputHighDensity0288Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 288 from a high density unit 
                transitions to the normal state."
           ::= 40288

           alarmInputHighDensity0289Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 289 from a high density unit
                transitions to the alarm state."
           ::= 30289

           alarmInputHighDensity0289Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 289 from a high density unit 
                transitions to the normal state."
           ::= 40289

           alarmInputHighDensity0290Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 290 from a high density unit
                transitions to the alarm state."
           ::= 30290

           alarmInputHighDensity0290Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 290 from a high density unit 
                transitions to the normal state."
           ::= 40290

           alarmInputHighDensity0291Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 291 from a high density unit
                transitions to the alarm state."
           ::= 30291

           alarmInputHighDensity0291Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 291 from a high density unit 
                transitions to the normal state."
           ::= 40291

           alarmInputHighDensity0292Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 292 from a high density unit
                transitions to the alarm state."
           ::= 30292

           alarmInputHighDensity0292Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 292 from a high density unit 
                transitions to the normal state."
           ::= 40292

           alarmInputHighDensity0293Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 293 from a high density unit
                transitions to the alarm state."
           ::= 30293

           alarmInputHighDensity0293Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 293 from a high density unit 
                transitions to the normal state."
           ::= 40293

           alarmInputHighDensity0294Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 294 from a high density unit
                transitions to the alarm state."
           ::= 30294

           alarmInputHighDensity0294Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 294 from a high density unit 
                transitions to the normal state."
           ::= 40294

           alarmInputHighDensity0295Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 295 from a high density unit
                transitions to the alarm state."
           ::= 30295

           alarmInputHighDensity0295Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 295 from a high density unit 
                transitions to the normal state."
           ::= 40295

           alarmInputHighDensity0296Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 296 from a high density unit
                transitions to the alarm state."
           ::= 30296

           alarmInputHighDensity0296Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 296 from a high density unit 
                transitions to the normal state."
           ::= 40296

           alarmInputHighDensity0297Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 297 from a high density unit
                transitions to the alarm state."
           ::= 30297

           alarmInputHighDensity0297Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 297 from a high density unit 
                transitions to the normal state."
           ::= 40297

           alarmInputHighDensity0298Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 298 from a high density unit
                transitions to the alarm state."
           ::= 30298

           alarmInputHighDensity0298Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 298 from a high density unit 
                transitions to the normal state."
           ::= 40298

           alarmInputHighDensity0299Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 299 from a high density unit
                transitions to the alarm state."
           ::= 30299

           alarmInputHighDensity0299Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 299 from a high density unit 
                transitions to the normal state."
           ::= 40299

           alarmInputHighDensity0300Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 300 from a high density unit
                transitions to the alarm state."
           ::= 30300

           alarmInputHighDensity0300Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 300 from a high density unit 
                transitions to the normal state."
           ::= 40300

           alarmInputHighDensity0301Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 301 from a high density unit
                transitions to the alarm state."
           ::= 30301

           alarmInputHighDensity0301Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 301 from a high density unit 
                transitions to the normal state."
           ::= 40301

           alarmInputHighDensity0302Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 302 from a high density unit
                transitions to the alarm state."
           ::= 30302

           alarmInputHighDensity0302Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 302 from a high density unit 
                transitions to the normal state."
           ::= 40302

           alarmInputHighDensity0303Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 303 from a high density unit
                transitions to the alarm state."
           ::= 30303

           alarmInputHighDensity0303Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 303 from a high density unit 
                transitions to the normal state."
           ::= 40303

           alarmInputHighDensity0304Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 304 from a high density unit
                transitions to the alarm state."
           ::= 30304

           alarmInputHighDensity0304Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 304 from a high density unit 
                transitions to the normal state."
           ::= 40304

           alarmInputHighDensity0305Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 305 from a high density unit
                transitions to the alarm state."
           ::= 30305

           alarmInputHighDensity0305Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 305 from a high density unit 
                transitions to the normal state."
           ::= 40305

           alarmInputHighDensity0306Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 306 from a high density unit
                transitions to the alarm state."
           ::= 30306

           alarmInputHighDensity0306Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 306 from a high density unit 
                transitions to the normal state."
           ::= 40306

           alarmInputHighDensity0307Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 307 from a high density unit
                transitions to the alarm state."
           ::= 30307

           alarmInputHighDensity0307Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 307 from a high density unit 
                transitions to the normal state."
           ::= 40307

           alarmInputHighDensity0308Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 308 from a high density unit
                transitions to the alarm state."
           ::= 30308

           alarmInputHighDensity0308Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 308 from a high density unit 
                transitions to the normal state."
           ::= 40308

           alarmInputHighDensity0309Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 309 from a high density unit
                transitions to the alarm state."
           ::= 30309

           alarmInputHighDensity0309Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 309 from a high density unit 
                transitions to the normal state."
           ::= 40309

           alarmInputHighDensity0310Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 310 from a high density unit
                transitions to the alarm state."
           ::= 30310

           alarmInputHighDensity0310Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 310 from a high density unit 
                transitions to the normal state."
           ::= 40310

           alarmInputHighDensity0311Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 311 from a high density unit
                transitions to the alarm state."
           ::= 30311

           alarmInputHighDensity0311Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 311 from a high density unit 
                transitions to the normal state."
           ::= 40311

           alarmInputHighDensity0312Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 312 from a high density unit
                transitions to the alarm state."
           ::= 30312

           alarmInputHighDensity0312Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 312 from a high density unit 
                transitions to the normal state."
           ::= 40312

           alarmInputHighDensity0313Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 313 from a high density unit
                transitions to the alarm state."
           ::= 30313

           alarmInputHighDensity0313Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 313 from a high density unit 
                transitions to the normal state."
           ::= 40313

           alarmInputHighDensity0314Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 314 from a high density unit
                transitions to the alarm state."
           ::= 30314

           alarmInputHighDensity0314Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 314 from a high density unit 
                transitions to the normal state."
           ::= 40314

           alarmInputHighDensity0315Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 315 from a high density unit
                transitions to the alarm state."
           ::= 30315

           alarmInputHighDensity0315Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 315 from a high density unit 
                transitions to the normal state."
           ::= 40315

           alarmInputHighDensity0316Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 316 from a high density unit
                transitions to the alarm state."
           ::= 30316

           alarmInputHighDensity0316Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 316 from a high density unit 
                transitions to the normal state."
           ::= 40316

           alarmInputHighDensity0317Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 317 from a high density unit
                transitions to the alarm state."
           ::= 30317

           alarmInputHighDensity0317Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 317 from a high density unit 
                transitions to the normal state."
           ::= 40317

           alarmInputHighDensity0318Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 318 from a high density unit
                transitions to the alarm state."
           ::= 30318

           alarmInputHighDensity0318Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 318 from a high density unit 
                transitions to the normal state."
           ::= 40318

           alarmInputHighDensity0319Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 319 from a high density unit
                transitions to the alarm state."
           ::= 30319

           alarmInputHighDensity0319Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 319 from a high density unit 
                transitions to the normal state."
           ::= 40319

           alarmInputHighDensity0320Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 320 from a high density unit
                transitions to the alarm state."
           ::= 30320

           alarmInputHighDensity0320Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 320 from a high density unit 
                transitions to the normal state."
           ::= 40320

           alarmInputHighDensity0321Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 321 from a high density unit
                transitions to the alarm state."
           ::= 30321

           alarmInputHighDensity0321Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 321 from a high density unit 
                transitions to the normal state."
           ::= 40321

           alarmInputHighDensity0322Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 322 from a high density unit
                transitions to the alarm state."
           ::= 30322

           alarmInputHighDensity0322Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 322 from a high density unit 
                transitions to the normal state."
           ::= 40322

           alarmInputHighDensity0323Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 323 from a high density unit
                transitions to the alarm state."
           ::= 30323

           alarmInputHighDensity0323Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 323 from a high density unit 
                transitions to the normal state."
           ::= 40323

           alarmInputHighDensity0324Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 324 from a high density unit
                transitions to the alarm state."
           ::= 30324

           alarmInputHighDensity0324Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 324 from a high density unit 
                transitions to the normal state."
           ::= 40324

           alarmInputHighDensity0325Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 325 from a high density unit
                transitions to the alarm state."
           ::= 30325

           alarmInputHighDensity0325Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 325 from a high density unit 
                transitions to the normal state."
           ::= 40325

           alarmInputHighDensity0326Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 326 from a high density unit
                transitions to the alarm state."
           ::= 30326

           alarmInputHighDensity0326Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 326 from a high density unit 
                transitions to the normal state."
           ::= 40326

           alarmInputHighDensity0327Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 327 from a high density unit
                transitions to the alarm state."
           ::= 30327

           alarmInputHighDensity0327Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 327 from a high density unit 
                transitions to the normal state."
           ::= 40327

           alarmInputHighDensity0328Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 328 from a high density unit
                transitions to the alarm state."
           ::= 30328

           alarmInputHighDensity0328Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 328 from a high density unit 
                transitions to the normal state."
           ::= 40328

           alarmInputHighDensity0329Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 329 from a high density unit
                transitions to the alarm state."
           ::= 30329

           alarmInputHighDensity0329Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 329 from a high density unit 
                transitions to the normal state."
           ::= 40329

           alarmInputHighDensity0330Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 330 from a high density unit
                transitions to the alarm state."
           ::= 30330

           alarmInputHighDensity0330Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 330 from a high density unit 
                transitions to the normal state."
           ::= 40330

           alarmInputHighDensity0331Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 331 from a high density unit
                transitions to the alarm state."
           ::= 30331

           alarmInputHighDensity0331Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 331 from a high density unit 
                transitions to the normal state."
           ::= 40331

           alarmInputHighDensity0332Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 332 from a high density unit
                transitions to the alarm state."
           ::= 30332

           alarmInputHighDensity0332Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 332 from a high density unit 
                transitions to the normal state."
           ::= 40332

           alarmInputHighDensity0333Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 333 from a high density unit
                transitions to the alarm state."
           ::= 30333

           alarmInputHighDensity0333Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 333 from a high density unit 
                transitions to the normal state."
           ::= 40333

           alarmInputHighDensity0334Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 334 from a high density unit
                transitions to the alarm state."
           ::= 30334

           alarmInputHighDensity0334Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 334 from a high density unit 
                transitions to the normal state."
           ::= 40334

           alarmInputHighDensity0335Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 335 from a high density unit
                transitions to the alarm state."
           ::= 30335

           alarmInputHighDensity0335Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 335 from a high density unit 
                transitions to the normal state."
           ::= 40335

           alarmInputHighDensity0336Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 336 from a high density unit
                transitions to the alarm state."
           ::= 30336

           alarmInputHighDensity0336Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 336 from a high density unit 
                transitions to the normal state."
           ::= 40336

           alarmInputHighDensity0337Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 337 from a high density unit
                transitions to the alarm state."
           ::= 30337

           alarmInputHighDensity0337Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 337 from a high density unit 
                transitions to the normal state."
           ::= 40337

           alarmInputHighDensity0338Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 338 from a high density unit
                transitions to the alarm state."
           ::= 30338

           alarmInputHighDensity0338Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 338 from a high density unit 
                transitions to the normal state."
           ::= 40338

           alarmInputHighDensity0339Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 339 from a high density unit
                transitions to the alarm state."
           ::= 30339

           alarmInputHighDensity0339Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 339 from a high density unit 
                transitions to the normal state."
           ::= 40339

           alarmInputHighDensity0340Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 340 from a high density unit
                transitions to the alarm state."
           ::= 30340

           alarmInputHighDensity0340Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 340 from a high density unit 
                transitions to the normal state."
           ::= 40340

           alarmInputHighDensity0341Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 341 from a high density unit
                transitions to the alarm state."
           ::= 30341

           alarmInputHighDensity0341Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 341 from a high density unit 
                transitions to the normal state."
           ::= 40341

           alarmInputHighDensity0342Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 342 from a high density unit
                transitions to the alarm state."
           ::= 30342

           alarmInputHighDensity0342Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 342 from a high density unit 
                transitions to the normal state."
           ::= 40342

           alarmInputHighDensity0343Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 343 from a high density unit
                transitions to the alarm state."
           ::= 30343

           alarmInputHighDensity0343Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 343 from a high density unit 
                transitions to the normal state."
           ::= 40343

           alarmInputHighDensity0344Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 344 from a high density unit
                transitions to the alarm state."
           ::= 30344

           alarmInputHighDensity0344Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 344 from a high density unit 
                transitions to the normal state."
           ::= 40344

           alarmInputHighDensity0345Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 345 from a high density unit
                transitions to the alarm state."
           ::= 30345

           alarmInputHighDensity0345Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 345 from a high density unit 
                transitions to the normal state."
           ::= 40345

           alarmInputHighDensity0346Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 346 from a high density unit
                transitions to the alarm state."
           ::= 30346

           alarmInputHighDensity0346Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 346 from a high density unit 
                transitions to the normal state."
           ::= 40346

           alarmInputHighDensity0347Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 347 from a high density unit
                transitions to the alarm state."
           ::= 30347

           alarmInputHighDensity0347Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 347 from a high density unit 
                transitions to the normal state."
           ::= 40347

           alarmInputHighDensity0348Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 348 from a high density unit
                transitions to the alarm state."
           ::= 30348

           alarmInputHighDensity0348Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 348 from a high density unit 
                transitions to the normal state."
           ::= 40348

           alarmInputHighDensity0349Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 349 from a high density unit
                transitions to the alarm state."
           ::= 30349

           alarmInputHighDensity0349Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 349 from a high density unit 
                transitions to the normal state."
           ::= 40349

           alarmInputHighDensity0350Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 350 from a high density unit
                transitions to the alarm state."
           ::= 30350

           alarmInputHighDensity0350Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 350 from a high density unit 
                transitions to the normal state."
           ::= 40350

           alarmInputHighDensity0351Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 351 from a high density unit
                transitions to the alarm state."
           ::= 30351

           alarmInputHighDensity0351Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 351 from a high density unit 
                transitions to the normal state."
           ::= 40351

           alarmInputHighDensity0352Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 352 from a high density unit
                transitions to the alarm state."
           ::= 30352

           alarmInputHighDensity0352Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 352 from a high density unit 
                transitions to the normal state."
           ::= 40352

           alarmInputHighDensity0353Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 353 from a high density unit
                transitions to the alarm state."
           ::= 30353

           alarmInputHighDensity0353Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 353 from a high density unit 
                transitions to the normal state."
           ::= 40353

           alarmInputHighDensity0354Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 354 from a high density unit
                transitions to the alarm state."
           ::= 30354

           alarmInputHighDensity0354Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 354 from a high density unit 
                transitions to the normal state."
           ::= 40354

           alarmInputHighDensity0355Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 355 from a high density unit
                transitions to the alarm state."
           ::= 30355

           alarmInputHighDensity0355Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 355 from a high density unit 
                transitions to the normal state."
           ::= 40355

           alarmInputHighDensity0356Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 356 from a high density unit
                transitions to the alarm state."
           ::= 30356

           alarmInputHighDensity0356Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 356 from a high density unit 
                transitions to the normal state."
           ::= 40356

           alarmInputHighDensity0357Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 357 from a high density unit
                transitions to the alarm state."
           ::= 30357

           alarmInputHighDensity0357Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 357 from a high density unit 
                transitions to the normal state."
           ::= 40357

           alarmInputHighDensity0358Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 358 from a high density unit
                transitions to the alarm state."
           ::= 30358

           alarmInputHighDensity0358Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 358 from a high density unit 
                transitions to the normal state."
           ::= 40358

           alarmInputHighDensity0359Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 359 from a high density unit
                transitions to the alarm state."
           ::= 30359

           alarmInputHighDensity0359Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 359 from a high density unit 
                transitions to the normal state."
           ::= 40359

           alarmInputHighDensity0360Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 360 from a high density unit
                transitions to the alarm state."
           ::= 30360

           alarmInputHighDensity0360Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 360 from a high density unit 
                transitions to the normal state."
           ::= 40360

           alarmInputHighDensity0361Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 361 from a high density unit
                transitions to the alarm state."
           ::= 30361

           alarmInputHighDensity0361Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 361 from a high density unit 
                transitions to the normal state."
           ::= 40361

           alarmInputHighDensity0362Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 362 from a high density unit
                transitions to the alarm state."
           ::= 30362

           alarmInputHighDensity0362Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 362 from a high density unit 
                transitions to the normal state."
           ::= 40362

           alarmInputHighDensity0363Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 363 from a high density unit
                transitions to the alarm state."
           ::= 30363

           alarmInputHighDensity0363Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 363 from a high density unit 
                transitions to the normal state."
           ::= 40363

           alarmInputHighDensity0364Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 364 from a high density unit
                transitions to the alarm state."
           ::= 30364

           alarmInputHighDensity0364Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 364 from a high density unit 
                transitions to the normal state."
           ::= 40364

           alarmInputHighDensity0365Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 365 from a high density unit
                transitions to the alarm state."
           ::= 30365

           alarmInputHighDensity0365Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 365 from a high density unit 
                transitions to the normal state."
           ::= 40365

           alarmInputHighDensity0366Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 366 from a high density unit
                transitions to the alarm state."
           ::= 30366

           alarmInputHighDensity0366Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 366 from a high density unit 
                transitions to the normal state."
           ::= 40366

           alarmInputHighDensity0367Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 367 from a high density unit
                transitions to the alarm state."
           ::= 30367

           alarmInputHighDensity0367Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 367 from a high density unit 
                transitions to the normal state."
           ::= 40367

           alarmInputHighDensity0368Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 368 from a high density unit
                transitions to the alarm state."
           ::= 30368

           alarmInputHighDensity0368Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 368 from a high density unit 
                transitions to the normal state."
           ::= 40368

           alarmInputHighDensity0369Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 369 from a high density unit
                transitions to the alarm state."
           ::= 30369

           alarmInputHighDensity0369Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 369 from a high density unit 
                transitions to the normal state."
           ::= 40369

           alarmInputHighDensity0370Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 370 from a high density unit
                transitions to the alarm state."
           ::= 30370

           alarmInputHighDensity0370Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 370 from a high density unit 
                transitions to the normal state."
           ::= 40370

           alarmInputHighDensity0371Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 371 from a high density unit
                transitions to the alarm state."
           ::= 30371

           alarmInputHighDensity0371Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 371 from a high density unit 
                transitions to the normal state."
           ::= 40371

           alarmInputHighDensity0372Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 372 from a high density unit
                transitions to the alarm state."
           ::= 30372

           alarmInputHighDensity0372Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 372 from a high density unit 
                transitions to the normal state."
           ::= 40372

           alarmInputHighDensity0373Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 373 from a high density unit
                transitions to the alarm state."
           ::= 30373

           alarmInputHighDensity0373Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 373 from a high density unit 
                transitions to the normal state."
           ::= 40373

           alarmInputHighDensity0374Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 374 from a high density unit
                transitions to the alarm state."
           ::= 30374

           alarmInputHighDensity0374Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 374 from a high density unit 
                transitions to the normal state."
           ::= 40374

           alarmInputHighDensity0375Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 375 from a high density unit
                transitions to the alarm state."
           ::= 30375

           alarmInputHighDensity0375Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 375 from a high density unit 
                transitions to the normal state."
           ::= 40375

           alarmInputHighDensity0376Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 376 from a high density unit
                transitions to the alarm state."
           ::= 30376

           alarmInputHighDensity0376Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 376 from a high density unit 
                transitions to the normal state."
           ::= 40376

           alarmInputHighDensity0377Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 377 from a high density unit
                transitions to the alarm state."
           ::= 30377

           alarmInputHighDensity0377Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 377 from a high density unit 
                transitions to the normal state."
           ::= 40377

           alarmInputHighDensity0378Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 378 from a high density unit
                transitions to the alarm state."
           ::= 30378

           alarmInputHighDensity0378Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 378 from a high density unit 
                transitions to the normal state."
           ::= 40378

           alarmInputHighDensity0379Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 379 from a high density unit
                transitions to the alarm state."
           ::= 30379

           alarmInputHighDensity0379Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 379 from a high density unit 
                transitions to the normal state."
           ::= 40379

           alarmInputHighDensity0380Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 380 from a high density unit
                transitions to the alarm state."
           ::= 30380

           alarmInputHighDensity0380Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 380 from a high density unit 
                transitions to the normal state."
           ::= 40380

           alarmInputHighDensity0381Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 381 from a high density unit
                transitions to the alarm state."
           ::= 30381

           alarmInputHighDensity0381Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 381 from a high density unit 
                transitions to the normal state."
           ::= 40381

           alarmInputHighDensity0382Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 382 from a high density unit
                transitions to the alarm state."
           ::= 30382

           alarmInputHighDensity0382Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 382 from a high density unit 
                transitions to the normal state."
           ::= 40382

           alarmInputHighDensity0383Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 383 from a high density unit
                transitions to the alarm state."
           ::= 30383

           alarmInputHighDensity0383Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 383 from a high density unit 
                transitions to the normal state."
           ::= 40383

           alarmInputHighDensity0384Alarm TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 384 from a high density unit
                transitions to the alarm state."
           ::= 30384

           alarmInputHighDensity0384Normal TRAP-TYPE
           ENTERPRISE mrvInReachProductDivision
           VARIABLES {
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 384 from a high density unit 
                transitions to the normal state."
           ::= 40384

END
