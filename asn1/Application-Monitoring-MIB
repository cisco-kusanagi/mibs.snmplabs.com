-->#
--># Copyright (C) Siemens AG 1998
-->#               All rights reserved
-->#
-->#protocol specification
-->%PROTOCOL SNMP
-->#
-->#configuration
-->%REMCONFIG NO
-->%REMOPERATION NO
-->#
-->#
--># Copyright (C) Siemens AG 1998
-->#               All rights reserved
-->#
-->#protocol specification
-->%PROTOCOL SNMP
-->#
-->#configuration
-->%REMCONFIG NO
-->%REMOPERATION NO
-->#
 
Application-Monitoring-MIB DEFINITIONS ::= BEGIN
 
--
-- Title:   MIB for the BS2000 Application Monitoring
--
-- Date:    Oct. 1999
-- Author:  Birgit Lamers        BS2000 DC3
-- Reason:  New subtrees sniAppMonJVs and sniAppMonObjects 
--
-- Date:    Jan.  1999
-- Author:  Birgit Lamers        BS2000 DC3
-- Reason:  appmon-sx (new subtrees appMonLogfiles and appMonTraps)
--
-- Date:    July 1998
-- Author:  Birgit Lamers        BS2000 DC3
-- Reason:  New subtree sniAppMonDcamAppl
--
-- Date:    Nov. 1996
-- Author:  Birgit Lamers        BS2000 DC3
-- Reason:  New Objects appMonVersion and appMonConfFile
--
-- Date:    June, 1996
-- Authors: Birgit Lamers        BS2000 DC3
--          Reinhard Unterstein  BS2000 OS45
--
 
 
IMPORTS
	TRAP-TYPE FROM RFC-1215
        enterprises
            FROM RFC1155-SMI
        DisplayString
            FROM RFC1213-MIB
        OBJECT-TYPE
            FROM RFC-1212;
 
 
sni                        OBJECT IDENTIFIER ::= { enterprises 231 }
sniProductMibs             OBJECT IDENTIFIER ::= { sni 2 }
sniAppMon                  OBJECT IDENTIFIER ::= { sniProductMibs 23 }
sniAppMonSubSystems        OBJECT IDENTIFIER ::= { sniAppMon 1 }
sniAppMonBcamAppl          OBJECT IDENTIFIER ::= { sniAppMon 2 }
sniAppMonUserAppl          OBJECT IDENTIFIER ::= { sniAppMon 3 }
-- appConsMon              OBJECT IDENTIFIER ::= { sniAppMon 4 }
sniAppMonGlobalData        OBJECT IDENTIFIER ::= { sniAppMon 5 }
sniAppMonDcamAppl          OBJECT IDENTIFIER ::= { sniAppMon 6 }
appMonLogfiles             OBJECT IDENTIFIER ::= { sniAppMon 7 }
sniAppMonJVs               OBJECT IDENTIFIER ::= { sniAppMon 8 }
sniAppMonObjects           OBJECT IDENTIFIER ::= { sniAppMon 9 }
appMonTraps                OBJECT IDENTIFIER ::= { sniAppMon 20 }
 
 
--
-- Subsystem Infos
--
 
appMonSubsysTabNum             OBJECT-TYPE
        SYNTAX  INTEGER
        ACCESS  read-only
        STATUS  mandatory
        DESCRIPTION "The number of entries in the table appMonSubsysTable"
        ::= {sniAppMonSubSystems 1}
 
appMonSubsysTable           OBJECT-TYPE
        SYNTAX  SEQUENCE OF AppMonSubsysEntry
        ACCESS  not-accessible
        STATUS  mandatory
        DESCRIPTION "The Subsystem information table"
        ::= {sniAppMonSubSystems 2}
 
appMonSubsysEntry        OBJECT-TYPE
        SYNTAX  AppMonSubsysEntry
        ACCESS  not-accessible
        STATUS  mandatory
        DESCRIPTION "An entry in the table"
        INDEX {appMonSubsysIndex}
        ::= {appMonSubsysTable 1}
 
 
AppMonSubsysEntry ::=
        SEQUENCE 
        {
            appMonSubsysIndex                   INTEGER,
            appMonSubsysName                    DisplayString,
            appMonSubsysVersion                 DisplayString,
            appMonSubsysState                   INTEGER,
            appMonSubsysTasks                   INTEGER
        }
 
appMonSubsysIndex   OBJECT-TYPE
        SYNTAX  INTEGER
        ACCESS  read-only
        STATUS  mandatory
        DESCRIPTION "A unique value for each entry, its value
                     ranges between 1 and the value of appMonSubsysTabNum"
        ::= {appMonSubsysEntry 1}
 
appMonSubsysName       OBJECT-TYPE
        SYNTAX  DisplayString
        ACCESS  read-only
        STATUS  mandatory
        DESCRIPTION "The name of the subsystem"
        ::= {appMonSubsysEntry 2}
 
appMonSubsysVersion       OBJECT-TYPE
        SYNTAX  DisplayString
        ACCESS  read-only
        STATUS  mandatory
        DESCRIPTION "The current version of the subsystem"
        ::= {appMonSubsysEntry 3}
 
appMonSubsysState       OBJECT-TYPE
        SYNTAX  INTEGER
        {
                 created       (1),
                 not-created   (2),
                 in-delete     (3),
                 in-create     (4),
                 in-resume     (5),
                 in-hold       (6),
                 not-resumed   (7),
                 locked        (8),
                 unknown       (255)
        }
        ACCESS  read-only
        STATUS  mandatory
        DESCRIPTION "The current state of the subsystem"
        ::= {appMonSubsysEntry 4}
 
appMonSubsysTasks       OBJECT-TYPE
        SYNTAX  INTEGER
        ACCESS  read-only
        STATUS  mandatory
        DESCRIPTION "Number of tasks connected to the subsystem"
        ::= {appMonSubsysEntry 5}
 
--
-- BCAM Application Infos
--
 
appMonBcamApplTabNum             OBJECT-TYPE
        SYNTAX  INTEGER
        ACCESS  read-only
        STATUS  mandatory
        DESCRIPTION "The number of entries in the table appMonTable"
        ::= {sniAppMonBcamAppl 1}
 
appMonBcamApplTable           OBJECT-TYPE
        SYNTAX  SEQUENCE OF AppMonBcamApplEntry
        ACCESS  not-accessible
        STATUS  mandatory
        DESCRIPTION "The BCAM Application information table"
        ::= {sniAppMonBcamAppl 2}
 
 
appMonBcamApplEntry        OBJECT-TYPE
        SYNTAX  AppMonBcamApplEntry
        ACCESS  not-accessible
        STATUS  mandatory
        DESCRIPTION "An entry in the table"
        INDEX {appMonBcamApplIndex}
        ::= {appMonBcamApplTable 1}
 
AppMonBcamApplEntry ::=
        SEQUENCE 
        {
            appMonBcamApplIndex                   INTEGER,
            appMonBcamApplName                    DisplayString,
            appMonBcamApplVersion                 DisplayString,
            appMonBcamApplState                   INTEGER,
            appMonBcamApplMonJV                   DisplayString
        }
 
appMonBcamApplIndex   OBJECT-TYPE
        SYNTAX  INTEGER
        ACCESS  read-only
        STATUS  mandatory
        DESCRIPTION "A unique value for each entry, its value
                     ranges between 1 and the value of appMonBcamApplTabNum"
        ::= {appMonBcamApplEntry 1}
 
appMonBcamApplName       OBJECT-TYPE
        SYNTAX  DisplayString
        ACCESS  read-only
        STATUS  mandatory
        DESCRIPTION "The name of the BCAM application"
        ::= {appMonBcamApplEntry 2}
 
appMonBcamApplVersion       OBJECT-TYPE
        SYNTAX  DisplayString
        ACCESS  read-only
        STATUS  mandatory
        DESCRIPTION "The current version of the BCAM application"
        ::= {appMonBcamApplEntry 3}
 
appMonBcamApplState       OBJECT-TYPE
        SYNTAX  INTEGER
        {
                 running     (1),
                 terminated  (2),
                 aborted     (3),
                 loaded      (4),
                 in-hold     (5),
                 scheduled   (6),
                 unknown     (255)
        }
        ACCESS  read-only
        STATUS  mandatory
        DESCRIPTION "The current state of the BCAM application"
        ::= {appMonBcamApplEntry 4}
 
appMonBcamApplMonJV      OBJECT-TYPE
        SYNTAX  DisplayString
        ACCESS  read-only
        STATUS  mandatory
        DESCRIPTION "Name of the MONJV monitoring the application"
        ::= {appMonBcamApplEntry 5}
 
 
--
-- User Application Infos
--
 
appMonUserApplTabNum             OBJECT-TYPE
        SYNTAX  INTEGER
        ACCESS  read-only
        STATUS  mandatory
        DESCRIPTION "The number of entries in the table appMonTable"
        ::= {sniAppMonUserAppl 1}
 
appMonUserApplTable           OBJECT-TYPE
        SYNTAX  SEQUENCE OF AppMonUserApplEntry
        ACCESS  not-accessible
        STATUS  mandatory
        DESCRIPTION "The User Application information table"
        ::= {sniAppMonUserAppl 2}
 
appMonUserApplEntry        OBJECT-TYPE
        SYNTAX  AppMonUserApplEntry
        ACCESS  not-accessible
        STATUS  mandatory
        DESCRIPTION "An entry in the table"
        INDEX {appMonUserApplIndex}
        ::= {appMonUserApplTable 1}
 
AppMonUserApplEntry ::=
        SEQUENCE 
        {
            appMonUserApplIndex                   INTEGER,
            appMonUserApplName                    DisplayString,
            appMonUserApplVersion                 DisplayString,
            appMonUserApplState                   INTEGER,
            appMonUserApplMonJV                   DisplayString
        }
 
appMonUserApplIndex   OBJECT-TYPE
        SYNTAX  INTEGER
        ACCESS  read-only
        STATUS  mandatory
        DESCRIPTION "A unique value for each entry, its value
                     ranges between 1 and the value of appMonUserApplTabNum"
        ::= {appMonUserApplEntry 1}
 
appMonUserApplName       OBJECT-TYPE
        SYNTAX  DisplayString
        ACCESS  read-only
        STATUS  mandatory
        DESCRIPTION "The name of the User application"
        ::= {appMonUserApplEntry 2}
 
appMonUserApplVersion       OBJECT-TYPE
        SYNTAX  DisplayString
        ACCESS  read-only
        STATUS  mandatory
        DESCRIPTION "The current version of the User application"
        ::= {appMonUserApplEntry 3}
 
appMonUserApplState       OBJECT-TYPE
        SYNTAX  INTEGER
        {
                 running     (1),
                 terminated  (2),
                 aborted     (3),
                 loaded      (4),
                 in-hold     (5),
                 scheduled   (6),
                 unknown     (255)
        }
        ACCESS  read-only
        STATUS  mandatory
        DESCRIPTION "The current state of the User application"
        ::= {appMonUserApplEntry 4}
 
appMonUserApplMonJV      OBJECT-TYPE
        SYNTAX  DisplayString
        ACCESS  read-only
        STATUS  mandatory
        DESCRIPTION "Name of the MONJV monitoring the application"
        ::= {appMonUserApplEntry 5}
 
 
appMonVersion             OBJECT-TYPE
        SYNTAX  DisplayString
        ACCESS  read-only
        STATUS  mandatory
        DESCRIPTION "Version of application monitor"
        ::= {sniAppMonGlobalData 1}
 
 
appMonConfFile            OBJECT-TYPE
        SYNTAX  DisplayString
        ACCESS  read-write
        STATUS  mandatory
        DESCRIPTION "Pathname of the configuration file"
        ::= {sniAppMonGlobalData 2}
 
appMonTrapFormat          OBJECT-TYPE
        SYNTAX  INTEGER
        {
                 generic     (1),
                 tv-cc       (2),
                 all         (3)
        }
        ACCESS  read-write
        STATUS  mandatory
        DESCRIPTION "Format of trap"
        ::= {sniAppMonGlobalData 3}
 
--
-- DCAM Application Infos
--
 
appMonDcamApplTabNum             OBJECT-TYPE
        SYNTAX  INTEGER
        ACCESS  read-only
        STATUS  mandatory
        DESCRIPTION "The number of entries in the table appMonDcamApplTable"
        ::= {sniAppMonDcamAppl 1}
 
appMonDcamApplTable           OBJECT-TYPE
        SYNTAX  SEQUENCE OF AppMonDcamApplEntry
        ACCESS  not-accessible
        STATUS  mandatory
        DESCRIPTION "The DCAM Application information table"
        ::= {sniAppMonDcamAppl 2}
 
 
appMonDcamApplEntry        OBJECT-TYPE
        SYNTAX  AppMonDcamApplEntry
        ACCESS  not-accessible
        STATUS  mandatory
        DESCRIPTION "An entry in the table"
        INDEX {appMonDcamApplIndex}
        ::= {appMonDcamApplTable 1}
 
AppMonDcamApplEntry ::=
        SEQUENCE 
        {
            appMonDcamApplIndex                   INTEGER,
            appMonDcamApplName                    DisplayString,
            appMonDcamApplHost                    DisplayString,
            appMonDcamApplState                   INTEGER
        }
 
appMonDcamApplIndex   OBJECT-TYPE
        SYNTAX  INTEGER
        ACCESS  read-only
        STATUS  mandatory
        DESCRIPTION "A unique value for each entry, its value
                     ranges between 1 and the value of appMonDcamApplTabNum"
        ::= {appMonDcamApplEntry 1}
 
appMonDcamApplName       OBJECT-TYPE
        SYNTAX  DisplayString
        ACCESS  read-only
        STATUS  mandatory
        DESCRIPTION "The name of the DCAM application"
        ::= {appMonDcamApplEntry 2}
 
appMonDcamApplHost OBJECT-TYPE
        SYNTAX  DisplayString
        ACCESS  read-only
        STATUS  mandatory
        DESCRIPTION "The host on which the DCAM application is running"
        ::= {appMonDcamApplEntry 3}
 
appMonDcamApplState       OBJECT-TYPE
        SYNTAX  INTEGER
        {
                 running     (1),
                 terminated  (2),
                 unknown     (255)
        }
        ACCESS  read-only
        STATUS  mandatory
        DESCRIPTION "The current state of the DCAM application"
        ::= {appMonDcamApplEntry 4}
 
--
-- Logfiles
--
 
appMonLogfTabNum          OBJECT-TYPE
        SYNTAX  INTEGER
        ACCESS  read-only
        STATUS  mandatory
        DESCRIPTION "The number of entries in the table appMonLogfTable"
        ::= {appMonLogfiles 1}
 
 
appMonLogfTable           OBJECT-TYPE
        SYNTAX  SEQUENCE OF AppMonLogfEntry
        ACCESS  not-accessible
        STATUS  mandatory
        DESCRIPTION "The Logfile table"
        ::= {appMonLogfiles 2}
 
appMonLogfEntry        OBJECT-TYPE
        SYNTAX  AppMonLogfEntry
        ACCESS  not-accessible
        STATUS  mandatory
        DESCRIPTION "An entry in the table"
        INDEX {appMonLogfName }
        ::= {appMonLogfTable 1}
 
 
AppMonLogfEntry ::=
        SEQUENCE 
        {
            appMonLogfName                    DisplayString,
            appMonLogfAppl                    DisplayString,
            appMonLogfState                   INTEGER,
            appMonLogfPattern                 DisplayString
        }
 
appMonLogfName       OBJECT-TYPE
        SYNTAX  DisplayString
        ACCESS  read-only
        STATUS  mandatory
        DESCRIPTION "Pathname of the logfile"
        ::= {appMonLogfEntry 1}
 
appMonLogfAppl          OBJECT-TYPE
        SYNTAX  DisplayString
        ACCESS  read-only
        STATUS  mandatory
        DESCRIPTION "The application name"
        ::= {appMonLogfEntry 2}
 
appMonLogfState       OBJECT-TYPE
        SYNTAX  INTEGER
        {
                 deactive      (1),
                 active        (2),
                 start-begin   (3),
                 start-new     (4),
                 start-end     (5)
        }
        ACCESS  read-write
        STATUS  mandatory
        DESCRIPTION "The current monitoring state of the logfile
          is either active or deactive. For write operation either
          start-begin, start-new, start-end or deactive has to be
          specified"
        ::= {appMonLogfEntry 3}
 
appMonLogfPattern OBJECT-TYPE
        SYNTAX  DisplayString
        ACCESS  read-only
        STATUS  mandatory
        DESCRIPTION "Pattern for which a trap is generated "
        ::= {appMonLogfEntry 4}
 
--
-- JV Infos
--
 
appMonJVTabNum             OBJECT-TYPE
        SYNTAX  INTEGER
        ACCESS  read-only
        STATUS  mandatory
        DESCRIPTION "The number of entries in the table appMonJVTable"
        ::= {sniAppMonJVs 1}
 
appMonJVTable           OBJECT-TYPE
        SYNTAX  SEQUENCE OF AppMonJVEntry
        ACCESS  not-accessible
        STATUS  mandatory
        DESCRIPTION "The BCAM Application information table"
        ::= {sniAppMonJVs 2}
 
 
appMonJVEntry        OBJECT-TYPE
        SYNTAX  AppMonJVEntry
        ACCESS  not-accessible
        STATUS  mandatory
        DESCRIPTION "An entry in the table"
        INDEX {appMonJVName}
        ::= {appMonJVTable 1}
 
AppMonJVEntry ::=
        SEQUENCE 
        {
            appMonJVName                    DisplayString,
            appMonJVAppl                    DisplayString,
            appMonJVValue                   DisplayString,
            appMonJVPattern                 DisplayString
        }
 
appMonJVName       OBJECT-TYPE
        SYNTAX  DisplayString
        ACCESS  read-only
        STATUS  mandatory
        DESCRIPTION "Name of the JV"
        ::= {appMonJVEntry 1}
 
appMonJVAppl          OBJECT-TYPE
        SYNTAX  DisplayString
        ACCESS  read-only
        STATUS  mandatory
        DESCRIPTION "The application name"
        ::= {appMonJVEntry 2}
 
appMonJVValue       OBJECT-TYPE
        SYNTAX  DisplayString
        ACCESS  read-only
        STATUS  mandatory
        DESCRIPTION "The current value of the JV"
        ::= {appMonJVEntry 3}
 
appMonJVPattern    OBJECT-TYPE
        SYNTAX  DisplayString
        ACCESS  read-only
        STATUS  mandatory
        DESCRIPTION "Value pattern for which a trap will be sent"
        ::= {appMonJVEntry 4}
--
-- Object Infos
--
 
appMonObjectsTabNum             OBJECT-TYPE
        SYNTAX  INTEGER
        ACCESS  read-only
        STATUS  mandatory
        DESCRIPTION "The number of entries in the table appMonObjectTable"
        ::= {sniAppMonObjects 1}
 
appMonObjectTable           OBJECT-TYPE
        SYNTAX  SEQUENCE OF AppMonObjectEntry
        ACCESS  not-accessible
        STATUS  mandatory
        DESCRIPTION "The Object table"
        ::= {sniAppMonObjects 2}
 
 
appMonObjectEntry        OBJECT-TYPE
        SYNTAX  AppMonObjectEntry
        ACCESS  not-accessible
        STATUS  mandatory
        DESCRIPTION "An entry in the table"
        INDEX {appMonObjectIndex}
        ::= {appMonObjectTable 1}
 
AppMonObjectEntry ::=
        SEQUENCE 
        {
            appMonObjectIndex                   INTEGER,
            appMonObjectName                    DisplayString,
            appMonObjectBcamAppl                DisplayString,
            appMonObjectUserAppl                DisplayString,
            appMonObjectDcamAppl                DisplayString,
            appMonObjectSub                     DisplayString,
            appMonObjectLogfile                 DisplayString,
            appMonObjectJV                      DisplayString 
        }
 
appMonObjectIndex   OBJECT-TYPE
        SYNTAX  INTEGER
        ACCESS  read-only
        STATUS  mandatory
        DESCRIPTION "A unique value for each entry, its value
                     ranges between 1 and the value of appMonObjectTabNum"
        ::= {appMonObjectEntry 1}
 
appMonObjectName       OBJECT-TYPE
        SYNTAX  DisplayString
        ACCESS  read-only
        STATUS  mandatory
        DESCRIPTION "The name of the object"
        ::= {appMonObjectEntry 2}
 
appMonObjectBcamAppl   OBJECT-TYPE
        SYNTAX  DisplayString
        ACCESS  read-only
        STATUS  mandatory
        DESCRIPTION "Name of the BCAM applications belonging to the object"
        ::= {appMonObjectEntry 3}
 
appMonObjectUserAppl   OBJECT-TYPE
        SYNTAX  DisplayString
        ACCESS  read-only
        STATUS  mandatory
        DESCRIPTION "Name of the user applications belonging to the object"
        ::= {appMonObjectEntry 4}
 
appMonObjectDcamAppl   OBJECT-TYPE
        SYNTAX  DisplayString
        ACCESS  read-only
        STATUS  mandatory
        DESCRIPTION "Name of the DCAM applications belonging to the object"
        ::= {appMonObjectEntry 5}
 
appMonObjectSub   OBJECT-TYPE
        SYNTAX  DisplayString
        ACCESS  read-only
        STATUS  mandatory
        DESCRIPTION "Name of the subsystems belonging to the object"
        ::= {appMonObjectEntry 6}
 
appMonObjectLogfile   OBJECT-TYPE
        SYNTAX  DisplayString
        ACCESS  read-only
        STATUS  mandatory
        DESCRIPTION "Name of the logfiles belonging to the object"
        ::= {appMonObjectEntry 7}
 
appMonObjectJV   OBJECT-TYPE
        SYNTAX  DisplayString
        ACCESS  read-only
        STATUS  mandatory
        DESCRIPTION "Name of the JVs belonging to the object"
        ::= {appMonObjectEntry 8}
 
--
-- Application Monitor Trap
--
 
appMonTrapData      OBJECT IDENTIFIER ::= {appMonTraps 1}
 
appMonSource    OBJECT-TYPE
        SYNTAX  DisplayString
        ACCESS  not-accessible
        STATUS  mandatory
        DESCRIPTION "  "
        ::= {appMonTrapData 1}
 
appMonDevice    OBJECT-TYPE
        SYNTAX  DisplayString
        ACCESS  not-accessible
        STATUS  mandatory
        DESCRIPTION "  "
        ::= {appMonTrapData 2}
 
appMonMsg       OBJECT-TYPE
        SYNTAX  DisplayString
        ACCESS  not-accessible
        STATUS  mandatory
        DESCRIPTION "  "
        ::= {appMonTrapData 3}
 
appMonWeight    OBJECT-TYPE
        SYNTAX  INTEGER
        ACCESS  not-accessible
        STATUS  mandatory
        DESCRIPTION "  "
        ::= {appMonTrapData 4}
 
appMonAckOID    OBJECT-TYPE
        SYNTAX  OBJECT IDENTIFIER
        ACCESS  not-accessible
        STATUS  mandatory
        DESCRIPTION "  "
        ::= {appMonTrapData 6}
 
appMonGeneric      OBJECT IDENTIFIER ::= {appMonTraps 2}
appMonConfirm      OBJECT IDENTIFIER ::= {appMonTraps 3}
 
appMonGenTrap     TRAP-TYPE
              ENTERPRISE appMonGeneric
              VARIABLES { appMonSource, appMonDevice, appMonMsg, 
                          appMonWeight }
              DESCRIPTION "General application trap" 
      ::= 999
 
appMonConfirmTrap     TRAP-TYPE 
              ENTERPRISE appMonConfirm
              VARIABLES { appMonSource, appMonDevice, appMonMsg,   
                          appMonWeight }
              DESCRIPTION "General application trap, the trap must 
                           be confirmed"                           
      ::= 999                                                      
 
END
