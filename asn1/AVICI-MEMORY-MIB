AVICI-MEMORY-MIB DEFINITIONS ::= BEGIN

    IMPORTS
        MODULE-IDENTITY, OBJECT-TYPE, Unsigned32
            FROM SNMPv2-SMI 
        MODULE-COMPLIANCE, OBJECT-GROUP
            FROM SNMPv2-CONF
        aviciMibs
            FROM AVICI-SMI
        aviciSysInventoryId
            FROM AVICI-SYSTEM-MIB;
    
aviciMemoryMIB MODULE-IDENTITY
        LAST-UPDATED "000907121500Z"
        ORGANIZATION "Avici Systems Inc"
        CONTACT-INFO "        
                  Avici Systems, Inc.
                  101 Billerica Avenue
                  North Billerica, MA 01862-1256
 
                  (978) 964-2000
                  (978) 964-2100 (fax)
 
                  snmp@avici.com"
        DESCRIPTION
            "Initial version of the MIB module for Avici memory."
        REVISION      "000907121500Z"
        DESCRIPTION
            "Changed mib arcs."
        ::= { aviciMibs 6 }

aviciMemoryObjects       OBJECT IDENTIFIER ::= { aviciMemoryMIB 1 }

--  the Platform Memory Table
--
--  This table contains memory attributes for each Avici platform type - 
--  server, module, or bay
-- 

aviciPlatformMemoryTable        OBJECT-TYPE
        SYNTAX      SEQUENCE OF AviciPlatformMemoryEntry
        MAX-ACCESS  not-accessible
        STATUS      current
        DESCRIPTION
            "This table contains memory attributes for a platform - server,
             module, bay"
        ::= { aviciMemoryObjects 1 }
    
aviciPlatformMemoryEntry        OBJECT-TYPE
        SYNTAX      AviciPlatformMemoryEntry
        MAX-ACCESS  not-accessible
        STATUS      current
        DESCRIPTION
            "An entry containing global memory attributes for a platform"
        INDEX       { aviciSysInventoryId }
        ::= { aviciPlatformMemoryTable 1 }
    
AviciPlatformMemoryEntry ::= SEQUENCE {
        aviciPlatformMemoryTotal                 Unsigned32,
        aviciPlatformMemoryUsed                  Unsigned32,
        aviciPlatformMemoryFree                  Unsigned32,
        aviciPlatformMemoryFreePages             Unsigned32,
        aviciPlatformMemoryPageSize              Unsigned32,
        aviciPlatformMemoryLargestFree           Unsigned32
       }

aviciPlatformMemoryTotal        OBJECT-TYPE
        SYNTAX      Unsigned32
        MAX-ACCESS  read-only
        STATUS      current
        DESCRIPTION
            "The total amount of memory in bytes on this platform."
        ::= { aviciPlatformMemoryEntry 1 }
     
aviciPlatformMemoryUsed        OBJECT-TYPE
        SYNTAX      Unsigned32
        MAX-ACCESS  read-only
        STATUS      current
        DESCRIPTION
            "The amount of memory in bytes allocated on this platform."
        ::= { aviciPlatformMemoryEntry 2 }

aviciPlatformMemoryFree        OBJECT-TYPE
        SYNTAX      Unsigned32
        MAX-ACCESS  read-only
        STATUS      current
        DESCRIPTION
            "The amount of memory in bytes available for use on this
             platform."
        ::= { aviciPlatformMemoryEntry 3 }

aviciPlatformMemoryFreePages  OBJECT-TYPE
        SYNTAX      Unsigned32
        MAX-ACCESS  read-only
        STATUS      current
        DESCRIPTION
            "The amount of memory in pages available for use on this
             platform."
        ::= { aviciPlatformMemoryEntry 4 }

aviciPlatformMemoryPageSize  OBJECT-TYPE
        SYNTAX      Unsigned32
        MAX-ACCESS  read-only
        STATUS      current
        DESCRIPTION
            "The size of a page in bytes on this platform."
        ::= { aviciPlatformMemoryEntry 5 }
       
  
aviciPlatformMemoryLargestFree        OBJECT-TYPE
        SYNTAX      Unsigned32
        MAX-ACCESS  read-only
        STATUS      current
        DESCRIPTION
            "The amount of memory in bytes of the largest block of 
             memory available for use on this platform."
        ::= { aviciPlatformMemoryEntry 6 }

--
-- Conformance Information
--    

aviciMemoryMIBConformance OBJECT IDENTIFIER ::= { aviciMemoryMIB 2 }
aviciMemoryMIBCompliances OBJECT IDENTIFIER ::= { aviciMemoryMIBConformance 1 }
aviciMemoryMIBGroups OBJECT IDENTIFIER ::= { aviciMemoryMIBConformance 2 }

aviciMemoryMIBCompliance MODULE-COMPLIANCE
        STATUS current
        DESCRIPTION
            "The compliance statement for aviciMemory."
        MODULE
        MANDATORY-GROUPS {
            aviciMemoryGroup
        }
        ::= { aviciMemoryMIBCompliances 1 }

aviciMemoryGroup OBJECT-GROUP
        OBJECTS {
            aviciPlatformMemoryTotal,
            aviciPlatformMemoryUsed,
            aviciPlatformMemoryFree,
            aviciPlatformMemoryFreePages,
            aviciPlatformMemoryPageSize,
            aviciPlatformMemoryLargestFree
        }
        STATUS     current
        DESCRIPTION
            "Objects for memory statistics."
        ::= { aviciMemoryMIBGroups 1 }

END
