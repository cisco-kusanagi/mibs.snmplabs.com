PANDATEL-GMF-MODEM-MIB DEFINITIONS ::= BEGIN

 -- This is the private mib group section for the GM-F modems.
 -- Because these modems must be installed in the PANDATEL modem rack
 -- the PANDATEL-MODEM-MIB also applies.

 -- Ver.1.06    Sep.13.1999

        IMPORTS
                enterprises, Gauge
                        FROM RFC1155-SMI
                DisplayString
                        FROM RFC1213-MIB
                OBJECT-TYPE
                        FROM RFC-1212
                mdmSpecifics, device-id
                        FROM PANDATEL-MODEM-MIB;

-- ********************** THE MDM-GMF SUBTREE ******************************

-- the specific identifier is identical to the modem type integer
-- of the GM-F modem entries in the PANDATEL-MODEM-MIB mdmModemTable.

gmf-modem      OBJECT IDENTIFIER ::= { device-id 202 }     -- chassis-mib

gmf            OBJECT IDENTIFIER ::= { mdmSpecifics 202 }  -- this subtree

gmfModemTable OBJECT-TYPE
        SYNTAX  SEQUENCE OF GmfTableEntry
        ACCESS  not-accessible
        STATUS  mandatory
        DESCRIPTION
                "This table contains information about all GM-F converters in all racks."
        ::= { gmf 1 }

gmfTableEntry OBJECT-TYPE
        SYNTAX  GmfTableEntry
        ACCESS  not-accessible
        STATUS  mandatory
        DESCRIPTION
                "The index of the table."
        INDEX   { mdmRack, mdmModem, mdmPosition }
        ::= { gmfModemTable 1 }

GmfTableEntry ::= SEQUENCE {
        mdmRack
                INTEGER,
        mdmModem
                INTEGER,
        mdmPosition
                INTEGER,
        mdmModemName
                DisplayString,
        mdmInterfaceEmulationMode
                INTEGER,
        mdmModemProperty
                INTEGER,
        mdmLineEmulationMode
                INTEGER,
        mdmClockSystem
                INTEGER,
        mdmClockSource
                INTEGER,
        mdmDataRate
                INTEGER,
        mdmStartTimeslot
                INTEGER,
        mdmTimeslotSize
                INTEGER,
        mdmTimeslot16
                INTEGER,
        mdmCRC4Generation
                INTEGER,
        mdmFramingMode
                INTEGER,
        mdmCodingMode
                INTEGER,
        mdmScrambler
                INTEGER,
        mdmRemoteAccessMode
                INTEGER,
        mdmForcedRemoteAccess
                INTEGER,
        mdmTDPhaseLocking
                INTEGER,
        mdmLineBuiltOut
                INTEGER,
        mdmCRC6Test
                INTEGER,
        mdmCRC6Status
                INTEGER,
        mdmCRC6Error
                Gauge
        }

mdmRack OBJECT-TYPE
        SYNTAX  INTEGER
        ACCESS  read-only
        STATUS  mandatory
        DESCRIPTION
                "The index of the rack where the converter is installed."
        ::= { gmfTableEntry 1 }

mdmModem OBJECT-TYPE
        SYNTAX  INTEGER
        ACCESS  read-only
        STATUS  mandatory
        DESCRIPTION
                "This entry displays the slot number where the corresponding
                 converter is installed in the rack."
        ::= { gmfTableEntry 2 }

mdmPosition OBJECT-TYPE
        SYNTAX  INTEGER {
                local       (1),
                remote      (2)
                }
        ACCESS  read-only
        STATUS  mandatory
        DESCRIPTION
                "This entry displays the location of the corresponding
                 converter: 'local' or 'remote'. The converter which is plugged
                 into a managed rack is 'local', the counterpart is 'remote'."
        ::= { gmfTableEntry 3 }

mdmModemName OBJECT-TYPE
        SYNTAX  DisplayString
        ACCESS  read-only
        STATUS  mandatory
        DESCRIPTION
                "The verbal name of this converter."
        ::= { gmfTableEntry 5 }

mdmInterfaceEmulationMode OBJECT-TYPE
        SYNTAX  INTEGER {
                other       (1),
                dte         (2),
                dce         (3),
                te          (4),
                nt          (5),
                unknown     (99)
        }
        ACCESS  read-only
        STATUS  mandatory
        DESCRIPTION
                "Interface mode of the unit: 'dte', 'dce', 'te' or 'nt'."
        ::= { gmfTableEntry 6 }

mdmModemProperty OBJECT-TYPE
        SYNTAX  INTEGER {
                other           (1),
                e1              (2),
                t1              (3),
                unknown         (99)
                }
        ACCESS  read-only
        STATUS  mandatory
        DESCRIPTION
                "This entry displays the speed class of the GM-F: 'e1' or 't1'."
        ::= { gmfTableEntry 7 }

mdmLineEmulationMode OBJECT-TYPE
        SYNTAX  INTEGER {
                other       (1),
                te          (4),
                nt          (5),
                unknown     (99)
        }
        ACCESS  read-only
        STATUS  mandatory
        DESCRIPTION
                "Line mode of the unit: 'te' or 'nt'."
        ::= { gmfTableEntry 8 }

mdmClockSystem OBJECT-TYPE
        SYNTAX  INTEGER {
                other       (1),
                dual        (2),
                single      (3)
        }
        ACCESS  read-write
        STATUS  mandatory
        DESCRIPTION
                "The clock system of the link: 'dual' or 'single'."
        ::= { gmfTableEntry 23 }

mdmClockSource OBJECT-TYPE
        SYNTAX  INTEGER {
                other       (1),
                internal    (2),
                remote      (3),
                external    (4)
        }
        ACCESS  read-write
        STATUS  mandatory
        DESCRIPTION
                "The clock source of the link: 'internal', 'external', or
                 'remote'."
        ::= { gmfTableEntry 24 }

mdmDataRate OBJECT-TYPE
        SYNTAX  INTEGER {
                other       (1)
        }
        ACCESS  read-write
        STATUS  mandatory
        DESCRIPTION
                "The data rate at the interface in bits per seconds. The data
                 rate at the remote counterpart changes simultaneously. A data
                 rate of 2.048 Mbps (E1) automatically disables CRC4, sets
                 mdmStartTimeslot to 'unframed', enables time slot 16, and disables
                 remote access. A data rate of 1.984 Mbps (E1) automatically sets
                 mdmStartTimeslot to 'timeslot-1', enables time slot 16 and sets
                 mdmRemoteAccessMode to 'via timeslot 0 sa4-bit'. A data rate of
                 1.544 Mbps (T1) automatically sets mdmStartTimeslot to 'unframed'
                 and disables remote access."
        ::= { gmfTableEntry 25 }

mdmStartTimeslot OBJECT-TYPE
        SYNTAX  INTEGER {
                timeslot-1       (1),
                timeslot-2       (2),
                timeslot-3       (3),
                timeslot-4       (4),
                timeslot-5       (5),
                timeslot-6       (6),
                timeslot-7       (7),
                timeslot-8       (8),
                timeslot-9       (9),
                timeslot-10      (10),
                timeslot-11      (11),
                timeslot-12      (12),
                timeslot-13      (13),
                timeslot-14      (14),
                timeslot-15      (15),
                timeslot-16      (16),
                timeslot-17      (17),
                timeslot-18      (18),
                timeslot-19      (19),
                timeslot-20      (20),
                timeslot-21      (21),
                timeslot-22      (22),
                timeslot-23      (23),
                timeslot-24      (24),
                timeslot-25      (25),
                timeslot-26      (26),
                timeslot-27      (27),
                timeslot-28      (28),
                timeslot-29      (29),
                timeslot-30      (30),
                timeslot-31      (31),
                unframed        (98),
                other           (99),
                not-available   (100)
        }
        ACCESS  read-write
        STATUS  mandatory
        DESCRIPTION
                "This entry determines the start time slot for framing. Start
                 time slot and data rate must match. A start time slot which
                 is too high will be ignored. The remote unit's configuration
                 changes simultaneously."
        ::= { gmfTableEntry 26 }

mdmTimeslotSize OBJECT-TYPE
        SYNTAX  INTEGER {
                other           (1),
                nx64k           (2),
                nx56k           (3),
                not-available   (100)
        }
        ACCESS  read-write
        STATUS  mandatory
        DESCRIPTION
                "This entry determines the size of the time slots: 'nx64k' or
                 'nx56k'. 'nx56k' is valid for T1 units only. The remote unit's configuration
                 changes simultaneously."
        ::= { gmfTableEntry 27 }

mdmTimeslot16 OBJECT-TYPE
        SYNTAX  INTEGER {
                other           (1),
                disable         (2),
                enable          (3),
                not-available   (100)
                }
        ACCESS  read-write
        STATUS  mandatory
        DESCRIPTION
                "This entry enables or disables time slot 16. If it is disabled,
                 it will not be used for data transmission but for framing. Valid
                 for E1 units only."
        ::= { gmfTableEntry 40 }

mdmCRC4Generation OBJECT-TYPE
        SYNTAX  INTEGER {
                other           (1),
                disable         (2),
                enable          (3),
                not-available   (100)
        }
        ACCESS  read-write
        STATUS  mandatory
        DESCRIPTION
                "This entry enables or disables the generation of a CRC4 check
                 sum. Valid for E1 units only."
        ::= { gmfTableEntry 41 }

mdmFramingMode OBJECT-TYPE
        SYNTAX  INTEGER {
                other           (1),
                d4              (2),
                esf             (3),
                not-available   (100)
        }
        ACCESS  read-write
        STATUS  mandatory
        DESCRIPTION
                "The T1 framing mode: 'd4' or 'esf'. The remote unit's
                 configuration changes simultaneously.
                 Valid for T1 units only."
        ::= { gmfTableEntry 50 }

mdmCodingMode OBJECT-TYPE
        SYNTAX  INTEGER {
                other           (1),
                ami             (2),
                b8zs            (3),
                not-available   (100)
        }
        ACCESS  read-write
        STATUS  mandatory
        DESCRIPTION
                "The T1 coding mode: 'ami' or 'b8zs'. The remote unit's
                 configuration changes simultaneously.
                 Valid for T1 units only."
        ::= { gmfTableEntry 51 }

mdmScrambler OBJECT-TYPE
        SYNTAX  INTEGER {
                other       (1),
                disable     (2),
                enable      (3)
        }
        ACCESS  read-write
        STATUS  mandatory
        DESCRIPTION
                "This entry enables or disables scrambling."
        ::= { gmfTableEntry 63 }

mdmRemoteAccessMode OBJECT-TYPE
        SYNTAX  INTEGER {
                other                   (1),
                disable                 (2),
                via-next-free-timeslot  (3),
                via-timeslot-0-Sa4-bit  (4),
                via-unframed-line       (6)
        }
        ACCESS  read-write
        STATUS  mandatory
        DESCRIPTION
                "The remote access mode: 'disable', 'via-next-free-timeslot',
                 'via-timeslot-0-Sa4-bit', or 'via-unframed-line'. The value
                 'via-next-free-timeslot' means that one time slot higher than the last
                 data time slot is used for remote access. The value 'via-timeslot-0-Sa4-bit'
                 means that the sa4-bit in time slot 0 is used for remote access
                 (for E1 units only). The value 'via-unframed-line' is valied for data rates of
                 2048 Kbps (E1) or 1544 Kbps (T1) only. With a data rate of 1536 Kbps (T1).
                 remote management is not available. The remote unit's configuration changes
                 simultaneously."
        ::= { gmfTableEntry 64 }

mdmForcedRemoteAccess OBJECT-TYPE
        SYNTAX  INTEGER {
                off             (1),
                on              (2),
                not-available   (100)
        }
        ACCESS  read-write
        STATUS  mandatory
        DESCRIPTION
                "Valid if 'mdmRemoteAccessMode' is set to 'via-unframed-line'.
                 Activation of remote management: 'on' or 'off'.
                 Status 'on' enables management of remote unit. During this
                 process the link is restricted to management data. The
                 transmission of user data is interrupted.
                 Status 'off' disables management of remote unit. The link
                 transmits user data."
        ::= { gmfTableEntry 65 }

mdmTDPhaseLocking OBJECT-TYPE
        SYNTAX  INTEGER {
                other                   (1),
                positive-clock-slope    (2),
                negative-clock-slope    (3),
                unknown                 (99),
                not-available           (100)
        }
        ACCESS  read-write
        STATUS  mandatory
        DESCRIPTION
                "This entry defines the data phase locking for I/F data:
                'positive-clock-slope' or 'negative-clock-slope'."
        ::= { gmfTableEntry 67 }

mdmLineBuiltOut OBJECT-TYPE
        SYNTAX  INTEGER {
                other               (1),
                dsx-1-0to133-ft     (3),
                dsx-1-133to266-ft   (4),
                dsx-1-266to399-ft   (5),
                dsx-1-399to533-ft   (6),
                dsx-1-533to655-ft   (7),
                csu-0db             (8),
                csu-7db5            (9),
                csu-15db            (10),
                csu-22db5           (11),
                not-available       (100)
        }
        ACCESS  read-write
        STATUS  mandatory
        DESCRIPTION
                "The T1 transmission mode of the unit. Valid for T1 units only."
        ::= { gmfTableEntry 68 }

mdmCRC6Test OBJECT-TYPE
        SYNTAX  INTEGER {
                other           (1),
                start           (3),
                stop            (4),
                not-available   (100)
        }
        ACCESS  read-write
        STATUS  mandatory
        DESCRIPTION
                "This entry enables the execution of a CRC6 test. Write requests
                 with values other than 'start' or 'stop' will be rejected. Valid
                 for T1 units only."
        ::= { gmfTableEntry 100 }

mdmCRC6Status OBJECT-TYPE
        SYNTAX  INTEGER {
                other           (1),
                never-started   (2),
                running         (5),
                stopped         (6),
                start-failed    (7),
                not-available   (100)
        }
        ACCESS  read-only
        STATUS  mandatory
        DESCRIPTION
                "This entry indicates the status of the CRC6 test.
                 Valid for T1 units only."
        ::= { gmfTableEntry 101 }

mdmCRC6Error OBJECT-TYPE
        SYNTAX  Gauge
        ACCESS  read-only
        STATUS  mandatory
        DESCRIPTION
                "This entry indicates the number of errors detected during
                 the last 60 seconds."
        ::= { gmfTableEntry 102 }

END
