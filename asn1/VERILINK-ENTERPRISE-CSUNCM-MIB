VERILINK-ENTERPRISE-CSUNCM-MIB

        -- set up MIB-wide defaults
        -- all functions can use %n for object name and
        -- %t for object type, %p for parent name,
        -- %d for name of default-bearing node and %% for %

          DEFINITIONS ::= BEGIN

     IMPORTS
             Gauge
                     FROM RFC1155-SMI
             OBJECT-TYPE
                     FROM RFC-1212
	      DisplayString
                     FROM RFC1213-MIB

	     ncm-csu
		     FROM 
             VERILINK-ENTERPRISE-NCMALARM-MIB;

             

     --  This MIB module uses the extended OBJECT-TYPE macro as
     --  defined in RFC 1212.
     --  This MIB module uses the TRAP-TYPE macro as
     --  defined in RFC 1215.




        

         
         -- The ncm csu Main configuration table

        ncmcsuMainConfigTable OBJECT-TYPE
        SYNTAX SEQUENCE OF NcmcsuMainConfigEntry
        ACCESS not-accessible
        STATUS mandatory
	DESCRIPTION
        " The ncm csu main configuration table."

	 --DEFAULT test-function csu-test
        --DEFAULT next-function csu-next
	
	
	

                  ::= { ncm-csu 6000 }


        ncmcsuMainConfigEntry OBJECT-TYPE
        SYNTAX NcmcsuMainConfigEntry
        ACCESS not-accessible
        STATUS mandatory
        DESCRIPTION
               "An entry in the ncm csu main configuration table."
        INDEX   { ncmcsuNIDMainConfigIndex, ncmcsuMainLineIndex }
        ::= { ncmcsuMainConfigTable 1 }


	NcmcsuMainConfigEntry ::=
        SEQUENCE {
		
	     ncmcsuNIDMainConfigIndex
		  INTEGER,	
             ncmcsuMainLineIndex
                 INTEGER,
             ncmcsuFormat
                 INTEGER,
	     ncmcsuLineCode
		INTEGER,
             ncmcsuEQCableLength
                 INTEGER,
             ncmcsuTiming
                 INTEGER,
             ncmdsudatabus
                 INTEGER,
             ncmcsuNetLineBuildOut
                 INTEGER,
	     ncmcsuValidIntervals
		 INTEGER,
	     ncmcsuCurrentIntervalSec
		INTEGER,
  	     ncmcsuJitterBuf
                INTEGER,
	     ncmcsuTestSigCfgEnable
		INTEGER,
	     ncmcsuTestSigCfgFrameSignal
		INTEGER,
	     ncmcsuRLBTimeoutIndex
		INTEGER,
	     ncmcsuCfgRptSendPRM
		INTEGER,
	     ncmcsuCfgRptPollFarEnd
		INTEGER,
	     ncmcsuCfgRptDataLinkUnsolicit
		INTEGER,
	     ncmcsuCfgRptAlmReporting
		INTEGER,
	     ncmcsuCfgRptPRMType
		INTEGER,
	     ncmcsuCfgCodeRegenCRC
		INTEGER,
	     ncmcsuCfgCodeXYellowAlarm
		INTEGER,
	     ncmcsuCfgCodeEQFIFO
		INTEGER,
	     ncmcsuCfgCodeNETFIFO
		INTEGER,
	     ncmcsuCfgCodeTranMode
		INTEGER,
	     ncmcsuCfgCodeSend1sLnkIdle
		INTEGER,
	     ncmcsuCfgAlmSelfTest
		INTEGER,
	     ncmcsuCfgAlmEnableTestState
		INTEGER,
	     ncmcsuCfgAlmUnframedMode
		INTEGER,
	     ncmcsuCfgAlmOnEqLoop
		INTEGER,
	     ncmcsuCfgAlmOnNetLoop
		INTEGER,
	     ncmcsuCfgAlmOnPowerUpLoop
		INTEGER,
	     ncmcsuCfgLoopRespLLB
                INTEGER,
             ncmcsuCfgLoopRespPLB
                INTEGER,
             ncmcsuCfgLoopRespELB
                INTEGER,
             ncmcsuCfgLoopRespRLB
                INTEGER,
             ncmcsuCfgLoopRespLLBTONE
                INTEGER,
             ncmcsuCfgLoopRespPLBTONE
                INTEGER,
             ncmcsuCfgSendReceiveInBandCode
                INTEGER
 

           
                }


	ncmcsuNIDMainConfigIndex OBJECT-TYPE
        SYNTAX  INTEGER
        ACCESS  read-only
        STATUS  mandatory
        DESCRIPTION
	"This variable specifies the node id."          
        ::= { ncmcsuMainConfigEntry 1 }

	
 
 
        ncmcsuMainLineIndex OBJECT-TYPE
        SYNTAX  INTEGER
        ACCESS  read-only
        STATUS  mandatory
	DESCRIPTION
	"This variable specifies the line index value."           
        ::= { ncmcsuMainConfigEntry 2 }
 
        ncmcsuFormat OBJECT-TYPE
         SYNTAX INTEGER{
		       unframed(1),
                       sf(2),
                       esf(3),
                       zbtsi(4)
 
               } 
        ACCESS read-write
        STATUS mandatory
        DESCRIPTION
               "The ncmcsu Net/Eq format."
 
        ::= { ncmcsuMainConfigEntry 3 }
 
 
 
        ncmcsuLineCode OBJECT-TYPE
         SYNTAX INTEGER {
			ami(1),
                       b8zs(2)
           
 
               } 
        ACCESS read-write
        STATUS mandatory
        DESCRIPTION
               "The ncmcsu Net/Eq Line Code."
 
        ::= { ncmcsuMainConfigEntry 4 }
 
 
	 ncmcsuEQCableLength OBJECT-TYPE
        SYNTAX INTEGER  {
                ft-0-133(1),
                fT-133-266(2),
                fT-266-399(3),
                fT-399-533(4),
                fT-533-655(5)
			}
        ACCESS read-write
        STATUS mandatory
        DESCRIPTION
               "The ncmcsu EQ Cable Length."
        ::= { ncmcsuMainConfigEntry 5 }
          
 
        ncmcsuTiming OBJECT-TYPE
        SYNTAX INTEGER  {
                through (1),
                internal (2),
                external-422 (3),
                ext-ttl (4),
                net(5),
                eq(6),
                tiu(7),
                dsu(8)
                                }
        ACCESS read-write
        STATUS mandatory
        DESCRIPTION
               "The ncmcsu timing."
        ::= { ncmcsuMainConfigEntry 6 }
          
 
         
        ncmdsudatabus OBJECT-TYPE
        SYNTAX INTEGER  {
                        none(1),
                        bus-a(2),
                        bus-b(3),
                        bus-c(4),
        		drop-uses-bus-b(5),   
        		insert-uses-bus-a(6)   
 
                        }
        ACCESS read-write
        STATUS mandatory
        DESCRIPTION
               "The dsu data bus reserved for future."
        ::= { ncmcsuMainConfigEntry 7 }
          

	ncmcsuNetLineBuildOut OBJECT-TYPE
        SYNTAX INTEGER
                        {
                        db-Zero(1),
                        db-Seven-point-five(2),
                        db-Fifteen(3)
                        }
        ACCESS read-write
        STATUS mandatory
        DESCRIPTION
               "The ncmcsu net line build out."
        ::= { ncmcsuMainConfigEntry 8 }

	
	ncmcsuValidIntervals OBJECT-TYPE
        SYNTAX INTEGER
        ACCESS read-only
        STATUS mandatory
        DESCRIPTION
               "The ncmcsu valid intervals."
        ::= { ncmcsuMainConfigEntry 9 }


        ncmcsuCurrentIntervalSec  OBJECT-TYPE
        SYNTAX INTEGER
        ACCESS read-only
        STATUS mandatory
        DESCRIPTION
               "The ncmcsu seconds in current 15 minutes interval. "
        ::= { ncmcsuMainConfigEntry 10 }


        ncmcsuJitterBuf OBJECT-TYPE
         SYNTAX INTEGER {
                        eq-Net-16-16(1),
                        eq-Net-40-16(2),
                        eq-Net-16-40(3),
                        eq-Net-40-40(4)

               } 
        ACCESS read-write
        STATUS mandatory
        DESCRIPTION
               "The ncmcsu Net/Eq Jitter buffer in bits."
        ::= { ncmcsuMainConfigEntry 11 }


	ncmcsuTestSigCfgEnable    OBJECT-TYPE
        SYNTAX INTEGER  {
			no(1),
                        yes(2)
        }                
        ACCESS read-write
        STATUS mandatory
        DESCRIPTION
               "bit 1 of MSGOUT+47 for read or of MSGIN+47 for write is test signal enable
		in this test signal configuration message."
        ::= { ncmcsuMainConfigEntry 12 }


        ncmcsuTestSigCfgFrameSignal  OBJECT-TYPE
        SYNTAX INTEGER  {
                        no(1),
                        yes(2)
        }       
        ACCESS read-write
        STATUS mandatory
        DESCRIPTION
               "bit 7 of MSGOUT+47 for read or of MSGIN+47 for write is frame test signal
		in this test signal configuration message."
        ::= { ncmcsuMainConfigEntry 13 }
 

	ncmcsuRLBTimeoutIndex      OBJECT-TYPE
        SYNTAX INTEGER
        ACCESS read-write
        STATUS mandatory
        DESCRIPTION
               "The rlb timeout index."
        ::= { ncmcsuMainConfigEntry 14 }


	ncmcsuCfgRptSendPRM	OBJECT-TYPE
        SYNTAX INTEGER  {
			no(1),
                        yes(2)
	}
        ACCESS read-write
        STATUS mandatory
        DESCRIPTION
               "bit 0 of MSGOUT+52 for read or MSGIN+52 for write is send prm
		in this configure report message."
        ::= { ncmcsuMainConfigEntry 15 }


	ncmcsuCfgRptPollFarEnd     OBJECT-TYPE
        SYNTAX INTEGER  {
			no(1),
                        yes(2)
        }
        ACCESS read-write
        STATUS mandatory
        DESCRIPTION
               "bit 1 of MSGOUT+52 for read or MSGIN+52 for write is poll far end
		in this configure report message."
        ::= { ncmcsuMainConfigEntry 16 }


	ncmcsuCfgRptDataLinkUnsolicit   OBJECT-TYPE
        SYNTAX INTEGER  {
			no(1),
                        yes(2)
        }
        ACCESS read-write
        STATUS mandatory
        DESCRIPTION
               "bit 2 of MSGOUT+52 for read or MSGIN+52 for write is data link unsolicited report
		in this configure report message."
        ::= { ncmcsuMainConfigEntry 17 }


	ncmcsuCfgRptAlmReporting    OBJECT-TYPE
        SYNTAX INTEGER  {
			no(1),
                        yes(2)
        }
        ACCESS read-write
        STATUS mandatory
        DESCRIPTION
               "bit 3 of MSGOUT+52 for read or MSGIN+52 for write is alarm reporting
		in this configure report message."
        ::= { ncmcsuMainConfigEntry 18 }


	ncmcsuCfgRptPRMType	OBJECT-TYPE
        SYNTAX INTEGER  {
                        nO-PRM(1),
                        uSER(2)
        }
        ACCESS read-write
        STATUS mandatory
        DESCRIPTION
               "bit 4,5 of MSGOUT+52 for read or of MSGIN+52 for write is PRM type
		in this configure report message."
        ::= { ncmcsuMainConfigEntry 19 }


	ncmcsuCfgCodeRegenCRC  	OBJECT-TYPE
        SYNTAX INTEGER  {
                        pass(1),
                        net-to-Eq(2),
                        eq-to-Net(3),
                        both(4)
        }
        ACCESS read-write
        STATUS mandatory
        DESCRIPTION
               "bit 0,1 of MSGOUT+53 for read or MSGIN+53 for write is regenerate 
		crc from net to dte or eq to net in this configure coding message. "
        ::= { ncmcsuMainConfigEntry 20 }


	ncmcsuCfgCodeXYellowAlarm  OBJECT-TYPE
        SYNTAX INTEGER  {
                        off(1),
                        net-to-Eq(2),
                        eq-to-Net(3),
                        both(4)
        }
        ACCESS read-write
        STATUS mandatory
        DESCRIPTION
               "bit 2,3 of MSGOUT+53 for read or MSGIN+53 for write is transcode yellow
                alarm from net to dte or eq to net in this configure coding message. "
        ::= { ncmcsuMainConfigEntry 21 }


	ncmcsuCfgCodeEQFIFO        OBJECT-TYPE
        SYNTAX INTEGER  {
                        fifteen-bits(1),
                        forty-bits(2)
        }
        ACCESS read-write
        STATUS mandatory
        DESCRIPTION
               "bit 4 of MSGOUT+53 for read or MSGIN+53 for write is eq fifo
                in this configure coding message. "
        ::= { ncmcsuMainConfigEntry 22 }


        ncmcsuCfgCodeNETFIFO        OBJECT-TYPE
        SYNTAX INTEGER  {
                        fifteen-bits(1),
                        forty-bits(2)
        }
        ACCESS read-write
        STATUS mandatory 
        DESCRIPTION
               "bit 5 of MSGOUT+53 for read or MSGIN+53 for write is net fifo
                in this configure coding message. "
        ::= { ncmcsuMainConfigEntry 23 }


	ncmcsuCfgCodeTranMode	OBJECT-TYPE
        SYNTAX INTEGER  {
			no(1),
                        yes(2)
        }
        ACCESS read-write
        STATUS mandatory
        DESCRIPTION
               "bit 6 of MSGOUT+53 for read or MSGIN+53 for write is transparent 
		mode in this configure report message."
        ::= { ncmcsuMainConfigEntry 24 }


        ncmcsuCfgCodeSend1sLnkIdle   OBJECT-TYPE 
        SYNTAX INTEGER  { 
			no(1),
                        yes(2) 
        } 
        ACCESS read-write
        STATUS mandatory 
        DESCRIPTION 
               "bit 7 of MSGOUT+53 for read or MSGIN+53 for write is send ones
                data link idle code in this configure report message."
        ::= { ncmcsuMainConfigEntry 25 }


        ncmcsuCfgAlmSelfTest       OBJECT-TYPE
        SYNTAX INTEGER  {
			no(1),
                        yes(2)
        }                
        ACCESS read-write
        STATUS mandatory
        DESCRIPTION
               "bit 0 of MSGOUT+54 for read or MSGIN+54 for write is enable
                power up self test in this configure alarm message."
        ::= { ncmcsuMainConfigEntry 26 }
 
 
        ncmcsuCfgAlmEnableTestState   OBJECT-TYPE
        SYNTAX INTEGER  {
			no(1),
                        yes(2)
        }                
        ACCESS read-write
        STATUS mandatory
        DESCRIPTION
               "bit 1 of MSGOUT+54 for read or MSGIN+54 for write is enable
                alarms in test state in this configure alarm message."
        ::= { ncmcsuMainConfigEntry 27 }
 
 
        ncmcsuCfgAlmUnframedMode   OBJECT-TYPE
        SYNTAX INTEGER  {
                        no(1),
                        yes(2)
        }
        ACCESS read-write
        STATUS mandatory
        DESCRIPTION
               "bit 2 of MSGOUT+54 for read or MSGIN+54 for write is
                alarms in unframe mode in this configure alarm message."
        ::= { ncmcsuMainConfigEntry 28 }
 
 
        ncmcsuCfgAlmOnEqLoop       OBJECT-TYPE
        SYNTAX INTEGER  {
			no(1),
                        yes(2)
        }
        ACCESS read-write
        STATUS mandatory
        DESCRIPTION
               "bit 3 of MSGOUT+54 for read or MSGIN+54 for write is alarm
                on eq loop loop in this configure alarm message."
        ::= { ncmcsuMainConfigEntry 29 }
 

        ncmcsuCfgAlmOnNetLoop       OBJECT-TYPE
        SYNTAX INTEGER  {
			no(1),
                        yes(2)
        }
        ACCESS read-write
        STATUS mandatory
        DESCRIPTION
               "bit 4 of MSGOUT+54 for read or MSGIN+54 for write is alarm
                on net loop in this configure alarm message."
        ::= { ncmcsuMainConfigEntry 30 }


        ncmcsuCfgAlmOnPowerUpLoop       OBJECT-TYPE 
        SYNTAX INTEGER  { 
			no(1),
                        yes(2)
        }
        ACCESS read-write
        STATUS mandatory 
        DESCRIPTION 
               "bit 5 of MSGOUT+54 for read or MSGIN+54 for write is alarm 
                power up loop in this configure alarm message." 
        ::= { ncmcsuMainConfigEntry 31 }


	ncmcsuCfgLoopRespLLB      OBJECT-TYPE
        SYNTAX INTEGER  {
                        no(1),
                        yes(2)
        }
        ACCESS read-write
        STATUS mandatory
        DESCRIPTION
               "bit 0 of MSGOUT+55 for read or MSGIN+55 for respond to LLB
                in this configure Loop Response Message."
        ::= { ncmcsuMainConfigEntry 32 }


        ncmcsuCfgLoopRespPLB      OBJECT-TYPE
        SYNTAX INTEGER  {
                        no(1),
                        yes(2)
        }
        ACCESS read-write
        STATUS mandatory
        DESCRIPTION
               "bit 1 of MSGOUT+55 for read or MSGIN+55 for respond to PLB
                in this configure Loop Response Message."
        ::= { ncmcsuMainConfigEntry 33 }
 
 
        ncmcsuCfgLoopRespELB     OBJECT-TYPE
        SYNTAX INTEGER  {
                        no(1),
                        yes(2)
        }
        ACCESS read-write
        STATUS mandatory
        DESCRIPTION
               "bit 2 of MSGOUT+55 for read or MSGIN+55 for respond to ELB
                in this configure Loop Response Message."
        ::= { ncmcsuMainConfigEntry 34 }
 
 
        ncmcsuCfgLoopRespRLB     OBJECT-TYPE
        SYNTAX INTEGER  {
                        no(1),
                        yes(2)
        }
        ACCESS read-write
        STATUS mandatory
        DESCRIPTION
               "bit 3 of MSGOUT+55 for read or MSGIN+55 for respond to RLB
                in this configure Loop Response Message."
        ::= { ncmcsuMainConfigEntry 35 }
 
 
        ncmcsuCfgLoopRespLLBTONE     OBJECT-TYPE
        SYNTAX INTEGER  {
                        no(1),
                        yes(2)
        }
        ACCESS read-write
        STATUS mandatory
        DESCRIPTION
               "bit 4 of MSGOUT+55 for read or MSGIN+55 for respond to LLB (T1.403)
                in this configure Loop Response Message."
        ::= { ncmcsuMainConfigEntry 36 }


	ncmcsuCfgLoopRespPLBTONE     OBJECT-TYPE
        SYNTAX INTEGER  {
                        no(1),
                        yes(2)
        }
        ACCESS read-write
        STATUS mandatory
        DESCRIPTION
               "bit 5 of MSGOUT+55 for read or MSGIN+55 for respond to PLB (T1.403)
                in this configure Loop Response Message."
        ::= { ncmcsuMainConfigEntry 37 }
 
 
        ncmcsuCfgSendReceiveInBandCode     OBJECT-TYPE
        SYNTAX INTEGER  {
                        disable(1),
                        enable(2)
        }
        ACCESS read-write
        STATUS mandatory
        DESCRIPTION
               "bit 6 of MSGOUT+55 for read or MSGIN+55 for enable to Send/Receive
                of in-band code."
        ::= { ncmcsuMainConfigEntry 38 }

 


	-- The ncmcsu Enhance Configuration table

        ncmcsuEnhanceConfigTable OBJECT-TYPE
        SYNTAX SEQUENCE OF NcmcsuEnhanceConfigEntry
        ACCESS not-accessible
        STATUS mandatory
	DESCRIPTION
        "The ncmcsu enhance configuration table."



	 --DEFAULT test-function csu-test
        --DEFAULT next-function csu-next
	
        ::= { ncm-csu 6001 }


        ncmcsuEnhanceConfigEntry OBJECT-TYPE
        SYNTAX NcmcsuEnhanceConfigEntry
        ACCESS not-accessible
        STATUS mandatory
        DESCRIPTION
               "An entry in the ncmcsu enhance configuration table."
        INDEX   { ncmcsuNIDEnhanceIndex, ncmcsuEnhanceLineIndex }
        ::= { ncmcsuEnhanceConfigTable 1 }


        NcmcsuEnhanceConfigEntry ::=
        SEQUENCE {

	     ncmcsuNIDEnhanceIndex
		  INTEGER,
             ncmcsuEnhanceLineIndex
                 INTEGER,
             ncmcsuNetworkKeepAlive
                 INTEGER,
             ncmcsuAlarmSetDelay
                 INTEGER,
             ncmcsuAlarmClearDelay
                 INTEGER,
             ncmcsuAlarmEnable
                INTEGER,
             ncmcsuNetDensityEnforcement
                 INTEGER,
             ncmcsuLoopback
                INTEGER,
	     ncmcsuTestPattern
		INTEGER,
	     ncmcsuResetPerfReg
		INTEGER,
	     ncmcsuTestErrorCounter
		Gauge,
	     ncmcsuTestSecondsRemain
		Gauge,
	     ncmcsuTestTimeSeconds
                INTEGER,
             ncmcsuNetLOFCIndexTime
                INTEGER,
             ncmcsuChannelMask
                DisplayString,
             ncmcsuApplication
                INTEGER,
             ncmcsuTestIntervalIndex
                INTEGER

 

                        }




	ncmcsuNIDEnhanceIndex OBJECT-TYPE
        SYNTAX  INTEGER 
        ACCESS  read-only
        STATUS  mandatory
        DESCRIPTION
	"This variable specifies the nid index."         
        ::= { ncmcsuEnhanceConfigEntry 1 }


 	ncmcsuEnhanceLineIndex OBJECT-TYPE
        SYNTAX  INTEGER 
        ACCESS  read-only
        STATUS  mandatory
        DESCRIPTION
	"This variable specifies the line index."         
        ::= { ncmcsuEnhanceConfigEntry 2 }

        ncmcsuNetworkKeepAlive OBJECT-TYPE
        SYNTAX INTEGER {
 
                       none(1),
                       loop(2),
                       aIS(3),
                       framed-all-ones(4)
                        
               } 
        ACCESS read-write
        STATUS mandatory
        DESCRIPTION
               "The ncmcsu  network keep alive varaible ."
                  
        ::= { ncmcsuEnhanceConfigEntry 3 }
 
 
        ncmcsuAlarmSetDelay OBJECT-TYPE
        SYNTAX INTEGER
        ACCESS read-write
        STATUS mandatory
        DESCRIPTION
               "The ncmcsu alarm set delay."
        ::= { ncmcsuEnhanceConfigEntry 4 }
 
 
        ncmcsuAlarmClearDelay OBJECT-TYPE
        SYNTAX INTEGER
        ACCESS read-write
        STATUS mandatory
        DESCRIPTION
               "The ncmcsu alarm clear delay."
        ::= { ncmcsuEnhanceConfigEntry 5 }
 
        ncmcsuAlarmEnable OBJECT-TYPE
        SYNTAX INTEGER {
 
                       disable(1),
                       enable(2)
                        
               }        
        ACCESS read-write
        STATUS mandatory
        DESCRIPTION
               "The ncmcsu alarm reporting."
                  
        ::= { ncmcsuEnhanceConfigEntry 6 }
 

	ncmcsuNetDensityEnforcement OBJECT-TYPE
        SYNTAX INTEGER {
                        none(1),
                        fcc-part-68(2),
                        pub-62411(3),
                        eighty-zeroes(4),
                        fifteen-zeroes(5)
 
                        }
         ACCESS read-write
         STATUS mandatory
         DESCRIPTION
               "The ncmcsu net density enforcement."
         ::= { ncmcsuEnhanceConfigEntry 7 }
         
 
 
        ncmcsuLoopback OBJECT-TYPE
        SYNTAX INTEGER {
                csu-Payload-Loop-Back(1),
                csu-Line-Loop-Back(2),
                repeater-Loop-Back(3),
                csu-Equip-Loop-Back(4),
                csu-No-Loop-Back(5),
                deactivate-LLB-and-PLB(6),
                deactivate-ELB-and-RLB(7),
                send-Inband-Loop-Up(9),
                send-Inband-Loop-Down(10)
                
                        }
                
        ACCESS read-write
        STATUS mandatory
        DESCRIPTION
            " The ncmcsu loop back config. "
 
        ::= { ncmcsuEnhanceConfigEntry 8 }



	ncmcsuTestPattern OBJECT-TYPE
        SYNTAX INTEGER {

		no-test(1),
		qrss-to-net(2),
		one-in-eight-to-net(3),
		three-in-twenty-four-to-net(4),
		all-ones-to-net(5),
		qrss-to-eq(6),
		one-in-eight-to-eq(7),
		three-in-twenty-four-to-eq(8),
		all-ones-to-eq(9)
		
                        }
                
        ACCESS read-write
        STATUS mandatory
        DESCRIPTION
            " The ncmcsu test pattern config. "
 
        ::= { ncmcsuEnhanceConfigEntry 9 }
 

	ncmcsuResetPerfReg OBJECT-TYPE 
        SYNTAX INTEGER { 
 
                no(1),     
                yes(2)       
                        } 
                 
        ACCESS read-write 
        STATUS mandatory 
        DESCRIPTION    
            " The ncmcsu  reset performance monitoring register " 
  
        ::= { ncmcsuEnhanceConfigEntry 10 }


	ncmcsuTestErrorCounter OBJECT-TYPE 
        SYNTAX Gauge 
        ACCESS read-only
        STATUS mandatory 
        DESCRIPTION 
            " The ncmcsu test error counter in the test status  " 
  
        ::= { ncmcsuEnhanceConfigEntry 11 } 
 



	ncmcsuTestSecondsRemain OBJECT-TYPE
        SYNTAX Gauge 
        ACCESS read-only
        STATUS mandatory
        DESCRIPTION
            " The ncmcsu test seconds remaining in the test status  "
 
        ::= { ncmcsuEnhanceConfigEntry 12 }



	ncmcsuTestTimeSeconds OBJECT-TYPE
        SYNTAX INTEGER
        ACCESS read-write
        STATUS mandatory
        DESCRIPTION
            " The csu test time duration. Enter Value (0-142, 255)
              0         corresponds to 0 Sec (Default)
              1 - 59    corresponds to 1-59 Seconds
              60 - 118  corresponds to 1-59 Min
              119 - 142 corresponds to 1-24 HR
              255       corresponds to (Forever) option "

        ::= { ncmcsuEnhanceConfigEntry 13 }


        ncmcsuNetLOFCIndexTime OBJECT-TYPE
        SYNTAX INTEGER
        ACCESS read-write
        STATUS mandatory
        DESCRIPTION
            " The csu net lofc index time  "

        ::= { ncmcsuEnhanceConfigEntry 14 }



        ncmcsuChannelMask OBJECT-TYPE
        SYNTAX DisplayString (SIZE (0..255))
        ACCESS read-write
        STATUS mandatory
        DESCRIPTION
            " The csu channel mask for the 24 channels  "
 
        ::= { ncmcsuEnhanceConfigEntry 15 }
 
 
        ncmcsuApplication OBJECT-TYPE
        SYNTAX INTEGER  {
                         none(1),
                         csu(2),
                         smds(3)
                        }
        ACCESS read-write
        STATUS mandatory
        DESCRIPTION
            " The csu application mode  "
 
        ::= { ncmcsuEnhanceConfigEntry 16 }
 
 
 
        ncmcsuTestIntervalIndex OBJECT-TYPE
        SYNTAX INTEGER
        ACCESS read-write
        STATUS mandatory
        DESCRIPTION
            " The csu Test Inteval Index value used for test pattern (0 - config default) " 
        ::= { ncmcsuEnhanceConfigEntry 17 }




  
	  -- The ncmcsu Element Status table
    
        ncmcsuElementStatusOneTable OBJECT-TYPE
        SYNTAX SEQUENCE OF NcmcsuElementStatusOneEntry
        ACCESS not-accessible
        STATUS mandatory
	DESCRIPTION
               " the ncmcsu element status table."
	       --DEFAULT test-function csucommon-test
               --DEFAULT next-function csucommon-next
        ::= { ncm-csu 6002 }

        ncmcsuElementStatusOneEntry OBJECT-TYPE
        SYNTAX NcmcsuElementStatusOneEntry
        ACCESS not-accessible
        STATUS mandatory
        DESCRIPTION
               "An entry in the ncmcsu element status table."
        INDEX   { ncmcsuNIDElementStatusIndex1,ncmcsuElementStatusIndex1 }
        ::= { ncmcsuElementStatusOneTable 1 }


        NcmcsuElementStatusOneEntry ::= SEQUENCE {
	     ncmcsuNIDElementStatusIndex1
		 INTEGER, 
             ncmcsuElementStatusIndex1
                 INTEGER,
             ncmcsuExcessiveError
                 INTEGER,
             ncmcsuOutOfFrame
                 INTEGER,
             ncmcsuNetLossOfSignal
                 INTEGER
                }


	ncmcsuNIDElementStatusIndex1 OBJECT-TYPE
        SYNTAX  INTEGER
        ACCESS  read-only
        STATUS  mandatory
        DESCRIPTION
	"This variable specifies the node id of the node."        
        ::= { ncmcsuElementStatusOneEntry 1 }

	

        ncmcsuElementStatusIndex1 OBJECT-TYPE
        SYNTAX  INTEGER
        ACCESS  read-only
        STATUS  mandatory
	DESCRIPTION
	"This variable specifies the interface index ."
         ::= { ncmcsuElementStatusOneEntry 2 }
 
 
        ncmcsuExcessiveError OBJECT-TYPE
        SYNTAX INTEGER {
 
                        signal(1),
                        ais(2)
 
                          }
        ACCESS read-write
        STATUS mandatory
        DESCRIPTION
               "The Net/Eq has excessive errors."
 
        ::= { ncmcsuElementStatusOneEntry 3 }


	 ncmcsuOutOfFrame   OBJECT-TYPE
        SYNTAX INTEGER {
 
                       signal(1),
                       ais(2)
 
               } 
        ACCESS read-write
        STATUS mandatory
        DESCRIPTION
               "The ncmcsu Eq is out of frame (OOF)."
 
        ::= { ncmcsuElementStatusOneEntry 4 }
 
 
        ncmcsuNetLossOfSignal OBJECT-TYPE
        SYNTAX INTEGER {
 
                signal(1),
                ais(2)
 
                        }

        ACCESS read-write
        STATUS mandatory
        DESCRIPTION
               "The ncmcsu Net/Eq uas interval."
        ::= { ncmcsuElementStatusOneEntry 5 }


 
  -- The ncmcsu Element Status Table2
     
        ncmcsuElementStatusTwoTable OBJECT-TYPE
        SYNTAX SEQUENCE OF NcmcsuElementStatusTwoEntry
        ACCESS not-accessible
        STATUS mandatory
	DESCRIPTION
               "The ncmcsu element status table2."



	--DEFAULT test-function csucommon-test
        --DEFAULT next-function csucommon-next
	 	
 
        ::= { ncm-csu 6003 }
 
 
        ncmcsuElementStatusTwoEntry OBJECT-TYPE
        SYNTAX NcmcsuElementStatusTwoEntry
        ACCESS not-accessible
        STATUS mandatory
        DESCRIPTION
               "An entry in the ncmcsu element status table2."
        INDEX   { ncmcsuNIDElementStatusIndex2,ncmcsuElementStatusIndex2 }
        ::= { ncmcsuElementStatusTwoTable 1 }
 
        NcmcsuElementStatusTwoEntry ::=
        SEQUENCE {
	     ncmcsuNIDElementStatusIndex2
		 INTEGER,
             ncmcsuElementStatusIndex2
                 INTEGER,
             ncmcsuStatus
                 INTEGER,
             ncmcsuAddress1
                 INTEGER,
             ncmcsuAddress2
                 INTEGER,
             ncmcsuLLBELBPLB
                 INTEGER
 
         
                }
	


	ncmcsuNIDElementStatusIndex2 OBJECT-TYPE
        SYNTAX  INTEGER
        ACCESS  read-only
        STATUS  mandatory
        DESCRIPTION
	"This variable specifies the node id for the  node."
        ::= { ncmcsuElementStatusTwoEntry 1 }


	ncmcsuElementStatusIndex2 OBJECT-TYPE
        SYNTAX  INTEGER
        ACCESS  read-only
        STATUS  mandatory
        DESCRIPTION
	"This variable specifies the interface index value." 
        ::= { ncmcsuElementStatusTwoEntry 2 }
 
         
        ncmcsuStatus OBJECT-TYPE
        SYNTAX INTEGER
        ACCESS read-only
        STATUS mandatory
        DESCRIPTION
               "The ncmcsu test status.
        The bit position are described as follows:
        BIT     NAME
        0       pulses
        1       frame loss
        2       crc error
        3       bpv
        4       looped
        5       yellow alarm
        6       sending test signal
        7       alarm."
        
        
        ::= { ncmcsuElementStatusTwoEntry 3}
 
         
 
        ncmcsuAddress1 OBJECT-TYPE
        SYNTAX INTEGER
        ACCESS read-write
        STATUS mandatory
        DESCRIPTION
               "The ncmcsu address1."
        ::= { ncmcsuElementStatusTwoEntry 4 }
        
        ncmcsuAddress2 OBJECT-TYPE
        SYNTAX INTEGER
        ACCESS read-write
        STATUS mandatory
        DESCRIPTION
               "The ncmcsu address2."
        ::= { ncmcsuElementStatusTwoEntry 5 }
 
 
         
        ncmcsuLLBELBPLB OBJECT-TYPE
        SYNTAX INTEGER	{
 
                signal(1),
                ais(2)
                        }

        ACCESS read-write
        STATUS mandatory
        DESCRIPTION
               "The ncmcsu Net/Eq uas threshold."
        ::= { ncmcsuElementStatusTwoEntry 6 }



	 -- The ncmcsu thresholdInterval table

        ncmcsuThresholdIntervalTable OBJECT-TYPE
        SYNTAX SEQUENCE OF NcmcsuThresholdIntervalEntry
        ACCESS not-accessible
        STATUS mandatory
		DESCRIPTION
               "The ncmcsu ThresholdInterval table."

	--DEFAULT test-function csu-test
        --DEFAULT next-function csu-next



                  ::= { ncm-csu 6004 }


        ncmcsuThresholdIntervalEntry OBJECT-TYPE
        SYNTAX NcmcsuThresholdIntervalEntry
        ACCESS not-accessible
        STATUS mandatory
        DESCRIPTION
               "An entry in the ncmcsu ThresholdInterval table."
        INDEX   { ncmcsuNIDThresholdIntervalIndex, ncmcsuThresholdIntervalIndex }
        ::= { ncmcsuThresholdIntervalTable 1 }


        NcmcsuThresholdIntervalEntry ::=
        SEQUENCE {

	     ncmcsuNIDThresholdIntervalIndex
		  INTEGER,
             ncmcsuThresholdIntervalIndex
                 INTEGER,
             ncmcsuBERThreshold
                 INTEGER,
             ncmcsubpvSecThreshold
                 INTEGER,
             ncmcsubpvSecInterval
                 INTEGER,
             ncmcsuESThreshold
                 INTEGER,
             ncmcsuESInterval
                 INTEGER,
             ncmcsuUASThreshold
                 INTEGER,
             ncmcsuUASInterval
                 INTEGER
                }

	ncmcsuNIDThresholdIntervalIndex OBJECT-TYPE
        SYNTAX  INTEGER
        ACCESS  read-only
        STATUS  mandatory
        DESCRIPTION
	"This variable specifies the node id of the node."
        ::= { ncmcsuThresholdIntervalEntry 1 }





        ncmcsuThresholdIntervalIndex OBJECT-TYPE
        SYNTAX  INTEGER
        ACCESS  read-only
        STATUS  mandatory
        DESCRIPTION
	"This variable specifies the interface index."
        ::= { ncmcsuThresholdIntervalEntry 2 }



	ncmcsuBERThreshold OBJECT-TYPE
        SYNTAX INTEGER {

                       disable(1),
                       ten-to-Four(2),
                       ten-to-Five(3),
                       ten-to-Six(4),
                       ten-to-Seven(5),
                       ten-to-Eight(6),
                       ten-to-Nine(7)
 
               } 
        ACCESS read-write
        STATUS mandatory
        DESCRIPTION
               "The ncmcsu Net/Eq ber threshold."
        ::= { ncmcsuThresholdIntervalEntry 3 }
 
 
 
        ncmcsubpvSecThreshold OBJECT-TYPE
        SYNTAX INTEGER 
        ACCESS read-write
        STATUS mandatory
        DESCRIPTION
               "The ncmcsu Net/Eq bpv sec threshold."
        ::= { ncmcsuThresholdIntervalEntry 4 }
 
 
        ncmcsubpvSecInterval OBJECT-TYPE
        SYNTAX INTEGER
        ACCESS read-write
        STATUS mandatory
        DESCRIPTION
               "The ncmcsu Net/Eq bpv sec interval."
        ::= { ncmcsuThresholdIntervalEntry 5 }
 
 
        ncmcsuESThreshold OBJECT-TYPE
        SYNTAX INTEGER 
        ACCESS read-write
        STATUS mandatory
        DESCRIPTION
               "The ncmcsu Net/Eq es threshold."
        ::= { ncmcsuThresholdIntervalEntry 6 }
 
 
        ncmcsuESInterval OBJECT-TYPE
        SYNTAX INTEGER
        ACCESS read-write
        STATUS mandatory
        DESCRIPTION
               "The ncmcsu Net/Eq es interval."
        ::= { ncmcsuThresholdIntervalEntry 7 }


	ncmcsuUASThreshold OBJECT-TYPE
        SYNTAX INTEGER 
        ACCESS read-write
        STATUS mandatory
        DESCRIPTION
               "The ncmcsu Net/Eq uas threshold."
          ::= { ncmcsuThresholdIntervalEntry 8 }
 
 
        ncmcsuUASInterval OBJECT-TYPE
        SYNTAX INTEGER
        ACCESS read-write
        STATUS mandatory
        DESCRIPTION
               "The ncmcsu Net/Eq uas interval."
        ::= { ncmcsuThresholdIntervalEntry 9 }



	 -- the ncm csu Current Table1

     -- The ncm csu  current table1 contains various statistics being
     -- collected for the current 15 minute interval.

         ncmcsuCurrentOneTable OBJECT-TYPE
             SYNTAX  SEQUENCE OF NcmcsuCurrentOneEntry
             ACCESS  not-accessible
             STATUS  mandatory
	     DESCRIPTION
                "The ncmcsu Current table1."


		 	--DEFAULT test-function    csucommon-test
                        --DEFAULT set-function    null-set-proc
                        --DEFAULT next-function    csucommon-next
		
		
            ::= { ncm-csu 6005 }


         ncmcsuCurrentOneEntry OBJECT-TYPE
             SYNTAX  NcmcsuCurrentOneEntry
             ACCESS  not-accessible
             STATUS  mandatory
             DESCRIPTION
                "An entry in the ncmcsu Current table1."
            INDEX   { ncmcsuNIDCurrentIndex1, ncmcsuCurrentIndex1, ncmcsuCurrentEndType1 }
            ::= { ncmcsuCurrentOneTable 1 }

	 NcmcsuCurrentOneEntry ::=
         SEQUENCE {
	
	     ncmcsuNIDCurrentIndex1
		INTEGER,
             ncmcsuCurrentIndex1
                 INTEGER,
	     ncmcsuCurrentEndType1
		 INTEGER,
             ncmcsuCurrentESs
                 Gauge,
             ncmcsuCurrentSESs
                 Gauge,
             ncmcsuCurrentSEFSs
                 Gauge,
             ncmcsuCurrentUASs
                 Gauge,
             ncmcsuCurrentCSSs
                 Gauge,
             ncmcsuCurrentPCVs
                 Gauge,
             ncmcsuCurrentLESs
                 Gauge,
             ncmcsuCurrentBESs
                 Gauge,
             ncmcsuCurrentDMs
                 Gauge,
             ncmcsuCurrentLCVs
                 Gauge
         }

	 ncmcsuNIDCurrentIndex1 OBJECT-TYPE
             SYNTAX  INTEGER (1..'7fffffff'h)
             ACCESS  read-only
             STATUS  mandatory
             DESCRIPTION
                "This variable specifies the node id of the node"
            ::= { ncmcsuCurrentOneEntry 1 }
 
 
         ncmcsuCurrentIndex1 OBJECT-TYPE
             SYNTAX  INTEGER (1..'7fffffff'h)
             ACCESS  read-only
             STATUS  mandatory
             DESCRIPTION
                "The index value which uniquely identifies  the
                ncmcsu  interface  to which this entry is applica-
                ble.  The interface identified by a  particular
                value  of  this  index is the same interface as
                identified by the same value as a ncmcsuLineIndex
                object instance."
            ::= { ncmcsuCurrentOneEntry 2 }


	ncmcsuCurrentEndType1 OBJECT-TYPE
             SYNTAX INTEGER {
 
                       near-End(1),
                       far-End(2)
 
                        }
             ACCESS read-only
             STATUS mandatory
             DESCRIPTION
             "The variable specifies the End Type   ."

	            ::= { ncmcsuCurrentOneEntry 3 }

 
 
         ncmcsuCurrentESs OBJECT-TYPE
             SYNTAX  Gauge
             ACCESS  read-only
             STATUS  mandatory
             DESCRIPTION
                "The number of Errored Seconds, encountered  by
                a ncmcsu interface in the current 15 minute inter-
                val."
            ::= { ncmcsuCurrentOneEntry 4 }
 
 
         ncmcsuCurrentSESs OBJECT-TYPE
             SYNTAX  Gauge
             ACCESS  read-only
             STATUS  mandatory
             DESCRIPTION
                "The number of Severely Errored Seconds encoun-
                tered  by  a  ncmcsu  interface  in the current 15
                minute interval."
            ::= { ncmcsuCurrentOneEntry 5 }

	 ncmcsuCurrentSEFSs OBJECT-TYPE
             SYNTAX  Gauge
             ACCESS  read-only
             STATUS  mandatory
             DESCRIPTION
                "The number of Severely Errored Framing Seconds
                encountered  by  a ncmcsu interface in the current
                15 minute interval."
            ::= { ncmcsuCurrentOneEntry 6 }
 
 
         ncmcsuCurrentUASs OBJECT-TYPE
             SYNTAX  Gauge
             ACCESS  read-only
             STATUS  mandatory
             DESCRIPTION
                "The number of Unavailable Seconds  encountered
                by a ncmcsu interface in the current 15 minute in-
                terval."
            ::= { ncmcsuCurrentOneEntry 7 }
 
 
         ncmcsuCurrentCSSs OBJECT-TYPE
             SYNTAX  Gauge
             ACCESS  read-only
             STATUS  mandatory
             DESCRIPTION
                "The number of Controlled Slip Seconds  encoun-
                tered  by  a  ncmcsu  interface  in the current 15
                minute interval."

	--DEFAULT get-function    get-dummy-counter
		
                                  ::= { ncmcsuCurrentOneEntry 8 }
 
 
         ncmcsuCurrentPCVs OBJECT-TYPE
             SYNTAX  Gauge
             ACCESS  read-only
             STATUS  mandatory
             DESCRIPTION
                "The number of Path Coding  Violations  encoun-
                tered  by  a  ncmcsu  interface  in the current 15
                minute interval."
	--DEFAULT get-function    get-dummy-counter
	    
                                    ::= { ncmcsuCurrentOneEntry 9 }
 

	 ncmcsuCurrentLESs OBJECT-TYPE
             SYNTAX  Gauge
             ACCESS  read-only
             STATUS  mandatory
             DESCRIPTION
                "The number of Line Errored Seconds encountered
                by a ncmcsu interface in the current 15 minute in-
                terval."
            ::= { ncmcsuCurrentOneEntry 10 }
 
 
         ncmcsuCurrentBESs OBJECT-TYPE
             SYNTAX Gauge
             ACCESS read-only
             STATUS mandatory
             DESCRIPTION
                "The number of Bursty  Errored  Seconds  (BESs)
                encountered  by  a ncmcsu interface in the current
                15 minute interval."
            ::= {ncmcsuCurrentOneEntry 11 }
 
 
         ncmcsuCurrentDMs OBJECT-TYPE
             SYNTAX Gauge
             ACCESS read-only
             STATUS mandatory
             DESCRIPTION
                "The number of Degraded Minutes  (DMs)  encoun-
                tered  by  a  ncmcsu  interface  in the current 15
                minute interval."

		--DEFAULT get-function    get-dummy-counter
		
                                  ::= { ncmcsuCurrentOneEntry 12 }
 
 
         ncmcsuCurrentLCVs OBJECT-TYPE
             SYNTAX Gauge
             ACCESS read-only
             STATUS mandatory
             DESCRIPTION
                "The number of Line Code Violations (LCVs)  en-
                countered  by a ncmcsu interface in the current 15
                minute interval."

	--DEFAULT get-function    get-dummy-counter

	
                        
         ::= {ncmcsuCurrentOneEntry 13 }




	    -- the ncm csu Interval Table1

     -- The ncmcsu Interval Table1 contains various statistics
     -- collected by each ncmcsu Interface over the previous 24 hours of
     -- operation.  The past 24 hours are broken into 96 completed
     -- 15 minute intervals.

         ncmcsuIntervalOneTable OBJECT-TYPE
             SYNTAX  SEQUENCE OF NcmcsuIntervalOneEntry
             ACCESS  not-accessible
             STATUS  mandatory
             DESCRIPTION
                "The ncmcsu Interval table1."
		 --DEFAULT test-function    csucommoninterval-test
                        --DEFAULT set-function     null-set-proc
                        --DEFAULT next-function    csucommoninterval-next
		

	    ::= { ncm-csu 6006 }


         ncmcsuIntervalOneEntry OBJECT-TYPE
             SYNTAX  NcmcsuIntervalOneEntry
             ACCESS  not-accessible
             STATUS  mandatory
             DESCRIPTION
                "An entry in the ncmcsu Interval table1."
            INDEX   { ncmcsuNIDIntervalIndex1, ncmcsuIntervalIndex1,ncmcsuIntervalEndType1, ncmcsuIntervalNumber1 }
            ::= { ncmcsuIntervalOneTable 1 }
             
     NcmcsuIntervalOneEntry ::=
         SEQUENCE {
               
             ncmcsuNIDIntervalIndex1
                INTEGER,
             ncmcsuIntervalIndex1
                 INTEGER,
	     ncmcsuIntervalEndType1
		INTEGER,
             ncmcsuIntervalNumber1
                 INTEGER,
	     ncmcsuIntervalESs
                 Gauge,
             ncmcsuIntervalSESs
                 Gauge,
             ncmcsuIntervalSEFSs
                 Gauge,
             ncmcsuIntervalUASs
                 Gauge,
             ncmcsuIntervalCSSs
                 Gauge,
             ncmcsuIntervalPCVs
                 Gauge,
             ncmcsuIntervalLESs
                 Gauge,
             ncmcsuIntervalBESs
                 Gauge,
             ncmcsuIntervalDMs
                 Gauge,
             ncmcsuIntervalLCVs
                 Gauge
         }
 
 
	ncmcsuNIDIntervalIndex1 OBJECT-TYPE
             SYNTAX  INTEGER (1..'7fffffff'h)
             ACCESS  read-only
             STATUS  mandatory
             DESCRIPTION
                "This variable specifies the node id of the node"
            ::= { ncmcsuIntervalOneEntry 1 }
             
         
 
        ncmcsuIntervalIndex1 OBJECT-TYPE
             SYNTAX  INTEGER (1..'7fffffff'h)
             ACCESS  read-only
             STATUS  mandatory
             DESCRIPTION
                "The index value which uniquely identifies  the
                ncmcsu  interface  to which this entry is applica-
                ble.  The interface identified by a  particular
                value  of  this  index is the same interface as
                identified by the same value as a ncmcsuLineIndex
                object instance."
            ::= { ncmcsuIntervalOneEntry 2 }


	 ncmcsuIntervalEndType1 OBJECT-TYPE
             SYNTAX INTEGER {
 
                       near-End(1),
                       far-End(2)
 
                        }
             ACCESS read-only
             STATUS mandatory
             DESCRIPTION
             "The variable specifies the End Type   ."
 
             ::= { ncmcsuIntervalOneEntry 3 }

             
 
         ncmcsuIntervalNumber1 OBJECT-TYPE
             SYNTAX  INTEGER (1..96)
             ACCESS  read-only
             STATUS  mandatory
             DESCRIPTION
                "A number between 1 and 96, where 1 is the most
                recently completed 15 minute interval and 96 is
                the least recently completed 15 minutes  inter-
                val   (assuming   that  all  96  intervals  are
                valid)."
            ::= { ncmcsuIntervalOneEntry 4 }
             
         ncmcsuIntervalESs OBJECT-TYPE
             SYNTAX  Gauge
             ACCESS  read-only
             STATUS  mandatory
             DESCRIPTION
                "The number of Errored Seconds encountered by a
                ncmcsu  interface in one of the previous 96, indi-
                vidual 15 minute, intervals."
            ::= { ncmcsuIntervalOneEntry 5 }
             
 
         ncmcsuIntervalSESs OBJECT-TYPE
             SYNTAX  Gauge
             ACCESS  read-only
             STATUS  mandatory
             DESCRIPTION
                "The number of Severely Errored Seconds encoun-
                tered by a ncmcsu interface in one of the previous
                96, individual 15 minute, intervals."
            ::= { ncmcsuIntervalOneEntry 6 }


	 ncmcsuIntervalSEFSs OBJECT-TYPE
             SYNTAX  Gauge
             ACCESS  read-only
             STATUS  mandatory
             DESCRIPTION
                "The number of Severely Errored Framing Seconds
                encountered  by  a  ncmcsu interface in one of the
                previous 96, individual 15 minute, intervals."
            ::= { ncmcsuIntervalOneEntry 7 }
             
 
         ncmcsuIntervalUASs OBJECT-TYPE
             SYNTAX  Gauge
             ACCESS  read-only
             STATUS  mandatory
             DESCRIPTION
                "The number of Unavailable Seconds  encountered
                by  a  ncmcsu interface in one of the previous 96,
                individual 15 minute, intervals."
            ::= { ncmcsuIntervalOneEntry 8 }
             
 
         ncmcsuIntervalCSSs OBJECT-TYPE
             SYNTAX  Gauge
             ACCESS  read-only
             STATUS  mandatory
             DESCRIPTION
                "The number of Controlled Slip Seconds  encoun-
                tered by a ncmcsu interface in one of the previous
                96, individual 15 minute, intervals."

		--DEFAULT get-function    get-dummy-counter		
                                    ::= { ncmcsuIntervalOneEntry 9 }
             
 
         ncmcsuIntervalPCVs OBJECT-TYPE
             SYNTAX  Gauge
             ACCESS  read-only
             STATUS  mandatory
             DESCRIPTION
                "The number of Path Coding  Violations  encoun-
                tered by a ncmcsu interface in one of the previous
                96, individual 15 minute, intervals."

		--DEFAULT get-function    get-dummy-counter	
                      
            ::= { ncmcsuIntervalOneEntry 10 }
             
 
         ncmcsuIntervalLESs OBJECT-TYPE
             SYNTAX  Gauge
             ACCESS  read-only
             STATUS  mandatory
             DESCRIPTION
                "The number of Line Errored Seconds encountered
                by  a  ncmcsu interface in one of the previous 96,
                individual 15 minute, intervals."
            ::= { ncmcsuIntervalOneEntry 11 }



	 ncmcsuIntervalBESs OBJECT-TYPE
             SYNTAX Gauge
             ACCESS read-only
             STATUS mandatory
             DESCRIPTION
                "The number of Bursty  Errored  Seconds  (BESs)
                encountered  by  a  ncmcsu interface in one of the
                previous 96, individual 15 minute, intervals."
            ::= {ncmcsuIntervalOneEntry 12 }
             
 
        ncmcsuIntervalDMs OBJECT-TYPE
             SYNTAX Gauge
             ACCESS read-only
             STATUS mandatory
             DESCRIPTION
                "The number of Degraded Minutes  (DMs)  encoun-
                tered by a ncmcsu interface in one of the previous
                96, individual 15 minute, intervals."
	--DEFAULT get-function    get-dummy-counter	
                                    ::= { ncmcsuIntervalOneEntry 13 }
             
 
         ncmcsuIntervalLCVs OBJECT-TYPE
             SYNTAX Gauge
             ACCESS read-only
             STATUS mandatory
             DESCRIPTION
                "The number of Line Code Violations (LCVs)  en-
                countered  by a ncmcsu interface in the current 15
                minute interval."

	--DEFAULT get-function    get-dummy-counter	
                                 ::= {ncmcsuIntervalOneEntry 14 }



	 -- the ncm csu Total Table1

     -- The ncm csu Total Table1 contains the cumulative sum of the
     -- various statistics for the 24 hour period preceding the
     -- current interval.

         ncmcsuTotalOneTable OBJECT-TYPE
             SYNTAX  SEQUENCE OF NcmcsuTotalOneEntry
             ACCESS  not-accessible
             STATUS  mandatory
             DESCRIPTION
                "The ncmcsu Total table.  24 hour interval."
		 --DEFAULT test-function    csucommon-test
                        --DEFAULT set-function    null-set-proc
                        --DEFAULT next-function    csucommon-next
	
		             ::= { ncm-csu 6007 }


         ncmcsuTotalOneEntry OBJECT-TYPE
             SYNTAX  NcmcsuTotalOneEntry
             ACCESS  not-accessible
             STATUS  mandatory
             DESCRIPTION
                "An entry in the ncmcsu Total table."
            INDEX   { ncmcsuNIDTotalIndex1, ncmcsuTotalIndex1, ncmcsuTotalEndType1 }
            ::= { ncmcsuTotalOneTable 1 }

	 NcmcsuTotalOneEntry ::=
         SEQUENCE {
                 
             ncmcsuNIDTotalIndex1
                 INTEGER,
             ncmcsuTotalIndex1
                 INTEGER,
	     ncmcsuTotalEndType1
		INTEGER,
             ncmcsuTotalESs
                 Gauge,
             ncmcsuTotalSESs
                 Gauge,
             ncmcsuTotalSEFSs
                 Gauge,
             ncmcsuTotalUASs
                 Gauge,
             ncmcsuTotalCSSs
                 Gauge,
             ncmcsuTotalPCVs
                 Gauge,
             ncmcsuTotalLESs
                 Gauge,
             ncmcsuTotalBESs
                 Gauge,
             ncmcsuTotalDMs
                 Gauge,
             ncmcsuTotalLCVs
                 Gauge
         }
 
         ncmcsuNIDTotalIndex1 OBJECT-TYPE
             SYNTAX  INTEGER (1..'7fffffff'h)
             ACCESS  read-only
             STATUS  mandatory
             DESCRIPTION
                "This variable specifies the node id of the node"
            ::= { ncmcsuTotalOneEntry 1 }
 
 
         ncmcsuTotalIndex1 OBJECT-TYPE
             SYNTAX  INTEGER (1..'7fffffff'h)
             ACCESS  read-only
             STATUS  mandatory
             DESCRIPTION
                "The index value which uniquely identifies  the
                ncmcsu  interface  to which this entry is applica-
                ble.  The interface identified by a  particular
                value  of  this  index is the same interface as
                identified by the same value as a ncmcsuLineIndex
                object instance."
            ::= { ncmcsuTotalOneEntry 2 }


	ncmcsuTotalEndType1 OBJECT-TYPE
             SYNTAX INTEGER {
 
                       near-End(1),
                       far-End(2)
 
                        }
             ACCESS read-only
             STATUS mandatory
             DESCRIPTION
             "The variable specifies the End Type   ."
 
             ::= { ncmcsuTotalOneEntry 3 }

 
         ncmcsuTotalESs OBJECT-TYPE
             SYNTAX  Gauge
             ACCESS  read-only
             STATUS  mandatory
             DESCRIPTION
                "The number of Errored Seconds encountered by a
                ncmcsu interface in the previous 24 hour interval"
            ::= { ncmcsuTotalOneEntry 4 }


	ncmcsuTotalSESs OBJECT-TYPE
             SYNTAX  Gauge
             ACCESS  read-only
             STATUS  mandatory
             DESCRIPTION
                "The number of Severely Errored Seconds encoun-
                tered  by  a  ncmcsu  interface in the previous 24
                hour interval."
            ::= { ncmcsuTotalOneEntry 5 }
 
 
         ncmcsuTotalSEFSs OBJECT-TYPE
             SYNTAX  Gauge
             ACCESS  read-only
             STATUS  mandatory
             DESCRIPTION
                "The number of Severely Errored Framing Seconds
                encountered  by a ncmcsu interface in the previous
                24 hour interval."
            ::= { ncmcsuTotalOneEntry 6 }
 
 
         ncmcsuTotalUASs OBJECT-TYPE
             SYNTAX  Gauge
             ACCESS  read-only
             STATUS  mandatory
             DESCRIPTION
                "The number of Unavailable Seconds  encountered
                by  a ncmcsu interface in the previous 24 hour in-
                terval."
            ::= { ncmcsuTotalOneEntry 7 }
 
        ncmcsuTotalCSSs OBJECT-TYPE
             SYNTAX  Gauge
             ACCESS  read-only
             STATUS  mandatory
             DESCRIPTION
                "The number of Controlled Slip Seconds  encoun-
                tered  by  a  ncmcsu  interface in the previous 24
                hour interval."

		
                        --DEFAULT get-function    get-dummy-counter

            ::= { ncmcsuTotalOneEntry 8 }
 
 
         ncmcsuTotalPCVs OBJECT-TYPE
             SYNTAX  Gauge
             ACCESS  read-only
             STATUS  mandatory
             DESCRIPTION
                "The number of Path Coding  Violations  encoun-
                tered  by  a  ncmcsu  interface in the previous 24
                hour interval."

		
                        --DEFAULT get-function    get-dummy-counter

            ::= { ncmcsuTotalOneEntry 9 }

	 ncmcsuTotalLESs OBJECT-TYPE
             SYNTAX  Gauge
             ACCESS  read-only
             STATUS  mandatory
             DESCRIPTION
                "The number of Line Errored Seconds encountered
                by  a ncmcsu interface in the previous 24 hour in-
                terval."
            ::= { ncmcsuTotalOneEntry 10 }
 
 
         ncmcsuTotalBESs OBJECT-TYPE
             SYNTAX Gauge
             ACCESS read-only
             STATUS mandatory
             DESCRIPTION
                "The number of Bursty  Errored  Seconds  (BESs)
                encountered  by a ncmcsu interface in the previous
                24 hour interval."
            ::= { ncmcsuTotalOneEntry 11 }
 
 
         ncmcsuTotalDMs OBJECT-TYPE
             SYNTAX Gauge
             ACCESS read-only
             STATUS mandatory
             DESCRIPTION
                "The number of Degraded Minutes  (DMs)  encoun-
                tered  by  a  ncmcsu  interface in the previous 24
                hour interval."

		
                        --DEFAULT get-function    get-dummy-counter

            ::= { ncmcsuTotalOneEntry 12 }
 
         ncmcsuTotalLCVs OBJECT-TYPE
             SYNTAX Gauge
             ACCESS read-only
             STATUS mandatory
             DESCRIPTION
                "The number of Line Code Violations (LCVs)  en-
                countered  by a ncmcsu interface in the current 15
                minute interval."

		
                        --DEFAULT get-function    get-dummy-counter

         ::= {ncmcsuTotalOneEntry 13 }



	-- the ncm csu Enhanced Current Table

     -- The ncm csu enhanced current table contains various statistics being
     -- collected for the current 15 minute interval.

         ncmcsuEnhancedCurrentTable OBJECT-TYPE
             SYNTAX  SEQUENCE OF NcmcsuEnhancedCurrentEntry
             ACCESS  not-accessible
             STATUS  mandatory
             DESCRIPTION
                "The ncm csu enhanced Current table."
			 --DEFAULT test-function    csucommon-test
                        --DEFAULT set-function    null-set-proc
                        --DEFAULT next-function    csucommon-next
		
            ::= { ncm-csu 6008 }


         ncmcsuEnhancedCurrentEntry OBJECT-TYPE
             SYNTAX  NcmcsuEnhancedCurrentEntry
             ACCESS  not-accessible
             STATUS  mandatory
             DESCRIPTION
                "An entry in the ncmcsu Enhanced Current table."
            INDEX   { ncmcsuNIDEnhancedCurrentIndex, ncmcsuEnhancedCurrentIndex, ncmcsuEnhancedCurrentEndType }
            ::= { ncmcsuEnhancedCurrentTable 1 }

         NcmcsuEnhancedCurrentEntry ::=
         SEQUENCE {
         
             ncmcsuNIDEnhancedCurrentIndex
                INTEGER,
             ncmcsuEnhancedCurrentIndex
                 INTEGER,
	     ncmcsuEnhancedCurrentEndType
		 INTEGER,
             ncmcsuEnhancedCurrentESs
                 Gauge,
             ncmcsuEnhancedCurrentSESs
                 Gauge,           
             ncmcsuEnhancedCurrentUASs
                 Gauge,
	     ncmcsuEnhancedCurrentCSSs
                 Gauge,
             ncmcsuEnhancedCurrentBESs
                 Gauge,
	      ncmcsuEnhancedCurrentLOFC
                Gauge

                     }

	ncmcsuNIDEnhancedCurrentIndex OBJECT-TYPE
             SYNTAX  INTEGER (1..'7fffffff'h)
             ACCESS  read-only
             STATUS  mandatory
             DESCRIPTION
                "This variable specifies the node id of the node"
            ::= { ncmcsuEnhancedCurrentEntry 1 }
 
 
         ncmcsuEnhancedCurrentIndex OBJECT-TYPE
             SYNTAX  INTEGER (1..'7fffffff'h)
             ACCESS  read-only
             STATUS  mandatory
             DESCRIPTION
                "The index value which uniquely identifies  the
                ncmcsu  interface  to which this entry is applica-
                ble.  The interface identified by a  particular
                value  of  this  index is the same interface as
                identified by the same value as a ncmcsuLineIndex
                object instance."
            ::= { ncmcsuEnhancedCurrentEntry 2 }

	ncmcsuEnhancedCurrentEndType OBJECT-TYPE
             SYNTAX INTEGER {
 
                       near-End(1),
                       far-End(2)
 
                        }
             ACCESS read-only
             STATUS mandatory
             DESCRIPTION
             "The variable specifies the End Type   ."
 
             ::= { ncmcsuEnhancedCurrentEntry 3 }

 
 
         ncmcsuEnhancedCurrentESs OBJECT-TYPE
             SYNTAX  Gauge
             ACCESS  read-only
             STATUS  mandatory
             DESCRIPTION
                "The number of Errored Seconds, encountered  by
                a ncmcsu interface in the current 15 minute inter-
                val."
            ::= { ncmcsuEnhancedCurrentEntry 4 }
 
 
         ncmcsuEnhancedCurrentSESs OBJECT-TYPE
             SYNTAX  Gauge
             ACCESS  read-only
             STATUS  mandatory
             DESCRIPTION
                "The number of Severely Errored Seconds encoun-
                tered  by  a  ncmcsu  interface  in the current 15
                minute interval."
            ::= { ncmcsuEnhancedCurrentEntry 5 }
 
        
	ncmcsuEnhancedCurrentUASs OBJECT-TYPE
             SYNTAX  Gauge
             ACCESS  read-only
             STATUS  mandatory
             DESCRIPTION
                "The number of Unavailable Seconds  encountered
                by a ncmcsu interface in the current 15 minute in-
                terval."
            ::= { ncmcsuEnhancedCurrentEntry 6 }


	ncmcsuEnhancedCurrentCSSs OBJECT-TYPE
             SYNTAX  Gauge
             ACCESS  read-only
             STATUS  mandatory
             DESCRIPTION
                "The number of Controlled Slip Seconds  encoun-
                tered by a ncmcsu interface in the current 15 minute
                intervals."
          ::= { ncmcsuEnhancedCurrentEntry 7 }

 
 
        
 
         
         ncmcsuEnhancedCurrentBESs OBJECT-TYPE
             SYNTAX Gauge
             ACCESS read-only
             STATUS mandatory
             DESCRIPTION
                "The number of Bursty  Errored  Seconds  (BESs)
                encountered  by  a ncmcsu interface in the current
                15 minute interval."
            ::= {ncmcsuEnhancedCurrentEntry 8 }



	
	  ncmcsuEnhancedCurrentLOFC OBJECT-TYPE
             SYNTAX Gauge
             ACCESS read-only
             STATUS mandatory
             DESCRIPTION
                "The number of LOFC
                encountered  by  a  ncmcsu interface in the current
                15 minute intervals."
            ::= {ncmcsuEnhancedCurrentEntry 9 }


	 -- the ncm csu Enhanced Interval Table

     -- The ncm csu Enhanced  Interval Table contains various statistics
     -- collected by each ncmcsu Interface over the previous 24 hours of
     -- operation.  The past 24 hours are broken into 96 completed
     -- 15 minute intervals.

         ncmcsuEnhancedIntervalTable OBJECT-TYPE
             SYNTAX  SEQUENCE OF NcmcsuEnhancedIntervalEntry
             ACCESS  not-accessible
             STATUS  mandatory
             DESCRIPTION
                "The ncmcsu Interval table1."
			 --DEFAULT test-function    csucommoninterval-test
                        --DEFAULT set-function     null-set-proc
                        --DEFAULT next-function    csucommoninterval-next
	
            ::= { ncm-csu 6009 }


         ncmcsuEnhancedIntervalEntry OBJECT-TYPE
             SYNTAX  NcmcsuEnhancedIntervalEntry
             ACCESS  not-accessible
             STATUS  mandatory
             DESCRIPTION
                "An entry in the ncmcsu Enhanced Interval table."
            INDEX   { ncmcsuNIDEnhancedIntervalIndex, ncmcsuEnhancedIntervalIndex,ncmcsuEnhancedIntervalEndType, ncmcsuEnhancedIntervalNumber }
            ::= { ncmcsuEnhancedIntervalTable 1 }

    	 NcmcsuEnhancedIntervalEntry ::=
         SEQUENCE {

             ncmcsuNIDEnhancedIntervalIndex
                INTEGER,
             ncmcsuEnhancedIntervalIndex
                 INTEGER,
             ncmcsuEnhancedIntervalEndType
                INTEGER,
             ncmcsuEnhancedIntervalNumber
                 INTEGER,
             ncmcsuEnhancedIntervalESs
                 Gauge,
             ncmcsuEnhancedIntervalSESs
                 Gauge,
             ncmcsuEnhancedIntervalUASs
                 Gauge,
             ncmcsuEnhancedIntervalCSSs
                 Gauge,
             ncmcsuEnhancedIntervalBESs
                 Gauge,
	     ncmcsuEnhancedIntervalLOFC
                 Gauge

	     
                      }


 	ncmcsuNIDEnhancedIntervalIndex OBJECT-TYPE
             SYNTAX  INTEGER (1..'7fffffff'h)
             ACCESS  read-only
             STATUS  mandatory
             DESCRIPTION
                "This variable specifies the node id of the node"
            ::= { ncmcsuEnhancedIntervalEntry 1 }
          
         
         
        ncmcsuEnhancedIntervalIndex OBJECT-TYPE
             SYNTAX  INTEGER (1..'7fffffff'h)
             ACCESS  read-only
             STATUS  mandatory
             DESCRIPTION
                "The index value which uniquely identifies  the
                ncmcsu  interface  to which this entry is applica-
                ble.  The interface identified by a  particular
                value  of  this  index is the same interface as
                identified by the same value as a ncmcsuLineIndex
                object instance."
            ::= { ncmcsuEnhancedIntervalEntry 2 }
 
 
         ncmcsuEnhancedIntervalEndType OBJECT-TYPE
             SYNTAX INTEGER {
 
                       near-End(1),
                       far-End(2)
 
                        }
             ACCESS read-only
             STATUS mandatory
             DESCRIPTION
             "The variable specifies the End Type   ."
 
             ::= { ncmcsuEnhancedIntervalEntry 3 }
 
         
 
         ncmcsuEnhancedIntervalNumber OBJECT-TYPE
             SYNTAX  INTEGER (1..96)
             ACCESS  read-only
             STATUS  mandatory
             DESCRIPTION
                "A number between 1 and 96, where 1 is the most
                recently completed 15 minute interval and 96 is
                the least recently completed 15 minutes  inter-
                val   (assuming   that  all  96  intervals  are
                valid)."
            ::= { ncmcsuEnhancedIntervalEntry 4 }

	

	 ncmcsuEnhancedIntervalESs OBJECT-TYPE
             SYNTAX  Gauge
             ACCESS  read-only
             STATUS  mandatory
             DESCRIPTION
                "The number of Errored Seconds encountered by a
                ncmcsu  interface in one of the previous 96, indi-
                vidual 15 minute, intervals."
            ::= { ncmcsuEnhancedIntervalEntry 5 }
          
 
         ncmcsuEnhancedIntervalSESs OBJECT-TYPE
             SYNTAX  Gauge
             ACCESS  read-only
             STATUS  mandatory
             DESCRIPTION
                "The number of Severely Errored Seconds encoun-
                tered by a ncmcsu interface in one of the previous
                96, individual 15 minute, intervals."
            ::= { ncmcsuEnhancedIntervalEntry 6 }

	 ncmcsuEnhancedIntervalUASs OBJECT-TYPE
             SYNTAX  Gauge
             ACCESS  read-only
             STATUS  mandatory
             DESCRIPTION
                "The number of Unavailable Seconds  encountered
                by  a  ncmcsu interface in one of the previous 96,
                individual 15 minute, intervals."
            ::= { ncmcsuEnhancedIntervalEntry 7 }
          
 
         ncmcsuEnhancedIntervalCSSs OBJECT-TYPE
             SYNTAX  Gauge
             ACCESS  read-only
             STATUS  mandatory
             DESCRIPTION
                "The number of Controlled Slip Seconds  encoun-
                tered by a ncmcsu interface in one of the previous
                96, individual 15 minute, intervals."
          ::= { ncmcsuEnhancedIntervalEntry 8 }


	 ncmcsuEnhancedIntervalBESs OBJECT-TYPE
             SYNTAX Gauge
             ACCESS read-only
             STATUS mandatory
             DESCRIPTION
                "The number of Bursty  Errored  Seconds  (BESs)
                encountered  by  a  ncmcsu interface in one of the
                previous 96, individual 15 minute, intervals."
            ::= {ncmcsuEnhancedIntervalEntry 9 }


	

	 ncmcsuEnhancedIntervalLOFC OBJECT-TYPE
             SYNTAX Gauge
             ACCESS read-only
             STATUS mandatory
             DESCRIPTION
                "The number of LOFC
                encountered  by  a  ncmcsu interface in one of the
                previous 96, individual 15 minute, intervals."
            ::= {ncmcsuEnhancedIntervalEntry 10 }

 



	 -- the ncm csu Enhanced Total Table

     -- The ncmcsu  Enhanced Total Table contains the cumulative sum of the
     -- various statistics for the 24 hour period preceding the
     -- current interval.

         ncmcsuEnhancedTotalTable OBJECT-TYPE
             SYNTAX  SEQUENCE OF NcmcsuEnhancedTotalEntry
             ACCESS  not-accessible
             STATUS  mandatory
             DESCRIPTION
                "The ncmcsu  Enhanced Total table.  24 hour interval."
		 	--DEFAULT test-function    csucommon-test
                        --DEFAULT set-function    null-set-proc
                        --DEFAULT next-function    csucommon-next
		


            ::= { ncm-csu 6010 }


         ncmcsuEnhancedTotalEntry OBJECT-TYPE
             SYNTAX  NcmcsuEnhancedTotalEntry
             ACCESS  not-accessible
             STATUS  mandatory
             DESCRIPTION
                "An entry in the ncmcsu Total table."
            INDEX   { ncmcsuNIDEnhancedTotalIndex, ncmcsuEnhancedTotalIndex, ncmcsuEnhancedTotalEndType }
            ::= { ncmcsuEnhancedTotalTable 1 }

         NcmcsuEnhancedTotalEntry ::=
         SEQUENCE {

             ncmcsuNIDEnhancedTotalIndex
                 INTEGER,
             ncmcsuEnhancedTotalIndex
                 INTEGER,
	     ncmcsuEnhancedTotalEndType
		INTEGER,
             ncmcsuEnhancedTotalESs
                 Gauge,
             ncmcsuEnhancedTotalSESs
                 Gauge,
             ncmcsuEnhancedTotalUASs
                 Gauge,
             ncmcsuEnhancedTotalCSSs
                 Gauge,
             ncmcsuEnhancedTotalBESs
                 Gauge,
             ncmcsuEnhancedTotalLOFC
                 Gauge
                      }

         ncmcsuNIDEnhancedTotalIndex OBJECT-TYPE
             SYNTAX  INTEGER (1..'7fffffff'h)
             ACCESS  read-only
             STATUS  mandatory
             DESCRIPTION
                "This variable specifies the node id of the node"
            ::= { ncmcsuEnhancedTotalEntry 1 }

	 ncmcsuEnhancedTotalIndex OBJECT-TYPE
             SYNTAX  INTEGER (1..'7fffffff'h)
             ACCESS  read-only
             STATUS  mandatory
             DESCRIPTION
                "The index value which uniquely identifies  the
                ncmcsu  interface  to which this entry is applica-
                ble.  The interface identified by a  particular
                value  of  this  index is the same interface as
                identified by the same value as a ncmcsuLineIndex
                object instance."
            ::= { ncmcsuEnhancedTotalEntry 2 }


	     ncmcsuEnhancedTotalEndType OBJECT-TYPE
             SYNTAX INTEGER {
 
                       near-End(1),
                       far-End(2)
 
                        }
             ACCESS read-only
             STATUS mandatory
             DESCRIPTION
             "The variable specifies the End Type   ."
 
             ::= { ncmcsuEnhancedTotalEntry 3 }

 
 
         ncmcsuEnhancedTotalESs OBJECT-TYPE
             SYNTAX  Gauge
             ACCESS  read-only
             STATUS  mandatory
             DESCRIPTION
                "The number of Errored Seconds encountered by a
                ncmcsu interface in the previous 24 hour interval"
            ::= { ncmcsuEnhancedTotalEntry 4 } 
                 
 
        ncmcsuEnhancedTotalSESs OBJECT-TYPE
             SYNTAX  Gauge
             ACCESS  read-only
             STATUS  mandatory
             DESCRIPTION
                "The number of Severely Errored Seconds encoun-
                tered  by  a  ncmcsu  interface in the previous 24
                hour interval."
            ::= { ncmcsuEnhancedTotalEntry 5 } 
 
 
         ncmcsuEnhancedTotalUASs OBJECT-TYPE
             SYNTAX  Gauge
             ACCESS  read-only
             STATUS  mandatory
             DESCRIPTION
                "The number of Unavailable Seconds  encountered
                by  a ncmcsu interface in the previous 24 hour in-
                terval."
            ::= { ncmcsuEnhancedTotalEntry 6 }


	ncmcsuEnhancedTotalCSSs OBJECT-TYPE
             SYNTAX  Gauge
             ACCESS  read-only
             STATUS  mandatory
             DESCRIPTION
                "The number of Controlled Slip Seconds  encoun-
                tered  by  a  ncmcsu  interface in the previous 24
                hour interval."
            ::= { ncmcsuEnhancedTotalEntry 7 }
 
 
         
 
         ncmcsuEnhancedTotalBESs OBJECT-TYPE
             SYNTAX Gauge
             ACCESS read-only
             STATUS mandatory
             DESCRIPTION
                "The number of Bursty  Errored  Seconds  (BESs)
                encountered  by a ncmcsu interface in the previous
                24 hour interval."
            ::= { ncmcsuEnhancedTotalEntry 8 }
 
 
         ncmcsuEnhancedTotalLOFC OBJECT-TYPE
             SYNTAX Gauge
             ACCESS read-only
             STATUS mandatory
             DESCRIPTION
                "The number of LOFC 
                encountered  by a ncmcsu interface in the previous
                24 hour interval."
            ::= { ncmcsuEnhancedTotalEntry 9 }

 

	       


	  -- The ncm csu current table



        ncmcsuCurrentTable OBJECT-TYPE
        SYNTAX SEQUENCE OF NcmcsuCurrentEntry
        ACCESS not-accessible
        STATUS mandatory
	DESCRIPTION
               "The Current Entry table."


	--DEFAULT test-function csucommon-test
        --DEFAULT next-function csucommon-next
	
        ::= { ncm-csu 6011 }



        ncmcsuCurrentEntry OBJECT-TYPE
        SYNTAX NcmcsuCurrentEntry
        ACCESS not-accessible
        STATUS mandatory
        DESCRIPTION
               "An entry in the Current Entry table."
        INDEX   { ncmcsuNIDCurrentIndex, ncmcsuCurrentIndex, ncmcsuCurrentEndType }
        ::= { ncmcsuCurrentTable 1 }


        NcmcsuCurrentEntry ::=
        SEQUENCE {
		ncmcsuNIDCurrentIndex
		INTEGER,
                ncmcsuCurrentIndex
                INTEGER,
		ncmcsuCurrentEndType
		INTEGER,
                ncmcsuCurrentNETOOFS
                Gauge,
                ncmcsuCurrentNETLOSS
                Gauge,
                ncmcsuCurrentNETAISS
                Gauge,
                ncmcsuCurrentNETBERS
                Gauge,
                ncmcsuCurrentNETYELS
                Gauge,
                ncmcsuCurrentNETLOFS
                Gauge,
                ncmcsuCurrentNETESL
                Gauge,
                ncmcsuCurrentNETSEFS
                Gauge,
                ncmcsuCurrentEQOOFS
                Gauge,
                ncmcsuCurrentEQDTED
                Gauge,
                ncmcsuCurrentEQDBER
                Gauge,
		ncmcsuCurrentEQES
		Gauge,
		ncmcsuCurrentEQUAS
		Gauge,
		ncmcsuCurrentEQESL
		Gauge


                }

	ncmcsuNIDCurrentIndex OBJECT-TYPE
        SYNTAX  INTEGER (1..'7fffffff'h)
        ACCESS  read-only
        STATUS  mandatory
        DESCRIPTION
	"This variable specifies the node id of the node."
 
        ::= { ncmcsuCurrentEntry 1 }
        



	ncmcsuCurrentIndex OBJECT-TYPE
        SYNTAX  INTEGER (1..'7fffffff'h)
        ACCESS  read-only
        STATUS  mandatory
        DESCRIPTION
	"This variable specifies the interface index."
        ::= { ncmcsuCurrentEntry 2 }


	ncmcsuCurrentEndType OBJECT-TYPE
             SYNTAX INTEGER {
 
                       near-End(1),
                       far-End(2)
 
                        }
             ACCESS read-only
             STATUS mandatory
             DESCRIPTION
             "The variable specifies the End Type   ."
 
             ::= { ncmcsuCurrentEntry 3 }

        
        
        ncmcsuCurrentNETOOFS OBJECT-TYPE
        SYNTAX Gauge
        ACCESS read-only
        STATUS mandatory
        DESCRIPTION
               "The ncmcsu Current OOFS of Net/Eq."
        ::= { ncmcsuCurrentEntry 4 }
 
 
        ncmcsuCurrentNETLOSS OBJECT-TYPE
        SYNTAX Gauge
        ACCESS read-only
        STATUS mandatory
        DESCRIPTION
               "The ncmcsu Current LOSS of Net/Eq."
        ::= { ncmcsuCurrentEntry 5 }
 
         
 
        ncmcsuCurrentNETAISS OBJECT-TYPE
        SYNTAX Gauge
        ACCESS read-only
        STATUS mandatory
        DESCRIPTION
               "The ncmcsu Current AISS of Net."
        ::= { ncmcsuCurrentEntry 6 }
 
 
        ncmcsuCurrentNETBERS OBJECT-TYPE
        SYNTAX Gauge
        ACCESS read-only
        STATUS mandatory
        DESCRIPTION
               "The ncmcsu Current BERS of Net."
        ::= { ncmcsuCurrentEntry 7 }
 
         ncmcsuCurrentNETYELS OBJECT-TYPE
        SYNTAX Gauge
        ACCESS read-only
        STATUS mandatory
        DESCRIPTION
               "The ncmcsu Current YELS of Net."
        ::= { ncmcsuCurrentEntry 8 }
        
        
        ncmcsuCurrentNETLOFS OBJECT-TYPE
        SYNTAX Gauge
        ACCESS read-only
        STATUS mandatory
        DESCRIPTION
               "The ncmcsu Current LOFS of Net."
        ::= { ncmcsuCurrentEntry 9 }



	ncmcsuCurrentNETESL OBJECT-TYPE
        SYNTAX Gauge
        ACCESS read-only
        STATUS mandatory
        DESCRIPTION
               "The ncmcsu Current ESL of Net."
        ::= { ncmcsuCurrentEntry 10 }
 
         
        ncmcsuCurrentNETSEFS OBJECT-TYPE
        SYNTAX Gauge
        ACCESS read-only
        STATUS mandatory
        DESCRIPTION
               "The ncmcsu Current SEFS of Net."
        ::= { ncmcsuCurrentEntry 11 }

        ncmcsuCurrentEQOOFS OBJECT-TYPE
        SYNTAX Gauge
        ACCESS read-only
        STATUS mandatory
        DESCRIPTION
               "The ncmcsu Current oofs of Eq."
        ::= { ncmcsuCurrentEntry 12 }
 
 
        ncmcsuCurrentEQDTED OBJECT-TYPE
        SYNTAX Gauge
        ACCESS read-only
        STATUS mandatory
        DESCRIPTION
               "The ncmcsu Current dted of Eq."
        ::= { ncmcsuCurrentEntry 13 }
 
 
         
        ncmcsuCurrentEQDBER OBJECT-TYPE
        SYNTAX Gauge
        ACCESS read-only
        STATUS mandatory
        DESCRIPTION
               "The ncmcsu Current dber of Eq."
        ::= { ncmcsuCurrentEntry 14 }

	ncmcsuCurrentEQES OBJECT-TYPE
        SYNTAX Gauge
        ACCESS read-only
        STATUS mandatory
        DESCRIPTION
               "The ncmcsu Current ES of Eq."
        ::= { ncmcsuCurrentEntry 15 }


	ncmcsuCurrentEQUAS OBJECT-TYPE
        SYNTAX Gauge
        ACCESS read-only
        STATUS mandatory
        DESCRIPTION
               "The ncmcsu Current UAS of Eq."
        ::= { ncmcsuCurrentEntry 16 }


	ncmcsuCurrentEQESL OBJECT-TYPE
        SYNTAX Gauge
        ACCESS read-only
        STATUS mandatory
        DESCRIPTION
               "The ncmcsu Current ESL of Eq."
        ::= { ncmcsuCurrentEntry 17 }













	  -- The ncm csu total table



        ncmcsuTotalTable OBJECT-TYPE
        SYNTAX SEQUENCE OF NcmcsuTotalEntry
        ACCESS not-accessible
        STATUS mandatory
		DESCRIPTION
               "The total Entry table."
	 --DEFAULT test-function csucommon-test
        --DEFAULT next-function csucommon-next



        ::= { ncm-csu 6012 }



        ncmcsuTotalEntry OBJECT-TYPE
        SYNTAX NcmcsuTotalEntry
        ACCESS not-accessible
        STATUS mandatory
        DESCRIPTION
               "An entry in the total Entry table."
        INDEX   { ncmcsuNIDTotalIndex, ncmcsuTotalIndex,ncmcsuTotalEndType }
        ::= { ncmcsuTotalTable 1 }

         
         NcmcsuTotalEntry ::=
         SEQUENCE {
		ncmcsuNIDTotalIndex
		INTEGER,
                ncmcsuTotalIndex
                INTEGER,
		ncmcsuTotalEndType
		INTEGER,
                ncmcsuTotalNETOOFS
                Gauge,
                ncmcsuTotalNETLOSS
                Gauge,
                ncmcsuTotalNETAISS
                Gauge,
                ncmcsuTotalNETBERS
                Gauge,
                ncmcsuTotalNETYELS
                Gauge,
                 ncmcsuTotalNETLOFS
                Gauge,
                ncmcsuTotalNETESL
                Gauge,
                ncmcsuTotalNETSEFS
                Gauge,
                ncmcsuTotalEQOOFS
                Gauge,
                ncmcsuTotalEQDTED
                Gauge,
                ncmcsuTotalEQDBER
                Gauge,
		ncmcsuTotalEQES
		Gauge,
		ncmcsuTotalEQUAS
		Gauge,
		ncmcsuTotalEQESL
		Gauge

         
                }
 


	ncmcsuNIDTotalIndex OBJECT-TYPE
        SYNTAX  INTEGER (1..'7fffffff'h)
        ACCESS  read-only
        STATUS  mandatory
        DESCRIPTION
	"This variable specifies the node id of the node ."
        ::= { ncmcsuTotalEntry 1 }


	ncmcsuTotalIndex OBJECT-TYPE
        SYNTAX  INTEGER (1..'7fffffff'h)
        ACCESS  read-only
        STATUS  mandatory
        DESCRIPTION
	"this variable specifies the interface index."
        ::= { ncmcsuTotalEntry 2 }

	ncmcsuTotalEndType OBJECT-TYPE
             SYNTAX INTEGER {
 
                       near-End(1),
                       far-End(2)
 
                        }
             ACCESS read-only
             STATUS mandatory
             DESCRIPTION
             "The variable specifies the End Type   ."
 
             ::= { ncmcsuTotalEntry 3 }

 
        ncmcsuTotalNETOOFS OBJECT-TYPE
        SYNTAX Gauge
        ACCESS read-only
        STATUS mandatory
        DESCRIPTION
               "The ncmcsu Total OOFS of Net."
        ::= { ncmcsuTotalEntry 4 }
 
        ncmcsuTotalNETLOSS OBJECT-TYPE
        SYNTAX Gauge
        ACCESS read-only
        STATUS mandatory
        DESCRIPTION
               "The ncmcsu Total LOSS of Net."
        ::= { ncmcsuTotalEntry 5 }
 
 
        ncmcsuTotalNETAISS OBJECT-TYPE
        SYNTAX Gauge
        ACCESS read-only
        STATUS mandatory
        DESCRIPTION
               "The ncmcsu Total AISS of Net."
        ::= { ncmcsuTotalEntry 6 }
 
 
        ncmcsuTotalNETBERS OBJECT-TYPE
        SYNTAX Gauge
        ACCESS read-only
        STATUS mandatory
        DESCRIPTION
               "The ncmcsu Total BERS of Net."
        ::= { ncmcsuTotalEntry 7 }
 
        ncmcsuTotalNETYELS OBJECT-TYPE
        SYNTAX Gauge
        ACCESS read-only
        STATUS mandatory
        DESCRIPTION
               "The ncmcsu Total YELS of Net."
        ::= { ncmcsuTotalEntry 8 }

        ncmcsuTotalNETLOFS OBJECT-TYPE
        SYNTAX Gauge
        ACCESS read-only
        STATUS mandatory
        DESCRIPTION
               "The ncmcsu Total LOFS of Net."
        ::= { ncmcsuTotalEntry 9 }


	ncmcsuTotalNETESL OBJECT-TYPE
        SYNTAX Gauge
        ACCESS read-only
        STATUS mandatory
        DESCRIPTION
               "The ncmcsu Total ESL of Net."
        ::= { ncmcsuTotalEntry 10 }
 
         
        ncmcsuTotalNETSEFS OBJECT-TYPE
        SYNTAX Gauge
        ACCESS read-only
        STATUS mandatory
        DESCRIPTION
               "The ncmcsu Total SEFS of Net."
        ::= { ncmcsuTotalEntry 11 }
 
 
        ncmcsuTotalEQOOFS OBJECT-TYPE
        SYNTAX Gauge
        ACCESS read-only
        STATUS mandatory
        DESCRIPTION
               "The ncmcsu Total oofs of Eq."
        ::= { ncmcsuTotalEntry 12 }
 
 
 
        ncmcsuTotalEQDTED OBJECT-TYPE
        SYNTAX Gauge
        ACCESS read-only
        STATUS mandatory
        DESCRIPTION
               "The ncmcsu Total dted of Eq."
        ::= { ncmcsuTotalEntry 13 }
 
 
        ncmcsuTotalEQDBER OBJECT-TYPE
        SYNTAX Gauge
        ACCESS read-only
        STATUS mandatory
        DESCRIPTION
               "The ncmcsu Total dber of Eq."
        ::= { ncmcsuTotalEntry 14 }


	ncmcsuTotalEQES OBJECT-TYPE
        SYNTAX Gauge
        ACCESS read-only
        STATUS mandatory
        DESCRIPTION
               "The ncmcsu Total ES of Eq."
        ::= { ncmcsuTotalEntry 15 }


	ncmcsuTotalEQUAS OBJECT-TYPE
        SYNTAX Gauge
        ACCESS read-only
        STATUS mandatory
        DESCRIPTION
               "The ncmcsu Total UAS of Eq."
        ::= { ncmcsuTotalEntry 16 }


	ncmcsuTotalEQESL OBJECT-TYPE
        SYNTAX Gauge
        ACCESS read-only
        STATUS mandatory
        DESCRIPTION
               "The ncmcsu Total ESL of Eq."
        ::= { ncmcsuTotalEntry 17 }





	-- The ncm csu interval table



        ncmcsuIntervalTable OBJECT-TYPE
        SYNTAX SEQUENCE OF NcmcsuIntervalEntry
        ACCESS not-accessible
        STATUS mandatory
		DESCRIPTION
               "The Interval Entry table."
	 --DEFAULT test-function csucommoninterval-test
        --DEFAULT next-function csucommoninterval-next



        ::= { ncm-csu 6013 }



        ncmcsuIntervalEntry OBJECT-TYPE
        SYNTAX NcmcsuIntervalEntry
        ACCESS not-accessible
        STATUS mandatory
        DESCRIPTION
               "An entry in the Interval Entry table."
        INDEX   { ncmcsuNIDIntervalIndex,ncmcsuIntervalIndex, ncmcsuIntervalEndType, ncmcsuIntervalNumber }
        ::= { ncmcsuIntervalTable 1 }



                NcmcsuIntervalEntry ::=
                SEQUENCE {
		ncmcsuNIDIntervalIndex
		INTEGER,
                ncmcsuIntervalIndex
                INTEGER,
		ncmcsuIntervalEndType
		INTEGER,
	        ncmcsuIntervalNumber
                INTEGER,
                ncmcsuIntervalNETOOFS
                Gauge,
                ncmcsuIntervalNETLOSS
                Gauge,
                ncmcsuIntervalNETAISS
                Gauge,
                 ncmcsuIntervalNETBERS
                Gauge,
                ncmcsuIntervalNETYELS
                Gauge,
                ncmcsuIntervalNETLOFS
                Gauge,
                ncmcsuIntervalNETESL
                Gauge,
                ncmcsuIntervalNETSEFS
                Gauge,
                ncmcsuIntervalEQOOFS
                Gauge,
                ncmcsuIntervalEQDTED
                Gauge,
                ncmcsuIntervalEQDBER
                Gauge,
		ncmcsuIntervalEQES
		Gauge,
		ncmcsuIntervalEQUAS
		Gauge,
		ncmcsuIntervalEQESL
		Gauge

         
                }

	ncmcsuNIDIntervalIndex OBJECT-TYPE
             SYNTAX  INTEGER 
             ACCESS  read-only
             STATUS  mandatory
             DESCRIPTION
                "This variable specifies the node id of the node."
            ::= { ncmcsuIntervalEntry 1 }
 
 
	ncmcsuIntervalIndex OBJECT-TYPE
        SYNTAX  INTEGER (1..'7fffffff'h)
        ACCESS  read-only
        STATUS  mandatory
        DESCRIPTION
	"This variable specifies the interface index value."
 
        ::= { ncmcsuIntervalEntry 2 }


	
	ncmcsuIntervalEndType OBJECT-TYPE
             SYNTAX INTEGER {
 
                       near-End(1),
                       far-End(2)
 
                        }
             ACCESS read-only
             STATUS mandatory
             DESCRIPTION
             "The variable specifies the End Type   ."
 
             ::= { ncmcsuIntervalEntry 3 }



        ncmcsuIntervalNumber OBJECT-TYPE
             SYNTAX  INTEGER (1..96)
             ACCESS  read-only
             STATUS  mandatory
             DESCRIPTION
                "A number between 1 and 96, where 1 is the most
                recently completed 15 minute interval and 96 is
                the least recently completed 15 minutes  inter-
                val   (assuming   that  all  96  intervals  are
                valid)."
            ::= { ncmcsuIntervalEntry 4 }

        ncmcsuIntervalNETOOFS OBJECT-TYPE
        SYNTAX Gauge
        ACCESS read-only
        STATUS mandatory
        DESCRIPTION
               "The ncmcsu interval OOFS of Net."
        ::= { ncmcsuIntervalEntry 5 }
 
 
        ncmcsuIntervalNETLOSS OBJECT-TYPE
        SYNTAX Gauge
        ACCESS read-only
        STATUS mandatory
        DESCRIPTION
               "The ncmcsu interval LOSS of Net."
        ::= { ncmcsuIntervalEntry 6 }
                 
        
        ncmcsuIntervalNETAISS OBJECT-TYPE
        SYNTAX Gauge
        ACCESS read-only
        STATUS mandatory
        DESCRIPTION
               "The ncmcsu interval AISS of Net."
        ::= { ncmcsuIntervalEntry 7 }
 
         
        ncmcsuIntervalNETBERS OBJECT-TYPE
        SYNTAX Gauge
        ACCESS read-only
        STATUS mandatory
        DESCRIPTION
               "The ncmcsu interval BERS of Net."
        ::= { ncmcsuIntervalEntry 8 }
	
	ncmcsuIntervalNETYELS OBJECT-TYPE
        SYNTAX Gauge
        ACCESS read-only
        STATUS mandatory
        DESCRIPTION
               "The ncmcsu interval YELS of Net."
        ::= { ncmcsuIntervalEntry 9 }
 
 
        ncmcsuIntervalNETLOFS OBJECT-TYPE
        SYNTAX Gauge
        ACCESS read-only
        STATUS mandatory
        DESCRIPTION
               "The ncmcsu interval LOFS of Net."
        ::= { ncmcsuIntervalEntry 10 }

        ncmcsuIntervalNETESL OBJECT-TYPE
        SYNTAX Gauge
        ACCESS read-only
        STATUS mandatory
        DESCRIPTION
               "The ncmcsu interval ESL of Net."
        ::= { ncmcsuIntervalEntry 11 }
 
         
        ncmcsuIntervalNETSEFS OBJECT-TYPE
        SYNTAX Gauge
        ACCESS read-only
        STATUS mandatory
        DESCRIPTION
               "The ncmcsu interval SEFS of Net."
        ::= { ncmcsuIntervalEntry 12 }
 
 
                 
        ncmcsuIntervalEQOOFS OBJECT-TYPE
        SYNTAX Gauge
        ACCESS read-only
        STATUS mandatory
        DESCRIPTION
               "The ncmcsu interval OOFS of Eq."
        ::= { ncmcsuIntervalEntry 13 }
 
 
        ncmcsuIntervalEQDTED OBJECT-TYPE
        SYNTAX Gauge
        ACCESS read-only
        STATUS mandatory
        DESCRIPTION
               "The ncmcsu interval DTED of Eq."
        ::= { ncmcsuIntervalEntry 14 }


	  ncmcsuIntervalEQDBER OBJECT-TYPE
        SYNTAX Gauge
        ACCESS read-only
        STATUS mandatory
        DESCRIPTION
               "The ncmcsu interval DBER of Eq."
        ::= { ncmcsuIntervalEntry 15 }


	ncmcsuIntervalEQES OBJECT-TYPE
        SYNTAX Gauge
        ACCESS read-only
        STATUS mandatory
        DESCRIPTION
               "The ncmcsu Interval ES of Eq."
        ::= { ncmcsuIntervalEntry 16 }


	ncmcsuIntervalEQUAS OBJECT-TYPE
        SYNTAX Gauge
        ACCESS read-only
        STATUS mandatory
        DESCRIPTION
               "The ncmcsu Interval UAS of Eq."
        ::= { ncmcsuIntervalEntry 17 }


	ncmcsuIntervalEQESL OBJECT-TYPE
        SYNTAX Gauge
        ACCESS read-only
        STATUS mandatory
        DESCRIPTION
               "The ncmcsu Interval ESL of Eq."
        ::= { ncmcsuIntervalEntry 18 }





	  -- The ncm csu common table

        ncmcsucommonTable OBJECT-TYPE
        SYNTAX SEQUENCE OF NcmcsucommonEntry
        ACCESS not-accessible
        STATUS mandatory
	DESCRIPTION
               "The csu common table."

	--DEFAULT test-function csucommon-test
        --DEFAULT next-function csucommon-next
	



                  ::= { ncm-csu 6014 }


        ncmcsucommonEntry OBJECT-TYPE
        SYNTAX NcmcsucommonEntry
        ACCESS not-accessible
        STATUS mandatory
        DESCRIPTION
               "An entry in the ncmcsu main configuration table."
        INDEX   { ncmcsuNIDcommonIndex, ncmcsucommonIndex, ncmcsucommonEndType }
        ::= { ncmcsucommonTable 1 }


	NcmcsucommonEntry ::=
        SEQUENCE {
		
	     ncmcsuNIDcommonIndex
		  INTEGER,	
             ncmcsucommonIndex
                 INTEGER,
             ncmcsucommonEndType
                 INTEGER,
             ncmValidInterval
                 INTEGER,
	     ncmCurrentIntervalSeconds
		 INTEGER,
	     ncmResetPerformanceReg
		 INTEGER

		}


	ncmcsuNIDcommonIndex OBJECT-TYPE
        SYNTAX  INTEGER
        ACCESS  read-only
        STATUS  mandatory
        DESCRIPTION
	"This variable specifies the node id."          
        ::= { ncmcsucommonEntry 1 }

 
        ncmcsucommonIndex OBJECT-TYPE
        SYNTAX  INTEGER
        ACCESS  read-only
        STATUS  mandatory
	DESCRIPTION
	"This variable specifies the line index value."           
        ::= { ncmcsucommonEntry 2 }


        ncmcsucommonEndType  OBJECT-TYPE
             SYNTAX INTEGER {

                       near-End(1),
                       far-End(2)

                        }
             ACCESS read-only
             STATUS mandatory
             DESCRIPTION
             "The variable specifies the End Type   ."
                    ::= { ncmcsucommonEntry 3 }


	ncmValidInterval OBJECT-TYPE
        SYNTAX INTEGER
        ACCESS read-only
        STATUS mandatory
        DESCRIPTION
               "The ncmcsu/idncmcsu valid intervals."
        ::= { ncmcsucommonEntry 4 }


        ncmCurrentIntervalSeconds  OBJECT-TYPE
        SYNTAX INTEGER
        ACCESS read-only
        STATUS mandatory
        DESCRIPTION
               "The ncmcsu seconds in current 15 minutes interval. "
        ::= { ncmcsucommonEntry 5 }



	ncmResetPerformanceReg OBJECT-TYPE 
        SYNTAX INTEGER { 
 
                no(1),     
                yes(2)       
                        } 
                 
        ACCESS read-write 
        STATUS mandatory 
        DESCRIPTION    
            " The ncmcsu  reset performance monitoring register " 
  
        ::= { ncmcsucommonEntry 6 }


-- The ncm csu Retrieval Status 1(sigma) table
   
        ncmcsuRetrievalStatusOneTable OBJECT-TYPE
        SYNTAX SEQUENCE OF NcmcsuRetrievalStatusOneEntry
        ACCESS not-accessible
        STATUS mandatory
	DESCRIPTION
               "The ncmcsu retrieval status table."


	--DEFAULT test-function csucommon-test
        --DEFAULT next-function csucommon-next
	

 
                  ::= { ncm-csu 6015 }
 
 
        ncmcsuRetrievalStatusOneEntry OBJECT-TYPE
        SYNTAX NcmcsuRetrievalStatusOneEntry
        ACCESS not-accessible
        STATUS mandatory
        DESCRIPTION
               "An entry in the ncmcsu element status table."
        INDEX   { ncmcsuNIDRetrievalStatusIndex1,ncmcsuRetrievalStatusIndex1 }
        ::= { ncmcsuRetrievalStatusOneTable 1 }
 
 
        NcmcsuRetrievalStatusOneEntry ::=
        SEQUENCE {
 
             ncmcsuNIDRetrievalStatusIndex1
                 INTEGER,
             ncmcsuRetrievalStatusIndex1
                 INTEGER,
             ncmcsuNearAlmBERthresexcd
                 INTEGER,
             ncmcsuNearAlmESthresexcd
                 INTEGER,
             ncmcsuNearAlmUASthresexcd
                 INTEGER,
             ncmcsuNearAlmLLBPLB
                 INTEGER,
	     ncmcsuFarAlmBERthresexcd
                 INTEGER,
             ncmcsuFarAlmESthresexcd
                 INTEGER,
             ncmcsuFarAlmUASthresexcd
                 INTEGER,
             ncmcsuFarAlmLLBDLB
                 INTEGER,
             ncmcsuFarCsuAbsent
                 INTEGER,
	     ncmcsuEqStatusLowDensity
		 INTEGER,
	     ncmcsuEqStatusOOF
		 INTEGER,
	     ncmcsuEqStatusCRCError
		 INTEGER,
             ncmcsuEqStatusBPV
                 INTEGER,
             ncmcsuEqStatusPLB
                 INTEGER,
             ncmcsuEqStatusELBRLB
                 INTEGER,
             ncmcsuNetStatusPulses
                 INTEGER,
	     ncmcsuNetStatusOOF
		 INTEGER,
	     ncmcsuNetStatusCRCError
		 INTEGER,
             ncmcsuNetStatusBPV
                 INTEGER,
             ncmcsuNetStatusLLB
                 INTEGER,
	     ncmcsuXNetStatus1BERthresexcd
                 INTEGER,
             ncmcsuXNetStatus1ES1thresexcd
                 INTEGER,
             ncmcsuXNetStatus1ESthresexcd
                 INTEGER,
             ncmcsuXNetStatus1UASthresexcd
                 INTEGER,
             ncmcsuXNetStatus1LLB
                 INTEGER,
             ncmcsuXNetStatus1PLB
                 INTEGER,
             ncmcsuXNetStatus1LOS
                 INTEGER,
             ncmcsuXNetStatus1YEL
                 INTEGER,
             ncmcsuXNetStatus2LOF
                 INTEGER,
             ncmcsuXNetStatus2AIS
                 INTEGER,
             ncmcsuXNetStatus2TSTProgress
                 INTEGER,
             ncmcsuXNetStatus2PowerAFail
                 INTEGER,
             ncmcsuXNetStatus2PowerBFail
                 INTEGER,
             ncmcsuXEqStatus1BERthresexcd
                 INTEGER,
             ncmcsuXEqStatus1ES1thresexcd
                 INTEGER,
             ncmcsuXEqStatus1ESthresexcd
                 INTEGER,
             ncmcsuXEqStatus1UASthresexcd
                 INTEGER, 
             ncmcsuXEqStatus1ELB
                 INTEGER,
             ncmcsuXEqStatus1RLB
                 INTEGER,
             ncmcsuXEqStatus1LOS
                 INTEGER,
             ncmcsuXEqStatus1YEL
                 INTEGER,
             ncmcsuXEqStatus2LOF
                 INTEGER,
             ncmcsuXEqStatus2AIS
                 INTEGER,
             ncmcsuXEqStatus2TSTSignal
                 INTEGER,
             ncmcsuTstRstNearRLBTstFail
                 INTEGER,
             ncmcsuTstRstNearPLBTstFail
                 INTEGER
                }
                 
 
        ncmcsuNIDRetrievalStatusIndex1 OBJECT-TYPE
        SYNTAX  INTEGER
        ACCESS  read-only
        STATUS  mandatory
        DESCRIPTION
        "This variable specifies the node id of the node."
        ::= { ncmcsuRetrievalStatusOneEntry 1 }
 
         
        ncmcsuRetrievalStatusIndex1 OBJECT-TYPE
        SYNTAX  INTEGER
        ACCESS  read-only
        STATUS  mandatory
        DESCRIPTION
        "This variable specifies the interface index ."
         ::= { ncmcsuRetrievalStatusOneEntry 2 }
 

        ncmcsuNearAlmBERthresexcd OBJECT-TYPE
        SYNTAX INTEGER {
                no(1),
                yes(2)
           }
        ACCESS read-only
        STATUS mandatory
        DESCRIPTION
        "The ncmcsu retrieval status 1 ber threshold exceeded 
		     which is bit# 0 in near alarm status."
        ::= { ncmcsuRetrievalStatusOneEntry 3 }


        ncmcsuNearAlmESthresexcd OBJECT-TYPE
        SYNTAX INTEGER {
                no(1),
                yes(2)
           }
        ACCESS read-only
        STATUS mandatory
        DESCRIPTION
        "The ncmcsu retrieval status 1 es threshold exceeded 
                     which is bit# 1 in near alarm status."
        ::= { ncmcsuRetrievalStatusOneEntry 4 }


        ncmcsuNearAlmUASthresexcd OBJECT-TYPE
        SYNTAX INTEGER {
                no(1),
                yes(2)
           }
        ACCESS read-only
        STATUS mandatory
        DESCRIPTION
        "The ncmcsu retrieval status 1 uas threshold exceeded
                     which is bit# 2 in near alarm status."
        ::= { ncmcsuRetrievalStatusOneEntry 5 }


        ncmcsuNearAlmLLBPLB OBJECT-TYPE
        SYNTAX INTEGER {
              no(1),
              yes(2)
          }
        ACCESS read-only
        STATUS mandatory
        DESCRIPTION
        "The ncmcsu retrieval status 1 llb or plb which is 
			bit# 3 in near alarm status."
        ::= { ncmcsuRetrievalStatusOneEntry 6 }


        ncmcsuFarAlmBERthresexcd OBJECT-TYPE
        SYNTAX INTEGER {
                no(1),
                yes(2)
           }
        ACCESS read-only
        STATUS mandatory
        DESCRIPTION
        "The ncmcsu retrieval status 1 ber threshold exceeded
                     which is bit# 0 in far alarm status."
        ::= { ncmcsuRetrievalStatusOneEntry 7 }
 
 
        ncmcsuFarAlmESthresexcd OBJECT-TYPE
        SYNTAX INTEGER {
                no(1),
                yes(2)
           }
        ACCESS read-only
        STATUS mandatory
        DESCRIPTION
        "The ncmcsu retrieval status 1 es threshold exceeded
                     which is bit# 1 in far alarm status."
        ::= { ncmcsuRetrievalStatusOneEntry 8 }
 
 
        ncmcsuFarAlmUASthresexcd OBJECT-TYPE
        SYNTAX INTEGER {
                no(1),
                yes(2)
           }
        ACCESS read-only
        STATUS mandatory
        DESCRIPTION
        "The ncmcsu retrieval status 1 uas threshold exceeded
                     which is bit# 2 in far alarm status."
        ::= { ncmcsuRetrievalStatusOneEntry 9 }
 
 
        ncmcsuFarAlmLLBDLB OBJECT-TYPE
        SYNTAX INTEGER {
                no(1),
                yes(2)
          }
        ACCESS read-only
        STATUS mandatory
        DESCRIPTION
        "The ncmcsu retrieval status 1 llb or dlb which is
                        bit# 3 in far alarm status."
        ::= { ncmcsuRetrievalStatusOneEntry 10 }


        ncmcsuFarCsuAbsent  OBJECT-TYPE
        SYNTAX INTEGER {
                no(1),
                yes(2)
          }
        ACCESS read-only
        STATUS mandatory
        DESCRIPTION
        "The ncmcsu retrieval status 1 ncmcsu absent
                        which is bit# 6 in far alarm status."
        ::= { ncmcsuRetrievalStatusOneEntry 11 }


        ncmcsuEqStatusLowDensity OBJECT-TYPE
        SYNTAX INTEGER {
                no(1),
                yes(2)
          }
        ACCESS read-only
        STATUS mandatory
        DESCRIPTION
        "The ncmcsu retrieval status 1 low density 
			which is bit# 0 in eq status."
        ::= { ncmcsuRetrievalStatusOneEntry 12 }


        ncmcsuEqStatusOOF  OBJECT-TYPE
        SYNTAX INTEGER {
                no(1),
                yes(2)
           }
        ACCESS read-only
        STATUS mandatory
        DESCRIPTION
        "The ncmcsu retrieval status 1 oof
                        which is bit# 1 in eq status."
        ::= { ncmcsuRetrievalStatusOneEntry 13 }


        ncmcsuEqStatusCRCError  OBJECT-TYPE
        SYNTAX INTEGER {
                no(1),
                yes(2)
           }    
        ACCESS read-only
        STATUS mandatory
        DESCRIPTION
        "The ncmcsu retrieval status 1 crc error
                        which is bit# 2 in eq status."
        ::= { ncmcsuRetrievalStatusOneEntry 14 }
 

	ncmcsuEqStatusBPV   OBJECT-TYPE
        SYNTAX INTEGER {
                no(1),
                yes(2)
           }    
        ACCESS read-only
        STATUS mandatory
        DESCRIPTION
        "The ncmcsu retrieval status 1 bpv
                        which is bit# 3 in eq status."
        ::= { ncmcsuRetrievalStatusOneEntry 15 }


        ncmcsuEqStatusPLB  OBJECT-TYPE 
        SYNTAX INTEGER {
                no(1),
                yes(2)
           }    
        ACCESS read-only
        STATUS mandatory
        DESCRIPTION
        "The ncmcsu retrieval status 1 plb
                        which is bit# 4 in eq status."
        ::= { ncmcsuRetrievalStatusOneEntry 16 }


        ncmcsuEqStatusELBRLB  OBJECT-TYPE 
        SYNTAX INTEGER {
		no-Loop(1),
                elb(2),
                rlb(3)
           }    
        ACCESS read-only
        STATUS mandatory 
        DESCRIPTION
        "The ncmcsu retrieval status 1 elb or rlb
                        which is bit# 6 in eq status."
        ::= { ncmcsuRetrievalStatusOneEntry 17 }


        ncmcsuNetStatusPulses OBJECT-TYPE
        SYNTAX INTEGER {
                no(1),
                yes(2)
           }    
        ACCESS read-only
        STATUS mandatory
        DESCRIPTION
        "The ncmcsu retrieval status 1 low density
                        which is bit# 0 in net status."
        ::= { ncmcsuRetrievalStatusOneEntry 18 }


        ncmcsuNetStatusOOF  OBJECT-TYPE
        SYNTAX INTEGER {
                no(1),
                yes(2)
           }    
        ACCESS read-only
        STATUS mandatory 
        DESCRIPTION
        "The ncmcsu retrieval status 1 oof
                        which is bit# 1 in net status."
        ::= { ncmcsuRetrievalStatusOneEntry 19 }


        ncmcsuNetStatusCRCError  OBJECT-TYPE
        SYNTAX INTEGER {
                no(1),
                yes(2)
           }    
        ACCESS read-only
        STATUS mandatory
        DESCRIPTION
        "The ncmcsu retrieval status 1 crc error
                        which is bit# 2 in net status."
        ::= { ncmcsuRetrievalStatusOneEntry 20 }


        ncmcsuNetStatusBPV  OBJECT-TYPE
        SYNTAX INTEGER {
                no(1),
                yes(2)
           }    
        ACCESS read-only
        STATUS mandatory
        DESCRIPTION
        "The ncmcsu retrieval status 1 bpv
                        which is bit# 3 in net status."
        ::= { ncmcsuRetrievalStatusOneEntry 21 }


        ncmcsuNetStatusLLB  OBJECT-TYPE
        SYNTAX INTEGER {
                no(1),
                yes(2)
           }    
        ACCESS read-only
        STATUS mandatory
        DESCRIPTION
        "The ncmcsu retrieval status 1 llb
                        which is bit# 4 in net status."
        ::= { ncmcsuRetrievalStatusOneEntry 22 }


	ncmcsuXNetStatus1BERthresexcd OBJECT-TYPE
        SYNTAX INTEGER {
                no(1),
                yes(2)
           }    
        ACCESS read-only
        STATUS mandatory
        DESCRIPTION
        "The ncmcsu retrieval status 1 ber threshold exceeded
                which is bit# 0 in extended net status 1."
        ::= { ncmcsuRetrievalStatusOneEntry 23 }


        ncmcsuXNetStatus1ES1thresexcd  OBJECT-TYPE
        SYNTAX INTEGER { 
                no(1), 
                yes(2) 
           }     
        ACCESS read-only 
        STATUS mandatory 
        DESCRIPTION
        "The ncmcsu retrieval status 1 es1 threshold exceeded
                which is bit# 1 in extended net status 1." 
        ::= { ncmcsuRetrievalStatusOneEntry 24 } 


        ncmcsuXNetStatus1ESthresexcd  OBJECT-TYPE
        SYNTAX INTEGER {
                no(1),
                yes(2)
           }    
        ACCESS read-only
        STATUS mandatory
        DESCRIPTION
        "The ncmcsu retrieval status 1 es threshold exceeded
                which is bit# 2 in extended net status 1."
        ::= { ncmcsuRetrievalStatusOneEntry 25 }


        ncmcsuXNetStatus1UASthresexcd  OBJECT-TYPE
        SYNTAX INTEGER {
                no(1),
                yes(2)
           }    
        ACCESS read-only
        STATUS mandatory
        DESCRIPTION
        "The ncmcsu retrieval status 1 uas threshold exceeded
                which is bit# 3 in extended net status 1."
        ::= { ncmcsuRetrievalStatusOneEntry 26 }


        ncmcsuXNetStatus1LLB  OBJECT-TYPE
        SYNTAX INTEGER {
                no(1),
                yes(2)
           }    
        ACCESS read-only
        STATUS mandatory
        DESCRIPTION
        "The ncmcsu retrieval status 1 llb
              which is bit# 4 in extended net status 1."
        ::= { ncmcsuRetrievalStatusOneEntry 27 }


        ncmcsuXNetStatus1PLB  OBJECT-TYPE
        SYNTAX INTEGER {
                no(1),
                yes(2)
           }    
        ACCESS read-only
        STATUS mandatory
        DESCRIPTION
        "The ncmcsu retrieval status 1 plb
              which is bit# 5 in extended net status 1."
        ::= { ncmcsuRetrievalStatusOneEntry 28 }


        ncmcsuXNetStatus1LOS  OBJECT-TYPE
        SYNTAX INTEGER {
                no(1),
                yes(2)
           }    
        ACCESS read-only
        STATUS mandatory
        DESCRIPTION
        "The ncmcsu retrieval status 1 los
              which is bit# 6 in extended net status 1."
        ::= { ncmcsuRetrievalStatusOneEntry 29 }


        ncmcsuXNetStatus1YEL  OBJECT-TYPE
        SYNTAX INTEGER {
                no(1),
                yes(2)
           }    
        ACCESS read-only
        STATUS mandatory
        DESCRIPTION
        "The ncmcsu retrieval status 1 yel
              which is bit# 7 in extended net status 1."
        ::= { ncmcsuRetrievalStatusOneEntry 30 }


        ncmcsuXNetStatus2LOF  OBJECT-TYPE
        SYNTAX INTEGER {
                no(1),
                yes(2)
           }    
        ACCESS read-only
        STATUS mandatory
        DESCRIPTION
        "The ncmcsu retrieval status 1 lof
              which is bit# 0 in extended net status 2."
        ::= { ncmcsuRetrievalStatusOneEntry 31 }


        ncmcsuXNetStatus2AIS  OBJECT-TYPE
        SYNTAX INTEGER {
                no(1),
                yes(2)
           }    
        ACCESS read-only
        STATUS mandatory
        DESCRIPTION
        "The ncmcsu retrieval status 1 ais
              which is bit# 1 in extended net status 2."
        ::= { ncmcsuRetrievalStatusOneEntry 32 }


        ncmcsuXNetStatus2TSTProgress  OBJECT-TYPE
        SYNTAX INTEGER {
                no(1),
                yes(2)
           }    
        ACCESS read-only
        STATUS mandatory
        DESCRIPTION
        "The ncmcsu retrieval status 1 test in progress
              which is bit# 2 in extended net status 2."
        ::= { ncmcsuRetrievalStatusOneEntry 33 }


        ncmcsuXNetStatus2PowerAFail  OBJECT-TYPE
        SYNTAX INTEGER {
                no(1),
                yes(2)
           }    
        ACCESS read-only
        STATUS mandatory
        DESCRIPTION
        "The ncmcsu retrieval status 1 power supply a failure
                 which is bit# 3 in extended net status 2."
        ::= { ncmcsuRetrievalStatusOneEntry 34 }


        ncmcsuXNetStatus2PowerBFail  OBJECT-TYPE
        SYNTAX INTEGER {
                no(1),
                yes(2)
           }    
        ACCESS read-only
        STATUS mandatory
        DESCRIPTION
        "The ncmcsu retrieval status 1 power supply b failure
                 which is bit# 4 in extended net status 2."
        ::= { ncmcsuRetrievalStatusOneEntry 35 }


        ncmcsuXEqStatus1BERthresexcd  OBJECT-TYPE
        SYNTAX INTEGER {
                no(1),
                yes(2)
           }    
        ACCESS read-only
        STATUS mandatory
        DESCRIPTION
        "The ncmcsu retrieval status 1 ber threshold exceeded
                which is bit# 0 in extended eq status 1."
        ::= { ncmcsuRetrievalStatusOneEntry 36 }
 
 
        ncmcsuXEqStatus1ES1thresexcd  OBJECT-TYPE
        SYNTAX INTEGER {
                no(1),
                yes(2)
           }    
        ACCESS read-only
        STATUS mandatory
        DESCRIPTION
        "The ncmcsu retrieval status 1 es1 threshold exceeded
                which is bit# 1 in extended eq status 1."
        ::= { ncmcsuRetrievalStatusOneEntry 37 }

 
        ncmcsuXEqStatus1ESthresexcd  OBJECT-TYPE 
        SYNTAX INTEGER { 
                no(1), 
                yes(2) 
           }     
        ACCESS read-only 
        STATUS mandatory 
        DESCRIPTION 
        "The ncmcsu retrieval status 1 es threshold exceeded 
                which is bit# 2 in extended eq status 1." 
        ::= { ncmcsuRetrievalStatusOneEntry 38 } 

 
        ncmcsuXEqStatus1UASthresexcd  OBJECT-TYPE
        SYNTAX INTEGER {
                no(1),
                yes(2)
           }    
        ACCESS read-only
        STATUS mandatory
        DESCRIPTION
        "The ncmcsu retrieval status 1 uas threshold exceeded
                which is bit# 3 in extended eq status 1."
        ::= { ncmcsuRetrievalStatusOneEntry 39 }
 
 
        ncmcsuXEqStatus1ELB  OBJECT-TYPE
        SYNTAX INTEGER {
                no(1),
                yes(2)
           }    
        ACCESS read-only
        STATUS mandatory
        DESCRIPTION
        "The ncmcsu retrieval status 1 elb
              which is bit# 4 in extended eq status 1."
        ::= { ncmcsuRetrievalStatusOneEntry 40 }


        ncmcsuXEqStatus1RLB  OBJECT-TYPE
        SYNTAX INTEGER {
                no(1),
                yes(2)
           }    
        ACCESS read-only
        STATUS mandatory
        DESCRIPTION
        "The ncmcsu retrieval status 1 rlb
              which is bit# 5 in extended eq status 1."
        ::= { ncmcsuRetrievalStatusOneEntry 41 }


        ncmcsuXEqStatus1LOS  OBJECT-TYPE
        SYNTAX INTEGER {
                no(1),
                yes(2)
           }    
        ACCESS read-only
        STATUS mandatory
        DESCRIPTION
        "The ncmcsu retrieval status 1 los
              which is bit# 6 in extended eq status 1."
        ::= { ncmcsuRetrievalStatusOneEntry 42 }


        ncmcsuXEqStatus1YEL  OBJECT-TYPE
        SYNTAX INTEGER {
                no(1),
                yes(2)
           }    
        ACCESS read-only
        STATUS mandatory
        DESCRIPTION
        "The ncmcsu retrieval status 1 yel
              which is bit# 7 in extended eq status 1."
        ::= { ncmcsuRetrievalStatusOneEntry 43 }


        ncmcsuXEqStatus2LOF  OBJECT-TYPE
        SYNTAX INTEGER {
                no(1),
                yes(2)
           }
        ACCESS read-only
        STATUS mandatory
        DESCRIPTION
        "The ncmcsu retrieval status 1 lof
              which is bit# 0 in extended eq status 2."
        ::= { ncmcsuRetrievalStatusOneEntry 44 }


        ncmcsuXEqStatus2AIS  OBJECT-TYPE
        SYNTAX INTEGER {
                no(1),
                yes(2)
           }
        ACCESS read-only
        STATUS mandatory
        DESCRIPTION
        "The ncmcsu retrieval status 1 ais
              which is bit# 1 in extended eq status 2."
        ::= { ncmcsuRetrievalStatusOneEntry 45 }


        ncmcsuXEqStatus2TSTSignal  OBJECT-TYPE
        SYNTAX INTEGER {
                no(1),
                yes(2)
           }    
        ACCESS read-only
        STATUS mandatory
        DESCRIPTION
        "The ncmcsu retrieval status 1 test signal
              which is bit# 2 in extended eq status 2."
        ::= { ncmcsuRetrievalStatusOneEntry 46 }


        ncmcsuTstRstNearRLBTstFail  OBJECT-TYPE
        SYNTAX INTEGER {
                no(1),
                yes(2)
           }    
        ACCESS read-only
        STATUS mandatory
        DESCRIPTION
        "The ncmcsu retrieval status 1 near rlb test failed
              		which is bit# 0 in test result."
        ::= { ncmcsuRetrievalStatusOneEntry 47 }


        ncmcsuTstRstNearPLBTstFail OBJECT-TYPE 
        SYNTAX INTEGER {
                no(1), 
                yes(2)
           }     
        ACCESS read-only 
        STATUS mandatory 
        DESCRIPTION 
        "The ncmcsu retrieval status 1 near plb test failed
                        which is bit# 1 in test result."
        ::= { ncmcsuRetrievalStatusOneEntry 48 } 


-- The ncm csu miscellaneous table

        ncmcsuMiscellaneousTable OBJECT-TYPE
        SYNTAX SEQUENCE OF NcmcsuMiscellaneousEntry
        ACCESS not-accessible
        STATUS mandatory
		DESCRIPTION
               "The ncmcsu miscellaneous table."


	 --DEFAULT test-function csucommon-test
        --DEFAULT next-function csucommon-next

        ::= { ncm-csu 6016 }


        ncmcsuMiscellaneousEntry OBJECT-TYPE
        SYNTAX NcmcsuMiscellaneousEntry
        ACCESS not-accessible
        STATUS mandatory
        DESCRIPTION
               "An entry in the ncmcsu miscellaneous table."
        INDEX   { ncmcsuNIDMiscellaneousIndex, ncmcsuMiscellaneousIndex }
        ::= { ncmcsuMiscellaneousTable 1 }


        NcmcsuMiscellaneousEntry ::=
        SEQUENCE {

             ncmcsuNIDMiscellaneousIndex
                 INTEGER,
             ncmcsuMiscellaneousIndex
                 INTEGER,
	     ncmcsuResetESFErrCounter
		 INTEGER,
	     ncmcsuRetrieveNetESFErrCounter
		 INTEGER,
	     ncmcsuRetrieveEqESFErrCounter
		 INTEGER,
	     ncmcsuSendBOPmessage
		 INTEGER,
	     ncmcsuResetNetEqBERAlarm
		 INTEGER
	     }


        ncmcsuNIDMiscellaneousIndex  OBJECT-TYPE
        SYNTAX  INTEGER
        ACCESS  read-only
        STATUS  mandatory
        DESCRIPTION
        "This variable specifies the node id of the node."
        ::= { ncmcsuMiscellaneousEntry 1 }


        ncmcsuMiscellaneousIndex  OBJECT-TYPE
        SYNTAX  INTEGER
        ACCESS  read-only
        STATUS  mandatory
        DESCRIPTION
        "This variable specifies the interface index ."
         ::= { ncmcsuMiscellaneousEntry 2 }


        ncmcsuResetESFErrCounter  OBJECT-TYPE
        SYNTAX INTEGER
        ACCESS read-write
        STATUS mandatory
        DESCRIPTION
        "The ncmcsu reset esf error counter message(44)."
        ::= { ncmcsuMiscellaneousEntry 3 }
 

        ncmcsuRetrieveNetESFErrCounter  OBJECT-TYPE
        SYNTAX INTEGER 
        ACCESS read-only
        STATUS mandatory
        DESCRIPTION
        "The ncmcsu retrieval net esf error counter from 
         the Retrieve Event Counters message(18 01 0F)."
        ::= { ncmcsuMiscellaneousEntry 4 } 


        ncmcsuRetrieveEqESFErrCounter  OBJECT-TYPE
        SYNTAX INTEGER  
        ACCESS read-only 
        STATUS mandatory 
        DESCRIPTION 
        "The ncmcsu retrieval eq esf error counter from 
         the Retrieve Event Counters message(18 01 0F)." 
        ::= { ncmcsuMiscellaneousEntry 5 }  
 

        ncmcsuSendBOPmessage  OBJECT-TYPE
        SYNTAX INTEGER  {
                plb-activate(1),
                plb-deactivate(2),
               llb-activate(3),
                llb-deactivate(4)
           }
        ACCESS read-write
        STATUS mandatory  
        DESCRIPTION  
        "The ncmcsu send messages(18 01 38,39,3A,3B) to 
	 activate or deactivate the plb or llb respectively."  
        ::= { ncmcsuMiscellaneousEntry 6 }   
 

        ncmcsuResetNetEqBERAlarm  OBJECT-TYPE
        SYNTAX INTEGER
        ACCESS read-write
        STATUS mandatory
        DESCRIPTION
        "The ncmcsu reset Net and Eq BER Alarms message(18 01 3D)."
        ::= { ncmcsuMiscellaneousEntry 7 }


END
