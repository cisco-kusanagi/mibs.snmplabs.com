--
-- DVB-MGSYSTEM-MIB.my
-- MIB generated by MG-SOFT Visual MIB Builder Version 2.5 Build 225
-- Friday, November 09, 2001 at 15:04:43
--

	DVB-MGSYSTEM-MIB DEFINITIONS ::= BEGIN

		IMPORTS 
			enterprises, TimeTicks, OBJECT-TYPE, MODULE-IDENTITY			
				FROM SNMPv2-SMI			
			DisplayString			
				FROM SNMPv2-TC;
	
	
		mgSystem MODULE-IDENTITY
			LAST-UPDATED "200105181600Z"
			ORGANIZATION
				"DVB"
			CONTACT-INFO
				"DVB project
				European Broadcasting Union
				CH-1218 GRAND SACONNEX (Geneva)
				Switzerland
				Tel: +41 22 717 21 11
				Fax: +41 22 717 24 81"
			DESCRIPTION
				"DVB Measurement Group MIB to support TR 101 290.
				This mgSystem module contains general system information, similar to that provided by MIB-II."
			::= { mg 1 }
		
	
	
--
-- Node definitions
--
	
		dvb OBJECT IDENTIFIER ::= { enterprises 2696 }
		
		mg OBJECT IDENTIFIER ::= { dvb 3 }
		
		mgSysDescr OBJECT-TYPE
			SYNTAX DisplayString
			MAX-ACCESS read-only
			STATUS current
			DESCRIPTION
				"A textual description of the entity.  This value
				should include the full name and version
				identification of the system's hardware type,
				software operating-system, and networking
				software.  It is mandatory that this only contain
				printable ASCII characters."
			::= { mgSystem 1 }
		
		mgSysObjectID OBJECT-TYPE
			SYNTAX OBJECT IDENTIFIER
			MAX-ACCESS read-only
			STATUS current
			DESCRIPTION
				"The vendor's authoritative identification of the
				network management subsystem contained in the
				entity.  This value is allocated within the SMI
				enterprises subtree (1.3.6.1.4.1) and provides an
				easy and unambiguous means for determining `what
				kind of box' is being managed.  For example, if
				vendor `Flintstones, Inc.' was assigned the
				subtree 1.3.6.1.4.1.4242, it could assign the
				identifier 1.3.6.1.4.1.4242.1.1 to its `Fred
				Router'."
			::= { mgSystem 2 }
		
		mgSysUpTime OBJECT-TYPE
			SYNTAX TimeTicks
			MAX-ACCESS read-only
			STATUS current
			DESCRIPTION
				"The time (in hundredths of a second) since the
				network management portion of the system was last
				re-initialized."
			::= { mgSystem 3 }
		
		mgSysContact OBJECT-TYPE
			SYNTAX DisplayString
			MAX-ACCESS read-write
			STATUS current
			DESCRIPTION
				"The textual identification of the contact person
				for this managed node, together with information
				on how to contact this person."
			::= { mgSystem 4 }
		
		mgSysName OBJECT-TYPE
			SYNTAX DisplayString
			MAX-ACCESS read-write
			STATUS current
			DESCRIPTION
				"An administratively-assigned name for this
				managed node.  By convention, this is the node's
				fully-qualified domain name."
			::= { mgSystem 5 }
		
		mgSysLocation OBJECT-TYPE
			SYNTAX DisplayString
			MAX-ACCESS read-write
			STATUS current
			DESCRIPTION
				"The physical location of this node (e.g.,
				`telephone closet, 3rd floor')."
			::= { mgSystem 6 }
		
		mgSysServices OBJECT-TYPE
			SYNTAX INTEGER (0..127)
			MAX-ACCESS read-only
			STATUS current
			DESCRIPTION
				"A value which indicates the set of services that
				this entity primarily offers.
				
				The value is a sum.  This sum initially takes the
				value zero, Then, for each layer, L, in the range
				1 through 7, that this node performs transactions
				for, 2 raised to (L - 1) is added to the sum.  For
				example, a node which performs primarily routing
				functions would have a value of 4 (2^(3-1)).  In
				contrast, a node which is a host offering
				application services would have a value of 72
				(2^(4-1) + 2^(7-1)).  Note that in the context of
				the Internet suite of protocols, values should be
				calculated accordingly:
				
				     layer  functionality
				         1  physical (e.g., repeaters)
				         2  datalink/subnetwork (e.g., bridges)
				         3  internet (e.g., IP gateways)
				         4  end-to-end  (e.g., IP hosts)
				         7  applications (e.g., mail relays)
				
				For systems including OSI protocols, layers 5 and
				6 may also be counted."
			::= { mgSystem 7 }
		
		mgSysSerialNumber OBJECT-TYPE
			SYNTAX DisplayString (SIZE (0..100))
			MAX-ACCESS read-only
			STATUS current
			DESCRIPTION
				"Manufacturer Serial Number"
			::= { mgSystem 8 }
		
		mgSysVersion OBJECT-TYPE
			SYNTAX DisplayString (SIZE (0..100))
			MAX-ACCESS read-only
			STATUS current
			DESCRIPTION
				"Manufacturer Version Number (hardware and software)"
			::= { mgSystem 9 }
		
	
	END

--
-- DVB-MGSYSTEM-MIB.my
--
