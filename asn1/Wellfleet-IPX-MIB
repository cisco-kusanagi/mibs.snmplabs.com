Wellfleet-IPX-MIB DEFINITIONS ::= BEGIN

-- Created by mdl2asn version 3.1
-- Creation date: Wed Aug 30 16:43:50 EDT 1995


    IMPORTS

      Counter, Opaque
        FROM RFC1155-SMI
      OBJECT-TYPE
        FROM RFC-1212
      DisplayString
        FROM RFC1213-MIB
      wfIpxGroup
        FROM Wellfleet-COMMON-MIB;


    wfIpxBase	OBJECT IDENTIFIER ::= { wfIpxGroup 1 }

    wfIpxBaseDelete OBJECT-TYPE
        SYNTAX	INTEGER {
    		    created(1),
    		    deleted(2)
    		}
        ACCESS	read-write
        STATUS	deprecated
        DESCRIPTION
                "Create/Delete parameter. Default is created.
                Users perform an SNMP SET operation on this
                object in order to create/delete IPX."
        DEFVAL	{ created }
        ::= { wfIpxBase 1 }

    wfIpxBaseDisable OBJECT-TYPE
        SYNTAX	INTEGER {
    		    enabled(1),
    		    disabled(2)
    		}
        ACCESS	read-write
        STATUS	deprecated
        DESCRIPTION
                "Enable/Disable parameter. Default is enabled.
                Users perform an SNMP SET operation on this
                object in order to enable/disable IPX."
        DEFVAL	{ enabled }
        ::= { wfIpxBase 2 }

    wfIpxBaseState OBJECT-TYPE
        SYNTAX	INTEGER {
    		    up(1),
    		    down(2),
    		    in(3),
    		    notpresent(4)
    		}
        ACCESS	read-only
        STATUS	deprecated
        DESCRIPTION
                "The current state of the entire IPX."
        DEFVAL	{ notpresent }
        ::= { wfIpxBase 3 }

    wfIpxBaseCfgHostNumber OBJECT-TYPE
        SYNTAX	OCTET STRING
        ACCESS	read-write
        STATUS	deprecated
        DESCRIPTION
                "Host Number of Router and potential MAC address of box.
                This host number will be used to overide the default
                box generated hostnumber."
        ::= { wfIpxBase 4 }

    wfIpxBaseActiveHostNumber OBJECT-TYPE
        SYNTAX	OCTET STRING
        ACCESS	read-only
        STATUS	deprecated
        DESCRIPTION
                "Host Number of Router and potential MAC address of box.
                This is not a restart variable because this will be
                filled in from the IPX code after reading it from
                either the configurable host number or from a box
                generated variable."
        ::= { wfIpxBase 5 }

    wfIpxBaseNetCount OBJECT-TYPE
        SYNTAX	Counter
        ACCESS	read-only
        STATUS	deprecated
        DESCRIPTION
                "Count the total number of nets in the box."
        ::= { wfIpxBase 6 }

    wfIpxBaseServiceCount OBJECT-TYPE
        SYNTAX	Counter
        ACCESS	read-only
        STATUS	deprecated
        DESCRIPTION
                "Count the total number of saps in the box."
        ::= { wfIpxBase 7 }

    wfIpxBaseLogFilter OBJECT-TYPE
        SYNTAX	INTEGER {
    		    debug(1),
    		    info(2),
    		    trace(16),
    		    debuginfo(3),
    		    debugtrace(17),
    		    infotrace(18),
    		    debuginfotrace(19)
    		}
        ACCESS	read-write
        STATUS	deprecated
        DESCRIPTION
                "Filter out some log messages, Default filters out
                debugs, info, and trace messages."
        DEFVAL	{ trace }
        ::= { wfIpxBase 8 }

    wfIpxBaseNetTblSize OBJECT-TYPE
        SYNTAX	INTEGER
        ACCESS	read-write
        STATUS	deprecated
        DESCRIPTION
                "Tell me how much space to set aside when creating the
                forwarding and network tables."
        ::= { wfIpxBase 9 }

    wfIpxBaseRouterName OBJECT-TYPE
        SYNTAX	DisplayString
        ACCESS	read-write
        STATUS	deprecated
        DESCRIPTION
                "The Name of the Router, used for IPXWAN"
        ::= { wfIpxBase 10 }

    wfIpxBasePrimaryNetNumber OBJECT-TYPE
        SYNTAX	OCTET STRING
        ACCESS	read-write
        STATUS	deprecated
        DESCRIPTION
                "The 'interfernal' network number, used for IPXWAN"
        ::= { wfIpxBase 11 }

    wfIpxBaseRipMethod OBJECT-TYPE
        SYNTAX	INTEGER {
    		    metric(1),
    		    tick(2)
    		}
        ACCESS	read-write
        STATUS	deprecated
        DESCRIPTION
                "Choose either Metric/Hops based or Tick based routing"
        DEFVAL	{ tick }
        ::= { wfIpxBase 12 }

    wfIpxBaseMaximumPath OBJECT-TYPE
        SYNTAX	INTEGER(0..1)
        ACCESS	read-write
        STATUS	deprecated
        DESCRIPTION
                "Declare Maximum number equal costs paths allowed for a given destination network"
        DEFVAL	{ 1 }
        ::= { wfIpxBase 13 }

    wfIpxBaseHostCount OBJECT-TYPE
        SYNTAX	Counter
        ACCESS	read-only
        STATUS	deprecated
        DESCRIPTION
                "Count the total number of hosts in the box."
        ::= { wfIpxBase 14 }

    wfIpxBaseMultipleHostAddrs OBJECT-TYPE
        SYNTAX	INTEGER {
    		    enabled(1),
    		    disabled(2)
    		}
        ACCESS	read-write
        STATUS	deprecated
        DESCRIPTION
                "Allow the user to configure one host/mac addr for the whole box (default)
                where, if configured, the CfgHostNumber is used (becomes ActiveHostNubmer)
                otherwise if left unconfigured the ActiveHostNumber is discerned from the
                backplane serial number.  If Multiple host is Enabled and the host number is
                configured in the interface record the configured value is used as the
                hostid/mac addr of the interface (except Token Ring which can't go into
                promiscous mode, uses Token Ring Mac as hostid/mac of interface). If the
                host number in left unconfigured then the hostid/mac is gotten from the
                mac of the circuit."
        DEFVAL	{ enabled }
        ::= { wfIpxBase 15 }

    wfIpxBaseNovellCertificationConformance OBJECT-TYPE
        SYNTAX	INTEGER {
    		    enabled(1),
    		    disabled(2)
    		}
        ACCESS	read-write
        STATUS	deprecated
        DESCRIPTION
                "enable/disable novell certification, disable/enable wellfleet specifics"
        DEFVAL	{ enabled }
        ::= { wfIpxBase 16 }

    wfIpxBaseTrigUpdateEn OBJECT-TYPE
        SYNTAX	INTEGER {
    		    enabled(1),
    		    disabled(2)
    		}
        ACCESS	read-write
        STATUS	deprecated
        DESCRIPTION
                "enable/disable triggered rip updates for Goldman Sax"
        DEFVAL	{ enabled }
        ::= { wfIpxBase 17 }

    wfIpxBaseNetSizeBoundEn OBJECT-TYPE
        SYNTAX  INTEGER {
                    enabled(1),
                    disabled(2)
                }
        ACCESS  read-write
        STATUS  deprecated
        DESCRIPTION
                "enable/disable maximum allowed size of the network table"
        DEFVAL  { disabled }
        ::= { wfIpxBase 18 }

    wfIpxBaseMaxNetTblSize OBJECT-TYPE
        SYNTAX  INTEGER
        ACCESS  read-write
        STATUS  deprecated
        DESCRIPTION
                "maximum allowed size of the network table"
        ::= { wfIpxBase 19 }

    wfIpxBaseNetTblFillNotify OBJECT-TYPE
        SYNTAX  INTEGER(1..100)
        ACCESS  read-write
        STATUS  deprecated
        DESCRIPTION
                "notify when (configured) percentage is reached"
        DEFVAL  { 100 }
        ::= { wfIpxBase 20 }    


    wfIpxBaseRtEntryTable OBJECT-TYPE
        SYNTAX	SEQUENCE OF WfIpxBaseRtEntry
        ACCESS	not-accessible
        STATUS	obsolete
        DESCRIPTION
                "The table of Elements in IPX's routing table"
        ::= { wfIpxGroup 2 }

    wfIpxBaseRtEntry OBJECT-TYPE
        SYNTAX	WfIpxBaseRtEntry
        ACCESS	not-accessible
        STATUS	obsolete
        DESCRIPTION
                "An entry in the Routing Table"
        INDEX	{ wfIpxBaseRouteDest }
        ::= { wfIpxBaseRtEntryTable 1 }

    WfIpxBaseRtEntry ::= SEQUENCE {
    	    wfIpxBaseRouteDest
    		OCTET STRING,
    	    wfIpxBaseRouteIfIndex
    		INTEGER,
    	    wfIpxBaseRouteMetric
    		INTEGER,
    	    wfIpxBaseRouteNextHopNetwork
    		OCTET STRING,
    	    wfIpxBaseRouteNextHopHost
    		OCTET STRING,
    	    wfIpxBaseRouteType
    		INTEGER,
    	    wfIpxBaseRouteProto
    		INTEGER,
    	    wfIpxBaseRouteAge
    		INTEGER,
    	    wfIpxBaseRouteInfo
    		OCTET STRING
        }

    wfIpxBaseRouteDest OBJECT-TYPE
        SYNTAX	OCTET STRING (SIZE (4))
        ACCESS	read-only
        STATUS	obsolete
        DESCRIPTION
                "Multiple routes to a single
                destination can appear in the table, but access to
                such multiple entries is dependent on the table-
                access mechanisms defined by the network
                management protocol in use."
        ::= { wfIpxBaseRtEntry 1 }

    wfIpxBaseRouteIfIndex OBJECT-TYPE
        SYNTAX	INTEGER
        ACCESS	read-only
        STATUS	obsolete
        DESCRIPTION
                "The index value which uniquely identifies the
                local interface through which the next hop of this
                route should be reached.  The interface identified
                by a particular value of this index is the same
                interface as identified by the same value of
                ifIndex."
        ::= { wfIpxBaseRtEntry 2 }

    wfIpxBaseRouteMetric OBJECT-TYPE
        SYNTAX	INTEGER
        ACCESS	read-only
        STATUS	obsolete
        DESCRIPTION
                "The primary routing metric for this route. The
                semantics of this metric are determined by the
                routing-protocol specified in the route's
                ipRouteProto value.  If this metric is not used,
                its value should be set to -1."
        ::= { wfIpxBaseRtEntry 3 }

    wfIpxBaseRouteNextHopNetwork OBJECT-TYPE
        SYNTAX	OCTET STRING
        ACCESS	read-only
        STATUS	obsolete
        DESCRIPTION
                "In the case of a route bound to an interface
                which is realized via a broadcast media, the value
                of this field is the agent's IPX address on that
                interface."
        ::= { wfIpxBaseRtEntry 4 }

    wfIpxBaseRouteNextHopHost OBJECT-TYPE
        SYNTAX	OCTET STRING
        ACCESS	read-only
        STATUS	obsolete
        DESCRIPTION
                "Full network.host_id address of nexthop host for
                this network."
        ::= { wfIpxBaseRtEntry 5 }

    wfIpxBaseRouteType OBJECT-TYPE
        SYNTAX	INTEGER {
    		    other(1),
    		    invalid(2),
    		    direct(3),
    		    indirect(4),
    		    static(5)
    		}
        ACCESS	read-only
        STATUS	obsolete
        DESCRIPTION
                "The type of route. Note that the values
                direct(3) and indirect(4) refer to the notion of
                direct and indirect routing in the IPX
                architecture.

                Setting this object to the value invalid(2) has
                the effect of invalidating the corresponding entry
                in the ipRouteTable object.  That is, it
                effectively dissasociates the destination
                identified with said entry from the route
                identified with said entry.  It is an
                implementation-specific matter as to whether the
                agent removes an invalidated entry from the table.
                nagement stations must be prepared
                to receive tabular information from agents that
                corresponds to entries not currently in use.
                Proper interpretation of such entries requires
                examination of the relevant ipRouteType object."
        ::= { wfIpxBaseRtEntry 6 }

    wfIpxBaseRouteProto OBJECT-TYPE
        SYNTAX	INTEGER {
    		    other(1),
    		    local(2),
    		    netmgmt(3),
    		    rip(4)
    		}
        ACCESS	read-only
        STATUS	obsolete
        DESCRIPTION
                "The routing mechanism via which this route was
                learned.  Inclusion of values for gateway routing
                protocols is not intended to imply that hosts
                should support those protocols."
        ::= { wfIpxBaseRtEntry 7 }

    wfIpxBaseRouteAge OBJECT-TYPE
        SYNTAX	INTEGER
        ACCESS	read-only
        STATUS	obsolete
        DESCRIPTION
                "The number of seconds since this route was last
                updated or otherwise determined to be correct.
                Note that no semantics of `too old' can be implied
                except through knowledge of the routing protocol
                by which the route was learned."
        ::= { wfIpxBaseRtEntry 8 }

    wfIpxBaseRouteInfo OBJECT-TYPE
        SYNTAX	OCTET STRING
        ACCESS	read-only
        STATUS	obsolete
        DESCRIPTION
                "A user-defined string which describes this Route entry"
        ::= { wfIpxBaseRtEntry 9 }

    wfIpxBaseRt2EntryTable OBJECT-TYPE
        SYNTAX	SEQUENCE OF WfIpxBaseRt2Entry
        ACCESS	not-accessible
        STATUS	obsolete
        DESCRIPTION
                "The table of Elements in IPX's routing table"
        ::= { wfIpxGroup 13 }

    wfIpxBaseRt2Entry OBJECT-TYPE
        SYNTAX	WfIpxBaseRt2Entry
        ACCESS	not-accessible
        STATUS	obsolete
        DESCRIPTION
                "An entry in the Routing Table"
        INDEX	{ wfIpxBaseRoute2Proto,
    		  wfIpxBaseRoute2Dest,
    		  wfIpxBaseRoute2NextHopNetwork,
    		  wfIpxBaseRoute2NextHopHost }
        ::= { wfIpxBaseRt2EntryTable 1 }

    WfIpxBaseRt2Entry ::= SEQUENCE {
    	    wfIpxBaseRoute2Dest
    		OCTET STRING,
    	    wfIpxBaseRoute2IfIndex
    		INTEGER,
    	    wfIpxBaseRoute2Ticks
    		INTEGER,
    	    wfIpxBaseRoute2Hops
    		INTEGER,
    	    wfIpxBaseRoute2NextHopNetwork
    		OCTET STRING,
    	    wfIpxBaseRoute2NextHopHost
    		OCTET STRING,
    	    wfIpxBaseRoute2Type
    		INTEGER,
    	    wfIpxBaseRoute2Proto
    		INTEGER,
    	    wfIpxBaseRoute2Age
    		INTEGER,
    	    wfIpxBaseRoute2Info
    		OCTET STRING
        }

    wfIpxBaseRoute2Dest OBJECT-TYPE
        SYNTAX	OCTET STRING (SIZE (4))
        ACCESS	read-only
        STATUS	obsolete
        DESCRIPTION
                "Multiple routes to a single
                destination can appear in the table, but access to
                such multiple entries is dependent on the table-
                access mechanisms defined by the network
                management protocol in use."
        ::= { wfIpxBaseRt2Entry 1 }

    wfIpxBaseRoute2IfIndex OBJECT-TYPE
        SYNTAX	INTEGER
        ACCESS	read-only
        STATUS	obsolete
        DESCRIPTION
                "The index value which uniquely identifies the
                local interface through which the next hop of this
                route should be reached.  The interface identified
                by a particular value of this index is the same
                interface as identified by the same value of
                ifIndex."
        ::= { wfIpxBaseRt2Entry 2 }

    wfIpxBaseRoute2Ticks OBJECT-TYPE
        SYNTAX	INTEGER
        ACCESS	read-only
        STATUS	obsolete
        DESCRIPTION
                "The primary routing metric (in ticks) for this route. The
                semantics of this metric are determined by the
                routing-protocol specified in the route's
                ipRouteProto value.  If this metric is not used,
                its value should be set to -1."
        ::= { wfIpxBaseRt2Entry 3 }

    wfIpxBaseRoute2Hops OBJECT-TYPE
        SYNTAX	INTEGER
        ACCESS	read-only
        STATUS	obsolete
        DESCRIPTION
                "The primary routing metric (in hops) for this route. The
                semantics of this metric are determined by the
                routing-protocol specified in the route's
                ipRouteProto value.  If this metric is not used,
                its value should be set to -1."
        ::= { wfIpxBaseRt2Entry 4 }

    wfIpxBaseRoute2NextHopNetwork OBJECT-TYPE
        SYNTAX	OCTET STRING (SIZE (4))
        ACCESS	read-only
        STATUS	obsolete
        DESCRIPTION
                "In the case of a route bound to an interface
                which is realized via a broadcast media, the value
                of this field is the agent's IPX address on that
                interface."
        ::= { wfIpxBaseRt2Entry 5 }

    wfIpxBaseRoute2NextHopHost OBJECT-TYPE
        SYNTAX	OCTET STRING (SIZE (6))
        ACCESS	read-only
        STATUS	obsolete
        DESCRIPTION
                "Full network.host_id address of nexthop host for
                this network."
        ::= { wfIpxBaseRt2Entry 6 }

    wfIpxBaseRoute2Type OBJECT-TYPE
        SYNTAX	INTEGER {
    		    other(1),
    		    invalid(2),
    		    direct(3),
    		    indirect(4),
    		    static(5)
    		}
        ACCESS	read-only
        STATUS	obsolete
        DESCRIPTION
                "The type of route. Note that the values
                direct(3) and indirect(4) refer to the notion of
                direct and indirect routing in the IPX
                architecture.

                Setting this object to the value invalid(2) has
                the effect of invalidating the corresponding entry
                in the ipRouteTable object.  That is, it
                effectively dissasociates the destination
                identified with said entry from the route
                identified with said entry.  It is an
                implementation-specific matter as to whether the
                agent removes an invalidated entry from the table.
                nagement stations must be prepared
                to receive tabular information from agents that
                corresponds to entries not currently in use.
                Proper interpretation of such entries requires
                examination of the relevant ipRouteType object."
        ::= { wfIpxBaseRt2Entry 7 }

    wfIpxBaseRoute2Proto OBJECT-TYPE
        SYNTAX	INTEGER {
    		    other(1),
    		    local(2),
    		    netmgmt(3),
    		    rip(4),
    		    nlsp(5)
    		}
        ACCESS	read-only
        STATUS	obsolete
        DESCRIPTION
                "The routing mechanism via which this route was
                learned.  Inclusion of values for gateway routing
                protocols is not intended to imply that hosts
                should support those protocols."
        ::= { wfIpxBaseRt2Entry 8 }

    wfIpxBaseRoute2Age OBJECT-TYPE
        SYNTAX	INTEGER
        ACCESS	read-only
        STATUS	obsolete
        DESCRIPTION
                "The number of seconds since this route was last
                updated or otherwise determined to be correct.
                Note that no semantics of `too old' can be implied
                except through knowledge of the routing protocol
                by which the route was learned."
        ::= { wfIpxBaseRt2Entry 9 }

    wfIpxBaseRoute2Info OBJECT-TYPE
        SYNTAX	OCTET STRING
        ACCESS	read-only
        STATUS	obsolete
        DESCRIPTION
                "A user-defined string which describes this Route entry"
        ::= { wfIpxBaseRt2Entry 10 }

    wfIpxBaseSapEntryTable OBJECT-TYPE
        SYNTAX	SEQUENCE OF WfIpxBaseSapEntry
        ACCESS	not-accessible
        STATUS	obsolete
        DESCRIPTION
                "The table of Elements in IPX's SAP table"
        ::= { wfIpxGroup 3 }

    wfIpxBaseSapEntry OBJECT-TYPE
        SYNTAX	WfIpxBaseSapEntry
        ACCESS	not-accessible
        STATUS	obsolete
        DESCRIPTION
                "An entry in the Routing Table"
        INDEX	{ wfIpxBaseSapIndex }
        ::= { wfIpxBaseSapEntryTable 1 }

    WfIpxBaseSapEntry ::= SEQUENCE {
    	    wfIpxBaseSapType
    		OCTET STRING,
    	    wfIpxBaseSapNetwork
    		OCTET STRING,
    	    wfIpxBaseSapHost
    		OCTET STRING,
    	    wfIpxBaseSapSocket
    		OCTET STRING,
    	    wfIpxBaseSapName
    		DisplayString,
    	    wfIpxBaseSapAge
    		INTEGER,
    	    wfIpxBaseSapHops
    		INTEGER,
    	    wfIpxBaseSapIndex
    		OCTET STRING,
    	    wfIpxBaseSapIntf
    		OCTET STRING
        }

    wfIpxBaseSapType OBJECT-TYPE
        SYNTAX	OCTET STRING
        ACCESS	read-only
        STATUS	obsolete
        DESCRIPTION
                "Multiple routes to a single
                destination can appear in the table, but access to
                such multiple entries is dependent on the table-
                access mechanisms defined by the network
                management protocol in use."
        ::= { wfIpxBaseSapEntry 1 }

    wfIpxBaseSapNetwork OBJECT-TYPE
        SYNTAX	OCTET STRING
        ACCESS	read-only
        STATUS	obsolete
        DESCRIPTION
                "The network address of this service."
        ::= { wfIpxBaseSapEntry 2 }

    wfIpxBaseSapHost OBJECT-TYPE
        SYNTAX	OCTET STRING
        ACCESS	read-only
        STATUS	obsolete
        DESCRIPTION
                "The host address for this service."
        ::= { wfIpxBaseSapEntry 3 }

    wfIpxBaseSapSocket OBJECT-TYPE
        SYNTAX	OCTET STRING
        ACCESS	read-only
        STATUS	obsolete
        DESCRIPTION
                "The socket for this particular service"
        ::= { wfIpxBaseSapEntry 4 }

    wfIpxBaseSapName OBJECT-TYPE
        SYNTAX	DisplayString
        ACCESS	read-only
        STATUS	obsolete
        DESCRIPTION
                "The server name."
        ::= { wfIpxBaseSapEntry 5 }

    wfIpxBaseSapAge OBJECT-TYPE
        SYNTAX	INTEGER
        ACCESS	read-only
        STATUS	obsolete
        DESCRIPTION
                "The number of seconds  since  SAP entry has been updated."
        ::= { wfIpxBaseSapEntry 6 }

    wfIpxBaseSapHops OBJECT-TYPE
        SYNTAX	INTEGER
        ACCESS	read-only
        STATUS	obsolete
        DESCRIPTION
                "The number of Hops away service is from router."
        ::= { wfIpxBaseSapEntry 7 }

    wfIpxBaseSapIndex OBJECT-TYPE
        SYNTAX	OCTET STRING (SIZE (14))
        ACCESS	read-only
        STATUS	obsolete
        DESCRIPTION
                "Index string comprised of type.network.hostid.socket
                used to uniquely index this server."
        ::= { wfIpxBaseSapEntry 8 }

    wfIpxBaseSapIntf OBJECT-TYPE
        SYNTAX	OCTET STRING
        ACCESS	read-only
        STATUS	obsolete
        DESCRIPTION
                "Network Address of Nexthop Interface."
        ::= { wfIpxBaseSapEntry 9 }

    wfIpxInterfaceTable OBJECT-TYPE
        SYNTAX	SEQUENCE OF WfIpxInterfaceEntry
        ACCESS	not-accessible
        STATUS	deprecated
        DESCRIPTION
                "The network interface record"
        ::= { wfIpxGroup 4 }

    wfIpxInterfaceEntry OBJECT-TYPE
        SYNTAX	WfIpxInterfaceEntry
        ACCESS	not-accessible
        STATUS	deprecated
        DESCRIPTION
                "An entry in the Routing Table"
        INDEX	{ wfIpxInterfaceNetworkNumber,
    		  wfIpxInterfaceCircuit }
        ::= { wfIpxInterfaceTable 1 }

    WfIpxInterfaceEntry ::= SEQUENCE {
    	    wfIpxInterfaceIndex
    		INTEGER,
    	    wfIpxInterfaceDelete
    		INTEGER,
    	    wfIpxInterfaceDisable
    		INTEGER,
    	    wfIpxInterfaceState
    		INTEGER,
    	    wfIpxInterfaceCircuit
    		INTEGER,
    	    wfIpxInterfaceNetworkNumber
    		OCTET STRING,
    	    wfIpxInterfaceCost
    		INTEGER,
    	    wfIpxInterfaceXsumOn
    		INTEGER,
    	    wfIpxInterfaceCfgEncaps
    		INTEGER,
    	    wfIpxInterfaceMacAddress
    		OCTET STRING,
    	    wfIpxInterfaceSMDSGroupAddress
    		OCTET STRING,
    	    wfIpxInterfaceMaxInfo
    		INTEGER,
    	    wfIpxInterfaceInReceives
    		Counter,
    	    wfIpxInterfaceInHdrErrors
    		Counter,
    	    wfIpxInterfaceInAddrErrors
    		Counter,
    	    wfIpxInterfaceForwDatagrams
    		Counter,
    	    wfIpxInterfaceInUnknownProtos
    		Counter,
    	    wfIpxInterfaceInDiscards
    		Counter,
    	    wfIpxInterfaceInDelivers
    		Counter,
    	    wfIpxInterfaceOutRequests
    		Counter,
    	    wfIpxInterfaceOutDiscards
    		Counter,
    	    wfIpxInterfaceOutNoRoutes
    		Counter,
    	    wfIpxInterfaceTrEndStation
    		INTEGER,
    	    wfIpxInterfaceNetbiosAccept
    		INTEGER,
    	    wfIpxInterfaceNetbiosDeliver
    		INTEGER,
    	    wfIpxInterfaceWanSapPeriod
    		INTEGER,
    	    wfIpxInterfaceFRBcast
    		OCTET STRING,
    	    wfIpxInterfaceFRMcast
    		OCTET STRING,
    	    wfIpxInterfaceEncaps
    		INTEGER,
    	    wfIpxInterfaceSplit
    		INTEGER,
    	    wfIpxInterfaceCacheHit
    		Counter,
    	    wfIpxInterfaceIpxWanDisable
    		INTEGER,
    	    wfIpxInterfaceIpxWanCommonNet
    		OCTET STRING,
    	    wfIpxInterfaceIpxWanTimeOut
    		INTEGER,
    	    wfIpxInterfaceIpxWanLinkRetry
    		INTEGER,
    	    wfIpxInterfaceWanRipPeriod
    		INTEGER,
    	    wfIpxInterfaceCfgHostNumber
    		OCTET STRING,
    	    wfIpxInterfaceActiveHostNumber
    		OCTET STRING
        }

    wfIpxInterfaceIndex OBJECT-TYPE
        SYNTAX	INTEGER
        ACCESS	read-only
        STATUS	deprecated
        DESCRIPTION
                "A unique value for each IPX interface. Its value
                ranges between 1 and the value of MAXCIRCUITS."
        ::= { wfIpxInterfaceEntry 1 }

    wfIpxInterfaceDelete OBJECT-TYPE
        SYNTAX	INTEGER {
    		    created(1),
    		    deleted(2)
    		}
        ACCESS	read-write
        STATUS	deprecated
        DESCRIPTION
                "Create/Delete parameter. Default is created.
                Users perform an SNMP SET operation on this
                object in order to create/delete an IPX interface."
        DEFVAL	{ created }
        ::= { wfIpxInterfaceEntry 2 }

    wfIpxInterfaceDisable OBJECT-TYPE
        SYNTAX	INTEGER {
    		    enabled(1),
    		    disabled(2)
    		}
        ACCESS	read-write
        STATUS	deprecated
        DESCRIPTION
                "Enable/Disable parameter. Default is enabled.
                Users perform an SNMP SET operation on this
                object in order to enable/disable an IPX interface."
        DEFVAL	{ enabled }
        ::= { wfIpxInterfaceEntry 3 }

    wfIpxInterfaceState OBJECT-TYPE
        SYNTAX	INTEGER {
    		    up(1),
    		    down(2),
    		    init(3),
    		    notpresent(4)
    		}
        ACCESS	read-only
        STATUS	deprecated
        DESCRIPTION
                "The current state of the IPX interface"
        DEFVAL	{ notpresent }
        ::= { wfIpxInterfaceEntry 4 }

    wfIpxInterfaceCircuit OBJECT-TYPE
        SYNTAX	INTEGER
        ACCESS	read-only
        STATUS	deprecated
        DESCRIPTION
                "The Circuit Number that this interface runs over"
        ::= { wfIpxInterfaceEntry 5 }

    wfIpxInterfaceNetworkNumber OBJECT-TYPE
        SYNTAX	OCTET STRING (SIZE (4))
        ACCESS	read-only
        STATUS	deprecated
        DESCRIPTION
                "The IPX Address to which this entry's
                addressing information pertains"
        ::= { wfIpxInterfaceEntry 6 }

    wfIpxInterfaceCost OBJECT-TYPE
        SYNTAX	INTEGER {
    		    cost(1)
    		}
        ACCESS	read-write
        STATUS	deprecated
        DESCRIPTION
                "The Cost associated with the IPX Address of this entry"
        DEFVAL	{ cost }
        ::= { wfIpxInterfaceEntry 7 }

    wfIpxInterfaceXsumOn OBJECT-TYPE
        SYNTAX	INTEGER {
    		    enabled(1),
    		    disabled(2)
    		}
        ACCESS	read-write
        STATUS	deprecated
        DESCRIPTION
                "Flag for checksums"
        DEFVAL	{ enabled }
        ::= { wfIpxInterfaceEntry 8 }

    wfIpxInterfaceCfgEncaps OBJECT-TYPE
        SYNTAX	INTEGER {
    		    ethernet(1),
    		    lsap(2),
    		    novell(3),
    		    snap(4),
    		    ppp(5)
    		}
        ACCESS	read-write
        STATUS	deprecated
        DESCRIPTION
                "The encapsulation method associated with this interface
                chosen by the user but not necessarily the one used.
                (See wfIpxInterfaceEncaps)"
        DEFVAL	{ ethernet }
        ::= { wfIpxInterfaceEntry 9 }

    wfIpxInterfaceMacAddress OBJECT-TYPE
        SYNTAX	OCTET STRING
        ACCESS	read-only
        STATUS	deprecated
        DESCRIPTION
                "The MacAddress of this interface
                this port will receive or transmit."
        ::= { wfIpxInterfaceEntry 10 }

    wfIpxInterfaceSMDSGroupAddress OBJECT-TYPE
        SYNTAX	OCTET STRING
        ACCESS	read-only
        STATUS	deprecated
        DESCRIPTION
                "The SMDS group address"
        ::= { wfIpxInterfaceEntry 11 }

    wfIpxInterfaceMaxInfo OBJECT-TYPE
        SYNTAX	INTEGER
        ACCESS	read-only
        STATUS	deprecated
        DESCRIPTION
                "The maximum size of the INFO (non-MAC) field
                that this port will receive or transmit."
        ::= { wfIpxInterfaceEntry 12 }

    wfIpxInterfaceInReceives OBJECT-TYPE
        SYNTAX	Counter
        ACCESS	read-only
        STATUS	deprecated
        DESCRIPTION
                "The total number of input datagrams received from
                interfaces, including those received in error."
        ::= { wfIpxInterfaceEntry 13 }

    wfIpxInterfaceInHdrErrors OBJECT-TYPE
        SYNTAX	Counter
        ACCESS	read-only
        STATUS	deprecated
        DESCRIPTION
                "The number of input datagrams discarded due to
                errors in their IPX headers, including bad
                checksums, version number mismatch, other format
                errors, time-to-live exceeded, errors discovered
                in processing their IPX options, etc."
        ::= { wfIpxInterfaceEntry 14 }

    wfIpxInterfaceInAddrErrors OBJECT-TYPE
        SYNTAX	Counter
        ACCESS	read-only
        STATUS	deprecated
        DESCRIPTION
                "The number of input datagrams discarded because
                the IPX address in their IPX header's destination
                field was not a valid address to be received at
                this entity."
        ::= { wfIpxInterfaceEntry 15 }

    wfIpxInterfaceForwDatagrams OBJECT-TYPE
        SYNTAX	Counter
        ACCESS	read-only
        STATUS	deprecated
        DESCRIPTION
                "The number of input datagrams for which this
                entity was not their final IPX destination, as a
                result of which an attempt was made to find a
                route to forward them to that final destination.
                In entities which do not act as IPX Gateways, this
                counter will include only those packets which were
                Source-Routed via this entity, and the Source-
                Route option processing was successful."
        ::= { wfIpxInterfaceEntry 16 }

    wfIpxInterfaceInUnknownProtos OBJECT-TYPE
        SYNTAX	Counter
        ACCESS	read-only
        STATUS	deprecated
        DESCRIPTION
                "The number of locally-addressed datagrams
                received successfully but discarded because of an
                unknown or unsupported protocol."
        ::= { wfIpxInterfaceEntry 17 }

    wfIpxInterfaceInDiscards OBJECT-TYPE
        SYNTAX	Counter
        ACCESS	read-only
        STATUS	deprecated
        DESCRIPTION
                "The number of input IPX datagrams for which no
                problems were encountered to prevent their
                continued processing, but which were discarded
                (e.g., for lack of buffer space).  Note that this
                counter does not include any datagrams discarded
                while awaiting re-assembly."
        ::= { wfIpxInterfaceEntry 18 }

    wfIpxInterfaceInDelivers OBJECT-TYPE
        SYNTAX	Counter
        ACCESS	read-only
        STATUS	deprecated
        DESCRIPTION
                "The total number of input datagrams successfully
                delivered to IPX user-protocols."
        ::= { wfIpxInterfaceEntry 19 }

    wfIpxInterfaceOutRequests OBJECT-TYPE
        SYNTAX	Counter
        ACCESS	read-only
        STATUS	deprecated
        DESCRIPTION
                "The total number of IPX datagrams which local IPX
                user-protocols supplied to IPX in
                requests for transmission.  Note that this counter
                does not include any datagrams counted in
                ipxForwDatagrams."
        ::= { wfIpxInterfaceEntry 20 }

    wfIpxInterfaceOutDiscards OBJECT-TYPE
        SYNTAX	Counter
        ACCESS	read-only
        STATUS	deprecated
        DESCRIPTION
                "The number of output IPX datagrams for which no
                problem was encountered to prevent their
                transmission to their destination, but which were
                discarded (e.g., for lack of buffer space).  Note
                that this counter would include datagrams counted
                in ipForwDatagrams if any such packets met this
                (discretionary) discard criterion."
        ::= { wfIpxInterfaceEntry 21 }

    wfIpxInterfaceOutNoRoutes OBJECT-TYPE
        SYNTAX	Counter
        ACCESS	read-only
        STATUS	deprecated
        DESCRIPTION
                "The number of IPX datagrams discarded because no
                route could be found to transmit them to their
                destination.  Note that this counter includes any
                packets counted in ipForwDatagrams which meet this
                `no-route' criterion.  Note that this includes any
                datagarms which a host cannot route because all of
                its default gateways are down."
        ::= { wfIpxInterfaceEntry 22 }

    wfIpxInterfaceTrEndStation OBJECT-TYPE
        SYNTAX	INTEGER {
    		    enabled(1),
    		    disabled(2)
    		}
        ACCESS	read-write
        STATUS	deprecated
        DESCRIPTION
                "Source Routing flag"
        DEFVAL	{ disabled }
        ::= { wfIpxInterfaceEntry 23 }

    wfIpxInterfaceNetbiosAccept OBJECT-TYPE
        SYNTAX	INTEGER {
    		    enabled(1),
    		    disabled(2)
    		}
        ACCESS	read-write
        STATUS	deprecated
        DESCRIPTION
                "Accept NetBios All Networks Broadcast Packets"
        DEFVAL	{ enabled }
        ::= { wfIpxInterfaceEntry 24 }

    wfIpxInterfaceNetbiosDeliver OBJECT-TYPE
        SYNTAX	INTEGER {
    		    enabled(1),
    		    disabled(2)
    		}
        ACCESS	read-write
        STATUS	deprecated
        DESCRIPTION
                "Deliver NetBios All Networks Broadcast Packets"
        DEFVAL	{ enabled }
        ::= { wfIpxInterfaceEntry 25 }

    wfIpxInterfaceWanSapPeriod OBJECT-TYPE
        SYNTAX	INTEGER {
    		    default(2)
    		}
        ACCESS	read-write
        STATUS	deprecated
        DESCRIPTION
                "Configurable timer for SAP updates over LAN-WAN"
        DEFVAL	{ default }
        ::= { wfIpxInterfaceEntry 26 }

    wfIpxInterfaceFRBcast OBJECT-TYPE
        SYNTAX	OCTET STRING
        ACCESS	read-write
        STATUS	deprecated
        DESCRIPTION
                "Configurable Frame Relay broadcast address"
        ::= { wfIpxInterfaceEntry 27 }

    wfIpxInterfaceFRMcast OBJECT-TYPE
        SYNTAX	OCTET STRING
        ACCESS	read-write
        STATUS	deprecated
        DESCRIPTION
                "Configurable Frame Relay multicast address"
        ::= { wfIpxInterfaceEntry 28 }

    wfIpxInterfaceEncaps OBJECT-TYPE
        SYNTAX	INTEGER {
    		    ethernet(1),
    		    lsap(2),
    		    novell(3),
    		    snap(4),
    		    ppp(5)
    		}
        ACCESS	read-only
        STATUS	deprecated
        DESCRIPTION
                "The Active or final encapsulation method associated with
                this interface as determined by the router's implementation
                of encapsulation algorithms (rules, restrictions) based on media type."
        DEFVAL	{ ethernet }
        ::= { wfIpxInterfaceEntry 29 }

    wfIpxInterfaceSplit OBJECT-TYPE
        SYNTAX	INTEGER {
    		    enabled(1),
    		    disabled(2)
    		}
        ACCESS	read-write
        STATUS	deprecated
        DESCRIPTION
                "Enable or Disable Split Horizon algorithm for this interface
                Comes into to play for non full-meshed WAN networks (Frame Relay)"
        DEFVAL	{ enabled }
        ::= { wfIpxInterfaceEntry 30 }

    wfIpxInterfaceCacheHit OBJECT-TYPE
        SYNTAX	Counter
        ACCESS	read-only
        STATUS	deprecated
        DESCRIPTION
                "This counter was added for performance investigation under the same
                category as the number of Nets and number SAP counters.  THis counter
                Will provide information that will determine the usefullness of caching."
        ::= { wfIpxInterfaceEntry 31 }

    wfIpxInterfaceIpxWanDisable OBJECT-TYPE
        SYNTAX	INTEGER {
    		    enabled(1),
    		    disabled(2)
    		}
        ACCESS	read-write
        STATUS	deprecated
        DESCRIPTION
                "Enable IPXWAN negotiations"
        DEFVAL	{ disabled }
        ::= { wfIpxInterfaceEntry 32 }

    wfIpxInterfaceIpxWanCommonNet OBJECT-TYPE
        SYNTAX	OCTET STRING
        ACCESS	read-write
        STATUS	deprecated
        DESCRIPTION
                "Common network number for IPXWAN link"
        ::= { wfIpxInterfaceEntry 33 }

    wfIpxInterfaceIpxWanTimeOut OBJECT-TYPE
        SYNTAX	INTEGER {
    		    default(60)
    		}
        ACCESS	read-write
        STATUS	deprecated
        DESCRIPTION
                "IPXWAN timer out period for negotiation"
        DEFVAL	{ default }
        ::= { wfIpxInterfaceEntry 34 }

    wfIpxInterfaceIpxWanLinkRetry OBJECT-TYPE
        SYNTAX	INTEGER {
    		    default(5)
    		}
        ACCESS	read-write
        STATUS	deprecated
        DESCRIPTION
                "IPXWAN number of times to retry negotiation"
        DEFVAL	{ default }
        ::= { wfIpxInterfaceEntry 35 }

    wfIpxInterfaceWanRipPeriod OBJECT-TYPE
        SYNTAX	INTEGER {
    		    default(2)
    		}
        ACCESS	read-write
        STATUS	deprecated
        DESCRIPTION
                "Configurable timer for routing updates LAN-WAN"
        DEFVAL	{ default }
        ::= { wfIpxInterfaceEntry 36 }

    wfIpxInterfaceCfgHostNumber OBJECT-TYPE
        SYNTAX	OCTET STRING
        ACCESS	read-write
        STATUS	deprecated
        DESCRIPTION
                "Host Number and possible MAC address of interface.
                This host number will be used to overide the default
                cct generated hostnumber (if Multiple Host enabled).

                This field is not valid/used if the IpxBaseMultipleHost is
                not enabled, if the media is non-promiscuous (Token Ring)
                or if the field length is not 6 bytes."
        ::= { wfIpxInterfaceEntry 37 }

    wfIpxInterfaceActiveHostNumber OBJECT-TYPE
        SYNTAX	OCTET STRING
        ACCESS	read-only
        STATUS	deprecated
        DESCRIPTION
                "Host Number and possible MAC address of interface.

                   This field will always be filled in by the router and
                   lists the HostNumber of each Interface."
        ::= { wfIpxInterfaceEntry 38 }

    wfIpxRipIntfTable OBJECT-TYPE
        SYNTAX	SEQUENCE OF WfIpxRipIntfEntry
        ACCESS	not-accessible
        STATUS	deprecated
        DESCRIPTION
                "The list of RIP interfaces"
        ::= { wfIpxGroup 5 }

    wfIpxRipIntfEntry OBJECT-TYPE
        SYNTAX	WfIpxRipIntfEntry
        ACCESS	not-accessible
        STATUS	deprecated
        DESCRIPTION
                "An entry in the Routing Table"
        INDEX	{ wfIpxRipInterfaceIndex }
        ::= { wfIpxRipIntfTable 1 }

    WfIpxRipIntfEntry ::= SEQUENCE {
    	    wfIpxRipInterfaceDelete
    		INTEGER,
    	    wfIpxRipInterfaceDisable
    		INTEGER,
    	    wfIpxRipInterfaceState
    		INTEGER,
    	    wfIpxRipInterfaceIndex
    		OCTET STRING,
    	    wfIpxRipInterfaceSupply
    		INTEGER,
    	    wfIpxRipInterfaceListen
    		INTEGER
        }

    wfIpxRipInterfaceDelete OBJECT-TYPE
        SYNTAX	INTEGER {
    		    created(1),
    		    deleted(2)
    		}
        ACCESS	read-write
        STATUS	deprecated
        DESCRIPTION
                "Create/Delete parameter. Default is created.
                Users perform an SNMP SET operation on this
                object in order to create/delete an RIP Interface instance."
        DEFVAL	{ created }
        ::= { wfIpxRipIntfEntry 1 }

    wfIpxRipInterfaceDisable OBJECT-TYPE
        SYNTAX	INTEGER {
    		    enabled(1),
    		    disabled(2)
    		}
        ACCESS	read-write
        STATUS	deprecated
        DESCRIPTION
                "Enable/Disable parameter. Default is enabled.
                Users perform an SNMP SET operation on this
                object in order to enable/disable an RIP instance."
        DEFVAL	{ enabled }
        ::= { wfIpxRipIntfEntry 2 }

    wfIpxRipInterfaceState OBJECT-TYPE
        SYNTAX	INTEGER {
    		    up(1),
    		    down(2),
    		    init(3),
    		    notpresent(4)
    		}
        ACCESS	read-only
        STATUS	deprecated
        DESCRIPTION
                "The current state of RIP on this interface."
        DEFVAL	{ notpresent }
        ::= { wfIpxRipIntfEntry 3 }

    wfIpxRipInterfaceIndex OBJECT-TYPE
        SYNTAX	OCTET STRING (SIZE (4))
        ACCESS	read-only
        STATUS	deprecated
        DESCRIPTION
                "The IPX interface to run RIP on (instance id )."
        ::= { wfIpxRipIntfEntry 4 }

    wfIpxRipInterfaceSupply OBJECT-TYPE
        SYNTAX	INTEGER {
    		    enabled(1),
    		    disabled(2)
    		}
        ACCESS	read-write
        STATUS	deprecated
        DESCRIPTION
                "Transmit RIP packets."
        DEFVAL	{ enabled }
        ::= { wfIpxRipIntfEntry 5 }

    wfIpxRipInterfaceListen OBJECT-TYPE
        SYNTAX	INTEGER {
    		    enabled(1),
    		    disabled(2)
    		}
        ACCESS	read-write
        STATUS	deprecated
        DESCRIPTION
                "Receive RIP packets."
        DEFVAL	{ enabled }
        ::= { wfIpxRipIntfEntry 6 }

    wfIpxAdjacentHostTable OBJECT-TYPE
        SYNTAX	SEQUENCE OF WfIpxAdjacentHostEntry
        ACCESS	not-accessible
        STATUS	deprecated
        DESCRIPTION
                "Table of configured Static Hosts
                This is implemented for hosts that are accessible over
                Frame Relay, SMDS etc.  where a corresponding DLCI address
                must be configured for a nexthop host."
        ::= { wfIpxGroup 6 }

    wfIpxAdjacentHostEntry OBJECT-TYPE
        SYNTAX	WfIpxAdjacentHostEntry
        ACCESS	not-accessible
        STATUS	deprecated
        DESCRIPTION
                "An entry in the Adjacent Host Table"
        INDEX	{ wfIpxAhTargHostNetwork,
    		  wfIpxAhTargHostId }
        ::= { wfIpxAdjacentHostTable 1 }

    WfIpxAdjacentHostEntry ::= SEQUENCE {
    	    wfIpxAhDelete
    		INTEGER,
    	    wfIpxAhDisable
    		INTEGER,
    	    wfIpxAhTargHostNetwork
    		OCTET STRING,
    	    wfIpxAhTargHostId
    		OCTET STRING,
    	    wfIpxAhNextHopIntf
    		OCTET STRING,
    	    wfIpxAhDlci
    		OCTET STRING
        }

    wfIpxAhDelete OBJECT-TYPE
        SYNTAX	INTEGER {
    		    created(1),
    		    deleted(2)
    		}
        ACCESS	read-write
        STATUS	deprecated
        DESCRIPTION
                "Create/Delete parameter. Default is created.
                Users perform an SNMP SET operation on this
                object in order to create/delete the IPX
                Static Host."
        DEFVAL	{ created }
        ::= { wfIpxAdjacentHostEntry 1 }

    wfIpxAhDisable OBJECT-TYPE
        SYNTAX	INTEGER {
    		    enabled(1),
    		    disabled(2)
    		}
        ACCESS	read-write
        STATUS	deprecated
        DESCRIPTION
                "Enable/Disable parameter. Default is enabled.
                Users perform an SNMP SET operation on this
                object in order to enable/disable this IPX
                Static Route."
        DEFVAL	{ enabled }
        ::= { wfIpxAdjacentHostEntry 2 }

    wfIpxAhTargHostNetwork OBJECT-TYPE
        SYNTAX	OCTET STRING (SIZE (4))
        ACCESS	read-only
        STATUS	deprecated
        DESCRIPTION
                "The network address of the static host."
        ::= { wfIpxAdjacentHostEntry 3 }

    wfIpxAhTargHostId OBJECT-TYPE
        SYNTAX	OCTET STRING (SIZE (6))
        ACCESS	read-only
        STATUS	deprecated
        DESCRIPTION
                "The Address of this static host."
        ::= { wfIpxAdjacentHostEntry 4 }

    wfIpxAhNextHopIntf OBJECT-TYPE
        SYNTAX	OCTET STRING
        ACCESS	read-write
        STATUS	deprecated
        DESCRIPTION
                "The Next Hop Interface Network Address"
        ::= { wfIpxAdjacentHostEntry 5 }

    wfIpxAhDlci OBJECT-TYPE
        SYNTAX	OCTET STRING
        ACCESS	read-write
        STATUS	deprecated
        DESCRIPTION
                "The next Hop Host address"
        ::= { wfIpxAdjacentHostEntry 6 }

    wfIpxStaticRouteTable OBJECT-TYPE
        SYNTAX	SEQUENCE OF WfIpxStaticRouteEntry
        ACCESS	not-accessible
        STATUS	deprecated
        DESCRIPTION
                "The list of static routes used for Configuring IPX"
        ::= { wfIpxGroup 7 }

    wfIpxStaticRouteEntry OBJECT-TYPE
        SYNTAX	WfIpxStaticRouteEntry
        ACCESS	not-accessible
        STATUS	deprecated
        DESCRIPTION
                "An entry in the Routing Table"
        INDEX	{ wfIpxSrTargNetwork,
    		  wfIpxSrNextHopNetwork }
        ::= { wfIpxStaticRouteTable 1 }

    WfIpxStaticRouteEntry ::= SEQUENCE {
    	    wfIpxSrDelete
    		INTEGER,
    	    wfIpxSrDisable
    		INTEGER,
    	    wfIpxSrTargNetwork
    		OCTET STRING,
    	    wfIpxSrCost
    		INTEGER,
    	    wfIpxSrNextHopNetwork
    		OCTET STRING,
    	    wfIpxSrNextHopHost
    		OCTET STRING,
    	    wfIpxSrTargNetworkRt
    		INTEGER,
    	    wfIpxSrTickCost
    		OCTET STRING
        }

    wfIpxSrDelete OBJECT-TYPE
        SYNTAX	INTEGER {
    		    created(1),
    		    deleted(2)
    		}
        ACCESS	read-write
        STATUS	deprecated
        DESCRIPTION
                "Create/Delete parameter. Default is created.
                Users perform an SNMP SET operation on this
                object in order to create/delete the IPX
                Static Route."
        DEFVAL	{ created }
        ::= { wfIpxStaticRouteEntry 1 }

    wfIpxSrDisable OBJECT-TYPE
        SYNTAX	INTEGER {
    		    enabled(1),
    		    disabled(2)
    		}
        ACCESS	read-write
        STATUS	deprecated
        DESCRIPTION
                "Enable/Disable parameter. Default is enabled.
                Users perform an SNMP SET operation on this
                object in order to enable/disable this IPX
                Static Route."
        DEFVAL	{ enabled }
        ::= { wfIpxStaticRouteEntry 2 }

    wfIpxSrTargNetwork OBJECT-TYPE
        SYNTAX	OCTET STRING (SIZE (4))
        ACCESS	read-only
        STATUS	deprecated
        DESCRIPTION
                "The Address of this static route"
        ::= { wfIpxStaticRouteEntry 3 }

    wfIpxSrCost OBJECT-TYPE
        SYNTAX	INTEGER
        ACCESS	read-write
        STATUS	deprecated
        DESCRIPTION
                "The Cost of this Static Route in Hops"
        ::= { wfIpxStaticRouteEntry 4 }

    wfIpxSrNextHopNetwork OBJECT-TYPE
        SYNTAX	OCTET STRING (SIZE (4))
        ACCESS	read-only
        STATUS	deprecated
        DESCRIPTION
                "The Next Hop IPX Address"
        ::= { wfIpxStaticRouteEntry 5 }

    wfIpxSrNextHopHost OBJECT-TYPE
        SYNTAX	OCTET STRING
        ACCESS	read-write
        STATUS	deprecated
        DESCRIPTION
                "The next Hop Host address"
        ::= { wfIpxStaticRouteEntry 6 }

    wfIpxSrTargNetworkRt OBJECT-TYPE
        SYNTAX	INTEGER
        ACCESS	read-only
        STATUS	deprecated
        DESCRIPTION
                "The Route Identifier Which numbered route this is to be"
        ::= { wfIpxStaticRouteEntry 7 }

    wfIpxSrTickCost OBJECT-TYPE
        SYNTAX	OCTET STRING
        ACCESS	read-write
        STATUS	deprecated
        DESCRIPTION
                "The Cost of this Static Route in Ticks"
        ::= { wfIpxStaticRouteEntry 8 }

    wfIpxNetBiosStaticRouteTable OBJECT-TYPE
        SYNTAX	SEQUENCE OF WfIpxNetBiosStaticRouteEntry
        ACCESS	not-accessible
        STATUS	deprecated
        DESCRIPTION
                "The list of static routes used for Configuring IPX"
        ::= { wfIpxGroup 8 }

    wfIpxNetBiosStaticRouteEntry OBJECT-TYPE
        SYNTAX	WfIpxNetBiosStaticRouteEntry
        ACCESS	not-accessible
        STATUS	deprecated
        DESCRIPTION
                "An entry in the Routing Table"
        INDEX	{ wfIpxNetBiosSrTargNetwork,
    		  wfIpxNetBiosSrIntf }
        ::= { wfIpxNetBiosStaticRouteTable 1 }

    WfIpxNetBiosStaticRouteEntry ::= SEQUENCE {
    	    wfIpxNetBiosSrDelete
    		INTEGER,
    	    wfIpxNetBiosSrDisable
    		INTEGER,
    	    wfIpxNetBiosSrTargNetwork
    		OCTET STRING,
    	    wfIpxNetBiosSrName
    		DisplayString,
    	    wfIpxNetBiosSrIntf
    		OCTET STRING,
    	    wfIpxNetBiosSrIndex
    		INTEGER
        }

    wfIpxNetBiosSrDelete OBJECT-TYPE
        SYNTAX	INTEGER {
    		    created(1),
    		    deleted(2)
    		}
        ACCESS	read-write
        STATUS	deprecated
        DESCRIPTION
                "Create/Delete parameter. Default is created.
                Users perform an SNMP SET operation on this
                object in order to create/delete the IPX NETBIOS
                Static Route."
        DEFVAL	{ created }
        ::= { wfIpxNetBiosStaticRouteEntry 1 }

    wfIpxNetBiosSrDisable OBJECT-TYPE
        SYNTAX	INTEGER {
    		    enabled(1),
    		    disabled(2)
    		}
        ACCESS	read-write
        STATUS	deprecated
        DESCRIPTION
                "Enable/Disable parameter. Default is enabled.
                Users perform an SNMP SET operation on this
                object in order to enable/disable this IPX NETBIOS
                Static Route."
        DEFVAL	{ enabled }
        ::= { wfIpxNetBiosStaticRouteEntry 2 }

    wfIpxNetBiosSrTargNetwork OBJECT-TYPE
        SYNTAX	OCTET STRING (SIZE (4))
        ACCESS	read-only
        STATUS	deprecated
        DESCRIPTION
                "The Address of this static route"
        ::= { wfIpxNetBiosStaticRouteEntry 3 }

    wfIpxNetBiosSrName OBJECT-TYPE
        SYNTAX	DisplayString
        ACCESS	read-write
        STATUS	deprecated
        DESCRIPTION
                "The Name of the Target Server"
        ::= { wfIpxNetBiosStaticRouteEntry 4 }

    wfIpxNetBiosSrIntf OBJECT-TYPE
        SYNTAX	OCTET STRING (SIZE (4))
        ACCESS	read-only
        STATUS	deprecated
        DESCRIPTION
                "The Interface Identifier for this static entry"
        ::= { wfIpxNetBiosStaticRouteEntry 5 }

    wfIpxNetBiosSrIndex OBJECT-TYPE
        SYNTAX	INTEGER
        ACCESS	read-only
        STATUS	deprecated
        DESCRIPTION
                "The Entry Index Which identifies this is entry"
        ::= { wfIpxNetBiosStaticRouteEntry 6 }

    wfIpxStaticSapTable OBJECT-TYPE
        SYNTAX	SEQUENCE OF WfIpxStaticSapEntry
        ACCESS	not-accessible
        STATUS	deprecated
        DESCRIPTION
                "The table of Static Services"
        ::= { wfIpxGroup 12 }

    wfIpxStaticSapEntry OBJECT-TYPE
        SYNTAX	WfIpxStaticSapEntry
        ACCESS	not-accessible
        STATUS	deprecated
        DESCRIPTION
                "An entry in the Routing Table"
        INDEX	{ wfIpxStaticSapIntf,
    		  wfIpxStaticSapCircuit,
    		  wfIpxStaticSapType,
    		  wfIpxStaticSapNetwork,
    		  wfIpxStaticSapSocket }
        ::= { wfIpxStaticSapTable 1 }

    WfIpxStaticSapEntry ::= SEQUENCE {
    	    wfIpxStaticSapDelete
    		INTEGER,
    	    wfIpxStaticSapDisable
    		INTEGER,
    	    wfIpxStaticSapType
    		OCTET STRING,
    	    wfIpxStaticSapNetwork
    		OCTET STRING,
    	    wfIpxStaticSapHost
    		OCTET STRING,
    	    wfIpxStaticSapSocket
    		OCTET STRING,
    	    wfIpxStaticSapName
    		DisplayString,
    	    wfIpxStaticSapHops
    		INTEGER,
    	    wfIpxStaticSapIndex
    		OCTET STRING,
    	    wfIpxStaticSapIntf
    		OCTET STRING,
    	    wfIpxStaticSapCircuit
    		INTEGER
        }

    wfIpxStaticSapDelete OBJECT-TYPE
        SYNTAX	INTEGER {
    		    created(1),
    		    deleted(2)
    		}
        ACCESS	read-write
        STATUS	deprecated
        DESCRIPTION
                "Create/Delete parameter. Default is created.
                Users perform an SNMP SET operation on this
                object in order to create/delete the IPX
                Static SAP."
        DEFVAL	{ created }
        ::= { wfIpxStaticSapEntry 1 }

    wfIpxStaticSapDisable OBJECT-TYPE
        SYNTAX	INTEGER {
    		    enabled(1),
    		    disabled(2)
    		}
        ACCESS	read-write
        STATUS	deprecated
        DESCRIPTION
                "Enable/Disable parameter. Default is enabled.
                Users perform an SNMP SET operation on this
                object in order to enable/disable this IPX
                Static Route."
        DEFVAL	{ enabled }
        ::= { wfIpxStaticSapEntry 2 }

    wfIpxStaticSapType OBJECT-TYPE
        SYNTAX	OCTET STRING (SIZE (2))
        ACCESS	read-only
        STATUS	deprecated
        DESCRIPTION
                "Multiple routes to a single
                destination can appear in the table, but access to
                such multiple entries is dependent on the table-
                access mechanisms defined by the network
                management protocol in use."
        ::= { wfIpxStaticSapEntry 3 }

    wfIpxStaticSapNetwork OBJECT-TYPE
        SYNTAX	OCTET STRING (SIZE (4))
        ACCESS	read-only
        STATUS	deprecated
        DESCRIPTION
                "The network address of this service."
        ::= { wfIpxStaticSapEntry 4 }

    wfIpxStaticSapHost OBJECT-TYPE
        SYNTAX	OCTET STRING
        ACCESS	read-write
        STATUS	deprecated
        DESCRIPTION
                "The host address for this service."
        ::= { wfIpxStaticSapEntry 5 }

    wfIpxStaticSapSocket OBJECT-TYPE
        SYNTAX	OCTET STRING (SIZE (2))
        ACCESS	read-only
        STATUS	deprecated
        DESCRIPTION
                "The socket for this particular service"
        ::= { wfIpxStaticSapEntry 6 }

    wfIpxStaticSapName OBJECT-TYPE
        SYNTAX	DisplayString
        ACCESS	read-write
        STATUS	deprecated
        DESCRIPTION
                "The server name."
        ::= { wfIpxStaticSapEntry 7 }

    wfIpxStaticSapHops OBJECT-TYPE
        SYNTAX	INTEGER
        ACCESS	read-write
        STATUS	deprecated
        DESCRIPTION
                "The number of Hops away service is from router."
        ::= { wfIpxStaticSapEntry 8 }

    wfIpxStaticSapIndex OBJECT-TYPE
        SYNTAX	OCTET STRING
        ACCESS	read-only
        STATUS	deprecated
        DESCRIPTION
                "Index string comprised of intf1.type.network.hostid.socket.
                Makes sorting easier and its a ah work around."
        ::= { wfIpxStaticSapEntry 9 }

    wfIpxStaticSapIntf OBJECT-TYPE
        SYNTAX	OCTET STRING (SIZE (4))
        ACCESS	read-only
        STATUS	deprecated
        DESCRIPTION
                "Network Address of Nexthop Interface."
        ::= { wfIpxStaticSapEntry 10 }

    wfIpxStaticSapCircuit OBJECT-TYPE
        SYNTAX	INTEGER
        ACCESS	read-only
        STATUS	deprecated
        DESCRIPTION
                "Circuit of Nexthop Interface."
        ::= { wfIpxStaticSapEntry 11 }

    wfIpxSapNetLvlFilterTable OBJECT-TYPE
        SYNTAX	SEQUENCE OF WfIpxSapNetLvlFilter
        ACCESS	not-accessible
        STATUS	deprecated
        DESCRIPTION
                "The list of Network Level SAP Filters"
        ::= { wfIpxGroup 9 }

    wfIpxSapNetLvlFilter OBJECT-TYPE
        SYNTAX	WfIpxSapNetLvlFilter
        ACCESS	not-accessible
        STATUS	deprecated
        DESCRIPTION
                "An entry in the Filter Table"
        INDEX	{ wfIpxSapNetLvlIntf,
    		  wfIpxSapNetLvlIndex }
        ::= { wfIpxSapNetLvlFilterTable 1 }

    WfIpxSapNetLvlFilter ::= SEQUENCE {
    	    wfIpxSapNetLvlDelete
    		INTEGER,
    	    wfIpxSapNetLvlDisable
    		INTEGER,
    	    wfIpxSapNetLvlTargNetwork
    		OCTET STRING,
    	    wfIpxSapNetLvlType
    		OCTET STRING,
    	    wfIpxSapNetLvlAction
    		INTEGER,
    	    wfIpxSapNetLvlIntf
    		OCTET STRING,
    	    wfIpxSapNetLvlIndex
    		INTEGER
        }

    wfIpxSapNetLvlDelete OBJECT-TYPE
        SYNTAX	INTEGER {
    		    created(1),
    		    deleted(2)
    		}
        ACCESS	read-write
        STATUS	deprecated
        DESCRIPTION
                "Create/Delete parameter. Default is created.
                Users perform an SNMP SET operation on this
                object in order to create/delete the IPX
                Sap network level filter."
        DEFVAL	{ created }
        ::= { wfIpxSapNetLvlFilter 1 }

    wfIpxSapNetLvlDisable OBJECT-TYPE
        SYNTAX	INTEGER {
    		    enabled(1),
    		    disabled(2)
    		}
        ACCESS	read-write
        STATUS	deprecated
        DESCRIPTION
                "Enable/Disable parameter. Default is enabled.
                Users perform an SNMP SET operation on this
                object in order to enable/disable this IPX
                network level SAP filter."
        DEFVAL	{ enabled }
        ::= { wfIpxSapNetLvlFilter 2 }

    wfIpxSapNetLvlTargNetwork OBJECT-TYPE
        SYNTAX	OCTET STRING
        ACCESS	read-write
        STATUS	deprecated
        DESCRIPTION
                "The Target Network address to monitor"
        ::= { wfIpxSapNetLvlFilter 3 }

    wfIpxSapNetLvlType OBJECT-TYPE
        SYNTAX	OCTET STRING
        ACCESS	read-write
        STATUS	deprecated
        DESCRIPTION
                "The Type of service to monitor"
        ::= { wfIpxSapNetLvlFilter 4 }

    wfIpxSapNetLvlAction OBJECT-TYPE
        SYNTAX	INTEGER {
    		    active(1),
    		    inactive(2)
    		}
        ACCESS	read-write
        STATUS	deprecated
        DESCRIPTION
                "The Action to take Advertise or not Advertise"
        DEFVAL	{ active }
        ::= { wfIpxSapNetLvlFilter 5 }

    wfIpxSapNetLvlIntf OBJECT-TYPE
        SYNTAX	OCTET STRING (SIZE (4))
        ACCESS	read-only
        STATUS	deprecated
        DESCRIPTION
                "The Interface identifier for this filter"
        ::= { wfIpxSapNetLvlFilter 6 }

    wfIpxSapNetLvlIndex OBJECT-TYPE
        SYNTAX	INTEGER
        ACCESS	read-only
        STATUS	deprecated
        DESCRIPTION
                "The Filter Index ."
        ::= { wfIpxSapNetLvlFilter 7 }

    wfIpxSapServtLvlFilterTable OBJECT-TYPE
        SYNTAX	SEQUENCE OF WfIpxSapServLvlFilter
        ACCESS	not-accessible
        STATUS	deprecated
        DESCRIPTION
                "The list of Server Level SAP Filters"
        ::= { wfIpxGroup 10 }

    wfIpxSapServLvlFilter OBJECT-TYPE
        SYNTAX	WfIpxSapServLvlFilter
        ACCESS	not-accessible
        STATUS	deprecated
        DESCRIPTION
                "An entry in the Filter Table"
        INDEX	{ wfIpxSapServLvlIntf,
    		  wfIpxSapServLvlIndex }
        ::= { wfIpxSapServtLvlFilterTable 1 }

    WfIpxSapServLvlFilter ::= SEQUENCE {
    	    wfIpxSapServLvlDelete
    		INTEGER,
    	    wfIpxSapServLvlDisable
    		INTEGER,
    	    wfIpxSapServLvlTargServer
    		DisplayString,
    	    wfIpxSapServLvlType
    		OCTET STRING,
    	    wfIpxSapServLvlAction
    		INTEGER,
    	    wfIpxSapServLvlIntf
    		OCTET STRING,
    	    wfIpxSapServLvlIndex
    		INTEGER
        }

    wfIpxSapServLvlDelete OBJECT-TYPE
        SYNTAX	INTEGER {
    		    created(1),
    		    deleted(2)
    		}
        ACCESS	read-write
        STATUS	deprecated
        DESCRIPTION
                "Create/Delete parameter. Default is created.
                Users perform an SNMP SET operation on this
                object in order to create/delete the IPX
                server-level SAP filter."
        DEFVAL	{ created }
        ::= { wfIpxSapServLvlFilter 1 }

    wfIpxSapServLvlDisable OBJECT-TYPE
        SYNTAX	INTEGER {
    		    enabled(1),
    		    disabled(2)
    		}
        ACCESS	read-write
        STATUS	deprecated
        DESCRIPTION
                "Enable/Disable parameter. Default is enabled.
                Users perform an SNMP SET operation on this
                object in order to enable/disable this IPX
                server-level SAP filter."
        DEFVAL	{ enabled }
        ::= { wfIpxSapServLvlFilter 2 }

    wfIpxSapServLvlTargServer OBJECT-TYPE
        SYNTAX	DisplayString
        ACCESS	read-write
        STATUS	deprecated
        DESCRIPTION
                "The Server Name to monitor."
        ::= { wfIpxSapServLvlFilter 3 }

    wfIpxSapServLvlType OBJECT-TYPE
        SYNTAX	OCTET STRING
        ACCESS	read-write
        STATUS	deprecated
        DESCRIPTION
                "Type of service File server, Printer, etc..."
        ::= { wfIpxSapServLvlFilter 4 }

    wfIpxSapServLvlAction OBJECT-TYPE
        SYNTAX	INTEGER {
    		    active(1),
    		    inactive(2)
    		}
        ACCESS	read-write
        STATUS	deprecated
        DESCRIPTION
                "Associated Action (advertise or ignore )"
        DEFVAL	{ active }
        ::= { wfIpxSapServLvlFilter 5 }

    wfIpxSapServLvlIntf OBJECT-TYPE
        SYNTAX	OCTET STRING (SIZE (4))
        ACCESS	read-only
        STATUS	deprecated
        DESCRIPTION
                "The Interface identifier for this filter"
        ::= { wfIpxSapServLvlFilter 6 }

    wfIpxSapServLvlIndex OBJECT-TYPE
        SYNTAX	INTEGER
        ACCESS	read-only
        STATUS	deprecated
        DESCRIPTION
                "The Filter Index ."
        ::= { wfIpxSapServLvlFilter 7 }

    wfIpxTrafficFilterTable OBJECT-TYPE
        SYNTAX	SEQUENCE OF WfIpxTrafficFilterEntry
        ACCESS	not-accessible
        STATUS	deprecated
        DESCRIPTION
                "IPX Traffic Filters"
        ::= { wfIpxGroup 11 }

    wfIpxTrafficFilterEntry OBJECT-TYPE
        SYNTAX	WfIpxTrafficFilterEntry
        ACCESS	not-accessible
        STATUS	deprecated
        DESCRIPTION
                "A traffic filter definition"
        INDEX	{ wfIpxTrafficFilterInterface,
    		  wfIpxTrafficFilterCircuit,
    		  wfIpxTrafficFilterRuleNumber,
    		  wfIpxTrafficFilterFragment }
        ::= { wfIpxTrafficFilterTable 1 }

    WfIpxTrafficFilterEntry ::= SEQUENCE {
    	    wfIpxTrafficFilterCreate
    		INTEGER,
    	    wfIpxTrafficFilterEnable
    		INTEGER,
    	    wfIpxTrafficFilterStatus
    		INTEGER,
    	    wfIpxTrafficFilterCounter
    		Counter,
    	    wfIpxTrafficFilterDefinition
    		Opaque,
    	    wfIpxTrafficFilterReserved
    		INTEGER,
    	    wfIpxTrafficFilterInterface
    		OCTET STRING,
    	    wfIpxTrafficFilterCircuit
    		INTEGER,
    	    wfIpxTrafficFilterRuleNumber
    		INTEGER,
    	    wfIpxTrafficFilterFragment
    		INTEGER,
    	    wfIpxTrafficFilterName
    		DisplayString
        }

    wfIpxTrafficFilterCreate OBJECT-TYPE
        SYNTAX	INTEGER {
    		    created(1),
    		    deleted(2)
    		}
        ACCESS	read-write
        STATUS	deprecated
        DESCRIPTION
                "Defines the existence of the traffic filter rule:
                created - traffic filter exists
                delete - traffic filter does not exist and can be deleted."
        DEFVAL	{ created }
        ::= { wfIpxTrafficFilterEntry 1 }

    wfIpxTrafficFilterEnable OBJECT-TYPE
        SYNTAX	INTEGER {
    		    enabled(1),
    		    disabled(2)
    		}
        ACCESS	read-write
        STATUS	deprecated
        DESCRIPTION
                "Defines whether or not the traffic filter rule should be used:
                enabled - activate the rule.
                disabled - inactivate the rule."
        DEFVAL	{ enabled }
        ::= { wfIpxTrafficFilterEntry 2 }

    wfIpxTrafficFilterStatus OBJECT-TYPE
        SYNTAX	INTEGER {
    		    active(1),
    		    error(2),
    		    inactive(3)
    		}
        ACCESS	read-only
        STATUS	deprecated
        DESCRIPTION
                "Defines the current status of the traffic filter:
                inactive - the rule is not in use.
                active - the rule is being used.
                error - the application detected an error in the rule."
        DEFVAL	{ inactive }
        ::= { wfIpxTrafficFilterEntry 3 }

    wfIpxTrafficFilterCounter OBJECT-TYPE
        SYNTAX	Counter
        ACCESS	read-only
        STATUS	deprecated
        DESCRIPTION
                "The number of received packets that have
                matched this rule."
        ::= { wfIpxTrafficFilterEntry 4 }

    wfIpxTrafficFilterDefinition OBJECT-TYPE
        SYNTAX	Opaque
        ACCESS	read-write
        STATUS	deprecated
        DESCRIPTION
                "The filter rule definition."
        ::= { wfIpxTrafficFilterEntry 5 }

    wfIpxTrafficFilterReserved OBJECT-TYPE
        SYNTAX	INTEGER
        ACCESS	read-only
        STATUS	deprecated
        DESCRIPTION
                "Reserved field."
        ::= { wfIpxTrafficFilterEntry 6 }

    wfIpxTrafficFilterInterface OBJECT-TYPE
        SYNTAX	OCTET STRING (SIZE (4))
        ACCESS	read-only
        STATUS	deprecated
        DESCRIPTION
                "The network address of the IPX
                interface to which this filter is applied."
        ::= { wfIpxTrafficFilterEntry 7 }

    wfIpxTrafficFilterCircuit OBJECT-TYPE
        SYNTAX	INTEGER
        ACCESS	read-only
        STATUS	deprecated
        DESCRIPTION
                "The ID of the Circuit to which the
                filter is applied."
        ::= { wfIpxTrafficFilterEntry 8 }

    wfIpxTrafficFilterRuleNumber OBJECT-TYPE
        SYNTAX	INTEGER
        ACCESS	read-only
        STATUS	deprecated
        DESCRIPTION
                "ID for the rule."
        ::= { wfIpxTrafficFilterEntry 9 }

    wfIpxTrafficFilterFragment OBJECT-TYPE
        SYNTAX	INTEGER
        ACCESS	read-only
        STATUS	deprecated
        DESCRIPTION
                "Fragment number - for large rules."
        ::= { wfIpxTrafficFilterEntry 10 }

    wfIpxTrafficFilterName OBJECT-TYPE
        SYNTAX	DisplayString
        ACCESS	read-write
        STATUS	deprecated
        DESCRIPTION
                "Name of the rule number."
        ::= { wfIpxTrafficFilterEntry 11 }

    wfIpxAggrStats	OBJECT IDENTIFIER ::= { wfIpxGroup 14 }

    wfIpxAggrInDatagrams OBJECT-TYPE
        SYNTAX	Counter
        ACCESS	read-only
        STATUS	mandatory
        DESCRIPTION
                "The total number of datagrams received"
        ::= { wfIpxAggrStats 1 }

    wfIpxAggrOutDatagrams OBJECT-TYPE
        SYNTAX	Counter
        ACCESS	read-only
        STATUS	mandatory
        DESCRIPTION
                "The total number of datagrams sent (includes datagrams
                forwarded)"
        ::= { wfIpxAggrStats 2 }

    wfIpxAggrFwdDatagrams OBJECT-TYPE
        SYNTAX	Counter
        ACCESS	read-only
        STATUS	mandatory
        DESCRIPTION
                "The total number of datagrams forwarded"
        ::= { wfIpxAggrStats 3 }

    wfIpxAggrInDiscards OBJECT-TYPE
        SYNTAX	Counter
        ACCESS	read-only
        STATUS	mandatory
        DESCRIPTION
                "The total number of datagrams queued for reception that
                were discarded for resource reasons"
        ::= { wfIpxAggrStats 4 }

    wfIpxAggrInHdrErrs OBJECT-TYPE
        SYNTAX	Counter
        ACCESS	read-only
        STATUS	mandatory
        DESCRIPTION
                "The total number of datagrams discarded because of errors
                in the IPX header."
        ::= { wfIpxAggrStats 5 }

    wfIpxAggrInAddrErrs OBJECT-TYPE
        SYNTAX	Counter
        ACCESS	read-only
        STATUS	mandatory
        DESCRIPTION
                "The total nmber of datagrams received whose destination
                address was invalid for this entity."
        ::= { wfIpxAggrStats 6 }

    wfIpxAggrInUnknownProtos OBJECT-TYPE
        SYNTAX	Counter
        ACCESS	read-only
        STATUS	mandatory
        DESCRIPTION
                "The total number of datagrams received locally which
                specified an unknown or unsupported protocol."
        ::= { wfIpxAggrStats 7 }

    wfIpxAggrOutDiscards OBJECT-TYPE
        SYNTAX	Counter
        ACCESS	read-only
        STATUS	mandatory
        DESCRIPTION
                "The total number of datagrams queued for transmission
                that were discarded for resource reasons."
        ::= { wfIpxAggrStats 8 }

    wfIpxAggrOutNoRoutes OBJECT-TYPE
        SYNTAX	Counter
        ACCESS	read-only
        STATUS	mandatory
        DESCRIPTION
                "The total number of datagrams queued for transmission thet
                were discarded because the destination was unreachable."
        ::= { wfIpxAggrStats 9 }

    END  -- Wellfleet-IPX-MIB
