USR-IPX-CFG-MIB DEFINITIONS ::= BEGIN
	IMPORTS
          OBJECT-TYPE, MODULE-IDENTITY,
          Integer32
                  FROM SNMPv2-SMI
          common
                  FROM USR-DEFINITIONS-MIB;
usrIpxCfg MODULE-IDENTITY
        LAST-UPDATED "200205051315Z"
        ORGANIZATION "CommWorks Corporation, a 3Com Company"
        CONTACT-INFO "Customer Support"
        DESCRIPTION
                "The commWorks enterprise defined MIB objects
                  for the IPX Configuration process."
--      REVISION "200205051315Z"
--      DESCRIPTION "Convert to SNMPv2"
        ::= { common 20 }
   -- Begin managed object definitions here...
     usrIpxCfgNetworkTable OBJECT-TYPE
	     SYNTAX SEQUENCE OF UsrIpxCfgNetworkEntry
	     MAX-ACCESS not-accessible
	     STATUS     current
	     DESCRIPTION
		     "This table is the same as the usrIpxPortalTable,
		      with the exception that it is indexed by the Network Number
			 defined in the usrIpxStaticRouteTable. This table will be
                used only by the the Configuration File Manager process to
                load permament configuration file records for named networks
                at system boot time. Any attempt to set this table from
                either the CLI process or SNMP will fail."
     ::= { usrIpxCfg 1 }
     usrIpxCfgNetworkEntry OBJECT-TYPE
	     SYNTAX UsrIpxCfgNetworkEntry
	     MAX-ACCESS not-accessible
	     STATUS     current
	     DESCRIPTION
		     "A (conceptual) entry for one IPX Network."
	     INDEX { usrIpxCfgNetSysInstance,
                  usrIpxCfgNetNetNumber }
     ::= { usrIpxCfgNetworkTable 1 }
     UsrIpxCfgNetworkEntry ::= SEQUENCE {
               usrIpxCfgNetSysInstance
                    Integer32,
               usrIpxCfgNetNetNumber
                    Integer32,
               usrIpxCfgNetNetBiosState
                    INTEGER,
               usrIpxCfgNetNetworkDelay
                    Integer32,
               usrIpxCfgNetRipBroadcastState
                    INTEGER,
               usrIpxCfgNetSapBroadcastState
                    INTEGER,
               usrIpxCfgNetRipPeriodicState
                    INTEGER,
               usrIpxCfgNetSapPeriodicState
                    INTEGER,
               usrIpxCfgNetNetBiosNameCachingState
                    INTEGER,
               usrIpxCfgNetNetBiosHops
                    Integer32,
               usrIpxCfgNetDiagnosticState
                    INTEGER,
               usrIpxCfgNetNetBiosNameCachingTimer
                    Integer32,
               usrIpxCfgNetMaxLearningRetries
                    Integer32,
			usrIpxCfgNetRipCircState
				INTEGER,
			usrIpxCfgNetRipCircUpdate
				Integer32,
			usrIpxCfgNetRipCircAgeMultiplier
				Integer32,
			usrIpxCfgNetRipCircPacketSize
				Integer32,
			usrIpxCfgNetSapCircState
				INTEGER,
			usrIpxCfgNetSapCircUpdate
				Integer32,
			usrIpxCfgNetSapCircAgeMultiplier
				Integer32,
			usrIpxCfgNetSapCircPacketSize
				Integer32,
			usrIpxCfgNetSapCircGetNearestServerReply
				INTEGER,
			usrIpxCfgNetIpxCircExistState
				INTEGER,
			usrIpxCfgNetIpxCircOperState
				INTEGER,
			usrIpxCfgNetIpxCircType
				INTEGER,
			usrIpxCfgNetIpxCircLocalMaxPacketSize
				Integer32
	}
     usrIpxCfgNetSysInstance OBJECT-TYPE
          SYNTAX      Integer32
          MAX-ACCESS      not-accessible
          STATUS          current
          DESCRIPTION 
               "The unique identifier of the instance of IPX to which this
               row corresponds."
     ::= {usrIpxCfgNetworkEntry 1}
     usrIpxCfgNetNetNumber OBJECT-TYPE
          SYNTAX      Integer32
          MAX-ACCESS      not-accessible
          STATUS          current
          DESCRIPTION
               "The unique identifier for this IPX network."
     ::= {usrIpxCfgNetworkEntry 2}
     usrIpxCfgNetNetBiosState OBJECT-TYPE
          SYNTAX      INTEGER {
                        disable(0),
                        enable(1)
                       }
          MAX-ACCESS      read-write
          STATUS          current
          DESCRIPTION
               "The state of NetBios Processing. When enabled the router
               maintains a NetBios name table."
          --CONFIGURABLE
     ::= {usrIpxCfgNetworkEntry 3}
     usrIpxCfgNetNetworkDelay OBJECT-TYPE
          SYNTAX      Integer32
          MAX-ACCESS      read-write
          STATUS          current
          DESCRIPTION
               "The delay, in ticks, for this portal interface."
          --CONFIGURABLE
     ::= {usrIpxCfgNetworkEntry 4}
     usrIpxCfgNetRipBroadcastState OBJECT-TYPE
          SYNTAX      INTEGER {
                        disable(0),
                        enable(1)
                       }
          MAX-ACCESS      read-write 
          STATUS          current
          DESCRIPTION
               "RIP broadcast packet state. When enabled IPX RIP will be
               enabled to send out RIP request packets transmitted over this
               portal. To totally disable RIP traffic
               usrIpxPortalRipPeriodicState must also be set to disable."
          --CONFIGURABLE
     ::= {usrIpxCfgNetworkEntry 5}
     usrIpxCfgNetSapBroadcastState OBJECT-TYPE
          SYNTAX      INTEGER {
                        disable(0),
                        enable(1)
                       }
          MAX-ACCESS      read-write
          STATUS          current
          DESCRIPTION
               "SAP broadcast packet state. When enabled IPX SAP will be
               enabled to send out SAP request packets transmitted over this
               portal. To totally disable SAP traffic
               usrIpxPortalSapPeriodicState must also be set to disable."
          --CONFIGURABLE
     ::= {usrIpxCfgNetworkEntry 6}
     usrIpxCfgNetRipPeriodicState OBJECT-TYPE
          SYNTAX      INTEGER {
                        disable(0),
                        enable(1)
                       }
          MAX-ACCESS      read-write
          STATUS          current
          DESCRIPTION
               "RIP periodic state."
          --CONFIGURABLE
     ::= {usrIpxCfgNetworkEntry 7}
     usrIpxCfgNetSapPeriodicState OBJECT-TYPE
          SYNTAX      INTEGER {
                        disable(0),
                        enable(1)
                       }
          MAX-ACCESS      read-write
          STATUS          current
          DESCRIPTION
               "Controls sending periodic SAP broadcasts over this portal."
          --CONFIGURABLE
     ::= {usrIpxCfgNetworkEntry 8}
     usrIpxCfgNetNetBiosNameCachingState OBJECT-TYPE
          SYNTAX      INTEGER {
                        disable(0),
                        enable(1)
                       }
          MAX-ACCESS      read-write
          STATUS          current
          DESCRIPTION
               "NetBios name caching state. When enabled IPX will maintain a
               table of NetBios names"
          --CONFIGURABLE
     ::= {usrIpxCfgNetworkEntry 9}
     usrIpxCfgNetNetBiosHops OBJECT-TYPE
          SYNTAX      Integer32 (0..65535)
          MAX-ACCESS      read-write
          STATUS          current
          DESCRIPTION
               "NetBios maximum number of hops."
          --CONFIGURABLE
     ::= {usrIpxCfgNetworkEntry 10}
     usrIpxCfgNetDiagnosticState OBJECT-TYPE
          SYNTAX      INTEGER {
                        disable(0),
                        enable(1)
                       }
          MAX-ACCESS      read-write
          STATUS          current
          DESCRIPTION
               "Diagnostic state."
          --CONFIGURABLE
     ::= {usrIpxCfgNetworkEntry 11}
     usrIpxCfgNetNetBiosNameCachingTimer OBJECT-TYPE
          SYNTAX      Integer32
          MAX-ACCESS      read-write
          STATUS          current
          DESCRIPTION
               "NetBios name caching timer."
          --CONFIGURABLE
     ::= {usrIpxCfgNetworkEntry 12}
     usrIpxCfgNetMaxLearningRetries OBJECT-TYPE
          SYNTAX      Integer32
          MAX-ACCESS      read-write
          STATUS          current
          DESCRIPTION
               "Maximum number of learning retries."
          --CONFIGURABLE
     ::= {usrIpxCfgNetworkEntry 13}
     usrIpxCfgNetRipCircState OBJECT-TYPE
   		SYNTAX      INTEGER {
                        off(1),
                        on(2),
                        auto-on(3),
                        auto-off(4)
                       }
   		MAX-ACCESS      read-write
   		STATUS          current
   		DESCRIPTION "Indicates whether RIP information may be sent/received
          	       over this circuit."
   		DEFVAL      { auto-off }
		--CONFIGURABLE
     ::= {usrIpxCfgNetworkEntry 14}
     usrIpxCfgNetRipCircUpdate OBJECT-TYPE
   		SYNTAX      Integer32
   		MAX-ACCESS      read-write
   		STATUS          current
   		DESCRIPTION "The RIP periodic update interval, in seconds."
   		DEFVAL      { 60 }
		--CONFIGURABLE
     ::= {usrIpxCfgNetworkEntry 15}
	usrIpxCfgNetRipCircAgeMultiplier OBJECT-TYPE
		SYNTAX      Integer32
		MAX-ACCESS      read-write
		STATUS          current
		DESCRIPTION "The holding multiplier for information received in RIP
          	       periodic updates."
		DEFVAL      { 4 }
		--CONFIGURABLE
     ::= {usrIpxCfgNetworkEntry 16}
	usrIpxCfgNetRipCircPacketSize OBJECT-TYPE
   		SYNTAX      Integer32
   		MAX-ACCESS      read-write
   		STATUS          current
   		DESCRIPTION "The RIP packet size used on this circuit."
		--CONFIGURABLE
   	::= {usrIpxCfgNetworkEntry 17}
     usrIpxCfgNetSapCircState OBJECT-TYPE
		SYNTAX      INTEGER {
                        off(1),
                        on(2),
                        auto-on(3),
                        auto-off(4)
                       }
   		MAX-ACCESS      read-write
   		STATUS          current
   		DESCRIPTION "Indicates whether SAP information may be sent/received
          	       over this circuit."
 		DEFVAL      { auto-off }
		--CONFIGURABLE
   	::= {usrIpxCfgNetworkEntry 18}
	usrIpxCfgNetSapCircUpdate OBJECT-TYPE
   		SYNTAX      Integer32
   		MAX-ACCESS      read-write
   		STATUS          current
   		DESCRIPTION "The SAP periodic update interval, in seconds."
   		DEFVAL      { 60 }
		--CONFIGURABLE
   	::= {usrIpxCfgNetworkEntry 19}
	usrIpxCfgNetSapCircAgeMultiplier OBJECT-TYPE
   		SYNTAX      Integer32
   		MAX-ACCESS      read-write
   		STATUS          current
   		DESCRIPTION "The holding multiplier for information received in SAP
	                 periodic updates."
   		DEFVAL      { 4 }
		--CONFIGURABLE
   	::= {usrIpxCfgNetworkEntry 20}
	usrIpxCfgNetSapCircPacketSize OBJECT-TYPE
   		SYNTAX      Integer32
   		MAX-ACCESS      read-write
   		STATUS          current
   		DESCRIPTION "The SAP packet size used on this circuit."
		--CONFIGURABLE
   	::= {usrIpxCfgNetworkEntry 21}
	usrIpxCfgNetSapCircGetNearestServerReply OBJECT-TYPE
   		SYNTAX      INTEGER {
                        no(1),
                        yes(2)
                       }
   		MAX-ACCESS      read-write
   		STATUS          current
   		DESCRIPTION "Indicates whether to respond to SAP get nearest server
          	       requests received on this circuit."
   		DEFVAL      { yes }
		--CONFIGURABLE
   	::= {usrIpxCfgNetworkEntry 22}
	usrIpxCfgNetIpxCircExistState OBJECT-TYPE
   		SYNTAX      INTEGER {
                        off(1),
                        on(2)
                       }
   		MAX-ACCESS      read-write
   		STATUS          current
   		DESCRIPTION "The validity of this circuit entry.  A circuit with this
          	       value set to off may be deleted from the table at the
                	  IPX implementation's discretion."
		--CONFIGURABLE
   	::= {usrIpxCfgNetworkEntry 23}
	usrIpxCfgNetIpxCircOperState OBJECT-TYPE
   		SYNTAX      INTEGER {
                        down(1),
                        up(2),
                        sleeping(3)
                       }
   		MAX-ACCESS      read-write
   		STATUS          current
   		DESCRIPTION "The operational state of the circuit."
		--CONFIGURABLE
   	::= {usrIpxCfgNetworkEntry 24}
	usrIpxCfgNetIpxCircType OBJECT-TYPE
   		SYNTAX      INTEGER {
                        other(1),
                        broadcast(2),
                        ptToPt(3),
                        wanRIP(4),
                        unnumberedRIP(5),
                        dynamic(6),
                        wanWS(7)
                       }
   		MAX-ACCESS      read-write
   		STATUS          current
   		DESCRIPTION "The type of the circuit."
		--CONFIGURABLE
   	::= {usrIpxCfgNetworkEntry 25}
	usrIpxCfgNetIpxCircLocalMaxPacketSize OBJECT-TYPE
   		SYNTAX      Integer32
   		MAX-ACCESS      read-write
   		STATUS          current
   		DESCRIPTION "The maximum size (including header), in bytes, that the
          	       system supports locally on this circuit."
		--CONFIGURABLE
   	::= {usrIpxCfgNetworkEntry 26}
END  -- End of USR-IPX-CFG-MIB DEFINITIONS
