Wellfleet-ISDN-MIB DEFINITIONS ::= BEGIN

-- Created by mdl2asn version 3.1
-- Creation date: Wed Aug 30 16:44:31 EDT 1995


    IMPORTS

      Counter
        FROM RFC1155-SMI
      OBJECT-TYPE
        FROM RFC-1212
      DisplayString
        FROM RFC1213-MIB
      wfIsdnGroup
        FROM Wellfleet-COMMON-MIB;


    wfModemIfTable OBJECT-TYPE
        SYNTAX	SEQUENCE OF WfModemIfEntry
        ACCESS	not-accessible
        STATUS	mandatory
        DESCRIPTION
                "ISDN SYNC  line record"
        ::= { wfIsdnGroup 1 }

    wfModemIfEntry OBJECT-TYPE
        SYNTAX	WfModemIfEntry
        ACCESS	not-accessible
        STATUS	mandatory
        DESCRIPTION
                "An entry in the MODEM_IF table"
        INDEX	{ wfModemIfSlot,
    		  wfModemIfConnector }
        ::= { wfModemIfTable 1 }

    WfModemIfEntry ::= SEQUENCE {
    	    wfModemIfDelete
    		INTEGER,
    	    wfModemIfSlot
    		INTEGER,
    	    wfModemIfConnectStatus
    		INTEGER,
    	    wfModemIfConnector
    		INTEGER,
    	    wfModemIfCct
    		INTEGER,
    	    wfModemIfConnectWhen
    		INTEGER,
    	    wfModemIfConnectionTime
    		INTEGER,
    	    wfModemIfMinDurationTime
    		INTEGER,
    	    wfModemIfInactivityTime
    		INTEGER,
    	    wfModemIfRetryDelayTime
    		INTEGER,
    	    wfModemIfLineBandwidth
    		INTEGER,
    	    wfModemIfChanAggrMax
    		INTEGER,
    	    wfModemIfChanAggrMin
    		INTEGER,
    	    wfModemIfChanMgmt
    		INTEGER,
    	    wfModemIfRestrictType
    		INTEGER,
    	    wfModemIfDialRetryCount
    		INTEGER,
    	    wfModemIfRetries
    		Counter,
    	    wfModemIfForceDial
    		INTEGER,
    	    wfModemIfForceHangup
    		INTEGER,
    	    wfModemIfBringUpHour
    		INTEGER,
    	    wfModemIfBringUpMinute
    		INTEGER,
    	    wfModemIfTakeDownHour
    		INTEGER,
    	    wfModemIfTakeDownMinute
    		INTEGER,
    	    wfModemIfConnectRmtStationNum
    		DisplayString,
    	    wfModemIfConnectSubAddr
    		DisplayString,
    	    wfModemIfMediaType
    		INTEGER,
    	    wfModemIfUpperLayerTimeOut
    		INTEGER,
    	    wfModemIfRingIndicator
    		INTEGER,
    	    wfModemIfFsmDebug
                INTEGER
        }

    wfModemIfDelete OBJECT-TYPE
        SYNTAX	INTEGER {
    		    created(1),
    		    deleted(2)
    		}
        ACCESS	read-write
        STATUS	mandatory
        DESCRIPTION
                "Create/Delete parameter"
        DEFVAL	{ created }
        ::= { wfModemIfEntry 1 }

    wfModemIfSlot OBJECT-TYPE
        SYNTAX	INTEGER(1..14)
        ACCESS	read-only
        STATUS	mandatory
        DESCRIPTION
                "Instance ID Slot, filled in by driver"
        ::= { wfModemIfEntry 2 }

    wfModemIfConnectStatus OBJECT-TYPE
        SYNTAX	INTEGER {
    		    connected(1),
    		    disconnected(2)
    		}
        ACCESS	read-only
        STATUS	mandatory
        DESCRIPTION
                "Dial up connection status"
        ::= { wfModemIfEntry 3 }

    wfModemIfConnector OBJECT-TYPE
        SYNTAX	INTEGER {
    		    one(1),
    		    two(2),
    		    three(3),
    		    four(4)
    		}
        ACCESS	read-only
        STATUS	mandatory
        DESCRIPTION
                "Instance ID Connector, filled in by driver"
        ::= { wfModemIfEntry 4 }

    wfModemIfCct OBJECT-TYPE
        SYNTAX	INTEGER(1..1023)
        ACCESS	read-only
        STATUS	mandatory
        DESCRIPTION
                "CCT number for this line instance"
        ::= { wfModemIfEntry 5 }

    wfModemIfConnectWhen OBJECT-TYPE
        SYNTAX	INTEGER {
    		    data(1),
    		    enable(2)
    		}
        ACCESS	read-write
        STATUS	mandatory
        DESCRIPTION
                "when to connect line"
        DEFVAL	{ data }
        ::= { wfModemIfEntry 6 }

    wfModemIfConnectionTime OBJECT-TYPE
        SYNTAX	INTEGER(1..2147483647)
        ACCESS	read-write
        STATUS	mandatory
        DESCRIPTION
                "connection wait timer interval (Seconds)"
        DEFVAL	{ 60 }
        ::= { wfModemIfEntry 7 }

    wfModemIfMinDurationTime OBJECT-TYPE
        SYNTAX	INTEGER(1..2147483647)
        ACCESS	read-write
        STATUS	mandatory
        DESCRIPTION
                "min duration time for the call (Seconds)"
        DEFVAL	{ 180 }
        ::= { wfModemIfEntry 8 }

    wfModemIfInactivityTime OBJECT-TYPE
        SYNTAX	INTEGER(1..720)
        ACCESS	read-write
        STATUS	mandatory
        DESCRIPTION
                "In the absence of data traffic, the timeout period
                before a dial line is disconnected.
                Value is in MINUTES (max 12 hours)"
        DEFVAL	{ 5 }
        ::= { wfModemIfEntry 9 }

    wfModemIfRetryDelayTime OBJECT-TYPE
        SYNTAX	INTEGER {
    		    default(3)
    		}
        ACCESS	read-write
        STATUS	mandatory
        DESCRIPTION
                "delay to wait after retrys fails."
        DEFVAL	{ default }
        ::= { wfModemIfEntry 10 }

    wfModemIfLineBandwidth OBJECT-TYPE
        SYNTAX	INTEGER {
    		    bw56k(56),
    		    bw64k(64),
    		    bw484k(384),
    		    bw1536k(1536)
    		}
        ACCESS	read-write
        STATUS	mandatory
        DESCRIPTION
                "requested bandwidth.  NULL_VAL = Default not to set bandwidth"
        ::= { wfModemIfEntry 11 }

    wfModemIfChanAggrMax OBJECT-TYPE
        SYNTAX	INTEGER(1..24)
        ACCESS	read-write
        STATUS	mandatory
        DESCRIPTION
                "max number of chans to aggregate. NULL_VAL = Default not to used value."
        ::= { wfModemIfEntry 12 }

    wfModemIfChanAggrMin OBJECT-TYPE
        SYNTAX	INTEGER(1..24)
        ACCESS	read-write
        STATUS	mandatory
        DESCRIPTION
                "min number of chans to aggregate. NULL_VAL = Default not to used value."
        ::= { wfModemIfEntry 13 }

    wfModemIfChanMgmt OBJECT-TYPE
        SYNTAX	INTEGER {
    		    disablemgmt(1),
    		    minmgmt(2),
    		    deltamgmt(3)
    		}
        ACCESS	read-write
        STATUS	mandatory
        DESCRIPTION
                "channel mgmt type. NULL_VAL = no management"
        ::= { wfModemIfEntry 14 }

    wfModemIfRestrictType OBJECT-TYPE
        SYNTAX	INTEGER {
    		    calls(1)
    		}
        ACCESS	read-write
        STATUS	mandatory
        DESCRIPTION
                "call restriction type.
                NULL_VAL = Default not to restrict calls,
                1        = Allow defined inbound call numbers only"
        ::= { wfModemIfEntry 15 }

    wfModemIfDialRetryCount OBJECT-TYPE
        SYNTAX	INTEGER(1..10)
        ACCESS	read-write
        STATUS	mandatory
        DESCRIPTION
                "Redial count"
        DEFVAL	{ 3 }
        ::= { wfModemIfEntry 16 }

    wfModemIfRetries OBJECT-TYPE
        SYNTAX	Counter
        ACCESS	read-only
        STATUS	mandatory
        DESCRIPTION
                "Number of retries attempted to connect a dialup line"
        ::= { wfModemIfEntry 17 }

    wfModemIfForceDial OBJECT-TYPE
        SYNTAX	INTEGER {
    		    true(1),
    		    false(2)
    		}
        ACCESS	read-write
        STATUS	mandatory
        DESCRIPTION
                "Force the modem to dial"
        DEFVAL	{ false }
        ::= { wfModemIfEntry 18 }

    wfModemIfForceHangup OBJECT-TYPE
        SYNTAX	INTEGER {
    		    true(1),
    		    false(2)
    		}
        ACCESS	read-write
        STATUS	mandatory
        DESCRIPTION
                "Force the modem to disconnect"
        DEFVAL	{ false }
        ::= { wfModemIfEntry 19 }

    wfModemIfBringUpHour OBJECT-TYPE
        SYNTAX	INTEGER
        ACCESS	read-write
        STATUS	mandatory
        DESCRIPTION
                "Time of day hour to allow a line to dial"
        ::= { wfModemIfEntry 20 }

    wfModemIfBringUpMinute OBJECT-TYPE
        SYNTAX	INTEGER
        ACCESS	read-write
        STATUS	mandatory
        DESCRIPTION
                "Time of day minute to allow a line to dial"
        ::= { wfModemIfEntry 21 }

    wfModemIfTakeDownHour OBJECT-TYPE
        SYNTAX	INTEGER
        ACCESS	read-write
        STATUS	mandatory
        DESCRIPTION
                "Time of day hour to take down a dial line"
        ::= { wfModemIfEntry 22 }

    wfModemIfTakeDownMinute OBJECT-TYPE
        SYNTAX	INTEGER
        ACCESS	read-write
        STATUS	mandatory
        DESCRIPTION
                "Time of day minute to take down a dial line"
        ::= { wfModemIfEntry 23 }

    wfModemIfConnectRmtStationNum OBJECT-TYPE
        SYNTAX	DisplayString
        ACCESS	read-only
        STATUS	mandatory
        DESCRIPTION
                "Phone number connected to (V.25bis mode only)"
        ::= { wfModemIfEntry 24 }

    wfModemIfConnectSubAddr OBJECT-TYPE
        SYNTAX	DisplayString
        ACCESS	read-only
        STATUS	mandatory
        DESCRIPTION
                "Phone number sub address for isdn numbers"
        ::= { wfModemIfEntry 25 }

    wfModemIfMediaType OBJECT-TYPE
        SYNTAX	INTEGER {
    		    raisedtr(1),
    		    v25bis(2),
		    hayes(3)
    		}
        ACCESS	read-only
        STATUS	mandatory
        DESCRIPTION
                "modem type"
        ::= { wfModemIfEntry 26 }

    wfModemIfUpperLayerTimeOut OBJECT-TYPE
        SYNTAX	INTEGER(1..60)
        ACCESS	read-write
        STATUS	mandatory
        DESCRIPTION
                "time out value for upper layer protocol initialization (seconds)"
        DEFVAL	{ 40 }
        ::= { wfModemIfEntry 27 }

    wfModemIfRingIndicator OBJECT-TYPE
        SYNTAX	INTEGER {
    		    enabled(1),
    		    disabled(2)
    		}
        ACCESS	read-write
        STATUS	mandatory
        DESCRIPTION
                "Ring Indicator enable/disable  parameter"
        DEFVAL	{ enabled }
        ::= { wfModemIfEntry 28 }

    wfModemIfFsmDebug OBJECT-TYPE
        SYNTAX	INTEGER {
    		    enabled(1),
    		    disabled(2)
    		}
        ACCESS	read-write
        STATUS	mandatory
        DESCRIPTION
                "FSM Debug indicator (for V25bis or RaiseDtr FSM)"
        DEFVAL	{ disabled }
        ::= { wfModemIfEntry 29 }


    wfIsdnMsgCtrTable OBJECT-TYPE
        SYNTAX	SEQUENCE OF WfIsdnMsgCtrEntry
        ACCESS	not-accessible
        STATUS	mandatory
        DESCRIPTION
                "ISDN message counters, one entry per Digital Subscriber
                Loop (DSL), maintained by the Line Manager."
        ::= { wfIsdnGroup 4 }

    wfIsdnMsgCtrEntry OBJECT-TYPE
        SYNTAX	WfIsdnMsgCtrEntry
        ACCESS	not-accessible
        STATUS	mandatory
        DESCRIPTION
                "An entry in the ISDN message counter table"
        INDEX	{ wfIsdnMsgCtrSlot,
    		  wfIsdnMsgCtrDslID }
        ::= { wfIsdnMsgCtrTable 1 }

    WfIsdnMsgCtrEntry ::= SEQUENCE {
    	    wfIsdnMsgCtrSlot
    		INTEGER,
    	    wfIsdnMsgCtrDslID
    		INTEGER,
    	    wfIsdnMsgCallProcInd
    		Counter,
    	    wfIsdnMsgClearConf
    		Counter,
    	    wfIsdnMsgClearInd
    		Counter,
    	    wfIsdnMsgConnectInd
    		Counter,
    	    wfIsdnMsgSetupInd
    		Counter,
    	    wfIsdnMsgRegisterConf
    		Counter,
    	    wfIsdnMsgMgmtInd
    		Counter,
    	    wfIsdnMsgDiscInd
    		Counter,
    	    wfIsdnMsgActInd
    		Counter,
    	    wfIsdnMsgDeactInd
    		Counter,
    	    wfIsdnMsgConnectConf
    		Counter,
    	    wfIsdnMsgAlertReq
    		Counter,
    	    wfIsdnMsgCallProcReq
    		Counter,
    	    wfIsdnMsgClearReq
    		Counter,
    	    wfIsdnMsgConnectReq
    		Counter,
    	    wfIsdnMsgSetupReq
    		Counter,
    	    wfIsdnMsgMgmtReq
    		Counter,
    	    wfIsdnMsgDiscReq
    		Counter,
    	    wfIsdnMsgActReq
    		Counter,
    	    wfIsdnMsgDeactReq
    		Counter,
    	    wfIsdnMsgAlertInd
    		Counter,
    	    wfIsdnMsgInfoInd
    		Counter
        }

    wfIsdnMsgCtrSlot OBJECT-TYPE
        SYNTAX	INTEGER
        ACCESS	read-write
        STATUS	mandatory
        DESCRIPTION
                "Digital Subscriber Loop (DSL) these counters
                apply to"
        ::= { wfIsdnMsgCtrEntry 1 }

    wfIsdnMsgCtrDslID OBJECT-TYPE
        SYNTAX	INTEGER
        ACCESS	read-write
        STATUS	mandatory
        DESCRIPTION
                "Digital Subscriber Loop (DSL) these counters
                apply to"
        ::= { wfIsdnMsgCtrEntry 2 }

    wfIsdnMsgCallProcInd OBJECT-TYPE
        SYNTAX	Counter
        ACCESS	read-only
        STATUS	mandatory
        DESCRIPTION
                "Call Proceeding Indication from the network"
        ::= { wfIsdnMsgCtrEntry 3 }

    wfIsdnMsgClearConf OBJECT-TYPE
        SYNTAX	Counter
        ACCESS	read-only
        STATUS	mandatory
        DESCRIPTION
                "Release Complete from the network"
        ::= { wfIsdnMsgCtrEntry 4 }

    wfIsdnMsgClearInd OBJECT-TYPE
        SYNTAX	Counter
        ACCESS	read-only
        STATUS	mandatory
        DESCRIPTION
                "Release Indication from the network"
        ::= { wfIsdnMsgCtrEntry 5 }

    wfIsdnMsgConnectInd OBJECT-TYPE
        SYNTAX	Counter
        ACCESS	read-only
        STATUS	mandatory
        DESCRIPTION
                "Connect Indication from the network"
        ::= { wfIsdnMsgCtrEntry 6 }

    wfIsdnMsgSetupInd OBJECT-TYPE
        SYNTAX	Counter
        ACCESS	read-only
        STATUS	mandatory
        DESCRIPTION
                "Setup Indication from the network"
        ::= { wfIsdnMsgCtrEntry 7 }

    wfIsdnMsgRegisterConf OBJECT-TYPE
        SYNTAX	Counter
        ACCESS	read-only
        STATUS	mandatory
        DESCRIPTION
                "Register Confirmation from the network"
        ::= { wfIsdnMsgCtrEntry 8 }

    wfIsdnMsgMgmtInd OBJECT-TYPE
        SYNTAX	Counter
        ACCESS	read-only
        STATUS	mandatory
        DESCRIPTION
                "Management Indication from the network"
        ::= { wfIsdnMsgCtrEntry 9 }

    wfIsdnMsgDiscInd OBJECT-TYPE
        SYNTAX	Counter
        ACCESS	read-only
        STATUS	mandatory
        DESCRIPTION
                "Disconnect Indication from the network"
        ::= { wfIsdnMsgCtrEntry 10 }

    wfIsdnMsgActInd OBJECT-TYPE
        SYNTAX	Counter
        ACCESS	read-only
        STATUS	mandatory
        DESCRIPTION
                "Activation Indication from the driver"
        ::= { wfIsdnMsgCtrEntry 11 }

    wfIsdnMsgDeactInd OBJECT-TYPE
        SYNTAX	Counter
        ACCESS	read-only
        STATUS	mandatory
        DESCRIPTION
                "Deactivation Indication from the driver"
        ::= { wfIsdnMsgCtrEntry 12 }

    wfIsdnMsgConnectConf OBJECT-TYPE
        SYNTAX	Counter
        ACCESS	read-only
        STATUS	mandatory
        DESCRIPTION
                "Connect Acknowledge from the network"
        ::= { wfIsdnMsgCtrEntry 13 }

    wfIsdnMsgAlertReq OBJECT-TYPE
        SYNTAX	Counter
        ACCESS	read-only
        STATUS	mandatory
        DESCRIPTION
                "Alert Request to the network"
        ::= { wfIsdnMsgCtrEntry 14 }

    wfIsdnMsgCallProcReq OBJECT-TYPE
        SYNTAX	Counter
        ACCESS	read-only
        STATUS	mandatory
        DESCRIPTION
                "Call Proceeding Request to the network"
        ::= { wfIsdnMsgCtrEntry 15 }

    wfIsdnMsgClearReq OBJECT-TYPE
        SYNTAX	Counter
        ACCESS	read-only
        STATUS	mandatory
        DESCRIPTION
                "Clear Request to the network"
        ::= { wfIsdnMsgCtrEntry 16 }

    wfIsdnMsgConnectReq OBJECT-TYPE
        SYNTAX	Counter
        ACCESS	read-only
        STATUS	mandatory
        DESCRIPTION
                "Connect Request to the network"
        ::= { wfIsdnMsgCtrEntry 17 }

    wfIsdnMsgSetupReq OBJECT-TYPE
        SYNTAX	Counter
        ACCESS	read-only
        STATUS	mandatory
        DESCRIPTION
                "Setup Request to the network"
        ::= { wfIsdnMsgCtrEntry 18 }

    wfIsdnMsgMgmtReq OBJECT-TYPE
        SYNTAX	Counter
        ACCESS	read-only
        STATUS	mandatory
        DESCRIPTION
                "Management Request to the network"
        ::= { wfIsdnMsgCtrEntry 19 }

    wfIsdnMsgDiscReq OBJECT-TYPE
        SYNTAX	Counter
        ACCESS	read-only
        STATUS	mandatory
        DESCRIPTION
                "Disconnect Request to the network"
        ::= { wfIsdnMsgCtrEntry 20 }

    wfIsdnMsgActReq OBJECT-TYPE
        SYNTAX	Counter
        ACCESS	read-only
        STATUS	mandatory
        DESCRIPTION
                "Activate Request to the driver"
        ::= { wfIsdnMsgCtrEntry 21 }

    wfIsdnMsgDeactReq OBJECT-TYPE
        SYNTAX	Counter
        ACCESS	read-only
        STATUS	mandatory
        DESCRIPTION
                "Deactivate Request to the driver"
        ::= { wfIsdnMsgCtrEntry 22 }

    wfIsdnMsgAlertInd OBJECT-TYPE
        SYNTAX	Counter
        ACCESS	read-only
        STATUS	mandatory
        DESCRIPTION
                "Alert Indication from the network"
        ::= { wfIsdnMsgCtrEntry 23 }

    wfIsdnMsgInfoInd OBJECT-TYPE
        SYNTAX	Counter
        ACCESS	read-only
        STATUS	mandatory
        DESCRIPTION
                "Information Indication from the network"
        ::= { wfIsdnMsgCtrEntry 24 }

    wfIsdnHostActionTable OBJECT-TYPE
        SYNTAX	SEQUENCE OF WfIsdnHostActionEntry
        ACCESS	not-accessible
        STATUS	mandatory
        DESCRIPTION
                "This table is for debugging purposes only! It allows
                Host initiated call control actions."
        ::= { wfIsdnGroup 5 }

    wfIsdnHostActionEntry OBJECT-TYPE
        SYNTAX	WfIsdnHostActionEntry
        ACCESS	not-accessible
        STATUS	mandatory
        DESCRIPTION
                "An entry in the host action table"
        INDEX	{ wfIsdnHostActSlot }
        ::= { wfIsdnHostActionTable 1 }

    WfIsdnHostActionEntry ::= SEQUENCE {
    	    wfIsdnHostActSlot
    		INTEGER,
    	    wfIsdnHostActDslId
    		INTEGER,
    	    wfIsdnHostActCallID
    		INTEGER,
    	    wfIsdnHostActMsgType
    		INTEGER,
    	    wfIsdnHostActCalledPtyType
    		INTEGER,
    	    wfIsdnHostActCalledPtyPlan
    		INTEGER,
    	    wfIsdnHostActCalledPtyNum
    		OCTET STRING,
    	    wfIsdnHostActCallingPtyType
    		INTEGER,
    	    wfIsdnHostActCallingPtyPlan
    		INTEGER,
    	    wfIsdnHostActCallingPtyNum
    		OCTET STRING,
    	    wfIsdnHostActCallingPtyPres
    		INTEGER,
    	    wfIsdnHostActChanPrefBit
    		INTEGER,
    	    wfIsdnHostActChanSelection
    		INTEGER,
    	    wfIsdnHostActCauseCode
    		INTEGER,
    	    wfIsdnHostActTransferCap
    		INTEGER,
    	    wfIsdnHostActCldSadType
    		INTEGER,
    	    wfIsdnHostActCldSadNum
    		OCTET STRING,
    	    wfIsdnHostActClgSadType
    		INTEGER,
    	    wfIsdnHostActClgSadNum
    		OCTET STRING,
	    wfIsdnHostActCldSadPres
		INTEGER,
	    wfIsdnHostActClgSadPres
		INTEGER	
        }

    wfIsdnHostActSlot OBJECT-TYPE
        SYNTAX	INTEGER
        ACCESS	read-only
        STATUS	mandatory
        DESCRIPTION
                "the slot the interface is on"
        ::= { wfIsdnHostActionEntry 1 }

    wfIsdnHostActDslId OBJECT-TYPE
        SYNTAX	INTEGER
        ACCESS	read-write
        STATUS	mandatory
        DESCRIPTION
                "DSL id of the interface"
        ::= { wfIsdnHostActionEntry 2 }

    wfIsdnHostActCallID OBJECT-TYPE
        SYNTAX	INTEGER
        ACCESS	read-write
        STATUS	mandatory
        DESCRIPTION
                "Call ID"
        ::= { wfIsdnHostActionEntry 3 }

    wfIsdnHostActMsgType OBJECT-TYPE
        SYNTAX	INTEGER {
    		    info(15),
    		    setup(28),
    		    disc(50),
    		    activate(82),
    		    deactivate(83)
    		}
        ACCESS	read-write
        STATUS	mandatory
        DESCRIPTION
                "type of message to be sent to call control (or ME)"
        ::= { wfIsdnHostActionEntry 4 }

    wfIsdnHostActCalledPtyType OBJECT-TYPE
        SYNTAX	INTEGER {
    		    intl(1),
    		    nat(2),
    		    loc(4)
    		}
        ACCESS	read-write
        STATUS	mandatory
        DESCRIPTION
                "called party type"
        DEFVAL	{ nat }
        ::= { wfIsdnHostActionEntry 5 }

    wfIsdnHostActCalledPtyPlan OBJECT-TYPE
        SYNTAX	INTEGER {
    		    isdn(1),
    		    tele(2),
    		    pvt(9)
    		}
        ACCESS	read-write
        STATUS	mandatory
        DESCRIPTION
                "called party plan"
        DEFVAL	{ isdn }
        ::= { wfIsdnHostActionEntry 6 }

    wfIsdnHostActCalledPtyNum OBJECT-TYPE
        SYNTAX	OCTET STRING
        ACCESS	read-write
        STATUS	mandatory
        DESCRIPTION
                "called party number in ASCII digits"
        ::= { wfIsdnHostActionEntry 7 }

    wfIsdnHostActCallingPtyType OBJECT-TYPE
        SYNTAX	INTEGER {
    		    intl(1),
    		    nat(2),
    		    loc(4)
    		}
        ACCESS	read-write
        STATUS	mandatory
        DESCRIPTION
                "calling party type"
        DEFVAL	{ nat }
        ::= { wfIsdnHostActionEntry 8 }

    wfIsdnHostActCallingPtyPlan OBJECT-TYPE
        SYNTAX	INTEGER {
    		    isdn(1),
    		    tele(2),
    		    pvt(9)
    		}
        ACCESS	read-write
        STATUS	mandatory
        DESCRIPTION
                "calling party plan"
        DEFVAL	{ isdn }
        ::= { wfIsdnHostActionEntry 9 }

    wfIsdnHostActCallingPtyNum OBJECT-TYPE
        SYNTAX	OCTET STRING
        ACCESS	read-write
        STATUS	mandatory
        DESCRIPTION
                "calling party number in ASCII digits"
        ::= { wfIsdnHostActionEntry 10 }

    wfIsdnHostActCallingPtyPres OBJECT-TYPE
        SYNTAX	INTEGER {
    		    rest(1),
    		    unavl(2)
    		}
        ACCESS	read-write
        STATUS	mandatory
        DESCRIPTION
                "calling party presentation indicator"
        ::= { wfIsdnHostActionEntry 11 }

    wfIsdnHostActChanPrefBit OBJECT-TYPE
        SYNTAX	INTEGER
        ACCESS	read-write
        STATUS	mandatory
        DESCRIPTION
                "channel preferred/exclusive bit"
        ::= { wfIsdnHostActionEntry 12 }

    wfIsdnHostActChanSelection OBJECT-TYPE
        SYNTAX	INTEGER {
    		    channelb1(1),
    		    channelb2(2),
    		    channel(3)
    		}
        ACCESS	read-write
        STATUS	mandatory
        DESCRIPTION
                "channel selection"
        DEFVAL	{ channelb1 }
        ::= { wfIsdnHostActionEntry 13 }

    wfIsdnHostActCauseCode OBJECT-TYPE
        SYNTAX	INTEGER {
    		    normal(16),
    		    rejected(21),
    		    unspecified(31),
    		    barred(54)
    		}
        ACCESS	read-write
        STATUS	mandatory
        DESCRIPTION
                "cause code"
        DEFVAL	{ normal }
        ::= { wfIsdnHostActionEntry 14 }

    wfIsdnHostActTransferCap OBJECT-TYPE
        SYNTAX	INTEGER {
    		    unrestricted(8),
    		    restricted(9)
    		}
        ACCESS	read-write
        STATUS	mandatory
        DESCRIPTION
                "Transfer Capability required for Bearer Cap IE"
        DEFVAL	{ unrestricted }
        ::= { wfIsdnHostActionEntry 15 }

    wfIsdnHostActCldSadType OBJECT-TYPE
        SYNTAX	INTEGER {
    		    user(2)
    		}
        ACCESS	read-write
        STATUS	mandatory
        DESCRIPTION
                "Called Party Subaddress Type"
        ::= { wfIsdnHostActionEntry 16 }

    wfIsdnHostActCldSadNum OBJECT-TYPE
        SYNTAX	OCTET STRING
        ACCESS	read-write
        STATUS	mandatory
        DESCRIPTION
                "Called Party subaddress Max length 20 octets"
        ::= { wfIsdnHostActionEntry 17 }

    wfIsdnHostActClgSadType OBJECT-TYPE
        SYNTAX	INTEGER {
    		    user(2)
    		}
        ACCESS	read-write
        STATUS	mandatory
        DESCRIPTION
                "Calling party subaddress Type"
        ::= { wfIsdnHostActionEntry 18 }

    wfIsdnHostActClgSadNum OBJECT-TYPE
        SYNTAX	OCTET STRING
        ACCESS	read-write
        STATUS	mandatory
        DESCRIPTION
                "Called Party subaddress Max length 20 octets"
        ::= { wfIsdnHostActionEntry 19 }

    wfIsdnHostActCldSadPres OBJECT-TYPE
        SYNTAX	INTEGER {
    		     
    		     enable(1)
    		}
        ACCESS	read-write
        STATUS	mandatory
        DESCRIPTION
                "Called party subaddress Type"
	DEFVAL	{ enable }
        ::= { wfIsdnHostActionEntry 20 }

	
    wfIsdnHostActClgSadPres OBJECT-TYPE
        SYNTAX	INTEGER {    		    
    		     enable(1)
    		}
        ACCESS	read-write
        STATUS	mandatory
        DESCRIPTION
                "Calling party subaddress presentation indication"	
	DEFVAL	{ enable }
        ::= { wfIsdnHostActionEntry 21 }    
	
    wfIsdnSwitchCfgTable OBJECT-TYPE
        SYNTAX	SEQUENCE OF WfIsdnSwitchCfgEntry
        ACCESS	not-accessible
        STATUS	mandatory
        DESCRIPTION
                "This is the Switchtype Configuration for the
                ISDN signaling stack."
        ::= { wfIsdnGroup 6 }

    wfIsdnSwitchCfgEntry OBJECT-TYPE
        SYNTAX	WfIsdnSwitchCfgEntry
        ACCESS	not-accessible
        STATUS	mandatory
        DESCRIPTION
                "An entry in the ISDN Switch table"
        INDEX	{ wfIsdnSwitchCfgSlot }
        ::= { wfIsdnSwitchCfgTable 1 }

    WfIsdnSwitchCfgEntry ::= SEQUENCE {
    	    wfIsdnSwitchCfgDelete
    		INTEGER,
    	    wfIsdnSwitchCfgSlot
    		INTEGER,
    	    wfIsdnSwitchCfgType
    		INTEGER,
    	    wfIsdnSwitchTestMode
    		INTEGER,
    	    wfIsdnSwitchIncomingFilter
    		INTEGER,
    	    wfIsdnSwitchTraceFacility
    		INTEGER,
    	    wfIsdnSwitchScreenedCalls
    		Counter,
    	    wfIsdnSwitchSendingComplete
    		INTEGER,
    	    wfIsdnSwitchGlobalRateAdaption
    		INTEGER,
            wfIsdnSwitchX25D
                INTEGER,
            wfIsdnSwitchAllowedScreeningBits
                INTEGER,
            wfIsdnSwitchPreauthTodCheck
                INTEGER
        }

    wfIsdnSwitchCfgDelete OBJECT-TYPE
        SYNTAX	INTEGER {
    		    created(1),
    		    deleted(2)
    		}
        ACCESS	read-write
        STATUS	mandatory
        DESCRIPTION
                "Create / Delete Parameter"
        DEFVAL	{ created }
        ::= { wfIsdnSwitchCfgEntry 1 }

    wfIsdnSwitchCfgSlot OBJECT-TYPE
        SYNTAX	INTEGER(1..14)
        ACCESS	read-only
        STATUS	mandatory
        DESCRIPTION
                "Slot which has the ISDN interface"
        ::= { wfIsdnSwitchCfgEntry 2 }

    wfIsdnSwitchCfgType OBJECT-TYPE
        SYNTAX	INTEGER {
    		    brinet3(1),
    		    briswissnet3(2),
    		    bri5ess(4),
    		    bridms100(7),
    		    brivn3(10),
    		    brikdd(11),
    		    brintt(12),
    		    brits013(14),
    		    brini1(15),
    		    pri4ess(17),
    		    pri5ess(18),
    		    pridms100(20),
    		    prikdd(21),
    		    printt(22),
    		    prinet5(27),
    		    prits014(29)
    		}
        ACCESS	read-write
        STATUS	mandatory
        DESCRIPTION
                "The Type of switch from which the ISDN
                service is subscribed for this slot."
        ::= { wfIsdnSwitchCfgEntry 3 }

    wfIsdnSwitchTestMode OBJECT-TYPE
        SYNTAX	INTEGER
        ACCESS	read-write
        STATUS	mandatory
        DESCRIPTION
                "enable engineering test mode"
        ::= { wfIsdnSwitchCfgEntry 4 }

    wfIsdnSwitchIncomingFilter OBJECT-TYPE
        SYNTAX	INTEGER {
    		    on(1),
    		    off(2)
    		}
        ACCESS	read-write
        STATUS	mandatory
        DESCRIPTION
                "Filter Calling address in the Incoming call"
        DEFVAL	{ off }
        ::= { wfIsdnSwitchCfgEntry 5 }

    wfIsdnSwitchTraceFacility OBJECT-TYPE
        SYNTAX	INTEGER {
    		    enabled(1)
    		}
        ACCESS	read-write
        STATUS	mandatory
        DESCRIPTION
                "Enable/Disable ISDN protocol stack message tracing
                facility - when this is enabled, all messages exchanged
                between Layer 2 and Layer 3 ISDN entities will be
                captured to the event log as TRACE messages"
        ::= { wfIsdnSwitchCfgEntry 6 }

    wfIsdnSwitchScreenedCalls OBJECT-TYPE
        SYNTAX	Counter
        ACCESS	read-only
        STATUS	mandatory
        DESCRIPTION
                "Number of incoming calls ignored because of screening, ie.
                the Calling Party number was not in the list of approved
                numbers"
        ::= { wfIsdnSwitchCfgEntry 7 }

    wfIsdnSwitchSendingComplete OBJECT-TYPE
        SYNTAX	INTEGER {
    		    enabled(1),
    		    disabled(2)
    		}
        ACCESS	read-write
        STATUS	mandatory
        DESCRIPTION
                "The Sending Complete IE is required to be sent in the Setup
                message indicating en-bloc sending. Enable this attribute to include
                Sending Complete IE if the Switch providing ISDN service requires
                it."
        DEFVAL	{ disabled }
        ::= { wfIsdnSwitchCfgEntry 8 }

    wfIsdnSwitchGlobalRateAdaption OBJECT-TYPE
        SYNTAX	INTEGER {
    		    rate64(1),
    		    rate56(2)
    		}
        ACCESS	read-write
        STATUS	mandatory
        DESCRIPTION
                "Global Rate Adaption, If this value is configured request
                the configured Rate adpation when establishing connection."
        DEFVAL	{ rate64 }
        ::= { wfIsdnSwitchCfgEntry 9 }

    wfIsdnSwitchX25D OBJECT-TYPE
        SYNTAX  INTEGER {
                    enabled(1),
                    disabled(2)
                }
        ACCESS  read-write
        STATUS  mandatory
        DESCRIPTION
                "Enable this attribute to support the X25 over ISDN D
                 channel feature."
        DEFVAL  { disabled }
        ::= { wfIsdnSwitchCfgEntry 10 }

    wfIsdnSwitchAllowedScreeningBits OBJECT-TYPE
        SYNTAX  INTEGER(0..4) 
        ACCESS  read-write
        STATUS  mandatory
        DESCRIPTION
                "Set this attribute to the value of the screening bits
                 that is allowed in the incoming calling number IE. Only
                 a calling number with screening bits matching this
                 attribute will be recognised, all others will be ignored.
                 If this attribute is disabled, the first calling number
                 found will be used."
        DEFVAL  { 4 }
        ::= { wfIsdnSwitchCfgEntry 11 }

    wfIsdnSwitchPreauthTodCheck OBJECT-TYPE
        SYNTAX  INTEGER {
                    enabled(1),
                    disabled(2)
                }
        ACCESS  read-write
        STATUS  mandatory
        DESCRIPTION
                "Enable this attribute to attempt to identify whether
                 a caller is outside of a valid TOD window using the
                 calling number, before accepting the call."
        DEFVAL  { disabled }
        ::= { wfIsdnSwitchCfgEntry 12 }

    wfIsdnCallInfoTable OBJECT-TYPE
        SYNTAX	SEQUENCE OF WfIsdnCallInfoEntry
        ACCESS	not-accessible
        STATUS	mandatory
        DESCRIPTION
                "Call Information Table - contains data pertinent to a
                an active call, both incoming and outgoing, indexed by
                an internally generated call reference number."
        ::= { wfIsdnGroup 7 }

    wfIsdnCallInfoEntry OBJECT-TYPE
        SYNTAX	WfIsdnCallInfoEntry
        ACCESS	not-accessible
        STATUS	mandatory
        DESCRIPTION
                "An entry in the ISDN Call Info Table"
        INDEX	{ wfIsdnCallInfoSlot,
    		  wfIsdnCallInfoDslID,
    		  wfIsdnCallInfoCallID }
        ::= { wfIsdnCallInfoTable 1 }

    WfIsdnCallInfoEntry ::= SEQUENCE {
    	    wfIsdnCallInfoSlot
    		INTEGER,
    	    wfIsdnCallInfoDslID
    		INTEGER,
    	    wfIsdnCallInfoCallID
    		INTEGER,
    	    wfIsdnCallInfoBChannel
    		INTEGER,
    	    wfIsdnCallInfoCallState
    		INTEGER,
    	    wfIsdnCallInfoTransferCap
    		INTEGER,
    	    wfIsdnCallInfoCalledPtyNum
    		DisplayString,
    	    wfIsdnCallInfoCallingPtyNum
    		DisplayString,
    	    wfIsdnCallInfoDuration
    		INTEGER,
    	    wfIsdnCallInfoConnectTime
    		INTEGER,
    	    wfIsdnCallInfoRateAdaption
    		INTEGER,
    	    wfIsdnCallInfoCalledPtySub
    		DisplayString,
    	    wfIsdnCallInfoCallingPtySub
    		DisplayString,
            wfIsdnCallInfoChanType
                INTEGER,
            wfIsdnCallInfoAggrChanCnt
                INTEGER,
            wfIsdnCallInfoTimeslotMask
                INTEGER,
            wfIsdnCallInfoCct
                INTEGER
        }

    wfIsdnCallInfoSlot OBJECT-TYPE
        SYNTAX	INTEGER
        ACCESS	read-only
        STATUS	mandatory
        DESCRIPTION
                "The slot this call resides on"
        ::= { wfIsdnCallInfoEntry 1 }

    wfIsdnCallInfoDslID OBJECT-TYPE
        SYNTAX	INTEGER
        ACCESS	read-only
        STATUS	mandatory
        DESCRIPTION
                "Digital Subscriber Loop (DSL) this call resides on"
        ::= { wfIsdnCallInfoEntry 2 }

    wfIsdnCallInfoCallID OBJECT-TYPE
        SYNTAX	INTEGER
        ACCESS	read-only
        STATUS	mandatory
        DESCRIPTION
                "Call ID instance identifier - numbers in the
                range 0x0000 - 0x7FFF are assigned to
                incoming calls, 0x8000 - 0xFFFF
                are assigned to outgoing calls - this is used
                as a handle to manage an active call"
        ::= { wfIsdnCallInfoEntry 3 }

    wfIsdnCallInfoBChannel OBJECT-TYPE
        SYNTAX	INTEGER
        ACCESS	read-only
        STATUS	mandatory
        DESCRIPTION
                "B Channel this call resides on"
        ::= { wfIsdnCallInfoEntry 4 }

    wfIsdnCallInfoCallState OBJECT-TYPE
        SYNTAX	INTEGER
        ACCESS	read-only
        STATUS	mandatory
        DESCRIPTION
                "Line Manager Call State"
        ::= { wfIsdnCallInfoEntry 5 }

    wfIsdnCallInfoTransferCap OBJECT-TYPE
        SYNTAX	INTEGER {
    		    udi(8),
    		    rdi(9)
    		}
        ACCESS	read-only
        STATUS	mandatory
        DESCRIPTION
                "Transfer Capability value from the Bearer
                Capability Information Element"
        ::= { wfIsdnCallInfoEntry 6 }

    wfIsdnCallInfoCalledPtyNum OBJECT-TYPE
        SYNTAX	DisplayString
        ACCESS	read-only
        STATUS	mandatory
        DESCRIPTION
                "Called Party Number"
        ::= { wfIsdnCallInfoEntry 7 }

    wfIsdnCallInfoCallingPtyNum OBJECT-TYPE
        SYNTAX	DisplayString
        ACCESS	read-only
        STATUS	mandatory
        DESCRIPTION
                "Calling Party Number"
        ::= { wfIsdnCallInfoEntry 8 }

    wfIsdnCallInfoDuration OBJECT-TYPE
        SYNTAX	INTEGER
        ACCESS	read-only
        STATUS	mandatory
        DESCRIPTION
                "Duration of the call in minutes"
        ::= { wfIsdnCallInfoEntry 9 }

    wfIsdnCallInfoConnectTime OBJECT-TYPE
        SYNTAX	INTEGER
        ACCESS	read-only
        STATUS	mandatory
        DESCRIPTION
                "Start time of the call (HHMMSS)"
        ::= { wfIsdnCallInfoEntry 10 }

    wfIsdnCallInfoRateAdaption OBJECT-TYPE
        SYNTAX	INTEGER
        ACCESS	read-only
        STATUS	mandatory
        DESCRIPTION
                "Rate adaption for this call in KBPS"
        ::= { wfIsdnCallInfoEntry 11 }

    wfIsdnCallInfoCalledPtySub OBJECT-TYPE
        SYNTAX	DisplayString
        ACCESS	read-only
        STATUS	mandatory
        DESCRIPTION
                "Called Party Subaddress"
        ::= { wfIsdnCallInfoEntry 12 }

    wfIsdnCallInfoCallingPtySub OBJECT-TYPE
        SYNTAX	DisplayString
        ACCESS	read-only
        STATUS	mandatory
        DESCRIPTION
                "Calling Party Subaddress"
        ::= { wfIsdnCallInfoEntry 13 }

    wfIsdnCallInfoChanType OBJECT-TYPE
        SYNTAX  INTEGER {
                    bchannel(1),
                    multirate(2)
                }
        ACCESS  read-only
        STATUS  mandatory
        DESCRIPTION
                "ISDN call channel type: B Channel or Multirate"
        DEFVAL  { bchannel }
        ::= { wfIsdnCallInfoEntry 14 }

    wfIsdnCallInfoAggrChanCnt OBJECT-TYPE
        SYNTAX  INTEGER
        ACCESS  read-only
        STATUS  mandatory
        DESCRIPTION
                "PRI Multirate call's aggreated channel count"
        ::= { wfIsdnCallInfoEntry 15 }

    wfIsdnCallInfoTimeslotMask OBJECT-TYPE
        SYNTAX  INTEGER
        ACCESS  read-only
        STATUS  mandatory
        DESCRIPTION
                "Timeslots used by a PRI Multirate call"
        ::= { wfIsdnCallInfoEntry 16 }

    wfIsdnCallInfoCct OBJECT-TYPE
        SYNTAX	INTEGER
        ACCESS	read-write
        STATUS	mandatory
        DESCRIPTION
                "Circuit using this call"
        ::= { wfIsdnCallInfoEntry 17 }


    wfIsdnBriInterfaceTable OBJECT-TYPE
        SYNTAX	SEQUENCE OF WfIsdnBriInterfaceEntry
        ACCESS	not-accessible
        STATUS	mandatory
        DESCRIPTION
                "
                   ISDN BRI D Channel MIB Record
                "
        ::= { wfIsdnGroup 9 }

    wfIsdnBriInterfaceEntry OBJECT-TYPE
        SYNTAX	WfIsdnBriInterfaceEntry
        ACCESS	not-accessible
        STATUS	mandatory
        DESCRIPTION
                "An entry in the ISDN table"
        INDEX	{ wfIsdnBriSlot,
    		  wfIsdnBriConnector }
        ::= { wfIsdnBriInterfaceTable 1 }

    WfIsdnBriInterfaceEntry ::= SEQUENCE {
    	    wfIsdnBriDelete
    		INTEGER,
    	    wfIsdnBriDisable
    		INTEGER,
    	    wfIsdnBriState
    		INTEGER,
    	    wfIsdnBriSlot
    		INTEGER,
    	    wfIsdnBriConnector
    		INTEGER,
    	    wfIsdnBriCct
    		INTEGER,
    	    wfIsdnBriDslId
    		INTEGER,
    	    wfIsdnBriLineNumber
    		INTEGER,
    	    wfIsdnBriModule
    		INTEGER,
    	    wfIsdnBriActualConnector
    		INTEGER,
    	    wfIsdnBriTeState
    		INTEGER,
    	    wfIsdnBriMtu
    		INTEGER,
    	    wfIsdnBriBChanLoop
    		INTEGER,
    	    wfIsdnBriTimer3Tmo
    		INTEGER,
    	    wfIsdnBriTimer4Tmo
    		INTEGER,
    	    wfIsdnBriRxOctets
    		Counter,
    	    wfIsdnBriRxFrames
    		Counter,
    	    wfIsdnBriTxOctets
    		Counter,
    	    wfIsdnBriTxFrames
    		Counter,
    	    wfIsdnBriRxErrors
    		Counter,
    	    wfIsdnBriTxErrors
    		Counter,
    	    wfIsdnBriRxLackRescs
    		Counter,
    	    wfIsdnBriTxLackRescs
    		Counter,
    	    wfIsdnBriTxUnderFlows
    		Counter,
    	    wfIsdnBriTxDChanCollisions
    		Counter,
    	    wfIsdnBriRxOverFlows
    		Counter,
    	    wfIsdnBriRxTooLongFrames
    		Counter,
    	    wfIsdnBriRxBadCrcs
    		Counter,
    	    wfIsdnBriRxAborts
    		Counter,
    	    wfIsdnBriRxReplenMisses
    		Counter,
    	    wfIsdnBriTimer3Timeouts
    		Counter,
    	    wfIsdnBriTimer4Timeouts
    		Counter,
    	    wfIsdnBriLineType
    		INTEGER,
    	    wfIsdnBriMode
    		INTEGER,
    	    wfIsdnBriInterfaceType
    		INTEGER,
    	    wfIsdnBriNtState
    		INTEGER,
    	    wfIsdnBriTimerM4Tmo
    		INTEGER,
    	    wfIsdnBriTimerM6Tmo
    		INTEGER,
            wfIsdnBriX25D
                INTEGER,
            wfIsdnBriX25DTeiType
                INTEGER,
            wfIsdnBriX25DTeiValue
                INTEGER
        }

    wfIsdnBriDelete OBJECT-TYPE
        SYNTAX	INTEGER {
    		    created(1),
    		    deleted(2)
    		}
        ACCESS	read-write
        STATUS	mandatory
        DESCRIPTION
                "Create/Delete parameter"
        DEFVAL	{ created }
        ::= { wfIsdnBriInterfaceEntry 1 }

    wfIsdnBriDisable OBJECT-TYPE
        SYNTAX	INTEGER {
    		    enabled(1),
    		    disabled(2)
    		}
        ACCESS	read-write
        STATUS	mandatory
        DESCRIPTION
                "Enable/Disable parameter"
        DEFVAL	{ enabled }
        ::= { wfIsdnBriInterfaceEntry 2 }

    wfIsdnBriState OBJECT-TYPE
        SYNTAX	INTEGER {
    		    up(1),
    		    down(2),
    		    init(3),
    		    ubcwaiting(10),
    		    notpresent(20)
    		}
        ACCESS	read-only
        STATUS	mandatory
        DESCRIPTION
                "Line Driver state variable, Not Present,
                Init, Down, Up"
        DEFVAL	{ notpresent }
        ::= { wfIsdnBriInterfaceEntry 3 }

    wfIsdnBriSlot OBJECT-TYPE
        SYNTAX	INTEGER
        ACCESS	read-only
        STATUS	mandatory
        DESCRIPTION
                "Instance ID Slot, filled in by driver."
        ::= { wfIsdnBriInterfaceEntry 4 }

    wfIsdnBriConnector OBJECT-TYPE
        SYNTAX	INTEGER(1..44)
        ACCESS	read-only
        STATUS	mandatory
        DESCRIPTION
                "Instance ID Connector, filled in by driver. For the ASN
                this attribute is an encoded value and is equal to
                'module'*10 + 'connector'. Where 'module' is defined in
                attribute 9 and 'connector' is defined in attribute 10
                of this table. For non-ASN platforms this attribute is
                the physical connector number on the slot."
        ::= { wfIsdnBriInterfaceEntry 5 }

    wfIsdnBriCct OBJECT-TYPE
        SYNTAX	INTEGER(1..1023)
        ACCESS	read-write
        STATUS	mandatory
        DESCRIPTION
                "CCT number for this interface instance"
        ::= { wfIsdnBriInterfaceEntry 6 }

    wfIsdnBriDslId OBJECT-TYPE
        SYNTAX	INTEGER
        ACCESS	read-only
        STATUS	mandatory
        DESCRIPTION
                "The ID of this DSL interface. This stands for 'Digital Subscriber
                Loop' which is the physical link from the TE (us) to the NT
                (switch)."
        ::= { wfIsdnBriInterfaceEntry 7 }

    wfIsdnBriLineNumber OBJECT-TYPE
        SYNTAX	INTEGER
        ACCESS	read-write
        STATUS	mandatory
        DESCRIPTION
                "Line number for this line instance. This is assigned at
                configuration time and uniquely identifies this line"
        ::= { wfIsdnBriInterfaceEntry 8 }

    wfIsdnBriModule OBJECT-TYPE
        SYNTAX	INTEGER {
    		    one(1),
    		    two(2),
    		    three(3),
    		    four(4)
    		}
        ACCESS	read-only
        STATUS	mandatory
        DESCRIPTION
                "Module number for ASN platform, filled in by driver. For non-ASN
                platforms this attribute will not be used."
        ::= { wfIsdnBriInterfaceEntry 9 }

    wfIsdnBriActualConnector OBJECT-TYPE
        SYNTAX	INTEGER {
    		    one(1),
    		    two(2),
    		    three(3),
    		    four(4)
    		}
        ACCESS	read-only
        STATUS	mandatory
        DESCRIPTION
                "Actual connector number for ASN platform, filled in
                by driver. For non-ASN platforms, this attribute will
                not be used."
        ::= { wfIsdnBriInterfaceEntry 10 }

    wfIsdnBriTeState OBJECT-TYPE
        SYNTAX	INTEGER {
    		    inactive(1),
    		    sensing(2),
    		    deactivated(3),
    		    awaitsignal(4),
    		    identifyinput(5),
    		    synchronized(6),
    		    activated(7),
    		    lostframing(8)
    		}
        ACCESS	read-only
        STATUS	mandatory
        DESCRIPTION
                "State of the S/T interface from the routers point of view. These states
                correspond to those described in the CCITT I.430 recommendation and
                with those described with relation to the ISAC-S."
        DEFVAL	{ inactive }
        ::= { wfIsdnBriInterfaceEntry 11 }

    wfIsdnBriMtu OBJECT-TYPE
        SYNTAX	INTEGER(3..1024)
        ACCESS	read-write
        STATUS	mandatory
        DESCRIPTION
                "Contains the largest frame size that can be received by this
                interface. Anything larger than the MTU will be discarded."
        DEFVAL	{ 400 }
        ::= { wfIsdnBriInterfaceEntry 12 }

    wfIsdnBriBChanLoop OBJECT-TYPE
        SYNTAX	INTEGER {
    		    enabled(1),
    		    disabled(2)
    		}
        ACCESS	read-write
        STATUS	mandatory
        DESCRIPTION
                "This allows us to put the B Channels into loopback at the physical
                interface. This is usually used for Layer 1 conformance testing."
        DEFVAL	{ disabled }
        ::= { wfIsdnBriInterfaceEntry 13 }

    wfIsdnBriTimer3Tmo OBJECT-TYPE
        SYNTAX	INTEGER(1..30)
        ACCESS	read-write
        STATUS	mandatory
        DESCRIPTION
                "Indicates the amount of time in seconds for our T3 timer.
                The T3 timer is initiated by the host (i.e. the router). The T3 timer is
                started whenever the S/T interface is in a deactivated state and the host
                (i.e. the Router) wishes to activate the interface. As an example, for
                our application, the Router would activate the interface when there was
                data to be transmitted out that interface. At the point when we try
                activating the interface, the T3 timer is started. During the duration
                of the T3 timer, the router in trying to activate the interface will
                transmit INFO 1's out the S/T interface until either a signal is detected
                (from the network) or the T3 timer expires."
        DEFVAL	{ 10 }
        ::= { wfIsdnBriInterfaceEntry 14 }

    wfIsdnBriTimer4Tmo OBJECT-TYPE
        SYNTAX	INTEGER(500..1000)
        ACCESS	read-write
        STATUS	mandatory
        DESCRIPTION
                "Indicates the amount of time in milliseconds for our T4 timer.
                The T4 timer is a debounce timer which is used to shield the
                upper layers from short glitches at the S/T interface. Spurious
                problems of short duration will not be reported to the upper
                layers until the T4 timer expires. The T4 timer is started when
                leaving state F7 or F8 upon the reception of INFO 0. The corresponding
                Deactivation Indication will be delivered to layer 2 only if layer 1
                does not enter an active state before expiration of this timer. (Note
                that a value of 0 indicates the timer is disabled)."
        DEFVAL	{ 750 }
        ::= { wfIsdnBriInterfaceEntry 15 }

    wfIsdnBriRxOctets OBJECT-TYPE
        SYNTAX	Counter
        ACCESS	read-only
        STATUS	mandatory
        DESCRIPTION
                "Number of octets received without error"
        ::= { wfIsdnBriInterfaceEntry 16 }

    wfIsdnBriRxFrames OBJECT-TYPE
        SYNTAX	Counter
        ACCESS	read-only
        STATUS	mandatory
        DESCRIPTION
                "Number of frames received without error"
        ::= { wfIsdnBriInterfaceEntry 17 }

    wfIsdnBriTxOctets OBJECT-TYPE
        SYNTAX	Counter
        ACCESS	read-only
        STATUS	mandatory
        DESCRIPTION
                "Number of octets transmitted without error"
        ::= { wfIsdnBriInterfaceEntry 18 }

    wfIsdnBriTxFrames OBJECT-TYPE
        SYNTAX	Counter
        ACCESS	read-only
        STATUS	mandatory
        DESCRIPTION
                "Number of frames transmitted without error"
        ::= { wfIsdnBriInterfaceEntry 19 }

    wfIsdnBriRxErrors OBJECT-TYPE
        SYNTAX	Counter
        ACCESS	read-only
        STATUS	mandatory
        DESCRIPTION
                "Total number of receive errors"
        ::= { wfIsdnBriInterfaceEntry 20 }

    wfIsdnBriTxErrors OBJECT-TYPE
        SYNTAX	Counter
        ACCESS	read-only
        STATUS	mandatory
        DESCRIPTION
                "Total number of transmission errors"
        ::= { wfIsdnBriInterfaceEntry 21 }

    wfIsdnBriRxLackRescs OBJECT-TYPE
        SYNTAX	Counter
        ACCESS	read-only
        STATUS	mandatory
        DESCRIPTION
                "Number of times a receive packet was discarded because
                there was no receive descriptor available."
        ::= { wfIsdnBriInterfaceEntry 22 }

    wfIsdnBriTxLackRescs OBJECT-TYPE
        SYNTAX	Counter
        ACCESS	read-only
        STATUS	mandatory
        DESCRIPTION
                "Number of frames clipped in driver's transmit routine due to
                transmit congestion."
        ::= { wfIsdnBriInterfaceEntry 23 }

    wfIsdnBriTxUnderFlows OBJECT-TYPE
        SYNTAX	Counter
        ACCESS	read-only
        STATUS	mandatory
        DESCRIPTION
                "Number of transmission underflows, device FIFO went empty before
                driver could replenish with more data"
        ::= { wfIsdnBriInterfaceEntry 24 }

    wfIsdnBriTxDChanCollisions OBJECT-TYPE
        SYNTAX	Counter
        ACCESS	read-only
        STATUS	mandatory
        DESCRIPTION
                "Number of times a collison occurred on the S-Bus transmitting
                a frame greater than 32 bytes, so frame had to be retransmitted"
        ::= { wfIsdnBriInterfaceEntry 25 }

    wfIsdnBriRxOverFlows OBJECT-TYPE
        SYNTAX	Counter
        ACCESS	read-only
        STATUS	mandatory
        DESCRIPTION
                "Number of receive overflows, device FIFO overflowed before the
                driver was able to read/empty the FIFO."
        ::= { wfIsdnBriInterfaceEntry 26 }

    wfIsdnBriRxTooLongFrames OBJECT-TYPE
        SYNTAX	Counter
        ACCESS	read-only
        STATUS	mandatory
        DESCRIPTION
                "Number of frames received which were larger than the defined MTU"
        ::= { wfIsdnBriInterfaceEntry 27 }

    wfIsdnBriRxBadCrcs OBJECT-TYPE
        SYNTAX	Counter
        ACCESS	read-only
        STATUS	mandatory
        DESCRIPTION
                "Number of bad receive frames caused by FCS errors"
        ::= { wfIsdnBriInterfaceEntry 28 }

    wfIsdnBriRxAborts OBJECT-TYPE
        SYNTAX	Counter
        ACCESS	read-only
        STATUS	mandatory
        DESCRIPTION
                "Number of aborted frames due to being non octet aligned (i.e seven
                one's in a row received)"
        ::= { wfIsdnBriInterfaceEntry 29 }

    wfIsdnBriRxReplenMisses OBJECT-TYPE
        SYNTAX	Counter
        ACCESS	read-only
        STATUS	mandatory
        DESCRIPTION
                "Number of packet buffer misses while attempting to replenish driver
                receive descriptor ring."
        ::= { wfIsdnBriInterfaceEntry 30 }

    wfIsdnBriTimer3Timeouts OBJECT-TYPE
        SYNTAX	Counter
        ACCESS	read-only
        STATUS	mandatory
        DESCRIPTION
                "Number of Timer 3 timeout's detected. This indicates the number of
                times the Router tried to activate the S/T interface without success."
        ::= { wfIsdnBriInterfaceEntry 31 }

    wfIsdnBriTimer4Timeouts OBJECT-TYPE
        SYNTAX	Counter
        ACCESS	read-only
        STATUS	mandatory
        DESCRIPTION
                "Number of Timer 4 timeout's detected. The T4 timer is started when
                leaving state F7 or F8 upon the reception of INFO 0. If layer 1 does not
                enter an active state before expiration of this timer, then a Deactivation
                Indication will be sent to layer 2."
        ::= { wfIsdnBriInterfaceEntry 32 }

    wfIsdnBriLineType OBJECT-TYPE
        SYNTAX	INTEGER {
    		    ptp(1),
    		    mtp(2)
    		}
        ACCESS	read-write
        STATUS	mandatory
        DESCRIPTION
                "BRI line type can be either Multipoint (passive bus configuration with
                more than one device connected) or Point-to-Point with a single device
                attached."
        DEFVAL	{ ptp }
        ::= { wfIsdnBriInterfaceEntry 33 }

    wfIsdnBriMode OBJECT-TYPE
        SYNTAX	INTEGER {
    		    dialup(1),
    		    leased(2),
    		    floatb(3)
    		}
        ACCESS	read-write
        STATUS	mandatory
        DESCRIPTION
                "This attribute controls the operation of the Basic Rate Interface.
                DIALUP is the traditional mode of operation in which call setup
                signalling is done in concert with the ISDN switch.  LEASED is a
                special case of ISDN in which no signalling will be done with
                the switch and instead the switch is configured with nailed up
                connections to specific remote ISDN termination points."
        DEFVAL	{ dialup }
        ::= { wfIsdnBriInterfaceEntry 34 }

    wfIsdnBriInterfaceType OBJECT-TYPE
        SYNTAX	INTEGER {
    		    isdns(1),
    		    isdnu(2)
    		}
        ACCESS	read-only
        STATUS	mandatory
        DESCRIPTION
                "Type of ISDN interface card being used. 
                It can either be 'U' or 'S/T'."
        DEFVAL	{ isdns }
        ::= { wfIsdnBriInterfaceEntry 35 }

    wfIsdnBriNtState OBJECT-TYPE
        SYNTAX	INTEGER {
                    fullreset(1),
                    alerting(2),
                    receivereset(3),
                    synchronized1(4),
                    synchronized2(5),
                    deactivated(6),
                    activated(7),
                    test(8),
                    error(9),
                    pendreceivereset(10)
    		}
        ACCESS	read-only
        STATUS	mandatory
        DESCRIPTION
                "State of the U interface from the routers point of view. These states
                correspond to those described in the ANSI T1.601 recommendation and
                with those described in relation to the IEC-Q."
        DEFVAL	{ deactivated }
        ::= { wfIsdnBriInterfaceEntry 36 }

    wfIsdnBriTimerM4Tmo OBJECT-TYPE
        SYNTAX	INTEGER(1..30)
        ACCESS	read-write
        STATUS	mandatory
        DESCRIPTION
                "Indicates the amount of time in seconds for our M4 timer.
                The M4 timer is initiated by the host (i.e. the router). The M4 timer is
                started whenever the host receives a wakeup signal from the U interface.
                During the duration of the M4 timer, the router in trying to activate the
                interface will respond with a TN signal followed with SN1 (optional) signal.
                The router will then receive SL1 from the U interface followed with SL2.
                Upon reception of SL2 signal, the router will respond with SN2.  At this
                point the timer is stopped if it has not expired yet."
        DEFVAL	{ 15 }
        ::= { wfIsdnBriInterfaceEntry 37 }

    wfIsdnBriTimerM6Tmo OBJECT-TYPE
        SYNTAX	INTEGER(1..100)
        ACCESS	read-write
        STATUS	mandatory
        DESCRIPTION
                "Indicates the amount of time in milliseconds for our M6 timer.
                The M6 timer is initiated by the host (i.e. the router). The host has
                to complete the start-up sequence for the duration of the M6 timer.  If
                it fails to do so, it will enter the receivereset state and remain in
                that state until it receives a wakeup signal from the U interface."
        DEFVAL	{ 40 }
        ::= { wfIsdnBriInterfaceEntry 38 }

    wfIsdnBriX25D OBJECT-TYPE
        SYNTAX  INTEGER {
                    enabled(1),
                    disabled(2)
                }
        ACCESS  read-write
        STATUS  mandatory
        DESCRIPTION
                "enable/disable the X25 over ISDN D channel feature on the interface."
        DEFVAL  { disabled }
        ::= { wfIsdnBriInterfaceEntry 39 }

    wfIsdnBriX25DTeiType OBJECT-TYPE
        SYNTAX  INTEGER {
                    auto(1),
                    fixed(2)
                }
        ACCESS  read-write
        STATUS  mandatory
        DESCRIPTION
                "TEI type used for the X25 over ISDN D channel feature."
        DEFVAL  { fixed }
        ::= { wfIsdnBriInterfaceEntry 40 }

    wfIsdnBriX25DTeiValue OBJECT-TYPE
        SYNTAX  INTEGER(0..127)
        ACCESS  read-write
        STATUS  mandatory
        DESCRIPTION
                "TEI value used for the X25 over ISDN D channel feature.
                 0 to 63 are for fixed TEI type and 127 for auto TEI type"
        DEFVAL  { 1 }
        ::= { wfIsdnBriInterfaceEntry 41 }


    wfIsdnBChanInterfaceTable OBJECT-TYPE
        SYNTAX	SEQUENCE OF WfIsdnBChanInterfaceEntry
        ACCESS	not-accessible
        STATUS	mandatory
        DESCRIPTION
                "
                   ISDN Logical B channel MIB Record
                "
        ::= { wfIsdnGroup 10 }

    wfIsdnBChanInterfaceEntry OBJECT-TYPE
        SYNTAX	WfIsdnBChanInterfaceEntry
        ACCESS	not-accessible
        STATUS	mandatory
        DESCRIPTION
                "An entry in the ISDN table"
        INDEX	{ wfIsdnBChanLineNumber,
    		  wfIsdnBChanIndex }
        ::= { wfIsdnBChanInterfaceTable 1 }

    WfIsdnBChanInterfaceEntry ::= SEQUENCE {
    	    wfIsdnBChanDelete
    		INTEGER,
    	    wfIsdnBChanLineNumber
    		INTEGER,
    	    wfIsdnBChanIndex
    		INTEGER,
    	    wfIsdnBChanDisable
    		INTEGER,
    	    wfIsdnBChanState
    		INTEGER,
    	    wfIsdnBChanCct
    		INTEGER,
    	    wfIsdnBChanWanProtocol
    		INTEGER,
    	    wfIsdnBChanBackupPool
    		INTEGER,
    	    wfIsdnBChanDemandPool
    		INTEGER,
    	    wfIsdnBChanDirectoryNum
    		DisplayString,
    	    wfIsdnBChanSpid
    		DisplayString,
    	    wfIsdnBChanActiveCct
    		INTEGER,
    	    wfIsdnBChanPriority
    		INTEGER,
    	    wfIsdnBchanMultilineMode
    		INTEGER
        }

    wfIsdnBChanDelete OBJECT-TYPE
        SYNTAX	INTEGER {
    		    created(1),
    		    deleted(2)
    		}
        ACCESS	read-write
        STATUS	mandatory
        DESCRIPTION
                "Create/Delete parameter"
        DEFVAL	{ created }
        ::= { wfIsdnBChanInterfaceEntry 1 }

    wfIsdnBChanLineNumber OBJECT-TYPE
        SYNTAX	INTEGER
        ACCESS	read-only
        STATUS	mandatory
        DESCRIPTION
                "line number for this line instance"
        ::= { wfIsdnBChanInterfaceEntry 2 }

    wfIsdnBChanIndex OBJECT-TYPE
        SYNTAX	INTEGER(1..32)
        ACCESS	read-only
        STATUS	mandatory
        DESCRIPTION
                "a unique one up type number to create a list"
        ::= { wfIsdnBChanInterfaceEntry 3 }

    wfIsdnBChanDisable OBJECT-TYPE
        SYNTAX	INTEGER {
    		    enabled(1),
    		    disabled(2)
    		}
        ACCESS	read-write
        STATUS	mandatory
        DESCRIPTION
                "Enable/Disable parameter"
        DEFVAL	{ enabled }
        ::= { wfIsdnBChanInterfaceEntry 4 }

    wfIsdnBChanState OBJECT-TYPE
        SYNTAX	INTEGER {
    		    up(1),
    		    down(2),
    		    init(3),
    		    notpresent(4)
    		}
        ACCESS	read-only
        STATUS	mandatory
        DESCRIPTION
                "Line Driver state variable, Not Present,
                Init, Down, Up"
        DEFVAL	{ notpresent }
        ::= { wfIsdnBChanInterfaceEntry 5 }

    wfIsdnBChanCct OBJECT-TYPE
        SYNTAX	INTEGER(1..1023)
        ACCESS	read-write
        STATUS	mandatory
        DESCRIPTION
                "CCT number for this interface instance"
        ::= { wfIsdnBChanInterfaceEntry 6 }

    wfIsdnBChanWanProtocol OBJECT-TYPE
        SYNTAX	INTEGER {
    		    ppp(1),
    		    framerelay(2),
    		    x25(3)
    		}
        ACCESS	read-write
        STATUS	mandatory
        DESCRIPTION
                "WAN protocol selection is provided via this parameter. The
                supported protocols can be selected per interface."
        DEFVAL	{ ppp }
        ::= { wfIsdnBChanInterfaceEntry 7 }

    wfIsdnBChanBackupPool OBJECT-TYPE
        SYNTAX	INTEGER(1..255)
        ACCESS	read-write
        STATUS	mandatory
        DESCRIPTION
                "Backup pool id containing this line driver"
        ::= { wfIsdnBChanInterfaceEntry 8 }

    wfIsdnBChanDemandPool OBJECT-TYPE
        SYNTAX	INTEGER(1..255)
        ACCESS	read-write
        STATUS	mandatory
        DESCRIPTION
                "Dial on demand  pool id containing this line driver"
        ::= { wfIsdnBChanInterfaceEntry 9 }

    wfIsdnBChanDirectoryNum OBJECT-TYPE
        SYNTAX	DisplayString
        ACCESS	read-write
        STATUS	mandatory
        DESCRIPTION
                "Directory Number associated with the interface"
        ::= { wfIsdnBChanInterfaceEntry 10 }

    wfIsdnBChanSpid OBJECT-TYPE
        SYNTAX	DisplayString
        ACCESS	read-write
        STATUS	mandatory
        DESCRIPTION
                "Service Profile IDentifier - assigned by the Central Office on ordering
                ISDN service from a switch conforming to National ISDN."
        ::= { wfIsdnBChanInterfaceEntry 11 }

    wfIsdnBChanActiveCct OBJECT-TYPE
        SYNTAX	INTEGER(1..1023)
        ACCESS	read-only
        STATUS	mandatory
        DESCRIPTION
                "CCT number for this interface instance"
        ::= { wfIsdnBChanInterfaceEntry 12 }

    wfIsdnBChanPriority OBJECT-TYPE
        SYNTAX	INTEGER(1..50)
        ACCESS	read-write
        STATUS	mandatory
        DESCRIPTION
                "Priority associated with this ISDN B Channel"
        DEFVAL	{ 1 }
        ::= { wfIsdnBChanInterfaceEntry 13 }

    wfIsdnBchanMultilineMode OBJECT-TYPE
        SYNTAX	INTEGER {
    		    standard(1),
    		    master(2),
    		    slave(3),
    		    secondary(4)
    		}
        ACCESS	read-write
        STATUS	mandatory
        DESCRIPTION
                "This indicates the roll the B channel plays in
                a Bandwidth on Demand-Multiline Circuit. If this
                is not BOD, the mode is standard."
        DEFVAL	{ standard }
        ::= { wfIsdnBChanInterfaceEntry 14 }

    wfIsdnPoolTable OBJECT-TYPE
        SYNTAX	SEQUENCE OF WfIsdnPoolEntry
        ACCESS	not-accessible
        STATUS	mandatory
        DESCRIPTION
                "
                   ISDN Pool MIB Record
                "
        ::= { wfIsdnGroup 11 }

    wfIsdnPoolEntry OBJECT-TYPE
        SYNTAX	WfIsdnPoolEntry
        ACCESS	not-accessible
        STATUS	mandatory
        DESCRIPTION
                "An entry in the Pool table"
        INDEX	{ wfIsdnPoolType,
    		  wfIsdnPoolLineNumber,
    		  wfIsdnPoolId }
        ::= { wfIsdnPoolTable 1 }

    WfIsdnPoolEntry ::= SEQUENCE {
    	    wfIsdnPoolDelete
    		INTEGER,
    	    wfIsdnPoolType
    		INTEGER,
    	    wfIsdnPoolLineNumber
    		INTEGER,
    	    wfIsdnPoolId
    		INTEGER,
    	    wfIsdnPoolChannelCnt
    		INTEGER,
    	    wfIsdnPoolPriority
    		INTEGER,
    	    wfIsdnPoolChannelInUse
    		INTEGER
        }

    wfIsdnPoolDelete OBJECT-TYPE
        SYNTAX	INTEGER {
    		    created(1),
    		    deleted(2)
    		}
        ACCESS	read-write
        STATUS	mandatory
        DESCRIPTION
                "Create/Delete parameter"
        DEFVAL	{ created }
        ::= { wfIsdnPoolEntry 1 }

    wfIsdnPoolType OBJECT-TYPE
        SYNTAX	INTEGER {
    		    demand(1),
    		    backup(2),
    		    bandwidth(3)
    		}
        ACCESS	read-only
        STATUS	mandatory
        DESCRIPTION
                "Type of Pool . Backup or Demand"
        ::= { wfIsdnPoolEntry 2 }

    wfIsdnPoolLineNumber OBJECT-TYPE
        SYNTAX	INTEGER
        ACCESS	read-only
        STATUS	mandatory
        DESCRIPTION
                "D channel line number associated with this pool instance"
        ::= { wfIsdnPoolEntry 3 }

    wfIsdnPoolId OBJECT-TYPE
        SYNTAX	INTEGER
        ACCESS	read-only
        STATUS	mandatory
        DESCRIPTION
                "a unique pool ID"
        ::= { wfIsdnPoolEntry 4 }

    wfIsdnPoolChannelCnt OBJECT-TYPE
        SYNTAX	INTEGER(1..30)
        ACCESS	read-write
        STATUS	mandatory
        DESCRIPTION
                "Number of Channels allocated for this  Pool"
        DEFVAL	{ 1 }
        ::= { wfIsdnPoolEntry 5 }

    wfIsdnPoolPriority OBJECT-TYPE
        SYNTAX	INTEGER(1..50)
        ACCESS	read-write
        STATUS	mandatory
        DESCRIPTION
                "Priority of Lines in  Pool"
        DEFVAL	{ 1 }
        ::= { wfIsdnPoolEntry 6 }

    wfIsdnPoolChannelInUse OBJECT-TYPE
        SYNTAX	INTEGER
        ACCESS	read-only
        STATUS	mandatory
        DESCRIPTION
                "Number of Channels  in use from this  Pool."
        ::= { wfIsdnPoolEntry 7 }

    wfIsdnLocalPhoneNumTable OBJECT-TYPE
        SYNTAX	SEQUENCE OF WfIsdnLocalPhoneNumEntry
        ACCESS	not-accessible
        STATUS	mandatory
        DESCRIPTION
                "ISDN Local  phone number list "
        ::= { wfIsdnGroup 12 }

    wfIsdnLocalPhoneNumEntry OBJECT-TYPE
        SYNTAX	WfIsdnLocalPhoneNumEntry
        ACCESS	not-accessible
        STATUS	mandatory
        DESCRIPTION
                "An entry in  table"
        INDEX	{ wfIsdnLocalPhoneNumLineNum,
    		  wfIsdnLocalPhoneNumIndex }
        ::= { wfIsdnLocalPhoneNumTable 1 }

    WfIsdnLocalPhoneNumEntry ::= SEQUENCE {
    	    wfIsdnLocalPhoneNumDelete
    		INTEGER,
    	    wfIsdnLocalPhoneNumLineNum
    		INTEGER,
    	    wfIsdnLocalPhoneNumIndex
    		INTEGER,
    	    wfIsdnLocalDirectoryNum
    		DisplayString,
    	    wfIsdnLocalSubAddr
    		DisplayString,
    	    wfIsdnLocalSpid
    		DisplayString,
    	    wfIsdnLocalAssignedChannel
    		INTEGER,
    	    wfIsdnLocalSpidStatus
    		INTEGER,
            wfIsdnLocalDirectoryNumType
    		INTEGER,
            wfIsdnLocalDirectoryNumPlan
    		INTEGER,
	    wfIsdnSpidRetries
		INTEGER,
	    wfIsdnSpidRetryAttempts
		INTEGER,
	    wfIsdnSpidRetryTimer
		INTEGER,
	    wfIsdnSpidResetBri
		INTEGER
        }

    wfIsdnLocalPhoneNumDelete OBJECT-TYPE
        SYNTAX	INTEGER {
    		    created(1),
    		    deleted(2)
    		}
        ACCESS	read-write
        STATUS	mandatory
        DESCRIPTION
                "Delete this phone number from the list"
        DEFVAL	{ created }
        ::= { wfIsdnLocalPhoneNumEntry 1 }

    wfIsdnLocalPhoneNumLineNum OBJECT-TYPE
        SYNTAX	INTEGER
        ACCESS	read-only
        STATUS	mandatory
        DESCRIPTION
                "D Channel Line Number"
        ::= { wfIsdnLocalPhoneNumEntry 2 }

    wfIsdnLocalPhoneNumIndex OBJECT-TYPE
        SYNTAX	INTEGER(1..255)
        ACCESS	read-only
        STATUS	mandatory
        DESCRIPTION
                "a unique sequetial index to create a list"
        ::= { wfIsdnLocalPhoneNumEntry 3 }

    wfIsdnLocalDirectoryNum OBJECT-TYPE
        SYNTAX	DisplayString
        ACCESS	read-write
        STATUS	mandatory
        DESCRIPTION
                "Directory Number (local phone number) assiciated with the interface"
        ::= { wfIsdnLocalPhoneNumEntry 4 }

    wfIsdnLocalSubAddr OBJECT-TYPE
        SYNTAX	DisplayString
        ACCESS	read-write
        STATUS	mandatory
        DESCRIPTION
                "Local Phone Number, the sub address portion"
        ::= { wfIsdnLocalPhoneNumEntry 5 }

    wfIsdnLocalSpid OBJECT-TYPE
        SYNTAX	DisplayString
        ACCESS	read-write
        STATUS	mandatory
        DESCRIPTION
                "Service Profile IDentifier - assigned by the Central Office on ordering
                ISDN service from a switch conforming to National ISDN."
        ::= { wfIsdnLocalPhoneNumEntry 6 }

    wfIsdnLocalAssignedChannel OBJECT-TYPE
        SYNTAX	INTEGER {
    		    channel1(1),
    		    channel2(2)
    		}
        ACCESS	read-write
        STATUS	mandatory
        DESCRIPTION
                "for Swserv phone numbers, the delimiter portion"
        ::= { wfIsdnLocalPhoneNumEntry 7 }

    wfIsdnLocalSpidStatus OBJECT-TYPE
        SYNTAX	INTEGER {
    		    accepted(1),
    		    rejected(2)
    		}
        ACCESS	read-only
        STATUS	mandatory
        DESCRIPTION
                "The status of SPID registration"
        ::= { wfIsdnLocalPhoneNumEntry 8 }

    wfIsdnLocalDirectoryNumType OBJECT-TYPE
        SYNTAX  INTEGER {
                    unknown(1),
                    international(16),
                    national(32),
                    specific(48),
                    subscriber(64),
                    abbreviated(96)
                }
        ACCESS  read-write
        STATUS  mandatory
        DESCRIPTION
                "For ISDN type number, it needs type of number
                UNKNOWN Type is 0, use 1 to satisfy MDL requirement
                This attribute value will be ANDED with  0xFFF0 before using it."
        DEFVAL  { unknown }
        ::= { wfIsdnLocalPhoneNumEntry 9 }

    wfIsdnLocalDirectoryNumPlan OBJECT-TYPE
        SYNTAX  INTEGER {
                    unknown(16),
                    telephony(1),
                    x121(3),
                    telex(4),
                    standard(8),
                    private(9)
                }
        ACCESS  read-write
        STATUS  mandatory
        DESCRIPTION
                "If Isdn and if type of number is UNKNOWN or INERNATIONAL or NATIONAL
                or SUBSCRIBER  then a plan number is needed. UNKNOWN is 0 ,
                using 16 (0x10)to satisfy MDL requirement. We will AND  this field with
                0x0F before using it."
        DEFVAL  { unknown }
        ::= { wfIsdnLocalPhoneNumEntry 10 }

    wfIsdnSpidRetries  OBJECT-TYPE
        SYNTAX	INTEGER 
        ACCESS	read-write
        STATUS	mandatory
        DESCRIPTION
                "Number of times the SPID registration request is sent to the ISDN switch"
	DEFVAL  { 20 }
        ::= { wfIsdnLocalPhoneNumEntry 11 }

    wfIsdnSpidRetryAttempts  OBJECT-TYPE
        SYNTAX	INTEGER
        ACCESS	read-write
        STATUS	mandatory
        DESCRIPTION
                "Number of times the SPID registration is re-envoked."
       	DEFVAL  { 0 }
	 ::= { wfIsdnLocalPhoneNumEntry 12 }

    wfIsdnSpidRetryTimer  OBJECT-TYPE
        SYNTAX	INTEGER
        ACCESS	read-write
        STATUS	mandatory
        DESCRIPTION
                "Amount of time in seconds to wait before re-envoking SPID registration"
	DEFVAL  { 60 }
        ::= { wfIsdnLocalPhoneNumEntry 13 }

    wfIsdnSpidResetBri  OBJECT-TYPE
        SYNTAX	INTEGER 
        ACCESS	read-write
        STATUS	mandatory
        DESCRIPTION
                "When enabled the ISDN BRI interface is reset after all the SPID registartion 
		attempts fail, zero setting disables this functionality. When set to a nonzero N
		the interface will be reset if the total number of BRI interface resets on this 
		slot is less than N."
	DEFVAL { 0 }
        ::= { wfIsdnLocalPhoneNumEntry 14 }
    	

    wfModemCommandTable OBJECT-TYPE
        SYNTAX	SEQUENCE OF WfModemCommandEntry
        ACCESS	not-accessible
        STATUS	mandatory
        DESCRIPTION
                "Modem Command String interface Entry "
        ::= { wfIsdnGroup 13 }

    wfModemCommandEntry OBJECT-TYPE
        SYNTAX	WfModemCommandEntry
        ACCESS	not-accessible
        STATUS	mandatory
        DESCRIPTION
                "An entry in table"
        INDEX	{ wfModemCommandSlot,
    		  wfModemCommandConnector }
        ::= { wfModemCommandTable 1 }

    WfModemCommandEntry ::= SEQUENCE {
    	    wfModemCommandDelete
    		INTEGER,
    	    wfModemCommandSlot
    		INTEGER,
    	    wfModemCommandConnector
    		INTEGER,
    	    wfModemCommandString
    		DisplayString
        }

    
    wfModemCommandDelete OBJECT-TYPE
        SYNTAX	INTEGER {
    		    created(1),
    		    deleted(2)
    		}
        ACCESS	read-write
        STATUS	mandatory
        DESCRIPTION
                "Delete this Modem Command Entry mib record"
        DEFVAL	{ created }
        ::= { wfModemCommandEntry 1 }

    wfModemCommandSlot OBJECT-TYPE
        SYNTAX	INTEGER(1..14)
        ACCESS	read-only
        STATUS	mandatory
        DESCRIPTION
                "Instance ID Slot, filled in by driver"
        ::= { wfModemCommandEntry 2 }

    wfModemCommandConnector OBJECT-TYPE
        SYNTAX	INTEGER {
    		    one(1),
    		    two(2),
    		    three(3),
    		    four(4),
		    five(5),
		    six(6),
		    seven(7),
		    eight(8)		
    		}
        ACCESS	read-only
        STATUS	mandatory
        DESCRIPTION
                "Instance ID Connector, filled in by driver"
        ::= { wfModemCommandEntry 3 }

    wfModemCommandString OBJECT-TYPE
        SYNTAX DisplayString
        ACCESS read-write
        STATUS mandatory
        DESCRIPTION
                "String to be passed to the modem to configure it. Syntax of
                 the string is not checked"
        ::= { wfModemCommandEntry 4 }


    END  -- Wellfleet-ISDN-MIB
