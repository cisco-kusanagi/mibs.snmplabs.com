AISLCASYNC-MIB DEFINITIONS ::= BEGIN

IMPORTS
	MODULE-IDENTITY, OBJECT-TYPE, enterprises
			FROM SNMPv2-SMI
	DisplayString, TruthValue
			FROM SNMPv2-TC;

	PositiveInteger    ::= INTEGER (1..2147483647)

	aii OBJECT IDENTIFIER ::= {enterprises 539}

aiSLCAsync MODULE-IDENTITY
	LAST-UPDATED "9909151700Z"
	ORGANIZATION "Applied Innovation Inc."
	CONTACT-INFO "Engineering MIB Administrator
					Postal: Applied Innovation Inc.
						5800 Innovation Drive
						Dublin, Ohio 43017-3271

					Tel:    614-798-2000
					Fax:    614-798-1770
					Email:  snmp@aiinet.com"
	DESCRIPTION "MIB module for SLCs with asynchronous links."
	::= {aii 23}

--=========================================================================

aiSLCAsyncTable OBJECT-TYPE
	SYNTAX		SEQUENCE OF AISLCAsyncEntry
	MAX-ACCESS	not-accessible
	STATUS		current
	DESCRIPTION
		"Table of asynchronous link information indexed by link number.
		Includes link appplication and direct connect alias."
	::= {aiSLCAsync 1}

aiSLCAsyncEntry OBJECT-TYPE
	SYNTAX		AISLCAsyncEntry
	MAX-ACCESS	not-accessible
	STATUS		current
	DESCRIPTION	"Entry of aiSLCAsyncTable."
	INDEX		{aislcasyLinkNumber}
	::= {aiSLCAsyncTable 1}

AISLCAsyncEntry ::= SEQUENCE {
	aislcasyLinkNumber		PositiveInteger,
	aislcasyApplication		INTEGER,
	aislcasyDirectConnectAlias	DisplayString,
	aislcasyXonInterval   INTEGER,
	aislcasyCallState	DisplayString,
	aislcasyMinimizeLatency	TruthValue
}

aislcasyLinkNumber OBJECT-TYPE
	SYNTAX		PositiveInteger
	MAX-ACCESS	read-only
	STATUS		current
	DESCRIPTION	"Link number to which this table row applies."
	::= {aiSLCAsyncEntry 1}

aislcasyApplication OBJECT-TYPE
	SYNTAX		INTEGER {
			login(1),
			destination(2),
			directConnect(3),
			callMenu(4)
			}
	MAX-ACCESS	read-write
	STATUS		current
	DESCRIPTION
		"Application configured for the this link.
		login(1):
			Link provides a login prompt.
		destination(2):
			Link is only a destination and cannot
			be used to place calls.
		directConnect(3):
			Link connects directly to the destination
			stored in aislcasyDirectConnectAlias.
		callMenu(4):
			Link provides a menu of destinations
			to which calls can be placed."
	::= {aiSLCAsyncEntry 2}

aislcasyDirectConnectAlias OBJECT-TYPE
	SYNTAX		DisplayString
	MAX-ACCESS	read-write
	STATUS		current
	DESCRIPTION
		"Alias used when aislcasyApplication is directConnect(3).
		Maximum length is 255 characters."
	::= {aiSLCAsyncEntry 3}

aislcasyXonInterval OBJECT-TYPE
	SYNTAX		INTEGER (0..120)
	UNITS		"seconds"
	MAX-ACCESS	read-write
	STATUS		current
	DESCRIPTION
		"Time between sending successive XON characters.
		Maximum is 120 seconds.
		Zero disables sending periodic XONs."
	::= {aiSLCAsyncEntry 4}

aislcasyCallState OBJECT-TYPE
	SYNTAX		DisplayString
	MAX-ACCESS	read-only
	STATUS		current
	DESCRIPTION
		"Read only string describing the current link call state."
	::= {aiSLCAsyncEntry 5}

aislcasyMinimizeLatency OBJECT-TYPE
	SYNTAX		TruthValue
	MAX-ACCESS	read-write
	STATUS		current
	DESCRIPTION	"Minimizes buffer latency."
	::= {aiSLCAsyncEntry 6}


--=========================================================================

aiSLCAsyncConnOptTable OBJECT-TYPE
	SYNTAX		SEQUENCE OF AISLCAsyncConnOptEntry
	MAX-ACCESS	not-accessible
	STATUS		current
	DESCRIPTION
		"Table of asynchronous link connect options indexed by
		link number.  Includes settings for when and how to
		establish connections."
	::= {aiSLCAsync 2}


aiSLCAsyncConnOptEntry OBJECT-TYPE
	SYNTAX		AISLCAsyncConnOptEntry
	MAX-ACCESS	not-accessible
	STATUS		current
	DESCRIPTION	"Entry of aiSLCAsyncConnOptTable."
	INDEX		{aislcacoLinkNumber}
	::= {aiSLCAsyncConnOptTable 1}

AISLCAsyncConnOptEntry ::= SEQUENCE {
	aislcacoLinkNumber	PositiveInteger,
	aislcacoOnActiveDSR	TruthValue,
	aislcacoOnActiveDCD	TruthValue,
	aislcacoOnIncomingChar	TruthValue,
	aislcacoDirectConnect	TruthValue,
	aislcacoRetryTimer	INTEGER,
	aislcacoConnectString	DisplayString
}

aislcacoLinkNumber OBJECT-TYPE
	SYNTAX		PositiveInteger
	MAX-ACCESS	read-only
	STATUS		current
	DESCRIPTION	"Link number to which this table row applies."
	::= {aiSLCAsyncConnOptEntry 1}

aislcacoOnActiveDSR OBJECT-TYPE
	SYNTAX		TruthValue
	MAX-ACCESS	read-write
	STATUS		current
	DESCRIPTION	"Consider link active when DSR is active."
	::= {aiSLCAsyncConnOptEntry 2}

aislcacoOnActiveDCD OBJECT-TYPE
	SYNTAX		TruthValue
	MAX-ACCESS	read-write
	STATUS		current
	DESCRIPTION	"Consider link active when DCD is active."
	::= {aiSLCAsyncConnOptEntry 3}

aislcacoOnIncomingChar OBJECT-TYPE
	SYNTAX		TruthValue
	MAX-ACCESS	read-write
	STATUS		current
	DESCRIPTION	"Consider link active when characters are received."
	::= {aiSLCAsyncConnOptEntry 4}

aislcacoDirectConnect OBJECT-TYPE
	SYNTAX		TruthValue
	MAX-ACCESS	read-write
	STATUS		current
	DESCRIPTION
		"Connect to destination specified in
		aislcasyDirectConnectAlias as soon as the link is
		enabled.  This overrides other connection options."
	::= {aiSLCAsyncConnOptEntry 5}

aislcacoRetryTimer OBJECT-TYPE
	SYNTAX		INTEGER (0..32767)
	UNITS		"seconds"
	MAX-ACCESS	read-write
	STATUS		current
	DESCRIPTION
			"Wait interval after unsuccessful call.
			Maximum is 32767 seconds.
			Zero disables retry."
	::= {aiSLCAsyncConnOptEntry 6}

aislcacoConnectString OBJECT-TYPE
	SYNTAX		DisplayString (SIZE (0..80))
	MAX-ACCESS	read-write
	STATUS		current
	DESCRIPTION
		"String to send immediately after a call is established.
		Maximum length is 80 characters."
	::= {aiSLCAsyncConnOptEntry 7}

--=========================================================================

aiSLCAsyncDiscOptTable OBJECT-TYPE
	SYNTAX		SEQUENCE OF AISLCAsyncDiscOptEntry
	MAX-ACCESS	not-accessible
	STATUS		current
	DESCRIPTION
		"Table of asynchronous link disconnect options indexed by
		link number.  Includes settings for when and how to close
		connections."
	::= {aiSLCAsync 3}

aiSLCAsyncDiscOptEntry OBJECT-TYPE
	SYNTAX		AISLCAsyncDiscOptEntry
	MAX-ACCESS	not-accessible
	STATUS		current
	DESCRIPTION	"Entry of aiSLCAsyncDiscOptTable."
	INDEX		{aislcadoLinkNumber}
	::= {aiSLCAsyncDiscOptTable 1}

AISLCAsyncDiscOptEntry ::= SEQUENCE {
	aislcadoLinkNumber		PositiveInteger,
	aislcadoOnLostDSR		TruthValue,
	aislcadoOnLostDCD		TruthValue,
	aislcadoOnBreak			TruthValue,
	aislcadoInactivityTimer		INTEGER,
	aislcadoDisconnectString	DisplayString,
	aislcadoInactivityReceive	TruthValue
}

aislcadoLinkNumber OBJECT-TYPE
	SYNTAX		PositiveInteger
	MAX-ACCESS	read-only
	STATUS		current
	DESCRIPTION	"Link number to which this table row applies."
	::= {aiSLCAsyncDiscOptEntry 1}

aislcadoOnLostDSR OBJECT-TYPE
	SYNTAX		TruthValue
	MAX-ACCESS	read-write
	STATUS		current
	DESCRIPTION	"Disconnect call when DSR is lost."
	::= {aiSLCAsyncDiscOptEntry 2}

aislcadoOnLostDCD OBJECT-TYPE
	SYNTAX		TruthValue
	MAX-ACCESS	read-write
	STATUS		current
	DESCRIPTION	"Disconnect call when DCD is lost."
	::= {aiSLCAsyncDiscOptEntry 3}

aislcadoOnBreak OBJECT-TYPE
	SYNTAX		TruthValue
	MAX-ACCESS	read-write
	STATUS		current
	DESCRIPTION	"Disconnect call when a break character is received."
	::= {aiSLCAsyncDiscOptEntry 4}

aislcadoInactivityTimer OBJECT-TYPE
	SYNTAX		INTEGER (0..32767)
	UNITS		"seconds"
	MAX-ACCESS	read-write
	STATUS		current
	DESCRIPTION
		"Interval of inactivity after which a call is disconnected.
		Maximum is 32767 seconds.
		Zero disables disconnect-on-inactivty."
	::= {aiSLCAsyncDiscOptEntry 5}

aislcadoDisconnectString OBJECT-TYPE
	SYNTAX		DisplayString (SIZE (0..80))
	MAX-ACCESS	read-write
	STATUS		current
	DESCRIPTION
		"String to send immediately before a call is disconnected.
		Maximum length is 80 characters."
	::= {aiSLCAsyncDiscOptEntry 6}

aislcadoInactivityReceive OBJECT-TYPE
	SYNTAX		TruthValue
	MAX-ACCESS	read-write
	STATUS		current
	DESCRIPTION	"Inactivity Timer enabled when link receives calls."
	::= {aiSLCAsyncDiscOptEntry 7}


--=========================================================================

aiSLCAsyncModemOptTable OBJECT-TYPE
	SYNTAX    SEQUENCE OF AISLCAsyncModemOptEntry
	MAX-ACCESS  not-accessible
	STATUS    current
	DESCRIPTION
		"Table of asynchronous link modem options indexed by
		link number.  Includes settings for modem strings, 
		dialing timeout, retry limit, and signal lead options."
	::= {aiSLCAsync 4}

aiSLCAsyncModemOptEntry OBJECT-TYPE
	SYNTAX    AISLCAsyncModemOptEntry
	MAX-ACCESS  not-accessible
	STATUS    current
	DESCRIPTION "Entry of aiSLCAsyncModemOptTable."
	INDEX   {aislcmdmLinkNumber}
	::= {aiSLCAsyncModemOptTable 1}

AISLCAsyncModemOptEntry ::= SEQUENCE {
	aislcmdmLinkNumber      PositiveInteger,
	aislcmdmInitString      DisplayString,
	aislcmdmTermString      DisplayString,
	aislcmdmTimeToConnect   INTEGER,
	aislcmdmMaxDialAttempts INTEGER,
	aislcmdmDtrConnState    INTEGER,
	aislcmdmDtrDconnState   INTEGER,
	aislcmdmRtsConnState    INTEGER,
	aislcmdmRtsDconnState   INTEGER
}

aislcmdmLinkNumber OBJECT-TYPE
	SYNTAX    PositiveInteger
	MAX-ACCESS  read-only
	STATUS    current
	DESCRIPTION "Link number to which this table row applies."
	::= {aiSLCAsyncModemOptEntry 1}

aislcmdmInitString OBJECT-TYPE
	SYNTAX    DisplayString (SIZE (0..80))
	MAX-ACCESS  read-write
	STATUS    current
	DESCRIPTION
		"String to send when a link is enabled or restarted, possibly
		to place a modem in auto-answer mode, to cause a modem to dial
		a remote location, or to prepare a modem in some other way.
		Maximum length is 80 characters."
	::= {aiSLCAsyncModemOptEntry 2}

aislcmdmTermString OBJECT-TYPE
	SYNTAX    DisplayString (SIZE (0..80))
	MAX-ACCESS  read-write
	STATUS    current
	DESCRIPTION
		"String to send immediately after the disconnect string, 
		before a call is disconnected, possibly for the bennefit 
		of an attached modem.
		Maximum length is 80 characters."
	::= {aiSLCAsyncModemOptEntry 3}

aislcmdmTimeToConnect OBJECT-TYPE
	SYNTAX    INTEGER (1..300)
	UNITS   "seconds"
	MAX-ACCESS  read-write
	STATUS    current
	DESCRIPTION
		"Number of seconds to wait for modem to connect after dialing.
		Maximum is 300 seconds.
		Minimum is 5 seconds"
	::= {aiSLCAsyncModemOptEntry 4}

aislcmdmMaxDialAttempts OBJECT-TYPE
	SYNTAX    INTEGER (0..100)
	MAX-ACCESS  read-write
	STATUS    current
	DESCRIPTION
		"Maximum number of times to dial when placing an outgoing call.
		Maximum is 100 attempts.
		Zero retrys dialing forever."
	::= {aiSLCAsyncModemOptEntry 5}

aislcmdmDtrConnState OBJECT-TYPE
	SYNTAX    INTEGER {
			on(1),
			off(2)
			}
	MAX-ACCESS  read-write
	STATUS    current
	DESCRIPTION
		"State of DTR when connected or connecting.
		on(1):
			DTR is on when link is connected or connecting.
		off(2):
			DTR is off when link is connected or connecting."
	::= {aiSLCAsyncModemOptEntry 6}

aislcmdmDtrDconnState OBJECT-TYPE
	SYNTAX    INTEGER {
			on(1),
			off(2),
			toggle(3)
			}
	MAX-ACCESS  read-write
	STATUS    current
	DESCRIPTION
		"State of DTR when disconnected.
		on(1):
			DTR is on when link is disconnected.
		off(2):
			DTR is off when link is disconnected.
		toggle(3):
			DTR toggles on-to-off when link disconnects."
	::= {aiSLCAsyncModemOptEntry 7}

aislcmdmRtsConnState OBJECT-TYPE
SYNTAX    INTEGER {
			on(1),
			off(2),
			followsDSR(3),
			xmitFlowControl(4),
			bidirectionalFlowControl(5),
			followsData(6)
			}
	MAX-ACCESS  read-write
	STATUS    current
	DESCRIPTION
		"State of DTR when connected or connecting.
			on(1),
				RTS is on when link is connected or connecting.
			off(2),
				RTS is off when link is connected or connecting.
			followsDSR(3),
				RTS follows the state of DSR when link is connected or connecting.
			xmitFlowControl(4),
				RTS is on when the DTE has data to send, and 
				DTE sends only when DCE asserts CTS on.
			bidirectionalFlowControl(5)
				RTS is on when DTE is ready to accept data from DCE, and
				DTE sends only when DCE asserts CTS on
			followsData(6),
				RTS is asserted only when data is transmitted."
	::= {aiSLCAsyncModemOptEntry 8}

aislcmdmRtsDconnState OBJECT-TYPE
	SYNTAX    INTEGER {
			on(1),
			off(2),
			toggle(3)
			}
	MAX-ACCESS  read-write
	STATUS    current
	DESCRIPTION
		"State of RTS when disconnected.
		on(1):
			RTS is on when link is disconnected.
		off(2):
			RTS is off when link is disconnected.
		toggle(3):
			DTR toggles on-to-off when link disconnects."
	::= {aiSLCAsyncModemOptEntry 9}


--=========================================================================

END
