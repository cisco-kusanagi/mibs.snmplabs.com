-- Change history here need to be removed prior to checking into
-- official 12.00.  Best to put them into source control history.
--
-- 12/18/96 F.Reichmeyer; changed IfTable according to the
--          experimental mib (ver. 04), moved IfFlowTable to
--          the int_serv mib, removed StaticResvFwdTable (it
--          was decided that ResvFwdTable should be read-only).
-- 12/23/96 K.H. Chan: Modified changes made by Fran to fit
--          both router's classic MIB Services need and MIB II.
--          Also updated CDL file to match the new MIB.
-- 12/28/96 D. Morrissette: Changed default enum of IfEnable (typo)
--          Also changed the spelling of wfReservationsProtocolsGroup
--          so ST2's definition of this mib could be imported
-- 12/30/96 F.Reichmeyer; Modified SenderTable
-- 01/14/97 F.Reichmeyer; Move static path and resv tables to
--          separate static mib file for rsvp proxy use.
-- 02/20/97 K.H.Chan: Merging rsvp_dev version and Site Manager
--          version for 12.00.
-- 6/19/97  D.Morrissette; comment format change for SM's mosy
-- 8/8/97   F.Reichmeyer; Change RsvpStatic names to be unique to
--          27 chars, now wfSRsvp is used.

Wellfleet-RSVP-MIB DEFINITIONS ::= BEGIN

    IMPORTS
      OBJECT-TYPE
        FROM RFC-1212
      IpAddress, Gauge
        FROM RFC1155-SMI
      wfReservationProtocolGroup
        FROM Wellfleet-COMMON-MIB;

    wfRsvpGroup
                OBJECT IDENTIFIER ::= { wfReservationProtocolGroup 1 }

    wfRsvp      OBJECT IDENTIFIER ::= { wfRsvpGroup 1 }

    wfRsvpDelete OBJECT-TYPE
        SYNTAX  INTEGER {
                created(1),
                deleted(2)
            }
        ACCESS  read-write
        STATUS  mandatory
        DESCRIPTION
                "Create/Delete parameter. Default is created.
                Users perform a set operation on this
                object in order to create/delete Rsvp."
        DEFVAL  { created }
        ::= { wfRsvp 1 }

    wfRsvpDisable OBJECT-TYPE
        SYNTAX  INTEGER {
                enabled(1),
                disabled(2)
            }
        ACCESS  read-write
        STATUS  mandatory
        DESCRIPTION
                "Enable/Disable parameter. Default is enabled.
                Users perform a set operation on this
                object in order to enable/disable Rsvp."
        DEFVAL  { enabled }
        ::= { wfRsvp 2 }

    wfRsvpState OBJECT-TYPE
        SYNTAX  INTEGER {
                up(1),
                down(2),
                init(3),
                notpres(4)
            }
        ACCESS  read-only
        STATUS  mandatory
        DESCRIPTION
                "The current state of Rsvp."
        DEFVAL  { notpres }
        ::= { wfRsvp 3 }

    wfRsvpSoloistSlots OBJECT-TYPE
        SYNTAX  Gauge(0..4294967295)
        ACCESS  read-write
        STATUS  mandatory
        DESCRIPTION
                "Slot mask for which slot(s) RSVP Soloist is eligible
                to run on.  The MSBit represents slot 1, the
                next most significant bit represents slot 2,
                and so on...  Slots can be 1-14.
                Default is all slots on a BCN."
        DEFVAL  { 4294705152 }
        ::= { wfRsvp 4 }

    wfRsvpInfoLogFilter OBJECT-TYPE
        SYNTAX  INTEGER
        ACCESS  read-write
        STATUS  mandatory
        DESCRIPTION
                "Turn RSVP log ON or OFF for RSVP informational
                 and warning messages. The bit position is used
                 to represent a RSVP module:
                 RSVP_LOG_RIF_PROCESSING            0x0001 - RIF processing.
                 RSVP_LOG_SOLO_PROCESSING           0x0002 - SOLO processing.
                 RSVP_LOG_ROUTE_INTF_PROCESSING     0x0004 - ROUTE interface processing.
                 RSVP_LOG_MERGE_PROCESSING          0x0008 - MERGE processing.
                 RSVP_LOG_DB_PROCESSING             0x0010 - database access processing.
                 RSVP_LOG_INTSERV_INTF_PROCESSING   0x0020 - INTSERV interface processing.
                 RSVP_LOG_CRM_INTF_PROCESSING       0x0040 - CRM interface processing.
                 RSVP_LOG_STATIC_RSVP               0x0080 - STATIC RSVP processing.
                 RSVP_LOG_CONTROL_PROCESSING        0x0100 - CONTROL processing.
                 RSVP_LOG_MAP_VEC_PROCESSING        0x0200 - MAP VECTOR processing.
                 RSVP_LOG_PROXY_PROCESSING          0x0400 - RSVP MIB PROXY processing.
                 RSVP_LOG_REFRESH_PROCESSING        0x0800 - Path/Resv Refresh processing."
        DEFVAL { 0 }
        ::= { wfRsvp 5 }

    wfRsvpDebugLogFilter OBJECT-TYPE
        SYNTAX  INTEGER
        ACCESS  read-write
        STATUS  mandatory
        DESCRIPTION
                "Turn RSVP log ON or OFF for RSVP debugging
                 messages. The bit position is used to
                 represent a RSVP module:
                 RSVP_LOG_RIF_PROCESSING            0x0001 - RIF processing.
                 RSVP_LOG_SOLO_PROCESSING           0x0002 - SOLO processing.
                 RSVP_LOG_ROUTE_INTF_PROCESSING     0x0004 - ROUTE interface processing.
                 RSVP_LOG_MERGE_PROCESSING          0x0008 - MERGE processing.
                 RSVP_LOG_DB_PROCESSING             0x0010 - database access processing.
                 RSVP_LOG_INTSERV_INTF_PROCESSING   0x0020 - INTSERV interface processing.
                 RSVP_LOG_CRM_INTF_PROCESSING       0x0040 - CRM interface processing.
                 RSVP_LOG_STATIC_RSVP               0x0080 - STATIC RSVP processing.
                 RSVP_LOG_CONTROL_PROCESSING        0x0100 - CONTROL processing.
                 RSVP_LOG_MAP_VEC_PROCESSING        0x0200 - MAP VECTOR processing.
                 RSVP_LOG_PROXY_PROCESSING          0x0400 - RSVP MIB PROXY processing.
                 RSVP_LOG_REFRESH_PROCESSING        0x0800 - Path/Resv Refresh processing."
        DEFVAL { 0 }
        ::= { wfRsvp 6 }

    wfRsvpTraceLogFilter OBJECT-TYPE
        SYNTAX  INTEGER
        ACCESS  read-write
        STATUS  mandatory
        DESCRIPTION
                "Turn RSVP log ON or OFF for RSVP trace
                 messages. The bit position is used to
                 represent a RSVP module:
                 RSVP_LOG_RIF_PROCESSING            0x0001 - RIF processing.
                 RSVP_LOG_SOLO_PROCESSING           0x0002 - SOLO processing.
                 RSVP_LOG_ROUTE_INTF_PROCESSING     0x0004 - ROUTE interface processing.
                 RSVP_LOG_MERGE_PROCESSING          0x0008 - MERGE processing.
                 RSVP_LOG_DB_PROCESSING             0x0010 - database access processing.
                 RSVP_LOG_INTSERV_INTF_PROCESSING   0x0020 - INTSERV interface processing.
                 RSVP_LOG_CRM_INTF_PROCESSING       0x0040 - CRM interface processing.
                 RSVP_LOG_STATIC_RSVP               0x0080 - STATIC RSVP processing.
                 RSVP_LOG_CONTROL_PROCESSING        0x0100 - CONTROL processing.
                 RSVP_LOG_MAP_VEC_PROCESSING        0x0200 - MAP VECTOR processing.
                 RSVP_LOG_PROXY_PROCESSING          0x0400 - RSVP MIB PROXY processing.
                 RSVP_LOG_REFRESH_PROCESSING        0x0800 - Path/Resv Refresh processing."
        DEFVAL { 0 }
        ::= { wfRsvp 7 }

    wfRsvpTotalSenders OBJECT-TYPE
        SYNTAX  Gauge(0..4294967295)
        ACCESS  read-only
        STATUS  mandatory
        DESCRIPTION
                "The total number of Sender (PATH) states in the router."
        ::= { wfRsvp 8 }        

    wfRsvpTotalReservations OBJECT-TYPE
        SYNTAX  Gauge(0..4294967295)
        ACCESS  read-only
        STATUS  mandatory
        DESCRIPTION
                "The total number of Reservation (RESV) states in the router."
        ::= { wfRsvp 9 }        

    wfRsvpTotalReserved OBJECT-TYPE
        SYNTAX  Gauge(0..4294967295)
        ACCESS  read-only
        STATUS  mandatory
        DESCRIPTION
                "The total number of of successful reservations."
        ::= { wfRsvp 10 }        

    wfRsvpCurrentSoloistSlot OBJECT-TYPE
        SYNTAX  INTEGER
        ACCESS  read-only
        STATUS  mandatory
        DESCRIPTION
                "The Current RSVP Soloist slot. Slots can be 1-14.
                Default is zero."
        DEFVAL  { 0 }
        ::= { wfRsvp 11 }


--      The RSVP Session Statistics Database displays statistics
--      relating to the number of senders and receivers in each
--      session.

    wfRsvpSessionTable OBJECT-TYPE
        SYNTAX  SEQUENCE OF WfRsvpSessionEntry
        ACCESS  not-accessible
        STATUS  mandatory
        DESCRIPTION
           "Statistics concerning the sessions seen  by  a
           given system."
        ::= { wfRsvpGroup 2 }
     
    wfRsvpSessionEntry OBJECT-TYPE
        SYNTAX  WfRsvpSessionEntry
        ACCESS  not-accessible
        STATUS  mandatory
        DESCRIPTION
           "Statistics concerning a  single  RSVP  session
           seen by a given system."
        INDEX   { wfRsvpSessionDestAddr,
                  wfRsvpSessionProtocol,
                  wfRsvpSessionPort }
        ::= { wfRsvpSessionTable 1 }

    WfRsvpSessionEntry ::= SEQUENCE {
        wfRsvpSessionDestAddr         IpAddress,
        wfRsvpSessionDestAddrLength   INTEGER,
        wfRsvpSessionProtocol         INTEGER,
        wfRsvpSessionPort             INTEGER,
        wfRsvpSessionSenders          Gauge,
        wfRsvpSessionReceivers        Gauge,
        wfRsvpSessionRequests         Gauge
        }

    wfRsvpSessionDestAddr OBJECT-TYPE
        SYNTAX  IpAddress
        ACCESS  read-only
        STATUS  mandatory
        DESCRIPTION
           "The destination address used by all senders in
           this  session.   This object may not be changed
           when the  value  of  the  RowStatus  object  is
           'valid'."
       ::= { wfRsvpSessionEntry 1 }

    wfRsvpSessionDestAddrLength OBJECT-TYPE
        SYNTAX  INTEGER(0..128)
        ACCESS  read-only
        STATUS  mandatory
        DESCRIPTION
           "The CIDR prefix length of the session address,
           which  is  32  for  IP4  host and multicast ad-
           dresses.  This object may not be  changed  when
           the value of the RowStatus object is 'valid'."
       ::= { wfRsvpSessionEntry 2 }
 
    wfRsvpSessionProtocol OBJECT-TYPE
        SYNTAX  INTEGER(1..255)
        ACCESS  read-only
        STATUS  mandatory
        DESCRIPTION
           "The IP Protocol used by  this  session.   This
           object may not be changed when the value of the
           RowStatus object is 'valid'."
       ::= { wfRsvpSessionEntry 3 }

    wfRsvpSessionPort OBJECT-TYPE
        SYNTAX  INTEGER(0..65535)
        ACCESS  read-only
        STATUS  mandatory
        DESCRIPTION
           "The UDP or TCP port number used as a  destina-
           tion  port for all senders in this session.  If
           the IP protocol in use, specified  by  rsvpSen-
           derProtocol,  is  50  (ESP)  or  51  (AH), this
           represents a virtual destination  port  number.
           A  value of zero indicates that the IP protocol
           in use does not have ports.   This  object  may
           not  be changed when the value of the RowStatus
           object is 'valid'."
       ::= { wfRsvpSessionEntry 4 }

    wfRsvpSessionSenders OBJECT-TYPE
        SYNTAX  Gauge (0..4294967295)
        ACCESS  read-only
        STATUS  mandatory
        DESCRIPTION
           "The number of senders currently  known  to  be
           part of this session."
       ::= { wfRsvpSessionEntry 5 }

    wfRsvpSessionReceivers OBJECT-TYPE
        SYNTAX  Gauge (0..4294967295)
        ACCESS  read-only
        STATUS  mandatory
        DESCRIPTION
           "The number of reservations being requested  of
           this system for this session."
       ::= { wfRsvpSessionEntry 6 }

    wfRsvpSessionRequests OBJECT-TYPE
        SYNTAX  Gauge (0..4294967295)
        ACCESS  read-only
        STATUS  mandatory
        DESCRIPTION
           "The number of reservation requests this system
           is sending upstream for this session."
       ::= { wfRsvpSessionEntry 7 }


--      The RSVP Session Sender Database contains the information
--      displayed by senders regarding their potential contribution
--      to session data content. It is in essence a list of the
--      valid PATH messages that the RSVP Router or Host is receiving.

    wfRsvpSenderTable OBJECT-TYPE
        SYNTAX  SEQUENCE OF WfRsvpSenderEntry
        ACCESS  not-accessible
        STATUS  mandatory
        DESCRIPTION
                "Information describing the  state  information
                displayed by senders in PATH messages."
       ::= { wfRsvpGroup 3 }

    wfRsvpSenderEntry OBJECT-TYPE
        SYNTAX  WfRsvpSenderEntry
        ACCESS  not-accessible
        STATUS  mandatory
        DESCRIPTION
                "Information describing the  state  information
                displayed by a single sender's PATH message."
       INDEX    { wfRsvpSenderDestAddr, 
                  wfRsvpSenderProtocol,
                  wfRsvpSenderDestPort,
                  wfRsvpSenderAddr, 
                  wfRsvpSenderPort }
       ::= { wfRsvpSenderTable 1 }

   WfRsvpSenderEntry ::= SEQUENCE {
	wfRsvpSenderDestAddr                      IpAddress,
	wfRsvpSenderAddr                          IpAddress,
        wfRsvpSenderDestAddrLength                INTEGER,
        wfRsvpSenderAddrLength                    INTEGER,
	wfRsvpSenderProtocol                      INTEGER,
        wfRsvpSenderDestPort                      INTEGER,
        wfRsvpSenderPort                          INTEGER,
        wfRsvpSenderHopAddr                       IpAddress,
        wfRsvpSenderHopLih                        INTEGER,
        wfRsvpSenderInterface                     INTEGER,
        wfRsvpSenderTSpecRate                     INTEGER,
        wfRsvpSenderTSpecPeakRate                 INTEGER,
        wfRsvpSenderTSpecBurst                    INTEGER,
        wfRsvpSenderTSpecMinTU			  INTEGER,
        wfRsvpSenderTSpecMaxTU                    INTEGER,
        wfRsvpSenderInterval                      INTEGER,
        wfRsvpSenderRSVPHop                       INTEGER,
        wfRsvpSenderLastChange                    INTEGER,
        wfRsvpSenderPSBTimeout	                  INTEGER,
        wfRsvpSenderPolicy                        OCTET STRING,
        wfRsvpSenderAdspecBreak                   INTEGER,
        wfRsvpSenderAdspecHopCount                INTEGER,
        wfRsvpSenderAdspecPathBw                  INTEGER,
        wfRsvpSenderAdspecMinLatency              INTEGER,
        wfRsvpSenderAdspecMtu                     INTEGER,
        wfRsvpSenderAdspecGSSvc           INTEGER,
        wfRsvpSenderAdspecGSBreak         INTEGER,
        wfRsvpSenderAdspecGSCtot          INTEGER,
        wfRsvpSenderAdspecGSDtot          INTEGER,
        wfRsvpSenderAdspecGSCsum          INTEGER,
        wfRsvpSenderAdspecGSDsum          INTEGER,
        wfRsvpSenderAdspecGSHopCount      INTEGER,
        wfRsvpSenderAdspecGSPathBw        INTEGER,
        wfRsvpSenderAdspecGSMinLatency    INTEGER,
        wfRsvpSenderAdspecGSMtu           INTEGER,
        wfRsvpSenderAdspecCLSvc             INTEGER,
        wfRsvpSenderAdspecCLBreak           INTEGER,
        wfRsvpSenderAdspecCLHopCount        INTEGER,
        wfRsvpSenderAdspecCLPathBw          INTEGER,
        wfRsvpSenderAdspecCLMinLatency      INTEGER,
        wfRsvpSenderAdspecCLMtu             INTEGER,
        wfRsvpSenderStatus                        INTEGER
    }

    wfRsvpSenderDestAddr OBJECT-TYPE
        SYNTAX  IpAddress
        ACCESS  read-only
        STATUS  mandatory
        DESCRIPTION
           "The destination IP address used by all senders in
           this  session.   This object may not be changed
           when the  value  of  the  RowStatus  object  is
           'valid'."
       ::= { wfRsvpSenderEntry 1 }


    wfRsvpSenderAddr OBJECT-TYPE
        SYNTAX  IpAddress
        ACCESS  read-only
        STATUS  mandatory
        DESCRIPTION
           "The source address used by this sender in this
           session.   This  object may not be changed when
           the value of the RowStatus object is 'valid'."
       ::= { wfRsvpSenderEntry 2 }


    wfRsvpSenderDestAddrLength OBJECT-TYPE
        SYNTAX  INTEGER(0..128)
        ACCESS  read-only
        STATUS  mandatory
        DESCRIPTION
           "The length of the destination address in bits.
           This  is  the CIDR Prefix Length, which for IP4
           hosts and multicast addresses is 32 bits.  This
           object may not be changed when the value of the
           RowStatus object is 'valid'."
       ::= { wfRsvpSenderEntry 3 }


    wfRsvpSenderAddrLength OBJECT-TYPE
        SYNTAX  INTEGER(0..128)
        ACCESS  read-only
        STATUS  mandatory
        DESCRIPTION
           "The length of the sender's  address  in  bits.
           This  is  the CIDR Prefix Length, which for IP4
           hosts and multicast addresses is 32 bits.  This
           object may not be changed when the value of the
           RowStatus object is 'valid'."
       ::= { wfRsvpSenderEntry 4 }


    wfRsvpSenderProtocol OBJECT-TYPE
        SYNTAX  INTEGER(1..255)
        ACCESS  read-only
        STATUS  mandatory
        DESCRIPTION
           "The IP Protocol used by  this  session.   This
           object may not be changed when the value of the
           RowStatus object is 'valid'."
       ::= { wfRsvpSenderEntry 5 }


    wfRsvpSenderDestPort OBJECT-TYPE
        SYNTAX  INTEGER(0..65535)
        ACCESS  read-only
        STATUS  mandatory
        DESCRIPTION
           "The UDP or TCP port number used as a  destina-
           tion  port for all senders in this session.  If
           the IP protocol in use, specified  by  rsvpSen-
           derProtocol,  is  50  (ESP)  or  51  (AH), this
           represents a virtual destination  port  number.
           A  value of zero indicates that the IP protocol
           in use does not have ports.   This  object  may
           not  be changed when the value of the RowStatus
           object is 'valid'."
       ::= { wfRsvpSenderEntry 6 }


    wfRsvpSenderPort OBJECT-TYPE
        SYNTAX  INTEGER(0..65535)
        ACCESS  read-only
        STATUS  mandatory
        DESCRIPTION
           "The UDP or TCP port number used  as  a  source
           port  for  this sender in this session.  If the
           IP protocol in use, specified by rsvpSenderPro-
           tocol is 50 (ESP) or 51 (AH), this represents a
           generalized port identifier (GPI).  A value  of
           zero indicates that the IP protocol in use does
           not have ports.  This object may not be changed
           when  the  value  of  the  RowStatus  object is
           'valid'."
       ::= { wfRsvpSenderEntry 7 }


    wfRsvpSenderHopAddr OBJECT-TYPE
        SYNTAX  IpAddress
        ACCESS  read-only
        STATUS  mandatory
        DESCRIPTION
           "The address used  by  the  previous  RSVP  hop
           (which may be the original sender)."
       ::= { wfRsvpSenderEntry 8 }


    wfRsvpSenderHopLih OBJECT-TYPE
        SYNTAX  INTEGER
        ACCESS  read-only
        STATUS  mandatory
        DESCRIPTION
           "The Logical Interface Handle used by the  pre-
           vious  RSVP  hop  (which  may  be  the original
           sender)."
       ::= { wfRsvpSenderEntry 9 }


    wfRsvpSenderInterface OBJECT-TYPE
        SYNTAX  INTEGER
        ACCESS  read-only
        STATUS  mandatory
        DESCRIPTION
           "The ifIndex value of the  interface  on  which
           this PATH message was most recently received."
       ::= { wfRsvpSenderEntry 10 }

    wfRsvpSenderTSpecRate OBJECT-TYPE
        SYNTAX  INTEGER(0..'7FFFFFFF'h)
        ACCESS  read-only
        STATUS  mandatory
        DESCRIPTION
           "The Average Bit  Rate  of  the  sender's  data
           stream.   Within  a transmission burst, the ar-
           rival rate may be as fast  as  rsvpSenderTSpec-
           PeakRate  (if  supported by the service model);
           however, averaged across two or more burst  in-
           tervals,  the  rate  should not exceed rsvpSen-
           derTSpecRate.

           Note that this is a prediction, often based  on
           the  general  capability  of a type of codec or
           particular encoding; the measured average  rate
           may be significantly lower.

           UNITS, bits per second"
       ::= { wfRsvpSenderEntry 11 }

    wfRsvpSenderTSpecPeakRate OBJECT-TYPE
        SYNTAX  INTEGER(0..'7FFFFFFF'h)
        ACCESS  read-only
        STATUS  mandatory
        DESCRIPTION
           "The Peak Bit Rate of the sender's data stream.
           Traffic  arrival is not expected to exceed this
           rate at any time, apart  from  the  effects  of
           jitter in the network.  If not specified in the
           TSpec, this returns zero or noSuchValue.
           UNITS, bits per second"
       ::= { wfRsvpSenderEntry 12 }


    wfRsvpSenderTSpecBurst OBJECT-TYPE
        SYNTAX  INTEGER(0..'7FFFFFFF'h)
        ACCESS  read-only
        STATUS  mandatory
        DESCRIPTION
           "The size of the largest  burst  expected  from
           the sender at a time.
           UNITS, bytes"
       ::= { wfRsvpSenderEntry 13 }


    wfRsvpSenderTSpecMinTU OBJECT-TYPE
        SYNTAX  INTEGER(0..'7FFFFFFF'h)
        ACCESS  read-only
        STATUS  mandatory
        DESCRIPTION
           "The minimum message size for  this  flow.  The
           policing  algorithm will treat smaller messages
           as though they are this size."
       ::= { wfRsvpSenderEntry 14 }


    wfRsvpSenderTSpecMaxTU OBJECT-TYPE
        SYNTAX  INTEGER(0..'7FFFFFFF'h)
        ACCESS  read-only
        STATUS  mandatory
        DESCRIPTION
           "The maximum message size for  this  flow.  The
           admission  algorithm  will  reject TSpecs whose
           Maximum Transmission Unit, plus  the  interface
           headers, exceed the interface MTU."
       ::= { wfRsvpSenderEntry 15 }

    wfRsvpSenderInterval OBJECT-TYPE
        SYNTAX  INTEGER(0..'7FFFFFFF'h)
        ACCESS  read-only
        STATUS  mandatory
        DESCRIPTION
           "The interval between refresh messages  as  ad-
           vertised by the Previous Hop.

	UNITS milliseconds"
       ::= { wfRsvpSenderEntry 16 }


    wfRsvpSenderRSVPHop OBJECT-TYPE
        SYNTAX  INTEGER {
                true(1), false(2)
                }
        ACCESS  read-only
        STATUS  mandatory
        DESCRIPTION
           "If TRUE, the node believes that  the  previous
           IP  hop is an RSVP hop.  If FALSE, the node be-
           lieves that the previous IP hop may not  be  an
           RSVP hop."
       ::= { wfRsvpSenderEntry 17 }

    wfRsvpSenderLastChange OBJECT-TYPE
        SYNTAX  INTEGER
        ACCESS  read-only
        STATUS  mandatory
        DESCRIPTION
           "The time of the last change in this PATH  mes-
           sage;  This is either the first time it was re-
           ceived or the time of the most recent change in
           parameters."
       ::= { wfRsvpSenderEntry 18 }


    wfRsvpSenderPSBTimeout OBJECT-TYPE
        SYNTAX  INTEGER
        ACCESS  read-only
        STATUS  mandatory
        DESCRIPTION
                "The remaining lifetime of this sender's PSB."
        ::= { wfRsvpSenderEntry 19 }

    wfRsvpSenderPolicy OBJECT-TYPE
        SYNTAX  OCTET STRING (SIZE(4..65536))
        ACCESS  read-only
        STATUS  mandatory
        DESCRIPTION
           "The contents of the policy  object,  displayed
           as an uninterpreted string of octets, including
           the object header.  In the absence of  such  an
           object, this should be of zero length."
       ::= { wfRsvpSenderEntry 20 }


    wfRsvpSenderAdspecBreak OBJECT-TYPE
        SYNTAX  INTEGER {
                true(1), false(2)
                }
        ACCESS  read-only
        STATUS  mandatory
        DESCRIPTION
           "The global break bit general  characterization
           parameter  from  the ADSPEC.  If TRUE, at least
           one non-IS hop was detected in  the  path.   If
           FALSE, no non-IS hops were detected."
       ::= { wfRsvpSenderEntry 21 }


    wfRsvpSenderAdspecHopCount OBJECT-TYPE
        SYNTAX  INTEGER (0..65535)
        ACCESS  read-only
        STATUS  mandatory
        DESCRIPTION
           "The hop count general characterization parame-
           ter  from  the  ADSPEC.   A  return  of zero or
           noSuchValue indicates one of the following con-
           ditions:

              the invalid bit was set
              the parameter was not present"
       ::= { wfRsvpSenderEntry 22 }

    wfRsvpSenderAdspecPathBw OBJECT-TYPE
        SYNTAX  INTEGER(0..'7FFFFFFF'h)
        ACCESS  read-only
        STATUS  mandatory
        DESCRIPTION
           "The path bandwidth estimate general character-
           ization parameter from the ADSPEC.  A return of
           zero or noSuchValue indicates one of  the  fol-
           lowing conditions:

              the invalid bit was set
              the parameter was not present

           UNITS, bits per second"
       ::= { wfRsvpSenderEntry 23 }


    wfRsvpSenderAdspecMinLatency OBJECT-TYPE
        SYNTAX  INTEGER
        ACCESS  read-only
        STATUS  mandatory
        DESCRIPTION
           "The minimum path latency general characteriza-
           tion  parameter  from  the ADSPEC.  A return of
           zero or noSuchValue indicates one of  the  fol-
           lowing conditions:

              the invalid bit was set
              the parameter was not present

           UNITS, microseconds"
       ::= { wfRsvpSenderEntry 24 }


    wfRsvpSenderAdspecMtu OBJECT-TYPE
        SYNTAX  INTEGER (0..65535)
        ACCESS  read-only
        STATUS  mandatory
        DESCRIPTION
           "The composed Maximum Transmission Unit general
           characterization  parameter from the ADSPEC.  A
           return of zero or noSuchValue indicates one  of
           the following conditions:

              the invalid bit was set
              the parameter was not present

           UNITS, bytes"
       ::= { wfRsvpSenderEntry 25 }


    wfRsvpSenderAdspecGSSvc OBJECT-TYPE
        SYNTAX  INTEGER {
                true(1), false(2)
                }
        ACCESS  read-only
        STATUS  mandatory
        DESCRIPTION
           "If TRUE, the ADSPEC contains a Guaranteed Ser-
           vice  fragment.   If FALSE or noValue, the ADSPEC does not
           contain a Guaranteed Service fragment."
       ::= { wfRsvpSenderEntry 26 }


    wfRsvpSenderAdspecGSBreak OBJECT-TYPE
        SYNTAX  INTEGER {
                true(1), flase(2)
                }
        ACCESS  read-only
        STATUS      mandatory
        DESCRIPTION
           "If TRUE, the Guaranteed Service  fragment  has
           its  'break'  bit  set,  indicating that one or
           more nodes along the path do  not  support  the
           guaranteed  service.   If  FALSE,  and rsvpSen-
           derAdspecGSSvc is TRUE, the 'break' bit
           is not set.

           If wfRsvpSenderAdspecGuaranteedSvc is FALSE, this
           returns FALSE or noSuchValue."
       ::= { wfRsvpSenderEntry 27 }


    wfRsvpSenderAdspecGSCtot OBJECT-TYPE
        SYNTAX  INTEGER
        ACCESS  read-only
        STATUS  mandatory
        DESCRIPTION

           "If wfRsvpSenderAdspecGSSvc is TRUE, this
           is   the  end-to-end  composed  value  for  the
           guaranteed service 'C' parameter.  A return  of
           zero  or  noSuchValue indicates one of the fol-
           lowing conditions:

              the invalid bit was set
              the parameter was not present

           If wfRsvpSenderAdspecGSSvc is FALSE, this
           returns zero or noSuchValue.
           UNITS, bytes"
       ::= { wfRsvpSenderEntry 28 }


    wfRsvpSenderAdspecGSDtot OBJECT-TYPE
        SYNTAX  INTEGER
        ACCESS  read-only
        STATUS  mandatory
        DESCRIPTION
           "If wfRsvpSenderAdspecGSSvc is TRUE, this
           is   the  end-to-end  composed  value  for  the
           guaranteed service 'D' parameter.  A return  of
           zero  or  noSuchValue indicates one of the fol-
           lowing conditions:

              the invalid bit was set
              the parameter was not present

           If wfRsvpSenderAdspecGSSvc is FALSE, this
           returns zero or noSuchValue.
           UNITS, microseconds"
       ::= { wfRsvpSenderEntry 29 }


    wfRsvpSenderAdspecGSCsum OBJECT-TYPE
        SYNTAX  INTEGER
        ACCESS  read-only
        STATUS  mandatory
        DESCRIPTION
           "If wfRsvpSenderAdspecGSSvc is TRUE, this
           is  the  composed value for the guaranteed ser-
           vice 'C' parameter  since  the  last  reshaping
           point.   A  return of zero or noSuchValue indi-
           cates one of the following conditions:

              the invalid bit was set
              the parameter was not present

           If wfRsvpSenderAdspecGSSvc is FALSE, this
           returns zero or noSuchValue.
           UNITS, bytes"
       ::= { wfRsvpSenderEntry 30 }


    wfRsvpSenderAdspecGSDsum OBJECT-TYPE
        SYNTAX  INTEGER
        ACCESS  read-only
        STATUS  mandatory
        DESCRIPTION
           "If wfRsvpSenderAdspecGSSvc is TRUE, this
           is  the  composed value for the guaranteed ser-
           vice 'D' parameter  since  the  last  reshaping
           point.   A  return of zero or noSuchValue indi-
           cates one of the following conditions:

              the invalid bit was set
              the parameter was not present

           If wfRsvpSenderAdspecGSSvc is FALSE, this
           returns zero or noSuchValue.
           UNITS, microseconds"
       ::= { wfRsvpSenderEntry 31 }


    wfRsvpSenderAdspecGSHopCount OBJECT-TYPE
        SYNTAX  INTEGER (0..65535)
        ACCESS  read-only
        STATUS  mandatory
        DESCRIPTION

           "If wfRsvpSenderAdspecGSSvc is TRUE, this
           is  the  service-specific  override  of the hop
           count general characterization  parameter  from
           the  ADSPEC.   A  return of zero or noSuchValue
           indicates one of the following conditions:

              the invalid bit was set
              the parameter was not present

           If wfRsvpSenderAdspecGSSvc is FALSE, this
           returns zero or noSuchValue."
       ::= { wfRsvpSenderEntry 32 }


    wfRsvpSenderAdspecGSPathBw OBJECT-TYPE
        SYNTAX  INTEGER(0..'7FFFFFFF'h)
        ACCESS  read-only
        STATUS  mandatory
        DESCRIPTION
           "If wfRsvpSenderAdspecGSSvc is TRUE, this
           is  the  service-specific  override of the path
           bandwidth  estimate  general   characterization
           parameter from the ADSPEC.  A return of zero or
           noSuchValue indicates one of the following con-
           ditions:

              the invalid bit was set
              the parameter was not present

           If wfRsvpSenderAdspecGSSvc is FALSE, this
           returns zero or noSuchValue.
           UNITS, bits per second"
       ::= { wfRsvpSenderEntry 33 }


    wfRsvpSenderAdspecGSMinLatency OBJECT-TYPE
        SYNTAX  INTEGER
        ACCESS  read-only
        STATUS  mandatory
        DESCRIPTION
           "If wfRsvpSenderAdspecGSSvc is TRUE, this
           is the service-specific override of the minimum
           path latency general characterization parameter
           from  the  ADSPEC.  A return of zero or noSuch-
           Value indicates one  of  the  following  condi-
           tions:

              the invalid bit was set
              the parameter was not present

           If wfRsvpSenderAdspecGSSvc is FALSE, this
           returns zero or noSuchValue. UNITS, microseconds"
       ::= { wfRsvpSenderEntry 34 }


    wfRsvpSenderAdspecGSMtu OBJECT-TYPE
        SYNTAX  INTEGER (0..65535)
        ACCESS  read-only
        STATUS  mandatory
        DESCRIPTION
           "If wfRsvpSenderAdspecGSSvc is TRUE, this
           is  the  service-specific  override of the com-
           posed Maximum Transmission Unit general charac-
           terization parameter from the ADSPEC.  A return
           of zero or noSuchValue  indicates  one  of  the
           following conditions:

              the invalid bit was set
              the parameter was not present

           If wfRsvpSenderAdspecGSSvc is FALSE, this
           returns zero or noSuchValue. UNITS, bytes"
       ::= { wfRsvpSenderEntry 35 }


    wfRsvpSenderAdspecCLSvc OBJECT-TYPE
        SYNTAX  INTEGER {
                true(1), false(2)
                }
        ACCESS  read-only
        STATUS  mandatory
        DESCRIPTION
           "If TRUE, the ADSPEC contains a Controlled Load
           Service  fragment.   If  FALSE, the ADSPEC does
           not contain a  Controlled  Load  Service  frag-
           ment."
       ::= { wfRsvpSenderEntry 36 }


    wfRsvpSenderAdspecCLBreak OBJECT-TYPE
        SYNTAX  INTEGER {
                true(1), false(2)
                }
        ACCESS  read-only
        STATUS  mandatory
        DESCRIPTION
           "If TRUE, the Controlled Load Service  fragment
           has its 'break' bit set, indicating that one or
           more nodes along the path do  not  support  the
           controlled   load   service.    If  FALSE,  and
           wfRsvpSenderAdspecCLSvc   is   TRUE,    the
           'break' bit is not set.

           If wfRsvpSenderAdspecCLSvc is  FALSE,  this
           returns FALSE or noSuchValue."
       ::= { wfRsvpSenderEntry 37 }


    wfRsvpSenderAdspecCLHopCount OBJECT-TYPE
        SYNTAX  INTEGER (0..65535)
        ACCESS  read-only
        STATUS  mandatory
        DESCRIPTION

           "If wfRsvpSenderAdspecCLSvc is  TRUE,  this
           is  the  service-specific  override  of the hop
           count general characterization  parameter  from
           the  ADSPEC.   A  return of zero or noSuchValue
           indicates one of the following conditions:

              the invalid bit was set
              the parameter was not present

           If wfRsvpSenderAdspecCLSvc is  FALSE,  this
           returns zero or noSuchValue."
       ::= { wfRsvpSenderEntry 38 }


    wfRsvpSenderAdspecCLPathBw OBJECT-TYPE
        SYNTAX  INTEGER (0..'7FFFFFFF'h)
        ACCESS  read-only
        STATUS      mandatory
        DESCRIPTION
           "If wfRsvpSenderAdspecCLSvc is  TRUE,  this
           is  the  service-specific  override of the path
           bandwidth  estimate  general   characterization
           parameter from the ADSPEC.  A return of zero or
           noSuchValue indicates one of the following con-
           ditions:

              the invalid bit was set
              the parameter was not present

           If wfRsvpSenderAdspecCLSvc is  FALSE,  this
           returns zero or noSuchValue.  UNITS, bits per second"
       ::= { wfRsvpSenderEntry 39 }


    wfRsvpSenderAdspecCLMinLatency OBJECT-TYPE
        SYNTAX  INTEGER
        ACCESS  read-only
        STATUS  mandatory
        DESCRIPTION
           "If wfRsvpSenderAdspecCLSvc is  TRUE,  this
           is the service-specific override of the minimum
           path latency general characterization parameter
           from  the  ADSPEC.  A return of zero or noSuch-
           Value indicates one  of  the  following  condi-
           tions:

              the invalid bit was set
              the parameter was not present

           If wfRsvpSenderAdspecCLSvc is  FALSE,  this
           returns zero or noSuchValue. UNITS, microseconds"
       ::= { wfRsvpSenderEntry 40 }


    wfRsvpSenderAdspecCLMtu OBJECT-TYPE
        SYNTAX  INTEGER (0..65535)
        ACCESS  read-only
        STATUS  mandatory
        DESCRIPTION
           "If wfRsvpSenderAdspecCLSvc is  TRUE,  this
           is  the  service-specific  override of the com-
           posed Maximum Transmission Unit general charac-
           terization parameter from the ADSPEC.  A return
           of zero or noSuchValue  indicates  one  of  the
           following conditions:

              the invalid bit was set
              the parameter was not present

           If wfRsvpSenderAdspecCLSvc is  FALSE,  this
           returns zero or noSuchValue. UNITS, bytes"
       ::= { wfRsvpSenderEntry 41 }


    wfRsvpSenderStatus OBJECT-TYPE
        SYNTAX  INTEGER{
                valid(1),
                invalid(2)
                }
        ACCESS  read-only
        STATUS  mandatory
        DESCRIPTION
           "'valid' for all active  PATH  messages."
       ::= { wfRsvpSenderEntry 42 }


--      The RSVP Reservation Requests Received Table contains the
--      information displayed by receivers regarding their needs with
--      respect to sessions and senders. It is in essence a list of the
--      valid RESV messages that the RSVP Router or Host is receiving.

    wfRsvpResvTable OBJECT-TYPE
        SYNTAX  SEQUENCE OF WfRsvpResvEntry
        ACCESS  not-accessible
        STATUS  mandatory
        DESCRIPTION
                "Information describing the  state  information
                displayed by receivers in RESV messages."
       ::= { wfRsvpGroup 4 }

    wfRsvpResvEntry OBJECT-TYPE
        SYNTAX  WfRsvpResvEntry
        ACCESS  not-accessible
        STATUS  mandatory
        DESCRIPTION
                "Information describing the  state  information
                displayed  by  a single receiver's RESV message
                concerning a single sender."
       INDEX { wfRsvpResvDestAddr, 
               wfRsvpResvProtocol,
               wfRsvpResvDestPort,
               wfRsvpResvSenderAddr, 
               wfRsvpResvPort,
               wfRsvpResvInterface, 
               wfRsvpResvHopAddr}
       ::= { wfRsvpResvTable 1 }

    WfRsvpResvEntry ::= SEQUENCE {
            wfRsvpResvDestAddr            IpAddress,
            wfRsvpResvSenderAddr          IpAddress,
            wfRsvpResvDestAddrLength      INTEGER,
            wfRsvpResvSenderAddrLength    INTEGER,
            wfRsvpResvProtocol            INTEGER,
            wfRsvpResvDestPort            INTEGER,
            wfRsvpResvPort                INTEGER,
            wfRsvpResvHopAddr             IpAddress,
            wfRsvpResvHopLih              INTEGER,
            wfRsvpResvInterface           INTEGER,
            wfRsvpResvService             INTEGER,
            wfRsvpResvTSpecRate           INTEGER,
            wfRsvpResvTSpecPeakRate       INTEGER,
            wfRsvpResvTSpecBurst          INTEGER,
            wfRsvpResvTSpecMinTU          INTEGER,
            wfRsvpResvTSpecMaxTU          INTEGER,
            wfRsvpResvTSpecLevel          INTEGER,
            wfRsvpResvRSpecRate           INTEGER,
            wfRsvpResvRSpecSlack          INTEGER,
            wfRsvpResvInterval            INTEGER,
            wfRsvpResvScope               OCTET STRING,
            wfRsvpResvShared              INTEGER,
            wfRsvpResvExplicit            INTEGER,
            wfRsvpResvRSVPHop             INTEGER,
            wfRsvpResvLastChange          INTEGER,
            wfRsvpResvRSBTimeout          INTEGER,
            wfRsvpResvPolicy              OCTET STRING,
            wfRsvpResvStatus              INTEGER
        }

    wfRsvpResvDestAddr OBJECT-TYPE
        SYNTAX  IpAddress
        ACCESS  read-only
        STATUS  mandatory
        DESCRIPTION
           "The destination address used by all senders in
           this  session.   This object may not be changed
           when the  value  of  the  RowStatus  object  is
           'valid'."
       ::= { wfRsvpResvEntry 1 }


    wfRsvpResvSenderAddr OBJECT-TYPE
        SYNTAX  IpAddress
        ACCESS  read-only
        STATUS  mandatory
        DESCRIPTION
           "The source address of the sender  selected  by
           this  reservation.  The value of all zeroes in-
           dicates 'all senders'.  This object may not  be
           changed  when the value of the RowStatus object
           is 'valid'."
       ::= { wfRsvpResvEntry 2 }

    wfRsvpResvDestAddrLength OBJECT-TYPE
        SYNTAX  INTEGER(0..128)
        ACCESS  read-only
        STATUS  mandatory
        DESCRIPTION
           "The length of the destination address in bits.
           This  is  the CIDR Prefix Length, which for IP4
           hosts and multicast addresses is 32 bits.  This
           object may not be changed when the value of the
           RowStatus object is 'valid'."
       ::= { wfRsvpResvEntry 3 }


    wfRsvpResvSenderAddrLength OBJECT-TYPE
        SYNTAX  INTEGER(0..128)
        ACCESS  read-only
        STATUS  mandatory
        DESCRIPTION
           "The length of the sender's  address  in  bits.
           This  is  the CIDR Prefix Length, which for IP4
           hosts and multicast addresses is 32 bits.  This
           object may not be changed when the value of the
           RowStatus object is 'valid'."
       ::= { wfRsvpResvEntry 4 }


    wfRsvpResvProtocol OBJECT-TYPE
        SYNTAX  INTEGER(1..255)
        ACCESS  read-only
        STATUS  mandatory
        DESCRIPTION
           "The IP Protocol used by  this  session.   This
           object may not be changed when the value of the
           RowStatus object is 'valid'."
       ::= { wfRsvpResvEntry 5 }

    wfRsvpResvDestPort OBJECT-TYPE
        SYNTAX  INTEGER(0..65535)
        ACCESS  read-only
        STATUS  mandatory
        DESCRIPTION
           "The UDP or TCP port number used as a  destina-
           tion  port for all senders in this session.  If
           the  IP   protocol   in   use,   specified   by
           wfRsvpResvProtocol,  is 50 (ESP) or 51 (AH), this
           represents a virtual destination  port  number.
           A  value of zero indicates that the IP protocol
           in use does not have ports.   This  object  may
           not  be changed when the value of the RowStatus
           object is 'valid'."
       ::= { wfRsvpResvEntry 6 }

    wfRsvpResvPort OBJECT-TYPE
        SYNTAX  INTEGER(0..65535)
        ACCESS  read-only
        STATUS  mandatory
        DESCRIPTION
           "The UDP or TCP port number used  as  a  source
           port  for  this sender in this session.  If the
           IP protocol in use, specified by wfRsvpResvProto-
           col  is  50 (ESP) or 51 (AH), this represents a
           generalized port identifier (GPI).  A value  of
           zero indicates that the IP protocol in use does
           not have ports.  This object may not be changed
           when  the  value  of  the  RowStatus  object is
           'valid'."
       ::= { wfRsvpResvEntry 7 }

    wfRsvpResvHopAddr OBJECT-TYPE
        SYNTAX  IpAddress
        ACCESS  read-only
        STATUS  mandatory
        DESCRIPTION
           "The address used by the next RSVP  hop  (which
           may be the ultimate receiver)."
       ::= { wfRsvpResvEntry 8 }

    wfRsvpResvHopLih OBJECT-TYPE
        SYNTAX  INTEGER
        ACCESS  read-only
        STATUS  mandatory
        DESCRIPTION
           "The Logical Interface Handle received from the
           previous  RSVP  hop  (which may be the ultimate
           receiver)."
       ::= { wfRsvpResvEntry 9 }


    wfRsvpResvInterface OBJECT-TYPE
        SYNTAX  INTEGER
        ACCESS  read-only
        STATUS  mandatory
        DESCRIPTION
           "The ifIndex value of the  interface  on  which
           this RESV message was most recently received."
       ::= { wfRsvpResvEntry 10 }

    wfRsvpResvService OBJECT-TYPE
        SYNTAX  INTEGER {
		   controlledDelay(1),
                   guaranteedDelay (2),    -- Guaranteed Delay
		   predictive(3),
                   controlledLoad (5)      -- Controlled Load
                 }
        ACCESS  read-only
        STATUS  mandatory
        DESCRIPTION
           "The QoS Service  classification  requested  by
           the receiver."
       ::= { wfRsvpResvEntry 11 }

    wfRsvpResvTSpecRate OBJECT-TYPE
        SYNTAX  INTEGER(0..'7FFFFFFF'h)
        ACCESS  read-only
        STATUS  mandatory
        DESCRIPTION
           "The Average Bit  Rate  of  the  sender's  data
           stream.   Within  a transmission burst, the ar-
           rival rate may be  as  fast  as  wfRsvpResvTSpec-
           PeakRate  (if  supported by the service model);
           however, averaged across two or more burst  in-
           tervals,    the    rate   should   not   exceed
           wfRsvpResvTSpecRate.

           Note that this is a prediction, often based  on
           the  general  capability  of a type of codec or
           particular encoding; the measured average  rate
           may be significantly lower. 
	   UNITS, bits per second"
       ::= { wfRsvpResvEntry 12 }

    wfRsvpResvTSpecPeakRate OBJECT-TYPE
        SYNTAX  INTEGER(0..'7FFFFFFF'h)
        ACCESS  read-only
        STATUS  mandatory
        DESCRIPTION
           "The Peak Bit Rate of the sender's data stream.
           Traffic  arrival is not expected to exceed this
           rate at any time, apart  from  the  effects  of
           jitter in the network.  If not specified in the
           TSpec, this returns zero or noSuchValue. 
	   UNITS, bits per second"
       ::= { wfRsvpResvEntry 13 }

    wfRsvpResvTSpecBurst OBJECT-TYPE
        SYNTAX  INTEGER(0..'7FFFFFFF'h)
        ACCESS  read-only
        STATUS  mandatory
        DESCRIPTION
           "The size of the largest  burst  expected  from
           the sender at a time.

           If this is less than  the  sender's  advertised
           burst  size, the receiver is asking the network
           to provide flow pacing  beyond  what  would  be
           provided  under normal circumstances. Such pac-
           ing is at the network's option. UNITS, bytes"
       ::= { wfRsvpResvEntry 14 }


    wfRsvpResvTSpecMinTU OBJECT-TYPE
        SYNTAX  INTEGER(0..'7FFFFFFF'h)
        ACCESS  read-only
        STATUS  mandatory
        DESCRIPTION
           "The minimum message size for  this  flow.  The
           policing  algorithm will treat smaller messages
           as though they are this size."
       ::= { wfRsvpResvEntry 15 }

    wfRsvpResvTSpecMaxTU OBJECT-TYPE
        SYNTAX  INTEGER(0..'7FFFFFFF'h)
        ACCESS  read-only
        STATUS  mandatory
        DESCRIPTION
           "The maximum message size for  this  flow.  The
           admission  algorithm  will  reject TSpecs whose
           Maximum Transmission Unit, plus  the  interface
           headers, exceed the interface MTU."
       ::= { wfRsvpResvEntry 16 }

    wfRsvpResvTSpecLevel OBJECT-TYPE
        SYNTAX  INTEGER(1..3)
        ACCESS  read-only
        STATUS  mandatory
        DESCRIPTION
                "If the service is  predictive  or  controlled-
                delay,  this is the service level that is being
                requested.  Otherwise, it is zero, or the agent
                may return noSuchValue."
       ::= { wfRsvpResvEntry 17 }


    wfRsvpResvRSpecRate OBJECT-TYPE
        SYNTAX  INTEGER(0..'7FFFFFFF'h)
        ACCESS  read-only
        STATUS  mandatory
        DESCRIPTION
           "If the requested  service  is  Guaranteed,  as
           specified   by  wfRsvpResvService,  this  is  the
           clearing rate that is being requested.   Other-
           wise,  it  is  zero,  or  the  agent may return
           noSuchValue. UNITS, bits per second"
       ::= { wfRsvpResvEntry 18 }


    wfRsvpResvRSpecSlack OBJECT-TYPE
        SYNTAX  INTEGER
        ACCESS  read-only
        STATUS  mandatory
        DESCRIPTION
           "If the requested  service  is  Guaranteed,  as
           specified by wfRsvpResvService, this is the delay
           slack.  Otherwise, it is zero, or the agent may
           return noSuchValue.UNITS, microseconds"
       ::= { wfRsvpResvEntry 19 }


    wfRsvpResvInterval OBJECT-TYPE
        SYNTAX  INTEGER(0..'7FFFFFFF'h)
        ACCESS  read-only
        STATUS  mandatory
        DESCRIPTION
           "The interval between refresh messages  as  ad-
           vertised by the Next Hop.
	UNITS milliseconds"
       ::= { wfRsvpResvEntry 20 }


    wfRsvpResvScope OBJECT-TYPE
        SYNTAX  OCTET STRING (SIZE(0..65536))
        ACCESS  read-only
        STATUS  mandatory
        DESCRIPTION
           "The contents of the scope object, displayed as
           an  uninterpreted  string  of octets, including
           the object header.  In the absence of  such  an
           object, this should be of zero length.

           If the length  is  non-zero,  this  contains  a
           series of IP4 or IP6 addresses."
       ::= { wfRsvpResvEntry 21 }


    wfRsvpResvShared OBJECT-TYPE
        SYNTAX  INTEGER {
                true(1), 
                false(2)
                }
        ACCESS  read-only
        STATUS  mandatory
        DESCRIPTION
           "If TRUE, a reservation shared among senders is
           requested.  If FALSE, a reservation specific to
           this sender is requested."
       ::= { wfRsvpResvEntry 22 }

    wfRsvpResvExplicit OBJECT-TYPE
        SYNTAX  INTEGER {
                true(1), 
                false(2)
                }
        ACCESS  read-only
        STATUS  mandatory
        DESCRIPTION
           "If TRUE, individual senders are  listed  using
           Filter  Specifications.   If FALSE, all senders
           are implicitly selected.  The Scope Object will
           contain  a list of senders that need to receive
           this reservation request  for  the  purpose  of
           routing the RESV message."
       ::= { wfRsvpResvEntry 23 }


    wfRsvpResvRSVPHop OBJECT-TYPE
        SYNTAX  INTEGER {
                true(1), 
                false(2)
                }
        ACCESS  read-only
        STATUS  mandatory
        DESCRIPTION
           "If TRUE, the node believes that  the  previous
           IP  hop is an RSVP hop.  If FALSE, the node be-
           lieves that the previous IP hop may not  be  an
           RSVP hop."
       ::= { wfRsvpResvEntry 24 }


    wfRsvpResvLastChange OBJECT-TYPE
        SYNTAX  INTEGER
        ACCESS  read-only
        STATUS  mandatory
        DESCRIPTION
           "The time of the last change in  this  reserva-
           tion  request; This is either the first time it
           was received or the time  of  the  most  recent
           change in parameters."
       ::= { wfRsvpResvEntry 25 }


   wfRsvpResvRSBTimeout OBJECT-TYPE
        SYNTAX  INTEGER
        ACCESS  read-only
        STATUS  mandatory
        DESCRIPTION
                 "The remaining lifetime of this reservation's RSB."
        ::= { wfRsvpResvEntry 26 }       


    wfRsvpResvPolicy OBJECT-TYPE
        SYNTAX  OCTET STRING (SIZE(0..65536))
        ACCESS  read-only
        STATUS  mandatory
        DESCRIPTION
           "The contents of the policy  object,  displayed
           as an uninterpreted string of octets, including
           the object header.  In the absence of  such  an
           object, this should be of zero length."
       ::= { wfRsvpResvEntry 27 }


    wfRsvpResvStatus OBJECT-TYPE
        SYNTAX  INTEGER {
                valid(1),
                invalid(2)
                }
        ACCESS  read-only
        STATUS  mandatory
        DESCRIPTION
           "'valid' for all active  RESV  messages."
       ::= { wfRsvpResvEntry 28 }

--      The RSVP Reservation Requests Forwarded Table contains the
--      information displayed by receivers regarding their needs with
--      respect to sessions and senders. It is in essence a list of the
--      valid RESV messages that the RSVP Router or Host is sending
--      to its upstream neighbors.

    wfRsvpResvFwdTable OBJECT-TYPE
        SYNTAX  SEQUENCE OF WfRsvpResvFwdEntry
        ACCESS  not-accessible
        STATUS  mandatory
        DESCRIPTION
                "Information describing the  state  information
                displayed upstream in RESV messages."
       ::= { wfRsvpGroup 5 }

    wfRsvpResvFwdEntry OBJECT-TYPE
        SYNTAX  WfRsvpResvFwdEntry
        ACCESS  not-accessible
        STATUS  mandatory
        DESCRIPTION
                "Information describing the  state  information
                displayed  upstream in an RESV message concern-
                ing a single sender."
       INDEX { wfRsvpResvFwdDestAddr,
               wfRsvpResvFwdProtocol,
               wfRsvpResvFwdDestPort,  
               wfRsvpResvFwdSenderAddr,
               wfRsvpResvFwdPort, 
               wfRsvpResvFwdInterface, 
               wfRsvpResvFwdHopAddr}
       ::= { wfRsvpResvFwdTable 1 }

    WfRsvpResvFwdEntry ::= SEQUENCE {
            wfRsvpResvFwdDestAddr            IpAddress,
            wfRsvpResvFwdSenderAddr          IpAddress,
            wfRsvpResvFwdDestAddrLength      INTEGER,
            wfRsvpResvFwdSenderAddrLength    INTEGER,
            wfRsvpResvFwdProtocol            INTEGER,
            wfRsvpResvFwdDestPort            INTEGER,
            wfRsvpResvFwdPort                INTEGER,
            wfRsvpResvFwdHopAddr             IpAddress,
            wfRsvpResvFwdHopLih              INTEGER,
            wfRsvpResvFwdInterface           INTEGER,
            wfRsvpResvFwdService             INTEGER,
            wfRsvpResvFwdTSpecRate           INTEGER,
            wfRsvpResvFwdTSpecPeakRate       INTEGER,
            wfRsvpResvFwdTSpecBurst          INTEGER,
            wfRsvpResvFwdTSpecMinTU          INTEGER,
            wfRsvpResvFwdTSpecMaxTU          INTEGER,
            wfRsvpResvFwdTSpecLevel          INTEGER,
            wfRsvpResvFwdRSpecRate           INTEGER,
            wfRsvpResvFwdRSpecSlack          INTEGER,
            wfRsvpResvFwdInterval            INTEGER,
            wfRsvpResvFwdScope               OCTET STRING,
            wfRsvpResvFwdShared              INTEGER,
            wfRsvpResvFwdExplicit            INTEGER,
            wfRsvpResvFwdRSVPHop             INTEGER,
            wfRsvpResvFwdLastChange          INTEGER,
            wfRsvpResvFwdPolicy              OCTET STRING,
            wfRsvpResvFwdStatus              INTEGER
        }

    wfRsvpResvFwdDestAddr OBJECT-TYPE
        SYNTAX  IpAddress
        ACCESS  read-only
        STATUS  mandatory
        DESCRIPTION
           "The destination address used by all senders in
           this  session.   This object may not be changed
           when the  value  of  the  RowStatus  object  is
           'valid'."
       ::= { wfRsvpResvFwdEntry 1 }

    wfRsvpResvFwdSenderAddr OBJECT-TYPE
        SYNTAX  IpAddress
        ACCESS  read-only
        STATUS  mandatory
        DESCRIPTION
           "The source address of the sender  selected  by
           this  reservation.  The value of all zeroes in-
           dicates 'all senders'.  This object may not  be
           changed  when the value of the RowStatus object
           is 'valid'."
       ::= { wfRsvpResvFwdEntry 2 }

    wfRsvpResvFwdDestAddrLength OBJECT-TYPE
        SYNTAX  INTEGER(0..128)
        ACCESS  read-only
        STATUS  mandatory
        DESCRIPTION
           "The length of the destination address in bits.
           This  is  the CIDR Prefix Length, which for IP4
           hosts and multicast addresses is 32 bits.  This
           object may not be changed when the value of the
           RowStatus object is 'valid'."
       ::= { wfRsvpResvFwdEntry 3 }

    wfRsvpResvFwdSenderAddrLength OBJECT-TYPE
        SYNTAX  INTEGER(0..128)
        ACCESS  read-only
        STATUS  mandatory
        DESCRIPTION
           "The length of the sender's  address  in  bits.
           This  is  the CIDR Prefix Length, which for IP4
           hosts and multicast addresses is 32 bits.  This
           object may not be changed when the value of the
           RowStatus object is 'valid'."
       ::= { wfRsvpResvFwdEntry 4 }

    wfRsvpResvFwdProtocol OBJECT-TYPE
        SYNTAX  INTEGER(1..255)
        ACCESS  read-only
        STATUS  mandatory
        DESCRIPTION
           "The IP Protocol used by  this  session.   This
           object may not be changed when the value of the
           RowStatus object is 'valid'."
       ::= { wfRsvpResvFwdEntry 5 }

    wfRsvpResvFwdDestPort OBJECT-TYPE
        SYNTAX  INTEGER(0..65535)
        ACCESS  read-only
        STATUS  mandatory
        DESCRIPTION
           "The UDP or TCP port number used as a  destina-
           tion  port for all senders in this session.  If
           the  IP   protocol   in   use,   specified   by
           wfRsvpResvFwdProtocol,  is 50 (ESP) or 51 (AH), this
           represents a virtual destination  port  number.
           A  value of zero indicates that the IP protocol
           in use does not have ports.   This  object  may
           not  be changed when the value of the RowStatus
           object is 'valid'."
       ::= { wfRsvpResvFwdEntry 6 }

    wfRsvpResvFwdPort OBJECT-TYPE
        SYNTAX  INTEGER(0..65535)
        ACCESS  read-only
        STATUS  mandatory
        DESCRIPTION
           "The UDP or TCP port number used  as  a  source
           port  for  this sender in this session.  If the
           IP protocol in use, specified by wfRsvpResvFwdProto-
           col  is  50 (ESP) or 51 (AH), this represents a
           generalized port identifier (GPI).  A value  of
           zero indicates that the IP protocol in use does
           not have ports.  This object may not be changed
           when  the  value  of  the  RowStatus  object is
           'valid'."
       ::= { wfRsvpResvFwdEntry 7 }

    wfRsvpResvFwdHopAddr OBJECT-TYPE
        SYNTAX  IpAddress
        ACCESS  read-only
        STATUS  mandatory
        DESCRIPTION
           "The address used by the next RSVP  hop  (which
           may be the ultimate receiver)."
       ::= { wfRsvpResvFwdEntry 8 }

    wfRsvpResvFwdHopLih OBJECT-TYPE
        SYNTAX  INTEGER
        ACCESS  read-only
        STATUS  mandatory
        DESCRIPTION
           "The Logical Interface Handle received from the
           previous  RSVP  hop  (which may be the ultimate
           receiver)."
       ::= { wfRsvpResvFwdEntry 9 }

    wfRsvpResvFwdInterface OBJECT-TYPE
        SYNTAX  INTEGER
        ACCESS  read-only
        STATUS  mandatory
        DESCRIPTION
           "The ifIndex value of the  interface  on  which
           this RESV message was most recently received."
       ::= { wfRsvpResvFwdEntry 10 }

    wfRsvpResvFwdService OBJECT-TYPE
        SYNTAX  INTEGER {
		   controlledDelay(1),
                   guaranteedDelay (2),    -- Guaranteed Delay
		   predictive(3),
                   controlledLoad (5)      -- Controlled Load
                 }
        ACCESS  read-only
        STATUS  mandatory
        DESCRIPTION
           "The QoS Service  classification  requested  by
           the receiver."
       ::= { wfRsvpResvFwdEntry 11 }

    wfRsvpResvFwdTSpecRate OBJECT-TYPE
        SYNTAX  INTEGER(0..'7FFFFFFF'h)
        ACCESS  read-only
        STATUS  mandatory
        DESCRIPTION
           "The Average Bit  Rate  of  the  sender's  data
           stream.   Within  a transmission burst, the ar-
           rival rate may be  as  fast  as  wfRsvpResvFwdTSpec-
           PeakRate  (if  supported by the service model);
           however, averaged across two or more burst  in-
           tervals,    the    rate   should   not   exceed
           wfRsvpResvFwdTSpecRate.

           Note that this is a prediction, often based  on
           the  general  capability  of a type of codec or
           particular encoding; the measured average  rate
           may be significantly lower. 
	   UNITS, bits per second"
       ::= { wfRsvpResvFwdEntry 12 }

    wfRsvpResvFwdTSpecPeakRate OBJECT-TYPE
        SYNTAX  INTEGER(0..'7FFFFFFF'h)
        ACCESS  read-only
        STATUS  mandatory
        DESCRIPTION
           "The Peak Bit Rate of the sender's data stream.
           Traffic  arrival is not expected to exceed this
           rate at any time, apart  from  the  effects  of
           jitter in the network.  If not specified in the
           TSpec, this returns zero or noSuchValue. 
	   UNITS, bits per second"
       ::= { wfRsvpResvFwdEntry 13 }

    wfRsvpResvFwdTSpecBurst OBJECT-TYPE
        SYNTAX  INTEGER(0..'7FFFFFFF'h)
        ACCESS  read-only
        STATUS  mandatory
        DESCRIPTION
           "The size of the largest  burst  expected  from
           the sender at a time.

           If this is less than  the  sender's  advertised
           burst  size, the receiver is asking the network
           to provide flow pacing  beyond  what  would  be
           provided  under normal circumstances. Such pac-
           ing is at the network's option. UNITS, bytes"
       ::= { wfRsvpResvFwdEntry 14 }

    wfRsvpResvFwdTSpecMinTU OBJECT-TYPE
        SYNTAX  INTEGER(0..'7FFFFFFF'h)
        ACCESS  read-only
        STATUS  mandatory
        DESCRIPTION
           "The minimum message size for  this  flow.  The
           policing  algorithm will treat smaller messages
           as though they are this size."
       ::= { wfRsvpResvFwdEntry 15 }

    wfRsvpResvFwdTSpecMaxTU OBJECT-TYPE
        SYNTAX  INTEGER(0..'7FFFFFFF'h)
        ACCESS  read-only
        STATUS  mandatory
        DESCRIPTION
           "The maximum message size for  this  flow.  The
           admission  algorithm  will  reject TSpecs whose
           Maximum Transmission Unit, plus  the  interface
           headers, exceed the interface MTU."
       ::= { wfRsvpResvFwdEntry 16 }

    wfRsvpResvFwdTSpecLevel OBJECT-TYPE
        SYNTAX  INTEGER(1..3)
        ACCESS  read-only
        STATUS  mandatory
        DESCRIPTION
                "If the service is  predictive  or  controlled-
                delay,  this is the service level that is being
                requested.  Otherwise, it is zero, or the agent
                may return noSuchValue."
       ::= { wfRsvpResvFwdEntry 17 }

    wfRsvpResvFwdRSpecRate OBJECT-TYPE
        SYNTAX  INTEGER(0..'7FFFFFFF'h)
        ACCESS  read-only
        STATUS  mandatory
        DESCRIPTION
           "If the requested  service  is  Guaranteed,  as
           specified   by  wfRsvpResvFwdService,  this  is  the
           clearing rate that is being requested.   Other-
           wise,  it  is  zero,  or  the  agent may return
           noSuchValue. UNITS, bits per second"
       ::= { wfRsvpResvFwdEntry 18 }

    wfRsvpResvFwdRSpecSlack OBJECT-TYPE
        SYNTAX  INTEGER
        ACCESS  read-only
        STATUS  mandatory
        DESCRIPTION
           "If the requested  service  is  Guaranteed,  as
           specified by wfRsvpResvFwdService, this is the delay
           slack.  Otherwise, it is zero, or the agent may
           return noSuchValue.UNITS, microseconds"
       ::= { wfRsvpResvFwdEntry 19 }

    wfRsvpResvFwdInterval OBJECT-TYPE
        SYNTAX  INTEGER(0..'7FFFFFFF'h)
        ACCESS  read-only
        STATUS  mandatory
        DESCRIPTION
           "The interval between refresh messages  as  ad-
           vertised by the Next Hop."
       ::= { wfRsvpResvFwdEntry 20 }

    wfRsvpResvFwdScope OBJECT-TYPE
        SYNTAX  OCTET STRING (SIZE(0..65536))
        ACCESS  read-only
        STATUS  mandatory
        DESCRIPTION
           "The contents of the scope object, displayed as
           an  uninterpreted  string  of octets, including
           the object header.  In the absence of  such  an
           object, this should be of zero length.

           If the length  is  non-zero,  this  contains  a
           series of IP4 or IP6 addresses."
       ::= { wfRsvpResvFwdEntry 21 }

    wfRsvpResvFwdShared OBJECT-TYPE
        SYNTAX  INTEGER {
                true(1), 
                false(2)
                }
        ACCESS  read-only
        STATUS  mandatory
        DESCRIPTION
           "If TRUE, a reservation shared among senders is
           requested.  If FALSE, a reservation specific to
           this sender is requested."
       ::= { wfRsvpResvFwdEntry 22 }

    wfRsvpResvFwdExplicit OBJECT-TYPE
        SYNTAX  INTEGER {
                true(1), 
                false(2)
                }
        ACCESS  read-only
        STATUS  mandatory
        DESCRIPTION
           "If TRUE, individual senders are  listed  using
           Filter  Specifications.   If FALSE, all senders
           are implicitly selected.  The Scope Object will
           contain  a list of senders that need to receive
           this reservation request  for  the  purpose  of
           routing the RESV message."
       ::= { wfRsvpResvFwdEntry 23 }

    wfRsvpResvFwdRSVPHop OBJECT-TYPE
        SYNTAX  INTEGER {
                true(1), 
                false(2)
                }
        ACCESS  read-only
        STATUS  mandatory
        DESCRIPTION
           "If TRUE, the node believes that  the  previous
           IP  hop is an RSVP hop.  If FALSE, the node be-
           lieves that the previous IP hop may not  be  an
           RSVP hop."
       ::= { wfRsvpResvFwdEntry 24 }

    wfRsvpResvFwdLastChange OBJECT-TYPE
        SYNTAX  INTEGER
        ACCESS  read-only
        STATUS  mandatory
        DESCRIPTION
           "The time of the last change in  this  reserva-
           tion  request; This is either the first time it
           was received or the time  of  the  most  recent
           change in parameters."
       ::= { wfRsvpResvFwdEntry 25 }

    wfRsvpResvFwdPolicy OBJECT-TYPE
        SYNTAX  OCTET STRING (SIZE(0..65536))
        ACCESS  read-only
        STATUS  mandatory
        DESCRIPTION
           "The contents of the policy  object,  displayed
           as an uninterpreted string of octets, including
           the object header.  In the absence of  such  an
           object, this should be of zero length."
       ::= { wfRsvpResvFwdEntry 26 }

    wfRsvpResvFwdStatus OBJECT-TYPE
        SYNTAX  INTEGER {
                valid(1),
                invalid(2)
                }
        ACCESS  read-only
        STATUS  mandatory
        DESCRIPTION
           "'valid' for all active  RESV  messages.   This
           object  may  be used to install static RESV in-
           formation or delete RESV information."
       ::= { wfRsvpResvFwdEntry 27 }

--      The RSVP Interface Attributes Database contains the
--      RSVP-specific information for an interface. Information
--      that is shared with other reservation procedures such
--      as ST-II is in the Integrated Interface Attributes
--      Database.


    wfRsvpIfTable OBJECT-TYPE
        SYNTAX  SEQUENCE OF WfRsvpIfEntry
        ACCESS  not-accessible
        STATUS  mandatory
        DESCRIPTION
                "List of configured RSVP interface."
        ::= { wfRsvpGroup 6 }

      
    wfRsvpIfEntry OBJECT-TYPE
        SYNTAX  WfRsvpIfEntry
        ACCESS  not-accessible
        STATUS  mandatory
        DESCRIPTION
                "A description of an RSVP interface"
        INDEX   { wfRsvpIfCct }
        ::= { wfRsvpIfTable 1 }

 
    WfRsvpIfEntry ::= SEQUENCE {
            wfRsvpIfDelete                      INTEGER,
            wfRsvpIfEnable                      INTEGER,
            wfRsvpIfState                       INTEGER,
            wfRsvpIfCct                         INTEGER,
            wfRsvpIfUdpNbrs                     Gauge,
            wfRsvpIfIpNbrs                      Gauge,
            wfRsvpIfNbrs                        Gauge,
            wfRsvpIfRefreshBlockadeMultiple     INTEGER,
    	    wfRsvpIfRefreshMultiple             INTEGER,
            wfRsvpIfTTL                         INTEGER,
            wfRsvpIfRefreshInterval             INTEGER,
            wfRsvpIfRouteDelay                  INTEGER,
            wfRsvpIfUdpRequired                 INTEGER
       }

    wfRsvpIfDelete OBJECT-TYPE
        SYNTAX  INTEGER {
                created(1),
                deleted(2)
            }
        ACCESS  read-write
        STATUS  mandatory
        DESCRIPTION
                "Indicates whether this RSVP If record is to 
                 be deleted or created"
        DEFVAL  { created }
        ::= { wfRsvpIfEntry 1 }

    wfRsvpIfEnable OBJECT-TYPE
        SYNTAX  INTEGER {
                enabled(1),
                disabled(2)
            }
        ACCESS  read-write
        STATUS  mandatory
        DESCRIPTION
           "Indicates whether this RSVP intf record
            is to be enabled or disabled"
        DEFVAL  { enabled }
        ::= { wfRsvpIfEntry 2 }

    wfRsvpIfState OBJECT-TYPE
        SYNTAX  INTEGER {
                up(1),
                down(2),
                init(3),
                notpres(4)
            }
        ACCESS  read-only
        STATUS  mandatory
        DESCRIPTION
                "The current state of the RSVP interface. Invalid 
                 indicates an error in processing the cfg record"
        DEFVAL  { notpres }
        ::= { wfRsvpIfEntry 3 }

    wfRsvpIfCct OBJECT-TYPE
        SYNTAX  INTEGER
        ACCESS  read-only
        STATUS  mandatory
        DESCRIPTION
                "The circuit number of this RSVP interface"
        ::= { wfRsvpIfEntry 4 }

    wfRsvpIfUdpNbrs OBJECT-TYPE
        SYNTAX  Gauge(0..4294967295)
        ACCESS  read-only
        STATUS  mandatory
        DESCRIPTION
                "The number of neighbors perceived to be  using
                only the RSVP UDP Encapsulation."
       ::= { wfRsvpIfEntry 5 }

    wfRsvpIfIpNbrs OBJECT-TYPE
        SYNTAX  Gauge(0..4294967295)
        ACCESS  read-only
        STATUS  mandatory
        DESCRIPTION
                "The number of neighbors perceived to be  using
                only the RSVP IP Encapsulation."
       ::= { wfRsvpIfEntry 6 }

    wfRsvpIfNbrs OBJECT-TYPE
        SYNTAX  Gauge(0..4294967295)
        ACCESS  read-only
        STATUS  mandatory
        DESCRIPTION
                "The number of neighbors currently perceived; this
                will exceed wfRsvpIfIpNbrs + wfRsvpIfUdpNbrs by
                the number of neighbors using both encapsulations."
       ::= { wfRsvpIfEntry 7 }

    wfRsvpIfRefreshBlockadeMultiple OBJECT-TYPE
        SYNTAX  INTEGER (1..65536)
        ACCESS  read-write
        STATUS  mandatory
        DESCRIPTION
           "The value of the RSVP value 'Kb', Which is the
           minimum   number   of  refresh  intervals  that
           blockade state will last once entered."
       DEFVAL      { 4 }
       ::= { wfRsvpIfEntry 8 }

    wfRsvpIfRefreshMultiple OBJECT-TYPE
        SYNTAX  INTEGER (1..65536)
        ACCESS  read-write
        STATUS  mandatory
        DESCRIPTION
           "The value of the RSVP value 'K', which is  the
           number  of  refresh intervals which must elapse
           (minimum) before a PATH or RESV  message  which
           is not being refreshed will be aged out."
       DEFVAL      { 3 }
       ::= { wfRsvpIfEntry 9 }

    wfRsvpIfTTL OBJECT-TYPE
        SYNTAX  INTEGER (0..255)
        ACCESS  read-write
        STATUS  mandatory
        DESCRIPTION
           "The value of SEND_TTL used on  this  interface
           for  messages  this node originates.  If set to
           zero, the node determines  the  TTL  via  other
           means."
       DEFVAL { 0 } -- which is to say, no override
       ::= { wfRsvpIfEntry 10 }

    wfRsvpIfRefreshInterval OBJECT-TYPE
        SYNTAX  INTEGER (2000..2147483647)
        ACCESS  read-write
        STATUS  mandatory
        DESCRIPTION
           "The value of the RSVP value 'R', which is  the
           minimum period between refresh transmissions of
           a given PATH or RESV message on an interface.
           UNITS   milliseconds"
       DEFVAL      { 30000 }
        ::= { wfRsvpIfEntry 11 } 

    wfRsvpIfRouteDelay OBJECT-TYPE
        SYNTAX  INTEGER
        ACCESS  read-write
        STATUS  mandatory
        DESCRIPTION
           "The approximate period from the time  a  route
           is  changed to the time a resulting message ap-
           pears on the interface.
           UNITS   hundredths of a second"
       DEFVAL      { 200 } -- 2 seconds
       ::= { wfRsvpIfEntry 12 }

    wfRsvpIfUdpRequired OBJECT-TYPE
        SYNTAX  INTEGER {
                true(1),
                false(2)
            }
        ACCESS  read-write
        STATUS  mandatory
        DESCRIPTION
                "If TRUE, manual configuration forcees the use
	        of UDP ncapsulation on the interface.  If FALSE,
                UDP encapsulation is only used if wfrsvpIfUdpNbrs
                is not zero."
        DEFVAL  { false }
        ::= { wfRsvpIfEntry 13 }

--
-- wfRsvpIfFlowTable moved to int_serv mib
--

--
--      The RSVP Neighbor Database lists the neighbors the RSVP
--      process currently is receiving messages from.

    wfRsvpNbrTable OBJECT-TYPE
        SYNTAX  SEQUENCE OF WfRsvpNbrEntry
        ACCESS  not-accessible
        STATUS  mandatory
        DESCRIPTION
                "Information describing  the  Neighbors  of  an
                RSVP system."
       ::= { wfRsvpGroup 7 }


    wfRsvpNbrEntry OBJECT-TYPE
        SYNTAX  WfRsvpNbrEntry
        ACCESS  not-accessible
        STATUS  mandatory
        DESCRIPTION
                "Information describing a  single  RSVP  Neigh-
                bor."
        INDEX { wfRsvpNbrCct, 
                wfRsvpNbrAddress }
        ::= { wfRsvpNbrTable 1 }

    WfRsvpNbrEntry ::= SEQUENCE {
        wfRsvpNbrAddress        IpAddress,
        wfRsvpNbrProtocol       INTEGER,
        wfRsvpNbrCct            INTEGER,
	wfRsvpNbrStatus		INTEGER
    }

    wfRsvpNbrAddress OBJECT-TYPE
        SYNTAX  IpAddress
        ACCESS  read-only
        STATUS  mandatory
        DESCRIPTION
            "The IP4 or IP6 Address used by this  neighbor.
           This  object  may not be changed when the value
           of the RowStatus object is 'valid'."
       ::= { wfRsvpNbrEntry 1 }


    wfRsvpNbrProtocol OBJECT-TYPE
        SYNTAX  INTEGER {
                ip(1),
                udp(2),
                both(3)
                }
        ACCESS  read-only
        STATUS  mandatory
        DESCRIPTION
                "The encapsulation being used  by  this  neigh-
                bor."
       ::= { wfRsvpNbrEntry 2 }


    wfRsvpNbrCct OBJECT-TYPE
        SYNTAX  INTEGER
        ACCESS  read-only
        STATUS  mandatory
        DESCRIPTION
                "The circuit number of the interface where
                 the neighbor is learned"
        ::= { wfRsvpNbrEntry 3 }

    wfRsvpNbrStatus OBJECT-TYPE
        SYNTAX  INTEGER {
                valid(1),
                invalid(2)
                }
        ACCESS  read-only
        STATUS  mandatory
        DESCRIPTION
           "'valid' for all neighbors.  This object may be
           used  to  configure neighbors.  In the presence
           of configured neighbors, the implementation may
           (but is not required to) limit the set of valid
           neighbors to those configured."
       ::= { wfRsvpNbrEntry 4 }

--
-- Static RSVP mib
--

    wfSRsvp OBJECT IDENTIFIER ::= { wfRsvpGroup 8 }

    wfSRsvpDelete OBJECT-TYPE
        SYNTAX  INTEGER {
                created(1),
                deleted(2)
            }
        ACCESS  read-write
        STATUS  mandatory
        DESCRIPTION
                "Create/Delete parameter. Default is created.
                Users perform a set operation on this
                object in order to create/delete Static Rsvp."
        DEFVAL  { created }
        ::= { wfSRsvp 1 }

    wfSRsvpDisable OBJECT-TYPE
        SYNTAX  INTEGER {
                enabled(1),
                disabled(2)
            }
        ACCESS  read-write
        STATUS  mandatory
        DESCRIPTION
                "Enable/Disable parameter. Default is enabled.
                Users perform a set operation on this
                object in order to enable/disable Static Rsvp."
        DEFVAL  { enabled }
        ::= { wfSRsvp 2 }

    wfSRsvpState OBJECT-TYPE
        SYNTAX  INTEGER {
                up(1),
                down(2),
                init(3),
                notpres(4)
            }
        ACCESS  read-only
        STATUS  mandatory
        DESCRIPTION
                "The current state of Static Rsvp."
        DEFVAL  { notpres }
        ::= { wfSRsvp 3 }

    wfSRsvpSoloistSlot OBJECT-TYPE
        SYNTAX  INTEGER(0..14)
        ACCESS  read-write
        STATUS  mandatory
        DESCRIPTION
                "Slot for which slot Static RSVP Soloist is
                eligible to run on. Slots can be 1-14."
        DEFVAL  { 2 }
        ::= { wfSRsvp 4 }

    wfSRsvpInfoLogFilter OBJECT-TYPE
        SYNTAX  INTEGER
        ACCESS  read-write
        STATUS  mandatory
        DESCRIPTION
                "Turn Static RSVP log ON or OFF for informational
                 and warning messages. There is only 
                 RSVP_LOG_RIF_PROCESSING            0x0001 - RIF processing.
                 RSVP_LOG_SOLO_PROCESSING           0x0002 - SOLO processing.
                 RSVP_LOG_ROUTE_INTF_PROCESSING     0x0004 - ROUTE interface processing.
                 RSVP_LOG_MERGE_PROCESSING          0x0008 - MERGE processing.
                 RSVP_LOG_DB_PROCESSING             0x0010 - database access processing.
                 RSVP_LOG_INTSERV_INTF_PROCESSING   0x0020 - INTSERV interface processing.
                 RSVP_LOG_CRM_INTF_PROCESSING       0x0040 - CRM interface processing.
                 RSVP_LOG_STATIC_RSVP               0x0080 - STATIC RSVP processing.
                 RSVP_LOG_CONTROL_PROCESSING        0x0100 - CONTROL processing.
                 RSVP_LOG_MAP_VEC_PROCESSING        0x0200 - MAP VECTOR processing.
                 RSVP_LOG_PROXY_PROCESSING          0x0400 - RSVP MIB PROXY processing.
                 RSVP_LOG_REFRESH_PROCESSING        0x0800 - Path/Resv Refresh processing."
        DEFVAL { 0 }
        ::= { wfSRsvp 5 }

    wfSRsvpDebugLogFilter OBJECT-TYPE
        SYNTAX  INTEGER
        ACCESS  read-write
        STATUS  mandatory
        DESCRIPTION
                "Turn Static RSVP log ON or OFF for debugging
                 messages. The bit position is used to
                 represent a RSVP module:
                 RSVP_LOG_RIF_PROCESSING            0x0001 - RIF processing.
                 RSVP_LOG_SOLO_PROCESSING           0x0002 - SOLO processing.
                 RSVP_LOG_ROUTE_INTF_PROCESSING     0x0004 - ROUTE interface processing.
                 RSVP_LOG_MERGE_PROCESSING          0x0008 - MERGE processing.
                 RSVP_LOG_DB_PROCESSING             0x0010 - database access processing.
                 RSVP_LOG_INTSERV_INTF_PROCESSING   0x0020 - INTSERV interface processing.
                 RSVP_LOG_CRM_INTF_PROCESSING       0x0040 - CRM interface processing.
                 RSVP_LOG_STATIC_RSVP               0x0080 - STATIC RSVP processing.
                 RSVP_LOG_CONTROL_PROCESSING        0x0100 - CONTROL processing.
                 RSVP_LOG_MAP_VEC_PROCESSING        0x0200 - MAP VECTOR processing.
                 RSVP_LOG_PROXY_PROCESSING          0x0400 - RSVP MIB PROXY processing.
                 RSVP_LOG_REFRESH_PROCESSING        0x0800 - Path/Resv Refresh processing."
        DEFVAL { 0 }
        ::= { wfSRsvp 6 }

    wfSRsvpTraceLogFilter OBJECT-TYPE
        SYNTAX  INTEGER
        ACCESS  read-write
        STATUS  mandatory
        DESCRIPTION
                "Turn RSVP log ON or OFF for RSVP trace
                 messages. The bit position is used to
                 represent a RSVP module:
                 RSVP_LOG_RIF_PROCESSING            0x0001 - RIF processing.
                 RSVP_LOG_SOLO_PROCESSING           0x0002 - SOLO processing.
                 RSVP_LOG_ROUTE_INTF_PROCESSING     0x0004 - ROUTE interface processing.
                 RSVP_LOG_MERGE_PROCESSING          0x0008 - MERGE processing.
                 RSVP_LOG_DB_PROCESSING             0x0010 - database access processing.
                 RSVP_LOG_INTSERV_INTF_PROCESSING   0x0020 - INTSERV interface processing.
                 RSVP_LOG_CRM_INTF_PROCESSING       0x0040 - CRM interface processing.
                 RSVP_LOG_STATIC_RSVP               0x0080 - STATIC RSVP processing.
                 RSVP_LOG_CONTROL_PROCESSING        0x0100 - CONTROL processing.
                 RSVP_LOG_MAP_VEC_PROCESSING        0x0200 - MAP VECTOR processing.
                 RSVP_LOG_PROXY_PROCESSING          0x0400 - RSVP MIB PROXY processing.
                 RSVP_LOG_REFRESH_PROCESSING        0x0800 - Path/Resv Refresh processing."
        DEFVAL { 0 }
        ::= { wfSRsvp 7 }

    wfSRsvpRefreshInterval OBJECT-TYPE
        SYNTAX  INTEGER (2000..2147483647)
        ACCESS  read-write
        STATUS  mandatory
        DESCRIPTION
           "The value of the RSVP value 'R', which is  the
           minimum period between refresh transmissions of
           a given STATIC PATH or STATIC RESV message.
        UNITS milliseconds"
       	DEFVAL      { 30000 }
        ::= { wfSRsvp 8 } 

    wfSRsvpTotalSenders OBJECT-TYPE
        SYNTAX  Gauge(0..4294967295)
        ACCESS  read-only
        STATUS  mandatory
        DESCRIPTION
                "The total number of Static Sender (PATH) states in the router."
        ::= { wfSRsvp 9 }        

    wfSRsvpTotalReservations OBJECT-TYPE
        SYNTAX  Gauge(0..4294967295)
        ACCESS  read-only
        STATUS  mandatory
        DESCRIPTION
                "The total number of Static Reservation (RESV) states in the router."
        ::= { wfSRsvp 10 }        

--
-- Static Sender Table
--
    wfSRsvpSenderTable OBJECT-TYPE
        SYNTAX  SEQUENCE OF WfSRsvpSenderEntry
        ACCESS  not-accessible
        STATUS  mandatory
        DESCRIPTION
                "Information describing the  state  information
                displayed by senders statically configured."
       ::= { wfRsvpGroup 9 }

    wfSRsvpSenderEntry OBJECT-TYPE
        SYNTAX  WfSRsvpSenderEntry
        ACCESS  not-accessible
        STATUS  mandatory
        DESCRIPTION
                "Information describing the  state  information
                used to create a sender thru configuration."
       INDEX    { wfSRsvpSenderNumber }
       ::= { wfSRsvpSenderTable 1 }

   WfSRsvpSenderEntry ::= SEQUENCE {
	wfSRsvpSenderCreate        		INTEGER,
        wfSRsvpSenderEnable        		INTEGER,
        wfSRsvpSenderStatus         		INTEGER,
        wfSRsvpSenderNumber                     INTEGER,
	wfSRsvpSenderDestReplicate		INTEGER,
	wfSRsvpSenderReplicate			INTEGER,
	wfSRsvpSenderIntegrity			OCTET STRING,
        wfSRsvpSenderDestAddr			IpAddress,
	wfSRsvpSenderAddr                  	IpAddress,
        wfSRsvpSenderDestAddrLength        	INTEGER,
        wfSRsvpSenderAddrLength            	INTEGER,
        wfSRsvpSenderProtocol              	INTEGER,
        wfSRsvpSenderDestPort        		INTEGER,
        wfSRsvpSenderPort        		INTEGER,
        wfSRsvpSenderHopAddr               	IpAddress,
        wfSRsvpSenderHopLih                	INTEGER,
        wfSRsvpSenderInterface             	INTEGER,
	wfSRsvpSenderTimeValue			INTEGER,
        wfSRsvpSenderTSpecRate        		INTEGER,
        wfSRsvpSenderTSpecPeakRate        	INTEGER,
        wfSRsvpSenderTSpecBurst    		INTEGER,
        wfSRsvpSenderTSpecMinTU            	INTEGER,
        wfSRsvpSenderTSpecMaxTU            	INTEGER,
        wfSRsvpSenderPolicy                     OCTET STRING,
	wfSRsvpSenderAdspec                     INTEGER,
        wfSRsvpSenderAdspecBreak                INTEGER,
        wfSRsvpSenderAdspecHopCount             INTEGER,
        wfSRsvpSenderAdspecPathBw               INTEGER,
        wfSRsvpSenderAdspecMinLatency           INTEGER,
        wfSRsvpSenderAdspecMtu                  INTEGER,
        wfSRsvpSenderAdspecGSSvc        	INTEGER,
        wfSRsvpSenderAdspecGSBreak      	INTEGER,
        wfSRsvpSenderAdspecGSCtot       	INTEGER,
        wfSRsvpSenderAdspecGSDtot       	INTEGER,
        wfSRsvpSenderAdspecGSCsum       	INTEGER,
        wfSRsvpSenderAdspecGSDsum       	INTEGER,
	wfSRsvpSenderAdspecGSOverrides		INTEGER,
        wfSRsvpSenderAdspecGSHopCount   	INTEGER,
        wfSRsvpSenderAdspecGSPathBw     	INTEGER,
        wfSRsvpSenderAdspecGSMinLatency 	INTEGER,
        wfSRsvpSenderAdspecGSMtu        	INTEGER,
        wfSRsvpSenderAdspecCLSvc          	INTEGER,
        wfSRsvpSenderAdspecCLBreak        	INTEGER,
	wfSRsvpSenderAdspecCLOverrides		INTEGER,
        wfSRsvpSenderAdspecCLHopCount     	INTEGER,
        wfSRsvpSenderAdspecCLPathBw       	INTEGER,
        wfSRsvpSenderAdspecCLMinLatency   	INTEGER,
        wfSRsvpSenderAdspecCLMtu          	INTEGER
    }


    wfSRsvpSenderCreate OBJECT-TYPE
        SYNTAX  INTEGER {
                create(1),
                delete(2)
            }
        ACCESS  read-write
        STATUS  mandatory
        DESCRIPTION
                "Whether to Delete this sender PSB"
        DEFVAL  { create }
        ::= { wfSRsvpSenderEntry 1 }

    wfSRsvpSenderEnable OBJECT-TYPE
        SYNTAX  INTEGER {
                enabled(1),
                disabled(2)
            }
        ACCESS  read-write
        STATUS  mandatory
        DESCRIPTION
                "Whether to Disable this Sender PSB"
        DEFVAL  { enabled }
        ::= { wfSRsvpSenderEntry 2 }

    wfSRsvpSenderStatus OBJECT-TYPE
        SYNTAX  INTEGER {
                valid(1),
                invalid(2),
                notpres(3)
            }
        ACCESS  read-only
        STATUS  mandatory
        DESCRIPTION
                "Whether this Static PSB is valid or not"
        DEFVAL  { notpres }
        ::= { wfSRsvpSenderEntry 3 }

    wfSRsvpSenderNumber OBJECT-TYPE
        SYNTAX  INTEGER
        ACCESS  read-only
        STATUS  mandatory
        DESCRIPTION
           "The number of this static sender.  This is for
           SNMP Indexing  purposes  only and has no relation to
           any protocol value."
       ::= { wfSRsvpSenderEntry 4 }

    wfSRsvpSenderDestReplicate OBJECT-TYPE
        SYNTAX  INTEGER
        ACCESS  read-write
        STATUS  mandatory
        DESCRIPTION
                "Number of sessions for which this static path state should
		be replicated. For each replication, wfSRsvpSenderDestAddr 
		will be	incremented by one."
        DEFVAL  { 0 }
        ::= { wfSRsvpSenderEntry 5 }

    wfSRsvpSenderReplicate OBJECT-TYPE
        SYNTAX  INTEGER
        ACCESS  read-write
        STATUS  mandatory
        DESCRIPTION
                "Number of senders for which this static path state should
		be replicated. For each replication, wfSRsvpSenderAddr
		will be incremented by one."
        DEFVAL  { 0 }
        ::= { wfSRsvpSenderEntry 6 }

    wfSRsvpSenderIntegrity OBJECT-TYPE
        SYNTAX  OCTET STRING (SIZE(0..65536))
        ACCESS  read-write
        STATUS  mandatory
        DESCRIPTION
           "The contents of the integrity object, displayed
           as an uninterpreted string of octets, including
           the object header.  In the absence of  such  an
           object, this should be of zero length."
	::= { wfSRsvpSenderEntry 7 }

    wfSRsvpSenderDestAddr OBJECT-TYPE
        SYNTAX  IpAddress
        ACCESS  read-write
        STATUS  mandatory
        DESCRIPTION
           "The destination IP address used by all senders in
           this  session.   This object may not be changed
           when the  value  of  the  Status  object  is
           'valid'."
       ::= { wfSRsvpSenderEntry 8 }


    wfSRsvpSenderAddr OBJECT-TYPE
        SYNTAX  IpAddress
        ACCESS  read-write
        STATUS  mandatory
        DESCRIPTION
           "The source address used by this sender in this
           session.   This  object may not be changed when
           the value of the Status object is 'valid'."
       ::= { wfSRsvpSenderEntry 9 }


    wfSRsvpSenderDestAddrLength OBJECT-TYPE
        SYNTAX  INTEGER(0..128)
        ACCESS  read-write
        STATUS  mandatory
        DESCRIPTION
           "The length of the destination address in bits.
           This  is  the CIDR Prefix Length, which for IP4
           hosts and multicast addresses is 32 bits.  This
           object may not be changed when the value of the
           Status object is 'valid'."
	DEFVAL { 32 }
       	::= { wfSRsvpSenderEntry 10 }


    wfSRsvpSenderAddrLength OBJECT-TYPE
        SYNTAX  INTEGER(0..128)
        ACCESS  read-write
        STATUS  mandatory
        DESCRIPTION
           "The length of the sender's  address  in  bits.
           This  is  the CIDR Prefix Length, which for IP4
           hosts and multicast addresses is 32 bits.  This
           object may not be changed when the value of the
           Status object is 'valid'."
	DEFVAL { 32 }
       	::= { wfSRsvpSenderEntry 11 }


    wfSRsvpSenderProtocol OBJECT-TYPE
        SYNTAX  INTEGER(1..255)
        ACCESS  read-write
        STATUS  mandatory
        DESCRIPTION
           "The IP Protocol used by  this  session.   This
           object may not be changed when the value of the
           Status object is 'valid'."
	DEFVAL { 17 }
       	::= { wfSRsvpSenderEntry 12 }


    wfSRsvpSenderDestPort OBJECT-TYPE
        SYNTAX  INTEGER (0..65536)
        ACCESS  read-write
        STATUS  mandatory
        DESCRIPTION
           "The UDP or TCP port number used as a  destina-
           tion  port for all senders in this session.  If
           the IP protocol in use, specified  by  rsvpSen-
           derProtocol,  is  50  (ESP)  or  51  (AH), this
           represents a virtual destination  port  number.
           A  value of zero indicates that the IP protocol
           in use does not have ports.   This  object  may
           not  be changed when the value of the Status
           object is 'valid'."
       ::= { wfSRsvpSenderEntry 13 }


    wfSRsvpSenderPort OBJECT-TYPE
        SYNTAX  INTEGER (0..65536)
        ACCESS  read-write
        STATUS  mandatory
        DESCRIPTION
           "The UDP or TCP port number used  as  a  source
           port  for  this sender in this session.  If the
           IP protocol in use, specified by RsvpStaticSenderPro-
           tocol is 50 (ESP) or 51 (AH), this represents a
           generalized port identifier (GPI).  A value  of
           zero indicates that the IP protocol in use does
           not have ports.  This object may not be changed
           when  the  value  of  the  Status  object is
           'valid'."
       ::= { wfSRsvpSenderEntry 14 }


    wfSRsvpSenderHopAddr OBJECT-TYPE
        SYNTAX  IpAddress
        ACCESS  read-write
        STATUS  mandatory
        DESCRIPTION
           "The address used  by  the  previous  RSVP  hop
           (which may be the original sender)."
       ::= { wfSRsvpSenderEntry 15 }


    wfSRsvpSenderHopLih OBJECT-TYPE
        SYNTAX  INTEGER
        ACCESS  read-write
        STATUS  mandatory
        DESCRIPTION
           "The Logical Interface Handle used by the  pre-
           vious  RSVP  hop  (which  may  be  the original
           sender)."
       ::= { wfSRsvpSenderEntry 16 }


    wfSRsvpSenderInterface OBJECT-TYPE
        SYNTAX  INTEGER
        ACCESS  read-write
        STATUS  mandatory
        DESCRIPTION
           "The ifIndex value of the  interface  on  which
           this PATH message was most recently received."
       ::= { wfSRsvpSenderEntry 17 }

    wfSRsvpSenderTimeValue OBJECT-TYPE
        SYNTAX  INTEGER (0..'7FFFFFFF'h)
        ACCESS  read-write
        STATUS  mandatory
        DESCRIPTION
           "The value of the RSVP value 'R', which is  the
           minimum period between refresh transmissions of
           a given PATH or RESV message on an interface.
           UNITS   milliseconds"
       	DEFVAL      { 30000 }
        ::= { wfSRsvpSenderEntry 18 } 

    wfSRsvpSenderTSpecRate OBJECT-TYPE
        SYNTAX  INTEGER(0..'7FFFFFFF'h)
        ACCESS  read-write
        STATUS  mandatory
        DESCRIPTION
           "The Average Bit  Rate  of  the  sender's  data
           stream.   Within  a transmission burst, the ar-
           rival rate may be as fast  as  RsvpStaticSenderTSpec-
           PeakRate  (if  supported by the service model);
           however, averaged across two or more burst  in-
           tervals,  the  rate  should not exceed rsvpSen-
           derTSpecRate.

           Note that this is a prediction, often based  on
           the  general  capability  of a type of codec or
           particular encoding; the measured average  rate
           may be significantly lower.

           UNITS, bits per second"
       ::= { wfSRsvpSenderEntry 19 }

    wfSRsvpSenderTSpecPeakRate OBJECT-TYPE
        SYNTAX  INTEGER(0..'7FFFFFFF'h)
        ACCESS  read-write
        STATUS  mandatory
        DESCRIPTION
           "The Peak Bit Rate of the sender's data stream.
           Traffic  arrival is not expected to exceed this
           rate at any time, apart  from  the  effects  of
           jitter in the network.  If not specified in the
           TSpec, this returns zero or noSuchValue.
           UNITS, bits per second"
       ::= { wfSRsvpSenderEntry 20 }


    wfSRsvpSenderTSpecBurst OBJECT-TYPE
        SYNTAX  INTEGER(0..'7FFFFFFF'h)
        ACCESS  read-write
        STATUS  mandatory
        DESCRIPTION
           "The size of the largest  burst  expected  from
           the sender at a time.
           UNITS, bytes"
       ::= { wfSRsvpSenderEntry 21 }


    wfSRsvpSenderTSpecMinTU OBJECT-TYPE
        SYNTAX  INTEGER(0..'7FFFFFFF'h)
        ACCESS  read-write
        STATUS  mandatory
        DESCRIPTION
           "The minimum message size for  this  flow.  The
           policing  algorithm will treat smaller messages
           as though they are this size."
       ::= { wfSRsvpSenderEntry 22 }


    wfSRsvpSenderTSpecMaxTU OBJECT-TYPE
        SYNTAX  INTEGER(0..'7FFFFFFF'h)
        ACCESS  read-write
        STATUS  mandatory
        DESCRIPTION
           "The maximum message size for  this  flow.  The
           admission  algorithm  will  reject TSpecs whose
           Maximum Transmission Unit, plus  the  interface
           headers, exceed the interface MTU."
       ::= { wfSRsvpSenderEntry 23 }

    wfSRsvpSenderPolicy OBJECT-TYPE
        SYNTAX  OCTET STRING (SIZE(0..65536))
        ACCESS  read-write
        STATUS  mandatory
        DESCRIPTION
           "The contents of the policy  object,  displayed
           as an uninterpreted string of octets, including
           the object header.  In the absence of  such  an
           object, this should be of zero length."
       ::= { wfSRsvpSenderEntry 24 }

    wfSRsvpSenderAdspec OBJECT-TYPE
        SYNTAX  INTEGER {
                true(1), false(2)
                }
        ACCESS  read-write
        STATUS  mandatory
        DESCRIPTION
           "If TRUE, an adspec is sent, if FALSE,
	    no adspec is sent."
	DEFVAL { true }
       	::= { wfSRsvpSenderEntry 25 }

    wfSRsvpSenderAdspecBreak OBJECT-TYPE
        SYNTAX  INTEGER {
                true(1), false(2)
                }
        ACCESS  read-write
        STATUS  mandatory
        DESCRIPTION
           "The global break bit general  characterization
           parameter  from  the ADSPEC.  If TRUE, at least
           one non-IS hop was detected in  the  path.   If
           FALSE, no non-IS hops were detected."
	DEFVAL { false }
       	::= { wfSRsvpSenderEntry 26 }


    wfSRsvpSenderAdspecHopCount OBJECT-TYPE
        SYNTAX  INTEGER (0..'7FFFFFFF'h)
        ACCESS  read-write
        STATUS  mandatory
        DESCRIPTION
           "The hop count general characterization parame-
           ter  from  the  ADSPEC.   A  return  of zero or
           noSuchValue indicates one of the following con-
           ditions:

              the invalid bit was set
              the parameter was not present"
       ::= { wfSRsvpSenderEntry 27 }

    wfSRsvpSenderAdspecPathBw OBJECT-TYPE
        SYNTAX  INTEGER(0..'7FFFFFFF'h)
        ACCESS  read-write
        STATUS  mandatory
        DESCRIPTION
           "The path bandwidth estimate general character-
           ization parameter from the ADSPEC.  A return of
           zero or noSuchValue indicates one of  the  fol-
           lowing conditions:

              the invalid bit was set
              the parameter was not present

           UNITS, bits per second"
       ::= { wfSRsvpSenderEntry 28 }


    wfSRsvpSenderAdspecMinLatency OBJECT-TYPE
        SYNTAX  INTEGER(0..'7FFFFFFF'h)
        ACCESS  read-write
        STATUS  mandatory
        DESCRIPTION
           "The minimum path latency general characteriza-
           tion  parameter  from  the ADSPEC.  A return of
           zero or noSuchValue indicates one of  the  fol-
           lowing conditions:

              the invalid bit was set
              the parameter was not present

           UNITS, microseconds"
       ::= { wfSRsvpSenderEntry 29 }


    wfSRsvpSenderAdspecMtu OBJECT-TYPE
        SYNTAX  INTEGER (0..'7FFFFFFF'h)
        ACCESS  read-write
        STATUS  mandatory
        DESCRIPTION
           "The composed Maximum Transmission Unit general
           characterization  parameter from the ADSPEC.  A
           return of zero or noSuchValue indicates one  of
           the following conditions:

              the invalid bit was set
              the parameter was not present

           UNITS, bytes"
       ::= { wfSRsvpSenderEntry 30 }


    wfSRsvpSenderAdspecGSSvc OBJECT-TYPE
        SYNTAX  INTEGER {
                true(1), false(2)
                }
        ACCESS  read-write
        STATUS  mandatory
        DESCRIPTION
           "If TRUE, the ADSPEC contains a Guaranteed Ser-
           vice  fragment.   If FALSE, the ADSPEC does not
           contain a Guaranteed Service fragment."
	DEFVAL { false }
       	::= { wfSRsvpSenderEntry 31 }


    wfSRsvpSenderAdspecGSBreak OBJECT-TYPE
        SYNTAX  INTEGER {
                true(1), false(2)
                }
        ACCESS  read-write
        STATUS      mandatory
        DESCRIPTION
           "If TRUE, the Guaranteed Service  fragment  has
           its  'break'  bit  set,  indicating that one or
           more nodes along the path do  not  support  the
           guaranteed  service.   If  FALSE,  and
           wfSRrsvpSenderAdspecGSSvc is TRUE, the 'break'
           bit is not set.

           If wfSRsvpSenderAdspecGSSvc is FALSE, this
           returns FALSE or noSuchValue."
	DEFVAL { true }
	::= { wfSRsvpSenderEntry 32 }


    wfSRsvpSenderAdspecGSCtot OBJECT-TYPE
        SYNTAX  INTEGER (0..'7FFFFFFF'h)
        ACCESS  read-write
        STATUS  mandatory
        DESCRIPTION

           "If wfSRsvpSenderAdspecGSSvc is TRUE, this
           is   the  end-to-end  composed  value  for  the
           guaranteed service 'C' parameter.  A return  of
           zero  or  noSuchValue indicates one of the fol-
           lowing conditions:

              the invalid bit was set
              the parameter was not present

           If wfSRsvpSenderAdspecGSSvc is FALSE, this
           returns zero or noSuchValue.
           UNITS, bytes"
	DEFVAL { 0 }
       	::= { wfSRsvpSenderEntry 33 }


    wfSRsvpSenderAdspecGSDtot OBJECT-TYPE
        SYNTAX  INTEGER (0..'7FFFFFFF'h)
        ACCESS  read-write
        STATUS  mandatory
        DESCRIPTION
           "If wfSRsvpSenderAdspecGSSvc is TRUE, this
           is   the  end-to-end  composed  value  for  the
           guaranteed service 'D' parameter.  A return  of
           zero  or  noSuchValue indicates one of the fol-
           lowing conditions:

              the invalid bit was set
              the parameter was not present

           If wfSRsvpSenderAdspecGSSvc is FALSE, this
           returns zero or noSuchValue.
           UNITS, microseconds"
	DEFVAL { 0 }
       	::= { wfSRsvpSenderEntry 34 }


    wfSRsvpSenderAdspecGSCsum OBJECT-TYPE
        SYNTAX  INTEGER (0..'7FFFFFFF'h)
        ACCESS  read-write
        STATUS  mandatory
        DESCRIPTION
           "If wfSRsvpSenderAdspecGSSvc is TRUE, this
           is  the  composed value for the guaranteed ser-
           vice 'C' parameter  since  the  last  reshaping
           point.   A  return of zero or noSuchValue indi-
           cates one of the following conditions:

              the invalid bit was set
              the parameter was not present

           If wfSRsvpSenderAdspecGSSvc is FALSE, this
           returns zero or noSuchValue.
           UNITS, bytes"
	DEFVAL { 0 }
       	::= { wfSRsvpSenderEntry 35 }


    wfSRsvpSenderAdspecGSDsum OBJECT-TYPE
        SYNTAX  INTEGER (0..'7FFFFFFF'h)
        ACCESS  read-write
        STATUS  mandatory
        DESCRIPTION
           "If wfSRsvpSenderAdspecGSSvc is TRUE, this
           is  the  composed value for the guaranteed ser-
           vice 'D' parameter  since  the  last  reshaping
           point.   A  return of zero or noSuchValue indi-
           cates one of the following conditions:

              the invalid bit was set
              the parameter was not present

           If wfSRsvpSenderAdspecGSSvc is FALSE, this
           returns zero or noSuchValue.
           UNITS, microseconds"
	DEFVAL { 0 }
       	::= { wfSRsvpSenderEntry 36 }

    wfSRsvpSenderAdspecGSOverrides OBJECT-TYPE
	SYNTAX  INTEGER {
		true(1), false(2)
		}
	ACCESS  read-write
	STATUS  mandatory
	DESCRIPTION
	   "If TRUE, the ADSPEC contains general parameter
	    overrides for guaranteed service. If FALSE, the 
	    ADSPEC does not contains guaranteed service 
	    overrides.
	    Note, if TRUE, ALL override parameters will be 
	    included and must be specified."
	DEFVAL { false }
	::= { wfSRsvpSenderEntry 37 }
	
    wfSRsvpSenderAdspecGSHopCount OBJECT-TYPE
        SYNTAX  INTEGER (0..'7FFFFFFF'h)
        ACCESS  read-write
        STATUS  mandatory
        DESCRIPTION

           "If wfSRsvpSenderAdspecGSSvc is TRUE, this
           is  the  service-specific  override  of the hop
           count general characterization  parameter  from
           the  ADSPEC.   A  return of zero or noSuchValue
           indicates one of the following conditions:

              the invalid bit was set
              the parameter was not present

           If wfSRsvpSenderAdspecGSSvc is FALSE, this
           returns zero or noSuchValue."
	DEFVAL { 0 }
       	::= { wfSRsvpSenderEntry 38 }


    wfSRsvpSenderAdspecGSPathBw OBJECT-TYPE
        SYNTAX  INTEGER(0..'7FFFFFFF'h)
        ACCESS  read-write
        STATUS  mandatory
        DESCRIPTION
           "If wfSRsvpSenderAdspecGSSvc is TRUE, this
           is  the  service-specific  override of the path
           bandwidth  estimate  general   characterization
           parameter from the ADSPEC.  A return of zero or
           noSuchValue indicates one of the following con-
           ditions:

              the invalid bit was set
              the parameter was not present

           If wfSRsvpSenderAdspecGSSvc is FALSE, this
           returns zero or noSuchValue.
           UNITS, bits per second"
	DEFVAL { 0 }
       	::= { wfSRsvpSenderEntry 39 }


    wfSRsvpSenderAdspecGSMinLatency OBJECT-TYPE
        SYNTAX  INTEGER (0..'7FFFFFFF'h)
        ACCESS  read-write
        STATUS  mandatory
        DESCRIPTION
           "If wfSRsvpSenderAdspecGSSvc is TRUE, this
           is the service-specific override of the minimum
           path latency general characterization parameter
           from  the  ADSPEC.  A return of zero or noSuch-
           Value indicates one  of  the  following  condi-
           tions:

              the invalid bit was set
              the parameter was not present

           If wfSRsvpSenderAdspecGSSvc is FALSE, this
           returns zero or noSuchValue. UNITS, microseconds"
	DEFVAL { 0 }
       	::= { wfSRsvpSenderEntry 40 }


    wfSRsvpSenderAdspecGSMtu OBJECT-TYPE
        SYNTAX  INTEGER (0..'7FFFFFFF'h)
        ACCESS  read-write
        STATUS  mandatory
        DESCRIPTION
           "If wfSRsvpSenderAdspecGSSvc is TRUE, this
           is  the  service-specific  override of the com-
           posed Maximum Transmission Unit general charac-
           terization parameter from the ADSPEC.  A return
           of zero or noSuchValue  indicates  one  of  the
           following conditions:

              the invalid bit was set
              the parameter was not present

           If wfSRsvpSenderAdspecGSSvc is FALSE, this
           returns zero or noSuchValue. UNITS, bytes"
	DEFVAL { 0 }
       	::= { wfSRsvpSenderEntry 41 }


    wfSRsvpSenderAdspecCLSvc OBJECT-TYPE
        SYNTAX  INTEGER {
                true(1), false(2)
                }
        ACCESS  read-write
        STATUS  mandatory
        DESCRIPTION
           "If TRUE, the ADSPEC contains a Controlled Load
           Service  fragment.   If  FALSE, the ADSPEC does
           not contain a  Controlled  Load  Service  frag-
           ment."
	DEFVAL { true }
       	::= { wfSRsvpSenderEntry 42 }


    wfSRsvpSenderAdspecCLBreak OBJECT-TYPE
        SYNTAX  INTEGER {
                true(1), false(2)
                }
        ACCESS  read-write
        STATUS  mandatory
        DESCRIPTION
           "If TRUE, the Controlled Load Service  fragment
           has its 'break' bit set, indicating that one or
           more nodes along the path do  not  support  the
           controlled   load   service.    If  FALSE,  and
           wfSRsvpSenderAdspecCLSvc   is   TRUE,    the
           'break' bit is not set.

           If wfSRsvpSenderAdspecCLSvc is  FALSE,  this
           returns FALSE or noSuchValue."
	DEFVAL { false }
       	::= { wfSRsvpSenderEntry 43 }

    wfSRsvpSenderAdspecCLOverrides OBJECT-TYPE
        SYNTAX  INTEGER {
                true(1), false(2)
                }
        ACCESS  read-write
        STATUS  mandatory
        DESCRIPTION
	   "If TRUE, the ADSPEC contains general parameter
	    overrides for controlled load service. If FALSE,
	    teh ADSPEC does not contains controlled load
	    service overrides.
	    Note, if TRUE, ALL override parameters will be 
	    included and must be specified."
	DEFVAL { false }
       	::= { wfSRsvpSenderEntry 44 }


    wfSRsvpSenderAdspecCLHopCount OBJECT-TYPE
        SYNTAX  INTEGER (0..'7FFFFFFF'h)
        ACCESS  read-write
        STATUS  mandatory
        DESCRIPTION

           "If wfSRsvpSenderAdspecCLSvc is  TRUE,  this
           is  the  service-specific  override  of the hop
           count general characterization  parameter  from
           the  ADSPEC.   A  return of zero or noSuchValue
           indicates one of the following conditions:

              the invalid bit was set
              the parameter was not present

           If wfSRsvpSenderAdspecCLSvc is  FALSE,  this
           returns zero or noSuchValue."
	DEFVAL { 0 }
       	::= { wfSRsvpSenderEntry 45 }


    wfSRsvpSenderAdspecCLPathBw OBJECT-TYPE
        SYNTAX  INTEGER(0..'7FFFFFFF'h)
        ACCESS  read-write
        STATUS      mandatory
        DESCRIPTION
           "If wfSRsvpSenderAdspecCLSvc is  TRUE,  this
           is  the  service-specific  override of the path
           bandwidth  estimate  general   characterization
           parameter from the ADSPEC.  A return of zero or
           noSuchValue indicates one of the following con-
           ditions:

              the invalid bit was set
              the parameter was not present

           If wfSRsvpSenderAdspecCLSvc is  FALSE,  this
           returns zero or noSuchValue.
           UNITS, bits per second"
	DEFVAL { 0 }
	::= { wfSRsvpSenderEntry 46 }


    wfSRsvpSenderAdspecCLMinLatency OBJECT-TYPE
        SYNTAX  INTEGER (0..'7FFFFFFF'h)
        ACCESS  read-write
        STATUS  mandatory
        DESCRIPTION
           "If wfSRsvpSenderAdspecCLSvc is  TRUE,  this
           is the service-specific override of the minimum
           path latency general characterization parameter
           from  the  ADSPEC.  A return of zero or noSuch-
           Value indicates one  of  the  following  condi-
           tions:

              the invalid bit was set
              the parameter was not present

           If wfSRsvpSenderAdspecCLSvc is  FALSE,  this
           returns zero or noSuchValue. UNITS, microseconds"
	DEFVAL { 0 }
       	::= { wfSRsvpSenderEntry 47 }


    wfSRsvpSenderAdspecCLMtu OBJECT-TYPE
        SYNTAX  INTEGER (0..'7FFFFFFF'h)
        ACCESS  read-write
        STATUS  mandatory
        DESCRIPTION
           "If wfSRsvpSenderAdspecCLSvc is  TRUE,  this
           is  the  service-specific  override of the com-
           posed Maximum Transmission Unit general charac-
           terization parameter from the ADSPEC.  A return
           of zero or noSuchValue  indicates  one  of  the
           following conditions:

              the invalid bit was set
              the parameter was not present

           If wfSRsvpSenderAdspecCLSvc is  FALSE,  this
           returns zero or noSuchValue. UNITS, bytes"
	DEFVAL { 0 }
       	::= { wfSRsvpSenderEntry 48 }


--
-- Static Resv Table
--
    wfSRsvpResvTable OBJECT-TYPE
        SYNTAX  SEQUENCE OF WfSRsvpResvEntry
        ACCESS  not-accessible
        STATUS  mandatory
        DESCRIPTION
                "Information describing the  state  information
                displayed by statically configured reservation."
       ::= { wfRsvpGroup 10 }

    wfSRsvpResvEntry OBJECT-TYPE
        SYNTAX  WfSRsvpResvEntry
        ACCESS  not-accessible
        STATUS  mandatory
        DESCRIPTION
                "Information describing the  state  information
                used to statically configure a reservation."
       INDEX { wfSRsvpResvNumber }
       ::= { wfSRsvpResvTable 1 }

    WfSRsvpResvEntry ::= SEQUENCE {
            wfSRsvpResvCreate           INTEGER,
            wfSRsvpResvEnable           INTEGER,
            wfSRsvpResvStatus           INTEGER,
	    wfSRsvpResvNumber		INTEGER,
	    wfSRsvpResvDestReplicate	INTEGER,
	    wfSRsvpResvReplicate	INTEGER,
	    wfSRsvpResvIntegrity        OCTET STRING,
            wfSRsvpResvDestAddr         IpAddress,
            wfSRsvpResvSenderAddr       IpAddress,
            wfSRsvpResvDestAddrLength   INTEGER,
            wfSRsvpResvSenderAddrLength INTEGER,
            wfSRsvpResvProtocol         INTEGER,
            wfSRsvpResvDestPort         INTEGER,
            wfSRsvpResvPort             INTEGER,
	    wfSRsvpResvFilterSpecNum    INTEGER,
            wfSRsvpResvHopAddr          IpAddress,
            wfSRsvpResvHopLih           INTEGER,
            wfSRsvpResvInterface        INTEGER,
	    wfSRsvpResvTimeValue	INTEGER,
            wfSRsvpResvService          INTEGER,
            wfSRsvpResvTSpecRate        INTEGER,
            wfSRsvpResvTSpecPeakRate    INTEGER,
            wfSRsvpResvTSpecBurst       INTEGER,
            wfSRsvpResvTSpecMinTU       INTEGER,
            wfSRsvpResvTSpecMaxTU       INTEGER,
            wfSRsvpResvTSpecLevel       INTEGER,
            wfSRsvpResvRSpecRate        INTEGER,
            wfSRsvpResvRSpecSlack       INTEGER,
	    wfSRsvpResvScopeNum	        INTEGER,
            wfSRsvpResvScope            OCTET STRING,
            wfSRsvpResvShared           INTEGER,
            wfSRsvpResvExplicit         INTEGER,
            wfSRsvpResvPolicy           OCTET STRING
        }

    wfSRsvpResvCreate OBJECT-TYPE
        SYNTAX  INTEGER {
                create(1),
                delete(2)
            }
        ACCESS  read-write
        STATUS  mandatory
        DESCRIPTION
                "Whether to Delete this RESV RSB"
        DEFVAL  { create }
        ::= { wfSRsvpResvEntry 1 }

    wfSRsvpResvEnable OBJECT-TYPE
        SYNTAX  INTEGER {
                enabled(1),
                disabled(2)
            }
        ACCESS  read-write
        STATUS  mandatory
        DESCRIPTION
                "Whether to Disable this RESV RSB"
        DEFVAL  { enabled }
        ::= { wfSRsvpResvEntry 2 }

    wfSRsvpResvStatus OBJECT-TYPE
        SYNTAX  INTEGER {
                valid(1),
                invalid(2),
                notpres(3)
                }
        ACCESS  read-only
        STATUS  mandatory
        DESCRIPTION
           "'valid' for all active  RESV  messages.   This
           object  may  be used to install static RESV in-
           formation or delete RESV information."
	DEFVAL { valid }
       	::= { wfSRsvpResvEntry 3 }

    wfSRsvpResvNumber OBJECT-TYPE
        SYNTAX  INTEGER
        ACCESS  read-only
        STATUS  mandatory
        DESCRIPTION
           "The number of this static resv.  This is for
           SNMP Indexing  purposes  only and has no relation to
           any protocol value."
       	::= { wfSRsvpResvEntry 4 }

    wfSRsvpResvDestReplicate OBJECT-TYPE
        SYNTAX  INTEGER
        ACCESS  read-write
        STATUS  mandatory
        DESCRIPTION
                "Number of sessions for which this static path state should
		be replicated. For each replication, wfSRsvpResvDestAddr 
		will be	incremented by one."
        DEFVAL  { 0 }
        ::= { wfSRsvpResvEntry 5 }

    wfSRsvpResvReplicate OBJECT-TYPE
        SYNTAX  INTEGER
        ACCESS  read-write
        STATUS  mandatory
        DESCRIPTION
                "Number of senders for which this static path state should
		be replicated. For each replication, wfSRsvpResvAddr
		will be incremented by one."
        DEFVAL  { 0 }
        ::= { wfSRsvpResvEntry 6 }

    wfSRsvpResvIntegrity OBJECT-TYPE
        SYNTAX  OCTET STRING (SIZE(0..65536))
        ACCESS  read-write
        STATUS  mandatory
        DESCRIPTION
           "The contents of the integrity  object,  displayed
           as an uninterpreted string of octets, including
           the object header.  In the absence of  such  an
           object, this should be of zero length."
        ::= { wfSRsvpResvEntry 7 }

    wfSRsvpResvDestAddr OBJECT-TYPE
        SYNTAX  IpAddress
        ACCESS  read-write
        STATUS  mandatory
        DESCRIPTION
           "The destination address used by all senders in
           this  session.   This object may not be changed
           when the  value  of  the  Status  object  is
           'valid'."
       	::= { wfSRsvpResvEntry 8 }

    wfSRsvpResvSenderAddr OBJECT-TYPE
        SYNTAX  IpAddress
        ACCESS  read-write
        STATUS  mandatory
        DESCRIPTION
           "The source address of the sender  selected  by
           this  reservation.  The value of all zeroes in-
           dicates 'all senders'.  This object may not  be
           changed  when the value of the Status object
           is 'valid'."
       	::= { wfSRsvpResvEntry 9 }

    wfSRsvpResvDestAddrLength OBJECT-TYPE
        SYNTAX  INTEGER(0..128)
        ACCESS  read-write
        STATUS  mandatory
        DESCRIPTION
           "The length of the destination address in bits.
           This  is  the CIDR Prefix Length, which for IP4
           hosts and multicast addresses is 32 bits.  This
           object may not be changed when the value of the
           Status object is 'valid'."
	DEFVAL { 32 }
       	::= { wfSRsvpResvEntry 10 }


    wfSRsvpResvSenderAddrLength OBJECT-TYPE
        SYNTAX  INTEGER(0..128)
        ACCESS  read-write
        STATUS  mandatory
        DESCRIPTION
           "The length of the sender's  address  in  bits.
           This  is  the CIDR Prefix Length, which for IP4
           hosts and multicast addresses is 32 bits.  This
           object may not be changed when the value of the
           Status object is 'valid'."
	DEFVAL { 32 }
       	::= { wfSRsvpResvEntry 11 }


    wfSRsvpResvProtocol OBJECT-TYPE
        SYNTAX  INTEGER(1..255)
        ACCESS  read-write
        STATUS  mandatory
        DESCRIPTION
           "The IP Protocol used by  this  session.   This
           object may not be changed when the value of the
           Status object is 'valid'."
	DEFVAL { 17 }
        ::= { wfSRsvpResvEntry 12 }

    wfSRsvpResvDestPort OBJECT-TYPE
        SYNTAX  INTEGER (0..65536)
        ACCESS  read-write
        STATUS  mandatory
        DESCRIPTION
           "The UDP or TCP port number used as a  destina-
           tion  port for all senders in this session.  If
           the  IP   protocol   in   use,   specified   by
           wfSRsvpResvProtocol,  is 50 (ESP) or 51 (AH), this
           represents a virtual destination  port  number.
           A  value of zero indicates that the IP protocol
           in use does not have ports.   This  object  may
           not  be changed when the value of the Status
           object is 'valid'."
       	::= { wfSRsvpResvEntry 13 }

    wfSRsvpResvPort OBJECT-TYPE
        SYNTAX  INTEGER (0..65536)
        ACCESS  read-write
        STATUS  mandatory
        DESCRIPTION
           "The UDP or TCP port number used  as  a  source
           port  for  this sender in this session.  If the
           IP protocol in use, specified by wfSRsvpResvProto-
           col  is  50 (ESP) or 51 (AH), this represents a
           generalized port identifier (GPI).  A value  of
           zero indicates that the IP protocol in use does
           not have ports.  This object may not be changed
           when  the  value  of  the  Status  object is
           'valid'."
       	::= { wfSRsvpResvEntry 14 }

    wfSRsvpResvFilterSpecNum OBJECT-TYPE
        SYNTAX  INTEGER
        ACCESS  read-write
        STATUS  mandatory
        DESCRIPTION
	   "For SE reservation style, this is the number of 
	    filter specs. For WF and FF styles, this is ignored.
	    If SE style, there must be wfSRsvpResvFilterSpecNum
      	    SenderAddr and SenderPort entries where SenderPort 'j' 
	    is used by SenderAddr 'j'."
	DEFVAL { 0 }
	::= { wfSRsvpResvEntry 15 }

    wfSRsvpResvHopAddr OBJECT-TYPE
        SYNTAX  IpAddress
        ACCESS  read-write
        STATUS  mandatory
        DESCRIPTION
           "The address used by the next RSVP  hop  (which
           may be the ultimate receiver)."
       	::= { wfSRsvpResvEntry 16 }

    wfSRsvpResvHopLih OBJECT-TYPE
        SYNTAX  INTEGER
        ACCESS  read-write
        STATUS  mandatory
        DESCRIPTION
           "The Logical Interface Handle received from the
           previous  RSVP  hop  (which may be the ultimate
           receiver)."
       	::= { wfSRsvpResvEntry 17 }


    wfSRsvpResvInterface OBJECT-TYPE
        SYNTAX  INTEGER
        ACCESS  read-write
        STATUS  mandatory
        DESCRIPTION
           "The ifIndex value of the  interface  on  which
           this RESV message was most recently received."
       	::= { wfSRsvpResvEntry 18 }

    wfSRsvpResvTimeValue OBJECT-TYPE
        SYNTAX  INTEGER (0..'7FFFFFFF'h)
        ACCESS  read-write
        STATUS  mandatory
        DESCRIPTION
           "The value of the RSVP value 'R', which is  the
           minimum period between refresh transmissions of
           a given PATH or RESV message on an interface.
           UNITS   milliseconds"
       	DEFVAL      { 30000 }
	::= { wfSRsvpResvEntry 19 } 

    wfSRsvpResvService OBJECT-TYPE
        SYNTAX  INTEGER {
		   controlledDelay(1),
                   guaranteedDelay (2),    -- Guaranteed Delay
		   predictive(3),
                   controlledLoad (5)      -- Controlled Load
                 }
        ACCESS  read-write
        STATUS  mandatory
        DESCRIPTION
           "The QoS Service  classification  requested  by
           the receiver."
	DEFVAL { controlledLoad }
       	::= { wfSRsvpResvEntry 20 }

    wfSRsvpResvTSpecRate OBJECT-TYPE
        SYNTAX  INTEGER(0..'7FFFFFFF'h)
        ACCESS  read-write
        STATUS  mandatory
        DESCRIPTION
           "The Average Bit  Rate  of  the  sender's  data
           stream.   Within  a transmission burst, the ar-
           rival rate may be  as  fast  as  wfSRsvpResvTSpec-
           PeakRate  (if  supported by the service model);
           however, averaged across two or more burst  in-
           tervals,    the    rate   should   not   exceed
           wfSRsvpResvTSpecRate.

           Note that this is a prediction, often based  on
           the  general  capability  of a type of codec or
           particular encoding; the measured average  rate
           may be significantly lower. 
	   UNITS, bits per second"
       	::= { wfSRsvpResvEntry 21 }

    wfSRsvpResvTSpecPeakRate OBJECT-TYPE
        SYNTAX  INTEGER(0..'7FFFFFFF'h)
        ACCESS  read-write
        STATUS  mandatory
        DESCRIPTION
           "The Peak Bit Rate of the sender's data stream.
           Traffic  arrival is not expected to exceed this
           rate at any time, apart  from  the  effects  of
           jitter in the network.  If not specified in the
           TSpec, this returns zero or noSuchValue. 
	   UNITS, bits per second"
       	::= { wfSRsvpResvEntry 22 }

    wfSRsvpResvTSpecBurst OBJECT-TYPE
        SYNTAX  INTEGER(0..'7FFFFFFF'h)
        ACCESS  read-write
        STATUS  mandatory
        DESCRIPTION
           "The size of the largest  burst  expected  from
           the sender at a time.

           If this is less than  the  sender's  advertised
           burst  size, the receiver is asking the network
           to provide flow pacing  beyond  what  would  be
           provided  under normal circumstances. Such pac-
           ing is at the network's option. UNITS, bytes"
       	::= { wfSRsvpResvEntry 23 }


    wfSRsvpResvTSpecMinTU OBJECT-TYPE
        SYNTAX  INTEGER(0..'7FFFFFFF'h)
        ACCESS  read-write
        STATUS  mandatory
        DESCRIPTION
           "The minimum message size for  this  flow.  The
           policing  algorithm will treat smaller messages
           as though they are this size."
       	::= { wfSRsvpResvEntry 24 }

    wfSRsvpResvTSpecMaxTU OBJECT-TYPE
        SYNTAX  INTEGER(0..'7FFFFFFF'h)
        ACCESS  read-write
        STATUS  mandatory
        DESCRIPTION
           "The maximum message size for  this  flow.  The
           admission  algorithm  will  reject TSpecs whose
           Maximum Transmission Unit, plus  the  interface
           headers, exceed the interface MTU."
       	::= { wfSRsvpResvEntry 25 }

    wfSRsvpResvTSpecLevel OBJECT-TYPE
        SYNTAX  INTEGER(1..3)
        ACCESS  read-write
        STATUS  mandatory
        DESCRIPTION
                "If the service is  predictive  or  controlled-
                delay,  this is the service level that is being
                requested.  Otherwise, it is zero, or the agent
                may return noSuchValue."
	DEFVAL { 1 }
       	::= { wfSRsvpResvEntry 26 }


    wfSRsvpResvRSpecRate OBJECT-TYPE
        SYNTAX  INTEGER(0..'7FFFFFFF'h)
        ACCESS  read-write
        STATUS  mandatory
        DESCRIPTION
           "If the requested  service  is  Guaranteed,  as
           specified   by  wfSRsvpResvService,  this  is  the
           clearing rate that is being requested.   Other-
           wise,  it  is  zero,  or  the  agent may return
           noSuchValue. UNITS, bits per second"
	DEFVAL { 0 }
        ::= { wfSRsvpResvEntry 27 }


    wfSRsvpResvRSpecSlack OBJECT-TYPE
        SYNTAX  INTEGER
        ACCESS  read-write
        STATUS  mandatory
        DESCRIPTION
           "If the requested  service  is  Guaranteed,  as
           specified by wfSRsvpResvService, this is the delay
           slack.  Otherwise, it is zero, or the agent may
           return noSuchValue.UNITS, microseconds"
	DEFVAL { 0 }
       	::= { wfSRsvpResvEntry 28 }

    wfSRsvpResvScopeNum OBJECT-TYPE
        SYNTAX  INTEGER
        ACCESS  read-write
        STATUS  mandatory
        DESCRIPTION
           "The number of addresses in wfSRsvpResvScope.
	   In the absence of the scope object, this should be zero"
	DEFVAL { 0 }
       	::= { wfSRsvpResvEntry 29 }

    wfSRsvpResvScope OBJECT-TYPE
        SYNTAX  OCTET STRING (SIZE(0..65536))
        ACCESS  read-write
        STATUS  mandatory
        DESCRIPTION
           "The contents of the scope object, displayed as
           an  uninterpreted  string  of octets.  In the 
	   absence of  such  an object, this should be of 
	   zero length.

           If the length  is  non-zero,  this  contains  a
           series of IP4 or IP6 addresses."
       	::= { wfSRsvpResvEntry 30 }

    wfSRsvpResvShared OBJECT-TYPE
        SYNTAX  INTEGER {
                true(1), 
                false(2)
                }
        ACCESS  read-write
        STATUS  mandatory
        DESCRIPTION
           "If TRUE, a reservation shared among senders is
           requested.  If FALSE, a reservation specific to
           this sender is requested."
	DEFVAL { false }
       	::= { wfSRsvpResvEntry 31 }

    wfSRsvpResvExplicit OBJECT-TYPE
        SYNTAX  INTEGER {
                true(1), 
                false(2)
                }
        ACCESS  read-write
        STATUS  mandatory
        DESCRIPTION
           "If TRUE, individual senders are  listed  using
           Filter  Specifications.   If FALSE, all senders
           are implicitly selected.  The Scope Object will
           contain  a list of senders that need to receive
           this reservation request  for  the  purpose  of
           routing the RESV message."
	DEFVAL { true }
       	::= { wfSRsvpResvEntry 32 }

    wfSRsvpResvPolicy OBJECT-TYPE
        SYNTAX  OCTET STRING (SIZE(0..65536))
        ACCESS  read-write
        STATUS  mandatory
        DESCRIPTION
           "The contents of the policy  object,  displayed
           as an uninterpreted string of octets, including
           the object header.  In the absence of  such  an
           object, this should be of zero length."
       	::= { wfSRsvpResvEntry 33 }

END  -- Wellfleet-RSVP-MIB
