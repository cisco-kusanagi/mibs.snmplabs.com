CXVMFC-MIB DEFINITIONS ::= BEGIN

IMPORTS
   OBJECT-TYPE          FROM RFC-1212
   DisplayString        FROM RFC1213-MIB
   cxMcVox              FROM CXMCVOX-MIB;

cxVMFC   OBJECT IDENTIFIER ::= {cxMcVox 22}

vmfcOutRegCallerCategory    OBJECT-TYPE
      SYNTAX   INTEGER {
               subscriber-without-priority (1),
               subscriber-with-priority (2),
               maintenance-equipment (3),
               charge-meter (4),
               operator  (5),
               data-tx (6)
            }
      ACCESS   read-write
      STATUS   mandatory
      DESCRIPTION
"The Outgoing register will need to know the category of the caller 
since the next Incoming register may request it. Since this information 
may not be available from the caller, it needs to be configurable for 
the general case.

Options:
subscriber-without-priority (1)
subscriber-with-priority (2)
maintenance-equipment (3)
charge-meter (4)
operator  (5)
data-tx (6)

Default Value: subscriber-without-priority (1)

Configuration Changed: administrative "
      DEFVAL { subscriber-without-priority }
      ::= { cxVMFC 1 }


vmfcOutRegCallerCatGrpII3      OBJECT-TYPE
      SYNTAX   INTEGER {
               normal-subscriber (1),
               atme-equipment (2),
               maintenance-equipment (3),
               operator-with-transfer-capability (4),
               operator-with-intercept-capability (5)
            }
      ACCESS   read-write
      STATUS   mandatory
      DESCRIPTION
"The Outgoing register will need to know the category of the caller 
since the next Incoming register may request it. This selection of 
category choices are from Mexican GroupII3 list.

Options:
normal-subscriber (1)
atme-equipment (2)
maintenance-equipment (3)
operator-with-transfer-capability (4)
operator-with-intercept-capability (5)

Default Value: normal-subscriber (1)

Configuration Changed: administrative "
      DEFVAL { normal-subscriber }
      ::= { cxVMFC 2 }


vmfcOutRegCallerCatGrpII6      OBJECT-TYPE
      SYNTAX   INTEGER {
               normal-subscriber (1),
               atme-equipment (2),
               maintenance-equipment (3),
               collect-call (4),
               time-and-charges (5),
               subscriber1-on-shared-line (6),
               subscriber2-on-shared-line (7),
               subscriber3-on-shared-line (8),
               operator-without-transfer-capability (9)
            }
      ACCESS   read-write
      STATUS   mandatory
      DESCRIPTION
"The Outgoing register will need to know the category of the caller 
since the next Incoming register may request it. This selection of 
category choices are from Mexican GroupII6 list.

Options:
normal-subscriber (1)
atme-equipment (2)
maintenance-equipment (3)
collect-call (4)
time-and-charges (5)
subscriber1-on-shared-line (6)
subscriber2-on-shared-line (7)
subscriber3-on-shared-line (8)
operator-without-transfer-capability (9)

Default Value: normal-subscriber (1)

Configuration Changed: administrative "
      DEFVAL { normal-subscriber }
      ::= { cxVMFC 3 }


vmfcOutRegExchangeType         OBJECT-TYPE
      SYNTAX   INTEGER {
               national-exchange (1),
               international-exchange (2)
            }
      ACCESS   read-write
      STATUS   mandatory
      DESCRIPTION
"Type of exchange the Outgoing register is connected to. This 
object only supports National Exchange (1) for the time being.

Default Value: national-exchange (1)

Configuration Changed: administrative "
      DEFVAL { national-exchange }
      ::= { cxVMFC 4 }


vmfcOutRegCallingID           OBJECT-TYPE
      SYNTAX   DisplayString
      ACCESS   read-write
      STATUS   mandatory
      DESCRIPTION
"Determines the calling ID that will be transmitted when the 
Outgoing register has requested for it.

Default Value: '0'

Configuration Changed: administrative "
      DEFVAL { "0" }
      ::= { cxVMFC 5 }


vmfcInRegNationalAddressSize   OBJECT-TYPE
      SYNTAX   INTEGER (1..40)
      ACCESS   read-write
      STATUS   mandatory
      DESCRIPTION
"The number of digits in a called number if the call is made to 
a national exchange.

Default Value: 16

Configuration Changed: administrative "
      DEFVAL { 16 }
      ::= { cxVMFC 6 }


vmfcInRegInfoRequest        OBJECT-TYPE
      SYNTAX   INTEGER
      ACCESS   read-write
      STATUS   mandatory
      DESCRIPTION
"This object represents a 3 bits bitmap. When a bit is set the 
respective information  will be requested by the Incoming register.

Options:
Bit 1 refers to the category.
Bit 2 refers to the calling ID.
Bit 3 refers to the charging category.

Default Value: '0'h equals 0

Configuration Changed: administrative "
      DEFVAL { '0'h }
      ::= { cxVMFC 7 }


vmfcInRegPulsePeriod        OBJECT-TYPE
      SYNTAX   INTEGER (1..65535)
      ACCESS   read-write
      STATUS   mandatory
      DESCRIPTION
"Determines the period of a pulse that an Incoming register will send.

Default Value: 150

Configuration Changed: administrative "
      DEFVAL { 150 }
      ::= { cxVMFC 8 }


vmfcCountry                 OBJECT-TYPE
      SYNTAX   INTEGER {
               mexico (1),
               philippines (2),
               nicaragua (3),
               korea (4),
               china (5),
               argentina (6)
            }
      ACCESS   read-write
      STATUS   mandatory
      DESCRIPTION
"Determines in which country the equipment is located. It will 
determine which protocol flavor to use.

Options:
mexico (1)
philippines (2)
nicaragua (3)
korea (4)
china (5)
argentina (6)

Default Value: mexico (1)

Configuration Changed: administrative "
      DEFVAL { mexico }
      ::= { cxVMFC 9 }


vmfcTimeOutBackwardSignal      OBJECT-TYPE
      SYNTAX   INTEGER (1..65535)
      ACCESS   read-write
      STATUS   mandatory
      DESCRIPTION
"Determines the delay in milliseconds allowed in 
reception of a backward signal.

Default Value: 15000

Configuration Changed: administrative "
      DEFVAL { 15000 }
      ::= { cxVMFC 10 }


vmfcTimeOutForwardSignal      OBJECT-TYPE
      SYNTAX   INTEGER (1..65535)
      ACCESS   read-write
      STATUS   mandatory
      DESCRIPTION
"Determines the delay in milliseconds allowed in 
reception of a forward signal.

Default Value: 24000

Configuration Changed: administrative "
      DEFVAL { 24000 }
      ::= { cxVMFC 11 }

END
