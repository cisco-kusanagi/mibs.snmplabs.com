--
-- Copyright 1997 ADC Telecommunications, Inc.  All rights reserved.
--
-- ADC Telecommunications, Inc. Confidential and Proprietary
-- This work contains valuable confidential and proprietary information.
-- Disclosure, use or reproduction without the written authorization of ADC
-- Telecommunications, Inc. is prohibited.  This unpublished work by ADC
-- Telecommunications, Inc. is protected by the laws of the United States and
-- other countries.
--

FRAMEVISIONFPING-MIB DEFINITIONS ::= BEGIN

IMPORTS
    enterprises, IpAddress, Counter, TimeTicks
        FROM RFC1155-SMI
    OBJECT-TYPE
        FROM RFC-1212;

-- Internal Datatypes
	-- Valid DLCIs are 0..1023 and OTHER (2^31-1 is "other" VC)
	FribDLCI ::= INTEGER (0..2147483646)
 
	-- From SNMPv2-SMI (SimpleTest can't compile if mix v1 & v2)
	Counter32 ::= Counter

--------------------------------------------------------------------------
--  The ADC Kentrox FrameVision Fping Enterprise MIB Module.
--------------------------------------------------------------------------
--  internet(1).private(4).enterprises(1).adcKentrox(181).miblets(100).2
--
-- NOTE: The following line must say "OBJECT IDENTIFIER" to compile
--   for HP OpenView and Sun Net Manager.  However, it must say "OBJECT-TYPE" 
--   to compile with Epilogue.
--
framevisionfping	OBJECT IDENTIFIER
    ::= { enterprises adcKentrox(181) miblets(100) 2 }

--------------------------------------------------------------------------
--  Groups in the ADC Kentrox FrameVision Enterprise MIB Module.
--------------------------------------------------------------------------

fpingMib		OBJECT IDENTIFIER ::= { framevisionfping 1 }
fpingAuto		OBJECT IDENTIFIER ::= { framevisionfping 2 }
fpingManual		OBJECT IDENTIFIER ::= { framevisionfping 3 }

--------------------------------------------------------------------
--  BEGIN -  framevision fping  MIB variables
--------------------------------------------------------------------
fpingMibVersion	OBJECT-TYPE
				SYNTAX	INTEGER {
				version1		(1)
				}
				ACCESS	read-only
				STATUS	mandatory
				DESCRIPTION
						"."
				::= { fpingMib 1 }

fpingMibLastChange	OBJECT-TYPE
				SYNTAX	TimeTicks
				ACCESS	read-only
				STATUS	mandatory
				DESCRIPTION
						"."
				::= { fpingMib 2 }

--------------------------------------------------------------------
--  BEGIN -  framevision fping auto fping config MIB variables
--------------------------------------------------------------------
fpingAutoCfgTable	OBJECT-TYPE
				SYNTAX	SEQUENCE OF FpingAutoCfgEntry
				ACCESS	not-accessible
				STATUS	mandatory
				DESCRIPTION
				"."
				::= { fpingAuto 1 }
 
fpingAutoCfgEntry	OBJECT-TYPE
				SYNTAX	FpingAutoCfgEntry
				ACCESS	not-accessible
				STATUS	mandatory
				DESCRIPTION
						"."
				INDEX	{ fpingAutoCfgIfIndex }
				::=	{ fpingAutoCfgTable 1 }

FpingAutoCfgEntry	::= SEQUENCE {
				fpingAutoCfgIfIndex		INTEGER,
				fpingAutoCfgLastChange	TimeTicks,
				fpingAutoCfgGen			INTEGER,
				fpingAutoCfgThresh		INTEGER,
				fpingAutoCfgReset		INTEGER
				}

fpingAutoCfgIfIndex	OBJECT-TYPE
				SYNTAX	INTEGER
				ACCESS	read-only
				STATUS	mandatory
				DESCRIPTION
						"."
				::= { fpingAutoCfgEntry 1 }

fpingAutoCfgLastChange	OBJECT-TYPE
				SYNTAX	TimeTicks
				ACCESS	read-only
				STATUS	mandatory
				DESCRIPTION
						"."
				::= { fpingAutoCfgEntry 2 }

fpingAutoCfgGen			OBJECT-TYPE
				SYNTAX	INTEGER
				ACCESS	read-write
				STATUS	mandatory
				DESCRIPTION
						"."
				::= { fpingAutoCfgEntry 3 }

fpingAutoCfgThresh		OBJECT-TYPE
				SYNTAX	INTEGER
				ACCESS	read-write
				STATUS	mandatory
				DESCRIPTION
						"."
				::= { fpingAutoCfgEntry 4 }

fpingAutoCfgReset		OBJECT-TYPE
				SYNTAX	INTEGER {
				fpingResetIdle	(1),
				fpingResetStart	(2)
				}
				ACCESS	read-write
				STATUS	mandatory
				DESCRIPTION
						"."
				::= { fpingAutoCfgEntry 5 }


fpingAutoDuration		OBJECT-TYPE
				SYNTAX	TimeTicks
				ACCESS	read-only
				STATUS	mandatory
				DESCRIPTION
						"."
				::= { fpingAuto 2 }

fpingAutoClearData		OBJECT-TYPE
				SYNTAX	INTEGER {
				clearDataIdle	(1),
				clearDataStart	(2)
				}
				ACCESS	read-write
				STATUS	mandatory
				DESCRIPTION
						"."
				::= { fpingAuto 3 }



fpingAutoTable	OBJECT-TYPE
				SYNTAX	SEQUENCE OF FpingAutoEntry
				ACCESS	not-accessible
				STATUS	mandatory
				DESCRIPTION
						"."
				::= { fpingAuto 4 }

fpingAutoEntry	OBJECT-TYPE
				SYNTAX	FpingAutoEntry
				ACCESS	not-accessible
				STATUS	mandatory
				DESCRIPTION
						"."
				INDEX { fpingAutoIfIndex, fpingAutoDLCI }
				::= { fpingAutoTable 1 }

FpingAutoEntry	::= SEQUENCE {
				fpingAutoIfIndex			INTEGER,
				fpingAutoDLCI				FribDLCI,
				fpingAutoDelayMin			INTEGER,
				fpingAutoDelayMax			INTEGER,
				fpingAutoDelayAvg			INTEGER,
				fpingAutoLost				Counter32,
				fpingAutoTotal				Counter32,
				fpingAutoThreshExceeded		Counter32,
				fpingAutoRmtDLCI			FribDLCI,
				fpingAutoRmtIpaddr			IpAddress,
				fpingAutoTotalPktsLocalTx	Counter32,
				fpingAutoTotalPktsLocalRx	Counter32,
				fpingAutoTotalPktsRmtTx		Counter32,
				fpingAutoTotalPktsRmtRx		Counter32,
				fpingAutoStatus				INTEGER,
				fpingAutoFailedEvents		Counter32
				}


fpingAutoIfIndex			OBJECT-TYPE
				SYNTAX	INTEGER
				ACCESS	read-only
				STATUS	mandatory
				DESCRIPTION
						"."
				::= { fpingAutoEntry 1 }

fpingAutoDLCI				OBJECT-TYPE
				SYNTAX	FribDLCI
				ACCESS	read-only
				STATUS	mandatory
				DESCRIPTION
						"."
				::= { fpingAutoEntry 2 }

fpingAutoDelayMin			OBJECT-TYPE
				SYNTAX	INTEGER
				ACCESS	read-only
				STATUS	mandatory
				DESCRIPTION
						"."
				::= { fpingAutoEntry 3 }

fpingAutoDelayMax			OBJECT-TYPE
				SYNTAX	INTEGER
				ACCESS	read-only
				STATUS	mandatory
				DESCRIPTION
						"."
				::= { fpingAutoEntry 4 }

fpingAutoDelayAvg			OBJECT-TYPE
				SYNTAX	INTEGER
				ACCESS	read-only
				STATUS	mandatory
				DESCRIPTION
						"."
				::= { fpingAutoEntry 5 }

fpingAutoLost				OBJECT-TYPE
				SYNTAX	Counter32
				ACCESS	read-only
				STATUS	mandatory
				DESCRIPTION
						"."
				::= { fpingAutoEntry 6 }

fpingAutoTotal				OBJECT-TYPE
				SYNTAX	Counter32
				ACCESS	read-only
				STATUS	mandatory
				DESCRIPTION
						"."
				::= { fpingAutoEntry 7 }

fpingAutoThreshExceeded		OBJECT-TYPE
				SYNTAX	Counter32
				ACCESS	read-only
				STATUS	mandatory
				DESCRIPTION
						"."
				::= { fpingAutoEntry 8 }

fpingAutoRmtDLCI			OBJECT-TYPE
				SYNTAX	FribDLCI
				ACCESS	read-only
				STATUS	mandatory
				DESCRIPTION
						"."
				::= { fpingAutoEntry 9 }

fpingAutoRmtIpaddr			OBJECT-TYPE
				SYNTAX	IpAddress
				ACCESS	read-only
				STATUS	mandatory
				DESCRIPTION
						"."
				::= { fpingAutoEntry 10 }

fpingAutoTotalPktsLocalTx	OBJECT-TYPE
				SYNTAX	Counter32
				ACCESS	read-only
				STATUS	mandatory
				DESCRIPTION
						"."
				::= { fpingAutoEntry 11 }

fpingAutoTotalPktsLocalRx	OBJECT-TYPE
				SYNTAX	Counter32
				ACCESS	read-only
				STATUS	mandatory
				DESCRIPTION
						"."
				::= { fpingAutoEntry 12 }

fpingAutoTotalPktsRmtTx		OBJECT-TYPE
				SYNTAX	Counter32
				ACCESS	read-only
				STATUS	mandatory
				DESCRIPTION
						"."
				::= { fpingAutoEntry 13 }

fpingAutoTotalPktsRmtRx		OBJECT-TYPE
				SYNTAX	Counter32
				ACCESS	read-only
				STATUS	mandatory
				DESCRIPTION
						"."
				::= { fpingAutoEntry 14 }

fpingAutoStatus				OBJECT-TYPE
				SYNTAX	INTEGER {
				fpingDisabled		(1),
				lastFpingSucceeded	(2),
				lastFpingFailed		(3),
				notMonitoringFping	(4),
				waitingToStartFping	(5)
				}
				ACCESS	read-only
				STATUS	mandatory
				DESCRIPTION
						"."
				::= { fpingAutoEntry 15 }

fpingAutoFailedEvents		OBJECT-TYPE
				SYNTAX	Counter32
				ACCESS	read-only
				STATUS	mandatory
				DESCRIPTION
						"."
				::= { fpingAutoEntry 16 }


--------------------------------------------------------------------
--  BEGIN -  framevision fping manual fping MIB variables
--------------------------------------------------------------------

fpingManualTable	OBJECT-TYPE
				SYNTAX	SEQUENCE OF FpingManualEntry
				ACCESS	not-accessible
				STATUS	mandatory
				DESCRIPTION
						"."
				::= { fpingManual 1 }

fpingManualEntry	OBJECT-TYPE
				SYNTAX	FpingManualEntry
				ACCESS	not-accessible
				STATUS	mandatory
				DESCRIPTION
						"."
				INDEX { fpingManualIfIndex, fpingManualDLCI }
				::=	{ fpingManualTable 1 }

FpingManualEntry	::= SEQUENCE {
				fpingManualIfIndex		INTEGER,
				fpingManualDLCI			FribDLCI,
				fpingManualAction		INTEGER,
				fpingManualState		INTEGER,
				fpingManualFreq			INTEGER,
				fpingManualLen			INTEGER,
				fpingManualCur			INTEGER,
				fpingManualMin			INTEGER,
				fpingManualMax			INTEGER,
				fpingManualAvg			INTEGER,
				fpingManualLost			INTEGER,
				fpingManualTotal		INTEGER,
				fpingManualRmtDLCI		FribDLCI,
				fpingManualRmtIpaddr	IpAddress
				}

fpingManualIfIndex		OBJECT-TYPE
				SYNTAX	INTEGER
				ACCESS	read-only
				STATUS	mandatory
				DESCRIPTION
						"."
				::= { fpingManualEntry 1 }

fpingManualDLCI			OBJECT-TYPE
				SYNTAX	FribDLCI
				ACCESS	read-write
				STATUS	mandatory
				DESCRIPTION
						"."
				::= { fpingManualEntry 2 }

fpingManualAction		OBJECT-TYPE
				SYNTAX	INTEGER {
				fpingManualActionStart	(1),
				fpingManualActionStop	(2)
				}
				ACCESS	read-write
				STATUS	mandatory
				DESCRIPTION
						"."
				::= { fpingManualEntry 3 }

fpingManualState		OBJECT-TYPE
				SYNTAX	INTEGER {
				fpingManualStateIdle		(1),
				fpingManualStateOtherStart	(2),
				fpingManualStarteRunning	(3)
				}
				ACCESS	read-only
				STATUS	mandatory
				DESCRIPTION
						"."
				::= { fpingManualEntry 4 }

fpingManualFreq			OBJECT-TYPE
				SYNTAX	INTEGER
				ACCESS	read-write
				STATUS	mandatory
				DESCRIPTION
						"."
				::= { fpingManualEntry 5 }

fpingManualLen			OBJECT-TYPE
				SYNTAX	INTEGER
				ACCESS	read-write
				STATUS	mandatory
				DESCRIPTION
						"."
				::= { fpingManualEntry 6 }

fpingManualCur			OBJECT-TYPE
				SYNTAX	INTEGER
				ACCESS	read-only
				STATUS	mandatory
				DESCRIPTION
						"."
				::= { fpingManualEntry 7 }

fpingManualMin			OBJECT-TYPE
				SYNTAX	INTEGER
				ACCESS	read-only
				STATUS	mandatory
				DESCRIPTION
						"."
				::= { fpingManualEntry 8 }

fpingManualMax			OBJECT-TYPE
				SYNTAX	INTEGER
				ACCESS	read-only
				STATUS	mandatory
				DESCRIPTION
						"."
				::= { fpingManualEntry 9 }

fpingManualAvg			OBJECT-TYPE
				SYNTAX	INTEGER
				ACCESS	read-only
				STATUS	mandatory
				DESCRIPTION
						"."
				::= { fpingManualEntry 10 }

fpingManualLost			OBJECT-TYPE
				SYNTAX	INTEGER
				ACCESS	read-only
				STATUS	mandatory
				DESCRIPTION
						"."
				::= { fpingManualEntry 11 }

fpingManualTotal		OBJECT-TYPE
				SYNTAX	INTEGER
				ACCESS	read-only
				STATUS	mandatory
				DESCRIPTION
						"."
				::= { fpingManualEntry 12 }

fpingManualRmtDLCI		OBJECT-TYPE
				SYNTAX	FribDLCI
				ACCESS	read-only
				STATUS	mandatory
				DESCRIPTION
						"."
				::= { fpingManualEntry 13 }

fpingManualRmtIpaddr	OBJECT-TYPE
				SYNTAX	IpAddress
				ACCESS	read-only
				STATUS	mandatory
				DESCRIPTION
						"."
				::= { fpingManualEntry 14 }




END
