DEC-ATM-CHASSIS-MIB DEFINITIONS ::= BEGIN

--
--  Definitions of Managed Objects for Digital Equipment Corporation's
--                       ATM Switch "Chassis MIB"
--                       ========================
--  
--  
--
--  
--                 Name:      dec-atm-chassis-mib-v1-2.txt
--                 Version:   1.2
--                 Date:      November, 1996
--                 Company:   Digital Equipment Corporation
--                 Mail:      TBD
--
--
--  
--  
--  
--  This Digital Equipment  Corporation  SNMP  Management  Information  Base
--  Specification  embodies Digital Equipment Corporation's confidential and
--  proprietary  intellectual  property.   Digital   Equipment   Corporation
--  retains  all  title  and  ownership  in the Specification, including any
--  revisions.
--  
--  It is Digital Equipment Corporation's intent to encourage the widespread
--  use  of  this Specification in connection with the management of Digital
--  Equipment Corporation products.
--  
--  Digital Equipment  Corporation  grants  vendors,  end-users,  and  other
--  interested  parties a non-exclusive license to use this Specification in
--  connection  with  the  management  of  Digital   Equipment   Corporation
--  products.
--  
--  Digital Equipment Corporation reserves the right to make changes in this
--  specification  and  other information contained in this document without
--  prior notice.
--  
--  Digital Equipment Corporation makes no  warranty,  either  expressed  or
--  implied,  as  to  the  use,  operation, condition, or performance of the
--  Specification.  In no  event  shall  Digital  Equipment  Corporation  be
--  liable  for  any incidental, indirect, special, or consequential damages
--  whatsoever (including but not limited to loss of profits) arising out of
--  or related to this document or the information contained in it.
--
--
--
--

--  Object Synopsis
--
--  All objects within this MIB are prefixed with the OBJECT IDENTIFIER "p",
--  where "p" is:
--
--      iso(1).org(3).dod(6).internet(1).private(4).enterprises(1).
--          dec(36).ema(2).decMIBextension(18).decAtmChassisMIB(30)
--
--  or, 1.3.6.1.4.1.36.2.18.30
--
--
--  Object Name                               Object Id         Non-vol
--  ==================================        ================  =======
--
--  decAtmChassisMIB                          p
--    decAtmChassisMIBObjects                 p.1
--      decAtmSysGroup                        p.1.1
--        decAtmSysType                       p.1.1.1.0
--        decAtmKeyswitchPosition             p.1.1.2.0
--      decAtmSlot                            p.1.2
--        decAtmSlotNumber                    p.1.2.1.0
--        decAtmMasterLinecardSlot            p.1.2.2.0
--        decAtmStandbyLinecardSlot           p.1.2.3.0
--        decAtmSlotTable                     p.1.2.4
--          decAtmSlotEntry                   p.1.2.4.1
--            decAtmSlotIndex                 p.1.2.4.1.1
--            decAtmCardStatus                p.1.2.4.1.2
--            decAtmCardType                  p.1.2.4.1.3
--            decAtmCardHasModPhys            p.1.2.4.1.4
--            decAtmCardHwRev                 p.1.2.4.1.5
--            decAtmCardFwRev                 p.1.2.4.1.6
--            decAtmCardFault                 p.1.2.4.1.7
--      decAtmPort                            p.1.3
--        decAtmPortTable                     p.1.3.1
--          decAtmPortEntry                   p.1.3.1.1
--            decAtmPortIndex                 p.1.3.1.1.1
--            decAtmPortConnector             p.1.3.1.1.2
--      decAtmLed                             p.1.4
--        decAtmSlotLedTable                  p.1.4.1
--          decAtmSlotLedEntry                p.1.4.1.1
--            decAtmSlotLedIndex              p.1.4.1.1.1
--            decAtmSlotLedDescr              p.1.4.1.1.2
--            decAtmSlotLedProgram            p.1.4.1.1.3
--        decAtmPortLedTable                  p.1.4.2
--          decAtmPortLedEntry                p.1.4.2.1
--            decAtmPortLedIndex              p.1.4.2.1.1
--            decAtmPortLedDescr              p.1.4.2.1.2
--            decAtmPortLedProgram            p.1.4.2.1.3
--        decAtmLedInterestingChanges         p.1.4.3.0
--      decAtmClockCard                       p.1.5
--        decAtmMgmtMemoryAvail               p.1.5.1.0
--        decAtmMgmtMemoryAction              p.1.5.2.0
--      decAtmPsc                             p.1.6
--        decAtmPscStatus                     p.1.6.1.0
--        decAtmPscFwRev                      p.1.6.2.0
--        decAtmPscHwRev                      p.1.6.3.0
--        decAtmPscFwImageStatus              p.1.6.4.0
--        decAtmPscBackplaneStatus            p.1.6.5.0
--        decAtmPscFaultLedProgram            p.1.6.6.0
--      decAtmPowerSupply                     p.1.7
--        decAtmPowerSupplyTable              p.1.7.1
--          decAtmPowerSupplyEntry            p.1.7.1.1
--            decAtmPowerIndex                p.1.7.1.1.1
--            decAtmPowerStatus               p.1.7.1.1.2
--            decAtmPowerInputSource          p.1.7.1.1.3
--            decAtmPowerVoltage              p.1.7.1.1.4
--            decAtmPowerOutputInWatts        p.1.7.1.1.5
--            decAtmPowerFaultLedProgram      p.1.7.1.1.6
--            decAtmPowerOkLedProgram         p.1.7.1.1.7
--      decAtmBattery                         p.1.8
--        decAtmBatteryStatus                 p.1.8.1.0
--        decAtmBatteryUsing                  p.1.8.2.0
--        decAtmBatteryCharge                 p.1.8.3.0
--        decAtmBatteryTest                   p.1.8.4.0
--      decAtmTemperature                     p.1.9
--        decAtmCabinetTemperature            p.1.9.1.0
--        decAtmTemperatureWarning            p.1.9.2.0
--        decAtmTemperatureLedProgram         p.1.9.3.0
--      decAtmFan                             p.1.10
--        decAtmFanSpeed                      p.1.10.1.0
--        decAtmFanTable                      p.1.10.2
--          decAtmFanEntry                    p.1.10.2.1
--            decAtmFanIndex                  p.1.10.2.1.1
--            decAtmFanStatus                 p.1.10.2.1.2
--            decAtmFanFaultLedProgram        p.1.10.2.1.3
--      decAtmFppnTable                       p.1.11
--        decAtmFppnEntry                     p.1.11.1
--          decAtmFppnSlotNumber              p.1.11.1.1
--          decAtmFppnPortOfThatSlot          p.1.11.1.2
--          decAtmFppnIfIndex                 p.1.11.1.3
--      decAtmUpgradeSoftware                 p.1.12
--        decAtmLoad                          p.1.12.1
--          decAtmLoadAdminStatus             p.1.12.1.1
--          decAtmLoadOperStatus              p.1.12.1.2
--          decAtmLoadFilename                p.1.12.1.3
--          decAtmLoadIpHostAddr              p.1.12.1.4
--          decAtmLoadDevSpecific             p.1.12.1.5
--          decAtmConfigIpHostAddr            p.1.12.1.6
--          decAtmConfigDefaultGateway        p.1.12.1.7
--          decAtmConfigFilename              p.1.12.1.8
--          decAtmConfigStatus                p.1.12.1.9


-- ===========================================================================
-- =====================  S t a r t   o f   M I B   ==========================
-- ===========================================================================

IMPORTS

    enterprises, IpAddress, Counter
	FROM RFC1155-SMI

    OBJECT-TYPE
	FROM RFC-1212

    DisplayString
	FROM RFC1213-MIB;


--  Path to the chassis MIB.  (This may be imported from another module
--  in some versions of this MIB.)

dec                 OBJECT IDENTIFIER ::= { enterprises 36 }
ema                 OBJECT IDENTIFIER ::= { dec 2 }
decMIBextension     OBJECT IDENTIFIER ::= { ema 18 }

--  The DEC ATM chassis MIB.


--  decAtmChassisMIB MODULE-IDENTITY
--
--    LAST-UPDATED "9609260000Z"
--    ORGANIZATION "Digital Equipment Corporation"
--    CONTACT-INFO
--
--        "Digital Equipment Corporation
--         550 King Street
--         Littleton, MA  01460
--         United States of America"
--
--    DESCRIPTION
--
--        "This module defines a portion of the management information
--         base (MIB) for DEC ATM switches, including GIGAswitch/ATM."
--
--    ::= { decMIBextension 30 }


decAtmChassisMIB         OBJECT IDENTIFIER ::= { decMIBextension 30 }

decAtmChassisMIBObjects  OBJECT IDENTIFIER ::= { decAtmChassisMIB 1 }


-- ===========================================================================
-- ===================   T h e  S y s t e m  G r o u p   =====================
-- ===========================================================================


--
--  This group is mandatory.
--


decAtmSysGroup      OBJECT IDENTIFIER  ::=  { decAtmChassisMIBObjects 1 }


decAtmSysType OBJECT-TYPE
    SYNTAX  INTEGER {
		other(1),
		an2(2),                    --  A prototype GIGAswitch/ATM
		gigaswitchAtm(3),
		hubSwitch(4)
	    }
    ACCESS  read-only
    STATUS  mandatory
    DESCRIPTION
	    "Indicates the overall type of chassis."
    ::= { decAtmSysGroup 1 }


decAtmKeyswitchPosition OBJECT-TYPE
    SYNTAX  INTEGER {
		noKeyswitch(1),
		fault(2),
		secure(3),
		local(4),
		remote(5),
		worldAccess(6),
		unknown(7)
	    }
    ACCESS  read-only
    STATUS  mandatory
    DESCRIPTION
	    "Indicates the position of the keyswitch.  The keyswitch
	     position determines the type of access allowed to network
	     management and to out-of-band management.

	     For SNMP access, 'secure' means no SNMP access.  'Local'
	     means read-only SNMP access.  Other values allow read-
	     write SNMP access.  Access is still subject to community
	     string, IP address, and privileged port restrictions.

	     Now that I think about it, the 'secure' value (which was
	     copied from GIGAswitch/FDDI) is silly.  If the keyswitch
	     is in that position, you will not be able to read <this>
	     object (unless SNMP makes a special exception)."
    ::= { decAtmSysGroup 2 }




-- ===========================================================================
-- =======================   T h e  S l o t  G r o u p   =====================
-- ===========================================================================


--
--  This group is mandatory.  It provides information about the linecards that
--  are currently installed in the chassis.
--
--  DEChub 900 modules such as the ATMswitch900F and ATMswitch900T do not have
--  card slots, but will be treated as one-slot switches for MIB purposes.
--


decAtmSlot          OBJECT IDENTIFIER  ::=  { decAtmChassisMIBObjects 2 }


decAtmSlotNumber OBJECT-TYPE
    SYNTAX  INTEGER
    ACCESS  read-only
    STATUS  mandatory
    DESCRIPTION
	    "The number of slots in the box."
    ::= { decAtmSlot 1 }


decAtmMasterLinecardSlot OBJECT-TYPE
    SYNTAX  INTEGER
    ACCESS  read-only
    STATUS  mandatory
    DESCRIPTION
	    "Identifies the slot that the master line card occupies.
	     A value of 0 will be returned if a master has not been
	     chosen, or if the concept of a master line card has no
	     meaning for the chassis."
    ::= { decAtmSlot 2 }


decAtmStandbyLinecardSlot OBJECT-TYPE
    SYNTAX  INTEGER
    ACCESS  read-only
    STATUS  mandatory
    DESCRIPTION
	    "Identifies the slot which the standby master occupies.
	     A value of 0 will be returned if a standby master has
	     not been chosen, or if the concept of a standby master
	     has no meaning for the chassis."
    ::= { decAtmSlot 3 }


decAtmSlotTable OBJECT-TYPE
    SYNTAX  SEQUENCE OF DecAtmSlotEntry
    ACCESS  not-accessible
    STATUS  mandatory
    DESCRIPTION
	    "Describes the current configuration of the box."
    ::= { decAtmSlot 4 }


decAtmSlotEntry OBJECT-TYPE
    SYNTAX  DecAtmSlotEntry
    ACCESS  not-accessible
    STATUS  mandatory
    DESCRIPTION
	    "Each entry contains the description and status of one
	     linecard."
    INDEX   { decAtmSlotIndex }
::= { decAtmSlotTable 1 }


DecAtmSlotEntry ::= SEQUENCE {
    decAtmSlotIndex               INTEGER,
    decAtmCardStatus              INTEGER,
    decAtmCardType                INTEGER,
    decAtmCardHasModPhys          INTEGER,
    decAtmCardHwRev               DisplayString,
    decAtmCardFwRev               DisplayString,
    decAtmCardFault               INTEGER
}


decAtmSlotIndex OBJECT-TYPE
    SYNTAX  INTEGER
    ACCESS  read-only
    STATUS  mandatory
    DESCRIPTION
	    "The slot number. Varies from 1 to decAtmSlotNumber."
    ::= { decAtmSlotEntry 1 }


decAtmCardStatus OBJECT-TYPE
    SYNTAX  INTEGER {
	       notPresent(1),
	       powerDown(2),        -- present but not poweredUp
	       powerUp(3),          -- present and poweredUp
	       powerDownThenUp(4),  -- for upgrading the firmware
	       fault(5),
	       revisionMismatch(6),
	       selfTestInProgress(7)
	    }
    ACCESS  read-write
    STATUS  mandatory
    DESCRIPTION
	    "The status of the card. If the value is
	     read as 'notPresent(1)', then the entire entry 
	     should be considered invalid.

	     Writing a value of 'powerDown(2)' will cause
	     the switch to power down the card. Writing a
	     value of 'powerUp(3)' will cause the switch to
	     power up the card.  Writing a value of
	     'powerDownThenUp(4)' will cause the switch to power
	     cycle the line card.  Attempts to set any other
	     values will result in a badValue error.

	     Cards which are fundamental to switch operation
	     cannot be powered up or down through this object.

	     Unpopulated slots will either be 'notPresent(1)'
	     or missing from the table, and cannot be powered
	     up or down."
    ::= { decAtmSlotEntry 2 }


decAtmCardType OBJECT-TYPE
    SYNTAX  INTEGER {
	       none(1),       -- empty slot
	       other(2),      -- none of the following
	       clockCard(3),  -- clock/management card for GIGAswitch/ATM
	       qlc10(4),      -- AN2 card : Four 155 Mb/s SONET ports, all MMF
	       qlc15(5),      -- DAGGL-AA : Four 155 Mb/s SONET ports, all MMF
	       qlc16(6),      -- DAGGL-AB : Four 155 Mb/s ports - 2 MMF, 2 SMF
	       qlc20(7),      -- DAGGL-BA : Four mod-PHYs (up to 155 Mb/s ea.)
	       qlc622(8),     -- DAGGL-Cx : One  622 Mb/s SONET port ( the 'q'
			      --            here is a typo )
	       hubSwitch(9)   -- fake card type used to make DEChub 900 ATM
			      -- switch fit into this MIB's slot/port model
	    }
    ACCESS  read-only
    STATUS  mandatory
    DESCRIPTION
	    "The type of the card."
    ::= { decAtmSlotEntry 3 }


decAtmCardHasModPhys OBJECT-TYPE
    SYNTAX  INTEGER {
	       true(1),
	       false(2)
	    }
    ACCESS  read-only
    STATUS  mandatory
    DESCRIPTION
	    "Indicates whether the linecard has modular physical
	     connectors."
    ::= { decAtmSlotEntry 4 }


decAtmCardHwRev OBJECT-TYPE
    SYNTAX  DisplayString
    ACCESS  read-only
    STATUS  mandatory
    DESCRIPTION
	    "The hardware revision of the card."
    ::= { decAtmSlotEntry 5 }


decAtmCardFwRev OBJECT-TYPE
    SYNTAX  DisplayString
    ACCESS  read-only
    STATUS  mandatory
    DESCRIPTION
	    "The firmware revision of the card."
    ::= { decAtmSlotEntry 6 }


decAtmCardFault OBJECT-TYPE
    SYNTAX  INTEGER
    ACCESS  read-only
    STATUS  mandatory
    DESCRIPTION
	    "Contains a diagnostic code which may aid in troubleshooting
	     faulty cards.  Meaningless if decAtmCardStatus is not equal
	     to 'fault'."
    ::= { decAtmSlotEntry 7 }




-- ===========================================================================
-- =======================   T h e  P o r t  T a b l e   =====================
-- ===========================================================================


--
--  This group is mandatory.  It provides information about the ports that are
--  currently installed.
--


decAtmPort          OBJECT IDENTIFIER  ::=  { decAtmChassisMIBObjects 3 }


decAtmPortTable OBJECT-TYPE
    SYNTAX  SEQUENCE OF DecAtmPortEntry
    ACCESS  not-accessible
    STATUS  mandatory
    DESCRIPTION
	    "Describes the current configuration of the box."
    ::= { decAtmPort 1 }


decAtmPortEntry OBJECT-TYPE
    SYNTAX  DecAtmPortEntry
    ACCESS  not-accessible
    STATUS  mandatory
    DESCRIPTION
	    "Each entry describes one physical port."
    INDEX   { decAtmSlotIndex, decAtmPortIndex }
    ::= { decAtmPortTable 1 }


DecAtmPortEntry ::= SEQUENCE {
    decAtmPortIndex               INTEGER,
    decAtmPortConnector           INTEGER
}


decAtmPortIndex OBJECT-TYPE
    SYNTAX  INTEGER
    ACCESS  read-only
    STATUS  mandatory
    DESCRIPTION
	    "The port number.  Varies from 1 to the number of
	     ATM ports on the linecard."
    ::= { decAtmPortEntry 1 }


decAtmPortConnector OBJECT-TYPE
    SYNTAX  INTEGER {
	       other(1),
	       notPresent(2),
	       sts3cSingleModeFiber(3),    -- SONET STS-3c SMF
	       sts3cMultiModeFiber(4),     -- SONET STS-3c MMF
	       sts3cTwistedPair(5),        -- SONET STS-3c UTP
	       t3(6),                      -- T3 ATM coaxial cable
	       e3(7),                      -- E3 ATM coaxial cable
	       e1(8),                      -- E1 ATM UTP (mini-jack connector)
	       sts1TwistedPair(9),         -- SONET STS-1 UTP
	       e3Hdlc(10),                 -- E3 HDLC (frame relay) coaxial
	       e3Proto(11),                -- Old E3 ATM coaxial cable PHY
	       sts12cSingleModeFiber(12),  -- SONET STS-12c SMF
	       sts12cMultiModeFiber(13),   -- SONET STS-13c MMF
	       t1(14)                      -- T1 ATM UTP (mini-jack connector)
	    }
    ACCESS  read-only
    STATUS  mandatory
    DESCRIPTION
	    "The type of physical layer hardware currently in
	     use by this ATM port."
    ::= { decAtmPortEntry 2 }

--
--  For mod-PHY ports, I believe that decAtmPortConnector values translate into
--  Digital part numbers as follows:
--
--
--      decAtmPortConnector                    Model number for mod-PHY card
--      ===================                    ==============================
--      port-type-other                        unknown
--      port-type-notPresent                   none
--      port-type-sts3cSingleModeFiber         DAGGS-AA
--      port-type-sts3cMultiModeFiber          DAGGM-AA
--      port-type-sts3cTwistedPair             DAGGU-AA
--      port-type-t3                           DAGGT-AA
--      port-type-e3                           DAGGE-AA
--      port-type-e1                           DAGE1-AA
--      port-type-sts1TwistedPair              unknown
--      port-type-e3Hdlc                       unknown
--      port-type-e3Proto                      DAGGE-AA prototype
--      port-type-sts12cSingleModeFiber        not available in mod-PHY form
--      port-type-sts12cMultiModeFiber         not available in mod-PHY form
--      port-type-t1                           DAGT1-AA
--





-- ===========================================================================
-- ========================   T h e  L E D  G r o u p   ======================
-- ===========================================================================


--
--  This group is mandatory.  It provides information about LEDs on currently-
--  installed linecards.  LEDs are arranged into two tables:
--
--      1.  The 'decAtmPortLedTable' describes LEDs which are associated
--          with a particular port.
--
--      2.  The 'decAtmSlotLedTable' describes LEDs which are associated
--          with the linecard as a whole.
--
--  For convenience, the LED objects use the same scheme as the pcomLedProgram
--  object in the DECHUB900-COMMON MIB.
--



decAtmLed           OBJECT IDENTIFIER  ::=  { decAtmChassisMIBObjects 4 }


decAtmSlotLedTable OBJECT-TYPE
    SYNTAX  SEQUENCE OF DecAtmSlotLedEntry
    ACCESS  not-accessible
    STATUS  mandatory
    DESCRIPTION
	"A list of LED entries, one for each module LED."
    ::= { decAtmLed 1 }
	    

decAtmSlotLedEntry OBJECT-TYPE
    SYNTAX  DecAtmSlotLedEntry
    ACCESS  not-accessible
    STATUS  mandatory
    DESCRIPTION
	"Each entry describes the state of one module LED."
    INDEX { decAtmSlotIndex, decAtmSlotLedIndex }
    ::= { decAtmSlotLedTable 1 }
	    

DecAtmSlotLedEntry ::=
    SEQUENCE {
	decAtmSlotLedIndex
	    INTEGER,
	decAtmSlotLedDescr
	    DisplayString,
	decAtmSlotLedProgram
	    OCTET STRING
    }
	    

decAtmSlotLedIndex OBJECT-TYPE
    SYNTAX  INTEGER (1..65535)
    ACCESS  read-only
    STATUS  mandatory
    DESCRIPTION
	"Secondary index which allows us to model cards with more than
	 one module LED.  The mapping between 'decAtmSlotLedIndex' and
	 physical LEDs will be consistent for each 'decAtmCardType'."
    ::= { decAtmSlotLedEntry 1 }
	    

decAtmSlotLedDescr OBJECT-TYPE
    SYNTAX  DisplayString (SIZE(0..80))
    ACCESS  read-only
    STATUS  mandatory
    DESCRIPTION
	"A textual description of the information which the LED is
	 meant to convey.  i.e.:
	    
	   +5 Volt Power, DC Okay
	   ATM port activity.
	   Diagnostic status."
    ::= { decAtmSlotLedEntry 2 }
	    

decAtmSlotLedProgram OBJECT-TYPE
    SYNTAX  OCTET STRING (SIZE(0..48))
    ACCESS  read-only
    STATUS  mandatory
    DESCRIPTION
	"The decAtmSlotLedProgram string is a sequence of instructions
	 for the LED state.  The LED constantly repeats the
	 program.  Each LED state is represented by a two octet
	 sequence where the value of the first octet of the pair
	 indicates the color of the LED, and the value of the
	 second octet of the pair indicates the duration in which
	 that color will be present.

	 +----------+----------+  --/ /--  +----------+----------+
	 |   Color  | Duration |           |   Color  | Duration |
	 +----------+----------+  --/ /--  +----------+----------+
	    
	 The 'color' octet may have one of the following values:

	    0 - off
	    1 - other
	    2 - red
	    3 - yellow
	    4 - green
	    5 - blue
	    6 - red-blinking
	    7 - yellow-blinking
	    8 - blue-blinking
	    9 - green-blinking
	    
	 The value 'off' indicates that the LED is off.
	    
	 The value 'other' indicates a color not covered by any
	 others in the list.

	 The value of the second octet in each pair indicates the
	 duration in which that color will be present.  A value
	 of zero indicates that the LED is off.  A value of 0xff
	 indicates that the LED is always on.  Values in between
	 0 and 0xff indicate the duration in 10 ms ticks.

	 A zero length string may be returned if the LED is 'not
	 present'.  This indicates that the LED is currently not
	 visible.
	    
	 Activity LEDs are a special case.  Activity LEDs are
	 defined as LEDs which blink whenever data is received on
	 the line.  They are typically on solid under heavy
	 activity.  Since these LEDs can change rapidly, the
	 following rules apply:
	    
	   o  The initial state of activity LEDs is off.
	   o  If the line shows activity any time in a 10 second
	      period, then the LED is shown as on.
	   o  If the line shown inactivity any time in a 10 second
	      period, then the LED is shown as off.

	See the 'pcomLedProgram' object in the DECHUB900-COMMON MIB
	for examples."
    ::= { decAtmSlotLedEntry 3 }
	    

decAtmPortLedTable OBJECT-TYPE
    SYNTAX  SEQUENCE OF DecAtmPortLedEntry
    ACCESS  not-accessible
    STATUS  mandatory
    DESCRIPTION
	"A list of LED entries, one for each port LED."
    ::= { decAtmLed 2 }
	    

decAtmPortLedEntry OBJECT-TYPE
    SYNTAX  DecAtmPortLedEntry
    ACCESS  not-accessible
    STATUS  mandatory
    DESCRIPTION
	"Each entry describes the state of one port LED."
    INDEX { decAtmSlotIndex, decAtmPortIndex, decAtmPortLedIndex }
    ::= { decAtmPortLedTable 1 }
	    

DecAtmPortLedEntry ::=
    SEQUENCE {
	decAtmPortLedIndex
	    INTEGER,
	decAtmPortLedDescr
	    DisplayString,
	decAtmPortLedProgram
	    OCTET STRING
	}
	    

decAtmPortLedIndex OBJECT-TYPE
    SYNTAX  INTEGER (1..65535)
    ACCESS  read-only
    STATUS  mandatory
    DESCRIPTION
	"Secondary index which lets us model ports with multiple LEDs."
    ::= { decAtmPortLedEntry 1 }
	    

decAtmPortLedDescr OBJECT-TYPE
    SYNTAX  DisplayString (SIZE(0..80))
    ACCESS  read-only
    STATUS  mandatory
    DESCRIPTION
	"A textual description of the information which the LED is
	 meant to convey.  i.e.:
	    
	   +5 Volt Power, DC Okay
	   ATM port activity.
	   Diagnostic status."
    ::= { decAtmPortLedEntry 2 }
	    

decAtmPortLedProgram OBJECT-TYPE
    SYNTAX  OCTET STRING (SIZE(0..48))
    ACCESS  read-only
    STATUS  mandatory
    DESCRIPTION
	"The decAtmLedProgram string is a sequence of instructions
	 for the LED state.  The LED constantly repeats the
	 program.  Each LED state is represented by a two octet
	 sequence where the value of the first octet of the pair
	 indicates the color of the LED, and the value of the
	 second octet of the pair indicates the duration in which
	 that color will be present.
	    
	 +----------+----------+  --/ /--  +----------+----------+
	 |   Color  | Duration |           |   Color  | Duration |
	 +----------+----------+  --/ /--  +----------+----------+
	    
	 The 'color' octet may have one of the following values:

	    0 - off
	    1 - other
	    2 - red
	    3 - yellow
	    4 - green
	    5 - blue
	    6 - red-blinking
	    7 - yellow-blinking
	    8 - blue-blinking
	    9 - green-blinking

	 The value 'off' indicates that the LED is off.

	 The value 'other' indicates a color not covered by any
	 others in the list.

	 The value of the second octet in each pair indicates the
	 duration in which that color will be present.  A value
	 of zero indicates that the LED is off.  A value of 0xff
	 indicates that the LED is always on.  Values in between
	 0 and 0xff indicate the duration in 10 ms ticks.
	    
	 A zero length string may be returned if the LED is 'not
	 present'.  This indicates that the LED is currently not
	 visible.
	    
	 Activity LEDs are a special case.  Activity LEDs are
	 defined as LEDs which blink whenever data is received on
	 the line.  They are typically on solid under heavy
	 activity.  Since these LEDs can change rapidly, the
	 following rules apply:
	    
	   o  The initial state of activity LEDs is off.
	   o  If the line shows activity any time in a 10 second
	      period, then the LED is shown as on.
	   o  If the line shown inactivity any time in a 10 second
	      period, then the LED is shown as off.

	See the 'pcomLedProgram' object in the DECHUB900-COMMON MIB
	for examples."
    ::= { decAtmPortLedEntry 3 }
	    

decAtmLedInterestingChanges OBJECT-TYPE
    SYNTAX  Counter
    ACCESS  read-only
    STATUS  mandatory
    DESCRIPTION
	"This counter may be polled to determine if any
	 interesting changes in the decAtmSlotLedTable
	 or decAtmPortLedTable have occurred."
    ::= { decAtmLed 3 }




-- ===========================================================================
-- ===============   T h e  C l o c k  C a r d  G r o u p   ==================
-- ===========================================================================


--
--  This group is mandatory for GIGAswitch/ATM systems.  It is not necessarily
--  applicable to other DEC ATM switches, and so is optional for them.
--
--
--  Note:  Because clock card firmware and hardware revisions can be retrieved
--         from the slotTable, they are not included here.


decAtmClockCard     OBJECT IDENTIFIER  ::=  { decAtmChassisMIBObjects 5 } 


decAtmMgmtMemoryAvail OBJECT-TYPE
    SYNTAX  INTEGER
    ACCESS  read-only
    STATUS  mandatory
    DESCRIPTION
	    "The number of unused bytes of management memory available
	     on the clock card.  The management memory is used for
	     storing management parameters."
    ::= { decAtmClockCard 1 }


decAtmMgmtMemoryAction OBJECT-TYPE
    SYNTAX  INTEGER {
	       other(1),
	       rewrite(2),
	       rewriting(3)
	    }
    ACCESS  read-write
    STATUS  mandatory
    DESCRIPTION
	    "This object, when read, returns a value of other(1) unless
	     the switch is in the middle of rewriting management memory.
	     At such times, it will return rewriting(3).  The state will
	     revert to other(1) when the action is completed.

	     Setting this variable to rewrite(2) will cause the switch
	     to attempt to rewrite the management memory on the
	     clock-card.  Attempts to set this variable to all other
	     values will result in an error.

	     Rewriting the management memory gets rid of duplicate
	     duplicate entries, and thus may increase the available
	     space.  This action should be allowed to complete before
	     you intentionally remove power from the switch."
    ::= { decAtmClockCard 2 }


--
--  In a GIGAswitch/ATM system, the clock card acts as a sort of 'bridge'
--  between the external Ethernet and an internal Ethernet.
--


decGigaAtmIntEthPktsSent OBJECT-TYPE
    SYNTAX  Counter
    ACCESS  read-only
    STATUS  mandatory
    DESCRIPTION
	    "The number of packets which the clock card has transmitted
	     over the internal Ethernet."
    ::= { decAtmClockCard 3 }


decGigaAtmIntEthPktsRcvd OBJECT-TYPE
    SYNTAX  Counter
    ACCESS  read-only
    STATUS  mandatory
    DESCRIPTION
	    "The number of packets which the clock card has received
	     from the internal Ethernet."
    ::= { decAtmClockCard 4 }


decGigaAtmExtEthPktsSent OBJECT-TYPE
    SYNTAX  Counter
    ACCESS  read-only
    STATUS  mandatory
    DESCRIPTION
	    "The number of packets which the clock card has transmitted
	     over the external Ethernet."
    ::= { decAtmClockCard 5 }


decGigaAtmExtEthPktsRcvd OBJECT-TYPE
    SYNTAX  Counter
    ACCESS  read-only
    STATUS  mandatory
    DESCRIPTION
	    "The number of packets which the clock card has received
	     from the external Ethernet."
    ::= { decAtmClockCard 6 }




-- ===========================================================================
-- ====   T h e  P o w e r  S y s t e m  C o n t r o l l e r  G r o u p   ====
-- ===========================================================================


--
--  This group is mandatory for GIGAswitch/ATM systems which have Power System
--  Controllers.  It is not necessarily applicable to other DEC ATM switches -
--  and so is optional for them.
--


decAtmPsc           OBJECT IDENTIFIER  ::=  { decAtmChassisMIBObjects 6 }


decAtmPscStatus OBJECT-TYPE
    SYNTAX  INTEGER {
	       notPresent(1),
	       okay(2),
	       fault(3),
	       unknown(4)
	    }
    ACCESS  read-only
    STATUS  mandatory
    DESCRIPTION
	    "The status of the Power System Controller (PSC)."
    ::= { decAtmPsc 1 }


decAtmPscFwRev OBJECT-TYPE
    SYNTAX  DisplayString
    ACCESS  read-only
    STATUS  mandatory
    DESCRIPTION
	    "The firmware revision of the Power System Controller
	     (PSC).  This is only meaningful if the PSC is present."
    ::= { decAtmPsc 2 }


decAtmPscHwRev OBJECT-TYPE
    SYNTAX  DisplayString
    ACCESS  read-only
    STATUS  mandatory
    DESCRIPTION
	    "The hardware revision of the Power System Controller
	    (PSC).  This is only meaningful if the PSC is present."
    ::= { decAtmPsc 3 }


decAtmPscFwImageStatus OBJECT-TYPE
    SYNTAX  INTEGER {
	       okay(1),
	       downloadRequired(2),
	       unknown(3)
	    }
    ACCESS  read-only
    STATUS  mandatory
    DESCRIPTION
	    "The status of the PSC firmware image. If the value of this
	     object is downloadRequired(2), the manager should download
	     a new firmware image to the PSC.  This can be done by using
	     objects in the gigaUpgradeSoftware group."
    ::= { decAtmPsc 4 }


decAtmPscBackplaneStatus OBJECT-TYPE
    SYNTAX  INTEGER {
	       okay(1),
	       fault(2),
	       unknown(3)
	    }
    ACCESS  read-only
    STATUS  mandatory
    DESCRIPTION
	    "The status of the GIGAswitch backplane."
    ::= { decAtmPsc 5 }


decAtmPscFaultLedProgram OBJECT-TYPE                    --  New for MIB V1.1
    SYNTAX  OCTET STRING (SIZE(0..48))
    ACCESS  read-only
    STATUS  mandatory
    DESCRIPTION
	   "The decAtmPscFaultLedProgram string is a sequence of instructions
	    for the power supply controller fault LED state.

	    The coding rules are as described for decAtmSlotLedProgram.

	    A zero-length string may be returned if the LED is 'not present',
	    or if the state of the LED is unknown."
    ::= { decAtmPsc 6 }



-- ===========================================================================
-- ================   T h e  P o w e r  S u p p l y  G r o u p   =============
-- ===========================================================================


--
--  This group is mandatory for GIGAswitch/ATM systems.  It is not necessarily
--  applicable to other DEC ATM switches, and so is optional for them.
--
--  In particular, ATM switch modules designed to fit into the DEChub 900 will
--  normally report power supply status via appropriate DEChub 900 MIBs.
--


decAtmPowerSupply   OBJECT IDENTIFIER  ::=  { decAtmChassisMIBObjects 7 }


decAtmPowerSupplyTable OBJECT-TYPE
    SYNTAX         SEQUENCE OF DecAtmPowerSupplyEntry
    ACCESS         not-accessible
    STATUS         mandatory
    DESCRIPTION
	    "A table describing all of the power supplies for this
	     chassis."
    ::= { decAtmPowerSupply 1 }


decAtmPowerSupplyEntry OBJECT-TYPE
    SYNTAX         DecAtmPowerSupplyEntry
    ACCESS         not-accessible
    STATUS         mandatory
    DESCRIPTION
	    "Each table entry describes one power supply."
    INDEX   { decAtmPowerIndex }
::= { decAtmPowerSupplyTable 1 }


DecAtmPowerSupplyEntry ::=
    SEQUENCE {
	decAtmPowerIndex             INTEGER,
	decAtmPowerStatus            INTEGER,
	decAtmPowerInputSource       INTEGER,
	decAtmPowerVoltage           INTEGER,
	decAtmPowerOutputInWatts     INTEGER,
	decAtmPowerFaultLedProgram   OCTET STRING,     --  New for MIB V1.1
	decAtmPowerOkLedProgram      OCTET STRING      --  New for MIB V1.1
		
    }


decAtmPowerIndex OBJECT-TYPE
    SYNTAX  INTEGER
    ACCESS  read-only
    STATUS  mandatory
    DESCRIPTION
	    "A unique index identifying each power supply.

	     For a GIGAswitch/ATM chassis, the left power supply
	     unit always has index 1, and the right power supply
	     unit always has index 2."
    ::= { decAtmPowerSupplyEntry 1 }


decAtmPowerStatus OBJECT-TYPE
    SYNTAX  INTEGER {
	       notPresent(1),
	       okay(2),
	       fault(3),
	       unknown(4)
	    }
    ACCESS  read-only
    STATUS  mandatory
    DESCRIPTION
	    "The status of the power supply unit."
::= { decAtmPowerSupplyEntry 2 }


decAtmPowerInputSource OBJECT-TYPE
    SYNTAX  INTEGER {
	       acLine(1),
	       dc48V(2),
	       decHub(3),
	       none(4),
	       unknown(5)
	    }
    ACCESS  read-only
    STATUS  mandatory
    DESCRIPTION
	    "The input source of the power supply.

	     A value of acLine(1) is returned if the power supply
	     is connected to an AC line.
 
	     A value of dc48V(2) is returned if the power supply is
	     connected to a 48 volt DC (telecommunications) line.

	     A value of decHub(3) is returned if the module's power
	     is being provided by a DEChub900.

	     A value of none(4) is returned if the power unit is
	     not present or not powered on.

	     See the batteryUsing object to see if the battery or
	     this power source is being used.                     "
    ::= { decAtmPowerSupplyEntry 3 }


decAtmPowerVoltage OBJECT-TYPE
    SYNTAX  INTEGER
    ACCESS  read-only
    STATUS  mandatory
    DESCRIPTION
	    "Voltage of power supply."
    ::= { decAtmPowerSupplyEntry 4 }

decAtmPowerOutputInWatts OBJECT-TYPE
    SYNTAX  INTEGER 
    ACCESS  read-write
    STATUS  mandatory
    DESCRIPTION
	    "Output power of power supply, in watts.

	     This is normally read-only.  However, the full-sized
	     GIGAswitch/ATM accepts both 15 and 20 amp supplies -
	     and has no way of automatically determining which is
	     installed.

	     The agent may optionally permit write access to this
	     object, in which case the following rules apply:

	     To inform a GIGAswitch/ATM that it has a 20 amp power
	     supply, write 1300 to this object.

		 Warning:  Don't do this until the new power supply
			   is installed.  Otherwise, the switch may
			   crash and reboot.

	     To inform a GIGAswitch/ATM that it has a 15 amp power
	     supply, write 950 to this object.

		Warning:  Note that this may cause line cards to be
			  shut down, as the switch readjusts to the
			  lower power budget.                        
	    "
    ::= { decAtmPowerSupplyEntry 5 }


decAtmPowerFaultLedProgram OBJECT-TYPE                 --  New for MIB V1.1
    SYNTAX  OCTET STRING (SIZE(0..48))
    ACCESS  read-only
    STATUS  mandatory
    DESCRIPTION
	   "The decAtmPowerFaultLedProgram string is a sequence of
	    instructions for the power supply fault LED state.

	    The coding rules are as described for decAtmSlotLedProgram.

	    A zero-length string may be returned if the LED is 'not present',
	    or if the state of the LED is unknown."
    ::= { decAtmPowerSupplyEntry 6 }


decAtmPowerOkLedProgram OBJECT-TYPE                     --  New for MIB V1.1
    SYNTAX  OCTET STRING (SIZE(0..48))
    ACCESS  read-only
    STATUS  mandatory
    DESCRIPTION
	   "The decAtmPowerOkLedProgram string is a sequence of instructions
	    for the power supply OK LED state.

	    The coding rules are as described for decAtmSlotLedProgram.

	    A zero-length string may be returned if the LED is 'not present',
	    or if the state of the LED is unknown."
    ::= { decAtmPowerSupplyEntry 7 }




-- ===========================================================================
-- ====================   T h e  B a t t e r y  G r o u p   ==================
-- ===========================================================================


--
--  This group is mandatory for GIGAswitch/ATM systems.  It is not necessarily
--  applicable to other DEC ATM switches, and so is optional for them.
--


decAtmBattery       OBJECT IDENTIFIER  ::=  { decAtmChassisMIBObjects 8 }


decAtmBatteryStatus OBJECT-TYPE
    SYNTAX  INTEGER {
	       notPresent(1),
	       okay(2),
	       fault(3),
	       unknown(4)
	    }
    ACCESS  read-only
    STATUS  mandatory
    DESCRIPTION
	    "The status of the backup battery."
    ::= { decAtmBattery 1 }


decAtmBatteryUsing OBJECT-TYPE
    SYNTAX  INTEGER {
	       batteryPower(1),
	       externalPower(2),
	       unknown(3)
	    }
    ACCESS  read-only
    STATUS  mandatory
    DESCRIPTION
	    "The source of power being used for the box.  The value
	     batteryPower(2) indicates that the backup battery unit
	     is being used to power the switch.  The external power
	     line can be any standard power supply (e.g., either AC
	     or 48V DC telecommunications power for GIGAswitch/ATM)."
    ::= { decAtmBattery 2 }


decAtmBatteryCharge OBJECT-TYPE
    SYNTAX  INTEGER {
	       fullyCharged(1),
	       okay(2),
	       low(3),
	       unknown(4)
	    }
    ACCESS  read-only
    STATUS  mandatory
    DESCRIPTION
	    "The charge-level of the backup battery.  Meaningful
	     only if the battery is present."
    ::= { decAtmBattery 3 }


decAtmBatteryTest OBJECT-TYPE
    SYNTAX  INTEGER {
	       pass(1),
	       fail(2),
	       test(3),
	       notTested(4)    
	    }
    ACCESS  read-write
    STATUS  mandatory
    DESCRIPTION
	    "This shows the result of the last battery test performed.
	     Testing the battery is risky -- the system is temporarily
	     switched to run off the battery, so if the battery backup
	     subsystem is not working, the system fails and restarts.

	     Only the value test(3) can be written.  Writes of other
	     values are erroneous.

	     This object is meaningful only if the battery is present."
    ::= { decAtmBattery 4 }




-- ===========================================================================
-- ========   T h e  T e m p e r a t u r e  S e n s i n g  G r o u p   =======
-- ===========================================================================


--
--  This group is mandatory for GIGAswitch/ATM systems.  It is not necessarily
--  applicable to other DEC ATM switches, and so is optional for them.
--
--  In particular, ATM switch modules designed to fit into the DEChub 900 will
--  normally report environmental status via appropriate DEChub 900 MIBs.
--


decAtmTemperature   OBJECT IDENTIFIER  ::=  { decAtmChassisMIBObjects 9 }


decAtmCabinetTemperature OBJECT-TYPE
    SYNTAX  INTEGER {
		normal(1),
		high(2),
		excessivelyHigh(3),
		low(4),
		excessivelyLow(5),
		noSensor(6),
		unknown(7)
	    }
    ACCESS  read-only
    STATUS  mandatory
    DESCRIPTION
	    "The cabinet temperature.  Chassis types which do not have
	     temperature sensors will always return 'noSensor(6)'."
    ::= { decAtmTemperature 1 }


decAtmTemperatureWarning OBJECT-TYPE
    SYNTAX  INTEGER {
		heedWarning(1),
		ignoreWarning(2),
		noWarningFeature(3)
	    }
    ACCESS  read-write
    STATUS  mandatory
    DESCRIPTION
	    "The value of this variable determines how the switch will
	     respond to a condition of too high or too low cabinet
	     temperature, or a condition of all fans being inoperative.
	     If the value is 'heedWarning(1)', the system will be shut
	     down when the temperature goes outside the designed limits
	     or when too many of its fans become inoperative.  If the
	     value is 'ignoreWarning(2)', the system will continue to
	     operate when either of these conditions occur.

	     Setting this variable to 'ignoreWarning(2)' lets a manager
	     cause a system that is too hot or too cold to continue to
	     run.  This setting will also allow the system to run while
	     no fans are operative.  Managers should note that this may
	     be detrimental to the equipment.

	     This object has a default value of 'heedWarning(1)'.  Note
	     that some switches may lack auto-shutdown capability; they
	     will have a value of 'noWarningFeature(3) for this object."
    ::= { decAtmTemperature 2 }


decAtmTemperatureLedProgram OBJECT-TYPE                --  New for MIB V1.1
    SYNTAX  OCTET STRING (SIZE(0..48))
    ACCESS  read-only
    STATUS  mandatory
    DESCRIPTION
	   "The decAtmTemperatureLedProgram string is a sequence of
	    instructions for the temperature LED state.

	    The coding rules are as described for decAtmSlotLedProgram.

	    A zero-length string may be returned if the LED is 'not present',
	    or if the state of the LED is unknown."
    ::= { decAtmTemperature 3 }



-- ===========================================================================
-- ========================   T h e  F a n  G r o u p   ======================
-- ===========================================================================


--
--  This group is mandatory for GIGAswitch/ATM systems.  It is not necessarily
--  applicable to other DEC ATM switches, and so is optional for them.
--
--  In particular, ATM switch modules designed to fit into the DEChub 900 will
--  normally report environmental status via appropriate DEChub 900 MIBs.
--


decAtmFan           OBJECT IDENTIFIER  ::=  { decAtmChassisMIBObjects 10 }


decAtmFanSpeed OBJECT-TYPE
    SYNTAX  INTEGER {
	       maximum(1),
	       normal(2),
	       unknown(3)
	    }
    ACCESS  read-write
    STATUS  mandatory
    DESCRIPTION
	    "The speed of the fans.  Set this variable to 'maximum(1)'
	     for maximum cooling where noise does not matter.  Set this
	     variable to normal(2) to cause fan speeds to be under
	     temperature control."
::= { decAtmFan 1 }


decAtmFanTable OBJECT-TYPE
    SYNTAX         SEQUENCE OF DecAtmFanEntry
    ACCESS         not-accessible
    STATUS         mandatory
    DESCRIPTION
	    "A table describing all of the fans for this chassis."
::= { decAtmFan 2 }


decAtmFanEntry OBJECT-TYPE
    SYNTAX         DecAtmFanEntry
    ACCESS         not-accessible
    STATUS         mandatory
    DESCRIPTION
	    "Each table entry describes one fan."
    INDEX   { decAtmFanIndex }
::= { decAtmFanTable 1 }


DecAtmFanEntry ::=
    SEQUENCE {
	decAtmFanIndex             INTEGER,
	decAtmFanStatus            INTEGER,
	decAtmFanFaultLedProgram   OCTET STRING        --  New for MIB V1.1
    }


decAtmFanIndex OBJECT-TYPE
    SYNTAX  INTEGER
    ACCESS  read-only
    STATUS  mandatory
    DESCRIPTION
	    "A unique index identifying each fan.

	     For a GIGAswitch/ATM chassis, the left fan tray always
	     has an index of 1, while the right fan tray always has
	     an index of 2."
::= { decAtmFanEntry 1 }


decAtmFanStatus OBJECT-TYPE
    SYNTAX  INTEGER {
	       notPresent(1),
	       okay(2),
	       fault(3),
	       unknown(4)
	    }
    ACCESS  read-only
    STATUS  mandatory
    DESCRIPTION
	    "The status of the fan."
::= { decAtmFanEntry 2 }


decAtmFanFaultLedProgram OBJECT-TYPE
    SYNTAX  OCTET STRING (SIZE(0..48))
    ACCESS  read-only
    STATUS  mandatory
    DESCRIPTION
	   "The decAtmFanFaultLedProgram string is a sequence of instructions
	    for the fan tray fault LED state.

	    The coding rules are as described for decAtmSlotLedProgram.

	    A zero-length string may be returned if the LED is 'not present',
	    or if the state of the LED is unknown."
::= { decAtmFanEntry 3 }




-- ===========================================================================
-- =====   T h e  F r o n t  P a n e l  P o r t  N u m b e r  G r o u p   ====
-- ===========================================================================


--
--  This group is mandatory.
--


decAtmFppnTable OBJECT-TYPE
    SYNTAX  SEQUENCE OF DecAtmFppnEntry
    ACCESS  not-accessible
    STATUS  mandatory
    DESCRIPTION
	    "A list of front panel port number to MIB-II interface
	    number mappings."
    ::= { decAtmChassisMIBObjects 11 }


decAtmFppnEntry OBJECT-TYPE
    SYNTAX  DecAtmFppnEntry
    ACCESS  not-accessible
    STATUS  mandatory
    DESCRIPTION
	    "Assigns the MIB-II interface ifIndex for a physical
	    datalink (cable) connection to the box."
    INDEX   { decAtmFppnSlotNumber, decAtmFppnPortOfThatSlot }
    ::= { decAtmFppnTable 1 }


DecAtmFppnEntry ::= SEQUENCE {
    decAtmFppnSlotNumber          INTEGER,
    decAtmFppnPortOfThatSlot      INTEGER,
    decAtmFppnIfIndex             INTEGER
}


decAtmFppnSlotNumber OBJECT-TYPE
    SYNTAX  INTEGER
    ACCESS  read-only
    STATUS  mandatory
    DESCRIPTION
	    "The 1-based slot number of the module."
    ::= { decAtmFppnEntry 1 }


decAtmFppnPortOfThatSlot OBJECT-TYPE
    SYNTAX  INTEGER
    ACCESS  read-only
    STATUS  mandatory
    DESCRIPTION
	    "The 1-based media connection to the module."
    ::= { decAtmFppnEntry 2 }


decAtmFppnIfIndex OBJECT-TYPE
    SYNTAX  INTEGER
    ACCESS  read-only
    STATUS  mandatory
    DESCRIPTION
	    "The assigned MIB-II ifIndex.  For an ATM port, this is the
	     ifIndex of the 'atm' interface, as opposed to the index of
	     the AAL5 entity or the physical (SONET, DS3) interface."
    ::= { decAtmFppnEntry 3 }






-- ===========================================================================
-- ======================   T h e  L o a d  G r o u p   ======================
-- ===========================================================================


--
--  This group is optional.
--

decAtmUpgradeSoftware  OBJECT IDENTIFIER ::= { decAtmChassisMIBObjects 12 }

decAtmLoad             OBJECT IDENTIFIER ::= { decAtmUpgradeSoftware 1 }


decAtmLoadAdminStatus OBJECT-TYPE
    SYNTAX  INTEGER {
		other(1),
		start-reboot (2),
		start-read-BootP (3),
		start-read-TFTP (4)
		}
    ACCESS  read-write
    STATUS  mandatory
    DESCRIPTION
	"This object is used to control the program load process of
	 a device.  When read, the value other(1) is returned.

	 When set to start-reboot (2) the device reloads the stored
	 firmware.

	 When set to start-read-BootP(3) the device clears the
	 address and host configuration file location in NVRAM and
	 initiates a BootP read operation to find and read a new 
	 program image. 

	 When set to start-read-TFTP(4) the device saves the local host 
	 address and host configuration file location in NVRAM and
	 initiates a TFTP read operation to read a new program image. 

	 A device always resets during a successful load attempt.
	 It may not reset upon unsuccessful completion of the load attempt."
    
    ::= { decAtmLoad 1 }

decAtmLoadOperStatus OBJECT-TYPE
    SYNTAX  INTEGER {
		none(1),
		success(2),
		failure(3)
		}
    ACCESS  read-only
    STATUS  mandatory
    DESCRIPTION
	"The final state of the last load attempt.   none(1) indicates 
	 that no load has been attempted, ever.
    
	 This object is non-volatile.  It's default value is none(1)."
    ::= { decAtmLoad 2 }
    
decAtmLoadFilename OBJECT-TYPE
    SYNTAX  DisplayString (SIZE(0..64))
    ACCESS  read-write
    STATUS  mandatory
    DESCRIPTION
	"The name of the file in which to load.  When the device is
	 reading, this is the name of the file to be read. If the device
	 can not check the file name then this object is ignored. 

	 The initial and default value is set by the 'bootp' operation."
    ::= { decAtmLoad 3 }
    
decAtmLoadIpHostAddr OBJECT-TYPE
    SYNTAX  IpAddress
    ACCESS  read-write
    STATUS  mandatory
    DESCRIPTION
	"The IP address of the host from which to load.  When the device
	 is reading, this is the IP address of the host in which the
	 read will be directed.  When the device is being written, this 
	 is the IP address of the only host in which writes will be
	 accepted.

	 This object is non-volatile.  The initial and default value 
	 of this object is set by the 'bootp' operation."

    ::= { decAtmLoad 4 }

decAtmLoadDevSpecific OBJECT-TYPE
    SYNTAX  DisplayString (SIZE(0..80))
    ACCESS  read-only
    STATUS  mandatory
    DESCRIPTION
	"A device specific parameter which may be used to indicate
	 detailed error information about the last attempted load.

	 This object is non-volatile."
     ::= { decAtmLoad 5 }

decAtmConfigIpHostAddr OBJECT-TYPE
    SYNTAX  IpAddress
    ACCESS  read-write
    STATUS  mandatory
    DESCRIPTION
	"The IP address of the host from which to load.  When the device
	 is reading, this is the IP address of the host in which the
	 read will be directed.  When the device is being written, this
	 is the IP address of the only host in which writes will be
	 accepted.

	 This object is non-volatile.  The initial and default value
	 of this object is set by the 'bootp' operation."

    ::= { decAtmLoad 6 }

decAtmConfigDefaultGateway OBJECT-TYPE
    SYNTAX  IpAddress
    ACCESS  read-write
    STATUS  mandatory
    DESCRIPTION
	"IP address of default gateway (router) to use if file IP address
	 is off LAN. If this value is NOT set, no default will be used.

	 this object is non-volatile.  The initial and default value
	 of this object is set by the 'bootp' operation."
    ::= { decAtmLoad 7 }



decAtmConfigFilename OBJECT-TYPE
    SYNTAX  DisplayString (SIZE(0..64))
    ACCESS  read-write
    STATUS  mandatory
    DESCRIPTION
	"The name of the file to read or write.  When the device is
	 reading, this is the name of the file to be read.  When the
	 device is being written, this is the only name of the file
	 in which a write will be accepted - provided the device can
	 check that the file does not exist.
	 It is the duty of the NMS triggering the device to load
	 this object."

    ::= { decAtmLoad 8 }

decAtmConfigStatus OBJECT-TYPE
    SYNTAX  INTEGER {
		other(1),
		start-read(2),
		start-write(3),
		start-read-inprogress(4),
		start-read-complete(5),
		start-write-inprogress(6),
		start-write-complete(7),
		read-error(8),
		write-error(9)
		}
    ACCESS  read-write
    STATUS  mandatory
    DESCRIPTION
	"This object is used to control the reading and writing of
	 Nvram.  When read, the value (1) is returned if no 
	 decAtmConfigStatus action has been initiated since the last
	 reboot. If a 'start-read' operation has been initiated, then
	 a 'start-read-inprogress' will be returned until the start-read
	 is complete, then a 'start-read-complete' will be returned.
	 If a 'start-write' operation has been initiated, then
	 a 'start-write-inprogress' will be returned until the start-write
	 is complete, then a 'start-write-complete' will be returned.

	 When set to start-read(2) the device initiates a TFTP read
	 operation to read the saved Nvram image.  When set to
	 start-write(3) the device checks to ensure that the file name
	 that the Nvram image will be saved in does not exist. If this
	 test is successful, a TFTP write operation will save the
	 configuration."

    ::= { decAtmLoad 9 }


END
