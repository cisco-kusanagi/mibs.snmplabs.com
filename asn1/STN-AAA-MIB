-- *****************************************************************
--
-- STN-AAA.mib:  
--      Spring Tide Networks Authentication, Authorization, and 
--      Accounting MIB file.
--
--
--      Copyright (c) 1999, 2000 by Spring Tide Networks, Inc.
--                      ALL RIGHTS RESERVED       
--
-- *****************************************************************

STN-AAA-MIB DEFINITIONS ::= BEGIN

   IMPORTS
        MODULE-IDENTITY, 
        OBJECT-TYPE,
        NOTIFICATION-TYPE, 
        IpAddress,
        Integer32
               FROM SNMPv2-SMI
        
        DisplayString
               FROM SNMPv2-TC
        
        stnSystems,
        stnNotification
               FROM SPRING-TIDE-NETWORKS-SMI

        stnRouterIndex
                FROM STN-ROUTER-MIB

        stnEngineIndex,
        stnEngineSlot,
        stnEngineCpu
                FROM STN-CHASSIS-MIB;


    stnAAA MODULE-IDENTITY
        LAST-UPDATED    "0002160000Z"
        ORGANIZATION    "Spring Tide Networks, Inc."
        CONTACT-INFO
                "
                Spring Tide Networks, Inc.
                Customer Service
                Postal: 3 Clock Tower Place
                        Maynard, MA 01754
                Tel:    1 888-786-4357
                Email:  stncs@springtidenet.com
                "
        DESCRIPTION
            "The MIB module that describes managed objects of
            Spring Tide Networks Authentication, Authorization and 
            Accounting functionality"
        ::= { stnSystems 10 }

    --
    -- Top Level STN AAA MIB Objects
    --
    stnAAAObjects         OBJECT IDENTIFIER  ::= { stnAAA 1 }
    stnAAAMibConformance  OBJECT IDENTIFIER  ::= { stnAAA 2 }
    stnAAATrapVars        OBJECT IDENTIFIER  ::= { stnAAA 3 }

    --
    --      Definitions of significant branches under stnAAAObjects
    --
    stnAAAConfig          OBJECT IDENTIFIER  ::= { stnAAAObjects 1 }
    stnAAAStats           OBJECT IDENTIFIER  ::= { stnAAAObjects 2 }


    --
    --      Definitions of significant branches under stnAAAConfig
    --
    stnStackingRuleGroup     OBJECT IDENTIFIER ::= { stnAAAConfig 1 }
    stnNetworkAccessGroup    OBJECT IDENTIFIER ::= { stnAAAConfig 4 }
    stnDefaultPppUserGroup   OBJECT IDENTIFIER ::= { stnAAAConfig 8 }
    stnNoAuthPppUserGroup    OBJECT IDENTIFIER ::= { stnAAAConfig 9 }


    --
    --      The Stacking Rule Group
    --
    --      This group contains objects that can be used to
    --      configure the operational characteristics of defaults
    --      for all users using this router - if administrators 
    --      want to use these parameters the users themselves must
    --      not have similar characteristics defined
    --     

    stnStackingRuleProtocol  OBJECT-TYPE
        SYNTAX          INTEGER {
                            none(1),
                            ppp(2)
                        }
        MAX-ACCESS      read-only
        STATUS          current
        DESCRIPTION
            "The rule comparison protocol. Users using this protocol will use 
            the TunnelType and TunnelEndpoint fields"
        DEFVAL          { none }
        ::= { stnStackingRuleGroup 1 }

    stnStackingRuleTunnelType  OBJECT-TYPE
        SYNTAX          INTEGER {
                            none(1),
                            pptp(2),
                            l2tp(4)
                        }
        MAX-ACCESS      read-only
        STATUS          current
        DESCRIPTION
            "The tunneling action the connection will take if the rule 
            comparison protocol is matched."
        DEFVAL          { none }
        ::= { stnStackingRuleGroup 2 }

    stnStackingRuleTunnelEndPoint  OBJECT-TYPE
        SYNTAX          DisplayString (SIZE(0..32))
        MAX-ACCESS      read-only
        STATUS          current
        DESCRIPTION
            "The name of server endpoint that we will TunnelType to when the 
            rule comparison protocol is matched."
        ::= { stnStackingRuleGroup 3 }


    --
    --      The Endpoint Table
    --
    --      This table contains objects that can be used to configure the 
    --      operational characteristics of both tunnelling and PPP endpoints  
    --      

    stnEndPointTable   OBJECT-TYPE
        SYNTAX          SEQUENCE OF StnEndPointEntry
        MAX-ACCESS      not-accessible
        STATUS          current
        DESCRIPTION     "The Endpoint Table."
        ::= { stnAAAConfig 2 }

    stnEndPointEntry   OBJECT-TYPE
        SYNTAX          StnEndPointEntry
        MAX-ACCESS      not-accessible
        STATUS          current
        DESCRIPTION
            "An Server Endpoint entry. An entry in this table corresponds to a 
            single PPP or tunnelling endpoint entity"
        INDEX           { stnEndPointIndex } 
        ::= { stnEndPointTable 1 }

    StnEndPointEntry ::=
        SEQUENCE {
            stnEndPointIndex        Integer32,
            stnEndPointIpAddress    IpAddress,
            stnEndPointName         DisplayString,
            stnEndPointPassword     OCTET STRING
    }

    stnEndPointIndex  OBJECT-TYPE
        SYNTAX          Integer32 
        MAX-ACCESS      read-only
        STATUS          current
        DESCRIPTION     "The configuration instance of this endpoint."
        ::= { stnEndPointEntry 1 }

    stnEndPointIpAddress  OBJECT-TYPE
        SYNTAX          IpAddress 
        MAX-ACCESS      read-only
        STATUS          current
        DESCRIPTION     "IP address of this endpoint."
        ::= { stnEndPointEntry 2 }

    stnEndPointName  OBJECT-TYPE
        SYNTAX          DisplayString (SIZE(0..32))
        MAX-ACCESS      read-only
        STATUS          current
        DESCRIPTION
            "The name of server endpoint - if no address is configured then 
            this name will be used for a DNS lookup"
        ::= { stnEndPointEntry 3 }

    stnEndPointPassword  OBJECT-TYPE
        SYNTAX          OCTET STRING (SIZE(0..255))
        MAX-ACCESS      not-accessible
        STATUS          current
        DESCRIPTION     
            "The challenge password or shared secret for this endpoint."
        ::= { stnEndPointEntry 4 }


    --
    --      The Address Pool Table
    --
    --      This table contains objects that can be used to
    --      configure the operational characteristics of 
    --      the address pool to be used by users terminating
    --      PPP sessions on this router

    stnAddressPoolTable OBJECT-TYPE
        SYNTAX          SEQUENCE OF StnAddressPoolEntry
        MAX-ACCESS      not-accessible
        STATUS          current
        DESCRIPTION     "The Address Pool Table."
        ::= { stnAAAConfig 3 }

    stnAddressPoolEntry   OBJECT-TYPE
        SYNTAX          StnAddressPoolEntry
        MAX-ACCESS      not-accessible
        STATUS          current
        DESCRIPTION
            "An Address Pool entry. An entry in this table corresponds to an 
            address range - all of the entries in this table make up a single 
            address pool for the router"
        INDEX           { stnAddressPoolIndex }
        ::= { stnAddressPoolTable 1 }

    StnAddressPoolEntry ::=
        SEQUENCE {
            stnAddressPoolIndex     Integer32,
            stnStartIpAddress       IpAddress,
            stnEndIpAddress         IpAddress
    }

    stnAddressPoolIndex  OBJECT-TYPE
        SYNTAX          Integer32 
        MAX-ACCESS      not-accessible
        STATUS          current
        DESCRIPTION     "The priority of each range"
        ::= { stnAddressPoolEntry 1 }

    stnStartIpAddress  OBJECT-TYPE
        SYNTAX          IpAddress 
        MAX-ACCESS      read-only
        STATUS          current
        DESCRIPTION     "The starting IP address of the address range"
        ::= { stnAddressPoolEntry 2 }

    stnEndIpAddress  OBJECT-TYPE
        SYNTAX          IpAddress 
        MAX-ACCESS      read-only
        STATUS          current
        DESCRIPTION     "The ending IP address of the address range"
        ::= { stnAddressPoolEntry 3 }
         

    --
    --      The Network Access Group
    --
    --      This group contains objects that can be used to
    --      configure the operational characteristics of 
    --      all AAA options and network access servers defined
    --      for the router

    stnNetworkAccessUserAuthenType  OBJECT-TYPE
        SYNTAX          BITS {
                            none(0),
                            internal(1),
                            radius(2)
                        } 
        MAX-ACCESS      read-only
        STATUS          current
        DESCRIPTION
            "The type of authentication that will be performed for all users 
            using the router - only one user authentication type may be 
            specified at a time"
        ::= { stnNetworkAccessGroup 1 }

    stnNetworkAccessEndPointAuthenType  OBJECT-TYPE
        SYNTAX          BITS {
                            none(0),
                            internal(1),
                            radius(2)
                        } 
        MAX-ACCESS      read-only
        STATUS          current
        DESCRIPTION
            "The type of authentication that will be performed for all 
            endpoints using the router - only one endpoint authentication 
            type may be specified at a time"
        ::= { stnNetworkAccessGroup 2 }

    stnNetworkAccessUserAccType  OBJECT-TYPE
        SYNTAX          BITS {
                            none(0),
                            internal(1),
                            radius(2)
                        } 
        MAX-ACCESS      read-only
        STATUS          current
        DESCRIPTION
            "The type of accounting that will be performed for all users using 
            the router - more than one user authentication may be specified at 
            a time"
        ::= { stnNetworkAccessGroup 3 }

    stnNetworkAccessEndPointAccType  OBJECT-TYPE
        SYNTAX          BITS {
                            none(0),
                            internal(1),
                            radius(2)
                        } 
        MAX-ACCESS      read-only
        STATUS          current
        DESCRIPTION
            "The type of accounting that will be performed for all endpoints 
            using the router - more than one endpoint authentication may be 
            specified at a time"
        ::= { stnNetworkAccessGroup 4 }

    stnNetworkAccessDomainName OBJECT-TYPE
        SYNTAX          DisplayString (SIZE(0..32))
        MAX-ACCESS      read-only
        STATUS          current
        DESCRIPTION
            "The domain name configured for the router - this domain name is 
            used primarily for PPPOE when no router can be determined from the 
            connection type - a username parse will occur attempting to match 
            this domain name with a string located after an '@' sign in the 
            user name ex: john@springtidenetworks.com"
        ::= { stnNetworkAccessGroup 5 }

    stnNetworkAccessServiceNameRadiusAttrType  OBJECT-TYPE
        SYNTAX          INTEGER {
                            servicename(1),
                            filterid(2),
                            class(3)
                        }
        MAX-ACCESS      read-only
        STATUS          current
        DESCRIPTION
            "The type of RADIUS attribute that will be used to carry the 
            service name for a user if applicable"
        ::= { stnNetworkAccessGroup 6 }

    stnNetworkAccessLdapAuthorizationUpdateTime  OBJECT-TYPE
        SYNTAX          INTEGER 
        MAX-ACCESS      read-only
        STATUS          current
        DESCRIPTION
            "The amount of time between LDAP updates for this router in 
            seconds"
        ::= { stnNetworkAccessGroup 7 }

    stnNetworkAccessLdapUpdateNotification OBJECT-TYPE
        SYNTAX          DisplayString 
        MAX-ACCESS      read-write
        STATUS          current
        DESCRIPTION
            "LDAP service update notification from network management apps."
        ::= { stnNetworkAccessGroup 8 }

    stnNetworkAccessRealmAttrType  OBJECT-TYPE
        SYNTAX          INTEGER {
                            springTide-ST-Realm-Name(0),
                            cisco-Avpair(1)
                        } 
        MAX-ACCESS      read-only
        STATUS          current
        DESCRIPTION     "The type of RADIUS attribute that will be used to 
                        specify the realm name for a user if applicable"
        ::= { stnNetworkAccessGroup 9 }


    --
    --      The Radius Accounting Server Table
    --
    --      This table contains objects that can be used to
    --      configure the operational characteristics of 
    --      accounting radius servers 

    stnRadiusAccServerTable OBJECT-TYPE
        SYNTAX          SEQUENCE OF StnRadiusAccServerEntry
        MAX-ACCESS      not-accessible
        STATUS          current
        DESCRIPTION     "The Radius Accounting Server Table."
        ::= { stnAAAConfig 5 }

    stnRadiusAccServerEntry   OBJECT-TYPE
        SYNTAX          StnRadiusAccServerEntry
        MAX-ACCESS      not-accessible
        STATUS          current
        DESCRIPTION
            "An Radius Accounting Server entry. An entry in this table 
            corresponds to a single radius accounting server entry"
        INDEX           { stnRadiusAccServerIndex }
        ::= { stnRadiusAccServerTable 1 }

    StnRadiusAccServerEntry ::=
        SEQUENCE {
            stnRadiusAccServerIndex             Integer32,
            stnRadiusAccServerAddress           IpAddress,
            stnRadiusAccServerDestPort          Integer32,
            stnRadiusAccServerRetrans           Integer32,
            stnRadiusAccServerTimeOut           Integer32,
            stnRadiusAccServerSecret            OCTET STRING,
            stnRadiusAccServerName              DisplayString,
            stnRadiusAccServerConfigInstance    Integer32     
    }

    stnRadiusAccServerIndex  OBJECT-TYPE
        SYNTAX          Integer32                              
        MAX-ACCESS      not-accessible
        STATUS          current
        DESCRIPTION
            "The priority of this accounting server - higher priority servers 
            will attempt to be contacted before lower priority servers - 
            highest priority is 1 - priority indexes must be contiguous"
        ::= { stnRadiusAccServerEntry 1 }

    stnRadiusAccServerAddress  OBJECT-TYPE
        SYNTAX          IpAddress 
        MAX-ACCESS      read-only
        STATUS          current
        DESCRIPTION     "The IP address of this Radius accounting server."
        ::= { stnRadiusAccServerEntry 2 }

    stnRadiusAccServerDestPort  OBJECT-TYPE
        SYNTAX          Integer32                              
        MAX-ACCESS      read-only
        STATUS          current
        DESCRIPTION
            "The destination accounting port of this Radius accounting server."
        ::= { stnRadiusAccServerEntry 3 }

    stnRadiusAccServerRetrans  OBJECT-TYPE
        SYNTAX          Integer32                              
        MAX-ACCESS      read-only
        STATUS          current
        DESCRIPTION
            "The number of times the router will attempt to retransmit to 
            this server if there is no response"
        DEFVAL          {10}
        ::= { stnRadiusAccServerEntry 4 }

    stnRadiusAccServerTimeOut  OBJECT-TYPE
        SYNTAX          Integer32                              
        MAX-ACCESS      read-only
        STATUS          current
        DESCRIPTION
            "The time in seconds to determine the last (re)transmission
            to this server failed."
        DEFVAL          {60}
        ::= { stnRadiusAccServerEntry 5 }

    stnRadiusAccServerSecret  OBJECT-TYPE
        SYNTAX          OCTET STRING (SIZE(0..255)) 
        MAX-ACCESS      not-accessible
        STATUS          current
        DESCRIPTION
            "The shared secret configured for this Radius accounting server - 
            this secret must also be configured on the RADIUS server itself"
        ::= { stnRadiusAccServerEntry 6 }

    stnRadiusAccServerName  OBJECT-TYPE
        SYNTAX          DisplayString (SIZE(0..32))
        MAX-ACCESS      read-only
        STATUS          current
        DESCRIPTION
            "The name of this Radius accounting server - this name will be 
            used for a DNS lookup if an ip address is not configured"
        ::= { stnRadiusAccServerEntry 7 }

    stnRadiusAccServerConfigInstance  OBJECT-TYPE
        SYNTAX          Integer32                              
        MAX-ACCESS      read-only
        STATUS          current
        DESCRIPTION     "The configuration instance of this accounting server" 
        ::= { stnRadiusAccServerEntry 8 }


    --
    --      The Radius Authentication Server Table
    --
    --      This table contains objects that can be used to
    --      configure the operational characteristics of 
    --      RADIUS authentication servers used by the router

    stnRadiusAuthServerTable OBJECT-TYPE
        SYNTAX          SEQUENCE OF StnRadiusAuthServerEntry
        MAX-ACCESS      not-accessible
        STATUS          current
        DESCRIPTION     "The Radius Authentication Server table."
        ::= { stnAAAConfig 6 }

    stnRadiusAuthServerEntry   OBJECT-TYPE
        SYNTAX          StnRadiusAuthServerEntry
        MAX-ACCESS      not-accessible
        STATUS          current
        DESCRIPTION
            "An Radius authentication server entry. An entry in this table 
            corresponds to a single radius authentication server entry"
        INDEX           { stnRadiusAuthServerIndex }
        ::= { stnRadiusAuthServerTable 1 }

    StnRadiusAuthServerEntry ::=
        SEQUENCE {
            stnRadiusAuthServerIndex            Integer32,
            stnRadiusAuthServerAddress          IpAddress,
            stnRadiusAuthServerDestPort         Integer32,
            stnRadiusAuthServerRetrans          Integer32,
            stnRadiusAuthServerTimeOut          Integer32,
            stnRadiusAuthServerSecret           OCTET STRING,
            stnRadiusAuthServerName             DisplayString,
            stnRadiusAuthServerConfigInstance   Integer32
    }

    stnRadiusAuthServerIndex  OBJECT-TYPE
        SYNTAX          Integer32                              
        MAX-ACCESS      not-accessible
        STATUS          current
        DESCRIPTION
            "The priority of this Radius authentication server - highest 
            priority is 1 and higher priority servers will be contacted first 
            - the priorities must be contiguous"
        ::= { stnRadiusAuthServerEntry 1 }

    stnRadiusAuthServerAddress  OBJECT-TYPE
        SYNTAX          IpAddress 
        MAX-ACCESS      read-only
        STATUS          current
        DESCRIPTION     "The IP address of this Radius authentication server."
        ::= { stnRadiusAuthServerEntry 2 }

    stnRadiusAuthServerDestPort  OBJECT-TYPE
        SYNTAX          Integer32                              
        MAX-ACCESS      read-only
        STATUS          current
        DESCRIPTION
            "The destination authenticaton port of this Radius authentication 
            server."
        ::= { stnRadiusAuthServerEntry 3 }

    stnRadiusAuthServerRetrans  OBJECT-TYPE
        SYNTAX          Integer32                              
        MAX-ACCESS      read-only
        STATUS          current
        DESCRIPTION
            "The number of times the router will attempt to retransmit to
            this radius authentication server"
        DEFVAL          {6}
        ::= { stnRadiusAuthServerEntry 4 }

    stnRadiusAuthServerTimeOut  OBJECT-TYPE
        SYNTAX          Integer32                              
        MAX-ACCESS      read-only
        STATUS          current
        DESCRIPTION
            "The time (in seconds) to determine the last (re)transmission
            to this authentication server failed."
        DEFVAL          {5}
        ::= { stnRadiusAuthServerEntry 5 }

    stnRadiusAuthServerSecret  OBJECT-TYPE
        SYNTAX          OCTET STRING (SIZE(0..255))
        MAX-ACCESS      not-accessible
        STATUS          current
        DESCRIPTION
            "The shared secret configured for this Radius authentication 
            server - this same secret must be configured on the RADIUS server 
            itself"
        ::= { stnRadiusAuthServerEntry 6 }

    stnRadiusAuthServerName  OBJECT-TYPE
        SYNTAX          DisplayString (SIZE(0..32))
        MAX-ACCESS      read-only
        STATUS          current
        DESCRIPTION
            "The name of this Radius authentication server - this name will be 
            used for a DNS lookup if no ip address is configured"
        ::= { stnRadiusAuthServerEntry 7 }

    stnRadiusAuthServerConfigInstance  OBJECT-TYPE
        SYNTAX          Integer32                              
        MAX-ACCESS      read-only
        STATUS          current
        DESCRIPTION
            "The configuration instance of this Radius authentication server"
        ::= { stnRadiusAuthServerEntry 8 }


    --
    --      The User Table
    --
    --      This table contains objects that can be used to
    --      configure the operational characteristics of 
    --      the internal users for the router

    stnUserTable OBJECT-TYPE
        SYNTAX          SEQUENCE OF StnUserEntry
        MAX-ACCESS      not-accessible
        STATUS          current
        DESCRIPTION     "The User Table."
        ::= { stnAAAConfig 7 }

    stnUserEntry   OBJECT-TYPE
        SYNTAX          StnUserEntry
        MAX-ACCESS      not-accessible
        STATUS          current
        DESCRIPTION
            "An User entry. An entry in this table corresponds to a single 
            user entry"
        INDEX           { stnUserIndex }
        ::= { stnUserTable 1 }

    StnUserEntry ::=
        SEQUENCE {
            stnUserIndex                    Integer32,
            stnUserName                     DisplayString,
            stnUserPassword                 OCTET STRING,
            stnUserIpAddress                IpAddress,
            stnUserIpNetMask                IpAddress,
            stnUserIpRouting                INTEGER,
            stnUserMTU                      INTEGER,
            stnUserIpCompression            INTEGER,
            stnUserTimeOut                  Integer32,
            stnUserIdleTime                 Integer32,
            stnUserTunnelType               INTEGER,
            stnUserTunnelServerEndPoint     DisplayString,
            stnUserTunnelClientEndPoint     DisplayString,
            stnUserAssignedTunnelName       DisplayString,
            stnUserTunnelPassword           OCTET STRING,
            stnUserServiceType              INTEGER,
            stnUserIpFilters                OCTET STRING,
            stnUserIpRoutes                 OCTET STRING,
            stnUserPrimaryDNSServer         IpAddress,
            stnUserSecondaryDNSServer       IpAddress,
            stnUserPrimaryNBNSServer        IpAddress,
            stnUserSecondaryNBNSServer      IpAddress,
            stnUserServiceName              DisplayString,
            stnUserPhysicalPort             Integer32,
            stnUserPhysicalSlot             Integer32,
            stnUserVirtualPathId            Integer32,
            stnUserVirtualCircuitId         Integer32,
            stnUserRealmInstance            Integer32
    }

    stnUserIndex  OBJECT-TYPE
        SYNTAX          Integer32
        MAX-ACCESS      read-only
        STATUS          current
        DESCRIPTION     "The configuration instance of this entry."
        ::= { stnUserEntry 1 }

    stnUserName  OBJECT-TYPE
        SYNTAX          DisplayString (SIZE(0..32))
        MAX-ACCESS      read-only
        STATUS          current
        DESCRIPTION     "The user name for this user table entry"
        ::= { stnUserEntry 2 }

    stnUserPassword OBJECT-TYPE
        SYNTAX          OCTET STRING (SIZE(0..255))
        MAX-ACCESS      not-accessible
        STATUS          current
        DESCRIPTION     "The password of this user."
        ::= { stnUserEntry 3 }
   
    stnUserIpAddress  OBJECT-TYPE
        SYNTAX          IpAddress 
        MAX-ACCESS      read-only
        STATUS          current
        DESCRIPTION
            "The IP address for user sessions created for this user - 
            255.255.255.254 picks an address from the address pool table and
            0 or 255.255.255.255 allows the user to pick the address."
        ::= { stnUserEntry 4 }

    stnUserIpNetMask  OBJECT-TYPE
        SYNTAX          IpAddress 
        MAX-ACCESS      read-only
        STATUS          current
        DESCRIPTION     
            "The IP sub-network mask for sessions created for this user."
        ::= { stnUserEntry 5 }

    stnUserIpRouting  OBJECT-TYPE
        SYNTAX          INTEGER {
                            unset(0),
                            none(1),
                            send(2),
                            listen(3),
                            both(4)
                        }
        MAX-ACCESS      read-only
        STATUS          current
        DESCRIPTION     "The routing method for this user session."
        DEFVAL          { none }
        ::= { stnUserEntry 6 }

    stnUserMTU  OBJECT-TYPE
        SYNTAX          INTEGER (64..65532)
        MAX-ACCESS      read-only
        STATUS          current
        DESCRIPTION
            "The maximum transmission unit used by the framed protocol that 
            this user is configured for."
        DEFVAL          { 1500 }
        ::= { stnUserEntry 7 }

    stnUserIpCompression  OBJECT-TYPE
        SYNTAX          INTEGER {
                               none(1),
                               vj(2)        -- Van Jacobson
                        }
        MAX-ACCESS      read-only
        STATUS          current
        DESCRIPTION
            "The compression type for sessions created for this user."
        DEFVAL          { none }
        ::= { stnUserEntry 8 }

    stnUserTimeOut  OBJECT-TYPE
        SYNTAX          Integer32
        MAX-ACCESS      read-only
        STATUS          current
        DESCRIPTION
            "The total amount of time a session should be allowed to stay 
            connected. A value of 0 indicates no timeout"
        DEFVAL          { 0 }
        ::= { stnUserEntry 9 }

    stnUserIdleTime  OBJECT-TYPE
        SYNTAX          Integer32
        MAX-ACCESS      read-only
        STATUS          current
        DESCRIPTION
            "The total amount of time a session should be allowed to stay 
            connected when idle. A value of 0 indicates no timeout"
        DEFVAL          { 0 }
        ::= { stnUserEntry 10 }

    stnUserTunnelType  OBJECT-TYPE
        SYNTAX          INTEGER {
                               unset(0),
                               none(1),
                               pptp(2),
                               l2tp(4)
                        }
        MAX-ACCESS      read-only
        STATUS          current
        DESCRIPTION
            "The type of tunnel that should be used for compulsory tunneling - 
            none indicates that this user should be given a strictly PPP 
            session"
        DEFVAL          { none }
        ::= { stnUserEntry 11 }

    stnUserTunnelServerEndPoint  OBJECT-TYPE
        SYNTAX          DisplayString (SIZE(0..32))
        MAX-ACCESS      read-only
        STATUS          current
        DESCRIPTION
            "The name of the tunnel server endpoint to be used when a valid 
            tunnel type is configured"
        ::= { stnUserEntry 12 }

    stnUserTunnelClientEndPoint  OBJECT-TYPE
        SYNTAX          DisplayString (SIZE(0..32))
        MAX-ACCESS      read-only
        STATUS          current
        DESCRIPTION
            "The name of the tunnel client endpoint to be used when a valid 
            tunnel type is configured"
        ::= { stnUserEntry 13 }

    stnUserAssignedTunnelName  OBJECT-TYPE
        SYNTAX          DisplayString
        MAX-ACCESS      read-only
        STATUS          current
        DESCRIPTION
            "The name of the tunnel initiator to which a session is to be 
            assigned - this variable allows for a grouping mechanism of tunnel 
            sessions"
        ::= { stnUserEntry 14 }

    stnUserTunnelPassword OBJECT-TYPE
        SYNTAX          OCTET STRING  (SIZE(0..255))
        MAX-ACCESS      not-accessible
        STATUS          current
        DESCRIPTION
            "The shared secret used for this tunnel session when a valid 
            tunnel type is configured"
        ::= { stnUserEntry 15 }

    stnUserServiceType OBJECT-TYPE
        SYNTAX          INTEGER {
                               unset(0),
                               login(1),
                               framed(2),
                               administrative(6),
                               provisioner(101)
                           }
        MAX-ACCESS      read-only
        STATUS          current
        DESCRIPTION
            "The permission level of the user - framed indicates a PPP user 
            and possibly a tunnel user, login indicates a telnet or serial 
            user with read-only allowances, provisioner indicates a telnet or 
            serial user with read-only allowances as well as write privileges 
            for the specific router they are configured on, administrative 
            indicates a telent or serial user with read-only allowances as 
            well as write priveleges for all routers"
        DEFVAL          { framed }
        ::= { stnUserEntry 16 }

    stnUserIpFilters OBJECT-TYPE
        SYNTAX          OCTET STRING (SIZE(0..1024))
        MAX-ACCESS      read-only
        STATUS          obsolete
        DESCRIPTION
            "The list of IP filters that this user entry will be using for its 
            sessions - every four bytes of the octet string contain a 32 bit 
            filter configuration instance"
        ::= { stnUserEntry 17 }

    stnUserIpRoutes OBJECT-TYPE
        SYNTAX          OCTET STRING (SIZE(0..1024))
        MAX-ACCESS      read-only
        STATUS          current
        DESCRIPTION
            "The list of IP routes for this user - every four bytes of 
            the octet string contain a 32 bit route configuration instance"
        ::= { stnUserEntry 18 }

    stnUserPrimaryDNSServer OBJECT-TYPE
        SYNTAX          IpAddress
        MAX-ACCESS      read-only
        STATUS          current
        DESCRIPTION
            "The IP address of the primary DNS server"
        ::= { stnUserEntry 19 }

     stnUserSecondaryDNSServer OBJECT-TYPE
        SYNTAX          IpAddress
        MAX-ACCESS      read-only
        STATUS          current
        DESCRIPTION
            "The IP address of the secondary DNS server"
        ::= { stnUserEntry 20 }

    stnUserPrimaryNBNSServer OBJECT-TYPE
        SYNTAX          IpAddress
        MAX-ACCESS      read-only
        STATUS          current
        DESCRIPTION
            "The IP address of the primary NBNS server"
        ::= { stnUserEntry 21 }

    stnUserSecondaryNBNSServer OBJECT-TYPE
        SYNTAX          IpAddress
        MAX-ACCESS      read-only
        STATUS          current
        DESCRIPTION
            "The IP address of the secondary NBNS server"
        ::= { stnUserEntry 22 }

    stnUserServiceName  OBJECT-TYPE
        SYNTAX          DisplayString (SIZE(0..64))
        MAX-ACCESS      read-only
        STATUS          current
        DESCRIPTION
            "The name indicating the service level for this user - 
            the correlating service and policies for the service may
            be configured either locally or on an LDAP server"
        ::= { stnUserEntry 23 }

    stnUserPhysicalPort OBJECT-TYPE
        SYNTAX          Integer32
        MAX-ACCESS      read-only
        STATUS          current
        DESCRIPTION     "The physical port this user is allowed to connect
                         to"
        ::= { stnUserEntry 24 }

    stnUserPhysicalSlot OBJECT-TYPE
        SYNTAX          Integer32
        MAX-ACCESS      read-only
        STATUS          current
        DESCRIPTION     "The physical slot this user is allowed to connect
                         to"
        ::= { stnUserEntry 25 }

    stnUserVirtualPathId OBJECT-TYPE
        SYNTAX          Integer32
        MAX-ACCESS      read-only
        STATUS          current
        DESCRIPTION     "The virtual path identifier that this user 
                         is allowed to use"
        ::= { stnUserEntry 26 }

    stnUserVirtualCircuitId OBJECT-TYPE
        SYNTAX          Integer32
        MAX-ACCESS      read-only
        STATUS          current
        DESCRIPTION     "The virtual circuit identifier that this user 
                         is allowed to use"
        ::= { stnUserEntry 27 }

    stnUserRealmInstance  OBJECT-TYPE
        SYNTAX                  Integer32
        MAX-ACCESS              read-only
        STATUS                  current
        DESCRIPTION             "The instance of this users Realm record"
        ::= { stnUserEntry 28 } 


    --
    --      The Default PPP User Group
    --
    --      This group contains objects that can be used to
    --      configure the operational characteristics of 
    --      the PPP default user - the PPP default user is used
    --      when PPP is not authenticating and there is no user name
    --      defined in the no authentication NoAuthenPppUserGroup below.

    stnDefaultUserIpAddress  OBJECT-TYPE
        SYNTAX          IpAddress 
        MAX-ACCESS      read-only
        STATUS          current
        DESCRIPTION     "The IP address for the default PPP user session."
        ::= { stnDefaultPppUserGroup 1 }

    stnDefaultUserIpNetMask  OBJECT-TYPE
        SYNTAX          IpAddress 
        MAX-ACCESS      read-only
        STATUS          current
        DESCRIPTION
            "The IP sub-network mask that the PPP default user will use."
        ::= { stnDefaultPppUserGroup 2 }
        
    stnDefaultUserIpRouting  OBJECT-TYPE
        SYNTAX          INTEGER {
                            none(1),
                            send(2),
                            listen(3),
                            both(4)
                        }
        MAX-ACCESS      read-only
        STATUS          current
        DESCRIPTION     "The routing method for the PPP default user"
        DEFVAL          { none }
        ::= { stnDefaultPppUserGroup 3 }

    stnDefaultUserMTU  OBJECT-TYPE
        SYNTAX          INTEGER (64..65532)
        MAX-ACCESS      read-only
        STATUS          current
        DESCRIPTION
            "The maximum transmission unit used by the framed protocol
            that the PPP default user is configured for."
        DEFVAL          { 1500 }
        ::= { stnDefaultPppUserGroup 4 }

    stnDefaultUserIpCompression  OBJECT-TYPE
        SYNTAX          INTEGER {
                            none(1),
                            vj(2)       -- Van Jacobson
                        }
        MAX-ACCESS      read-only
        STATUS          current
        DESCRIPTION     "The compression type for the PPP default user"
        DEFVAL          { none }
        ::= { stnDefaultPppUserGroup 5 }

    stnDefaultUserTimeOut  OBJECT-TYPE
        SYNTAX          Integer32
        MAX-ACCESS      read-only
        STATUS          current
        DESCRIPTION
            "The total amount of time the default PPP user should be allowed 
            to stay connected. A value of 0 indicates no timeout"
        DEFVAL          { 0 }
        ::= { stnDefaultPppUserGroup 6 }

    stnDefaultUserIdleTime  OBJECT-TYPE
        SYNTAX          Integer32
        MAX-ACCESS      read-only
        STATUS          current
        DESCRIPTION
            "The total amount of time the PPP default user should be allowed 
            to stay connected when idle. A value of 0 indicates no timeout" 
        DEFVAL          { 0 }
        ::= { stnDefaultPppUserGroup 7 }

    stnDefaultUserTunnelType  OBJECT-TYPE
        SYNTAX          INTEGER {
                            none(1),
                            pptp(2),
                            l2tp(4)
                        }
        MAX-ACCESS      read-only
        STATUS          current
        DESCRIPTION
            "The type of tunnel that should be used for compulsory tunneling 
            for the PPP default user - if none is indicated then PPP 
            termination with no tunneling occurs"
        DEFVAL          { none }
        ::= { stnDefaultPppUserGroup 8 }

    stnDefaultUserTunnelServerEndPoint  OBJECT-TYPE
        SYNTAX          DisplayString (SIZE(0..32))
        MAX-ACCESS      read-only
        STATUS          current
        DESCRIPTION
            "The name of the tunnel server endpoint for the PPP default user 
            to be used if a valid tunnel type is configured for the tunnel 
            type"
        ::= { stnDefaultPppUserGroup 9 }

    stnDefaultUserTunnelClientEndPoint  OBJECT-TYPE
        SYNTAX          DisplayString (SIZE(0..32))
        MAX-ACCESS      read-only
        STATUS          current
        DESCRIPTION
            "The name of the tunnel client endpoint for the PPP default user 
            to be used if a valid tunnel type is configured for the tunnel 
            type"
        ::= { stnDefaultPppUserGroup 10 }

    stnDefaultUserIpFilters OBJECT-TYPE
        SYNTAX          OCTET STRING (SIZE(0..1024))
        MAX-ACCESS      read-only
        STATUS          obsolete
        DESCRIPTION
            "The list of IP filters for the PPP default user - 
            each 32 bits of the octet string specifies a filter file
            configuration instance"
        ::= { stnDefaultPppUserGroup 11 }

    stnDefaultUserIpRoutes OBJECT-TYPE
        SYNTAX          OCTET STRING (SIZE(0..1024))
        MAX-ACCESS      read-only
        STATUS          current
        DESCRIPTION
            "The list of IP routes for the PPP default user -
            each 32 bits of the octet string specifies a route
            configuration instance"
        ::= { stnDefaultPppUserGroup 12 }
    
    stnDefaultUserPrimaryDNSServer OBJECT-TYPE
        SYNTAX          IpAddress
        MAX-ACCESS      read-only
        STATUS          current
        DESCRIPTION
            "The IP address of the primary DNS server"
        ::= { stnDefaultPppUserGroup 13 }

    stnDefaultUserSecondaryDNSServer OBJECT-TYPE
        SYNTAX          IpAddress
        MAX-ACCESS      read-only
        STATUS          current
        DESCRIPTION
            "The IP address of the secondary DNS server"
        ::= { stnDefaultPppUserGroup 14 }

    stnDefaultUserPrimaryNBNSServer OBJECT-TYPE
        SYNTAX          IpAddress
        MAX-ACCESS      read-only
        STATUS          current
        DESCRIPTION
            "The IP address of the primary NBNS server"
        ::= { stnDefaultPppUserGroup 15 }

    stnDefaultUserSecondaryNBNSServer OBJECT-TYPE
        SYNTAX          IpAddress
        MAX-ACCESS      read-only
        STATUS          current
        DESCRIPTION
            "The IP address of the secondary NBNS server"
        ::= { stnDefaultPppUserGroup 16 }
    
    stnDefaultUserServiceName   OBJECT-TYPE
        SYNTAX          DisplayString (SIZE(0..64))
        MAX-ACCESS      read-only
        STATUS          current
        DESCRIPTION
            "The name indicating the service level for this default user - 
            the correlating service and policies for the service may 
            be configured either locally or on an LDAP server"
        ::= { stnDefaultPppUserGroup 17 }

 
    --
    --      The No Authentication PPP User Group
    --
    --      This group contains objects that can be used to
    --      configure the operational characteristics of 
    --      the PPP no authentication default user name and password
    --      - this group is used if PPP is not authenticating users
    --      and a specific user's entry in the local user table or a 
    --      remote authentication database is to be used.

    stnNoAuthPppUserName  OBJECT-TYPE
        SYNTAX          DisplayString (SIZE(0..32))
        MAX-ACCESS      read-only
        STATUS          current
        DESCRIPTION     "The name of this no-authentication PPP user."
        ::= { stnNoAuthPppUserGroup 1 }

    stnNoAuthPppUserPassword  OBJECT-TYPE
        SYNTAX          OCTET STRING (SIZE(0..255)) 
        MAX-ACCESS      not-accessible
        STATUS          current
        DESCRIPTION     "The password of this no-authentication PPP user."
        ::= { stnNoAuthPppUserGroup 2 }


    --
    --      The IP Filter Table
    --
    --      This table contains objects that can be used to
    --      configure the operational characteristics of 
    --      
    --

    stnUserIpFilterTable   OBJECT-TYPE
        SYNTAX          SEQUENCE OF StnUserIpFilterEntry
        MAX-ACCESS      not-accessible
        STATUS          obsolete
        DESCRIPTION     "The IP Filter table."
        ::= { stnAAAConfig 10 }

    stnUserIpFilterEntry   OBJECT-TYPE
        SYNTAX          StnUserIpFilterEntry
        MAX-ACCESS      not-accessible
        STATUS          obsolete
        DESCRIPTION 
            "An User IP filter entry. An entry in this table corresponds to a 
            single filter file"
        INDEX           { stnUserIpFilterIndex }
        ::= { stnUserIpFilterTable 1 }

    StnUserIpFilterEntry ::=
        SEQUENCE {
            stnUserIpFilterIndex        Integer32,
            stnUserIpFilterName         DisplayString,
            stnUserIpFilterRules        OCTET STRING
    }

    stnUserIpFilterIndex  OBJECT-TYPE
        SYNTAX          Integer32 
        MAX-ACCESS      read-only
        STATUS          obsolete
        DESCRIPTION     "The configuration instance of this IP filter file"
        ::= { stnUserIpFilterEntry 1 }

    stnUserIpFilterName  OBJECT-TYPE
        SYNTAX          DisplayString (SIZE(0..32)) 
        MAX-ACCESS      read-only
        STATUS          obsolete
        DESCRIPTION     "The name of this IP filter file."
        ::= { stnUserIpFilterEntry 2 }

    stnUserIpFilterRules  OBJECT-TYPE
        SYNTAX          OCTET STRING (SIZE(0..1024))
        MAX-ACCESS      read-only
        STATUS          obsolete
        DESCRIPTION
            "A list of the IP Filter Rules that this filter file contains - 
            each 32 bits of the octet string contains a filter rule 
            configuration instance"
        ::= { stnUserIpFilterEntry 3 }


    --
    --      The IP Filter Rule Table
    --
    --      This table contains objects that can be used to
    --      configure the operational characteristics of 
    --      
    --

    stnUserIpFilterRuleTable   OBJECT-TYPE
        SYNTAX          SEQUENCE OF StnUserIpFilterRuleEntry
        MAX-ACCESS      not-accessible
        STATUS          obsolete
        DESCRIPTION     "The User IP filte rule table."
        ::= { stnAAAConfig 11 }

    stnUserIpFilterRuleEntry   OBJECT-TYPE
        SYNTAX          StnUserIpFilterRuleEntry
        MAX-ACCESS      not-accessible
        STATUS          obsolete
        DESCRIPTION
            "An User IP filter rule entry. An entry in this
             table corresponds to a single IP filter rule entry"
        INDEX           { stnUserIpFilterRuleIndex }
        ::= { stnUserIpFilterRuleTable 1 }

    StnUserIpFilterRuleEntry ::=
        SEQUENCE {
            stnUserIpFilterRuleIndex        Integer32,
            stnUserIpFilterRuleSrcAddress   IpAddress,
            stnUserIpFilterRuleSrcNetMask   IpAddress,
            stnUserIpFilterRuleSrcPort      Integer32,
            stnUserIpFilterRuleDestAddress  IpAddress,
            stnUserIpFilterRuleDestNetMask  IpAddress,
            stnUserIpFilterRuleDestPort     Integer32,
            stnUserIpFilterRuleProtocol     Integer32,
            stnUserIpFilterRuleAction       Integer32,
            stnUserIpFilterRuleEndPoint     DisplayString
    }

    stnUserIpFilterRuleIndex  OBJECT-TYPE
        SYNTAX          Integer32 
        MAX-ACCESS      read-only
        STATUS          obsolete
        DESCRIPTION     "The configuration instance of this IP filter rule"
        ::= { stnUserIpFilterRuleEntry 1 }

    stnUserIpFilterRuleSrcAddress  OBJECT-TYPE
        SYNTAX          IpAddress 
        MAX-ACCESS      read-only
        STATUS          obsolete
        DESCRIPTION     "The filter rule comparison source IP address."
        ::= { stnUserIpFilterRuleEntry 2 }

    stnUserIpFilterRuleSrcNetMask  OBJECT-TYPE
        SYNTAX          IpAddress 
        MAX-ACCESS      read-only
        STATUS          obsolete
        DESCRIPTION     "The filter rule comparison source IP sub-network mask."
        ::= { stnUserIpFilterRuleEntry 3 }

    stnUserIpFilterRuleSrcPort  OBJECT-TYPE
        SYNTAX          Integer32 
        MAX-ACCESS      read-only
        STATUS          obsolete
        DESCRIPTION     "The filter rule comparison source port."
        ::= { stnUserIpFilterRuleEntry 4 }

   stnUserIpFilterRuleDestAddress  OBJECT-TYPE
        SYNTAX          IpAddress 
        MAX-ACCESS      read-only
        STATUS          obsolete
        DESCRIPTION     "The filter rule comparison destination IP address."
        ::= { stnUserIpFilterRuleEntry 5 }

    stnUserIpFilterRuleDestNetMask  OBJECT-TYPE
        SYNTAX          IpAddress 
        MAX-ACCESS      read-only
        STATUS          obsolete
        DESCRIPTION     "The filter rule comparison destination IP sub-network mask."
        ::= { stnUserIpFilterRuleEntry 6 }

    stnUserIpFilterRuleDestPort  OBJECT-TYPE
        SYNTAX          Integer32 
        MAX-ACCESS      read-only
        STATUS          obsolete
        DESCRIPTION     "The filter rule comparison destination port."
        ::= { stnUserIpFilterRuleEntry 7 }

    stnUserIpFilterRuleProtocol  OBJECT-TYPE
        SYNTAX          Integer32 
        MAX-ACCESS      read-only
        STATUS          obsolete
        DESCRIPTION     "The filter rule comparison protocol."
        ::= { stnUserIpFilterRuleEntry 8 }

    stnUserIpFilterRuleAction  OBJECT-TYPE
        SYNTAX          Integer32 
        MAX-ACCESS      read-only
        STATUS          obsolete
        DESCRIPTION     "The action we should take if a match occurs to the 
                        specified comparisons above"
        ::= { stnUserIpFilterRuleEntry 9 }

    stnUserIpFilterRuleEndPoint  OBJECT-TYPE
        SYNTAX          DisplayString (SIZE(0..32))
        MAX-ACCESS      read-only
        STATUS          obsolete
        DESCRIPTION     "The name of endpoint we will use for the action if appropriate"
        ::= { stnUserIpFilterRuleEntry 10 }


    --
    --      The User IP Route Table
    --
    --      This table contains objects that can be used to
    --      configure the operational characteristics of 
    --      ip routes

    stnUserIpRouteTable   OBJECT-TYPE
        SYNTAX          SEQUENCE OF StnUserIpRouteEntry
        MAX-ACCESS      not-accessible
        STATUS          current
        DESCRIPTION     "The User IP route table."
        ::= { stnAAAConfig 12 }

    stnUserIpRouteEntry   OBJECT-TYPE
        SYNTAX          StnUserIpRouteEntry
        MAX-ACCESS      not-accessible
        STATUS          current
        DESCRIPTION
              "An User IP route entry. An entry in this
               table may correspond to a single IP route"
        INDEX           { stnUserIpRouteIndex }
        ::= { stnUserIpRouteTable 1 }

    StnUserIpRouteEntry ::=
        SEQUENCE {
            stnUserIpRouteIndex         Integer32,
            stnUserIpRouteDestAddress   IpAddress,
            stnUserIpRouteDestNetMask   IpAddress,
            stnUserIpRouteDestGateway   IpAddress,
            stnUserIpRouteMetric        Integer32
    }

    stnUserIpRouteIndex  OBJECT-TYPE
        SYNTAX          Integer32 
        MAX-ACCESS      read-only
        STATUS          current
        DESCRIPTION     "The configuration instance of this IP route."
        ::= { stnUserIpRouteEntry 1 }

    stnUserIpRouteDestAddress  OBJECT-TYPE
        SYNTAX          IpAddress 
        MAX-ACCESS      read-only
        STATUS          current
        DESCRIPTION
            "The destination IP address of this route. An entry with a 
            value of 0.0.0.0 is considered a default route."
        ::= { stnUserIpRouteEntry 2 }

    stnUserIpRouteDestNetMask  OBJECT-TYPE
        SYNTAX          IpAddress 
        MAX-ACCESS      read-only
        STATUS          current
        DESCRIPTION
            "The IP sub-network mask associated with the destination
            IP address of this entry."
        ::= { stnUserIpRouteEntry 3 }

    stnUserIpRouteDestGateway  OBJECT-TYPE
        SYNTAX          IpAddress 
        MAX-ACCESS      read-only
        STATUS          current
        DESCRIPTION
            "The gateway for packets with a matching destination
            address and netmask."
        ::= { stnUserIpRouteEntry 4 }

    stnUserIpRouteMetric  OBJECT-TYPE
        SYNTAX          Integer32 
        MAX-ACCESS      read-only
        STATUS          current
        DESCRIPTION     "The number of hops to the gateway."
        DEFVAL          { 1 }
        ::= { stnUserIpRouteEntry 5 }


    --
    --      The LDAP Authorization Server Table
    --
    --     

    stnLDAPAuthorServerTable OBJECT-TYPE
        SYNTAX      SEQUENCE OF StnLDAPAuthorServerEntry
        MAX-ACCESS  not-accessible
        STATUS      current
        DESCRIPTION
            "The (conceptual) table listing the LDAP authorization
             servers with which the client shares a secret."
        ::= { stnAAAConfig 13 }

    stnLDAPAuthorServerEntry OBJECT-TYPE
        SYNTAX      StnLDAPAuthorServerEntry
        MAX-ACCESS  not-accessible
        STATUS      current
        DESCRIPTION
            "An entry (conceptual row) representing a LDAP authorization 
            server with which the client shares a secret."
        INDEX      { stnLDAPAuthorServerIndex }
        ::= { stnLDAPAuthorServerTable 1 }

    StnLDAPAuthorServerEntry ::= 
        SEQUENCE {
            stnLDAPAuthorServerIndex                    Integer32,
            stnLDAPAuthorServerAddress                  IpAddress,
            stnLDAPAuthorClientServerPortNumber         Integer32,
            stnLDAPAuthorServerTimeout                  Integer32,
            stnLDAPAuthorConnectionEstablishTimeout     Integer32,
            stnLDAPAuthorBindPassword                   OCTET STRING,
            stnLDAPAuthorRootDirectory                  DisplayString,
            stnLDAPAuthorServiceDirectoryName           DisplayString,
            stnLDAPAuthorBindOrganizationalUnit         DisplayString,
            stnLDAPAuthorBindUserId                     DisplayString,
            stnLDAPAuthorServerName                     DisplayString,
            stnLDAPAuthorServerConfigInstance           Integer32
    }

    stnLDAPAuthorServerIndex OBJECT-TYPE
        SYNTAX      Integer32
        MAX-ACCESS  not-accessible
        STATUS      current
        DESCRIPTION
            "A number uniquely identifying each LDAP Authorization server 
            with which this client communicates."
        ::= { stnLDAPAuthorServerEntry 1 }

    stnLDAPAuthorServerAddress OBJECT-TYPE
        SYNTAX      IpAddress
        MAX-ACCESS  read-only
        STATUS      current
        DESCRIPTION
            "The IP address of the LDAP authorization server referred to in 
            this table entry."
        ::= { stnLDAPAuthorServerEntry 2 }

    stnLDAPAuthorClientServerPortNumber  OBJECT-TYPE
        SYNTAX      Integer32 (0..65535)
        MAX-ACCESS  read-only
        STATUS      current
        DESCRIPTION
            "The UDP port the client is using to send requests to this server."
        ::= { stnLDAPAuthorServerEntry 3 }

    stnLDAPAuthorServerTimeout  OBJECT-TYPE
        SYNTAX      Integer32
        MAX-ACCESS  read-only
        STATUS      current
        DESCRIPTION
            "Amount of time in seconds the STN 5000 will wait for a reply 
             before considering the transmission a failure"
        ::= { stnLDAPAuthorServerEntry 4 }

    stnLDAPAuthorConnectionEstablishTimeout  OBJECT-TYPE
        SYNTAX      Integer32
        MAX-ACCESS  read-only
        STATUS      current
        DESCRIPTION
            "Amount of time in seconds the STN 5000 will wait to reestablish a             
             failed connection"
        ::= { stnLDAPAuthorServerEntry 5 }

    stnLDAPAuthorBindPassword  OBJECT-TYPE
        SYNTAX      OCTET STRING
        MAX-ACCESS  read-only
        STATUS      current
        DESCRIPTION
            "This is the password used in conjunction with the 
             stnLDAPAuthorBindUserId to authenticate to the server 
             during a bind"
        ::= { stnLDAPAuthorServerEntry 6 }

    stnLDAPAuthorRootDirectory  OBJECT-TYPE
        SYNTAX      DisplayString
        MAX-ACCESS  read-only
        STATUS      current
        DESCRIPTION
            "The path from the topmost (root) directory of the LDAP server 
             to the directory that contains the 
             stnLDAPAuthorServiceDirectoryName"
        ::= { stnLDAPAuthorServerEntry 7 }

    stnLDAPAuthorServiceDirectoryName  OBJECT-TYPE
        SYNTAX      DisplayString
        MAX-ACCESS  read-only
        STATUS      current
        DESCRIPTION
            "The domain name component of a company or organization.  This
             is the directory where the services and policies directories are
             located"
        ::= { stnLDAPAuthorServerEntry 8 }

    stnLDAPAuthorBindOrganizationalUnit  OBJECT-TYPE
        SYNTAX      DisplayString
        MAX-ACCESS  read-only
        STATUS      current
        DESCRIPTION
            "Directory where the stnLDAPAuthorBindUserId user entry can
             be found"
        ::= { stnLDAPAuthorServerEntry 9 }

    stnLDAPAuthorBindUserId      OBJECT-TYPE
        SYNTAX      DisplayString
        MAX-ACCESS  read-only
        STATUS      current
        DESCRIPTION
            "The user id to be used in conjunction with the 
             stnLDAPAuthorBindPassword to authenticate to the server during
             bind process"
        ::= { stnLDAPAuthorServerEntry 10 }

    stnLDAPAuthorServerName  OBJECT-TYPE
        SYNTAX      DisplayString (SIZE(0..32))
        MAX-ACCESS  read-only
        STATUS      current
        DESCRIPTION
            "The name of this LDAP authorization server - this name will be 
            used for a DNS lookup if no ip address is configured"
        ::= { stnLDAPAuthorServerEntry 11 }

    stnLDAPAuthorServerConfigInstance  OBJECT-TYPE
        SYNTAX      Integer32                              
        MAX-ACCESS  read-only
        STATUS      current
        DESCRIPTION
            "The configuration instance of this LDAP authorization server"
        ::= { stnLDAPAuthorServerEntry 12 }


    --
    -- STN Realm Table
    --
    stnRealmTable  OBJECT-TYPE
        SYNTAX                  SEQUENCE OF StnRealmEntry
        MAX-ACCESS              not-accessible
        STATUS                  current
        DESCRIPTION             "The Realm Table."
        ::= { stnAAAConfig 14 }

    stnRealmEntry  OBJECT-TYPE
        SYNTAX                          StnRealmEntry
        MAX-ACCESS                      not-accessible
        STATUS                          current
        DESCRIPTION
        "A Realm entry. An entry in this table corresponds to a single 
        realm entry"
        INDEX           { stnRealmIndex }
        ::= { stnRealmTable 1 }
        
        StnRealmEntry ::=
            SEQUENCE {
                    stnRealmIndex                   Integer32,
                    stnRealmName                    DisplayString,
                    stnRealmAddrPoolInstance        Integer32,
                    stnRealmForcedNextHop           IpAddress
        }   
    
    stnRealmIndex  OBJECT-TYPE
        SYNTAX                  Integer32
        MAX-ACCESS              read-only
        STATUS                  current
        DESCRIPTION             "The configuration instance of this realm entry."
        ::= { stnRealmEntry 1 }

    stnRealmName  OBJECT-TYPE
        SYNTAX                  DisplayString (SIZE(0..32))
        MAX-ACCESS              read-only
        STATUS                  current
        DESCRIPTION             "The realm name for this realm table entry"
        ::= { stnRealmEntry 2 }
    
    stnRealmAddrPoolInstance OBJECT-TYPE
        SYNTAX                  Integer32
        MAX-ACCESS              read-only
        STATUS                  current
        DESCRIPTION             "The address pool instance associated with 
                                this realm"
        ::= { stnRealmEntry 3 }
            
    stnRealmForcedNextHop  OBJECT-TYPE
        SYNTAX                  IpAddress
        MAX-ACCESS              read-only
        STATUS                  current
        DESCRIPTION             "The IP address of the next hop router that all IP 
                                traffic received on this interface will be sent to"
        ::= { stnRealmEntry 4 }
            

    --
    -- STN Realm RADIUS Authentication Servers Table
    --
    stnRealmRADIUSAuthenTable  OBJECT-TYPE
        SYNTAX                  SEQUENCE OF StnRealmRADIUSAuthenEntry
        MAX-ACCESS              not-accessible
        STATUS                  current
        DESCRIPTION             "The Realm RADIUS Authen Servers Table."
        ::= { stnAAAConfig 15 }

    stnRealmRADIUSAuthenEntry  OBJECT-TYPE
        SYNTAX                          StnRealmRADIUSAuthenEntry
        MAX-ACCESS                      not-accessible
        STATUS                          current
        DESCRIPTION
        "A Realm RADIUS Authentication server entry. An entry in this table 
         corresponds to a single Realm authentication server entry"
        INDEX           { stnRealmIndex,
                          stnRealmRADIUSAuthenServerIndex }
        ::= { stnRealmRADIUSAuthenTable 1 }
        
        StnRealmRADIUSAuthenEntry ::=
            SEQUENCE {
                    stnRealmRADIUSAuthenServerIndex         Integer32,
                    stnRealmRADIUSAuthenServerInstance      Integer32,
                    stnRealmRADIUSAuthenServerAddress       IpAddress,
                    stnRealmRADIUSAuthenServerDestPort      Integer32,
                    stnRealmRADIUSAuthenServerRetrans       Integer32,
                    stnRealmRADIUSAuthenServerTimeOut       Integer32,
                    stnRealmRADIUSAuthenServerSecret        OCTET STRING,
                    stnRealmRADIUSAuthenServerName          DisplayString
        }   
    
    stnRealmRADIUSAuthenServerIndex  OBJECT-TYPE
        SYNTAX                  Integer32
        MAX-ACCESS              read-only
        STATUS                  current
        DESCRIPTION             "The RADIUS authentication server array index."
        ::= { stnRealmRADIUSAuthenEntry 1 }

    stnRealmRADIUSAuthenServerInstance  OBJECT-TYPE
        SYNTAX                  Integer32
        MAX-ACCESS              read-only
        STATUS                  current
        DESCRIPTION             "The instance of a RADIUS authentication server"
        ::= { stnRealmRADIUSAuthenEntry 2 }
    
    stnRealmRADIUSAuthenServerAddress  OBJECT-TYPE
        SYNTAX          IpAddress 
        MAX-ACCESS      read-only
        STATUS          current
        DESCRIPTION     "The IP address of this Radius authentication server."
        ::= { stnRealmRADIUSAuthenEntry 3}

    stnRealmRADIUSAuthenServerDestPort  OBJECT-TYPE
        SYNTAX          Integer32                              
        MAX-ACCESS      read-only
        STATUS          current
        DESCRIPTION
            "The destination authenticaton port of this Radius authentication 
            server."
        ::= { stnRealmRADIUSAuthenEntry 4 }

    stnRealmRADIUSAuthenServerRetrans  OBJECT-TYPE
        SYNTAX          Integer32                              
        MAX-ACCESS      read-only
        STATUS          current
        DESCRIPTION
            "The number of times the router will attempt to retransmit to
            this radius authentication server"
        DEFVAL          {6}
        ::= { stnRealmRADIUSAuthenEntry 5 }

    stnRealmRADIUSAuthenServerTimeOut  OBJECT-TYPE
        SYNTAX          Integer32                              
        MAX-ACCESS      read-only
        STATUS          current
        DESCRIPTION
            "The time (in seconds) to determine the last (re)transmission
            to this authentication server failed."
        DEFVAL          {5}
        ::= { stnRealmRADIUSAuthenEntry 6 }

    stnRealmRADIUSAuthenServerSecret  OBJECT-TYPE
        SYNTAX          OCTET STRING (SIZE(0..255))
        MAX-ACCESS      not-accessible
        STATUS          current
        DESCRIPTION
            "The shared secret configured for this Radius authentication 
            server - this same secret must be configured on the RADIUS server 
            itself"
        ::= { stnRealmRADIUSAuthenEntry 7 }

    stnRealmRADIUSAuthenServerName  OBJECT-TYPE
        SYNTAX          DisplayString (SIZE(0..32))
        MAX-ACCESS      read-only
        STATUS          current
        DESCRIPTION
            "The name of this Radius authentication server - this name will be 
            used for a DNS lookup if no ip address is configured"
        ::= { stnRealmRADIUSAuthenEntry 8 }


    --
    -- STN Named Address Pool
    --
    stnNamedAddressPoolTable  OBJECT-TYPE
        SYNTAX                    SEQUENCE OF StnNamedAddressPoolEntry
        MAX-ACCESS                not-accessible
        STATUS                    current
        DESCRIPTION               "The Named Address Pool Table."
        ::= { stnAAAConfig 16 }

    stnNamedAddressPoolEntry  OBJECT-TYPE
        SYNTAX                    StnNamedAddressPoolEntry
        MAX-ACCESS                not-accessible
        STATUS                    current
        DESCRIPTION               "A named address pool entry. An entry in 
                                  this table corresponds to a single named
                                  address pool"
        INDEX           { stnNamedAddressPoolIndex }
        ::= { stnNamedAddressPoolTable 1 }
                
        StnNamedAddressPoolEntry ::=
            SEQUENCE { 
                    stnNamedAddressPoolIndex              Integer32,
                    stnNamedAddressPoolName               DisplayString
        }

    stnNamedAddressPoolIndex     OBJECT-TYPE
        SYNTAX                   Integer32
        MAX-ACCESS               read-only
        STATUS                   current
        DESCRIPTION              "The configuration instance of this 
                                 Named Address Pool entry."
        ::= { stnNamedAddressPoolEntry 1 }

    stnNamedAddressPoolName  OBJECT-TYPE
        SYNTAX                   DisplayString (SIZE(0..32))
        MAX-ACCESS               read-only
        STATUS                   current
        DESCRIPTION              "The name of this named address pool table 
                                 entry"
        ::= { stnNamedAddressPoolEntry 2 }

    --
    -- STN Named Address Pool Address Range Table
    --
    stnNamedAddressPoolRangeTable  OBJECT-TYPE
        SYNTAX                    SEQUENCE OF StnNamedAddressPoolRangeEntry
        MAX-ACCESS                not-accessible
        STATUS                    current
        DESCRIPTION               "The Named Address Pool Address Range Table."
        ::= { stnAAAConfig 17 }

    stnNamedAddressPoolRangeEntry  OBJECT-TYPE
        SYNTAX                    StnNamedAddressPoolRangeEntry
        MAX-ACCESS                not-accessible
        STATUS                    current
        DESCRIPTION               "A named address pool range entry. An entry
                                  in this table corresponds to a single
                                  address range"
        INDEX           { stnNamedAddressPoolIndex,
                          stnNamedAddressPoolRangeIndex }
        ::= { stnNamedAddressPoolRangeTable 1 }
                
        StnNamedAddressPoolRangeEntry ::=
            SEQUENCE { 
                    stnNamedAddressPoolRangeIndex      Integer32,
                    stnNamedAddressPoolStartIpAddress  IpAddress,
                    stnNamedAddressPoolEndIpAddress    IpAddress
        }

    stnNamedAddressPoolRangeIndex  OBJECT-TYPE
        SYNTAX                   Integer32
        MAX-ACCESS               read-only
        STATUS                   current
        DESCRIPTION              "The index into the array of address ranges"
        ::= { stnNamedAddressPoolRangeEntry 1 }

    stnNamedAddressPoolStartIpAddress  OBJECT-TYPE
        SYNTAX                   IpAddress 
        MAX-ACCESS               read-only
        STATUS                   current
        DESCRIPTION              "The starting IP address of the address range"
        ::= { stnNamedAddressPoolRangeEntry 2 }

    stnNamedAddressPoolEndIpAddress  OBJECT-TYPE
        SYNTAX                           IpAddress 
        MAX-ACCESS                       read-only
        STATUS                           current
        DESCRIPTION                      "The ending IP address of the address range"
        ::= { stnNamedAddressPoolRangeEntry 3 }


    --
    -- STN Session notification support objects.
    --
    stnNotificationRadiusAuthServerIndex OBJECT-TYPE
        SYNTAX          Integer32                              
        MAX-ACCESS      read-only
        STATUS          current
        DESCRIPTION
              "The priority of this Radius authentication server - 
               highest priority is 1 and higher priority servers
               will be contacted first - the priorities must be contiguous"
        ::= { stnAAATrapVars 1 }

    stnNotificationRadiusAccServerIndex  OBJECT-TYPE
        SYNTAX          Integer32                              
        MAX-ACCESS      read-only
        STATUS          current
        DESCRIPTION
              "The priority of this accounting server - higher priority 
               servers will attempt to be contacted before lower priority
               servers - highest priority is 1 - priority indexes must
               be contiguous"
        ::= { stnAAATrapVars 2 }


    --
    -- STN Notifications 
    --
    stnMaxUserSessionLimitExceeded NOTIFICATION-TYPE
        OBJECTS         { stnEngineIndex, stnEngineSlot, stnEngineCpu }
        STATUS          current
        DESCRIPTION     "A stnMaxUserSessionLimitExceeded trap signifies that 
                        the agent entity has detected that the maximum 
                        number of sessions has been exceeded on one of its 
                        engines.
                        The generation of this trap can be controlled by the
                        AAATraps configuration object."
        ::= { stnNotification 20 }

    stnRadiusAuthenMismatch NOTIFICATION-TYPE
        OBJECTS         { stnNotificationRadiusAuthServerIndex, 
                          stnRadiusAuthServerName,
                          stnRadiusAuthServerConfigInstance, 
                          stnRouterIndex }
        STATUS          current
        DESCRIPTION     "A stnRadiusAuthenMismatch trap signifies that 
                        the agent entity has detected that the a 
                        authentication failure (security breach or 
                        retransmission parameter) has been detected on one 
                        of its routers.
                        The generation of this trap can be controlled by the
                        AAATraps configuration object."
        ::= { stnNotification 21 }

    stnPrimaryBillingServerFailure NOTIFICATION-TYPE
        OBJECTS         { stnNotificationRadiusAccServerIndex, 
                          stnRadiusAccServerName,
                          stnRadiusAccServerConfigInstance, 
                          stnRouterIndex }
        STATUS          current
        DESCRIPTION     "A stnPrimaryBillingServerFailure trap signifies that 
                        the agent entity has detected that a problem has
                        occurred with the primary billing server and is 
                        switching to a secondary billing server.
                        The generation of this trap can be controlled by the
                        AAATraps configuration object."
        ::= { stnNotification 22 }

    stnNoAddressesAvailable NOTIFICATION-TYPE
        OBJECTS         { stnRouterIndex }
        STATUS          current
        DESCRIPTION     "A stnNoAddressesAvailable trap signifies that 
                        the agent entity has detected that no addresses
                        are available on the indicated router.
                        The generation of this trap can be controlled by the
                        AAATraps configuration object."
        ::= { stnNotification 23 }

END
