DEC-ATM-SIGNALLING-MIB DEFINITIONS ::= BEGIN

--
--  Definitions of Managed Objects for Digital Equipment Corporation's
--                     ATM Switch "Signalling" MIB"
--                     ============================
--  
--  
--
--  
--                 Name:      dec-atm-signalling-mib-v1-0.txt
--                 Version:   1.0
--                 Date:      September, 1996
--                 Company:   Digital Equipment Corporation
--                 Mail:      TBD
--
--
--  
--  
--  
--  This Digital Equipment  Corporation  SNMP  Management  Information  Base
--  Specification  embodies Digital Equipment Corporation's confidential and
--  proprietary  intellectual  property.   Digital   Equipment   Corporation
--  retains  all  title  and  ownership  in the Specification, including any
--  revisions.
--  
--  It is Digital Equipment Corporation's intent to encourage the widespread
--  use  of  this Specification in connection with the management of Digital
--  Equipment Corporation products.
--  
--  Digital Equipment  Corporation  grants  vendors,  end-users,  and  other
--  interested  parties a non-exclusive license to use this Specification in
--  connection  with  the  management  of  Digital   Equipment   Corporation
--  products.
--  
--  Digital Equipment Corporation reserves the right to make changes in this
--  specification  and  other information contained in this document without
--  prior notice.
--  
--  Digital Equipment Corporation makes no  warranty,  either  expressed  or
--  implied,  as  to  the  use,  operation, condition, or performance of the
--  Specification.  In no  event  shall  Digital  Equipment  Corporation  be
--  liable  for  any incidental, indirect, special, or consequential damages
--  whatsoever (including but not limited to loss of profits) arising out of
--  or related to this document or the information contained in it.
--
--
--
--

--  Object Synopsis
--
--  All objects within this MIB are prefixed with the OBJECT IDENTIFIER "p",
--  where "p" is:
--
--      iso(1).org(3).dod(6).internet(1).private(4).enterprises(1).
--          dec(36).ema(2).decMIBextension(18).decAtmSignallingMIB(34)
--
--  or, 1.3.6.1.4.1.36.2.18.34
--
--
--  Object Name                               Object Id         Non-vol
--  ==================================        ================  =======
--
--  decAtmSignallingMIB                       p
--    decAtmSignallingMIBObjects              p.1
--      decSignallingGroup                    p.1.1
--        decSignallingConfigTable            p.1.1.1
--          decSignallingConfigEntry          p.1.1.1.1
--            decAtmSignallingIndex           p.1.1.1.1.1
--            decAtmSignallingMode            p.1.1.1.1.2
--      decQ2931Group                         p.1.2
--        decQ2931MsgTable                    p.1.2.1
--          decQ2931MsgEntry                  p.1.2.1.1
--            callProceedingTx                p.1.2.1.1.1
--            callProceedingRx                p.1.2.1.1.2
--            connectTx                       p.1.2.1.1.3
--            connectRx                       p.1.2.1.1.4
--            connectAcknowledgeTx            p.1.2.1.1.5
--            connectAcknowledgeRx            p.1.2.1.1.6
--            setupTx                         p.1.2.1.1.7
--            setupRx                         p.1.2.1.1.8
--            releaseTx                       p.1.2.1.1.9
--            releaseRx                       p.1.2.1.1.10
--            releaseCompleteTx               p.1.2.1.1.11
--            releaseCompleteRx               p.1.2.1.1.12
--            restartTx                       p.1.2.1.1.13
--            restartRx                       p.1.2.1.1.14
--            restartAcknowledgeTx            p.1.2.1.1.15
--            restartAcknowledgeRx            p.1.2.1.1.16
--            statusTx                        p.1.2.1.1.17
--            statusRx                        p.1.2.1.1.18
--            statusEnquiryTx                 p.1.2.1.1.19
--            statusEnquiryRx                 p.1.2.1.1.20
--            addPartyTx                      p.1.2.1.1.21
--            addPartyRx                      p.1.2.1.1.22
--            addPartyAcknowledgeTx           p.1.2.1.1.23
--            addPartyAcknowledgeRx           p.1.2.1.1.24
--            addPartyRejectTx                p.1.2.1.1.25
--            addPartyRejectRx                p.1.2.1.1.26
--            dropPartyTx                     p.1.2.1.1.27
--            dropPartyRx                     p.1.2.1.1.28
--            dropPartyAcknowledgeTx          p.1.2.1.1.29
--            dropPartyAcknowledgeRx          p.1.2.1.1.30
--        decQ2931StatusTable                 p.1.2.2
--          decQ2931StatusEntry               p.1.2.2.1
--            totalConns                      p.1.2.2.1.1
--            activeConns                     p.1.2.2.1.2
--            lastTxCause                     p.1.2.2.1.3
--            lastTxDiagnostic                p.1.2.2.1.4
--            lastRxCause                     p.1.2.2.1.5
--            lastRxDiagnostic                p.1.2.2.1.6
--        decQ2931TimerTable                  p.1.2.3
--          decQ2931TimerEntry                p.1.2.3.1
--            t303                            p.1.2.3.1.1
--            t308                            p.1.2.3.1.2
--            t309                            p.1.3.3.1.3
--            t310                            p.1.2.3.1.4
--            t313                            p.1.2.3.1.5
--            t316                            p.1.2.3.1.6
--            t317                            p.1.2.3.1.7
--            t322                            p.1.2.3.1.8
--            t398                            p.1.2.3.1.9
--            t399                            p.1.2.3.1.10
--      decQSaalGroup                         p.1.3
--        decQSaalMsgTable                    p.1.3.1
--          decQSaalMsgEntry                  p.1.3.1.1
--            txDiscardedSdus                 p.1.3.1.1.1
--            rxErrorPdus                     p.1.3.1.1.2
--            txErrorPdus                     p.1.3.1.1.3
--            rxDiscardedPdus                 p.1.3.1.1.4
--            txDiscardedPdus                 p.1.3.1.1.5
--            bgnTx                           p.1.3.1.1.6
--            bgnRx                           p.1.3.1.1.7
--            bgakTx                          p.1.3.1.1.8
--            bgakRx                          p.1.3.1.1.9
--            endTx                           p.1.3.1.1.10
--            endRx                           p.1.3.1.1.11
--            endakTx                         p.1.3.1.1.12
--            endakRx                         p.1.3.1.1.13
--            rsTx                            p.1.3.1.1.14
--            rsRx                            p.1.3.1.1.15
--            rsakTx                          p.1.3.1.1.16
--            rsakRx                          p.1.3.1.1.17
--            bgrejTx                         p.1.3.1.1.18
--            bgrejRx                         p.1.3.1.1.19
--            sdTx                            p.1.3.1.1.20
--            sdRx                            p.1.3.1.1.21
--            sdpTx                           p.1.3.1.1.22
--            sdpRx                           p.1.3.1.1.23
--            erTx                            p.1.3.1.1.24
--            erRx                            p.1.3.1.1.25
--            pollTx                          p.1.3.1.1.26
--            pollRx                          p.1.3.1.1.27
--            statTx                          p.1.3.1.1.28
--            statRx                          p.1.3.1.1.29
--            ustatTx                         p.1.3.1.1.30
--            ustatRx                         p.1.3.1.1.31
--            udTx                            p.1.3.1.1.32
--            udRx                            p.1.3.1.1.33
--            mdTx                            p.1.3.1.1.34
--            mdRx                            p.1.3.1.1.35
--            erakTx                          p.1.3.1.1.36
--            erakRx                          p.1.3.1.1.37




-- ===========================================================================
-- =====================  S t a r t   o f   M I B   ==========================
-- ===========================================================================

    IMPORTS

      Counter
        FROM RFC1155-SMI

      OBJECT-TYPE
        FROM RFC-1212
  
      ifIndex
        FROM RFC1213-MIB

      decMIBextension
        FROM DECATM-MIB;


--  Path to the signalling MIB.

--  dec                 OBJECT IDENTIFIER ::= { enterprises 36 }
--  ema                 OBJECT IDENTIFIER ::= { dec 2 }
--  decMIBextension     OBJECT IDENTIFIER ::= { ema 18 }


--  The DEC ATM signalling MIB.


--  decAtmSignallingMIB MODULE-IDENTITY
--
--    LAST-UPDATED "9609060000Z"
--    ORGANIZATION "Digital Equipment Corporation"
--    CONTACT-INFO
--
--        "Digital Equipment Corporation
--         550 King Street
--         Littleton, MA  01460
--         United States of America"
--
--    DESCRIPTION
--
--        "This module defines a portion of the management information
--         base (MIB) for DEC ATM switches, including GIGAswitch/ATM."
--
--    ::= { decMIBextension 34 }


decAtmSignallingMIB         OBJECT IDENTIFIER ::= { decMIBextension 34 }
decAtmSignallingMIBObjects  OBJECT IDENTIFIER ::= { decAtmSignallingMIB 1 }


-- ===========================================================================
-- ======================   T h e  L i n k  G r o u p   ======================
-- ===========================================================================


--
--  This group is mandatory.
--


decSignallingGroup  OBJECT IDENTIFIER  ::=  { decAtmSignallingMIBObjects 1 }


decSignallingConfigTable OBJECT-TYPE
    SYNTAX  SEQUENCE OF DecSignallingConfigEntry
    ACCESS  not-accessible
    STATUS  mandatory
    DESCRIPTION
            ""
    ::= { decSignallingGroup 1 }


decSignallingConfigEntry OBJECT-TYPE
    SYNTAX  DecSignallingConfigEntry
    ACCESS  not-accessible
    STATUS  mandatory
    DESCRIPTION
            "Each entry describes one UNI / NNI.  Note that the table is
             indexed by 'atm' interfaces, rather than 'aal5' entities."
    INDEX   { ifIndex, decAtmSignallingIndex }
    ::= { decSignallingConfigTable 1 }


DecSignallingConfigEntry ::= SEQUENCE {
    decAtmSignallingIndex      INTEGER,
    decAtmSignallingMode       INTEGER
}


decAtmSignallingIndex OBJECT-TYPE
    SYNTAX  INTEGER
    ACCESS  read-only
    STATUS  mandatory
    DESCRIPTION
            "An arbitrary integer index that can be used to distinguish
             among multiple signalling entities for the same (physical)
             interface."
    ::= { decSignallingConfigEntry 1 }


decAtmSignallingMode OBJECT-TYPE
    SYNTAX  INTEGER {
                     autoConfigure(1),
                     pnni(2),
                     uni30(3),
                     uni31(4),
                     uni40(5)
            }
    ACCESS  read-write                --  MIN-ACCESS  read-only
    STATUS  mandatory
    DESCRIPTION
            "Indicates the mode in which the port is configured to run."
    ::= { decSignallingConfigEntry 2 }




-- ===========================================================================
-- ====================   T h e  Q 2 9 3 1  G r o u p   ======================
-- ===========================================================================


--
--  This group has both mandatory and optional subgroups, as noted below.
--


decQ2931Group       OBJECT IDENTIFIER  ::=  { decAtmSignallingMIBObjects 2 }




-- ===========================================================================
-- =========   T h e  Q 2 9 3 1  S t a t i s t i c s  T a b l e s   ==========
-- ===========================================================================


--
--  This table is mandatory.
--


decQ2931MsgTable OBJECT-TYPE
    SYNTAX  SEQUENCE OF DecQ2931MsgEntry
    ACCESS  not-accessible
    STATUS  mandatory
    DESCRIPTION
            "Describes the number of call/connection processing messages
             sent and received on each UNI or NNI."
    ::= { decQ2931Group 1 }


decQ2931MsgEntry OBJECT-TYPE
    SYNTAX  DecQ2931MsgEntry
    ACCESS  not-accessible
    STATUS  mandatory
    DESCRIPTION
            "Each entry contains signalling statistics for one UNI / NNI.
             Note that the table is indexed by ATM ports (ifType = 'atm')
             as opposed to AAL5 entities (ifType = 'aal5')."
    INDEX   { ifIndex, decAtmSignallingIndex }
    ::= { decQ2931MsgTable 1 }


DecQ2931MsgEntry ::= SEQUENCE {
    callProceedingTx              Counter,
    callProceedingRx              Counter,
    connectTx                     Counter,
    connectRx                     Counter,
    connectAcknowledgeTx          Counter,
    connectAcknowledgeRx          Counter,
    setupTx                       Counter,
    setupRx                       Counter,
    releaseTx                     Counter,
    releaseRx                     Counter,
    releaseCompleteTx             Counter,
    releaseCompleteRx             Counter,
    restartTx                     Counter,
    restartRx                     Counter,
    restartAcknowledgeTx          Counter,
    restartAcknowledgeRx          Counter,
    statusTx                      Counter,
    statusRx                      Counter,
    statusEnquiryTx               Counter,
    statusEnquiryRx               Counter,
    addPartyTx                    Counter,
    addPartyRx                    Counter,
    addPartyAcknowledgeTx         Counter,
    addPartyAcknowledgeRx         Counter,
    addPartyRejectTx              Counter,
    addPartyRejectRx              Counter,
    dropPartyTx                   Counter,
    dropPartyRx                   Counter,
    dropPartyAcknowledgeTx        Counter,
    dropPartyAcknowledgeRx        Counter
}

callProceedingTx OBJECT-TYPE
    SYNTAX  Counter
    ACCESS  read-only
    STATUS  mandatory
    DESCRIPTION
            "The number of CALL PROCEEDING messages transmitted on this
             interface."
    ::= { decQ2931MsgEntry 1 }


callProceedingRx OBJECT-TYPE
    SYNTAX  Counter
    ACCESS  read-only
    STATUS  mandatory
    DESCRIPTION
            "The number of CALL PROCEEDING messages received on this
             interface."
    ::= { decQ2931MsgEntry 2 }


connectTx OBJECT-TYPE
    SYNTAX  Counter
    ACCESS  read-only
    STATUS  mandatory
    DESCRIPTION
            "The number of CONNECT messages transmitted on this
             interface."
    ::= { decQ2931MsgEntry 3 }


connectRx OBJECT-TYPE
    SYNTAX  Counter
    ACCESS  read-only
    STATUS  mandatory
    DESCRIPTION
            "The number of CONNECT messages received on this
             interface."
    ::= { decQ2931MsgEntry 4 }


connectAcknowledgeTx OBJECT-TYPE
    SYNTAX  Counter
    ACCESS  read-only
    STATUS  mandatory
    DESCRIPTION
            "The number of CONNECT ACKNOWLEDGE messages transmitted on
             this interface."
    ::= { decQ2931MsgEntry 5 }


connectAcknowledgeRx OBJECT-TYPE
    SYNTAX  Counter
    ACCESS  read-only
    STATUS  mandatory
    DESCRIPTION
            "The number of CONNECT ACKNOWLEDGE messages received on
             this interface."
    ::= { decQ2931MsgEntry 6 }


setupTx OBJECT-TYPE
    SYNTAX  Counter
    ACCESS  read-only
    STATUS  mandatory
    DESCRIPTION
            "The number of SETUP messages transmitted on this
             interface."
    ::= { decQ2931MsgEntry 7 }


setupRx OBJECT-TYPE
    SYNTAX  Counter
    ACCESS  read-only
    STATUS  mandatory
    DESCRIPTION
            "The number of SETUP messages received on this
             interface."
    ::= { decQ2931MsgEntry 8 }


releaseTx OBJECT-TYPE
    SYNTAX  Counter
    ACCESS  read-only
    STATUS  mandatory
    DESCRIPTION
            "The number of RELEASE messages transmitted on this
             interface."
    ::= { decQ2931MsgEntry 9 }


releaseRx OBJECT-TYPE
    SYNTAX  Counter
    ACCESS  read-only
    STATUS  mandatory
    DESCRIPTION
            "The number of RELEASE messages received on this
             interface."
    ::= { decQ2931MsgEntry 10 }


releaseCompleteTx OBJECT-TYPE
    SYNTAX  Counter
    ACCESS  read-only
    STATUS  mandatory
    DESCRIPTION
            "The number of RELEASE COMPLETE messages transmitted on this
             interface."
    ::= { decQ2931MsgEntry 11 }


releaseCompleteRx OBJECT-TYPE
    SYNTAX  Counter
    ACCESS  read-only
    STATUS  mandatory
    DESCRIPTION
            "The number of RELEASE COMPLETE messages received on this
             interface."
    ::= { decQ2931MsgEntry 12 }


restartTx OBJECT-TYPE
    SYNTAX  Counter
    ACCESS  read-only
    STATUS  mandatory
    DESCRIPTION
            "The number of RESTART messages transmitted on this
             interface."
    ::= { decQ2931MsgEntry 13 }


restartRx OBJECT-TYPE
    SYNTAX  Counter
    ACCESS  read-only
    STATUS  mandatory
    DESCRIPTION
            "The number of RESTART messages received on this
             interface."
    ::= { decQ2931MsgEntry 14 }


restartAcknowledgeTx OBJECT-TYPE
    SYNTAX  Counter
    ACCESS  read-only
    STATUS  mandatory
    DESCRIPTION
            "The number of RESTART ACKNOWLEDGE messages transmitted on
             this interface."
    ::= { decQ2931MsgEntry 15 }


restartAcknowledgeRx OBJECT-TYPE
    SYNTAX  Counter
    ACCESS  read-only
    STATUS  mandatory
    DESCRIPTION
            "The number of RESTART ACKNOWLEDGE messages received on
             this interface."
    ::= { decQ2931MsgEntry 16 }


statusTx OBJECT-TYPE
    SYNTAX  Counter
    ACCESS  read-only
    STATUS  mandatory
    DESCRIPTION
            "The number of STATUS messages transmitted on this
             interface."
    ::= { decQ2931MsgEntry 17 }


statusRx OBJECT-TYPE
    SYNTAX  Counter
    ACCESS  read-only
    STATUS  mandatory
    DESCRIPTION
            "The number of STATUS messages received on this
             interface."
    ::= { decQ2931MsgEntry 18 }


statusEnquiryTx OBJECT-TYPE
    SYNTAX  Counter
    ACCESS  read-only
    STATUS  mandatory
    DESCRIPTION
            "The number of STATUS ENQUIRY messages transmitted on this
             interface."
    ::= { decQ2931MsgEntry 19 }


statusEnquiryRx OBJECT-TYPE
    SYNTAX  Counter
    ACCESS  read-only
    STATUS  mandatory
    DESCRIPTION
            "The number of STATUS ENQUIRY messages received on this
             interface."
    ::= { decQ2931MsgEntry 20 }


addPartyTx OBJECT-TYPE
    SYNTAX  Counter
    ACCESS  read-only
    STATUS  mandatory
    DESCRIPTION
            "The number of ADD PARTY messages transmitted on this
             interface."
    ::= { decQ2931MsgEntry 21 }


addPartyRx OBJECT-TYPE
    SYNTAX  Counter
    ACCESS  read-only
    STATUS  mandatory
    DESCRIPTION
            "The number of ADD PARTY messages received on this
             interface."
    ::= { decQ2931MsgEntry 22 }


addPartyAcknowledgeTx OBJECT-TYPE
    SYNTAX  Counter
    ACCESS  read-only
    STATUS  mandatory
    DESCRIPTION
            "The number of ADD PARTY ACKNOWLEDGE messages transmitted
             on this interface."
    ::= { decQ2931MsgEntry 23 }


addPartyAcknowledgeRx OBJECT-TYPE
    SYNTAX  Counter
    ACCESS  read-only
    STATUS  mandatory
    DESCRIPTION
            "The number of ADD PARTY ACKNOWLEDGE messages received
             on this interface."
    ::= { decQ2931MsgEntry 24 }


addPartyRejectTx OBJECT-TYPE
    SYNTAX  Counter
    ACCESS  read-only
    STATUS  mandatory
    DESCRIPTION
            "The number of ADD PARTY REJECT messages transmitted on
             this interface."
    ::= { decQ2931MsgEntry 25 }


addPartyRejectRx OBJECT-TYPE
    SYNTAX  Counter
    ACCESS  read-only
    STATUS  mandatory
    DESCRIPTION
            "The number of ADD PARTY REJECT messages received on this
             interface."
    ::= { decQ2931MsgEntry 26 }


dropPartyTx OBJECT-TYPE
    SYNTAX  Counter
    ACCESS  read-only
    STATUS  mandatory
    DESCRIPTION
            "The number of DROP PARTY messages transmitted on this
             interface."
    ::= { decQ2931MsgEntry 27 }


dropPartyRx OBJECT-TYPE
    SYNTAX  Counter
    ACCESS  read-only
    STATUS  mandatory
    DESCRIPTION
            "The number of DROP PARTY messages received on this
             interface."
    ::= { decQ2931MsgEntry 28 }


dropPartyAcknowledgeTx OBJECT-TYPE
    SYNTAX  Counter
    ACCESS  read-only
    STATUS  mandatory
    DESCRIPTION
            "The number of DROP PARTY ACKNOWLEDGE messages transmitted
             on this interface."
    ::= { decQ2931MsgEntry 29 }


dropPartyAcknowledgeRx OBJECT-TYPE
    SYNTAX  Counter
    ACCESS  read-only
    STATUS  mandatory
    DESCRIPTION
            "The number of DROP PARTY ACKNOWLEDGE messages received on
             this interface."
    ::= { decQ2931MsgEntry 30 }




--
--  This table is mandatory.
--


decQ2931StatusTable OBJECT-TYPE
    SYNTAX  SEQUENCE OF DecQ2931StatusEntry
    ACCESS  not-accessible
    STATUS  mandatory
    DESCRIPTION
            "Contains additional Q2931 signalling statistics."
    ::= { decQ2931Group 2 }


decQ2931StatusEntry OBJECT-TYPE
    SYNTAX  DecQ2931StatusEntry
    ACCESS  not-accessible
    STATUS  mandatory
    DESCRIPTION
            "Each entry contains signalling statistics for one UNI / NNI.
             Note that the table is indexed by ATM ports (ifType = 'atm')
             as opposed to AAL5 entities (ifType = 'aal5')."
    INDEX   { ifIndex, decAtmSignallingIndex }
    ::= { decQ2931StatusTable 1 }


DecQ2931StatusEntry ::= SEQUENCE {
    totalConns                    INTEGER,
    activeConns                   INTEGER,
    lastTxCause                   INTEGER,
    lastTxDiagnostic              INTEGER,
    lastRxCause                   INTEGER,
    lastRxDiagnostic              INTEGER
}


totalConns OBJECT-TYPE
    SYNTAX  INTEGER
    ACCESS  read-only
    STATUS  mandatory
    DESCRIPTION
            "The total number of connections established so far."
    ::= { decQ2931StatusEntry 1 }


activeConns OBJECT-TYPE
    SYNTAX  INTEGER
    ACCESS  read-only
    STATUS  mandatory
    DESCRIPTION
            "The number of currently-active connections."
    ::= { decQ2931StatusEntry 2 }


lastTxCause OBJECT-TYPE
    SYNTAX  INTEGER
    ACCESS  read-only
    STATUS  mandatory
    DESCRIPTION
            "The most recently transmitted cause code."
    ::= { decQ2931StatusEntry 3 }


lastTxDiagnostic OBJECT-TYPE
    SYNTAX  INTEGER
    ACCESS  read-only
    STATUS  mandatory
    DESCRIPTION
            "The most recently transmitted diagnostic code."
    ::= { decQ2931StatusEntry 4 }


lastRxCause OBJECT-TYPE
    SYNTAX  INTEGER
    ACCESS  read-only
    STATUS  mandatory
    DESCRIPTION
            "The most recently received cause code."
    ::= { decQ2931StatusEntry 5 }


lastRxDiagnostic OBJECT-TYPE
    SYNTAX  INTEGER
    ACCESS  read-only
    STATUS  mandatory
    DESCRIPTION
            "The most recently received diagnostic code."
    ::= { decQ2931StatusEntry 6 }




-- ===========================================================================
-- ==============   T h e  Q 2 9 3 1  T i m e r s  T a b l e   ===============
-- ===========================================================================

--
--  This table is optional.  It lets network managers examine and configure
--  the Q.2931 timeouts documented in the ATM Forum's UNI 3.0 Specification.
--


decQ2931TimerTable OBJECT-TYPE
    SYNTAX  SEQUENCE OF DecQ2931TimerEntry
    ACCESS  not-accessible
    STATUS  mandatory
    DESCRIPTION
            "Allows network managers to examine and configure the timers
             used for Q.2931 call processing."
    ::= { decQ2931Group 3 }


decQ2931TimerEntry OBJECT-TYPE
    SYNTAX  DecQ2931TimerEntry
    ACCESS  not-accessible
    STATUS  mandatory
    DESCRIPTION
            "Each entry contains timers for one UNI / NNI.

             Note that the table is indexed by ATM ports (ifType = 'atm')
             as opposed to AAL5 entities (ifType = 'aal5').

             Sorry about the cryptic timer names, but that's what the ATM
             Forum calls these timers in the UNI V3.0 Specification."
    INDEX   { ifIndex, decAtmSignallingIndex }
    ::= { decQ2931TimerTable 1 }


DecQ2931TimerEntry ::= SEQUENCE {
    t303        INTEGER,
    t308        INTEGER,
    t309        INTEGER,
    t310        INTEGER,
    t313        INTEGER,
    t316        INTEGER,
    t317        INTEGER,
    t322        INTEGER,
    t398        INTEGER,
    t399        INTEGER
}    

t303 OBJECT-TYPE
    SYNTAX  INTEGER
    ACCESS  read-only
    STATUS  mandatory
    DESCRIPTION
            "SETUP message timeout, in seconds."
    DEFVAL { 4 }
    ::= { decQ2931TimerEntry 1 }


t308 OBJECT-TYPE
    SYNTAX  INTEGER
    ACCESS  read-only
    STATUS  mandatory
    DESCRIPTION
            "RELEASE message timeout, in seconds."
    DEFVAL { 30 }
    ::= { decQ2931TimerEntry 2 }


t309 OBJECT-TYPE
    SYNTAX  INTEGER
    ACCESS  read-only
    STATUS  mandatory
    DESCRIPTION
            "SAAL disconnection timeout, in seconds."
    DEFVAL { 90 }
    ::= { decQ2931TimerEntry 3 }


t310 OBJECT-TYPE
    SYNTAX  INTEGER
    ACCESS  read-only
    STATUS  mandatory
    DESCRIPTION
            "CALL PROCEEDING timeout, in seconds."
    DEFVAL { 10 }
    ::= { decQ2931TimerEntry 4 }


t313 OBJECT-TYPE
    SYNTAX  INTEGER
    ACCESS  read-only
    STATUS  mandatory
    DESCRIPTION
            "CONNECT timeout, in seconds.  This timer is only used on
             the User side of a UNI."
    DEFVAL { 4 }
    ::= { decQ2931TimerEntry 5 }


t316 OBJECT-TYPE
    SYNTAX  INTEGER
    ACCESS  read-only
    STATUS  mandatory
    DESCRIPTION
            "RESTART timeout, in seconds."
    DEFVAL { 120 }
    ::= { decQ2931TimerEntry 6 }


t317 OBJECT-TYPE
    SYNTAX  INTEGER
    ACCESS  read-only
    STATUS  mandatory
    DESCRIPTION
            "RESTART reply timeout, in seconds.  This should be less
             than the value for timer 't316'."
    ::= { decQ2931TimerEntry 7 }


t322 OBJECT-TYPE
    SYNTAX  INTEGER
    ACCESS  read-only
    STATUS  mandatory
    DESCRIPTION
            "STATUS ENQUIRY timeout, in seconds."
    DEFVAL { 4 }
    ::= { decQ2931TimerEntry 8 }


t398 OBJECT-TYPE
    SYNTAX  INTEGER
    ACCESS  read-only
    STATUS  mandatory
    DESCRIPTION
            "DROP PARTY timeout, in seconds."
    DEFVAL { 4 }
    ::= { decQ2931TimerEntry 9 }


t399 OBJECT-TYPE
    SYNTAX  INTEGER
    ACCESS  read-only
    STATUS  mandatory
    DESCRIPTION
            "ADD PARTY timeout, in seconds."
    DEFVAL { 14 }
    ::= { decQ2931TimerEntry 10 }




-- ===========================================================================
-- ====================   T h e  Q S A A L  G r o u p   ======================
-- ===========================================================================


decQSaalGroup       OBJECT IDENTIFIER  ::=  { decAtmSignallingMIBObjects 3 }


--
--  This table is mandatory.
--


decQSaalMsgTable OBJECT-TYPE
    SYNTAX  SEQUENCE OF DecQSaalMsgEntry
    ACCESS  not-accessible
    STATUS  mandatory
    DESCRIPTION
            ""
    ::= { decQSaalGroup 1 }


decQSaalMsgEntry OBJECT-TYPE
    SYNTAX  DecQSaalMsgEntry
    ACCESS  not-accessible
    STATUS  mandatory
    DESCRIPTION
            "Each entry contains signalling statistics for one UNI / NNI.
             Note that the table is indexed by ATM ports (ifType = 'atm')
             as opposed to AAL5 entities (ifType = 'aal5')."
    INDEX   { ifIndex, decAtmSignallingIndex }
    ::= { decQSaalMsgTable 1 }


DecQSaalMsgEntry ::= SEQUENCE {
    txDiscardedSdus        Counter,
    rxErrorPdus            Counter,
    txErrorPdus            Counter,
    rxDiscardedPdus        Counter,
    txDiscardedPdus        Counter,
    bgnTx                  Counter,
    bgnRx                  Counter,
    bgakTx                 Counter,
    bgakRx                 Counter,
    endTx                  Counter,
    endRx                  Counter,
    endakTx                Counter,
    endakRx                Counter,
    rsTx                   Counter,
    rsRx                   Counter,
    rsakTx                 Counter,
    rsakRx                 Counter,
    bgrejTx                Counter,
    bgrejRx                Counter,
    sdTx                   Counter,
    sdRx                   Counter,
    sdpTx                  Counter,
    sdpRx                  Counter,
    erTx                   Counter,
    erRx                   Counter,
    pollTx                 Counter,
    pollRx                 Counter,
    statTx                 Counter,
    statRx                 Counter,
    ustatTx                Counter,
    ustatRx                Counter,
    udTx                   Counter,
    udRx                   Counter,
    mdTx                   Counter,
    mdRx                   Counter,
    erakTx                 Counter,
    erakRx                 Counter
}



txDiscardedSdus OBJECT-TYPE
    SYNTAX  Counter
    ACCESS  read-only
    STATUS  mandatory
    DESCRIPTION
            "The number of outgoing SDUs which were discarded."
    ::= { decQSaalMsgEntry 1 }


rxErrorPdus OBJECT-TYPE
    SYNTAX  Counter
    ACCESS  read-only
    STATUS  mandatory
    DESCRIPTION
            "The number of incoming PDUs which could not be received
             due to errors."
    ::= { decQSaalMsgEntry 2 }


txErrorPdus OBJECT-TYPE
    SYNTAX  Counter
    ACCESS  read-only
    STATUS  mandatory
    DESCRIPTION
            "The number of transmission errors for outgoing PDUs."
    ::= { decQSaalMsgEntry 3 }


rxDiscardedPdus OBJECT-TYPE
    SYNTAX  Counter
    ACCESS  read-only
    STATUS  mandatory
    DESCRIPTION
            "The number of incoming PDUs which were discarded."
    ::= { decQSaalMsgEntry 4 }


txDiscardedPdus OBJECT-TYPE
    SYNTAX  Counter
    ACCESS  read-only
    STATUS  mandatory
    DESCRIPTION
            "The number of outgoing PDUs which were discarded."
    ::= { decQSaalMsgEntry 5 }


bgnTx OBJECT-TYPE
    SYNTAX  Counter
    ACCESS  read-only
    STATUS  mandatory
    DESCRIPTION
            "The number of BGN (Request Initialization) messages
             transmitted over the interface."
    ::= { decQSaalMsgEntry 6 }


bgnRx OBJECT-TYPE
    SYNTAX  Counter
    ACCESS  read-only
    STATUS  mandatory
    DESCRIPTION
            "The number of BGN (Request Initialization) messages
             received over the interface."
    ::= { decQSaalMsgEntry 7 }


bgakTx OBJECT-TYPE
    SYNTAX  Counter
    ACCESS  read-only
    STATUS  mandatory
    DESCRIPTION
            "The number of BGAK (Request Acknowledgement) messages
             transmitted over the interface."
    ::= { decQSaalMsgEntry 8 }


bgakRx OBJECT-TYPE
    SYNTAX  Counter
    ACCESS  read-only
    STATUS  mandatory
    DESCRIPTION
            "The number of BGAK (Request Acknowledgement) messages
             received over the interface."
    ::= { decQSaalMsgEntry 9 }


endTx OBJECT-TYPE
    SYNTAX  Counter
    ACCESS  read-only
    STATUS  mandatory
    DESCRIPTION
            "The number of END (Disconnect Command) messages transmitted
             over the interface."
    ::= { decQSaalMsgEntry 10 }


endRx OBJECT-TYPE
    SYNTAX  Counter
    ACCESS  read-only
    STATUS  mandatory
    DESCRIPTION
            "The number of END (Disconnect Command) messages received
             over the interface."
    ::= { decQSaalMsgEntry 11 }


endakTx OBJECT-TYPE
    SYNTAX  Counter
    ACCESS  read-only
    STATUS  mandatory
    DESCRIPTION
            "The number of ENDAK (Disconnect Acknowledgement) messages
             transmitted over the interface."
    ::= { decQSaalMsgEntry 12 }


endakRx OBJECT-TYPE
    SYNTAX  Counter
    ACCESS  read-only
    STATUS  mandatory
    DESCRIPTION
            "The number of ENDAK (Disconnect Acknowledgement) messages
             received over the interface."
    ::= { decQSaalMsgEntry 13 }


rsTx OBJECT-TYPE
    SYNTAX  Counter
    ACCESS  read-only
    STATUS  mandatory
    DESCRIPTION
            "The number of RS (Resynchronization Command) messages
             transmitted over the interface."
    ::= { decQSaalMsgEntry 14 }


rsRx OBJECT-TYPE
    SYNTAX  Counter
    ACCESS  read-only
    STATUS  mandatory
    DESCRIPTION
            "The number of RS (Resynchronization Command) messages
             received over the interface."
    ::= { decQSaalMsgEntry 15 }


rsakTx OBJECT-TYPE
    SYNTAX  Counter
    ACCESS  read-only
    STATUS  mandatory
    DESCRIPTION
            "The number of RSAK (Resynchronization Acknowledgement)
             messages transmitted over the interface."
    ::= { decQSaalMsgEntry 16 }


rsakRx OBJECT-TYPE
    SYNTAX  Counter
    ACCESS  read-only
    STATUS  mandatory
    DESCRIPTION
            "The number of RSAK (Resynchronization Acknowledgement)
             messages received over the interface."
    ::= { decQSaalMsgEntry 17 }


bgrejTx OBJECT-TYPE
    SYNTAX  Counter
    ACCESS  read-only
    STATUS  mandatory
    DESCRIPTION
            "The number of BGREJ (Connection Reject) messages
             transmitted over the interface."
    ::= { decQSaalMsgEntry 18 }


bgrejRx OBJECT-TYPE
    SYNTAX  Counter
    ACCESS  read-only
    STATUS  mandatory
    DESCRIPTION
            "The number of BGREJ (Connection Reject) messages
             received over the interface."
    ::= { decQSaalMsgEntry 19 }


sdTx OBJECT-TYPE
    SYNTAX  Counter
    ACCESS  read-only
    STATUS  mandatory
    DESCRIPTION
            "The number of SD (Sequenced Connection-Mode Data) messages
             transmitted over the interface."
    ::= { decQSaalMsgEntry 20 }


sdRx OBJECT-TYPE
    SYNTAX  Counter
    ACCESS  read-only
    STATUS  mandatory
    DESCRIPTION
            "The number of SD (Sequenced Connection-Mode Data) messages
             received over the interface."
    ::= { decQSaalMsgEntry 21 }


sdpTx OBJECT-TYPE
    SYNTAX  Counter
    ACCESS  read-only
    STATUS  mandatory
    DESCRIPTION
            "The number of SDP (Sequenced Connection-Mode Data with
             request for Receive State Information) messages transmitted
             over the interface.

             This object only applies to UNI 3.0."
    ::= { decQSaalMsgEntry 22 }


sdpRx OBJECT-TYPE
    SYNTAX  Counter
    ACCESS  read-only
    STATUS  mandatory
    DESCRIPTION
            "The number of SDP (Sequenced Connection-Mode Data with
             request for Receive State Information) messages received
             over the interface.

             This object only applies to UNI 3.0."
    ::= { decQSaalMsgEntry 23 }


erTx OBJECT-TYPE
    SYNTAX  Counter
    ACCESS  read-only
    STATUS  mandatory
    DESCRIPTION
            "The number of ER (Recovery Command) messages transmitted
             over the interface.

             This object is not applicable to UNI 3.0."
    ::= { decQSaalMsgEntry 24 }


erRx OBJECT-TYPE
    SYNTAX  Counter
    ACCESS  read-only
    STATUS  mandatory
    DESCRIPTION
            "The number of ER (Recovery Command) messages received
             over the interface.

             This object is not applicable to UNI 3.0."
    ::= { decQSaalMsgEntry 25 }


pollTx OBJECT-TYPE
    SYNTAX  Counter
    ACCESS  read-only
    STATUS  mandatory
    DESCRIPTION
            "The number of POLL (Transmitter State Information with
             request for Receive State Information) messages transmitted
             over the interface."
    ::= { decQSaalMsgEntry 26 }


pollRx OBJECT-TYPE
    SYNTAX  Counter
    ACCESS  read-only
    STATUS  mandatory
    DESCRIPTION
            "The number of POLL (Transmitter State Information with
             request for Receive State Information) messages received
             over the interface."
    ::= { decQSaalMsgEntry 27 }


statTx OBJECT-TYPE
    SYNTAX  Counter
    ACCESS  read-only
    STATUS  mandatory
    DESCRIPTION
            "The number of STAT (Solicited Receiver State Information)
             messages transmitted over the interface."
    ::= { decQSaalMsgEntry 28 }


statRx OBJECT-TYPE
    SYNTAX  Counter
    ACCESS  read-only
    STATUS  mandatory
    DESCRIPTION
            "The number of STAT (Solicited Receiver State Information)
             messages received over the interface."
    ::= { decQSaalMsgEntry 29 }


ustatTx OBJECT-TYPE
    SYNTAX  Counter
    ACCESS  read-only
    STATUS  mandatory
    DESCRIPTION
            "The number of USTAT (Unsolicited Receiver State Info)
             messages transmitted over the interface."
    ::= { decQSaalMsgEntry 30 }


ustatRx OBJECT-TYPE
    SYNTAX  Counter
    ACCESS  read-only
    STATUS  mandatory
    DESCRIPTION
            "The number of USTAT (Unsolicited Receiver State Info)
             messages received over the interface."
    ::= { decQSaalMsgEntry 31 }


udTx OBJECT-TYPE
    SYNTAX  Counter
    ACCESS  read-only
    STATUS  mandatory
    DESCRIPTION
            "The number of UD (Unnumbered User Data) messages
             transmitted over the interface."
    ::= { decQSaalMsgEntry 32 }


udRx OBJECT-TYPE
    SYNTAX  Counter
    ACCESS  read-only
    STATUS  mandatory
    DESCRIPTION
            "The number of UD (Unnumbered User Data) messages
             received over the interface."
    ::= { decQSaalMsgEntry 33 }


mdTx OBJECT-TYPE
    SYNTAX  Counter
    ACCESS  read-only
    STATUS  mandatory
    DESCRIPTION
            "The number of MD (Unnumbered Management Data) messages
             transmitted over the interface."
    ::= { decQSaalMsgEntry 34 }


mdRx OBJECT-TYPE
    SYNTAX  Counter
    ACCESS  read-only
    STATUS  mandatory
    DESCRIPTION
            "The number of MD (Unnumbered Management Data) messages
             received over the interface."
    ::= { decQSaalMsgEntry 35 }


erakTx OBJECT-TYPE
    SYNTAX  Counter
    ACCESS  read-only
    STATUS  mandatory
    DESCRIPTION
            "The number of ERAK (Recovery Acknowledgement) messages
             transmitted over the interface.

             This object is not applicable to UNI 3.0."
    ::= { decQSaalMsgEntry 36 }


erakRx OBJECT-TYPE
    SYNTAX  Counter
    ACCESS  read-only
    STATUS  mandatory
    DESCRIPTION
            "The number of ERAK (Recovery Acknowledgement) messages
             received over the interface.

             This object is not applicable to UNI 3.0."
    ::= { decQSaalMsgEntry 37 }




END
