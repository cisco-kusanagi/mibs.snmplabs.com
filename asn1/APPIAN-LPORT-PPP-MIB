--
--      Title:  Appian PPP/MLPPP Services MIB
--
--      Dated:  11/8/99
--      Author: D. Theriault
--
--      Description:
--
--      This MIB file contains the definitions and support for the Appian
--      Optical Services Access Platform(s).
-- 
--      This MIB is a subsection of the Appian Services MIB (services.mib) and
--      contains the configuration and statistics MIBs for the Point-to-Point
--      and Multi-Link Point-to-Point protocol.
--
--  Notes:
--
--      1.  Now that there will be a multilink flag in the acTrunkTable may
--          want to break out the MLPPP stuff into its own table
--
APPIAN-LPORT-PPP-MIB  DEFINITIONS ::= BEGIN
    IMPORTS
        acLport, AcNodeId                                   FROM APPIAN-SMI-MIB
        
        MODULE-IDENTITY, OBJECT-TYPE                        FROM SNMPv2-SMI

        TEXTUAL-CONVENTION, DisplayString                   FROM SNMPv2-TC;

--
-- Top Level PPP Node
--        
acPppLinks

    MODULE-IDENTITY
        LAST-UPDATED     "0002230000Z"
        ORGANIZATION    "Appian Communications, Inc."
        CONTACT-INFO    "Gerry Pednault"

        DESCRIPTION     "Appian Communications PPP/MLPPP Services MIB."

        ::= { acLport 5  }

--
-- Local TC's for PPP
--
    AcPppEndDiscriminator  ::= TEXTUAL-CONVENTION
    STATUS  current
    DESCRIPTION
    "The EndPoint descriminator class provided to the remote PPP peer.  For 
    further information, refer to RFC-1990 for details."
    SYNTAX  INTEGER {
                null(1),
                localAddress(2),
                networkAddress(3),
                macAddress(4),
                magicNumber(5),
                psndn(6)
            }


-- THIS IS THE acPppSessionTable
--
-- The PPP Link Group. Implementation of this
-- group is mandatory for all PPP entities.
--
-- The following object reflect the values of the option
-- parameters used in the PPP Link Control Protocol
--   acPppLinkStatusLocalMRU
--   acPppLinkStatusRemoteMRU
--   acPppLinkStatusLocalToPeerACCMap
--   acPppLinkStatusPeerToLocalACCMap
--   acPppLinkStatusLocalToRemoteProtocolCompression
--   acPppLinkStatusRemoteToLocalProtocolCompression
--   acPppLinkStatusLocalToRemoteACCompression
--   acPppLinkStatusRemoteToLocalACCompression
--   acPppLinkStatusTransmitFcsSize
--   acPppLinkStatusReceiveFcsSize
--   PppLinkStatusLocalMRRU
--   PppLinkStatusRemoteMRRU
--   PppLinkStatusLocalEPDClass
--   PppLinkStatusLocalEPDLength
--   PppLinkStatusLocalEPDArray
--   PppLinkStatusRemoteEPDClass
--   PppLinkStatusRemoteEPDLength
--   PppLinkStatusRemoteEPDArray
--
-- These values are not available until after the PPP Option
-- negotiation has completed, which is indicated by the link
-- reaching the open state (i.e., ifOperStatus is set to
-- up).
--
-- Therefore, when ifOperStatus is not up
-- the contents of these objects is undefined. The value
-- returned when accessing the objects is an implementation
-- dependent issue.


acPppLinkStatusTable   OBJECT-TYPE
    SYNTAX  SEQUENCE OF AcPppLinkStatusEntry
    MAX-ACCESS  not-accessible
    STATUS      current
    DESCRIPTION
    "A table containing PPP-link specific variables for this PPP
    implementation. This is an OSAP created Read Only record" 
    
    ::= { acPppLinks 1 }

acPppLinkStatusEntry    OBJECT-TYPE
    SYNTAX  AcPppLinkStatusEntry
    MAX-ACCESS  not-accessible
    STATUS      current
    DESCRIPTION
    "This record contains operational start up information about
     a particular PPP Link."
    
    INDEX { acPppLinkStatusNodeId, acPppLinkStatusTimeSlotIndex }
    
    ::= { acPppLinkStatusTable 1 }
    
    AcPppLinkStatusEntry ::= 
        SEQUENCE {
            acPppLinkStatusNodeId                               AcNodeId,
            acPppLinkStatusTimeSlotIndex                        INTEGER,
            acPppLinkStatusLocalMRU                             INTEGER,
            acPppLinkStatusRemoteMRU                            INTEGER,
            acPppLinkStatusLocalToPeerACCMap                    INTEGER,
            acPppLinkStatusPeerToLocalACCMap                    INTEGER,
            acPppLinkStatusLocalToRemoteProtocolCompression     INTEGER,
            acPppLinkStatusRemoteToLocalProtocolCompression     INTEGER,
            acPppLinkStatusLocalToRemoteACCompression           INTEGER,
            acPppLinkStatusRemoteToLocalACCompression           INTEGER,
            acPppLinkStatusTransmitFcsSize                      INTEGER,
            acPppLinkStatusReceiveFcsSize                       INTEGER,
            acPppLinkStatusLocalMRRU                            INTEGER,
            acPppLinkStatusRemoteMRRU                           INTEGER,
            acPppLinkStatusLocalEPDClass                        AcPppEndDiscriminator,
            acPppLinkStatusLocalEPDLength                       INTEGER,
            acPppLinkStatusLocalEPDArray                        DisplayString,
            acPppLinkStatusRemoteEPDClass                       AcPppEndDiscriminator,
            acPppLinkStatusRemoteEPDLength                      INTEGER, 
            acPppLinkStatusRemoteEPDArray                       DisplayString
        }

acPppLinkStatusNodeId   OBJECT-TYPE
    SYNTAX  AcNodeId
    MAX-ACCESS  accessible-for-notify
    STATUS  current
    DESCRIPTION
    "The node id is the id for this specific node in the OSAP ring."

    ::= { acPppLinkStatusEntry 1 }

acPppLinkStatusTimeSlotIndex   OBJECT-TYPE
    SYNTAX  INTEGER (0..2147483647)
    MAX-ACCESS  accessible-for-notify
    STATUS      current
    DESCRIPTION
    "The value of acPppLinkStatusTimeSlotIndex is the same as acTimeSlotIndex
    in acTimeslotTable that this interface PPP link corresponds to."
    
    ::= { acPppLinkStatusEntry 2 }


acPppLinkStatusLocalMRU   OBJECT-TYPE
    SYNTAX  INTEGER
    MAX-ACCESS  read-only
    STATUS      current
    DESCRIPTION
    "The current value of the MRU for the local PPP Entity. This value is the
    MRU that the remote entity is using when sending packets to the local PPP
    entity. The value of this object is meaningful only when the link has
    reached the open state."
    
    ::= { acPppLinkStatusEntry 3 }


acPppLinkStatusRemoteMRU   OBJECT-TYPE
    SYNTAX  INTEGER
    MAX-ACCESS  read-only
    STATUS      current
    DESCRIPTION
    "The current value of the MRU for the remote PPP Entity. This value is the
    MRU that the local entity is using when sending packets to the remote PPP
    entity. The value of this object is meaningful only when the link has 
    reached the open state."
    
    ::= { acPppLinkStatusEntry 4 }


acPppLinkStatusLocalToPeerACCMap   OBJECT-TYPE
    SYNTAX  INTEGER
    MAX-ACCESS  read-only
    STATUS      current
    DESCRIPTION
    "The current value of the ACC Map used for sending packets from the local
    PPP entity to the remote PPP entity. The value of this object is 
    meaningful only when the link has reached the open state."
    
    ::= { acPppLinkStatusEntry 5 }


acPppLinkStatusPeerToLocalACCMap   OBJECT-TYPE
    SYNTAX  INTEGER
    MAX-ACCESS  read-only
    STATUS      current
    DESCRIPTION
    "The ACC Map used by the remote PPP entity when transmitting packets to
    the local PPP entity. The value of this object is meaningful only when the
    link has reached the open state." 
    
    ::= { acPppLinkStatusEntry 6 }


acPppLinkStatusLocalToRemoteProtocolCompression OBJECT-TYPE
    SYNTAX  INTEGER {
                enabled(1),
                disabled(2)
            }
    MAX-ACCESS  read-only
    STATUS      current
    DESCRIPTION
    "Indicates whether the local PPP entity will use Protocol Compression when
    transmitting packets to the remote PPP entity. The value of this object is
    meaningful only when the link has reached the open state."
               
    ::= { acPppLinkStatusEntry 7 }


acPppLinkStatusRemoteToLocalProtocolCompression OBJECT-TYPE
    SYNTAX  INTEGER {
                enabled(1),
                disabled(2)
            }
    MAX-ACCESS  read-only
    STATUS      current
    DESCRIPTION
    "Indicates whether the remote PPP entity will use Protocol Compression
    when transmitting packets to the local PPP entity. The value of this
    object is meaningful only when the link has reached the open state."
    
    ::= { acPppLinkStatusEntry 8 }


acPppLinkStatusLocalToRemoteACCompression   OBJECT-TYPE
    SYNTAX  INTEGER {
                enabled(1),
                disabled(2)
             }
    MAX-ACCESS  read-only
    STATUS      current
    DESCRIPTION
    "Indicates whether the local PPP entity will use Address and Control
    Compression when transmitting packets to the remote PPP entity.  The 
    value of this object is meaningful only when the link has reached the 
    open state." 
    
    ::= { acPppLinkStatusEntry 9 }


acPppLinkStatusRemoteToLocalACCompression   OBJECT-TYPE
    SYNTAX  INTEGER {
                enabled(1),
                disabled(2)
            }
    MAX-ACCESS  read-only
    STATUS      current
    DESCRIPTION
    "Indicates whether the remote PPP entity will use Address and Control
    Compression when transmitting packets to the local PPP entity.  The 
    value of this object is meaningful only when the link has reached the 
    open state." 
    
    ::= { acPppLinkStatusEntry 10 }


acPppLinkStatusTransmitFcsSize   OBJECT-TYPE
    SYNTAX  INTEGER (0..128)
    MAX-ACCESS  read-only
    STATUS      current
    DESCRIPTION
    "The size of the Frame Check Sequence (FCS) in bits that the local node
    will generate when sending packets to the remote node. The value of this
    object is meaningful only when the link has reached the open state."
               
    ::= { acPppLinkStatusEntry 11 }


acPppLinkStatusReceiveFcsSize   OBJECT-TYPE
    SYNTAX  INTEGER (0..128)
    MAX-ACCESS  read-only
    STATUS      current
    DESCRIPTION
    "The size of the Frame Check Sequence (FCS) in bits that the remote node
    will generate when sending packets to the local node. The value of this
    object is meaningful only when the link has reached the open state."
    
    ::= { acPppLinkStatusEntry 12 }


acPppLinkStatusLocalMRRU   OBJECT-TYPE
    SYNTAX  INTEGER
    MAX-ACCESS  read-only
    STATUS      current
    DESCRIPTION
    "The current value of the MRRU for the local PPP Entity. This value is 
    the MRRU that the remote entity is using when sending packets to the
    local PPP entity. The value of this object is meaningful only when the
    link has reached the open state."
    
    ::= { acPppLinkStatusEntry 13 }


acPppLinkStatusRemoteMRRU   OBJECT-TYPE
    SYNTAX  INTEGER
    MAX-ACCESS  read-only
    STATUS      current
    DESCRIPTION
    "The current value of the MRRU for the remote PPP link Entity. This value
    is the MRRU that the local entity is using when sending packets to the
    remote PPP link entity. The value of this object is meaningful only when
    the link has reached the open state."
    
    ::= { acPppLinkStatusEntry 14 }

acPppLinkStatusLocalEPDClass   OBJECT-TYPE
    SYNTAX  AcPppEndDiscriminator
    MAX-ACCESS  read-only
    STATUS      current
    DESCRIPTION
    "The Endpoint Discriminator class provided to the remote PPP peer (See 
    RFC-1990 for details)." 
    
    ::= { acPppLinkStatusEntry 15 }


acPppLinkStatusLocalEPDLength   OBJECT-TYPE
    SYNTAX  INTEGER (0..20)
    MAX-ACCESS  read-only
    STATUS      current
    DESCRIPTION
    "The length of the Local Endpoint Discriminator, in bytes."
               
    ::= { acPppLinkStatusEntry 16 }


acPppLinkStatusLocalEPDArray   OBJECT-TYPE
    SYNTAX  DisplayString (SIZE (0..55))
    MAX-ACCESS  read-only
    STATUS      current
    DESCRIPTION
    "An ASCII representation of the contents of the Local Endpoint
    Discriminator." 
    
    ::= { acPppLinkStatusEntry 17 }

acPppLinkStatusRemoteEPDClass   OBJECT-TYPE
    SYNTAX  AcPppEndDiscriminator
    MAX-ACCESS  read-only
    STATUS      current
    DESCRIPTION
    "The Endpoint Discriminator class provided to the local PPP peer (See 
    RFC-1990 for details)." 
    
    ::= { acPppLinkStatusEntry 18 }


acPppLinkStatusRemoteEPDLength   OBJECT-TYPE
    SYNTAX  INTEGER (0..20)
    MAX-ACCESS  read-only
    STATUS      current
    DESCRIPTION
    "The length of the Remote Endpoint Discriminator, in bytes."
    
    ::= { acPppLinkStatusEntry 19 }


acPppLinkStatusRemoteEPDArray   OBJECT-TYPE
    SYNTAX  DisplayString (SIZE (0..55))
    MAX-ACCESS  read-only
    STATUS      current
    DESCRIPTION
    "An Ascii representation of the contents of the Remote Endpoint
    Discriminator." 
    
    ::= { acPppLinkStatusEntry 20 }

END
