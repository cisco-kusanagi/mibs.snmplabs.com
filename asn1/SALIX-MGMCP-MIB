SALIX-MGMCP-MIB DEFINITIONS ::= BEGIN

IMPORTS
         OBJECT-TYPE, Integer32,
         IpAddress, Counter32,MODULE-IDENTITY            FROM SNMPv2-SMI
         
         DisplayString                    FROM RFC1213-MIB         

         MODULE-COMPLIANCE, OBJECT-GROUP            FROM SNMPv2-CONF

         platform1                        FROM SALIX-MIB;

salixMgmcpMIB MODULE-IDENTITY
     LAST-UPDATED "9906170000Z"
     ORGANIZATION "SALIX Technologies"
     CONTACT-INFO "904 Wind River Lane
                   Suite 101
                   Gaithersburg, MD  20878
                   (301)-417-0017"
     DESCRIPTION  "The MIB describing MGMCP sessions."
     ::= { platform1 2 } 
     
   salixMgmcpMIBObjects OBJECT IDENTIFIER ::= { salixMgmcpMIB 1 }
   salixMgmcpMIBTraps   OBJECT IDENTIFIER ::= { salixMgmcpMIB 2 }
   salixMgmcpMIBCompliance OBJECT IDENTIFIER ::= { salixMgmcpMIB 3 }
   salixMgmcpMIBTrapPrefix OBJECT IDENTIFIER ::= { salixMgmcpMIBTraps 0 }
   
   -- IPDC Objects
   
   salixMgmcpIpdcObjects OBJECT IDENTIFIER ::= { salixMgmcpMIBObjects 1 }

      -- IPDC Session Table

         ipdcSessionTable OBJECT-TYPE
            SYNTAX     SEQUENCE OF    IpdcSessionEntry
            MAX-ACCESS not-accessible
            STATUS     current
            DESCRIPTION
               "The ipdcSessionTable maps IPDC session indices to
                IP addresses and ports.  There should be an entry
                in the table for each IPDC session."
            ::= { salixMgmcpIpdcObjects 1 }
         
         ipdcSessionEntry OBJECT-TYPE
            SYNTAX     IpdcSessionEntry
            MAX-ACCESS not-accessible
            STATUS     current
            DESCRIPTION
               "An entry in the ipdcSessionTable.  The attributes
                describe the IPDC session"
            INDEX { ipdcSessionIndex }
            ::= { ipdcSessionTable 1 }
         
         IpdcSessionEntry ::= SEQUENCE {
            ipdcSessionIndex                    Integer32,
            ipdcSessionLocalIpAddress           IpAddress,
            ipdcSessionLocalPort                INTEGER,
            ipdcSessionMediaControllerIpAddress IpAddress,
            ipdcSessionMediaControllerPort      INTEGER
         }
         
         ipdcSessionIndex OBJECT-TYPE
            SYNTAX     Integer32
            MAX-ACCESS not-accessible
            STATUS     current
            DESCRIPTION
               "A unique index for IPDC sessions.  This number is 
                assigned by the agent when the session is created 
                and has no relationship to the IPDC session except 
                for identification purposes"
            ::= { ipdcSessionEntry 1 }
         
         ipdcSessionLocalIpAddress OBJECT-TYPE
            SYNTAX     IpAddress
            MAX-ACCESS read-write
            STATUS     current
            DESCRIPTION
               "The local (agent side) IP Address being used by the
                IPDC session"
            ::= { ipdcSessionEntry 2 }
         
         ipdcSessionLocalPort OBJECT-TYPE
            SYNTAX     INTEGER(0..65535)
            MAX-ACCESS read-write
            STATUS     current
            DESCRIPTION
               "The local (agent side) UDP port being used by the
                IDPC session"
            ::= { ipdcSessionEntry 3 }
         
         ipdcSessionMediaControllerIpAddress OBJECT-TYPE
            SYNTAX     IpAddress
            MAX-ACCESS read-write
            STATUS     current
            DESCRIPTION
               "The IP Address for the Media Controller using the 
                IPDC session"
            ::= { ipdcSessionEntry 4 }
         
         ipdcSessionMediaControllerPort OBJECT-TYPE
            SYNTAX     INTEGER(0..65535)
            MAX-ACCESS read-write
            STATUS     current
            DESCRIPTION
               "The UDP port for the Media Controller using the 
                IPDC session"
            ::= { ipdcSessionEntry 5 }
         
      -- IPDC Session Statistics table
         ipdcSessionStatsTable OBJECT-TYPE
            SYNTAX     SEQUENCE OF    IpdcSessionStatsEntry
            MAX-ACCESS not-accessible
            STATUS     current
            DESCRIPTION
               "The IPDC Session Stats table maintains statistics on
               IPDC sessions."
            ::= { salixMgmcpIpdcObjects 2 }
         
         ipdcSessionStatsEntry OBJECT-TYPE
            SYNTAX     IpdcSessionStatsEntry
            MAX-ACCESS not-accessible
            STATUS     current
            DESCRIPTION
               "An entry in the ipdcSessionStatsTable"
            INDEX { ipdcSessionIndex }
            ::= { ipdcSessionStatsTable 1 }
         
         IpdcSessionStatsEntry ::= SEQUENCE {
            ipdcSessionStatsPacketsRcvd             Counter32,
            ipdcSessionStatsPacketsSent             Counter32,
            ipdcSessionStatsBytesRcvd               Counter32,
            ipdcSessionStatsBytesSent               Counter32,
            ipdcSessionStatsMessagesRejected        Counter32,
            ipdcSessionStatsUnacknowledgedRequests  Counter32  
         }
         
         ipdcSessionStatsPacketsRcvd OBJECT-TYPE
            SYNTAX     Counter32
            MAX-ACCESS read-only
            STATUS     current
            DESCRIPTION
               "The number of IPDC packets received for this session"
            ::= { ipdcSessionStatsEntry 2 }
         
         ipdcSessionStatsPacketsSent OBJECT-TYPE
            SYNTAX     Counter32
            MAX-ACCESS read-only
            STATUS     current
            DESCRIPTION
               "The number of IPDC packets sent for this session"
            ::= { ipdcSessionStatsEntry 3 }
         
         ipdcSessionStatsBytesRcvd OBJECT-TYPE
            SYNTAX     Counter32
            MAX-ACCESS read-only
            STATUS     current
            DESCRIPTION
               "The number of IPDC bytes received for this session"
            ::= { ipdcSessionStatsEntry 4 }
         
         ipdcSessionStatsBytesSent OBJECT-TYPE
            SYNTAX     Counter32
            MAX-ACCESS read-only
            STATUS     current
            DESCRIPTION
               "The number of IPDC bytes send for this session"
            ::= { ipdcSessionStatsEntry 5 }
         
         ipdcSessionStatsMessagesRejected OBJECT-TYPE
            SYNTAX     Counter32
            MAX-ACCESS read-only
            STATUS     current
            DESCRIPTION
               "The number of IPDC messages that were rejected on this
               session"
            ::= { ipdcSessionStatsEntry 6 }

         ipdcSessionStatsUnacknowledgedRequests OBJECT-TYPE
            SYNTAX     Counter32
            MAX-ACCESS read-only
            STATUS     current
            DESCRIPTION
               "The number of IPDC requests that were unacknowledged by
               the media controller"
            ::= { ipdcSessionStatsEntry 7 }
            
         ipdcSystemType OBJECT-TYPE
            SYNTAX     DisplayString (SIZE(1..9))
            MAX-ACCESS read-only
            STATUS     current
            DESCRIPTION
               "A character string used to identify the manufacturer 
                and model of the ITX"
         ::= { salixMgmcpIpdcObjects 3 }
         
         ipdcSystemID OBJECT-TYPE
            SYNTAX     DisplayString (SIZE(1..24))
            MAX-ACCESS read-only
            STATUS     current
            DESCRIPTION
               "A character string used to identify the ITX being
                controlled by IPDC."
         ::= { salixMgmcpIpdcObjects 4 }
         
         ipdcBayNumber OBJECT-TYPE
            SYNTAX     DisplayString (SIZE(1..8))
            MAX-ACCESS read-write
            STATUS     current
            DESCRIPTION
               "A character string used to identify the bay number where
                this ITX resides"
         ::= { salixMgmcpIpdcObjects 5 }

         -- Objects relating to the IPDC Heartbeat (RTE-ARTE messages)
         ipdcHeartbeatObjects OBJECT IDENTIFIER ::= { salixMgmcpIpdcObjects 6 }

           ipdcHeartbeatFrequency OBJECT-TYPE
              SYNTAX     Integer32
              MAX-ACCESS read-write
              STATUS     current
              DESCRIPTION
                 "The Frequency (in seconds) in which the Media
                  Gateway should initiate an RTE-ARTE transaction by
                  sending an RTE to the Media Controller.  This object
                  controls the Frequency for both the Primary and Secondary
                  Media Controller connections"
              ::= { ipdcHeartbeatObjects 1}
  
           ipdcHeartbeatPrimaryEnable OBJECT-TYPE
              SYNTAX      INTEGER { disabled(0),
                                    enabled(1) }
              MAX-ACCESS read-write
              STATUS     current
              DESCRIPTION
                 "This value contols whether an Heartbeat (RTE-ARTE
                  transaction) is sent to the primary media controller.
                     enable  - send the heartbeat
                     disable - don't send the heartbeat"
              ::= { ipdcHeartbeatObjects 2}

           ipdcHeartbeatSecondaryEnable OBJECT-TYPE
              SYNTAX      INTEGER { disabled(0),
                                    enabled(1) }
              MAX-ACCESS read-write
              STATUS     current
              DESCRIPTION
                 "This value contols whether an Heartbeat (RTE-ARTE
                  transaction) is sent to the secondary media controller.
                     enable  - send the heartbeat
                     disable - don't send the heartbeat"
              ::= { ipdcHeartbeatObjects 3}

         -- Objects relating to the IPDC Logger Utility
         ipdcLoggerObjects OBJECT IDENTIFIER ::= { salixMgmcpIpdcObjects 7 }

           ipdcLoggerEnable OBJECT-TYPE
              SYNTAX      INTEGER { disabled(0),
                                    enabled(1) }
              MAX-ACCESS read-write
              STATUS     current
              DESCRIPTION
                 "This value controls whether the ipdc logger is enabled.
                     enable  - log IPDC requests and responses to ipdclog.txt
                     disable - don't log"
              ::= { ipdcLoggerObjects 1}
  
      -- SGCP Objects
        
      salixMgmcpSgcpObjects OBJECT IDENTIFIER ::= { salixMgmcpMIBObjects 2 }
      
      sgcpUdpPortNumber OBJECT-TYPE
         SYNTAX     INTEGER(0..65535)
         MAX-ACCESS read-write
         STATUS     current
         DESCRIPTION
            "The local UDP port for SGCP to use.  This port cannot be changed dynamically.
             Any new value written to this objects will take affect after the system is
             restarted.  When the system starts up again, the last value written to this
             object is used as the local UDP port for SGCP"
         DEFVAL     { 0 }
      ::= { salixMgmcpSgcpObjects 1 }  

-- Conformance Statements

ipdcGroups      OBJECT IDENTIFIER  ::= { salixMgmcpMIBCompliance 1 }
sgcpGroups      OBJECT IDENTIFIER  ::= { salixMgmcpMIBCompliance 2 }
ipdcCompliances OBJECT IDENTIFIER  ::= { salixMgmcpMIBCompliance 3 }            
sgcpCompliances OBJECT IDENTIFIER  ::= { salixMgmcpMIBCompliance 4 }
            
   ipdcGroup OBJECT-GROUP
      OBJECTS {
         ipdcSessionStatsPacketsRcvd,      
         ipdcSessionStatsPacketsSent,      
         ipdcSessionStatsBytesRcvd,        
         ipdcSessionStatsBytesSent,        
         ipdcSessionStatsMessagesRejected, 
         ipdcSessionLocalIpAddress,
         ipdcSessionLocalPort,
         ipdcSessionMediaControllerIpAddress,
         ipdcSessionMediaControllerPort        
      }
      STATUS         current
      DESCRIPTION    "IPDC Group"
      ::= { ipdcGroups 1}  
      
   sgcpGroup OBJECT-GROUP
      OBJECTS {
         sgcpUdpPortNumber
      }
      STATUS         current
      DESCRIPTION    "IPDC Group"
      ::= { sgcpGroups 2} 
      
-- Compliance Statements

ipdcCompliance MODULE-COMPLIANCE
     STATUS       current
     DESCRIPTION
                  "The basic implementation requirements for the SALIX-IPDC-MIB."
     MODULE       -- This module
     MANDATORY-GROUPS { ipdcGroup, sgcpGroup }
     ::= { ipdcCompliances 1 }             

END
