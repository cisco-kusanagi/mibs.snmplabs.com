-- SAP Filtering for IPX router.

CXFLT-IPXSAP-MIB DEFINITIONS ::= BEGIN
 
   IMPORTS
      OBJECT-TYPE                     
         FROM RFC-1212
      DisplayString        FROM RFC1213-MIB
      cxIpx               
         FROM CXProduct-SMI;

cxFltIpxSapTable OBJECT-TYPE
   SYNTAX  SEQUENCE OF CxFltIpxSapEntry
   ACCESS  not-accessible
   STATUS  mandatory
   DESCRIPTION 
"Provides the parameters used to filter various IPX SAP's (Service 
Advertising Protocol). SAP filtering allows certain SAP types and names 
(selected by the network administrator) to be excluded from the router's 
SAP database; filtered SAPs will not be advertised by the router.

Each row (entry) of the table corresponds to a particular SAP selected for 
filtering."
   ::= { cxIpx 3 }

   cxFltIpxSapEntry OBJECT-TYPE
      SYNTAX  CxFltIpxSapEntry
      ACCESS  not-accessible
      STATUS  mandatory
      DESCRIPTION
"Provides the parameters used to filter a particular type of IPX SAP 
(Service Advertising Protocol). SAP filtering allows a particular 
combination of SAP type and name (selected by the network administrator) 
to be excluded from the SAP database; filtered SAPs will not be advertised 
by the router."
      INDEX   { cxFltIpxSapIndex  }
      ::= { cxFltIpxSapTable 1 }

   CxFltIpxSapEntry ::=
      SEQUENCE {
         cxFltIpxSapIndex           INTEGER, 
         cxFltIpxSapType            INTEGER,
         cxFltIpxSapName            DisplayString (SIZE (0..48)),
         cxFltIpxSapStatus          INTEGER,
         cxFltIpxSapRowStatus       INTEGER
         }

      cxFltIpxSapIndex  OBJECT-TYPE
         SYNTAX  INTEGER (1..65535)
         ACCESS  read-only
         STATUS  mandatory
         DESCRIPTION 
"Identifies a number used to index the filtering information for 
particular SAP. Each number must be unique.

Range of Values: 1 to 32

Default Value: None."

         ::= { cxFltIpxSapEntry 1 }

      cxFltIpxSapType  OBJECT-TYPE
         SYNTAX  INTEGER (0..65535)
         ACCESS  read-write
         STATUS  mandatory
         DESCRIPTION 
"Determines the IPX SAP type that is included in the filter. The SAP type 
(i.e. 0004 for file server ) must be a valid SAP number as defined by 
Novell. 

Range of Values: 0 - 65535

Note: If 0 is selected, then all SAP types will be included in this filter.

Default Value: None

Configuration Changed: administrative"
         ::= { cxFltIpxSapEntry 2 }

      cxFltIpxSapName  OBJECT-TYPE
         SYNTAX  DisplayString (SIZE (0..48))
         ACCESS  read-write
         STATUS  mandatory
         DESCRIPTION
"Determines the IPX SAP name of the Novell server that advertises the SAP 
type(s) assigned in cxFltIpxSapType. The name must be a valid SAP name as 
defined by Novell. 

Range of Values: 0-48 ASCII characters

Note: If 0 is selected, then all SAP names will be included in this filter.

Default Value: None

Configuration Changed:  administrative" 
                 ::= { cxFltIpxSapEntry 3 }
      
      cxFltIpxSapStatus  OBJECT-TYPE
         SYNTAX  INTEGER {
            discard (1),
            nodiscard (2)
            }
         ACCESS  read-write
         STATUS  mandatory
         DESCRIPTION
"Determines whether the filter as defined in cxFltIpxSapType and 
cxFltIpxSapName will be discarded (filtered). If the value is set to 
discard, then the SAP will not be included in the router's database; hence 
the SAP will not be advertised by the router. If the value is set to 
nodiscard the SAP will be included in the local database.

Options:
discard (1)

nodiscard (2)

Default Value: discard (1)

Configuration Changed:  administrative " 
        DEFVAL { discard }
         ::= { cxFltIpxSapEntry 4 }

      cxFltIpxSapRowStatus  OBJECT-TYPE
         SYNTAX  INTEGER {
            invalid (1),
            valid   (2)
            }
         ACCESS  read-write
         STATUS  mandatory
         DESCRIPTION 
"Determines the status of the objects in a table row.

Options:
invalid (1): row is flagged, after next reset the values will be disabled 
and the row will be deleted from the table.

valid (2): values are enabled

Default Value: valid (2)

Configuration Changed:  administrative"
        DEFVAL { valid }
         ::= { cxFltIpxSapEntry 5 }

END
