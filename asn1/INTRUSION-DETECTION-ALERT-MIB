-- extracted from draft-glenn-id-notification-mib-04.txt
-- at Sat Nov 25 16:04:48 2000

      INTRUSION-DETECTION-ALERT-MIB DEFINITIONS ::= BEGIN

       IMPORTS
         MODULE-IDENTITY,  Counter32, Gauge32, OBJECT-TYPE,
         OBJECT-IDENTITY,  IpAddress, mib-2    FROM SNMPv2-SMI
         DateAndTime, TimeStamp
                    FROM SNMPv2-TC
         SnmpAdminString
                    FROM SNMP-FRAMEWORK-MIB
         MODULE-COMPLIANCE, OBJECT-GROUP
                    FROM SNMPv2-CONF
         URLString
                    FROM NETWORK-SERVICES-MIB;

       idMIB MODULE-IDENTITY
          LAST-UPDATED "200011200000Z"        --  20th November 2000
          ORGANIZATION "IETF Intrusion Detection Message Exchange Format
                        Working Group"
          CONTACT-INFO
         "                      Glenn Mansfield
                        Postal: Cyber Solutions Inc.
                                6-6-3, Minami Yoshinari
                                Aoba-ku, Sendai, Japan 989-3204.

                           Tel: +81-22-303-4012
                           Fax: +81-22-303-4015
                        E-mail: glenn@cysols.com

          Working Group E-mail: idwg-public@zurich.ibm.com
                  To subscribe: idwg-public-request@zurich.ibm.com"

          DESCRIPTION
                  " The MIB for Intrusion Detection Messages."

          REVISION "200007250000Z" -- 25th July 2000
          DESCRIPTION "First draft of the idMIB"

          REVISION "200011160000Z" -- 16th November 2000
          DESCRIPTION "Revised to reflect the structure of the
                       objects in the XML-DTD.
                       Syntactic nits removed."

          REVISION "200011200000Z" -- 20th November 2000
          DESCRIPTION "Syntactic nits removed."
               ::= { mib-2 xxx }     -- to be assigned by IANA

       idAlertObjects OBJECT-IDENTITY
           STATUS current
           DESCRIPTION
             " This is the base object for the objects used in the
               alert notifications."
           ::= {idMIB 1}


   --  idAlertTable: The Table of Alerts. Each row represents an Alert.
   --  AlertID is the key to the table
       idAlertTable OBJECT-TYPE
           SYNTAX  SEQUENCE OF IdAlertEntry
           MAX-ACCESS  not-accessible
           STATUS  current
           DESCRIPTION
             " Each row of this table contains information
               about an alert indexed by idAlertID."
           ::= { idAlertObjects 1 }

       idAlertEntry OBJECT-TYPE
           SYNTAX  IdAlertEntry
           MAX-ACCESS  not-accessible
           STATUS  current
           DESCRIPTION
             " Entry containing information pertaining to
               an alert."
           INDEX { idAlertID}
           ::= { idAlertTable 1 }

       IdAlertEntry ::= SEQUENCE {
          idAlertVersion
                    INTEGER,
          idAlertID
                    INTEGER,
          idAlertImpact
                    INTEGER
       }

       idAlertVersion OBJECT-TYPE
           SYNTAX SnmpAdminString
           MAX-ACCESS read-only
           STATUS current
           DESCRIPTION
             " The version of the class hierarchy used in defining the
               alert."
           ::= {idAlertEntry 1}

       idAlertID OBJECT-TYPE
           SYNTAX INTEGER (1..2147483647)
           MAX-ACCESS read-only
           STATUS current
           DESCRIPTION
             " The AlertID uniquely identifies each alert generated
               by an analyzer."
           ::= {idAlertEntry 2}

       -- will be enumerated to represent the allowed types
       idAlertImpact OBJECT-TYPE
           SYNTAX INTEGER
           MAX-ACCESS read-only
           STATUS current
           DESCRIPTION
             "An indication of the impact of the (potential) impact of
              the event on the system."
           ::= {idAlertEntry 3}

       idTimeTable OBJECT-TYPE
           SYNTAX  SEQUENCE OF IdTimeEntry
           MAX-ACCESS  not-accessible
           STATUS  current
           DESCRIPTION
             " Each row of this table contains information
               about the time of an alert indexed by idAlertID."
           ::= { idAlertObjects 2 }

       idTimeEntry OBJECT-TYPE
           SYNTAX  IdTimeEntry
           MAX-ACCESS  not-accessible
           STATUS  current
           DESCRIPTION
             " Entry containing information pertaining to the time
               an alert was generated."
           INDEX { idAlertID}
           ::= { idTimeTable 1 }

       IdTimeEntry ::= SEQUENCE {
          idTimeOffset
                        SnmpAdminString,
          idTimeNtpStamp
                        SnmpAdminString,
          idTimeDate
                        SnmpAdminString,
          idTimeTime
                        SnmpAdminString
       }
       idTimeOffset OBJECT-TYPE
           SYNTAX SnmpAdminString
           MAX-ACCESS read-only
           STATUS current
           DESCRIPTION
             " Specifies the offset from Coordinated Universal Time
               UTC, formerly referred to as Greenwich Mean Time
               that the <date> and <time> elements represent."
           ::= {idTimeEntry 1}

      idTimeNtpStamp OBJECT-TYPE
           SYNTAX SnmpAdminString
           MAX-ACCESS read-only
           STATUS current
           DESCRIPTION
             " The NTP timestamp."
           ::= {idTimeEntry 2}

      idTimeDate OBJECT-TYPE
           SYNTAX SnmpAdminString
           MAX-ACCESS read-only
           STATUS current
           DESCRIPTION
             " The Date. "
           ::= {idTimeEntry 3}

      idTimeTime OBJECT-TYPE
           SYNTAX SnmpAdminString
           MAX-ACCESS read-only
           STATUS current
           DESCRIPTION
             " The Time."
           ::= {idTimeEntry 4}

       idDTimeTable OBJECT-TYPE
           SYNTAX  SEQUENCE OF IdTimeEntry
           MAX-ACCESS  not-accessible
           STATUS  current
           DESCRIPTION
             " Each row of this table contains information
               about the detection time of the event that
               caused the alert."
           ::= {idAlertObjects 3 }

       idDTimeEntry OBJECT-TYPE
           SYNTAX  IdDTimeEntry
           MAX-ACCESS  not-accessible
           STATUS  current
           DESCRIPTION
             " Entry containing information pertaining to the time
               an event was detected."
           INDEX {idAlertID}
           ::= {idDTimeTable 1 }

       IdDTimeEntry ::= SEQUENCE {
          idDTimeOffset
                     SnmpAdminString,
          idDTimeNtpStamp
                     SnmpAdminString,
          idDTimeDate
                     SnmpAdminString,
          idDTimeTime
                     SnmpAdminString
       }

       idDTimeOffset OBJECT-TYPE
           SYNTAX SnmpAdminString
           MAX-ACCESS read-only
           STATUS current
           DESCRIPTION
             " Specifies the offset from Coordinated Universal Time
               UTC, that the idTimeDate and idTimeTime elements it
               represents."
           ::= {idDTimeEntry 1}

      idDTimeNtpStamp OBJECT-TYPE
           SYNTAX SnmpAdminString
           MAX-ACCESS read-only
           STATUS current
           DESCRIPTION
             " The NTP timestamp."
           ::= { idDTimeEntry 2 }

      idDTimeDate OBJECT-TYPE
           SYNTAX SnmpAdminString
           MAX-ACCESS read-only
           STATUS current
           DESCRIPTION
             " The Date. "
           ::= { idDTimeEntry 3 }

      idDTimeTime OBJECT-TYPE
           SYNTAX SnmpAdminString
           MAX-ACCESS read-only
           STATUS current
           DESCRIPTION
             " The Time."
           ::= { idDTimeEntry 4 }

       idAnTimeTable OBJECT-TYPE
           SYNTAX  SEQUENCE OF IdAnTimeEntry
           MAX-ACCESS  not-accessible
           STATUS  current
           DESCRIPTION
             " A row of this table contains information
               about the current time on the Analyzer.
               This table will have only one row."
           ::= { idAlertObjects 4 }

       idAnTimeEntry OBJECT-TYPE
           SYNTAX  IdAnTimeEntry
           MAX-ACCESS  not-accessible
           STATUS  current
           DESCRIPTION
             " Entry containing information pertaining to the time
               an alert was generated."
           INDEX { idAlertID}
           ::= { idAnTimeTable 1 }

       IdAnTimeEntry ::= SEQUENCE {
          idAnTimeOffset
            SnmpAdminString,
          idAnTimeNtpStamp
            SnmpAdminString,
          idAnTimeDate
            SnmpAdminString,
          idAnTimeTime
            SnmpAdminString
       }

       idAnTimeOffset OBJECT-TYPE
           SYNTAX SnmpAdminString
           MAX-ACCESS read-only
           STATUS current
           DESCRIPTION
             " Specifies the offset from Coordinated Universal Time
               UTC, formerly referred to as Greenwich Mean Time,
               that the idAnTimeDate and idAnTimeTime elements represent."
           ::= {idAnTimeEntry 1}

      idAnTimeNtpStamp OBJECT-TYPE
           SYNTAX SnmpAdminString
           MAX-ACCESS read-only
           STATUS current
           DESCRIPTION
             " The NTP timestamp."
           ::= {idAnTimeEntry 2}

      idAnTimeDate OBJECT-TYPE
           SYNTAX SnmpAdminString
           MAX-ACCESS read-only
           STATUS current
           DESCRIPTION
             " The Date. "
           ::= {idAnTimeEntry 3}

      idAnTimeTime OBJECT-TYPE
           SYNTAX SnmpAdminString
           MAX-ACCESS read-only
           STATUS current
           DESCRIPTION
             " The Time."
          ::= {idAnTimeEntry 4}

       idClassificationTable OBJECT-TYPE
           SYNTAX  SEQUENCE OF IdClassificationEntry
           MAX-ACCESS  not-accessible
           STATUS  current
           DESCRIPTION
             " Each row of this table contains information
               about the classification of an alert and is
               indexed by idAlertID and the idClassification Index."
           ::= { idAlertObjects 5 }

       idClassificationEntry OBJECT-TYPE
           SYNTAX  IdClassificationEntry
           MAX-ACCESS  not-accessible
           STATUS  current
           DESCRIPTION
             " Entry containing information pertaining to the
               classification of the alert."
           INDEX { idAlertID, idClassificationIndex}
           ::= { idClassificationTable 1 }

       IdClassificationEntry ::= SEQUENCE {
           idClassificationIndex
                         INTEGER,
           idClassificationOrigin
                         SnmpAdminString,
           idClassificationName
                         SnmpAdminString,
           idClassificationUrl
                         SnmpAdminString
       }

       idClassificationIndex OBJECT-TYPE
           SYNTAX INTEGER (1..2147483647)
           MAX-ACCESS read-only
           STATUS current
           DESCRIPTION
             "An index that uniquely identifies the row in the table."
           ::= {idClassificationEntry 1}

      idClassificationOrigin OBJECT-TYPE
           SYNTAX SnmpAdminString
           MAX-ACCESS read-only
           STATUS current
           DESCRIPTION
             " The NTP timestamp."
           ::= {idClassificationEntry 2}

      idClassificationName OBJECT-TYPE
           SYNTAX SnmpAdminString
           MAX-ACCESS read-only
           STATUS current
           DESCRIPTION
             " The Date. "
           ::= {idClassificationEntry 3}

      idClassificationUrl OBJECT-TYPE
           SYNTAX SnmpAdminString
           MAX-ACCESS read-only
           STATUS current
           DESCRIPTION
             " The Time."
          ::= {idClassificationEntry 4}

       idSourceTable OBJECT-TYPE
           SYNTAX  SEQUENCE OF IdSourceEntry
           MAX-ACCESS  not-accessible
           STATUS  current
           DESCRIPTION
             " Each row of this table contains information
               about the source of an attack for which the alert
               is being raised."
           ::= { idAlertObjects 6 }

       idSourceEntry OBJECT-TYPE
           SYNTAX  IdSourceEntry
           MAX-ACCESS  not-accessible
           STATUS  current
           DESCRIPTION
             " Entry pertaining to a source of the attack."
           INDEX { idAlertID, idSourceIndex}
           ::= { idSourceTable 1 }

       IdSourceEntry ::= SEQUENCE {
           idSourceIndex
                  INTEGER,
           idSourceSpoofed
                  INTEGER,
           idSourceID
                  SnmpAdminString
       }

       idSourceIndex OBJECT-TYPE
           SYNTAX INTEGER (1..2147483647)
           MAX-ACCESS read-only
           STATUS current
           DESCRIPTION
             " An index uniquely identifying the host entry in
               the table."
           ::= {idSourceEntry 1}

       idSourceSpoofed OBJECT-TYPE
           SYNTAX INTEGER {
                  unknown(0),            -- do not know if spoofed or not
                  spoofed(1),            -- this is not the true source
                  notSpoofed(2)          -- this is the true source
           }
           MAX-ACCESS read-only
           STATUS current
           DESCRIPTION
             " An indication of whether the analyzer believes
               this to be the true source of the event."
           ::= {idSourceEntry 2}

       idSourceID OBJECT-TYPE
           SYNTAX SnmpAdminString
           MAX-ACCESS read-only
           STATUS current
           DESCRIPTION
             " An Identifier for the source "
           ::= {idSourceEntry 3}

       idTargetTable OBJECT-TYPE
           SYNTAX  SEQUENCE OF IdTargetEntry
           MAX-ACCESS  not-accessible
           STATUS  current
           DESCRIPTION
             " Each row of this table contains information
               about the target of the attack for which the alert
               is being raised."
           ::= { idAlertObjects 7 }

       idTargetEntry OBJECT-TYPE
           SYNTAX  IdTargetEntry
           MAX-ACCESS  not-accessible
           STATUS  current
           DESCRIPTION
             " Entry containing information pertaining to the time
               an alert was generated."
           INDEX { idAlertID, idTargetIndex}
           ::= { idTargetTable 1 }

       IdTargetEntry ::= SEQUENCE {
           idTargetIndex
                   INTEGER,
           idTargetDecoy
                   INTEGER,
           idTargetID
                   SnmpAdminString
       }

       idTargetIndex OBJECT-TYPE
           SYNTAX INTEGER (1..2147483647)
           MAX-ACCESS read-only
           STATUS current
           DESCRIPTION
             " An index uniquely identifying the target entry in
               the table."
           ::= {idTargetEntry 1}

       idTargetDecoy OBJECT-TYPE
           SYNTAX INTEGER {
                  unknown(0),            -- no information available
                  decoy(1),              -- this is not the true target
                  notdecoy(2)            -- this is the true target
           }
           MAX-ACCESS read-only
           STATUS current
           DESCRIPTION
             " An indication of whether the analyzer believes
               this to be the true target of the event."
           ::= {idTargetEntry 2}

       idTargetID OBJECT-TYPE
           SYNTAX SnmpAdminString
           MAX-ACCESS read-only
           STATUS current
           DESCRIPTION
             " An Identifier for the target "
           ::= {idTargetEntry 3}


       idToolAlertTable OBJECT-TYPE
           SYNTAX  SEQUENCE OF IdToolAlertEntry
           MAX-ACCESS  not-accessible
           STATUS  current
           DESCRIPTION
             " Each row of this table contains information
               tool used in the attacks."
           ::= { idAlertObjects 8 }

       idToolAlertEntry OBJECT-TYPE
           SYNTAX  IdToolAlertEntry
           MAX-ACCESS  not-accessible
           STATUS  current
           DESCRIPTION
             " Entry containing information about the tool which was
               used in the attack."
           INDEX { idAlertID, idToolAlertIDIndex}
           ::= { idToolAlertTable 1 }

       IdToolAlertEntry ::= SEQUENCE {
           idToolAlertIDIndex
                      INTEGER,
           idToolAlertName
                      SnmpAdminString,
           idToolAlertCommand
                      SnmpAdminString,
           idToolAlertIDs
                      SnmpAdminString
       }


       idToolAlertIDIndex OBJECT-TYPE
           SYNTAX INTEGER (1..2147483647)
           MAX-ACCESS read-only
           STATUS current
           DESCRIPTION
             " An index uniquely identifying the entry in
               the table."
           ::= {idToolAlertEntry 1}

       idToolAlertName OBJECT-TYPE
           SYNTAX SnmpAdminString
           MAX-ACCESS read-only
           STATUS current
           DESCRIPTION
             " The name of the tool used in the attack."
           ::= {idToolAlertEntry 2}

       idToolAlertCommand OBJECT-TYPE
           SYNTAX SnmpAdminString
           MAX-ACCESS read-only
           STATUS current
           DESCRIPTION
             " The command or operation the tool was asked to
                perform."
           ::= {idToolAlertEntry 3}

       idToolAlertIDs OBJECT-TYPE
           SYNTAX SnmpAdminString
           MAX-ACCESS read-only
           STATUS current
           DESCRIPTION
             " The alerts that have been identified as being
               related to the tool name."
           ::= {idToolAlertEntry 4}

       idOverflowAlertTable OBJECT-TYPE
           SYNTAX  SEQUENCE OF IdOverflowAlertEntry
           MAX-ACCESS  not-accessible
           STATUS  current
           DESCRIPTION
             " Each row of this table contains information
               about the buffer-overflow types of attacks."
           ::= { idAlertObjects 9 }

       idOverflowAlertEntry OBJECT-TYPE
           SYNTAX  IdOverflowAlertEntry
           MAX-ACCESS  not-accessible
           STATUS  current
           DESCRIPTION
             " Entry containing buffer-overflow related information
               for the corresponding attack."
           INDEX { idAlertID }
           ::= { idOverflowAlertTable 1 }

       IdOverflowAlertEntry ::= SEQUENCE {
           idOverflowAlertProgram
                 SnmpAdminString,

           idOverflowAlertSize
                 INTEGER,
           idOverflowAlertBuffer
                  SnmpAdminString
       }

       idOverflowAlertProgram OBJECT-TYPE
           SYNTAX SnmpAdminString
           MAX-ACCESS read-only
           STATUS current
           DESCRIPTION
             " The program that the overflow attacker attempted to run."
           ::= {idOverflowAlertEntry 1}

       idOverflowAlertSize OBJECT-TYPE
           SYNTAX SnmpAdminString
           MAX-ACCESS read-only
           STATUS current
           DESCRIPTION
             " The size, in bytes, of the overflowing buffer."
           ::= {idOverflowAlertEntry 2}

       idOverflowAlertBuffer OBJECT-TYPE
           SYNTAX SnmpAdminString
           MAX-ACCESS read-only
           STATUS current
           DESCRIPTION
             "Some or all of the data that was sent to the program."
           ::= {idOverflowAlertEntry 3}

       idCorrelationAlertTable OBJECT-TYPE
           SYNTAX  SEQUENCE OF IdCorrelationAlertEntry
           MAX-ACCESS  not-accessible
           STATUS  current
           DESCRIPTION
             " Contains the list of alerts(indexed by
               idCorrelationIndex) which were correlated to
               generate the present alert (indexed by idAlertID)."
           ::= { idAlertObjects 10 }

       idCorrelationAlertEntry OBJECT-TYPE
           SYNTAX  IdCorrelationAlertEntry
           MAX-ACCESS  not-accessible
           STATUS  current
           DESCRIPTION
             " One of the alerts that was used in the correlation
               to generate the present alert indexed by idAlertID ."
           INDEX { idAlertID}
           ::= { idCorrelationAlertTable 1 }

       IdCorrelationAlertEntry ::= SEQUENCE {
           idCorrelationAlertIndex
                 INTEGER,
           idCorrelationAlertIDs
                 SnmpAdminString
       }

       idCorrelationAlertIndex OBJECT-TYPE
           SYNTAX INTEGER (1..2147483647)
           MAX-ACCESS read-only
           STATUS current
           DESCRIPTION
             " An index uniquely identifying the CorrelationAlert entry
               in the table."
           ::= {idCorrelationAlertEntry 1}

       idCorrelationAlertIDs OBJECT-TYPE
           SYNTAX SnmpAdminString
           MAX-ACCESS read-only
           STATUS current
           DESCRIPTION
             " List of alertIds that are correlated."
           ::= {idCorrelationAlertEntry 2}


       idAdditionalDataTable OBJECT-TYPE
           SYNTAX  SEQUENCE OF IdAdditionalDataEntry
           MAX-ACCESS  not-accessible
           STATUS  current
           DESCRIPTION
             " Each row of this table contains additional information
               related to the alert that is being raised."
           ::= { idAlertObjects 11 }

       idAdditionalDataEntry OBJECT-TYPE
           SYNTAX  IdAdditionalDataEntry
           MAX-ACCESS  not-accessible
           STATUS  current
           DESCRIPTION
             " Additional information corresponding to the alert that
               has been raised."
           INDEX { idAlertID, idAdditionalDataIndex }
           ::= { idAdditionalDataTable 1 }

       IdAdditionalDataEntry ::= SEQUENCE {
           idAdditionalDataIndex
               INTEGER,
           idAdditionalDataType
               INTEGER,
           idAdditionalDataMeaning
               SnmpAdminString
       }
       idAdditionalDataIndex OBJECT-TYPE
           SYNTAX INTEGER (1..2147483647)
           MAX-ACCESS read-only
           STATUS current
           DESCRIPTION
             " An index that along with the Alert-ID uniquely
               identifies the row in the table."
           ::= {idAdditionalDataEntry 1}

      idAdditionalDataType OBJECT-TYPE
           SYNTAX SnmpAdminString
           MAX-ACCESS read-only
           STATUS current
           DESCRIPTION
             "The type of the data in this element. "
           ::= {idAdditionalDataEntry 2}

      idAdditionalDataMeaning OBJECT-TYPE
           SYNTAX SnmpAdminString
           MAX-ACCESS read-only
           STATUS current
           DESCRIPTION
             " A string that describes the meaning of the data in
               this element.  These strings will be implementation
               dependent."
           ::= {idAdditionalDataEntry 3}

       idArgumentsTable OBJECT-TYPE
           SYNTAX  SEQUENCE OF IdArgumentsEntry
           MAX-ACCESS  not-accessible
           STATUS  current
           DESCRIPTION
             " Each row of this table contains information
               about the arguments used in the process indexed
               by idTargetIndex."
           ::= { idAlertObjects 12 }

       idArgumentsEntry OBJECT-TYPE
           SYNTAX  IdArgumentsEntry
           MAX-ACCESS  not-accessible
           STATUS  current
           DESCRIPTION
             " A row containing one element of the argument
               information."
           INDEX { idAlertID, idArgumentsSDType, idArgumentsProcIndex }
           ::= { idArgumentsTable 1 }

       IdArgumentsEntry ::= SEQUENCE {
           idArgumentsSDType      -- Source/Destination
                  INTEGER,
           idArgumentsProcIndex
                  INTEGER,
           idArguments
                  SnmpAdminString
       }

      idArgumentsSDType OBJECT-TYPE
           SYNTAX INTEGER {
                  source(1),        -- process is on Node of type source
                  destination(2),   -- process is on Node of type destination
                  analyzer(3)       -- process is on Node of type analyzer
           }
           MAX-ACCESS read-only
           STATUS current
           DESCRIPTION
             " An enumeration of the type of the node on which
               the referenced process is running ."
           ::= {idArgumentsEntry 1}

      idArgumentsProcIndex OBJECT-TYPE
           SYNTAX SnmpAdminString
           MAX-ACCESS read-only
           STATUS current
           DESCRIPTION
             " An index to identify the process."
           ::= {idArgumentsEntry 2}

      idArguments OBJECT-TYPE
           SYNTAX SnmpAdminString
           MAX-ACCESS read-only
           STATUS current
           DESCRIPTION
             " The list of the arguments. "
           ::= {idArgumentsEntry 3}

       idUserTable OBJECT-TYPE
           SYNTAX  SEQUENCE OF IdUserEntry
           MAX-ACCESS  not-accessible
           STATUS  current
           DESCRIPTION
             "The table containing information about
              users. ."
           ::= { idAlertObjects 13 }

       idUserEntry OBJECT-TYPE
           SYNTAX  IdUserEntry
           MAX-ACCESS  not-accessible
           STATUS  current
           DESCRIPTION
             "A row containing the details of a user"
           INDEX { idAlertID, idUserSDType, idUserIndex}
           ::= { idUserTable 1 }

       IdUserEntry ::= SEQUENCE {
           idUserSDType
             INTEGER,
           idUserIndex
             INTEGER,
           idUserIdent
             SnmpAdminString,
           idUserName
             SnmpAdminString,
           idUserUid
             SnmpAdminString,
           idUserGroup
             SnmpAdminString,
           idUserGid
             SnmpAdminString,
           idUserSerial
             SnmpAdminString
       }


       idUserSDType OBJECT-TYPE
           SYNTAX INTEGER {
                  source(1),        -- user is on Node of type source
                  destination(2),   -- user is on Node of type destination
                  analyzer(3)       -- user is on Node of type analyzer
           }
           MAX-ACCESS read-only
           STATUS current
           DESCRIPTION
             " An enumeration of the type of the node on which
               the referenced user exists ."
           ::= { idUserEntry 1 }

       idUserIndex OBJECT-TYPE
           SYNTAX INTEGER (1..2147483647)
           MAX-ACCESS read-only
           STATUS current
           DESCRIPTION
             " An index uniquely identifying the user entry
               in the table."
           ::= { idUserEntry 2 }


       idUserIdent OBJECT-TYPE
           SYNTAX SnmpAdminString
           MAX-ACCESS read-only
           STATUS current
           DESCRIPTION
             " The ID of the user."
           ::= { idUserEntry 3 }

       idUserName OBJECT-TYPE
           SYNTAX SnmpAdminString
           MAX-ACCESS read-only
           STATUS current
           DESCRIPTION
             " The name of the user."
           ::= { idUserEntry 4 }

      idUserUid OBJECT-TYPE
           SYNTAX SnmpAdminString
           MAX-ACCESS read-only
           STATUS current
           DESCRIPTION
             " The UID of the user."
           ::= { idUserEntry 5 }

      idUserGroup OBJECT-TYPE
           SYNTAX SnmpAdminString
           MAX-ACCESS read-only
           STATUS current
           DESCRIPTION
             " The group of the user."
           ::= { idUserEntry 6 }

      idUserGid OBJECT-TYPE
           SYNTAX SnmpAdminString
           MAX-ACCESS read-only
           STATUS current
           DESCRIPTION
             " The gid of the user."
           ::= { idUserEntry 7 }

      idUserSerial OBJECT-TYPE
           SYNTAX SnmpAdminString
           MAX-ACCESS read-only
           STATUS current
           DESCRIPTION
             " The serial number of the user."
           ::= { idUserEntry 8 }

      idProcessTable OBJECT-TYPE
           SYNTAX  SEQUENCE OF IdProcessEntry
           MAX-ACCESS  not-accessible
           STATUS  current
           DESCRIPTION
             " A Table containing details of processes. "
           ::= { idAlertObjects 14 }

      idProcessEntry OBJECT-TYPE
           SYNTAX  IdProcessEntry
           MAX-ACCESS  not-accessible
           STATUS  current
           DESCRIPTION
             "Each row contains details of a process indexed by
              idProcessIndex on a node indexed by idNodeIndex of type
              given by idProcessSDType related  to the alert indexed
              by idAlertID."
           INDEX { idAlertID, idProcessSDType, idNodeIndex, idProcessIndex}
           ::= { idProcessTable 1 }

       IdProcessEntry ::= SEQUENCE {
           idProcessSDType
              INTEGER,
           idProcessIndex
              INTEGER,
           idProcessID
              SnmpAdminString,
           idProcessName
              SnmpAdminString,
           idProcessPid
              SnmpAdminString,
           idProcessPath
              SnmpAdminString
       }

       idProcessSDType OBJECT-TYPE
           SYNTAX INTEGER {
                  source(1),             -- The process is running on a source
                  destination(2),        -- The process is running on a destination
                  analyzer(3)            -- The process is running on an analyzer

           }
           MAX-ACCESS read-only
           STATUS current
           DESCRIPTION
             " An enumeration of the type of the node on which
               the referenced process is running ."
           ::= { idProcessEntry 1 }

       idProcessIndex OBJECT-TYPE
           SYNTAX INTEGER (1..2147483647)
           MAX-ACCESS read-only
           STATUS current
           DESCRIPTION
             " An index uniquely identifying the process entry
               in the table."
           ::= { idProcessEntry 2 }


       idProcessID OBJECT-TYPE
           SYNTAX SnmpAdminString
           MAX-ACCESS read-only
           STATUS current
           DESCRIPTION
             " The ID of the process."
           ::= { idProcessEntry 3 }

       idProcessName OBJECT-TYPE
           SYNTAX SnmpAdminString
           MAX-ACCESS read-only
           STATUS current
           DESCRIPTION
             " The name of the process."
           ::= { idProcessEntry 4 }

      idProcessPid OBJECT-TYPE
           SYNTAX SnmpAdminString
           MAX-ACCESS read-only
           STATUS current
           DESCRIPTION
             " The PID of the process."
           ::= { idProcessEntry 5 }

      idProcessPath OBJECT-TYPE
           SYNTAX SnmpAdminString
           MAX-ACCESS read-only
           STATUS current
           DESCRIPTION
             " The absolute path of the process."
           ::= { idProcessEntry 6 }

       idAddressTable OBJECT-TYPE
           SYNTAX  SEQUENCE OF IdAddressEntry
           MAX-ACCESS  not-accessible
           STATUS  current
           DESCRIPTION
             "A Table containing address entries. "
           ::= { idAlertObjects 15 }

       idAddressEntry OBJECT-TYPE
           SYNTAX  IdAddressEntry
           MAX-ACCESS  not-accessible
           STATUS  current
           DESCRIPTION
             " A row containing the address details. "
           INDEX { idAddressType, idAddressTypeIndex, idAddressIndex }
           ::= { idAddressTable 1 }

       IdAddressEntry ::= SEQUENCE {
           idAddressType      -- source, target, user
              INTEGER,
           idAddressTypeIndex -- idSourceIndex, idTargetIndex idUserIndex
              INTEGER,
           idAddressIndex
              INTEGER,
           idAddressID
              SnmpAdminString,
           idAddressCategory
              SnmpAdminString,
           idAddressAddress
              SnmpAdminString,
           idAddressNetmask
              IpAddress
       }

       idAddressType OBJECT-TYPE
           SYNTAX INTEGER {
                  source(1),             -- Source type
                  destination(2),        -- Destination type
                  analyzer(3),           -- Analyzer
                  user    (4)            -- User
           }
           MAX-ACCESS read-only
           STATUS current
           DESCRIPTION
             " An enumeration of the node type - this may
               be a source node a destination node or just
               an analyzer."
           ::= {idAddressEntry 1}

       idAddressTypeIndex OBJECT-TYPE
           SYNTAX INTEGER {
                  source(1),             -- Source type
                  destination(2),        -- Destination type
                  analyzer(3),           -- Analyzer
                  user    (4)            -- User
           }
           MAX-ACCESS read-only
           STATUS current
           DESCRIPTION
             " An enumeration of the node type - this may
               be a source node a destination node or just
               an analyzer."
           ::= {idAddressEntry 2}

       idAddressIndex OBJECT-TYPE
           SYNTAX INTEGER (1..2147483647)
           MAX-ACCESS read-only
           STATUS current
           DESCRIPTION
             " An index uniquely identifying the node entry
               in the table."
           ::= {idAddressEntry 3}

       idAddressID OBJECT-TYPE
           SYNTAX SnmpAdminString
           MAX-ACCESS read-only
           STATUS current
           DESCRIPTION
             " An Identifier for the node "
           ::= {idAddressEntry 4}

      idAddressCategory OBJECT-TYPE
           SYNTAX SnmpAdminString
           MAX-ACCESS read-only
           STATUS current
           DESCRIPTION
             " A category for the node "
           ::= {idAddressEntry 5}

      idAddressAddress OBJECT-TYPE
           SYNTAX SnmpAdminString
           MAX-ACCESS read-only
           STATUS current
           DESCRIPTION
             " The address."
           ::= {idAddressEntry 6}

      idAddressNetmask OBJECT-TYPE
           SYNTAX IpAddress
           MAX-ACCESS read-only
           STATUS current
           DESCRIPTION
             " The mask of the address."
           ::= {idAddressEntry 7}

       idNodeTable OBJECT-TYPE
           SYNTAX  SEQUENCE OF IdNodeEntry
           MAX-ACCESS  not-accessible
           STATUS  current
           DESCRIPTION
             "A table containing details of nodes related to
              alerts. "
           ::= { idAlertObjects 16 }

       idNodeEntry OBJECT-TYPE
           SYNTAX  IdNodeEntry
           MAX-ACCESS  not-accessible
           STATUS  current
           DESCRIPTION
             "A row pertaining to one node "
           INDEX { idAlertID, idNodeIndexType, idNodeIndex }
           ::= { idNodeTable 1 }

       IdNodeEntry ::= SEQUENCE {
           idNodeIndexType
              INTEGER,
           idNodeIndex
              INTEGER,
           idNodeID
              SnmpAdminString,
           idNodeCategory
              SnmpAdminString,
           idNodeName
              SnmpAdminString,
           idNodeLocation
              SnmpAdminString
       }

       idNodeIndexType OBJECT-TYPE
           SYNTAX INTEGER {
                  source(1),             -- no information available
                  destination(2),        -- this is not the true target
                  analyzer(3)            -- this is the true target
           }
           MAX-ACCESS read-only
           STATUS current
           DESCRIPTION
             " An enumeration of the node type - this may
               be a source node a destination node or just
               an analyzer."
           ::= {idNodeEntry 1}

       idNodeIndex OBJECT-TYPE
           SYNTAX INTEGER (1..2147483647)
           MAX-ACCESS read-only
           STATUS current
           DESCRIPTION
             " An index uniquely identifying the node entry
               in the table."
           ::= {idNodeEntry 2}

       idNodeID OBJECT-TYPE
           SYNTAX SnmpAdminString
           MAX-ACCESS read-only
           STATUS current
           DESCRIPTION
             " An Identifier for the node "
           ::= {idNodeEntry 3}

      idNodeCategory OBJECT-TYPE
           SYNTAX SnmpAdminString
           MAX-ACCESS read-only
           STATUS current
           DESCRIPTION
             " An category for the node "
           ::= {idNodeEntry 4}

      idNodeName OBJECT-TYPE
           SYNTAX SnmpAdminString
           MAX-ACCESS read-only
           STATUS current
           DESCRIPTION
             " An name for the node "
           ::= {idNodeEntry 5}

      idNodeLocation OBJECT-TYPE
           SYNTAX SnmpAdminString
           MAX-ACCESS read-only
           STATUS current
           DESCRIPTION
             " The location of the node "
           ::= {idNodeEntry 6}

       idAnalyzerTable OBJECT-TYPE
           SYNTAX  SEQUENCE OF IdAnalyzerEntry
           MAX-ACCESS  not-accessible
           STATUS  current
           DESCRIPTION
             " A table containing the list of analyzers serviced
               by this MIB."
           ::= { idAlertObjects 17 }

       idAnalyzerEntry OBJECT-TYPE
           SYNTAX  IdAnalyzerEntry
           MAX-ACCESS  not-accessible
           STATUS  current
           DESCRIPTION
             " A row containing details of an Analyzer"
           INDEX { idAnalyzerIndex }
           ::= { idAnalyzerTable 1 }

       IdAnalyzerEntry ::= SEQUENCE {
           idAnalyzerIndex
               INTEGER,
           idAnalyzerID
               SnmpAdminString,
           idAnalyzerNodeIndex
               INTEGER,
           idAnalyzerProcessIndex
               INTEGER
       }

      idAnalyzerIndex OBJECT-TYPE
           SYNTAX INTEGER (1..2147483647)
           MAX-ACCESS read-only
           STATUS current
           DESCRIPTION
             " An Index to uniquely identify the Analyzer in
               this table."
           ::= {idAnalyzerEntry 1}

     idAnalyzerID OBJECT-TYPE
           SYNTAX SnmpAdminString
           MAX-ACCESS read-only
           STATUS current
           DESCRIPTION
             " An identifier to uniquely identify the Analyzer
               in the domain."
           ::= {idAnalyzerEntry 2}

      idAnalyzerNodeIndex OBJECT-TYPE
           SYNTAX INTEGER (1..2147483647)
           MAX-ACCESS read-only
           STATUS current
           DESCRIPTION
             " An Index pointing to the corresponding Node
               in the Node Table."
           ::= {idAnalyzerEntry 3}

      idAnalyzerProcessIndex OBJECT-TYPE
           SYNTAX INTEGER (1..2147483647)
           MAX-ACCESS read-only
           STATUS current
           DESCRIPTION
             " An Index pointing to the corresponding process
               in the process table."
           ::= {idAnalyzerEntry 4}

      idEnvironmentTable OBJECT-TYPE
           SYNTAX  SEQUENCE OF IdEnvironmentEntry
           MAX-ACCESS  not-accessible
           STATUS  current
           DESCRIPTION
             " Each row of this table contains information
               about the environment variables used in the process
               indexed by idTargetIndex."
           ::= { idAlertObjects 18 }

      idEnvironmentEntry OBJECT-TYPE
           SYNTAX  IdEnvironmentEntry
           MAX-ACCESS  not-accessible
           STATUS  current
           DESCRIPTION
             "
               ."
           INDEX { idAlertID, idProcessIndex, idEnvironmentIndex}
           ::= { idEnvironmentTable 1 }

       IdEnvironmentEntry ::= SEQUENCE {
           idEnvironmentIndex
               INTEGER,
           idEnvironment
               SnmpAdminString
       }

       idEnvironmentIndex OBJECT-TYPE
           SYNTAX INTEGER (1..2147483647)
           MAX-ACCESS read-only
           STATUS current
           DESCRIPTION
             " An index uniquely identifying the process entry
               in the table."
           ::= { idEnvironmentEntry 2 }


       idEnvironment OBJECT-TYPE
           SYNTAX SnmpAdminString
           MAX-ACCESS read-only
           STATUS current
           DESCRIPTION
             " The ID of the process."
           ::= { idEnvironmentEntry 3 }

      idServiceTable OBJECT-TYPE
           SYNTAX  SEQUENCE OF IdServiceEntry
           MAX-ACCESS  not-accessible
           STATUS  current
           DESCRIPTION
             " Each row of this table contains information
               about the services that have been targeted.."
           ::= { idAlertObjects 19 }

      idServiceEntry OBJECT-TYPE
           SYNTAX  IdServiceEntry
           MAX-ACCESS  not-accessible
           STATUS  current
           DESCRIPTION
             "
               ."
           INDEX { idAlertID, idTargetIndex, idServiceIndex}
           ::= { idServiceTable 1 }

       IdServiceEntry ::= SEQUENCE {
           idServiceIndex
             INTEGER,
           idServiceID
             SnmpAdminString,
           idServiceName
             SnmpAdminString,
           idServiceDport
             SnmpAdminString,
           idServiceSport
             SnmpAdminString,
           idServiceProtocol
             SnmpAdminString,
           idServicePortList
             SnmpAdminString
       }

       idServiceIndex OBJECT-TYPE
           SYNTAX INTEGER (1..2147483647)
           MAX-ACCESS read-only
           STATUS current
           DESCRIPTION
             " An index uniquely identifying the process entry
               in the table."
           ::= { idServiceEntry 1 }


       idServiceID OBJECT-TYPE
           SYNTAX SnmpAdminString
           MAX-ACCESS read-only
           STATUS current
           DESCRIPTION
             " The ID of the service."
           ::= { idServiceEntry 2 }

       idServiceName OBJECT-TYPE
           SYNTAX SnmpAdminString
           MAX-ACCESS read-only
           STATUS current
           DESCRIPTION
             " The name of the service."
           ::= { idServiceEntry 3 }

      idServiceDport OBJECT-TYPE
           SYNTAX SnmpAdminString
           MAX-ACCESS read-only
           STATUS current
           DESCRIPTION
             " The list of destination ports."
           ::= { idServiceEntry 4 }

      idServiceSport OBJECT-TYPE
           SYNTAX SnmpAdminString
           MAX-ACCESS read-only
           STATUS current
           DESCRIPTION
             " The list of source ports."
           ::= { idServiceEntry 5 }

      idServiceProtocol OBJECT-TYPE
           SYNTAX SnmpAdminString
           MAX-ACCESS read-only
           STATUS current
           DESCRIPTION
             " The protocol used by the service."
           ::= { idServiceEntry 6 }

      idServicePortList OBJECT-TYPE
           SYNTAX SnmpAdminString
           MAX-ACCESS read-only
           STATUS current
           DESCRIPTION
             " The list of service related ports."
           ::= { idServiceEntry 7 }

       -- Conformance information

       --      [TBD]

      END

-- 
--          "Copyright (C) The Internet Society (date). All Rights
--          Reserved.
-- 
--          This document and translations of it may be copied and
--          furnished to others, and derivative works that comment on or
--          otherwise explain it or assist in its implmentation may be
--          prepared, copied, published and distributed, in whole or in
--          part, without restriction of any kind, provided that the above
--          copyright notice and this paragraph are included on all such
--          copies and derivative works.  However, this document itself may
--          not be modified in any way, such as by removing the copyright
--          notice or references to the Internet Society or other Internet
--          organizations, except as needed for the  purpose of developing
--          Internet standards in which case the procedures for copyrights
--          defined in the Internet Standards process must be followed, or
--          as required to translate it into languages other than English.
-- 
--          The limited permissions granted above are perpetual and will
--          not be revoked by the Internet Society or its successors or
--          assigns.
-- 
--          This document and the information contained herein is provided
--          on an "AS IS" basis and THE INTERNET SOCIETY AND THE INTERNET
--          ENGINEERING TASK FORCE DISCLAIMS ALL WARRANTIES, EXPRESS OR
--          IMPLIED, INCLUDING BUT NOT LIMITED TO ANY WARRANTY THAT THE USE
--          OF THE INFORMATION HEREIN WILL NOT INFRINGE ANY RIGHTS OR ANY
--          IMPLIED WARRANTIES OF MERCHANTABILITY OR FITNESS FOR A
--          PARTICULAR PURPOSE."
