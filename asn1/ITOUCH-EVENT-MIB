-- $Id: it-event-mib.mib,v 1.1 2000/07/25 14:41:23 sse Exp $
           ITOUCH-EVENT-MIB DEFINITIONS ::= BEGIN

                    IMPORTS
                            DisplayString
                                    FROM RFC1213-MIB
                            OBJECT-TYPE
                                    FROM RFC-1212
                            DateTime, iTouch 
                                    FROM ITOUCH-MIB;

            xEvent             OBJECT IDENTIFIER ::= { iTouch 33 }

            --  This is the MIB module for iTouch Event logging.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.

            -- Textual Conventions

            EventGroup ::=
                INTEGER { appleTalk(1), appleTalkArps(2), appleTalkRtmp(3),
                          appleTalkZip(4), appleTalkNbp(5),
                          appleTalkTraffic(6), atm(7), backup(8), pcmcia(9),
                          chassis(10), circuit(11), clns(12), decNet(13),
                          decNetTraffic(14), egp(15), esis(16), fddi(17),
                          fddiTraffic(18), frame(19), frameRelay(20),
                          hubManagement(21), interface(22), ip(23), ipRip(24),
                          ipRoutes(25), ipTraffic(26), ipx(27), ipxRip(28),
                          ipxSap(29), isdn(30), isdnQ931(31), isdnTrace(32),
                          isis(33), isisHello(34), isisLsp(35), link(36),
                          lmb(37), lqm(38), ospf(39), ospfHello(40),
                          ospfLsaPacket(41), ospfSpf(42), param(43), ppp(44),
                          session(45), spanningTree(46), snmp(47),
                          switchForwarding(48), switchLoopDetect(49),
                          switchManagement(50), system(51), tcp(52), time(53),
                          tokenRingManagement(54), udp(55), ui(56), vlmp(57),
                          x25(58) }


            -- the Event Information group

            -- Implementation of this group is mandatory for all iTouch
            -- Devices that support SNMP management

            eventTableSize OBJECT-TYPE
                SYNTAX INTEGER (20..800)
                ACCESS read-write
                STATUS mandatory
                DESCRIPTION
                    "Controls the size of the event table in number of
                     entries.  Event storage begins with entry number one
                     and continues to the upper bound.  When the table
                     becomes full, event storeage begins again with entry
                     number one, overwriting the previously stored entry.
                     A newly defined table size will not take effect until
                     the unit is reinitialized."
                DEFVAL { 100 }
                ::= { xEvent 1 }

            eventSeverity OBJECT-TYPE
                SYNTAX INTEGER { discard(1), low(2), medium(3), high(4) }
                ACCESS read-write
                STATUS mandatory
                DESCRIPTION
                    "The severity of the event to be logged.  All events
                     fall into one of the above severity levels.  Events
                     are added to the event table if and only if the
                     current value of this object is less than or equal to
                     the severity of the event.  If this object is set to
                     discard, no events are logged to the table."
                DEFVAL { low }
                ::= { xEvent 2 }

            eventTimestamp OBJECT-TYPE
                SYNTAX INTEGER { none(1), date(2), time(3), datetime(4) }
                ACCESS read-write
                STATUS mandatory
                DESCRIPTION
                    "This object controls the timestamp embedded into the
                     actual text of the event for event table text object
                     eventTextText.  If this object is set to none, no
                     timestamp will be embedded in the text.  This object
                     has no effect on the event table text object
                     eventTextDateTime."
                DEFVAL { datetime }
                ::= { xEvent 3 }

            eventLanguage OBJECT-TYPE
                SYNTAX INTEGER { english(1) }
                ACCESS read-only
                STATUS mandatory
                DESCRIPTION
                    "This object indicates the language of the event text
                     in the table."
                ::= { xEvent 4 }

            eventClearLog OBJECT-TYPE
                SYNTAX INTEGER { ready(1), execute(2) }
                ACCESS read-write
                STATUS mandatory
                DESCRIPTION
                    "When this object is set to execute, all events are
                     cleared from the event table.  Setting this object
                     to ready has no effect."
                ::= { xEvent 5 }

            eventEnableAll OBJECT-TYPE
                SYNTAX INTEGER { ready(1), execute(2) }
                ACCESS read-write
                STATUS mandatory
                DESCRIPTION
                    "When this object is set to execute, all events groups
                     are enabled.  Setting this object to ready has no effect."
                ::= { xEvent 6 }

            eventDisableAll OBJECT-TYPE
                SYNTAX INTEGER { ready(1), execute(2) }
                ACCESS read-write
                STATUS mandatory
                DESCRIPTION
                    "When this object is set to execute, all events groups
                     are disabled.  Setting this object to ready has no effect."
                ::= { xEvent 7 }


            -- the event group table

            -- Implementation of this group is mandatory for all iTouch
            -- devices that support SNMP management

            -- An event group is a collection of events which are related
            -- to a specific feature (eg. IP, RIP, HUB management, etc.).
            -- This table defines whether events from a specific group may
            -- be stored to the event table.


            eventGroupTable OBJECT-TYPE
                SYNTAX SEQUENCE OF EventGroupEntry
                ACCESS not-accessible
                STATUS mandatory
                DESCRIPTION
                    "Table of descriptive and status information about 
                    event groups."
                ::= { xEvent 8 }

            eventGroupEntry OBJECT-TYPE
                SYNTAX EventGroupEntry
                ACCESS not-accessible
                STATUS mandatory
                DESCRIPTION
                    "An entry in the table, containing information about 
                    an event group."
                INDEX { eventGroupIndex }
                ::= { eventGroupTable 1 }

            EventGroupEntry ::=
                SEQUENCE {
                    eventGroupIndex
                        EventGroup,
                    eventGroupState
                        INTEGER
                }

            eventGroupIndex OBJECT-TYPE
                SYNTAX EventGroup
                ACCESS read-only
                STATUS mandatory
                DESCRIPTION
                    "This variable identifies the event group."
                ::= { eventGroupEntry 1 }

            eventGroupState OBJECT-TYPE
                SYNTAX INTEGER { disabled(1), enabled(2) }
                ACCESS read-write
                STATUS mandatory
                DESCRIPTION
                    "This variable controls whether events from a
                     particular event group may be logged to the event
                     table."
                DEFVAL { disabled }
                ::= { eventGroupEntry 2 }


            -- the event text table

            -- Implementation of this group is mandatory for all iTouch
            -- devices that support SNMP management

            -- This table contains the actual text of the event.

            eventTextTable OBJECT-TYPE
                SYNTAX SEQUENCE OF EventTextEntry
                ACCESS not-accessible
                STATUS mandatory
                DESCRIPTION
                    "Table of descriptive and status information about 
                    an event."
                ::= { xEvent 9 }

            eventTextEntry OBJECT-TYPE
                SYNTAX EventTextEntry
                ACCESS not-accessible
                STATUS mandatory
                DESCRIPTION
                    "An entry in the table, containing information about 
                    an event."
                INDEX { eventTextGroupIndex, eventTextEventIndex }
                ::= { eventTextTable 1 }

            EventTextEntry ::=
                SEQUENCE {
                    eventTextGroupIndex
                        EventGroup,
                    eventTextEventIndex
                        INTEGER,
                    eventTextText
                        DisplayString,
                    eventTextDateTime
                        DateTime,
                    eventTextSeverity
                        INTEGER
                }

            eventTextGroupIndex OBJECT-TYPE
                SYNTAX EventGroup
                ACCESS read-only
                STATUS mandatory
                DESCRIPTION
                    "This variable identifies the event group."
                ::= { eventTextEntry 1 }

            eventTextEventIndex OBJECT-TYPE
                SYNTAX INTEGER
                ACCESS read-only
                STATUS mandatory
                DESCRIPTION
                    "This variable identifies the event of the desired
                     group.  This number is arbitrary, and translates
                     to nth event of the specified group.  This value
                     wraps at the 32 bit maximum."
                ::= { eventTextEntry 2 }

            eventTextText OBJECT-TYPE
                SYNTAX DisplayString (SIZE (1..80))
                ACCESS read-only
                STATUS mandatory
                DESCRIPTION
                    "The text of the event in the language defined by
                     eventLanguage."
                ::= { eventTextEntry 3 }

            eventTextDateTime OBJECT-TYPE
                SYNTAX DateTime
                ACCESS read-only
                STATUS mandatory
                DESCRIPTION
                    "The timestamp of when the event was posted."
                ::= { eventTextEntry 4 }

            eventTextSeverity OBJECT-TYPE
                SYNTAX INTEGER { low(2), medium(3), high(4) }
                ACCESS read-only
                STATUS mandatory
                DESCRIPTION
                    "The severity of the event."
                ::= { eventTextEntry 5 }

END
