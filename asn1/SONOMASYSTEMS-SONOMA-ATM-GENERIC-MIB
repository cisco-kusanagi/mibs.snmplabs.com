-- |**********************************************************************|
 -- | Copyright 1998 - Sonoma Systems, Inc. Marina del Rey, CA 90292       |
 -- |    Unpublished software - All rights reserved.                       |
 -- |                                                                      |
 -- | The information in this software is subject to change without notice |
 -- | and should not be construed as a commitment by Sonoma Systems, Inc.  |
 -- |                                                                      |
 -- | Sonoma Systems, Inc. assumes no responsibility for the use or        |
 -- | reliability of its software on equipment which is not supplied by    |
 -- | Sonoma Systems, Inc.                                                 |
 -- |                                                                      |
 -- | This software is furnished under a license and may be copied only    |
 -- | under the terms of that license and with the inclusion of this       |
 -- | notice. This software, or any other copies thereof, may not be       |
 -- | provided or otherwise made available to any other person except to   |
 -- | one who agrees to these license terms. Title to and ownership of the |
 -- | software shall at all times remain with Sonoma Systems, Inc.         |
 -- |**********************************************************************|
 --
 -- Sonoma Systems Inc.,
 -- 4640 Admiralty Way, Suite #600,
 -- Marina Del Rey,
 -- California 90292-6695.
 --
 -- Web : www.sonoma-systems.com
 -- Phone:  310.827.8000
 --
 -- NAME        :  atmmib.def
 --
 -- DESCRIPTION : 
 --
 -- This is the generic ATM MIB for the Sonoma product line.
 --
 -- ARCHIVE : $Archive:   M:\pvcs\pvcsproj\sonoma3\src\mib\atmmib.dev  $
 -- REVISION: $Revision:   1.9  $
 -- AUTHOR  : $Author:   HHARRIS  $
 -- DATE    : $Date:   Mar 12 1999 19:17:58  $


      SONOMASYSTEMS-SONOMA-ATM-GENERIC-MIB --{ iso org(3) dod(6) internet(1) private(4) enterprises(1) sonomaSystems(2926) sonomaSeries(25) sonomaATM(7) 1 }
      DEFINITIONS ::= BEGIN

      IMPORTS
        Counter
        FROM RFC1155-SMI
        OBJECT-TYPE
        FROM RFC-1212
        sonomaATM
        FROM SONOMASYSTEMS-SONOMA-MIB;

  --  This MIB module uses the extended OBJECT-TYPE macro as
  --  defined in [14];


      -- Hierarchy for these objects
      -- enterprises OBJECT IDENTIFIER ::= { private 4 }
      -- sonomaSystems OBJECT IDENTIFIER ::= {  enterprises 2926 }
      -- sonomaSeries OBJECT IDENTIFIER ::= { sonomaSystems 25 }
      -- sonomaATM OBJECT IDENTIFIER ::= { sonomaSeries 7 }
      sonomaGenericATMGroup OBJECT IDENTIFIER ::= { sonomaATM 1 }
      -- Sonoma ATM Group MIB groups
      atmGenericPhysGroup OBJECT IDENTIFIER ::= { sonomaGenericATMGroup 1 }
      atmGenericVclGroup  OBJECT IDENTIFIER ::= { sonomaGenericATMGroup 2 }
      atmGenericLpGroup   OBJECT IDENTIFIER ::= { sonomaGenericATMGroup 3 }
      atmCesGroup         OBJECT IDENTIFIER ::= { sonomaGenericATMGroup 4 }
      atmAsiPhysGroup     OBJECT IDENTIFIER ::= { sonomaGenericATMGroup 5 }
      atmAsmPhysGroup     OBJECT IDENTIFIER ::= { sonomaGenericATMGroup 6 }

  --
  -- Starting ATM MIB, in the Sequence of Sonoma Systems, ATM Forum, and RFC-1695
  --

    --
    --  Sonoma Systems Private ATM MIB
    --


    -- Physical Port Parameter Group

    -- This group contains the Physical Port Group
    -- parameters associated with one physical
    -- interface

    atmGenPhysTable  OBJECT-TYPE
    SYNTAX  SEQUENCE OF AtmGenPhysEntry
        ACCESS  not-accessible
        STATUS  mandatory
        DESCRIPTION
        "A table of physical layer status and parameter information
         for the UNI's physical interface"
        ::= { atmGenericPhysGroup 1 }
      
    atmGenPhysEntry  OBJECT-TYPE
        SYNTAX  AtmGenPhysEntry
        ACCESS  not-accessible
        STATUS  mandatory
        DESCRIPTION
         "A entry in the table, containing information about the
          physical layer of a UNI interface"
        INDEX  { atmGenPhysIndex }
        ::= { atmGenPhysTable 1 }
    
    AtmGenPhysEntry ::= SEQUENCE {
      atmGenPhysIndex               INTEGER,
      atmGenPhysAal5Mtu             INTEGER,
      atmGenPhysAal5CrcErrors       Counter,
      atmGenPhysAal5OverSizedSDUs   Counter,
      atmGenPhysAal5DiscardPDU      Counter,
      atmGenPhysHECErrors           Counter,
      atmGenPhysUnknownProtocols    Counter,
      atmGenPhysCellsReceived       Counter,
      atmGenPhysCellsTransmitted    Counter,
      atmGenPhysRxBufStarvation  Counter,
      atmGenPhysRxFreeze         Counter,
      atmGenPhysTxFreeze         Counter
    }

    atmGenPhysIndex OBJECT-TYPE
        SYNTAX      INTEGER
        ACCESS      read-only
        STATUS      mandatory
        DESCRIPTION
        "The physical interface instance."
        ::= { atmGenPhysEntry 1 }

    atmGenPhysAal5Mtu  OBJECT-TYPE
        SYNTAX  INTEGER
        ACCESS  read-only
        STATUS  mandatory
        DESCRIPTION
        "The AAL5 MTU capacity for the physical interface, assigned by PM."
        ::= { atmGenPhysEntry 2 }

    atmGenPhysAal5CrcErrors  OBJECT-TYPE
        SYNTAX  Counter
        ACCESS  read-only
        STATUS  mandatory
        DESCRIPTION
        "The total number of AAL5 CPCS PDUs received with CRC-32 errors
         at the interface associated with an AAL5 entity."
        ::= { atmGenPhysEntry 3 }

    atmGenPhysAal5OverSizedSDUs  OBJECT-TYPE
        SYNTAX  Counter
        ACCESS  read-only
        STATUS  mandatory
        DESCRIPTION
        "The total number of AAL5 CPCS PDUs discarded at
         the interface associated with an AAL5 entity because the
         AAL5 SDUs were too large."
        ::= { atmGenPhysEntry 4 }

    atmGenPhysAal5DiscardPDU  OBJECT-TYPE
        SYNTAX  Counter
        ACCESS  read-only
        STATUS  mandatory
        DESCRIPTION
        "The total number of AAL5 CPCS PDUs discarded at
         the interface associated with an AAL5 entity because no
         receive free buffers were available.  Only available with
         TCOP atm card."
        ::= { atmGenPhysEntry 5 }

    atmGenPhysHECErrors OBJECT-TYPE
        SYNTAX  Counter
        ACCESS  read-only
        STATUS  mandatory
        DESCRIPTION
        "The total number ATM cells dropped out to HEC errors.  Only
         available with TCOP atm card."
        ::= { atmGenPhysEntry 6 }

    atmGenPhysUnknownProtocols OBJECT-TYPE
        SYNTAX  Counter
        ACCESS  read-only
        STATUS  mandatory
        DESCRIPTION
        "The total number cells received with an unknown header.
         Only available with TCOP atm card."
        ::= { atmGenPhysEntry 7 }

    atmGenPhysCellsReceived OBJECT-TYPE
        SYNTAX  Counter
        ACCESS  read-only
        STATUS  mandatory
        DESCRIPTION
        "The total number ATM cells received with no errors. Only
         available with TCOP atm card."
        ::= { atmGenPhysEntry 8 }

    atmGenPhysCellsTransmitted OBJECT-TYPE
        SYNTAX  Counter
        ACCESS  read-only
        STATUS  mandatory
        DESCRIPTION
        "The total number ATM cells actually transmitted.  Only
         available with TCOP atm card." 
        ::= { atmGenPhysEntry 9 }

    atmGenPhysRxBufStarvation OBJECT-TYPE
        SYNTAX  Counter
        ACCESS  read-only
        STATUS  mandatory
        DESCRIPTION
        "The total number of occurrences when no Rx free buffer is available 
         at the interface associated with an AAL5 entity."
        ::= { atmGenPhysEntry 10 }

    atmGenPhysRxFreeze OBJECT-TYPE
        SYNTAX  Counter
        ACCESS  read-only
        STATUS  mandatory
        DESCRIPTION
        "The total number of occurrences when Rx completion ring overflows
         at the interface associated with an AAL5 entity."
        ::= { atmGenPhysEntry 11 }

    atmGenPhysTxFreeze OBJECT-TYPE
        SYNTAX  Counter
        ACCESS  read-only
        STATUS  mandatory
        DESCRIPTION
        "The total number of occurrences when Tx completion ring overflows
         at the interface associated with an AAL5 entity."
        ::= { atmGenPhysEntry 12 }

-------------------
    atmGenRateTable  OBJECT-TYPE
    SYNTAX  SEQUENCE OF AtmGenRateEntry
        ACCESS  not-accessible
        STATUS  mandatory
        DESCRIPTION
        "A table of ATM layer configuration for the ATM-DS3/E3/OC3c
         interface.  Only used by earlier version of software."
        ::= { atmGenericPhysGroup 2 }

    atmGenRateEntry  OBJECT-TYPE
        SYNTAX  AtmGenRateEntry
        ACCESS  not-accessible
        STATUS  mandatory
        DESCRIPTION
          "A entry in the table, containing information about the
           rate queues on this physical interface."
        INDEX  { atmGenRatePhysIndex }
        ::= { atmGenRateTable 1 }

    AtmGenRateEntry ::= SEQUENCE {
      atmGenRatePhysIndex   INTEGER,
      atmGenRateQueOne     INTEGER,
      atmGenRateQueTwo     INTEGER,
      atmGenRateQueThree   INTEGER,
      atmGenRateQueFour    INTEGER,
      atmGenRateQueFive    INTEGER,
      atmGenRateQueSix     INTEGER,
      atmGenRateQueSeven   INTEGER,
      atmGenRateQueEight   INTEGER
    }

   atmGenRatePhysIndex   OBJECT-TYPE
        SYNTAX  INTEGER (1..256)
        ACCESS  read-only
        STATUS  mandatory
        DESCRIPTION
            "The ATM interface index, for this table the value of this
             object corresponds to the physical port instance."
        ::= { atmGenRateEntry 1 }

    atmGenRateQueOne   OBJECT-TYPE
        SYNTAX  INTEGER (0..135150)
        ACCESS  read-write
        STATUS  mandatory
        DESCRIPTION
            "The value of this object can be set to any value in
             the range 0 to 30720 for E3, the range 0 to 36864 for DS3, and
             the range 0 to 135150 for OC3. The combination of all the values
             of all the rate queue objects must equal 30720 for E3, 
             36864 for DS3, and 135150 for OC3. Thus,
             if this object has a value of 36864 for DS3, then the values
             of the rest of the objects cannot be set to anything
             other than 0.
             The value of any rate queue object is rounded down to
             the nearest multiple of 10."
        ::= { atmGenRateEntry 2 }

    atmGenRateQueTwo   OBJECT-TYPE
        SYNTAX  INTEGER (0..135150)
        ACCESS  read-write
        STATUS  mandatory
        DESCRIPTION
            "The ATM layer rate queue number two bandwidth."
        ::= { atmGenRateEntry 3 }

    atmGenRateQueThree OBJECT-TYPE
        SYNTAX  INTEGER (0..135150)
        ACCESS  read-write
        STATUS  mandatory
        DESCRIPTION
            "The ATM layer rate queue number three bandwidth."
        ::= { atmGenRateEntry 4 }

    atmGenRateQueFour  OBJECT-TYPE
        SYNTAX  INTEGER (0..135150)
        ACCESS  read-write
        STATUS  mandatory
        DESCRIPTION
            "The ATM layer rate queue number four bandwidth."
        ::= { atmGenRateEntry 5 }

    atmGenRateQueFive  OBJECT-TYPE
        SYNTAX  INTEGER (0..135150)
        ACCESS  read-write
        STATUS  mandatory
        DESCRIPTION
            "The ATM layer rate queue number five bandwidth."
        ::= { atmGenRateEntry 6 }

    atmGenRateQueSix   OBJECT-TYPE
        SYNTAX  INTEGER (0..135150)
        ACCESS  read-write
        STATUS  mandatory
        DESCRIPTION
            "The ATM layer rate queue number six bandwidth."
        ::= { atmGenRateEntry 7 }

    atmGenRateQueSeven OBJECT-TYPE
        SYNTAX  INTEGER (0..135150)
        ACCESS  read-write
        STATUS  mandatory
        DESCRIPTION
            "The ATM layer rate queue number seven bandwidth."
        ::= { atmGenRateEntry 8 }

    atmGenRateQueEight OBJECT-TYPE
        SYNTAX  INTEGER (0..135150)
        ACCESS  read-write
        STATUS  mandatory
        DESCRIPTION
            "The ATM layer rate queue number eight bandwidth."
        ::= { atmGenRateEntry 9 }
--------------------
    atmGenRateQTable  OBJECT-TYPE
    SYNTAX  SEQUENCE OF AtmGenRateQEntry
        ACCESS  not-accessible
        STATUS  mandatory
        DESCRIPTION
        "A table of ATM layer configuration for the ATM-DS3/E3/OC3c
         interface.  Not used with TCOP atm card."
        ::= { atmGenericPhysGroup 3 }

    atmGenRateQEntry  OBJECT-TYPE
        SYNTAX  AtmGenRateQEntry
        ACCESS  not-accessible
        STATUS  mandatory
        DESCRIPTION
          "A entry in the table, containing information about the
           rate queues on this physical interface."
        INDEX  { atmGenRateQPhysIndex, atmGenRateQNumber }
        ::= { atmGenRateQTable 1 }

    AtmGenRateQEntry ::= SEQUENCE {
      atmGenRateQPhysIndex  INTEGER,
      atmGenRateQNumber     INTEGER,
      atmGenRateQueue       INTEGER
    }

   atmGenRateQPhysIndex   OBJECT-TYPE
        SYNTAX  INTEGER (1..256)
        ACCESS  read-only
        STATUS  mandatory
        DESCRIPTION
            "The ATM interface index, for this table the value of this
             object corresponds to the physical port instance."
        ::= { atmGenRateQEntry 1 }

    atmGenRateQNumber   OBJECT-TYPE
        SYNTAX  INTEGER (1..255)
        ACCESS  read-write
        STATUS  mandatory
        DESCRIPTION
            "The ATM layer rate queue number."
        ::= { atmGenRateQEntry 2 }

    atmGenRateQueue    OBJECT-TYPE
        SYNTAX  INTEGER (0..135150)
        ACCESS  read-write
        STATUS  mandatory
        DESCRIPTION
            "The value of this object can be set to any value in
             the range 0 to 30720 for E3, the range 0 to 36864 for DS3, and
             the range 0 to 135150 for OC3. The combination of all the values
             of all the rate queue objects must equal 30720 for E3, 
             36864 for DS3, and 135150 for OC3. Thus,
             if this object has a value of 36864 for DS3, then the values
             of the rest of the objects cannot be set to anything
             other than 0.
             The value of any rate queue object is rounded down to
             the nearest multiple of 10."
        DEFVAL { 0 }
        ::= { atmGenRateQEntry 3 }

    -- Virtual Circuit Group

    -- This group contains the Virtual Circuit Group
    -- parameters associated with virtual circuits
    -- configuration for the 1561 ATM adapter.

    atmGenVclTable   OBJECT-TYPE
        SYNTAX  SEQUENCE OF AtmGenVclEntry
        ACCESS  not-accessible
        STATUS  mandatory
        DESCRIPTION
        "The Virtual Channel Link (VCL) table. A bi-directional VCL
         is modeled as one entry in this table."
        ::= { atmGenericVclGroup 1 }
      
    atmGenVclEntry   OBJECT-TYPE
        SYNTAX  AtmGenVclEntry
        ACCESS  not-accessible
        STATUS  mandatory
        DESCRIPTION
         "An entry in the VCL table.  This entry is used to model a
          bi-directional VCL."
        INDEX  { atmGenVclIfIndex, atmGenVclVpi, atmGenVclVci }
        ::= { atmGenVclTable 1 }
    
    AtmGenVclEntry ::= SEQUENCE {
      atmGenVclIfIndex      INTEGER,
      atmGenVclVpi          INTEGER,
      atmGenVclVci          INTEGER,
      atmGenVclRateQ        INTEGER,
      atmGenVclAction       INTEGER
    }

    atmGenVclIfIndex  OBJECT-TYPE
        SYNTAX  INTEGER
        ACCESS  read-only
        STATUS  mandatory
        DESCRIPTION
        "The physical interface instance."
        ::= { atmGenVclEntry 1 }

    atmGenVclVpi  OBJECT-TYPE
        SYNTAX  INTEGER(0..255)
        ACCESS  read-only
        STATUS  mandatory
        DESCRIPTION
        "The VPI value of the VCL, 0 - 255."
        ::= { atmGenVclEntry 2 }

    atmGenVclVci  OBJECT-TYPE
        SYNTAX  INTEGER(1..1023)
        ACCESS  read-only
        STATUS  mandatory
        DESCRIPTION
        "The VCI value of the VCL. Minimum value of 32
        when VPI is 0 and minimum value of 1 for all
        other VPI. Maximum value of 1023 for 1561
        adapter and maximum value of 4095 for 1575
        tcop adapter."
        ::= { atmGenVclEntry 3 }

    atmGenVclRateQ   OBJECT-TYPE
        SYNTAX  INTEGER(1..255)
        ACCESS  read-write
        STATUS  mandatory
        DESCRIPTION
        "The Rate Queue used by this virtual circuit."
        DEFVAL { 1 }
        ::={ atmGenVclEntry 4 }

    atmGenVclAction OBJECT-TYPE
        SYNTAX  INTEGER { 
                create(5), 
                destroy(6)
                }
        ACCESS  read-write
        STATUS  mandatory
        DESCRIPTION
        "This object is used to create or delete a row in this table. 
         A set request to add a row to this table need only contain this
         object's value in the PDU. The row created will be defined by the
         instance passed with the object identifier. Thus, to add the 
         following entry: Logical Port 257, VP 1, VC 36, send a set request
         with a var bind containing atmGenVclAction.257.1.36 as the object
         identifier component and 5 as the value of the value component."
        ::= { atmGenVclEntry 5 }

    -- This group contains the Virtual Circuit Group
    -- parameters associated with virtual circuits
    -- configuration for the 1575 ATM adapter.

    atmGenVclTmTable   OBJECT-TYPE
        SYNTAX  SEQUENCE OF AtmGenVclTmEntry
        ACCESS  not-accessible
        STATUS  mandatory
        DESCRIPTION
        "The Virtual Channel Link (VCL) table. A bi-directional VCL
         is modeled as one entry in this table."
        ::= { atmGenericVclGroup 2 }
      
    atmGenVclTmEntry   OBJECT-TYPE
        SYNTAX  AtmGenVclTmEntry
        ACCESS  not-accessible
        STATUS  mandatory
        DESCRIPTION
         "An entry in the VCL table.  This entry is used to model a
          bi-directional VCL."
        INDEX  { atmGenVclTmIfIndex, atmGenVclTmVpi, atmGenVclTmVci }
        ::= { atmGenVclTmTable 1 }
    
    AtmGenVclTmEntry ::= SEQUENCE {
      atmGenVclTmIfIndex        INTEGER,
      atmGenVclTmVpi            INTEGER,
      atmGenVclTmVci            INTEGER,
      atmGenVclTmPCR            INTEGER,
      atmGenVclTmSCR            INTEGER,
      atmGenVclTmMBS            INTEGER,
      atmGenVclTmAction     INTEGER
    }

    atmGenVclTmIfIndex  OBJECT-TYPE
        SYNTAX  INTEGER
        ACCESS  read-only
        STATUS  mandatory
        DESCRIPTION
        "The physical interface instance."
        ::= { atmGenVclTmEntry 1 }

    atmGenVclTmVpi  OBJECT-TYPE
        SYNTAX  INTEGER(0..255)
        ACCESS  read-only
        STATUS  mandatory
        DESCRIPTION
        "The VPI value of the VCL, 0 - 255."
        ::= { atmGenVclTmEntry 2 }

    atmGenVclTmVci  OBJECT-TYPE
        SYNTAX  INTEGER(1..4095)
        ACCESS  read-only
        STATUS  mandatory
        DESCRIPTION
        "The VCI value of the VCL. Minimum value of 32
        when VPI is 0 and minimum value of 1 for all
        other VPI. Maximum value of 1023 for 1561
        adapter and maximum value of 4095 for 1575
        tcop adapter."
        ::= { atmGenVclTmEntry 3 }

    atmGenVclTmPCR    OBJECT-TYPE
        SYNTAX  INTEGER (0..16777215)
        ACCESS  read-write
        STATUS  mandatory
        DESCRIPTION
            "Specify Peak Cell Rate."
        DEFVAL { 0 }
        ::= { atmGenVclTmEntry 4 }


    atmGenVclTmSCR    OBJECT-TYPE
        SYNTAX  INTEGER (0..16777215)
        ACCESS  read-write
        STATUS  mandatory
        DESCRIPTION
            "Specify Sustainable Cell Rate."
        DEFVAL { 0 }
        ::= { atmGenVclTmEntry 5 }

    atmGenVclTmMBS    OBJECT-TYPE
        SYNTAX  INTEGER (0..16777215)
        ACCESS  read-write
        STATUS  mandatory
        DESCRIPTION
            "Specify Maximum Burst Size."
        DEFVAL { 0 }
        ::= { atmGenVclTmEntry 6 }

    atmGenVclTmAction OBJECT-TYPE
        SYNTAX  INTEGER { 
                create(5), 
                destroy(6)
                }
        ACCESS  read-write
        STATUS  mandatory
        DESCRIPTION
        "This object is used to create or delete a row in this table. 
         A set request to add a row to this table need only contain this
         object's value in the PDU. The row created will be defined by the
         instance passed with the object identifier. Thus, to add the 
         following entry: Logical Port 257, VP 1, VC 36, send a set request
         with a var bind containing atmGenVclAction.257.1.36 as the object
         identifier component and 5 as the value of the value if you want
         to create AAL5 VC.
         
         "
        ::= { atmGenVclTmEntry 7 }

    -- atmGenVclStatsGroup 

    atmGenVclStatsTable   OBJECT-TYPE
    SYNTAX  SEQUENCE OF AtmGenVclStatsEntry
        ACCESS  not-accessible
        STATUS  mandatory
        DESCRIPTION
        "The Virtual Channel Link (VCL) table. A bi-directional VCL
         is modeled as one entry in this table."
        ::= { atmGenericVclGroup 3 }
      
    atmGenVclStatsEntry   OBJECT-TYPE
        SYNTAX  AtmGenVclStatsEntry
        ACCESS  not-accessible
        STATUS  mandatory
        DESCRIPTION
         "An entry in the VCL table."
        INDEX  { atmGenVclStatsIfIndex, atmGenVclStatsVpi, atmGenVclStatsVci }
        ::= { atmGenVclStatsTable 1 }
    
    AtmGenVclStatsEntry ::= SEQUENCE {
      atmGenVclStatsIfIndex         INTEGER,
      atmGenVclStatsVpi             INTEGER,
      atmGenVclStatsVci             INTEGER,
      atmGenVclStatsCellsReceived   Counter,
      atmGenVclStatsCellsTransmitted    Counter,
      atmGenVclStatsOamAisRcvCells   Counter,
      atmGenVclStatsOamAisXmtCells   Counter,
      atmGenVclStatsOamRdiRcvCells   Counter,
      atmGenVclStatsOamRdiXmtCells   Counter,
      atmGenVclStatsOamLoopbackRcvCells   Counter,
      atmGenVclStatsOamLoopbackXmtCells   Counter      
    }

    atmGenVclStatsIfIndex  OBJECT-TYPE
        SYNTAX  INTEGER
        ACCESS  read-only
        STATUS  mandatory
        DESCRIPTION
        "The physical interface instance."
        ::= { atmGenVclStatsEntry 1 }

    atmGenVclStatsVpi  OBJECT-TYPE
        SYNTAX  INTEGER(0..255)
        ACCESS  read-only
        STATUS  mandatory
        DESCRIPTION
        "The VPI value of the VCL, 0 - 255."
        ::= { atmGenVclStatsEntry 2 }

    atmGenVclStatsVci  OBJECT-TYPE
        SYNTAX  INTEGER(35..1023)
        ACCESS  read-only
        STATUS  mandatory
        DESCRIPTION
        "The VCI value of the VCL, 35 - 1023."
        ::= { atmGenVclStatsEntry 3 }

    atmGenVclStatsCellsReceived OBJECT-TYPE
        SYNTAX  Counter
        ACCESS  read-only
        STATUS  mandatory
        DESCRIPTION
        "The total number of cells received by this virtual circuit."
        ::= { atmGenVclStatsEntry 4 }

    atmGenVclStatsCellsTransmitted OBJECT-TYPE
        SYNTAX  Counter 
        ACCESS  read-only
        STATUS  mandatory
        DESCRIPTION
        "The total number of cells transmitted by this virtual circuit."
        ::= { atmGenVclStatsEntry 5 }
        
    atmGenVclStatsOamAisRcvCells OBJECT-TYPE
        SYNTAX  Counter
        ACCESS  read-only
        STATUS  mandatory
        DESCRIPTION
        "The total number of AIS OAM cells received by this virtual circuit."
        ::= { atmGenVclStatsEntry 6 }

    atmGenVclStatsOamAisXmtCells OBJECT-TYPE
        SYNTAX  Counter
        ACCESS  read-only
        STATUS  mandatory
        DESCRIPTION
        "The total number of AIS OAM cells transmitted by this 
	 virtual circuit."
        ::= { atmGenVclStatsEntry 7 }

    atmGenVclStatsOamRdiRcvCells OBJECT-TYPE
        SYNTAX  Counter
        ACCESS  read-only
        STATUS  mandatory
        DESCRIPTION
        "The total number of RDI OAM cells received by this virtual circuit."
        ::= { atmGenVclStatsEntry 8 }

    atmGenVclStatsOamRdiXmtCells OBJECT-TYPE
        SYNTAX  Counter
        ACCESS  read-only
        STATUS  mandatory
        DESCRIPTION
        "The total number of RDI OAM cells transmitted by this 
	 virtual circuit."
        ::= { atmGenVclStatsEntry 9 }

    atmGenVclStatsOamLoopbackRcvCells OBJECT-TYPE
        SYNTAX  Counter
        ACCESS  read-only
        STATUS  mandatory
        DESCRIPTION
        "The total number of Loopback OAM cells received by this 
	 virtual circuit."
        ::= { atmGenVclStatsEntry 10 }

    atmGenVclStatsOamLoopbackXmtCells OBJECT-TYPE
        SYNTAX  Counter
        ACCESS  read-only
        STATUS  mandatory
        DESCRIPTION
        "The total number of Loopback OAM cells transmitted by this 
	 virtual circuit."
        ::= { atmGenVclStatsEntry 11 }
        


    -- Logical Port Parameter Group

    -- This group contains the Logical Port Group
    -- parameters associated with one logical port
    -- interface

    atmGenLogicalPortTable   OBJECT-TYPE
        SYNTAX  SEQUENCE OF AtmGenLogicalPortEntry
        ACCESS  not-accessible
        STATUS  mandatory
        DESCRIPTION
          "A table of physical layer status and parameter information
           for the UNI's physical interface"
        ::= { atmGenericLpGroup 1 }
      
    atmGenLogicalPortEntry  OBJECT-TYPE
        SYNTAX  AtmGenLogicalPortEntry
        ACCESS  not-accessible
        STATUS  mandatory
        DESCRIPTION
          "A entry in the table, containing information about the
           physical layer of a UNI interface"
        INDEX  { atmGenLpIfIndex }
        ::= { atmGenLogicalPortTable 1 }
    
    AtmGenLogicalPortEntry ::= SEQUENCE {
      atmGenLpIfIndex         INTEGER,
      atmGenLpPhysIf          INTEGER,
      atmGenLpLoopTime        INTEGER,
      atmGenLpProtocol        INTEGER,
      atmGenLpAal5EncapsType  INTEGER,
      atmGenLpAal5Mtu         INTEGER,
      atmGenLpAal5RateQ       INTEGER,
      atmGenLpAdminStatus     INTEGER,
      atmGenLpLoopThreshold   INTEGER,
      atmGenLpLoopTrapTime    INTEGER,
      atmGenLpOamGeneration   INTEGER      
    }

    atmGenLpIfIndex  OBJECT-TYPE
        SYNTAX  INTEGER(257..512)
        ACCESS  read-only
        STATUS  mandatory
        DESCRIPTION
        "The logical port index."
        ::= { atmGenLogicalPortEntry 1 }

    atmGenLpPhysIf  OBJECT-TYPE
        SYNTAX  INTEGER(1..256)
        ACCESS  read-only
        STATUS  mandatory
        DESCRIPTION
        "The physical interface associated with this logical port."
        ::= { atmGenLogicalPortEntry 2 }

    atmGenLpLoopTime OBJECT-TYPE
        SYNTAX  INTEGER
        ACCESS  read-write
        STATUS  mandatory
        DESCRIPTION
        "The time (in hundredths of a second) to drop a receive frame."
        DEFVAL { 0 }
        ::= { atmGenLogicalPortEntry 3 }

    atmGenLpProtocol   OBJECT-TYPE
        SYNTAX INTEGER {
            ethernet (7),
            ethernetII (8),
            ethernet8023 (9),
            tokenRing (10),
            fddi (11)
        }
        ACCESS  read-only
        STATUS  mandatory
        DESCRIPTION
        "Network layer for the VC's attached to this LP"
        ::= { atmGenLogicalPortEntry 4 }

    atmGenLpAal5EncapsType   OBJECT-TYPE
        SYNTAX  INTEGER { 
                rfc1483-vc(1), 
                rfc1483-llc(2) 
                }
        ACCESS  read-write
        STATUS  mandatory
        DESCRIPTION
        "An instance of this object only exists when the local VCL
         end-point is also the VCC end-point, and AAL5 is in use.
         The type of data encapsulation used over the AAL5 SSCS layer.
         The definitions reference RFC 1483 Multiprotocol Encapsulation
         over ATM AAL5 and to the ATM Forum LAN Emulation
         specification."
        DEFVAL { rfc1483-llc }
        ::= { atmGenLogicalPortEntry 5 }

    atmGenLpAal5Mtu  OBJECT-TYPE
        SYNTAX  INTEGER
        ACCESS  read-write
        STATUS  mandatory
        DESCRIPTION
        "The PDU size for the AAL5 CPCS layer that can be processed
         by the AAL5 entity, 64 - 16K."
        ::={ atmGenLogicalPortEntry 6 }

    atmGenLpAal5RateQ   OBJECT-TYPE
        SYNTAX  INTEGER
        ACCESS  read-only
        STATUS  mandatory
        DESCRIPTION
        "The rate queue used by this virtual circuit."
        ::={ atmGenLogicalPortEntry 7 }

    atmGenLpAdminStatus  OBJECT-TYPE
        SYNTAX  INTEGER { 
                enable (1), 
                disable (2) 
                }
        ACCESS  read-only
        STATUS  mandatory
        DESCRIPTION
        "The logical port status, just for reference. The Port Manager
         has control of the status."
        ::= { atmGenLogicalPortEntry 8 }

    atmGenLpLoopThreshold OBJECT-TYPE
        SYNTAX  INTEGER
        ACCESS  read-write
        STATUS  mandatory
        DESCRIPTION
        "The number of frames receives before a snmp trap will be sent."
        DEFVAL { 5 }
        ::={ atmGenLogicalPortEntry 9 }

    atmGenLpLoopTrapTime OBJECT-TYPE
        SYNTAX  INTEGER
        ACCESS  read-write
        STATUS  mandatory
        DESCRIPTION
        "The time (in seconds) between checks to send out snmp trap."
        DEFVAL { 5 }
        ::= { atmGenLogicalPortEntry 10 }

    atmGenLpOamGeneration OBJECT-TYPE
        SYNTAX  INTEGER
        ACCESS  read-write
        STATUS  mandatory
        DESCRIPTION
        "Enable or Disable the generation of OAM cells."
        DEFVAL { 1 }
        ::= { atmGenLogicalPortEntry 11 }
        

  --
  -- Starting CES MIB, in the Sequence of Sonoma Systems, ATM Forum, and RFC-1695
  --

    --
    --  Sonoma Systems Private CES MIB
    --


-- This is the MIB module for the ATM Forum Circuit Emulation
-- Service Interoperability Specification Version 2.0.
--
-- This MIB contains three tables:
-- CES Configuration Table
-- CES Statistics Table

-- CES Configuration Table

    cesConfTable OBJECT-TYPE
        SYNTAX SEQUENCE OF CesConfEntry
        ACCESS not-accessible
        STATUS mandatory
        DESCRIPTION
        "The CES configuration table used to manage interworking
         between CBR interfaces or channels and ATM Virtual Channel
         Links (VCLs). The reverse mapping is shown in the
         cesMappingTable."
         ::= { atmCesGroup 1 }
         
    cesConfEntry OBJECT-TYPE
        SYNTAX CesConfEntry
        ACCESS not-accessible
        STATUS mandatory
        DESCRIPTION
        "An entry in the CES configuration table. There is one
         entry in the table per ATM Port/VPI/VCI."
        INDEX { cesAtmPhysPort, cesAtmVpi, cesAtmVci }
        ::= { cesConfTable 1 }

        CesConfEntry ::= SEQUENCE {
            cesAtmPhysPort INTEGER,
            cesAtmVpi INTEGER,
            cesAtmVci INTEGER,
            cesCbrService INTEGER,
            cesCbrClockMode INTEGER,
            cesCas INTEGER,
            cesPartialFill INTEGER,
            cesBufMaxSize INTEGER,
            cesCdvRxT INTEGER,
            cesCellLossIntegrationPeriod INTEGER,
            cesConnType INTEGER,
            cesDynBw INTEGER,
            cesSigType INTEGER,
			cesConfAction INTEGER
            }
            
    cesAtmPhysPort OBJECT-TYPE
        SYNTAX  INTEGER
        ACCESS read-only
        STATUS mandatory
        DESCRIPTION
        "The value of this object is equal to MIB II's
        ifIndex value of the ATM Port interface mapped
        through this CES IWF to a CBR interface. This value
        is overwritten whenever an active or passive SVC is
        established.
        The distinguished value zero indicates that no ATM
        interface has been specified."
        ::= { cesConfEntry 1 }

    cesAtmVpi OBJECT-TYPE
        SYNTAX  INTEGER(0..255)
        ACCESS read-only
        STATUS mandatory
        DESCRIPTION
        "The value of this object is equal to the VPI used
        by the ATM VCL mapped through this CES IWF to a CBR
        interface. This value is overwritten whenever an
        active or passive SVC is established.
        The value is not relevant if no ATM interface has been
        specified (i.e., cesAtmIndex is set to zero)."
        ::= { cesConfEntry 2 }

    cesAtmVci OBJECT-TYPE
        SYNTAX  INTEGER(1..1023)
        ACCESS read-only
        STATUS mandatory
        DESCRIPTION
        "The value of this object is equal to the VCI used
        by the ATM VCL mapped through this CES IWF to a CBR
        interface. This value is overwritten whenever an
        active or passive SVC is established.
        The distinguished value zero indicates that no ATM
        VCL has been specified."
        ::= { cesConfEntry 3 }

    cesCbrService OBJECT-TYPE
        SYNTAX INTEGER {
        unstructured(1),
        structured(2)
        }
        ACCESS read-write
        STATUS mandatory
        DESCRIPTION
        "Define if DSx/Ex service is structured or unstructured. A
        structured(2) interface is some nx64kbKbps. An unstructured
        (1) interface is 1.544Mbps, 2.048Mbps, 6.312Mbps, 44.736 Mbps,
        or 34.368 Mbps. unstructured(1) passes all bits through the
        ATM network. strucutured(2) passes data bits through the
        ATM network, and may also pass signalling bits
        At this time, only unstructured mode is defined for the
        44.736 Mbps and 34.368 Mbps services."
        ::= { cesConfEntry 4 }

    cesCbrClockMode OBJECT-TYPE
        SYNTAX INTEGER {
            synchronous(1),
            srts-master(2),
            adaptive(3),
            srts-slave(4)
        }
        ACCESS read-write
        STATUS mandatory
        DESCRIPTION
        "Define if DSx/Ex service clocking mode. This maps into
        transmit clock source of CBR interface.
        For structured modes this value, if present, must be set to
        synchronous(1)."
        DEFVAL { synchronous }
        ::= { cesConfEntry 5 }

    cesCas OBJECT-TYPE
        SYNTAX INTEGER {
            without(1),
            with(2)
        }
        ACCESS read-write
        STATUS mandatory
        DESCRIPTION
        "This parameter selects which AAL1 Format should be used:
        Without does not carry CAS bits, and uses a single 125 usec frame.
        With carris CAS bits in a multiframe structure for E1, DS1 SF, or 
        DS1 ESF.  This applies to structured interfaces only. Default is
        without (1). For unstructured interfaces this value, if present,
        must be set to the default of without (1)."
        DEFVAL { without }
        ::= { cesConfEntry 6 }

    cesPartialFill OBJECT-TYPE
        SYNTAX INTEGER (0..47)
        ACCESS read-write
        STATUS mandatory
        DESCRIPTION
        "If partial cell fill is used, the number of user octets per
        cell must be set with this parameter. Setting this parameter
        to zero disables partial cell fill, and causes all cells to
        be completely filled before they are sent."
        DEFVAL { 0 } -- Partial Cell Fill not used
        ::= { cesConfEntry 7 }

    cesBufMaxSize OBJECT-TYPE
        SYNTAX INTEGER (1..65536)
        ACCESS read-write
        STATUS mandatory
        DESCRIPTION
        "Define maximum size in 10 microsecond increments of the
        reassembly buffer. Some implementations may want allow the
        maximum buffer size to be programmed to a size less than the
        physical limit to reduce the maximum delay through a circuit."
        DEFVAL { 128 }
        ::= { cesConfEntry 8 }

    cesCdvRxT OBJECT-TYPE
        SYNTAX INTEGER (1..65535)
        ACCESS read-write
        STATUS mandatory
        DESCRIPTION
        "The maximum cell arrival jitter in 10 usec increments that
        the reassembly process will tolerate in the cell stream
        without producing errors on the CBR service interface."
        DEFVAL { 100 }
        ::= { cesConfEntry 9 }

    cesCellLossIntegrationPeriod OBJECT-TYPE
        SYNTAX INTEGER (1000 .. 65535)
        ACCESS read-write
        STATUS mandatory
        DESCRIPTION
        "The time in milliseconds for the cell loss integration period.
        If a cells are continuously lost for this period of time,
        cesCellLossStatus is set to loss (2). The
        default definition is 2500."
        DEFVAL { 2500 }
        ::= { cesConfEntry 10 }

    cesConnType OBJECT-TYPE
        SYNTAX INTEGER {
        pvc(2)
        }
        ACCESS read-write
        STATUS mandatory
        DESCRIPTION
        "The type of ATM connectivity between associated CES IWF's.
        Valid values are:
        other - none of the types specified below
        pvc - supporting connectivity is a permanent
        virtual connection
        activeSvc - attempt calls whenever none established
        passiveSvc - accept calls
        Only pvc is supported in this release."
        ::= { cesConfEntry 11 }

    cesDynBw OBJECT-TYPE
        SYNTAX INTEGER {
            enabled(1),
            disabled(2)
        }
        ACCESS read-write
        STATUS mandatory
        DESCRIPTION
        "The Sonoma Dynamic Bandwidth feature may be enabled 
        or disabled."
        ::= { cesConfEntry 12 }

    cesSigType OBJECT-TYPE
        SYNTAX INTEGER {
            other(1),
            fxo-loop(2),
            fxs-loop(3),
            fxo-ground(4),
            fxs-ground(5),
            e-and-m(6),
            r2(7)
        }
        ACCESS read-write
        STATUS mandatory
        DESCRIPTION
        "This is the A/B signalling type for dynamic bandwidth Idle detection."
        ::= { cesConfEntry 13 }

	cesConfAction OBJECT-TYPE
		SYNTAX INTEGER {
			attach(5),
			remove(6)
		}
		ACCESS read-write
		STATUS mandatory
		DESCRIPTION
		"The value of this object indicates whether the entry,
		is to be attached or removed from the CES Configuration Table.
		A value of attach has the effect of adding an entry to this table.
		A value of remove has the effect of removing an entry from the table."
		::= { cesConfEntry 14 }



-- CES Statistics Table
    cesStatsTable OBJECT-TYPE
        SYNTAX SEQUENCE OF CesStatsEntry
        ACCESS not-accessible
        STATUS mandatory
        DESCRIPTION
        "The CES AAL1 statistical data table."
        ::= { atmCesGroup 3 }

    cesStatsEntry OBJECT-TYPE
        SYNTAX CesStatsEntry
        ACCESS not-accessible
        STATUS mandatory
        DESCRIPTION
        "An entry in the CES AAL1 Stats table. There is one
        entry in this table corresponding to each entry in the
        cesConfTable."
        INDEX { cesStatsAtmPhyPort, cesStatsAtmVpi, cesStatsAtmVci }
        ::= { cesStatsTable 1 }

        CesStatsEntry ::= SEQUENCE {
            cesStatsAtmPhyPort INTEGER,
            cesStatsAtmVpi INTEGER,
            cesStatsAtmVci INTEGER,
            cesReassCells Counter,
            cesHdrErrors Counter,
            cesPointerReframes Counter,
            cesPointerParityErrors Counter,
            cesAal1SeqErrors Counter,
            cesLostCells Counter,
            cesMisinsertedCells Counter,
            cesBufUnderflows Counter,
            cesBufOverflows Counter,
            cesCellLossStatus INTEGER
        }

    cesStatsAtmPhyPort  OBJECT-TYPE
        SYNTAX  INTEGER
        ACCESS  read-only
        STATUS  mandatory
        DESCRIPTION
        "The physical interface instance."
        ::= { cesStatsEntry 1 }

    cesStatsAtmVpi  OBJECT-TYPE
        SYNTAX  INTEGER(0..255)
        ACCESS  read-only
        STATUS  mandatory
        DESCRIPTION
        "The VPI value of the VCL, 0 - 255."
        ::= { cesStatsEntry 2 }

    cesStatsAtmVci  OBJECT-TYPE
        SYNTAX  INTEGER(35..1023)
        ACCESS  read-only
        STATUS  mandatory
        DESCRIPTION
        "The VCI value of the VCL, 35 - 1023."
        ::= { cesStatsEntry 3 }

    cesReassCells OBJECT-TYPE
        SYNTAX Counter
        ACCESS read-only
        STATUS mandatory
        DESCRIPTION
        "This count gives the number of cells played out to the
        CES Service Interface. It excludes cells that were
        discarded for any reason, including cells that were not used
        due to being declared misinserted, or discarded while the
        reassembler was waiting to achieve synchronization."
        ::= { cesStatsEntry 4 }

    cesHdrErrors OBJECT-TYPE
        SYNTAX Counter
        ACCESS read-only
        STATUS mandatory
        DESCRIPTION
        "The count of the number of AAL1 header errors detected,
        including those corrected. Header errors include correctable
        and uncorrectable CRC, plus bad parity."
        ::= { cesStatsEntry 5 }

    cesPointerReframes OBJECT-TYPE
        SYNTAX Counter
        ACCESS read-only
        STATUS mandatory
        DESCRIPTION
        "This records the count of the number of events in which the
        AAL1 reassembler found that an SDT pointer is not where it is
        expected, and the pointer must be reacquired. This count is
        only meaningful for structured CES modes, as unstructured CES
        modes do not use pointers. For unstructured CES modes, this
        count, if present, should indicate zero."
        ::= { cesStatsEntry 6}

    cesPointerParityErrors OBJECT-TYPE
        SYNTAX Counter
        ACCESS read-only
        STATUS mandatory
        DESCRIPTION
        "This records the count of the number of events in which the
        AAL1 reassembler detects a parity check failure at the point
        where a structured data pointer is expected. This count is only
        meaningful for structured CES modes, as unstructured CES modes
        do not use pointers. For unstructured CES modes, this count, if
        present, should indicate zero."
        ::= { cesStatsEntry 7 }

    cesAal1SeqErrors OBJECT-TYPE
        SYNTAX Counter
        ACCESS read-only
        STATUS mandatory
        DESCRIPTION
        "Number of times that the sequence number of an incoming AAL1
        Type 1 SAR-PDU causes a transition from the 'sync' state to
        the 'out of sequence' state, as defined by ITU-T I.363.1."
        ::= { cesStatsEntry 8 }

    cesLostCells OBJECT-TYPE
        SYNTAX Counter
        ACCESS read-only
        STATUS mandatory
        DESCRIPTION
        "Number of lost cells, as detected by the AAL1 sequence number
        processing, for example. This records the count of the number
        of cells detected as lost in the network prior to the
        destination CES IWF AAL1 layer processing."
        ::= { cesStatsEntry 9 }

    cesMisinsertedCells OBJECT-TYPE
        SYNTAX Counter
        ACCESS read-only
        STATUS mandatory
        DESCRIPTION
        "Number of AAL1 sequence violations which the AAL Convergence
        sublayer interprets as a misinserted cell, as defined by
        ITU-T I.363.1."
        ::= { cesStatsEntry 10 }

        cesBufUnderflows OBJECT-TYPE
        SYNTAX Counter
        ACCESS read-only
        STATUS mandatory
        DESCRIPTION
        "Number of buffer underflows. This records the count of the
        number of times the CES reassembly buffer underflows. In the
        case of a continuous underflow caused by a loss of ATM cell
        flow, a single buffer underflow should be counted. If the CES
        IWF is implemented with multiple buffers (such as a cell level
        buffer and a bit level buffer), then either buffer underflow
        will cause this count to be incremented."
        ::= { cesStatsEntry 11 }

    cesBufOverflows OBJECT-TYPE
        SYNTAX Counter
        ACCESS read-only
        STATUS mandatory
        DESCRIPTION
        "Number of buffer overflows. This records the count of the
        number of times the CES reassembly buffer overflows. If the CES
        IWF is implemented with multiple buffers (such as a cell level
        buffer and a bit level buffer, then either buffer overflow will
        cause this count to be incremented "
        ::= { cesStatsEntry 12 }

    cesCellLossStatus OBJECT-TYPE
        SYNTAX INTEGER {
        noLoss(1),
        loss(2)
        }
        ACCESS read-only
        STATUS deprecated
        DESCRIPTION
        "When cells are continuously lost for the number of milliseconds
        specified by cesCellLossIntegrationPeriod, the value is set
        to loss (2). When cells are no longer lost, the value is set
        to noLoss (1)."
        ::= { cesStatsEntry 13 }

-- Sonoma Systems private CES mib
-- The following Bundle Attachment Table provides mapping between the DS0
-- channel and the CES DS0 bundle.

    cesAttachmentTable  OBJECT-TYPE
        SYNTAX  SEQUENCE OF CesAttachmentEntry
        ACCESS  not-accessible
        STATUS  mandatory
        DESCRIPTION
            "This table is used to attach a bundle to a physical
             port and DS0 channel."
        ::= { atmCesGroup 4 }
   
    cesAttachmentEntry  OBJECT-TYPE
        SYNTAX  CesAttachmentEntry
        ACCESS  not-accessible
        STATUS  mandatory
        DESCRIPTION
            "This is an entry in the attach bundle to physical port and DS0 channel
             table. An entry in this table indicates if the bundle
             is attached to the physical port and what DS0 channel on the physical
             port the bundle is attached to, if applicable. To set an
             entry in this table, ALL the objects in the entry must be present
             in a single SET PDU."
        INDEX  { cesAttachmentPhysPort, cesAttachmentBundle, cesAttachmentChan }

        ::= { cesAttachmentTable 1 }

    CesAttachmentEntry ::= SEQUENCE {
            cesAttachmentPhysPort      INTEGER,
            cesAttachmentBundle        INTEGER,
            cesAttachmentChan          INTEGER,
            cesAttachmentAction        INTEGER
    }

	cesAttachmentPhysPort  OBJECT-TYPE
        SYNTAX  INTEGER (1..256)
        ACCESS  read-only
        STATUS  mandatory
        DESCRIPTION
            "The physical port number of the port to which the 
             bundle is being attached." 
        ::= { cesAttachmentEntry 1 }

    cesAttachmentBundle  OBJECT-TYPE
        SYNTAX  INTEGER (1025..1536)
        ACCESS  read-only
        STATUS  mandatory
        DESCRIPTION
            "The bundle number. The range of settable values
             for this object is 1025 to 1536."
        ::= { cesAttachmentEntry 2 }

    cesAttachmentChan  OBJECT-TYPE
        SYNTAX  INTEGER (0..32)
        ACCESS  read-only
        STATUS  mandatory
        DESCRIPTION
            "The value of this object indicates the DS0 channel to which
             the bundle, identified by cesAttachmentBundle, is attached
             or is to be attached."
        ::= { cesAttachmentEntry 3 }

    cesAttachmentAction  OBJECT-TYPE
        SYNTAX  INTEGER {
                         attach (5),
                         remove (6)
                        }
        ACCESS  read-write
        STATUS  mandatory
        DESCRIPTION
            "The value of this object indicates whether the bundle,
             is to be attached or removed from the physical port and DS0 channel.
             A value of attach has the effect of adding an entry to this table,
             and either to create the bundle, or to attach it to another
             physical port.  A value of remove has the effect of removing
             an entry from the table and if the DS0 channel is the last one
             attached to the bundle then the remove action has the
             effect of deleting the bundle also."
        ::= { cesAttachmentEntry 4 }


    -----------------------------------------------------------------------

    -- Sonoma ATM ASI Adapter Specific Group MIB groups

    -- This group contains all informat specificly for
    -- Sonoma Systems ASI adapter. It includes the configuration and
    -- some statistics information

    -- Sonoma ATM ASI Adapter Specific Group MIB groups
       atmAsiConfGroup OBJECT IDENTIFIER ::= { atmAsiPhysGroup 1 }
       atmAsiStatsGroup OBJECT IDENTIFIER ::= { atmAsiPhysGroup 2 }
    

    --  atmAsiConfGroup

    atmAsiConfPhyTable  OBJECT-TYPE
        SYNTAX  SEQUENCE OF AtmAsiConfPhyEntry
        ACCESS  not-accessible
        STATUS  mandatory
        DESCRIPTION
            "A table of physical layer configuration for the ASI
         interface"
        ::= { atmAsiConfGroup 1 }

    atmAsiConfPhyEntry  OBJECT-TYPE
        SYNTAX  AtmAsiConfPhyEntry
        ACCESS  not-accessible
        STATUS  mandatory
        DESCRIPTION
          "A entry in the table, containing information about the
           physical layer of an ASI interface"
        INDEX  { atmAsiConfPhysIndex }
        ::= { atmAsiConfPhyTable 1 }
    
    AtmAsiConfPhyEntry ::= SEQUENCE {
      atmAsiConfPhysIndex     INTEGER,
      atmAsiConfLineType      INTEGER,
      atmAsiConfLineCoding    INTEGER,
      atmAsiConfTxClkSelect   INTEGER,
      atmAsiConfSignalMode    INTEGER,      
      atmAsiConfLIUType       INTEGER,
      atmAsiConfLBOType       INTEGER,
      atmAsiConfIdlePattern   INTEGER,
      atmAsiConfLoopbackMode  INTEGER,
      atmAsiConfStopMode      INTEGER,
      atmAsiConfRecoveredClkSource    INTEGER,
      atmAsiDebugAddr         INTEGER,
      atmAsiDebugReadValue    INTEGER,
      atmAsiDebugWriteValue   INTEGER,
      atmAsiDebugRead         INTEGER
    }

    atmAsiConfPhysIndex   OBJECT-TYPE
        SYNTAX  INTEGER
        ACCESS  read-only
        STATUS  mandatory
        DESCRIPTION
            "The physical interface index."
        ::= { atmAsiConfPhyEntry 1 }   

    atmAsiConfLineType OBJECT-TYPE
        SYNTAX  INTEGER { 
                        esf(2), 
                        d4(3),
                        e1(4),
                        e1-crc(5),
                        e1-cas(6),
                        e1-crc-cas(7)
                        }
        ACCESS  read-write
        STATUS  mandatory
        DESCRIPTION
            "Configure the line type."
          DEFVAL { esf }
        ::= { atmAsiConfPhyEntry 2 }


    atmAsiConfLineCoding OBJECT-TYPE
        SYNTAX  INTEGER {  
            b8zs(2),
            hdb3(3),
            zbtsi(4),
            ami(5)
            }
        ACCESS  read-write
        STATUS  mandatory
        DESCRIPTION
            "Configure the line coding."
            DEFVAL { b8zs }
        ::= { atmAsiConfPhyEntry 4 }

    atmAsiConfTxClkSelect OBJECT-TYPE
        SYNTAX  INTEGER {
                        internal(1),
                        line(2),
                        through(3)
                        }
        ACCESS  read-write
        STATUS  mandatory
        DESCRIPTION
            "This parameter configures the source of the Tx clock."
            DEFVAL { line }
        ::= { atmAsiConfPhyEntry 5 }
        
    atmAsiConfSignalMode OBJECT-TYPE
        SYNTAX  INTEGER {
                        none(1),
                        robbed-bit(2),
                        bit-oriented (3)
                        }
        ACCESS  read-write
        STATUS  mandatory
        DESCRIPTION
            "This parameter configures the signal mode."
            DEFVAL { none }
        ::= { atmAsiConfPhyEntry 6 }
        


	atmAsiConfLIUType OBJECT-TYPE
        SYNTAX  INTEGER {
                        t1-long(1),
                        itu-120(2),
                        itu-75(3),
                        dsx1-short(4)
                        }
        ACCESS  read-write
        STATUS  mandatory
        DESCRIPTION
            "This parameter configures the Line Interface Unit type."
            DEFVAL { dsx1-short }
        ::= { atmAsiConfPhyEntry 7 }

	atmAsiConfLBOType OBJECT-TYPE
        SYNTAX  INTEGER {
                        short-133(1),
                        short-266(2),
                        short-399(3),
                        short-533(4),
                        short-655(5),
                        long-0(8),
                        long-75(9),
                        long-150(10),
                        long-225(11)
                        }
        ACCESS  read-write
        STATUS  mandatory
        DESCRIPTION
            "This parameter configures the Line Build Out."
            DEFVAL { short-133 }
        ::= { atmAsiConfPhyEntry 8 }

atmAsiConfIdlePattern OBJECT-TYPE
        SYNTAX  INTEGER(0..255)
        ACCESS  read-write
        STATUS  mandatory
        DESCRIPTION
            "This parameter configures the idle pattern for trunk
             conditioning."
            DEFVAL { 127 }
        ::= { atmAsiConfPhyEntry 9 }

atmAsiConfLoopbackMode OBJECT-TYPE
        SYNTAX  INTEGER {
                        disable(1),
                        internal(2),
                        external(3)
                        }
        ACCESS  read-write
        STATUS  mandatory
        DESCRIPTION
            "This parameter configures the loopback mode."
            DEFVAL { disable }
        ::= { atmAsiConfPhyEntry 10 }

atmAsiConfStopMode OBJECT-TYPE
        SYNTAX  INTEGER {
                        immediate(1),
                        on-idle(2)
                        }
        ACCESS  read-write
        STATUS  mandatory
        DESCRIPTION
            "This parameter configures the mode used for stop commands."
            DEFVAL { immediate }
        ::= { atmAsiConfPhyEntry 11 }

atmAsiConfRecoveredClkSource OBJECT-TYPE
        SYNTAX  INTEGER {
			fourth-port(1),
			third-port(2),
			second-port(3),
			first-port(4),
			phy-port(5)			
			}
        ACCESS  read-write
        STATUS  mandatory
        DESCRIPTION
            "This parameter configures the source of the recovered clock used for
             through timing."
            DEFVAL { fourth-port }
        ::= { atmAsiConfPhyEntry 12 }

atmAsiDebugAddr  OBJECT-TYPE
        SYNTAX  INTEGER 
        ACCESS  read-write
        STATUS  mandatory
        DESCRIPTION
            "PCI Phy address for DS1 port register."
        DEFVAL { 0 }
        ::= { atmAsiConfPhyEntry 13 }

    atmAsiDebugReadValue  OBJECT-TYPE
        SYNTAX  INTEGER 
        ACCESS  read-write
        STATUS  mandatory
        DESCRIPTION
            "Value read from DS1 port register."
        DEFVAL { 0 }
        ::= { atmAsiConfPhyEntry 14 }

    atmAsiDebugWriteValue  OBJECT-TYPE
        SYNTAX  INTEGER 
        ACCESS  read-write
        STATUS  mandatory
        DESCRIPTION
            "Value written to DS1 port register."
        DEFVAL { 0 }
        ::= {atmAsiConfPhyEntry 15 }

    atmAsiDebugRead  OBJECT-TYPE
        SYNTAX  INTEGER {
                        read(1),
                        write(2)
                        }
        ACCESS  read-write
        STATUS  mandatory
        DESCRIPTION
            "Read or Write of DS1 port register (TRUE = READ)."
        DEFVAL { read }
        ::= { atmAsiConfPhyEntry 16 }



    --  atmAsiStatsGroup

    atmAsiStatsTable  OBJECT-TYPE
        SYNTAX  SEQUENCE OF AtmAsiStatsEntry
        ACCESS  not-accessible
        STATUS  mandatory
        DESCRIPTION
            "A table of physical layer statistics information for the ASI 
         interface"
        ::= { atmAsiStatsGroup 1 }

    atmAsiStatsEntry  OBJECT-TYPE
        SYNTAX  AtmAsiStatsEntry
        ACCESS  not-accessible
        STATUS  mandatory
        DESCRIPTION
          "A entry in the table, containing information about the
           physical layer of an ASI interface"
        INDEX  { atmAsiStatsPhysIndex }
        ::= { atmAsiStatsTable 1 }
    
    AtmAsiStatsEntry ::= SEQUENCE {
      atmAsiStatsPhysIndex      INTEGER,
      atmAsiStatsNoSignals      Counter,
      atmAsiStatsAISDetects     Counter,
      atmAsiStatsYelAlarmCount  Counter,
      atmAsiStatsLCVErrors      Counter,
      atmAsiStatsPCVErrors      Counter,
      atmAsiStatsMOSErrors      Counter,
      atmAsiStatsSyncLossCount  Counter,
      atmAsiStatsHECErrors      Counter,
      atmAsiStatsSignalLoss       INTEGER,
      atmAsiStatsAISDetect        INTEGER,
      atmAsiStatsYellowAlarm      INTEGER,
      atmAsiStatsSyncLoss          INTEGER,
      atmAsiStatsTxClockLoss         INTEGER,
      atmAsiStatsClearCounters     INTEGER
    }

    atmAsiStatsPhysIndex  OBJECT-TYPE
        SYNTAX  INTEGER
        ACCESS  read-only
        STATUS  mandatory
        DESCRIPTION
            "The physical interface index."
        ::= { atmAsiStatsEntry 1 }  

    atmAsiStatsNoSignals  OBJECT-TYPE
        SYNTAX  Counter
        ACCESS  read-only
        STATUS  mandatory
        DESCRIPTION
            "No signal error counter."
        ::= { atmAsiStatsEntry 2 }

    atmAsiStatsAISDetects  OBJECT-TYPE
        SYNTAX  Counter
        ACCESS  read-only
        STATUS  mandatory
        DESCRIPTION
            "AIS Detect counter."
        ::= {atmAsiStatsEntry 3 }
    
    atmAsiStatsYelAlarmCount  OBJECT-TYPE
        SYNTAX  Counter
        ACCESS  read-only
        STATUS  mandatory
        DESCRIPTION
            "A count of the number of Yellow Alarms."
        ::= { atmAsiStatsEntry 4 }

    atmAsiStatsLCVErrors  OBJECT-TYPE
        SYNTAX  Counter
        ACCESS  read-only
        STATUS  mandatory
        DESCRIPTION
            "LCV (Line Code Violation) error counter."
        ::= { atmAsiStatsEntry 5 }

    atmAsiStatsPCVErrors  OBJECT-TYPE
        SYNTAX  Counter
        ACCESS  read-only
        STATUS  mandatory
        DESCRIPTION
            "PCV (Path Code Violation) error counter."
        ::= { atmAsiStatsEntry 6 }

    atmAsiStatsMOSErrors  OBJECT-TYPE
        SYNTAX  Counter
        ACCESS  read-only
        STATUS  mandatory
        DESCRIPTION
            "Multiframe out of sync error counter."
        ::= { atmAsiStatsEntry 7 }

    atmAsiStatsSyncLossCount  OBJECT-TYPE
        SYNTAX  Counter
        ACCESS  read-only
        STATUS  mandatory
        DESCRIPTION
            "Sync Loss counter."
        ::= { atmAsiStatsEntry 8 }

    atmAsiStatsHECErrors  OBJECT-TYPE
        SYNTAX  Counter
        ACCESS  read-only
        STATUS  mandatory
        DESCRIPTION
            "HEC error counter."
        ::= { atmAsiStatsEntry 9 }

    atmAsiStatsSignalLoss  OBJECT-TYPE
        SYNTAX  INTEGER {
                        true (1), 
                        false (2)
                        }
        ACCESS  read-only
        STATUS  mandatory
        DESCRIPTION
            "Signal loss indication."
        ::= { atmAsiStatsEntry 10 }

    atmAsiStatsAISDetect  OBJECT-TYPE
        SYNTAX  INTEGER {
                        true (1), 
                        false (2)
                        }
        ACCESS  read-only
        STATUS  mandatory
        DESCRIPTION
            "AIS indication."
        ::= { atmAsiStatsEntry 11 }

    atmAsiStatsYellowAlarm  OBJECT-TYPE
        SYNTAX  INTEGER {
                        true (1), 
                        false (2)
                        }
        ACCESS  read-only
        STATUS  mandatory
        DESCRIPTION
            "Yellow Alarm indication."
        ::= { atmAsiStatsEntry 12 }

    atmAsiStatsSyncLoss  OBJECT-TYPE
        SYNTAX  INTEGER {
                        true (1), 
                        false (2)
                        }
        ACCESS  read-only
        STATUS  mandatory
        DESCRIPTION
            "Loss of sync indication."
        ::= { atmAsiStatsEntry 13 }

    atmAsiStatsTxClockLoss  OBJECT-TYPE
        SYNTAX  INTEGER {
                    true (1), 
                    false (2)
                    }
        ACCESS  read-only
        STATUS  mandatory
        DESCRIPTION
            "Loss of transmit clock indication."
        ::= { atmAsiStatsEntry 14 }

    atmAsiStatsClearCounters  OBJECT-TYPE
        SYNTAX  INTEGER {
                        true (1), 
                        false (2)
                        }
        ACCESS  read-write
        STATUS  mandatory
        DESCRIPTION
            "Clear all counters in this group ONLY."
        DEFVAL { false }
        ::= { atmAsiStatsEntry 15 }

    -----------------------------------------------------------------------

    -- Sonoma ATM ASM Adapter Specific Group

    -- This group contains all information specifically for the
    -- Sonoma Systems ASM adapter. Currently it includes an object
    -- to set the physical port's line usage.

       atmAsmPhyConfGroup OBJECT IDENTIFIER ::= { atmAsmPhysGroup 1 }

    --  atmAsmPhyConfGroup

    atmAsmPhyConfTable  OBJECT-TYPE
        SYNTAX  SEQUENCE OF AtmAsmPhyConfEntry
        ACCESS  not-accessible
        STATUS  mandatory
        DESCRIPTION
          "A table of physical layer configuration for the ASM
           interfaces."
        ::= { atmAsmPhyConfGroup 1 }

    atmAsmPhyConfEntry  OBJECT-TYPE
        SYNTAX  AtmAsmPhyConfEntry
        ACCESS  not-accessible
        STATUS  mandatory
        DESCRIPTION
          "A entry in the table, containing information about the
           physical layer of an ASM interfaces."
        INDEX  { atmAsmPhyConfIndex }
        ::= { atmAsmPhyConfTable 1 }
    
    AtmAsmPhyConfEntry ::= SEQUENCE {
      atmAsmPhyConfIndex          INTEGER,
      atmAsmPhyConfAdminLineUsage INTEGER,
      atmAsmPhyConfOperLineUsage  INTEGER
    }

    atmAsmPhyConfIndex   OBJECT-TYPE
        SYNTAX  INTEGER
        ACCESS  read-only
        STATUS  mandatory
        DESCRIPTION
            "The physical interface index."
        ::= { atmAsmPhyConfEntry 1 }

    atmAsmPhyConfAdminLineUsage OBJECT-TYPE
        SYNTAX  INTEGER {
                        ces-udt(1), 
                        ces-sdt(2),
                        uni(4),
                        ima(5) 
                        } 
        ACCESS  read-write
        STATUS  mandatory
        DESCRIPTION
            "The desired physical port's line usage. For some port 
             types, the desired line usage will become effective 
             after the system is rebooted."
            DEFVAL { uni }
        ::= { atmAsmPhyConfEntry 2 }

    atmAsmPhyConfOperLineUsage OBJECT-TYPE
        SYNTAX  INTEGER {
                        ces-udt(1), 
                        ces-sdt(2),
                        uni(4),
                        ima(5) 
                        } 
        ACCESS  read-only
        STATUS  mandatory
        DESCRIPTION
            "The physical port's current line usage."
            DEFVAL { uni }
        ::= { atmAsmPhyConfEntry 3 }

END
