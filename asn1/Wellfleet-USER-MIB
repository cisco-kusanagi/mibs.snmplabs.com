Wellfleet-USER-MIB DEFINITIONS ::= BEGIN

    IMPORTS

      OBJECT-TYPE
        FROM RFC-1212
      IpAddress, Counter
        FROM RFC1155-SMI
      DisplayString
        FROM RFC1213-MIB
      wfUserServicesGroup
        FROM Wellfleet-COMMON-MIB;


    wfUserAccess  OBJECT IDENTIFIER ::= { wfUserServicesGroup 1 }

    wfUserAccessDelete    OBJECT-TYPE
        SYNTAX  INTEGER {
                    created(1),
                    deleted(2)
                }
        ACCESS  read-write
        STATUS  mandatory
        DESCRIPTION
                "Indication to create or delete User Access  record."
        DEFVAL  { created }
        ::= { wfUserAccess  1 }

    wfUserAccessConfig OBJECT-TYPE
        SYNTAX	INTEGER {
    		    enabled(1),
    		    disabled(2)
    		}
        ACCESS	read-write
        STATUS	mandatory
        DESCRIPTION
                "Indicates local password (configuration file ) information is 
                 to be used"
        DEFVAL	{ enabled }
        ::= { wfUserAccess  2 }

    wfUserAccessRadius OBJECT-TYPE
        SYNTAX	INTEGER {
    		    enabled(1),
    		    disabled(2)
    		}
        ACCESS	read-write
        STATUS	mandatory
        DESCRIPTION
                "Indicates radius authentication server is to be used"
        DEFVAL	{ disabled }
        ::= { wfUserAccess  3 }


    wfUserAccessMaxLogin OBJECT-TYPE
        SYNTAX	INTEGER (1..16)
        ACCESS	read-write
        STATUS	mandatory
        DESCRIPTION
                "This the maximum allowed login name, in the range 1 to 16"
        DEFVAL	{ 16 }
        ::= { wfUserAccess  4 }

    wfUserAccessMinLogin OBJECT-TYPE
        SYNTAX	INTEGER (1..16)
        ACCESS	read-write
        STATUS	mandatory
        DESCRIPTION
                "This the minimum allowed login name, in the range 1 to 16"
        DEFVAL	{ 4 }
        ::= { wfUserAccess  5 }

    wfUserAccessMaxGroup OBJECT-TYPE
        SYNTAX	INTEGER (1..16)
        ACCESS	read-write
        STATUS	mandatory
        DESCRIPTION

                "This the maximum allowed Group name, in the range 1 to 16"
        DEFVAL	{ 16 }
        ::= { wfUserAccess  6 }

    wfUserAccessMinGroup OBJECT-TYPE
        SYNTAX	INTEGER (1..16)
        ACCESS	read-write
        STATUS	mandatory
        DESCRIPTION
                "This the minimum allowed Group name, in the range 1 to 16"
        DEFVAL	{ 4 }
        ::= { wfUserAccess  7 }

    wfUserAccessMaxPassword OBJECT-TYPE
        SYNTAX	INTEGER (1..16)
        ACCESS	read-write
        STATUS	mandatory
        DESCRIPTION
                "This the maximum allowed Password , in the range 1 to 16"
        DEFVAL	{ 16 }
        ::= { wfUserAccess  8 }

    wfUserAccessMinPassword OBJECT-TYPE
        SYNTAX	INTEGER (0..16)
        ACCESS	read-write
        STATUS	mandatory
        DESCRIPTION
                "This the minimum allowed Password, in the range 0 to 16"
        DEFVAL	{ 0 }
        ::= { wfUserAccess  9 }

    wfUserManagerLock OBJECT-TYPE		
        SYNTAX	INTEGER {
    		    enabled(1),
    		    disabled(2),
		    serverwait(3)
    		}
        ACCESS	read-write
        STATUS	mandatory
        DESCRIPTION
                "When enabled Manager and user are not usable"
        DEFVAL	{ disabled }
        ::= { wfUserAccess  10 }	

    wfUserAccessRadiusAcctEnable  OBJECT-TYPE		
        SYNTAX	INTEGER {
    		    enabled(1),
    		    disabled(2)
    		}
        ACCESS	read-write
        STATUS	mandatory
        DESCRIPTION
                "When enabled Radius Accouting is performed for Login Access"
        DEFVAL	{ disabled }
        ::= { wfUserAccess  11 }	

    wfUserAccessNameTable OBJECT-TYPE
        SYNTAX  SEQUENCE OF WfUserAccessNameEntry
        ACCESS  not-accessible
        STATUS  mandatory
        DESCRIPTION
              "A table to contain user information to be searched on the router"
        ::= { wfUserServicesGroup  2 }

        wfUserAccessNameEntry OBJECT-TYPE
            SYNTAX  WfUserAccessNameEntry
            ACCESS  not-accessible
            STATUS  mandatory
            DESCRIPTION
                    "The attributes for individual User account"
            INDEX   { wfUserAccessNameId }
            ::= { wfUserAccessNameTable 1 }

        WfUserAccessNameEntry ::= SEQUENCE {
                wfUserAccessNameDelete
                    INTEGER,
                wfUserAccessNameDisable
                    INTEGER,
                wfUserAccessNameId
                    DisplayString,
                wfUserAccessNameName
                    DisplayString,
                wfUserAccessNamePasswd
                    DisplayString,
                wfUserAccessNameGroups
                    INTEGER,
                wfUserAccessNameAudit
                    INTEGER,
                wfUserAccessNameScript
                    DisplayString
    
        }
        wfUserAccessNameDelete OBJECT-TYPE
            SYNTAX  INTEGER {
                    created(1),
                    deleted(2)
                    }
            ACCESS  read-write
            STATUS  mandatory
            DESCRIPTION
                  "Indication to create or delete a user record"
            DEFVAL  { created }
            ::= { wfUserAccessNameEntry 1 }

        wfUserAccessNameDisable OBJECT-TYPE
            SYNTAX  INTEGER {
                    enabled(1),
                    disabled(2)
                    }
            ACCESS  read-write
            STATUS  mandatory
            DESCRIPTION
                  "enable/disable this user login"
            DEFVAL  { enabled }
            ::= { wfUserAccessNameEntry 2 }

        wfUserAccessNameId  OBJECT-TYPE
            SYNTAX  DisplayString
            ACCESS  read-only
            STATUS  mandatory
            DESCRIPTION
                    "Login name of the user  "
            ::= { wfUserAccessNameEntry 3 }
    
        wfUserAccessNameName  OBJECT-TYPE
            SYNTAX  DisplayString
            ACCESS  read-write
            STATUS  mandatory
            DESCRIPTION
                    "True name of the user"
            ::= { wfUserAccessNameEntry 4 }
    
        wfUserAccessNamePasswd  OBJECT-TYPE
            SYNTAX  DisplayString
            ACCESS  read-write
            STATUS  mandatory
            DESCRIPTION
                    "Encripted user password"
            ::= { wfUserAccessNameEntry 5 }
    
        wfUserAccessNameGroups  OBJECT-TYPE
            SYNTAX  INTEGER
            ACCESS  read-write
            STATUS  mandatory
            DESCRIPTION
                    "Bit Field of the groups the user belongs to"
            ::= { wfUserAccessNameEntry 6 }
    
        wfUserAccessNameAudit  OBJECT-TYPE
            SYNTAX  INTEGER
            ACCESS  read-write
            STATUS  mandatory
            DESCRIPTION
                    "Audit level for this user 
                     0 No Audit
                     Bit 1 Manager
                     Bit 2 User
		     Bit 3 Operator
                     All Bits Anything user typed
                     All others RFU "
            DEFVAL { 1 } 
            ::= { wfUserAccessNameEntry 7 }

        wfUserAccessNameScript  OBJECT-TYPE
            SYNTAX  DisplayString
            ACCESS  read-write
            STATUS  mandatory
            DESCRIPTION
                    "User specified BCC startup script"
            ::= { wfUserAccessNameEntry 8 }
     
    wfUserAccessActiveTable OBJECT-TYPE
        SYNTAX  SEQUENCE OF WfUserAccessActiveEntry
        ACCESS  not-accessible
        STATUS        mandatory
        DESCRIPTION 
                " Group access table definition"
        ::= { wfUserServicesGroup  3 }

        wfUserAccessActiveEntry OBJECT-TYPE
            SYNTAX  WfUserAccessActiveEntry
            ACCESS  not-accessible
            STATUS  mandatory
            DESCRIPTION
                    "records indicating active users"
            INDEX { wfUserAccessActiveLoginAddress,
                    wfUserAccessActivePort }
            ::= { wfUserAccessActiveTable 1 }
 
        WfUserAccessActiveEntry ::= SEQUENCE {
             wfUserAccessActiveDelete
                INTEGER,
             wfUserAccessActiveDisable
                INTEGER,
             wfUserAccessActiveId 
                DisplayString,
             wfUserAccessActiveLoginAddress
                IpAddress,
             wfUserAccessActivePort
                INTEGER,
             wfUserAccessActiveState
                INTEGER,
             wfUserAccessActiveCmd
                DisplayString,
             wfUserAccessActiveLastCmdTime
                INTEGER,
              wfUserAccessActiveLoginTime
                Counter,
	     wfUserAccessActiveAcctInOctets
		Counter,
	     wfUserAccessActiveAcctOutOctets
		Counter,
	     wfUserAccessActiveAcctAccessType
		INTEGER,
	     wfUserAccessActiveAcctTermCause
		INTEGER,
	     wfUserAccessActiveAcctServiceType
		INTEGER,
	     wfUserAccessActiveAcctNasPortType
		INTEGER,
	     wfUserAccessActiveAcctPriv
		INTEGER

           }
        wfUserAccessActiveDelete OBJECT-TYPE
            SYNTAX  INTEGER {
                    created(1),
                    deleted(2)
                }
            ACCESS  read-write
            STATUS  mandatory
            DESCRIPTION
                    "Indication ot create/delete a active user record"
            DEFVAL  { created }
            ::= { wfUserAccessActiveEntry 1 }

        wfUserAccessActiveDisable OBJECT-TYPE
            SYNTAX  INTEGER {
                    enabled(1),
                    disabled(2)
                }
            ACCESS  read-write
            STATUS  mandatory
            DESCRIPTION
                    "Enable/disable this record"
            DEFVAL  { enabled }
            ::= { wfUserAccessActiveEntry 2 }

        wfUserAccessActiveId  OBJECT-TYPE
            SYNTAX  DisplayString
            ACCESS  read-only
            STATUS  mandatory
            DESCRIPTION
                    "Login name of the login  "
            ::= { wfUserAccessActiveEntry 3 }


        wfUserAccessActiveLoginAddress OBJECT-TYPE
            SYNTAX  IpAddress
            ACCESS  read-only
            STATUS  mandatory
            DESCRIPTION
                    "Indicated the IP address this user is logged in from.
                     zero indidates the console. This is undefined when
                     the users state is logout"
            ::= { wfUserAccessActiveEntry 4 }
	
        wfUserAccessActivePort  OBJECT-TYPE
            SYNTAX  INTEGER 
            ACCESS  read-only
            STATUS  mandatory
            DESCRIPTION
                    "Port number this user is logged in on ( identifies 
                     multiple logins from the same ip address"
            ::= { wfUserAccessActiveEntry 5 }

        wfUserAccessActiveState  OBJECT-TYPE
            SYNTAX  INTEGER {
                    active(1),
                    config(2),
		    ftp(3)
                    }
            ACCESS  read-only 
            STATUS  mandatory
            DESCRIPTION
                    "Current State ofthis login "
            DEFVAL { active } 
            ::= { wfUserAccessActiveEntry 6 }

    
        wfUserAccessActiveCmd  OBJECT-TYPE
            SYNTAX  DisplayString
            ACCESS  read-only
            STATUS  mandatory
            DESCRIPTION
                    "Last Command Issued by the user"
            ::= { wfUserAccessActiveEntry 7 }

        wfUserAccessActiveLastCmdTime  OBJECT-TYPE
            SYNTAX  INTEGER
            ACCESS  read-only
            STATUS  mandatory
            DESCRIPTION
                    "Time last command issued "
            DEFVAL  { 0 }
            ::= { wfUserAccessActiveEntry 8 }

        wfUserAccessActiveLoginTime  OBJECT-TYPE
            SYNTAX  Counter
            ACCESS  read-only
            STATUS  mandatory
            DESCRIPTION
                    "Time user logged in "
            ::= { wfUserAccessActiveEntry 9 }

        wfUserAccessActiveAcctInOctets  OBJECT-TYPE
            SYNTAX  Counter
            ACCESS  read-only
            STATUS  mandatory
            DESCRIPTION
                    "Number of Octets Received "
            ::= { wfUserAccessActiveEntry 10 }

        wfUserAccessActiveAcctOutOctets  OBJECT-TYPE
            SYNTAX  Counter
            ACCESS  read-only
            STATUS  mandatory
            DESCRIPTION
                    "Number of Octets Sent "
            ::= { wfUserAccessActiveEntry 11 }

        wfUserAccessActiveAcctAccessType  OBJECT-TYPE
            SYNTAX  INTEGER {
                    console(1),
                    telnet(2),
		    ftp(3)
                    }
            ACCESS  read-only
            STATUS  mandatory
            DESCRIPTION
                    "Type of login access "
            DEFVAL  { console }
            ::= { wfUserAccessActiveEntry 12 }

        wfUserAccessActiveAcctTermCause  OBJECT-TYPE
            SYNTAX  INTEGER
            ACCESS  read-only
            STATUS  mandatory
            DESCRIPTION
                    "Reason for ACCT session termination "
            DEFVAL  { 0 }
            ::= { wfUserAccessActiveEntry 13}

        wfUserAccessActiveAcctServiceType   OBJECT-TYPE
            SYNTAX  INTEGER
            ACCESS  read-only
            STATUS  mandatory
            DESCRIPTION
                    "Accounting Service Type "
            DEFVAL  { 0 }
            ::= { wfUserAccessActiveEntry 14 }

        wfUserAccessActiveAcctNasPortType  OBJECT-TYPE
            SYNTAX  INTEGER
            ACCESS  read-only
            STATUS  mandatory
            DESCRIPTION
                    "NAS Port type "
            DEFVAL  { 0 }
            ::= { wfUserAccessActiveEntry 15}

        wfUserAccessActiveAcctPriv        OBJECT-TYPE
            SYNTAX  INTEGER
            ACCESS  read-only
            STATUS  mandatory
            DESCRIPTION
                    "Access Privilege for account "
            DEFVAL  { 0 }
            ::= { wfUserAccessActiveEntry 16}


    wfUserAccessGroupTable OBJECT-TYPE
        SYNTAX  SEQUENCE OF WfUserAccessGroupEntry
        ACCESS  not-accessible
        STATUS        mandatory
        DESCRIPTION 
                " Group access table definition"
        ::= { wfUserServicesGroup  4 }

        wfUserAccessGroupEntry OBJECT-TYPE
            SYNTAX  WfUserAccessGroupEntry
            ACCESS  not-accessible
            STATUS  mandatory
            DESCRIPTION
                    "Group Names"
            INDEX { wfUserAccessGroupNumber }
            ::= { wfUserAccessGroupTable 1 }

        WfUserAccessGroupEntry ::= SEQUENCE {
             wfUserAccessGroupDelete
                INTEGER,
             wfUserAccessGroupDisable
                INTEGER,
             wfUserAccessGroupNumber
                INTEGER,
             wfUserAccessGroupName
                DisplayString,
             wfUserAccessGroupPriv
                INTEGER,
             wfUserAccessGroupAudit
                INTEGER
        }

        wfUserAccessGroupDelete OBJECT-TYPE
            SYNTAX  INTEGER {
                    created(1),
                    deleted(2)
                }
            ACCESS  read-write
            STATUS  mandatory
            DESCRIPTION
                    "Indication of create/delete a group record"
            DEFVAL  { created }
            ::= { wfUserAccessGroupEntry 1 }

        wfUserAccessGroupDisable OBJECT-TYPE
            SYNTAX  INTEGER {
                    enabled(1),
                    disabled(2)
                }
            ACCESS  read-write
            STATUS  mandatory
            DESCRIPTION
                    "Enable/disable this group"
            DEFVAL  { enabled }
            ::= { wfUserAccessGroupEntry 2 }

        wfUserAccessGroupNumber OBJECT-TYPE
            SYNTAX  INTEGER 
            ACCESS  read-only
            STATUS  mandatory
            DESCRIPTION
                    "Number of this group"
            ::= { wfUserAccessGroupEntry 3 }

        wfUserAccessGroupName   OBJECT-TYPE
            SYNTAX  DisplayString
            ACCESS  read-write
            STATUS  mandatory
            DESCRIPTION
                    "Name of this group"
            ::= { wfUserAccessGroupEntry 4 }

        wfUserAccessGroupPriv   OBJECT-TYPE
            SYNTAX  INTEGER
            ACCESS  read-write
            STATUS  mandatory
            DESCRIPTION
                    "Bit field of priveledge classes for this group
                     Bit 1 Manager
                     Bit 2 User
		     Bit 3 Operator
                     All others RFU "
           DEFVAL { 2 } 
           ::= { wfUserAccessGroupEntry 5 }

        wfUserAccessGroupAudit   OBJECT-TYPE
            SYNTAX  INTEGER
            ACCESS  read-write
            STATUS  mandatory
            DESCRIPTION
                    "Bit field matching the group priveledge levels indicating
                      what should or should not be logged
                     0 No audit
                     Bit 1 Manager
                     Bit 2 User
		     Bit 3 Operator
                     All bits Anything user typed
                     All others RFU "
           DEFVAL { 2 } 
           ::= { wfUserAccessGroupEntry 6 }


    wfUserAudit  OBJECT IDENTIFIER ::= { wfUserServicesGroup 5 }

    wfUserAuditDelete    OBJECT-TYPE
        SYNTAX  INTEGER {
                    created(1),
                    deleted(2)
                }
        ACCESS  read-write
        STATUS  mandatory
        DESCRIPTION
                "Indication to create or delete Audit record."
        DEFVAL  { created }
        ::= { wfUserAudit 1 }

    wfUserAuditDisable    OBJECT-TYPE
        SYNTAX  INTEGER {
                    enabled(1),
                    disabled(2)
                }
        ACCESS  read-write
        STATUS  mandatory
        DESCRIPTION
                "Indication to enable/disable Audit subsystem."
        DEFVAL  { enabled }
        ::= { wfUserAudit 2 }

    wfUserAuditlevel    OBJECT-TYPE
        SYNTAX  INTEGER 
        ACCESS  read-write
        STATUS  mandatory
        DESCRIPTION
                " A bit field priveledge levels to audit log. This field
                  is global, groups may override this system default
                     0 No audit
                     Bit 1 Manager
                     Bit 2 User
		     Bit 3 Operator
                     All bits Anything user typed
                     All others RFU "
       DEFVAL { 1 } 
       ::= { wfUserAudit 3 }

    wfUserBccLock  OBJECT IDENTIFIER ::= { wfUserServicesGroup 6 }

    wfUserBccLockDelete    OBJECT-TYPE
        SYNTAX  INTEGER {
                    created(1),
                    deleted(2)
                }
        ACCESS  read-write
        STATUS  mandatory
        DESCRIPTION
                "Indication to create or delete BCC lock record."
        DEFVAL  { created }
        ::= { wfUserBccLock 1 }

    wfUserBccLockId OBJECT-TYPE
        SYNTAX  INTEGER
        ACCESS  read-write
        STATUS  mandatory
        DESCRIPTION 
              "Indicates which BCC/TI user has a configuration mode lock"
        DEFVAL  { 0 }
        ::= { wfUserBccLock 2 }

    wfUserBccLockTimer OBJECT-TYPE
        SYNTAX  INTEGER
        ACCESS  read-write
        STATUS  mandatory
        DESCRIPTION 
              "Indicated last time config changed "
        DEFVAL  { 0 }
        ::= { wfUserBccLock 3 }

    wfUserBccLockAddress OBJECT-TYPE
        SYNTAX  INTEGER
        ACCESS  read-write
        STATUS  mandatory
        DESCRIPTION 
              " IP address of the User holding the lock, used to
                access  
                wfUserAccessActiveTable see below"
        DEFVAL  { 0 }
        ::= { wfUserBccLock 4 }

    wfUserBccLockPort OBJECT-TYPE
        SYNTAX  INTEGER
        ACCESS  read-write
        STATUS  mandatory
        DESCRIPTION 
              " IP port of the User holding the lock, used to
                access  
                wfUserAccessActiveTable "
        DEFVAL  { 0 }
        ::= { wfUserBccLock 5 }

    wfUserBccConfig  OBJECT IDENTIFIER ::= { wfUserServicesGroup 7 }

    wfUserBccConfigDelete    OBJECT-TYPE
        SYNTAX  INTEGER {
                    created(1),
                    deleted(2)
                }
        ACCESS  read-write
        STATUS  mandatory
        DESCRIPTION
                "Indication to create or delete BCC configuration record."
        DEFVAL  { created }
        ::= { wfUserBccConfig 1 }

    wfUserBccConfigDefaultShell OBJECT-TYPE
        SYNTAX  INTEGER {
                    enabled(1),
                    disabled(2)
                }
        ACCESS  read-write
        STATUS  mandatory
        DESCRIPTION 
              "Should BCC be started as the default shell, if resources
               are avaliable. if disabled, TI is the default shell"
        DEFVAL  { disabled }
        ::= { wfUserBccConfig 2 }



    END  -- Wellfleet-USER-MIB
