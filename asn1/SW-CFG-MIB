--  =======================================================================
--  File        : sw-cfg.mib
--  Description : Private MIB for Device Layer-2 Configuration
--  By          : Yaron, Sharon, Alon & Alex & Yakov
--  Version     : 0.1  
--  Date        : 
--  =======================================================================
--
--
-- Copyright (c) 1999 NBase-Xyplex.  All Rights Reserved.
--
--
-- Reproduction of this document is authorized on condition that this
-- copyright notice is included.  This NBase-Xyplex SNMP MIB Specification
-- embodies NBase-Xyplex's proprietary intellectual property.  NBase-Xyplex
-- retains all title and ownership in the specification, including any
-- revisions.
--
-- It is NBase-Xyplex's intent to encourage the widespread use of this
-- specification in connection with the management of NBase-Xyplex's
-- products. NBase-Xyplex grants vendor, end-users, and other interested
-- parties a non-exclusive license to use this specification in
-- connection with the management of NBase-Xyplex's products.
--
-- This specification is supplied "AS IS," and NBase-Xyplex makes no
-- warranty, either express or implied, as to the use, operation,
-- condition, or performance of the specification.
--
-- Copyright text courtesy of NBase-Xyplex
--
-- If you have any questions about this MIB, please call NBase-Xyplex
-- Technical Support Center at 1-800-858-7815 from inside USA or
-- 1-818-773-0900 from outside USA.
--
--
-- NBase-Xyplex retains the right to change this MIB without notification.
--

SW-CFG-MIB DEFINITIONS ::= BEGIN

		IMPORTS
				enterprises,
				Counter                         FROM RFC1155-SMI
				IpAddress			FROM RFC1155-SMI
				DisplayString			FROM RFC1213-MIB
				OBJECT-TYPE			FROM RFC-1212
				TRAP-TYPE              		FROM RFC-1215;

		MacAddress ::=  OCTET STRING(SIZE(6))

-- ************************************************************
-- Object Identifier Definition.
-- ************************************************************

nbase              OBJECT IDENTIFIER ::= { enterprises 629 }
nbSwitchG1         OBJECT IDENTIFIER ::= { nbase 1 }
nbSwitchG1Il       OBJECT IDENTIFIER ::= { nbSwitchG1 50}

-- GROUPS for Layer-2 Interface
nbSwitchConfig	   OBJECT IDENTIFIER ::= { nbSwitchG1Il 13}

-- *************************************************************
--  MAC Address Table of the Device.
-- *************************************************************

nbSwMacTable			OBJECT-TYPE
		SYNTAX  SEQUENCE OF NbSwMacEntry
		ACCESS  not-accessible
		STATUS  mandatory
		DESCRIPTION
			"A table that contains Learning Table with fields
			 that does not exsist in dot1dTpFdbTable."
		::= { nbSwitchConfig 5 }
			

nbSwMacEntry    		OBJECT-TYPE
		SYNTAX  NbSwMacEntry
		ACCESS  not-accessible
		STATUS  mandatory
		DESCRIPTION
			"Information about a specific MAC address in the
			 nbSwMacTable."
		INDEX   { nbSwMac, nbSwMacVid}

		::= { nbSwMacTable 1 }

NbSwMacEntry ::= SEQUENCE {
		nbSwMac			MacAddress,
		nbSwMacVid		INTEGER,
		nbSwMacVidx		INTEGER,
		nbSwMacGetViewIndex	INTEGER,
		nbSwMacPort		INTEGER,
		nbSwMacMode		INTEGER,
		nbSwMacTagged		INTEGER,
		nbSwMacStatus		INTEGER
		}
				
nbSwMac            		OBJECT-TYPE
		SYNTAX  MacAddress
	        ACCESS  read-only
	       	STATUS  mandatory
		DESCRIPTION
			"MAC address for which the bridge has
			 forwarding and/or filtering information."
		::= { nbSwMacEntry 1 }

nbSwMacVid         		OBJECT-TYPE
		SYNTAX  INTEGER  (2..4096)
		ACCESS  read-only
	       	STATUS  mandatory
		DESCRIPTION
			"Tag of the entry: the address 'Address recognition'
			 is concatenation of nbSwMac and nbSwMacVid.
			 When ISVP is not implemented or ISVL mode is disabled,
			 this field in SET/NEXT operations may have any value,
			 GET operation should return 0."
		::= { nbSwMacEntry 2 }

nbSwMacVidx        		OBJECT-TYPE
		SYNTAX  INTEGER  (2..4096)
	        ACCESS  read-write
	       	STATUS  mandatory
		DESCRIPTION
			"Outbound VLAN tag: if frame 'Address recognition'
			 was resolved with this entry, the forwarding
			 will be maked according the VLAN with this tag.
			 When ISVP is not implemented or ISVL mode is disabled,
			 this field in SET operations may have any value,
			 GET operation should return 0."
		::= { nbSwMacEntry 3 }
			
nbSwMacGetViewIndex  OBJECT-TYPE
		SYNTAX  INTEGER
	        ACCESS  read-only
	       	STATUS  mandatory
		DESCRIPTION
			"Sequantial index of the entry."
		::= { nbSwMacEntry 4 }

nbSwMacPort        		OBJECT-TYPE
		SYNTAX  INTEGER   (0..65535)
	        ACCESS  read-write
	       	STATUS  mandatory
		DESCRIPTION
			"Port of the entry. '0' value indicates that
			 the port number has not been learned but
			 that the bridge does have some forwarding/filtering
			 information about this address.
			 Another words, the frame will be forwarding
			 'to the CPU only' and the bridge will sovle,
			 what it must be done with this frame."
		::= { nbSwMacEntry 5 }
			
nbSwMacMode        		OBJECT-TYPE
		SYNTAX  INTEGER
		{
		 dynamic (1),
		 static  (2)
		}
	        ACCESS  read-write
	       	STATUS  mandatory
		DESCRIPTION
			"Status of the entry: Only 'dynamic (1)'
			 entries are aged.
			 Note, that when the bridge is to age some dynamic
			 entry in nbSwRunVlansMode=isvpMode (3) case,
			 it must delete all static(2) entres with this MAC."
		::= { nbSwMacEntry 6 }

nbSwMacTagged	   		OBJECT-TYPE
		SYNTAX  INTEGER
		{
		 no  (0),
		 yes (1)
		}
	        ACCESS  read-write
	       	STATUS  mandatory
		DESCRIPTION
			"'Tagged' state of the entry.
			 When ISVP is not implemented or ISVL mode
			 is disabled, this field in SET operations
			 may have any value, GET operation should return 0."
		::= { nbSwMacEntry 7 }

nbSwMacStatus 			OBJECT-TYPE
		SYNTAX  INTEGER
		{
		 valid   (1),
		 invalid (2)
		}
	        ACCESS  read-write
	       	STATUS  mandatory
		DESCRIPTION
			"State of the entry: Only 'valid(1)' entries
			 participate in the forwarding/filtering process.

			The new entry is created when PDU with
			nbSwMacStatus=valid(1), nbSwMac, nbSwMacVid and
			optionally nbSwMacPort (default '0'),
			nbSwMacVidx (default nbSwMacVid) and
			nbSwMacMode (default dynamic (1)) comes.

			If {nbSwMac,nbSwMacVid} exists, the bridge replaces it.
			
			The old entry is deleted when PDU with
			nbSwMacStatus=invalid(2), nbSwMac, nbSwMacVid comes.
			
			The old entry is modified when PDU with
			nbSwMac, nbSwMacVid and new value of fields nbSwMacPort
			and/or nbSwMacVidx and/or nbSwMacMode comes."
		::= { nbSwMacEntry 8 }
        
-- *************************************************************
-- Ports Configuration Group.
-- *************************************************************

nbSwPortCfg	OBJECT IDENTIFIER ::= { nbSwitchConfig 6 }

nbSwPortsMaxNumber 		OBJECT-TYPE
	        SYNTAX  INTEGER
	        ACCESS  read-only
	        STATUS  mandatory
	        DESCRIPTION
			"Maximum number of Switching Ports supported
	                by the system."
        	::= { nbSwPortCfg 1 }

nbSwPortsActualNumber 		OBJECT-TYPE
	        SYNTAX  INTEGER
	        ACCESS  read-only
	        STATUS  mandatory
	        DESCRIPTION
        	        "Actual number of Switching Ports supported
                	by the system."
	        ::= { nbSwPortCfg 2 }

-- *************************************************************
-- Ports Configuration Table of the Device.
-- *************************************************************

nbSwPortTable 			OBJECT-TYPE
		SYNTAX  SEQUENCE OF NbSwPortEntry
	        ACCESS  not-accessible
	        STATUS  mandatory
	        DESCRIPTION
			"A list of the port configuration entries.
			The number of entries is given by nbSwPortsMaxNumber."
	        ::= { nbSwPortCfg 3 }

nbSwPortEntry      		OBJECT-TYPE
	        SYNTAX  NbSwPortEntry
        	ACCESS  not-accessible
	        STATUS  mandatory
        	DESCRIPTION
			"Contains the information necessary to
			configure/describe a port configuration.
			The number of rows/entries is fixed.
			A row/entry may not be created or deleted."
	        INDEX { nbSwPortIndex }

	        ::= { nbSwPortTable 1 }

NbSwPortEntry ::= SEQUENCE {
	        nbSwPortIndex		INTEGER,
	        nbSwPortLanType		INTEGER,
		nbSwPortIfType		INTEGER,
		nbSwPortLink		INTEGER,
		nbSwPortFctrl		INTEGER,
		nbSwPortDplex		INTEGER,
		nbSwPortSpeedSelect	INTEGER,
		nbSwPortSpeed		INTEGER,
		nbSwPortEnable		INTEGER,
		nbSwPortIsvpMode	INTEGER,
		nbSwPortValid		INTEGER
		}

nbSwPortIndex			OBJECT-TYPE
		SYNTAX  INTEGER
	        ACCESS  read-only
	        STATUS  mandatory
	        DESCRIPTION
			"A unique value for each switched port.
			Its value ranges from 1 to the value of
			nbSwPortsMaxNumber. There may be holes in
			the ports sequence."
	        ::= { nbSwPortEntry 1 }

nbSwPortLanType			OBJECT-TYPE
		SYNTAX  INTEGER
		{
                 none         (1), -- no LAN interface installed
                 eth10        (2), -- Ethernet  10Mbps
                 eth100       (3), -- Ethernet 100Mbps
                 eth10-100    (4), -- Ethernet 10/100Mbps
                 eth100B      (5), -- Ethernet 100Mbps Backbone/ISVLAN
                 eth1000B     (6), -- Ethernet 1000Mbps Backbone/ISVLAN
                 atmLane      (7), -- ATM Lan Emulation Module
                 eth100Grp    (8), -- Ethernet 100Mbps Group Switching
		 eth10-100Grp (9), -- Ethernet 10/100Mbps Group Switching
		 fddi         (10) -- FDDI
		}
	        ACCESS  read-only
	        STATUS  mandatory
	        DESCRIPTION
			"The port LAN type
			 that is installed (if any)."
	        ::= { nbSwPortEntry 2 }

nbSwPortIfType  		OBJECT-TYPE
		SYNTAX  INTEGER
		{
                 aui    (1),       -- AUI interface - Ethernet 10 Mbps only
                 tp     (2),       -- TP  interface - 10 or 100 Mbps
                 auiTp  (3),       -- AUI & TP interface - Ethernet 10 Mbps only
                 tpfd   (4),       -- TP Full Duplex capable - 10 or 100 Mbps
                 coax   (5),       -- COAX interface- Ethernet 10 Mbps only
                 foMm   (6),       -- Fiber Optic Multimode  - 10 or 100 Mbps
                 foSm   (7),       -- Fiber Optic Singlemode - 10 or 100 Mbps
		 none   (8),       -- no interface installed - no LAN installed
		 foSxM  (9),       -- Fiber Optic MultiMode  - GigaBit - (WaveLength=850nm,  DistanceLimit= 0-260m)
		 foLxM  (10),      -- Fiber Optic MultiMode  - GigaBit - (WaveLength=1310nm, DistanceLimit= 0-550m)
		 foLxS1 (11),      -- Fiber Optic SingleMode - GigaBit - (WaveLength=1310nm, DistanceLimit= 0-6km)
		 foLxS2 (12),      -- Fiber Optic SingleMode - GigaBit - (WaveLength=1310nm, DistanceLimit= 0-32km)
		 foLxS3 (13),      -- Fiber Optic SingleMode - GigaBit - (WaveLength=1550nm, DistanceLimit= 30-60km)
		 foM    (14),      -- Fiber Optic MultiMode  - FastEthernet,FDDI,ATM - (WaveLength=1310nm, DistanceLimit= 0-2km)
		 foMX   (15),      -- Fiber Optic MultiMode  - FastEthernet          - (WaveLength=1310nm, DistanceLimit= 2-7km)
		 foS1   (16),      -- Fiber Optic SingleMode - FastEthernet,FDDI,ATM - (WaveLength=1310nm, DistanceLimit= 0-25km)
		 foS2   (17),      -- Fiber Optic SingleMode - FastEthernet,FDDI,ATM - (WaveLength=1310nm, DistanceLimit= 25-50km)
		 foS3   (18)       -- Fiber Optic SingleMode - FastEthernet,FDDI,ATM - (WaveLength=1550nm, DistanceLimit= 50-100km)
		}
		ACCESS  read-only
		STATUS  mandatory
		DESCRIPTION
			"The port Physical Interface type
			 that is installed (if any)."
	        ::= { nbSwPortEntry 3 }

nbSwPortLink    		OBJECT-TYPE
		SYNTAX  INTEGER
		{
                 other   (1),      -- non existing/non Ethernet ifs state
                 enable  (2),      -- link is  enabled - for Ethernet if-s only
                 disable (3)       -- link is disabled - for Ethernet if-s only
	        }
	        ACCESS  read-only
        	STATUS  mandatory
	        DESCRIPTION
			"The port Link Integrity status."
        ::= { nbSwPortEntry 5 }

nbSwPortFctrl   		OBJECT-TYPE
		SYNTAX  INTEGER
		{
                 other   (1),
                 enable  (2),      -- enable  flow control
		 disable (3)       -- disable flow control
        	}
	        ACCESS  read-write
        	STATUS  mandatory
	        DESCRIPTION
			"The port Flow Control mode selection:
			 enable (default) or disable."
		DEFVAL { enable }
	        ::= { nbSwPortEntry 6 }

nbSwPortDplex   		OBJECT-TYPE
		SYNTAX  INTEGER
	        {
                 other      (1),
                 halfDuplex (2),
		 fullDuplex (3)
		}
	        ACCESS  read-write
	        STATUS  mandatory
	        DESCRIPTION
			"The port Duplex mode selection:
			 halfDuplex ( default) or fullDuplex."
		DEFVAL { halfDuplex }
        	::= { nbSwPortEntry 7 }

nbSwPortSpeedSelect     	OBJECT-TYPE
		SYNTAX  INTEGER
		{
                 other     (1),
		 autoSense (2),
		 force10   (3),
		 force100  (4),
		 force1000 (5)
		}
	        ACCESS  read-write
	        STATUS  mandatory
	        DESCRIPTION
			"The port Speed Selection mode."
		DEFVAL { autoSense }
	        ::= { nbSwPortEntry 8 }

nbSwPortSpeed   		OBJECT-TYPE
		SYNTAX  INTEGER
	        ACCESS  read-only
	        STATUS  mandatory
	        DESCRIPTION
			"The Ethernet port Real Speed in MBps."
	        ::= { nbSwPortEntry 9 }

nbSwPortEnable  		OBJECT-TYPE
		SYNTAX  INTEGER
		{
                 other       (1),
	 	 portDisable (2),
	 	 portEnable  (3)
	        }
	        ACCESS  read-write
		STATUS  mandatory
	        DESCRIPTION
	                "Port Enable/Disable mode."
		DEFVAL { portEnable }
	        ::= { nbSwPortEntry 10 }


nbSwPortIsvpMode		OBJECT-TYPE
		SYNTAX  INTEGER
		{
                 other   (1),
	 	 access  (2),
	 	 trunk   (3),
		 nonIsvp (4)
		}
		ACCESS  read-write
		STATUS  mandatory
		DESCRIPTION
			"The Inter-Switch Virtual Mode of this port.
			nonIsvp(3) means that the port does not support
			this mode of operation.
			access(1) means the the port is in Access mode.
			trunk(2) means 	the port is in Trunk mode."
		::= { nbSwPortEntry 11 }

nbSwPortValid			OBJECT-TYPE
                SYNTAX  INTEGER
                {
                 valid   (1),
                 broken  (2)
                }
                ACCESS  read-only
                STATUS  mandatory
                DESCRIPTION
                        ""
                ::= { nbSwPortEntry 12 }

-- *************************************************************
-- Ports Ethernet Statistics Table of the Device.
-- *************************************************************

nbSwPortStatTable  		OBJECT-TYPE

		SYNTAX  SEQUENCE OF NbSwPortStatEntry
	        ACCESS  not-accessible
	        STATUS  mandatory
	        DESCRIPTION
			"A list of the ports ethernet statistics entries.
			The number of entries is given by nbSwPortsMaxNumber."

		::= { nbSwitchConfig 7 }

nbSwPortStatEntry  		OBJECT-TYPE
		SYNTAX  NbSwPortStatEntry
        	ACCESS  not-accessible
	        STATUS  mandatory
        	DESCRIPTION
			"Contains the information about the
			Port Ethernet Statistics.
			The number of rows/entries is fixed.
			A row/entry may not be created or deleted."
		INDEX { nbSwPortStatIndex }

		::= { nbSwPortStatTable 1 }

NbSwPortStatEntry ::= SEQUENCE {
		nbSwPortStatIndex		INTEGER,
		nbSwPortStatBtRec		Counter,
		nbSwPortStatFrRec		Counter,
		nbSwPortStatMulticastFrRec	Counter,
		nbSwPortStatBroadcastFrRec	Counter,
		nbSwPortStatUnicastFrRec	Counter,
		nbSwPortStatBtSent		Counter,
		nbSwPortStatFrSent		Counter,
		nbSwPortStatExcessiveCollis	Counter,
		nbSwPortStatSingleCollis	Counter,
		nbSwPortStatMultipleCollis	Counter,
		nbSwPortStatLateCollis		Counter,
		nbSwPortStatAlignmentErrors	Counter,
		nbSwPortStatFCSErrors		Counter,
		nbSwPortStatFrDiscarded		Counter,
		nbSwPortStatBadLongFr		Counter,
		nbSwPortStatGoodLongFr		Counter,
		nbSwPortStatGoodShortFr		Counter,
		nbSwPortStatValid		INTEGER
		}

nbSwPortStatIndex		OBJECT-TYPE
		SYNTAX  INTEGER
	        ACCESS  read-only
	        STATUS  mandatory
	        DESCRIPTION
			"A unique value for each switched port.
			Its value ranges from 1 to the value of
			nbSwPortsMaxNumber. There may be holes in
			the ports sequence."
		::= { nbSwPortStatEntry 1 }

nbSwPortStatBtRec		OBJECT-TYPE
		SYNTAX  Counter
	        ACCESS  read-only
	        STATUS  mandatory
	        DESCRIPTION
			"The total number of Bytes received
			 on the Port."
		::= { nbSwPortStatEntry 2 }

nbSwPortStatFrRec		OBJECT-TYPE
		SYNTAX  Counter
	        ACCESS  read-only
	        STATUS  mandatory
	        DESCRIPTION
			"The total number of Frames received
			 on the Port."
		::= { nbSwPortStatEntry 3 }

nbSwPortStatMulticastFrRec	OBJECT-TYPE
		SYNTAX  Counter
	        ACCESS  read-only
	        STATUS  mandatory
	        DESCRIPTION
			"The number of Multicast Frames received
			 on the Port."
		::= { nbSwPortStatEntry 4 }

nbSwPortStatBroadcastFrRec	OBJECT-TYPE
		SYNTAX  Counter
	        ACCESS  read-only
	        STATUS  mandatory
	        DESCRIPTION
			"The number of Broadcast Frames received
			 on the Port."
		::= { nbSwPortStatEntry 5 }

nbSwPortStatUnicastFrRec	OBJECT-TYPE
		SYNTAX  Counter
	        ACCESS  read-only
	        STATUS  mandatory
	        DESCRIPTION
			"The number of Unicast Frames received
			 on the Port."
		::= { nbSwPortStatEntry 6 }

nbSwPortStatBtSent		OBJECT-TYPE
		SYNTAX  Counter
	        ACCESS  read-only
	        STATUS  mandatory
	        DESCRIPTION
			"The total number of Bytes sent
			 from the Port."
		::= { nbSwPortStatEntry 7 }

nbSwPortStatFrSent		OBJECT-TYPE
		SYNTAX  Counter
	        ACCESS  read-only
	        STATUS  mandatory
	        DESCRIPTION
			"The total number of Frames sent
			 from the Port."
		::= { nbSwPortStatEntry 8 }

nbSwPortStatExcessiveCollis	OBJECT-TYPE
		SYNTAX  Counter
	        ACCESS  read-only
	        STATUS  mandatory
	        DESCRIPTION
			"A number of Frames for which
			 transmission on a particular
			 Port fails due to Excessive
			 Collisions."
		::= { nbSwPortStatEntry 9 }

nbSwPortStatSingleCollis	OBJECT-TYPE
		SYNTAX  Counter
	        ACCESS  read-only
	        STATUS  mandatory
	        DESCRIPTION
			"A number of successfully transmitted
			 Frames on a particular Port for which
			 transmission is inhibited by exactly
			 one Collision."
		::= { nbSwPortStatEntry 10 }

nbSwPortStatMultipleCollis	OBJECT-TYPE
		SYNTAX  Counter
	        ACCESS  read-only
	        STATUS  mandatory
	        DESCRIPTION
			"A number of successfully transmitted
			 Frames on a particular Port for which
			 transmission is inhibited by more than
			 one Collision."
		::= { nbSwPortStatEntry 11 }

nbSwPortStatLateCollis		OBJECT-TYPE
		SYNTAX  Counter
	        ACCESS  read-only
	        STATUS  mandatory
	        DESCRIPTION
			"The number of times that a Collision
			 is detected on a particular Port
			 later than 512 bit-times
			 (51.2 microseconds on a 10 Mbit/s system)
			 into the transmission of a packet."
		::= { nbSwPortStatEntry 12 }

nbSwPortStatAlignmentErrors	OBJECT-TYPE
		SYNTAX  Counter
	        ACCESS  read-only
	        STATUS  mandatory
	        DESCRIPTION
			"A number of Frames received on a
			 particular Port that are not an integral
			 number of Bytes in length and do not pass
			 the FCS check."
		::= { nbSwPortStatEntry 13 }

nbSwPortStatFCSErrors		OBJECT-TYPE
		SYNTAX  Counter
	        ACCESS  read-only
	        STATUS  mandatory
	        DESCRIPTION
			"A number of Frames received on a
			 particular Port that are an integral number
			 of Bytes in length but do not pass
			 the FCS check."
		::= { nbSwPortStatEntry 14 }

nbSwPortStatFrDiscarded		OBJECT-TYPE
		SYNTAX  Counter
	        ACCESS  read-only
	        STATUS  mandatory
	        DESCRIPTION
			"The number of inbound Frames which
			 were chosen to be discarded even
			 though no errors had been detected
			 to prevent their being deliverable to a
			 higher-layer protocol."
		::= { nbSwPortStatEntry 15 }

nbSwPortStatBadLongFr		OBJECT-TYPE
		SYNTAX  Counter
	        ACCESS  read-only
	        STATUS  mandatory
	        DESCRIPTION
			"The total number of Frames received
			 that were longer than 1518 Bytes long and
			 were not an integral number of octets in length
			 or had  a bad Frame Check Sequence (FCS)."
		::= { nbSwPortStatEntry 16 }

nbSwPortStatGoodLongFr		OBJECT-TYPE
		SYNTAX  Counter
	        ACCESS  read-only
	        STATUS  mandatory
	        DESCRIPTION
			"The total number of Frames received
			 that were longer than 1518 Bytes long and
			 were otherwise well formed."
		::= { nbSwPortStatEntry 17 }

nbSwPortStatGoodShortFr		OBJECT-TYPE
		SYNTAX  Counter
	        ACCESS  read-only
	        STATUS  mandatory
	        DESCRIPTION
			"The total number of Frames received
			 that were less than 64 Bytes long and
			 were otherwise well formed."
		::= { nbSwPortStatEntry 18 }

nbSwPortStatValid                   OBJECT-TYPE
                SYNTAX  INTEGER
                {
                 valid   (1),
                 broken  (2)
                }
                ACCESS  read-only
                STATUS  mandatory
                DESCRIPTION
                        ""
                ::= { nbSwPortStatEntry 19 }

END
