UNISYS-TIMEPLEX-MIB DEFINITIONS     ::= BEGIN

IMPORTS 
        mgmt, Counter, Gauge, NetworkAddress, IpAddress, TimeTicks 
			FROM RFC1065-SMI
		PhysAddress, DisplayString  FROM SNMPv2-TC
		enterprises FROM RFC1155-SMI
		OBJECT-TYPE FROM RFC-1212;

unisys-timeplex             OBJECT IDENTIFIER ::= { enterprises 16 }
umgmt                       OBJECT IDENTIFIER ::= { unisys-timeplex 2 }
umib                        OBJECT IDENTIFIER ::= { umgmt 1 }
usystem                     OBJECT IDENTIFIER ::= { umib 1 }
uinterfaces                 OBJECT IDENTIFIER ::= { umib 2 }
uat                         OBJECT IDENTIFIER ::= { umib 3 }
uip                         OBJECT IDENTIFIER ::= { umib 4 }
uicmp                       OBJECT IDENTIFIER ::= { umib 5 }
utcp                        OBJECT IDENTIFIER ::= { umib 6 }
uudp                        OBJECT IDENTIFIER ::= { umib 7 }
uegp                        OBJECT IDENTIFIER ::= { umib 8 }
uggp                        OBJECT IDENTIFIER ::= { umib 12 }
urip                        OBJECT IDENTIFIER ::= { umib 13 }
usnmp                       OBJECT IDENTIFIER ::= { umib 14 }
uhfp                        OBJECT IDENTIFIER ::= { umib 15 }
uddn                        OBJECT IDENTIFIER ::= { umib 16 }
ux25                        OBJECT IDENTIFIER ::= { umib 17 }
ufddi                       OBJECT IDENTIFIER ::= { umib 18 }
ufddiSMT                    OBJECT IDENTIFIER ::= { ufddi 1 }
ufddiSMTStationIdGrp        OBJECT IDENTIFIER ::= { ufddiSMT 1 }
ufddiSMTStationCfgGrp       OBJECT IDENTIFIER ::= { ufddiSMT 2 }
ufddiSMTOperationalGrp      OBJECT IDENTIFIER ::= { ufddiSMT 3 }
ufddiMACTable               OBJECT IDENTIFIER ::= { ufddi 2 }
ufddiMACEntry               OBJECT IDENTIFIER ::= { ufddiMACTable 1 }
ufddiMACAddressGrp          OBJECT IDENTIFIER ::= { ufddiMACEntry 1 }
ufddiMACCfgGrp              OBJECT IDENTIFIER ::= { ufddiMACEntry 2 }
ufddiMACOperGrp             OBJECT IDENTIFIER ::= { ufddiMACEntry 3 }
ufddiMACCountersGrp         OBJECT IDENTIFIER ::= { ufddiMACEntry 4 }
ufddiMACErrorCntrsGrp       OBJECT IDENTIFIER ::= { ufddiMACEntry 5 }
ufddiMACSTATUSGrp           OBJECT IDENTIFIER ::= { ufddiMACEntry 6 }
ufddiPHYTable               OBJECT IDENTIFIER ::= { ufddi 3 }
ufddiPHYEntry               OBJECT IDENTIFIER ::= { ufddiPHYTable 1 }
ufddiPHYCfgGrp              OBJECT IDENTIFIER ::= { ufddiPHYEntry 1 }
tlip                        OBJECT IDENTIFIER ::= { umib 19 }
tl1mib                      OBJECT IDENTIFIER ::= { umgmt 2 }
tl1system                   OBJECT IDENTIFIER ::= { tl1mib 1 }
tl1interfaces               OBJECT IDENTIFIER ::= { tl1mib 2 }
tl1at                       OBJECT IDENTIFIER ::= { tl1mib 3 }
tl1ip                       OBJECT IDENTIFIER ::= { tl1mib 4 }
tl1icmp                     OBJECT IDENTIFIER ::= { tl1mib 5 }
tl1tcp                      OBJECT IDENTIFIER ::= { tl1mib 6 }
tl1udp                      OBJECT IDENTIFIER ::= { tl1mib 7 }
tl1egp                      OBJECT IDENTIFIER ::= { tl1mib 8 }
tl1snmp                     OBJECT IDENTIFIER ::= { tl1mib 11 }
tl1bre                      OBJECT IDENTIFIER ::= { tl1mib 12 }
tl1breConfigParams          OBJECT IDENTIFIER ::= { tl1bre 1 }
tl1rip                      OBJECT IDENTIFIER ::= { tl1mib 13 }
tl1x25                      OBJECT IDENTIFIER ::= { tl1mib 14 }
tl1fddi                     OBJECT IDENTIFIER ::= { tl1mib 15 }
tl1stap                     OBJECT IDENTIFIER ::= { tl1mib 16 }
tl1stapBridgeConfig         OBJECT IDENTIFIER ::= { tl1stap 1 }
tl1stapBridgeState          OBJECT IDENTIFIER ::= { tl1stap 3 }
tl1idp                      OBJECT IDENTIFIER ::= { tl1mib 17 }
tl1ppp                      OBJECT IDENTIFIER ::= { tl1mib 18 }
tl1srtb                     OBJECT IDENTIFIER ::= { tl1mib 19 }
tl1srtbFilterDbParams       OBJECT IDENTIFIER ::= { tl1srtb 6 }
tl1srtbStaticFilterDbParams OBJECT IDENTIFIER ::= { tl1srtb 8 }
tl1srtbMaskAcfInfo          OBJECT IDENTIFIER ::= { tl1srtb 11 }
tl1ospf                     OBJECT IDENTIFIER ::= { tl1mib 20 }
tl1tok                      OBJECT IDENTIFIER ::= { tl1mib 21 }


usystemAction OBJECT-TYPE
   SYNTAX  INTEGER {
	normal(0),
        reset(1),
        shutdown(2)
   }
   ACCESS  read-write
   STATUS  mandatory
   ::= { usystem 1 }

usystemReboots OBJECT-TYPE
   SYNTAX  INTEGER
   ACCESS  read-only
   STATUS  mandatory
   ::= { usystem 2 }

usystemErrorCode OBJECT-TYPE
   SYNTAX  INTEGER
   ACCESS  read-only
   STATUS  mandatory
   ::= { usystem 3 }

uifTable OBJECT-TYPE
   SYNTAX  SEQUENCE OF UifEntry
   ACCESS  read-write
   STATUS  mandatory
   ::= { uinterfaces 1 }

uifEntry OBJECT-TYPE
   SYNTAX  UifEntry
   ACCESS  read-write
   STATUS  mandatory
   ::= { uifTable 1 }

UifEntry ::= SEQUENCE {
	uifEthernetArpWait
                INTEGER,
        uifIpAddr
                IpAddress,
        uifSubnetMask
                NetworkAddress,
        uifHdlcBaudRate
                INTEGER,
        uifHdlcRto
                INTEGER,
        uifHdlcAckTo
                INTEGER,
        uifHdlcSabmInterval
                INTEGER,
        uifHdlcRnrInterval
                INTEGER,
        uifHdlcClockType 
                INTEGER,
        uifHdlcDCE 
                INTEGER,
        uifHdlcThrowaway
                INTEGER,
        uifHdlcAckCount 
                INTEGER,
	uifFddiArpWait
                INTEGER
   }

uifEthernetArpWait OBJECT-TYPE
   SYNTAX  INTEGER (1..65535)
   ACCESS  read-write
   STATUS  mandatory
   ::= { uifEntry 1 }


uifIpAddr OBJECT-TYPE
   SYNTAX  IpAddress
   ACCESS  read-write
   STATUS  mandatory
   ::= { uifEntry 2 }

uifSubnetMask OBJECT-TYPE
   SYNTAX  NetworkAddress
   ACCESS  read-write
   STATUS  mandatory
   ::= { uifEntry 3 }

uifHdlcBaudRate OBJECT-TYPE
   SYNTAX  INTEGER (0..16384)
   ACCESS  read-write
   STATUS  mandatory
   ::= { uifEntry 4 }

uifHdlcRto OBJECT-TYPE
   SYNTAX  INTEGER (1..16384)
   ACCESS  read-write
   STATUS  mandatory
   ::= { uifEntry 5 }

uifHdlcAckTo OBJECT-TYPE
   SYNTAX  INTEGER (1..16384) 
   ACCESS  read-write
   STATUS  mandatory
   ::= { uifEntry 6 }

uifHdlcSabmInterval OBJECT-TYPE
   SYNTAX  INTEGER (1..16384)
   ACCESS  read-write
   STATUS  mandatory
   ::= { uifEntry 7 }

uifHdlcRnrInterval OBJECT-TYPE
   SYNTAX  INTEGER (1..16384)
   ACCESS  read-write
   STATUS  mandatory
   ::= { uifEntry 8 }

uifHdlcClockType OBJECT-TYPE
   SYNTAX  INTEGER {
         dte-accepts-tx-and-rx-clocks(3),
         dce-generates-tx-and-rx-clocks(4)
   }
   ACCESS  read-write
   STATUS  mandatory
   ::= { uifEntry 9 }

uifHdlcDCE OBJECT-TYPE
   SYNTAX  INTEGER 
   ACCESS  read-write
   STATUS  mandatory
   ::= { uifEntry 10 }

uifHdlcThrowaway OBJECT-TYPE
   SYNTAX  INTEGER 
   ACCESS  read-write
   STATUS  mandatory
   ::= { uifEntry 11 }

uifHdlcAckCount OBJECT-TYPE
   SYNTAX  INTEGER (1..255)
   ACCESS  read-write
   STATUS  mandatory
   ::= { uifEntry 12 }

uifFddiArpWait OBJECT-TYPE
   SYNTAX  INTEGER (1..255)
   ACCESS  read-write
   STATUS  mandatory
   ::= { uifEntry 13 }

uipLogicalDisconnect OBJECT-TYPE
   SYNTAX  INTEGER 
   ACCESS  read-write
   STATUS  mandatory
   ::= { uip 1 }

uipLoopback OBJECT-TYPE
   SYNTAX  INTEGER 
   ACCESS  read-write
   STATUS  mandatory
   ::= { uip 2 }

uipRemoteg1 OBJECT-TYPE
   SYNTAX  INTEGER 
   ACCESS  read-write
   STATUS  mandatory
   ::= { uip 3 }

uipRemoteg2 OBJECT-TYPE
   SYNTAX  INTEGER 
   ACCESS  read-write
   STATUS  mandatory
   ::= { uip 4 }

uipNet1MaxPkt OBJECT-TYPE
   SYNTAX  INTEGER (65..65535)
   ACCESS  read-write
   STATUS  mandatory
   ::= { uip 5 }

uipNet2MaxPkt OBJECT-TYPE
   SYNTAX  INTEGER (65..65535)
   ACCESS  read-write
   STATUS  mandatory
   ::= { uip 6 }

uipRedirectTo OBJECT-TYPE
   SYNTAX  INTEGER (1..65535)
   ACCESS  read-write     
   STATUS  mandatory
   ::= { uip 7 }

uipMasker OBJECT-TYPE
   SYNTAX  INTEGER 
   ACCESS  read-write
   STATUS  mandatory
   ::= { uip 8 }

uipWellKnownGateway OBJECT-TYPE
   SYNTAX  IpAddress
   ACCESS  read-write
   STATUS  mandatory
   ::= { uip 9 }

uipMaxRoutePids OBJECT-TYPE
   SYNTAX  INTEGER
   ACCESS  read-only
   STATUS  mandatory
   ::= { uip 10 }

uipRoutePidsTable OBJECT-TYPE
   SYNTAX  SEQUENCE OF UipRoutePidsEntry
   ACCESS  read-write
   STATUS  mandatory
   ::= { uip 11 }

uipRoutePidsEntry OBJECT-TYPE
   SYNTAX  UipRoutePidsEntry
   ACCESS  read-write
   STATUS  mandatory
   ::= { uipRoutePidsTable 1 }

UipRoutePidsEntry ::= SEQUENCE {
	uipRoutePid
        	INTEGER 
   }

uipRoutePid OBJECT-TYPE
   SYNTAX  INTEGER {
        gateway-to-gateway-protocol(3),
        routing-information-protocol(7),
	exterior-gateway-protocol(8),
	internet-protocol(1)
   }
   ACCESS  read-write
   STATUS  mandatory
   ::= { uipRoutePidsEntry 1 }

uipNbrStaticRoutes OBJECT-TYPE
   SYNTAX  INTEGER
   ACCESS  read-only
   STATUS  mandatory
   ::= { uip 12 }

uipStaticRouteTable OBJECT-TYPE
   SYNTAX  SEQUENCE OF UipStaticRouteEntry
   ACCESS  read-write
   STATUS  mandatory
   ::= { uip 13 }

uipStaticRouteEntry OBJECT-TYPE
   SYNTAX  UipStaticRouteEntry
   ACCESS  read-write
   STATUS  mandatory
   ::= { uipStaticRouteTable 1 }

UipStaticRouteEntry ::= SEQUENCE {
        uipStaticRouteNetwork
       	        NetworkAddress,
	uipStaticRouteGateway
        	IpAddress,
        uipStaticRouteCost
	        INTEGER,
        uipStaticRouteOverride
	        INTEGER,
        uipStaticRouteMask
        	IpAddress
   }

uipStaticRouteNetwork OBJECT-TYPE
   SYNTAX  NetworkAddress
   ACCESS  read-only
   STATUS  mandatory
   ::= { uipStaticRouteEntry 1 }

uipStaticRouteGateway OBJECT-TYPE
   SYNTAX  IpAddress
   ACCESS  read-write
   STATUS  mandatory
   ::= { uipStaticRouteEntry 2 }

uipStaticRouteCost OBJECT-TYPE
   SYNTAX  INTEGER (0..255)
   ACCESS  read-write
   STATUS  mandatory
   ::= { uipStaticRouteEntry 3 }

uipStaticRouteOverride OBJECT-TYPE
   SYNTAX  INTEGER 
   ACCESS  read-write
   STATUS  mandatory
   ::= { uipStaticRouteEntry 4 }

utcpRetransTo OBJECT-TYPE
   SYNTAX  INTEGER (1..65535)
   ACCESS  read-write
   STATUS  mandatory
   ::= { utcp 1 }

utcpRtoMin OBJECT-TYPE
   SYNTAX  INTEGER (1..65535)
   ACCESS  read-write
   STATUS  mandatory
   ::= { utcp 2 }

utcpRtoMax OBJECT-TYPE
   SYNTAX  INTEGER (1..65635)
   ACCESS  read-write
   STATUS  mandatory
   ::= { utcp 3 }

utcpWakeup OBJECT-TYPE
   SYNTAX  INTEGER (1..16384)
   ACCESS  read-write
   STATUS  mandatory
   ::= { utcp 4 }

utcpAckTime OBJECT-TYPE
   SYNTAX  INTEGER (1..16384)
   ACCESS  read-write
   STATUS  mandatory
   ::= { utcp 5 }

utcpTimeToLive OBJECT-TYPE
   SYNTAX  INTEGER (1..255)
   ACCESS  read-write
   STATUS  mandatory
   ::= { utcp 6 }

utcpThruput OBJECT-TYPE
   SYNTAX  INTEGER (1..255)
   ACCESS  read-write
   STATUS  mandatory
   ::= { utcp 7 }

utcpFlowAck OBJECT-TYPE
   SYNTAX  INTEGER -- (1..utcpThruput)
   ACCESS  read-write
   STATUS  mandatory
   ::= { utcp 8 }

uegpMaxNeighbors OBJECT-TYPE
   SYNTAX  INTEGER
   ACCESS  read-only
   STATUS  mandatory
   ::= { uegp 1 }

uegpNumberTrustedNeighbors OBJECT-TYPE
   SYNTAX  INTEGER -- (0..uegpMaxNeighbors)
   ACCESS  read-write
   STATUS  mandatory
   ::= { uegp 2 }

uegpNumberNeighbors OBJECT-TYPE
   SYNTAX  INTEGER -- (0..uegpNumberTrustedNeighbors)
   ACCESS  read-write
   STATUS  mandatory
   ::= { uegp 3 }

uegpNeighborTable OBJECT-TYPE
   SYNTAX  SEQUENCE OF UegpNeighborEntry
   ACCESS  read-write
   STATUS  mandatory
   ::= { uegp 4 }

uegpNeighborEntry OBJECT-TYPE
   SYNTAX  UegpNeighborEntry
   ACCESS  read-write
   STATUS  mandatory
   ::= { uegpNeighborTable 1 }

UegpNeighborEntry ::= SEQUENCE {
        uegpNeighbor
	        IpAddress
   }

uegpNeighbor OBJECT-TYPE
   SYNTAX  IpAddress
   ACCESS  read-write
   STATUS  mandatory
   ::= { uegpNeighborEntry 1 }

uegpAutoSysNumber OBJECT-TYPE
   SYNTAX  INTEGER (0..65535)
   ACCESS  read-write
   STATUS  mandatory
   ::= { uegp 5 }

uegpMinHelloInterval OBJECT-TYPE
   SYNTAX  INTEGER (15..65535)
   ACCESS  read-write
   STATUS  mandatory
   ::= { uegp 6 }

uegpMinPollInterval OBJECT-TYPE
   SYNTAX  INTEGER (30..65535)
   ACCESS  read-write
   STATUS  mandatory
   ::= { uegp 7 }

uegpRequestCeaseInterval OBJECT-TYPE
   SYNTAX  INTEGER (15..65535)
   ACCESS  read-write
   STATUS  mandatory
   ::= { uegp 8 }

uegpDeclareDownInterval OBJECT-TYPE
   SYNTAX  INTEGER (1800..65535)
   ACCESS  read-write
   STATUS  mandatory
   ::= { uegp 9 }

uegpAcquireCeaseInterval OBJECT-TYPE
   SYNTAX  INTEGER (30..240)
   ACCESS  read-write
   STATUS  mandatory
   ::= { uegp 10 }

uegpEnoughInterval OBJECT-TYPE
   SYNTAX  INTEGER (60..65535)
   ACCESS  read-write
   STATUS  mandatory
   ::= { uegp 11 }

uegpPurgeInterval OBJECT-TYPE
   SYNTAX  INTEGER (0..600)
   ACCESS  read-write
   STATUS  mandatory
   ::= { uegp 12 }

uegpMode OBJECT-TYPE
   SYNTAX  INTEGER {
        both-active-and-passive(0),
        active(1),
        passive(2)
   }
   ACCESS  read-write
   STATUS  mandatory
   ::= { uegp 13 }

uegpErrorTreatment OBJECT-TYPE
   SYNTAX  INTEGER (0..255) 
   ACCESS  read-write
   STATUS  mandatory
   ::= { uegp 14 }

uegpSharedNetwork OBJECT-TYPE
   SYNTAX  IpAddress
   ACCESS  read-write
   STATUS  mandatory
   ::= { uegp 15 }

uggpEchoInterval OBJECT-TYPE
   SYNTAX  INTEGER (1..65535)
   ACCESS  read-write
   STATUS  mandatory
   ::= { uggp 1 }

uggpMaxNeighbors OBJECT-TYPE
   SYNTAX  INTEGER
   ACCESS  read-only
   STATUS  mandatory
   ::= { uggp 2 }

uggpNumberNeighbors OBJECT-TYPE
   SYNTAX  INTEGER -- (0..uggpMaxNeighbors)
   ACCESS  read-only
   STATUS  mandatory
   ::= { uggp 3 }

uggpNeighborTable OBJECT-TYPE
   SYNTAX  SEQUENCE OF UggpNeighborEntry
   ACCESS  read-write
   STATUS  mandatory
   ::= { uggp 4 }

uggpNeighborEntry OBJECT-TYPE
   SYNTAX  UggpNeighborEntry
   ACCESS  read-write
   STATUS  mandatory
   ::= { uggpNeighborTable 1 }

UggpNeighborEntry ::= SEQUENCE {
        uggpNeighbor
	        IpAddress 
   }

uggpNeighbor OBJECT-TYPE
   SYNTAX  IpAddress
   ACCESS  read-write
   STATUS  mandatory
   ::= { uggpNeighborEntry 1 }

 usnmpVersion OBJECT-TYPE
   SYNTAX  INTEGER
   ACCESS  read-only
   STATUS  mandatory
   ::= { usnmp 1 }

usnmpCommunity OBJECT-TYPE
   SYNTAX  OCTET STRING
   ACCESS  read-write
   STATUS  mandatory
   ::= { usnmp 2 }

usnmpRequests OBJECT-TYPE
   SYNTAX  Counter
   ACCESS  read-only
   STATUS  mandatory
   ::= { usnmp 3 }

usnmpTraps OBJECT-TYPE
   SYNTAX  Counter
   ACCESS  read-only
   STATUS  mandatory
   ::= { usnmp 4 }

usnmpForwardTraps OBJECT-TYPE
   SYNTAX  INTEGER 
   ACCESS  read-write
   STATUS  mandatory
   ::= { usnmp 5 }

uhfpMaxMsg OBJECT-TYPE
   SYNTAX  INTEGER (9..1420)
   ACCESS  read-write
   STATUS  mandatory
   ::= { uhfp 1 }

uhfpPad OBJECT-TYPE
   SYNTAX  INTEGER (0..6)
   ACCESS  read-write
   STATUS  mandatory
   ::= { uhfp 2 }

uhfpSwap OBJECT-TYPE
   SYNTAX  INTEGER 
   ACCESS  read-write
   STATUS  mandatory
   ::= { uhfp 3 }

uddnTimeout OBJECT-TYPE
   SYNTAX  INTEGER (1..65535)
   ACCESS  read-write
   STATUS  mandatory
   ::= { uddn 1 }

uddnMsgout OBJECT-TYPE
   SYNTAX  INTEGER (1..8)
   ACCESS  read-write
   STATUS  mandatory
   ::= { uddn 2 }

uddnHipUp OBJECT-TYPE
   SYNTAX  INTEGER 
   ACCESS  read-only
   STATUS  mandatory
   ::= { uddn 3 }

uddnHdhUp OBJECT-TYPE
   SYNTAX  INTEGER 
   ACCESS  read-only
   STATUS  mandatory
   ::= { uddn 4 }

uddnLinkUp OBJECT-TYPE
   SYNTAX  INTEGER 
   ACCESS  read-only
   STATUS  mandatory
   ::= { uddn 5 }

uddnTotalQ OBJECT-TYPE
   SYNTAX  Gauge
   ACCESS  read-only
   STATUS  mandatory
   ::= { uddn 6 }

uddnConnections OBJECT-TYPE
   SYNTAX  Gauge
   ACCESS  read-only
   STATUS  mandatory
   ::= { uddn 7 }

uddnLinkDownTo OBJECT-TYPE
   SYNTAX  INTEGER  
   ACCESS  read-only
   STATUS  mandatory
   ::= { uddn 8 }

uddnRcvIncomplete OBJECT-TYPE
   SYNTAX  Counter
   ACCESS  read-only
   STATUS  mandatory
   ::= { uddn 9 }

uddnConnectionsReused OBJECT-TYPE
   SYNTAX  Counter
   ACCESS  read-only
   STATUS  mandatory
   ::= { uddn 10 }

uddnHdhWentDown OBJECT-TYPE
   SYNTAX  Counter
   ACCESS  read-only
   STATUS  mandatory
   ::= { uddn 11 }

uddnLinkWentDown OBJECT-TYPE
   SYNTAX  Counter
   ACCESS  read-only
   STATUS  mandatory
   ::= { uddn 12 }

uddnLeaderErrs OBJECT-TYPE
   SYNTAX  Counter
   ACCESS  read-only
   STATUS  mandatory
   ::= { uddn 13 }

uddnPSNGoingDown OBJECT-TYPE
   SYNTAX  Counter
   ACCESS  read-only
   STATUS  mandatory
   ::= { uddn 14 }

uddnDeadHostSTATUS OBJECT-TYPE
   SYNTAX  Counter
   ACCESS  read-only
   STATUS  mandatory
   ::= { uddn 15 }

uddnIfReset OBJECT-TYPE
   SYNTAX  Counter
   ACCESS  read-only
   STATUS  mandatory
   ::= { uddn 16 }

ux25IfTable OBJECT-TYPE
   SYNTAX  SEQUENCE OF Ux25IfEntry
   ACCESS  read-write
   STATUS  mandatory
   ::= { ux25 1 }

ux25IfEntry OBJECT-TYPE
   SYNTAX  Ux25IfEntry
   ACCESS  read-write
   STATUS  mandatory
   ::= { ux25IfTable 1 }

Ux25IfEntry ::= SEQUENCE {
        ux25Service
                INTEGER,
        ux25Window
                INTEGER,
        ux25PktSize
                INTEGER
   }

ux25Service OBJECT-TYPE
   SYNTAX  INTEGER {
	basic-service(0),
	standard-service(7)
   }
   ACCESS  read-write
   STATUS  mandatory
   ::= { ux25IfEntry 1 }

ux25Window OBJECT-TYPE
   SYNTAX  INTEGER (2..7)
   ACCESS  read-write
   STATUS  mandatory
   ::= { ux25IfEntry 2 }

ux25PktSize OBJECT-TYPE
   SYNTAX  INTEGER (7..11) 
   ACCESS  read-write
   STATUS  mandatory
   ::= { ux25IfEntry 3 }

ufddiSMTStationId OBJECT-TYPE
   SYNTAX  OCTET STRING
   ACCESS  read-only
   STATUS  mandatory
   ::= { ufddiSMTStationIdGrp 1 }

ufddiSMTStationType OBJECT-TYPE
   SYNTAX  INTEGER {
	station(1),
	concentrator(2)
   }
   ACCESS  read-only
   STATUS  mandatory
   ::= { ufddiSMTStationIdGrp 2 }

ufddiSMTVersionId OBJECT-TYPE
   SYNTAX  INTEGER
   ACCESS  read-only
   STATUS  mandatory
   ::= { ufddiSMTStationIdGrp 3 }

ufddiSMTMACCount OBJECT-TYPE
   SYNTAX  INTEGER
   ACCESS  read-only
   STATUS  mandatory
   ::= { ufddiSMTStationCfgGrp 1 }

ufddiSMTAttachCount OBJECT-TYPE
   SYNTAX  INTEGER
   ACCESS  read-only
   STATUS  mandatory
   ::= { ufddiSMTStationCfgGrp 2 }

ufddiSMTSpurCount OBJECT-TYPE
   SYNTAX  INTEGER
   ACCESS  read-only
   STATUS  mandatory
   ::= { ufddiSMTStationCfgGrp 3 }

ufddiSMTDasScmState OBJECT-TYPE
   SYNTAX  INTEGER {
        isolated(1),
        wrap-a(2),
        wrap-b(3),
        thru(4)
   }
   ACCESS  read-only
   STATUS  mandatory
   ::= { ufddiSMTOperationalGrp 1 }

ufddiMACSMTLongAddr OBJECT-TYPE
   SYNTAX  OCTET STRING (SIZE (6))
   ACCESS  read-write
   STATUS  mandatory
   ::= { ufddiMACAddressGrp 1 }

ufddiMACShortGrpAddr OBJECT-TYPE
   SYNTAX  OCTET STRING (SIZE (2))
   ACCESS  read-write
   STATUS  mandatory
   ::= { ufddiMACAddressGrp 2 }

ufddiMACUpstreamNeighbor OBJECT-TYPE
   SYNTAX  OCTET STRING
   ACCESS  read-only
   STATUS  mandatory
   ::= { ufddiMACCfgGrp 1 }

ufddiMACDownstreamNeighbor OBJECT-TYPE
   SYNTAX  OCTET STRING
   ACCESS  read-only
   STATUS  mandatory
   ::= { ufddiMACCfgGrp 2 }

ufddiMACResourceIndex OBJECT-TYPE
   SYNTAX  INTEGER
   ACCESS  read-only
   STATUS  mandatory
   ::= { ufddiMACCfgGrp 3 }

ufddiMACConnectedResId OBJECT-TYPE
   SYNTAX  INTEGER
   ACCESS  read-only
   STATUS  mandatory
   ::= { ufddiMACCfgGrp 4 }

ufddiMACTReq OBJECT-TYPE
   SYNTAX  INTEGER -- (ufddiMACTMin..ufddiMACTMax)
   ACCESS  read-write
   STATUS  mandatory
   ::= { ufddiMACOperGrp 1 }

ufddiMACTMax OBJECT-TYPE
   SYNTAX  INTEGER -- (ufddiMACTMin..335540)
   ACCESS  read-write
   STATUS  mandatory
   ::= { ufddiMACOperGrp 2 }

ufddiMACTvxValue OBJECT-TYPE
   SYNTAX  INTEGER (1..5000)
   ACCESS  read-write
   STATUS  mandatory
   ::= { ufddiMACOperGrp 3 }

ufddiMACTMin OBJECT-TYPE
   SYNTAX  INTEGER -- (4000..ufddiMACTMax)
   ACCESS  read-write
   STATUS  mandatory
   ::= { ufddiMACOperGrp 4 }

ufddiMACReceiveCt OBJECT-TYPE
   SYNTAX  Counter
   ACCESS  read-only
   STATUS  mandatory
   ::= { ufddiMACCountersGrp 1 }

ufddiMACTransmitCt OBJECT-TYPE
   SYNTAX  Counter
   ACCESS  read-only
   STATUS  mandatory
   ::= { ufddiMACCountersGrp 2 }

ufddiMACTokenCt OBJECT-TYPE
   SYNTAX  Counter
   ACCESS  read-only
   STATUS  mandatory
   ::= { ufddiMACCountersGrp 3 }

ufddiMACTvxExpiredCt OBJECT-TYPE
   SYNTAX  Counter
   ACCESS  read-only
   STATUS  mandatory
   ::= { ufddiMACErrorCntrsGrp 1 }

ufddiMACNotCopiedCt OBJECT-TYPE
   SYNTAX  Counter
   ACCESS  read-only
   STATUS  mandatory
   ::= { ufddiMACErrorCntrsGrp 2 }

ufddiMACLateCt OBJECT-TYPE
   SYNTAX  Counter
   ACCESS  read-only
   STATUS  mandatory
   ::= { ufddiMACErrorCntrsGrp 3 }

ufddiMACReceiveOverflowCt OBJECT-TYPE
   SYNTAX  Counter
   ACCESS  read-only
   STATUS  mandatory
   ::= { ufddiMACErrorCntrsGrp 4 }

ufddiMACRingOpCt OBJECT-TYPE
   SYNTAX  Counter
   ACCESS  read-only
   STATUS  mandatory
   ::= { ufddiMACSTATUSGrp 1 }

ufddiMACEnteredBeaconCt OBJECT-TYPE
   SYNTAX  Counter
   ACCESS  read-only
   STATUS  mandatory
   ::= { ufddiMACSTATUSGrp 2 }

ufddiPHYType OBJECT-TYPE
   SYNTAX  INTEGER {
	a(1),
	b(2),
	m(3),
	s(4)
   }
   ACCESS  read-only
   STATUS  mandatory
   ::= { ufddiPHYCfgGrp 1 }

ufddiPHYConnectState OBJECT-TYPE
   SYNTAX  INTEGER {
	disabled(1),
	connecting(2),
	standby(3),
	active(4)
   }
   ACCESS  read-only
   STATUS  mandatory
   ::= { ufddiPHYCfgGrp 2 }

ufddiPHYRemotePHYType OBJECT-TYPE
   SYNTAX  INTEGER {
	a(1),
	b(2),
	m(3),
	s(4),
	unknown(5)
   }
   ACCESS  read-only
   STATUS  mandatory
   ::= { ufddiPHYCfgGrp 3 }

ufddiPHYRemoteMACIndicated OBJECT-TYPE
   SYNTAX  INTEGER 
   ACCESS  read-only
   STATUS  mandatory
   ::= { ufddiPHYCfgGrp 4 }

ufddiPHYResourceIndex OBJECT-TYPE
   SYNTAX  INTEGER
   ACCESS  read-only
   STATUS  mandatory
   ::= { ufddiPHYCfgGrp 5 }

ufddiPHYConnectedResId OBJECT-TYPE
   SYNTAX  INTEGER
   ACCESS  read-only
   STATUS  mandatory
   ::= { ufddiPHYCfgGrp 6 }

ufddiPHYAction OBJECT-TYPE
   SYNTAX  INTEGER {
	enabled(0),
	disabled(1)
   }
   ACCESS  read-write
   STATUS  mandatory
   ::= { ufddiPHYEntry 2 }

tlipLogicalDisconnect OBJECT-TYPE
   SYNTAX  INTEGER 
   ACCESS  read-write
   STATUS  mandatory
   ::= { tlip 1 }

tlipLoopback OBJECT-TYPE
   SYNTAX  INTEGER 
   ACCESS  read-write
   STATUS  mandatory
   ::= { tlip 2 }

tlipRedirectTo OBJECT-TYPE
   SYNTAX  INTEGER (1..65535)
   ACCESS  read-write     
   STATUS  mandatory
   ::= { tlip 3 }

tlipMasker OBJECT-TYPE
   SYNTAX  INTEGER 
   ACCESS  read-write
   STATUS  mandatory
   ::= { tlip 4 }

tlipWellKnownGateway OBJECT-TYPE
   SYNTAX  IpAddress
   ACCESS  read-write
   STATUS  mandatory
   ::= { tlip 5 }

tlipMaxRoutePids OBJECT-TYPE
   SYNTAX  INTEGER
   ACCESS  read-only
   STATUS  mandatory
   ::= { tlip 6 }

tlipRoutePidsTable OBJECT-TYPE
   SYNTAX  SEQUENCE OF TlipRoutePidsEntry
   ACCESS  read-write
   STATUS  mandatory
   ::= { tlip 7 }

tlipRoutePidsEntry OBJECT-TYPE
   SYNTAX  TlipRoutePidsEntry
   ACCESS  read-write
   STATUS  mandatory
   ::= { tlipRoutePidsTable 1 }

TlipRoutePidsEntry ::= SEQUENCE {
	tlipRoutePid
        	INTEGER 
   }

tlipRoutePid OBJECT-TYPE
   SYNTAX  INTEGER {
        gateway-to-gateway-protocol(3),
        routing-information-protocol(7),
	exterior-gateway-protocol(8),
	internet-protocol(1)
   }
   ACCESS  read-write
   STATUS  mandatory
   ::= { tlipRoutePidsEntry 1 }

tlipNbrStaticRoutes OBJECT-TYPE
   SYNTAX  INTEGER
   ACCESS  read-only
   STATUS  mandatory
   ::= { tlip 8 }

tlipStaticRouteTable OBJECT-TYPE
   SYNTAX  SEQUENCE OF TlipStaticRouteEntry
   ACCESS  read-write
   STATUS  mandatory
   ::= { tlip 9 }

tlipStaticRouteEntry OBJECT-TYPE
   SYNTAX  TlipStaticRouteEntry
   ACCESS  read-write
   STATUS  mandatory
   ::= { tlipStaticRouteTable 1 }

TlipStaticRouteEntry ::= SEQUENCE {
        tlipStaticRouteNetwork
       	        NetworkAddress,
	tlipStaticRouteGateway
        	IpAddress,
        tlipStaticRouteCost
	        INTEGER,
        tlipStaticRouteOverride
	        INTEGER
   }

tlipStaticRouteNetwork OBJECT-TYPE
   SYNTAX  NetworkAddress
   ACCESS  read-only
   STATUS  mandatory
   ::= { tlipStaticRouteEntry 1 }

tlipStaticRouteGateway OBJECT-TYPE
   SYNTAX  IpAddress
   ACCESS  read-write
   STATUS  mandatory
   ::= { tlipStaticRouteEntry 2 }

tlipStaticRouteCost OBJECT-TYPE
   SYNTAX  INTEGER (0..255)
   ACCESS  read-write
   STATUS  mandatory
   ::= { tlipStaticRouteEntry 3 }

tlipStaticRouteOverride OBJECT-TYPE
   SYNTAX  INTEGER 
   ACCESS  read-write
   STATUS  mandatory
   ::= { tlipStaticRouteEntry 4 }

tlipRemotegTable OBJECT-TYPE
   SYNTAX  SEQUENCE OF TlipRemotegEntry
   ACCESS  read-write
   STATUS  mandatory
   ::= { tlip 10 }

tlipRemotegEntry OBJECT-TYPE
   SYNTAX  TlipRemotegEntry
   ACCESS  read-write
   STATUS  mandatory
   ::= { tlipRemotegTable 1 }

TlipRemotegEntry ::= SEQUENCE {
	tlipRemoteg
        	INTEGER 
   }

tlipRemoteg OBJECT-TYPE
   SYNTAX  INTEGER 
   ACCESS  read-write
   STATUS  mandatory
   ::= { tlipRemotegEntry 1 }

tlipNetMaxPktTable OBJECT-TYPE
   SYNTAX  SEQUENCE OF TlipNetMaxPktEntry
   ACCESS  read-write
   STATUS  mandatory
   ::= { tlip 11 }

tlipNetMaxPktEntry OBJECT-TYPE
   SYNTAX  TlipNetMaxPktEntry
   ACCESS  read-write
   STATUS  mandatory
   ::= { tlipNetMaxPktTable 1 }

TlipNetMaxPktEntry ::= SEQUENCE {
	tlipNetMaxPkt
        	INTEGER
   }

tlipNetMaxPkt OBJECT-TYPE
   SYNTAX  INTEGER (65..65535)
   ACCESS  read-write
   STATUS  mandatory
   ::= { tlipNetMaxPktEntry 1 }

        -- object types
        -- the TL1 System Group

tl1systemAction OBJECT-TYPE
   SYNTAX  INTEGER {
		normal(0),
                reset(1),
                shutdown(2)
            }
   ACCESS  read-write
   STATUS  mandatory
   ::= { tl1system 1 }
        
tl1systemReboots OBJECT-TYPE
   SYNTAX  INTEGER
   ACCESS  read-only
   STATUS  mandatory
   ::= { tl1system 2 }
   
tl1systemErrorCode OBJECT-TYPE
   SYNTAX  INTEGER
   ACCESS  read-only
   STATUS  mandatory
   ::= { tl1system 3 }

        -- the TL1 Interfaces Group
   
tl1ifTable OBJECT-TYPE
   SYNTAX  SEQUENCE OF Tl1ifEntry
   ACCESS  read-write
   STATUS  mandatory
   ::= { tl1interfaces 1 }
   
tl1ifEntry OBJECT-TYPE
   SYNTAX  Tl1ifEntry
   ACCESS  read-write
   STATUS  mandatory
   ::= { tl1ifTable 1 }

Tl1ifEntry ::= SEQUENCE {
        tl1ifIpAddr
             IpAddress,
        tl1ifSubnetMask
             IpAddress,
        tl1ifProxyARP
             INTEGER,
        tl1ifType
             INTEGER,
        tl1ifHardwareAddress
             OCTET STRING
}
   
tl1ifIpAddr OBJECT-TYPE
   SYNTAX  IpAddress
   ACCESS  read-write
   STATUS  mandatory
   ::= { tl1ifEntry 1 } 
   
tl1ifSubnetMask OBJECT-TYPE
   SYNTAX  IpAddress
   ACCESS  read-write
   STATUS  mandatory
   ::= { tl1ifEntry 2 } 
   
tl1ifProxyARP OBJECT-TYPE
   SYNTAX  INTEGER {
                disable(0),
                enabled(1)
           }
   ACCESS  read-write
   STATUS  mandatory
   ::= { tl1ifEntry 3 } 
   
tl1ifType OBJECT-TYPE
   SYNTAX  INTEGER {
                not-configured(0),
                ethernet-II(1),
                iso802-3(2),
                fddi(3),
                lapb(4),
                x25(5),
                ppp(6),
                token-ring(7)
           }
   ACCESS  read-write
   STATUS  mandatory
   ::= { tl1ifEntry 4 } 
   
tl1ifHardwareAddress OBJECT-TYPE
   SYNTAX  OCTET STRING (SIZE (6))
   ACCESS  read-write
   STATUS  mandatory
   ::= { tl1ifEntry 5 } 

        -- the TL1 IP Group

tl1ipLogicalDisconnect OBJECT-TYPE
   SYNTAX  INTEGER {
                true(1),
                false(0)     
           }
   ACCESS  read-write
   STATUS  mandatory
   ::= { tl1ip 1 }
   
tl1ipLoopback OBJECT-TYPE
   SYNTAX  INTEGER {
                true(1),
                false(0)     
           }
   ACCESS  read-write
   STATUS  mandatory
   ::= { tl1ip 2 }
   
tl1ipRedirectTo OBJECT-TYPE
   SYNTAX  INTEGER (1..65535)
   ACCESS  read-write     
   STATUS  mandatory
   ::= { tl1ip 3 }

tl1ipMaxRoutePids OBJECT-TYPE
   SYNTAX  INTEGER
   ACCESS  read-only
   STATUS  mandatory
   ::= { tl1ip 4 }
  
tl1ipRoutePidsTable OBJECT-TYPE
   SYNTAX  SEQUENCE OF Tl1ipRoutePidsEntry
   ACCESS  read-write
   STATUS  mandatory
   ::= { tl1ip 5 }

tl1ipRoutePidsEntry OBJECT-TYPE
   SYNTAX  Tl1ipRoutePidsEntry
   ACCESS  read-write
   STATUS  mandatory
   ::= { tl1ipRoutePidsTable 1 }

Tl1ipRoutePidsEntry ::= SEQUENCE {
      	tl1ipRoutePid
             INTEGER 
}
   
tl1ipRoutePid OBJECT-TYPE
   SYNTAX  INTEGER {
                open-Shortest-Path-First(23),
                routing-Information-Protocol(7),
		exterior-Gateway-Protocol(8),
		internet-Protocol(1),
                static-Routes(0)
           }
   ACCESS  read-write
   STATUS  mandatory
   ::= { tl1ipRoutePidsEntry 1 } 
   
tl1ipNbrStaticRoutes OBJECT-TYPE
   SYNTAX  INTEGER
   ACCESS  read-write
   STATUS  mandatory
   ::= { tl1ip 6 }

tl1ipStaticRouteTable OBJECT-TYPE
   SYNTAX  SEQUENCE OF Tl1ipStaticRouteEntry
   ACCESS  read-write
   STATUS  mandatory
   ::= { tl1ip 7 }
   
tl1ipStaticRouteEntry OBJECT-TYPE
   SYNTAX  Tl1ipStaticRouteEntry
   ACCESS  read-write
   STATUS  mandatory
   ::= { tl1ipStaticRouteTable 1 }
   
Tl1ipStaticRouteEntry ::= SEQUENCE {
	tl1ipStaticRouteNetwork
	     IpAddress,
       	tl1ipStaticRouteGateway
             IpAddress,
	tl1ipStaticRouteCost
             INTEGER,
	tl1ipStaticRouteOverride
             INTEGER,
	tl1ipStaticRouteMask
             IpAddress
}

tl1ipStaticRouteNetwork OBJECT-TYPE
   SYNTAX  IpAddress
   ACCESS  read-only
   STATUS  mandatory
   ::= { tl1ipStaticRouteEntry 1 }

tl1ipStaticRouteGateway OBJECT-TYPE
   SYNTAX  IpAddress
   ACCESS  read-write
   STATUS  mandatory
   ::= { tl1ipStaticRouteEntry 2 }

tl1ipStaticRouteCost OBJECT-TYPE
   SYNTAX  INTEGER (0..255)
   ACCESS  read-write
   STATUS  mandatory
   ::= { tl1ipStaticRouteEntry 3 }
   
tl1ipStaticRouteOverride OBJECT-TYPE
   SYNTAX  INTEGER {
                true(1),
                false(0)     
           }
   ACCESS  read-write
   STATUS  mandatory
   ::= { tl1ipStaticRouteEntry 4 }

tl1ipStaticRouteMask OBJECT-TYPE
   SYNTAX  IpAddress
   ACCESS  read-write
   STATUS  mandatory
   ::= { tl1ipStaticRouteEntry 5 }

tl1ipConfigIntfTable OBJECT-TYPE
   SYNTAX  SEQUENCE OF Tl1ipConfigIntfEntry
   ACCESS  read-write
   STATUS  mandatory
   ::= { tl1ip 8 }

tl1ipConfigIntfEntry OBJECT-TYPE
   SYNTAX  Tl1ipConfigIntfEntry
   ACCESS  read-write
   STATUS  mandatory
   ::= { tl1ipConfigIntfTable 1 }

Tl1ipConfigIntfEntry ::= SEQUENCE {
       	tl1ipRemoteg
       	     INTEGER,
        tl1ipNetMaxPkt
       	     INTEGER,
        tl1ipMasker
             INTEGER
}
   
tl1ipRemoteg OBJECT-TYPE
   SYNTAX  INTEGER {
                true(1),
                false(0)     
           }
   ACCESS  read-write
   STATUS  mandatory
   ::= { tl1ipConfigIntfEntry 1 }
   
tl1ipNetMaxPkt OBJECT-TYPE
   SYNTAX  INTEGER (65..65535)
   ACCESS  read-write
   STATUS  mandatory
   ::= { tl1ipConfigIntfEntry 2 }
   
tl1ipMasker OBJECT-TYPE
   SYNTAX  INTEGER 
   ACCESS  read-write
   STATUS  mandatory
   ::= { tl1ipConfigIntfEntry 3 }
   
tl1ipNumFilters OBJECT-TYPE
   SYNTAX  INTEGER
   ACCESS  read-only
   STATUS  mandatory
   ::= { tl1ip 9 }

tl1ipFilterTable OBJECT-TYPE
   SYNTAX  SEQUENCE OF Tl1ipFilterEntry
   ACCESS  read-write
   STATUS  mandatory
   ::= { tl1ip 10 }

tl1ipFilterEntry OBJECT-TYPE
   SYNTAX  Tl1ipFilterEntry
   ACCESS  read-write
   STATUS  mandatory
   ::= { tl1ipFilterTable 1 }

Tl1ipFilterEntry ::= SEQUENCE {
	tl1ipFilterSrcMask
             IpAddress,
       	tl1ipFilterSrcNet
             IpAddress,
	tl1ipFilterDstMask
             IpAddress,
       	tl1ipFilterDstNet
             IpAddress,
	tl1ipFilterNbrExceptions
             INTEGER
}

tl1ipFilterSrcMask OBJECT-TYPE
   SYNTAX  IpAddress
   ACCESS  read-write
   STATUS  mandatory
   ::= { tl1ipFilterEntry 1 }

tl1ipFilterSrcNet OBJECT-TYPE
   SYNTAX  IpAddress
   ACCESS  read-write
   STATUS  mandatory
   ::= { tl1ipFilterEntry 2 }

tl1ipFilterDstMask OBJECT-TYPE
   SYNTAX  IpAddress
   ACCESS  read-write
   STATUS  mandatory
   ::= { tl1ipFilterEntry 3 }

tl1ipFilterDstNet OBJECT-TYPE
   SYNTAX  IpAddress
   ACCESS  read-write
   STATUS  mandatory
   ::= { tl1ipFilterEntry 4 }

tl1ipFilterNbrExceptions OBJECT-TYPE
   SYNTAX  INTEGER
   ACCESS  read-write
   STATUS  mandatory
   ::= { tl1ipFilterEntry 5 }
   
tl1ipFilterExceptionTable OBJECT-TYPE
   SYNTAX  SEQUENCE OF Tl1ipFilterExceptionEntry
   ACCESS  read-write
   STATUS  mandatory
   ::= { tl1ip 11 }

tl1ipFilterExceptionEntry OBJECT-TYPE
   SYNTAX  Tl1ipFilterExceptionEntry
   ACCESS  read-write
   STATUS  mandatory
   ::= { tl1ipFilterExceptionTable 1 }

Tl1ipFilterExceptionEntry ::= SEQUENCE {
       	tl1ipFilterExceptionSrcNet
             IpAddress,
       	tl1ipFilterExceptionDstNet
             IpAddress
}

tl1ipFilterExceptionSrcNet OBJECT-TYPE
   SYNTAX  IpAddress
   ACCESS  read-write
   STATUS  mandatory
   ::= { tl1ipFilterExceptionEntry 1 }

tl1ipFilterExceptionDstNet OBJECT-TYPE
   SYNTAX  IpAddress
   ACCESS  read-write
   STATUS  mandatory
   ::= { tl1ipFilterExceptionEntry 2 }

        -- the TL1 TCP Group
   
tl1tcpRetransTo OBJECT-TYPE
   SYNTAX  INTEGER (1..65535)
   ACCESS  read-write
   STATUS  mandatory
   ::= { tl1tcp 1 }

tl1tcpRtoMin OBJECT-TYPE
   SYNTAX  INTEGER (1..65535)
   ACCESS  read-write
   STATUS  mandatory
   ::= { tl1tcp 2 }

tl1tcpRtoMax OBJECT-TYPE
   SYNTAX  INTEGER (1..65635)
   ACCESS  read-write
   STATUS  mandatory
   ::= { tl1tcp 3 }

tl1tcpWakeup OBJECT-TYPE
   SYNTAX  INTEGER (1..16384)
   ACCESS  read-write
   STATUS  mandatory
   ::= { tl1tcp 4 }

tl1tcpAckTime OBJECT-TYPE
   SYNTAX  INTEGER (1..16384)
   ACCESS  read-write
   STATUS  mandatory
   ::= { tl1tcp 5 }

tl1tcpTimeToLive OBJECT-TYPE
   SYNTAX  INTEGER (1..255)
   ACCESS  read-write
   STATUS  mandatory
   ::= { tl1tcp 6 } 

tl1tcpThruput OBJECT-TYPE
   SYNTAX  INTEGER (1..255)
   ACCESS  read-write
   STATUS  mandatory
   ::= { tl1tcp 7 }

tl1tcpFlowAck OBJECT-TYPE
   SYNTAX  INTEGER (1..255)
   ACCESS  read-write
   STATUS  mandatory
   ::= { tl1tcp 8 }

        -- the TL1 EGP Group
   
tl1egpMaxNbrs OBJECT-TYPE
   SYNTAX  INTEGER
   ACCESS  read-only
   STATUS  mandatory
   ::= { tl1egp 1 } 

tl1egpNumberTrustedNbrs OBJECT-TYPE
   SYNTAX  INTEGER (0..20)
   ACCESS  read-write
   STATUS  mandatory
   ::= { tl1egp 2 } 

tl1egpNumberNbrs OBJECT-TYPE
   SYNTAX  INTEGER (0..20)
   ACCESS  read-write
   STATUS  mandatory
   ::= { tl1egp 3 } 

tl1egpNbrTable OBJECT-TYPE
   SYNTAX  SEQUENCE OF Tl1egpNbrEntry
   ACCESS  read-write
   STATUS  mandatory
   ::= { tl1egp 4 } 

tl1egpNbrEntry OBJECT-TYPE
   SYNTAX  Tl1egpNbrEntry
   ACCESS  read-write
   STATUS  mandatory
   ::= { tl1egpNbrTable 1 } 

Tl1egpNbrEntry ::= SEQUENCE {
	tl1egpNbr
       	     IpAddress
}

tl1egpNbr OBJECT-TYPE
   SYNTAX  IpAddress
   ACCESS  read-write
   STATUS  mandatory
   ::= { tl1egpNbrEntry 1 } 

tl1egpAutoSysNumber OBJECT-TYPE
   SYNTAX  INTEGER (0..65535)
   ACCESS  read-write
   STATUS  mandatory
   ::= { tl1egp 5 } 

tl1egpMinHelloInterval OBJECT-TYPE
   SYNTAX  INTEGER (15..65535)
   ACCESS  read-write
   STATUS  mandatory
   ::= { tl1egp 6 } 

tl1egpMinPollInterval OBJECT-TYPE
   SYNTAX  INTEGER (30..65535)
   ACCESS  read-write
   STATUS  mandatory
   ::= { tl1egp 7 } 

tl1egpRequestCeaseInterval OBJECT-TYPE
   SYNTAX  INTEGER (15..65535)
   ACCESS  read-write
   STATUS  mandatory
   ::= { tl1egp 8 } 

tl1egpDeclareDownInterval OBJECT-TYPE
   SYNTAX  INTEGER (1800..65535)
   ACCESS  read-write
   STATUS  mandatory
   ::= { tl1egp 9 } 

tl1egpAcquireCeaseInterval OBJECT-TYPE
   SYNTAX  INTEGER (30..240)
   ACCESS  read-write
   STATUS  mandatory
   ::= { tl1egp 10 } 

tl1egpEnoughInterval OBJECT-TYPE
   SYNTAX  INTEGER (60..65535)
   ACCESS  read-write
   STATUS  mandatory
   ::= { tl1egp 11 } 

tl1egpPurgeInterval OBJECT-TYPE
   SYNTAX  INTEGER (0..600)
   ACCESS  read-write
   STATUS  mandatory
   ::= { tl1egp 12 } 

tl1egpMode OBJECT-TYPE
   SYNTAX  INTEGER {
                active-and-passive(0),
                active(1),
                passive(2)
           }
   ACCESS  read-write
   STATUS  mandatory
   ::= { tl1egp 13 } 

tl1egpErrorTreatment OBJECT-TYPE
   SYNTAX  INTEGER (0..255) 
   ACCESS  read-write
   STATUS  mandatory
   ::= { tl1egp 14 } 

tl1egpSharedNetwork OBJECT-TYPE
   SYNTAX  IpAddress
   ACCESS  read-write
   STATUS  mandatory
   ::= { tl1egp 15 } 

        -- the TL1 SNMP Group

 tl1snmpVersion OBJECT-TYPE
   SYNTAX  INTEGER
   ACCESS  read-only
   STATUS  mandatory
   ::= { tl1snmp 1 }

tl1snmpTrapTable OBJECT-TYPE
   SYNTAX  SEQUENCE OF Tl1snmpTrapEntry
   ACCESS  read-write
   STATUS  mandatory
   ::= { tl1snmp 2 }
   
tl1snmpTrapEntry OBJECT-TYPE
   SYNTAX  Tl1snmpTrapEntry
   ACCESS  read-write
   STATUS  mandatory
   ::= { tl1snmpTrapTable 1 }
   
Tl1snmpTrapEntry ::= SEQUENCE {
        tl1snmpTrapAddress
             IpAddress
}

tl1snmpTrapAddress OBJECT-TYPE
   SYNTAX  IpAddress
   ACCESS  read-write
   STATUS  mandatory
   ::= { tl1snmpTrapEntry 1 }
   
tl1snmpForwardTraps OBJECT-TYPE
   SYNTAX  INTEGER {
                forward(2),
                dont-forward(1)
           }
   ACCESS  read-write
   STATUS  mandatory
   ::= { tl1snmp 3 }

tl1snmpLastTrapMessage OBJECT-TYPE
   SYNTAX  OCTET STRING (SIZE (0..128))
   ACCESS  read-only
   STATUS  mandatory
   ::= { tl1snmp 4 }

tl1snmpNMSTable OBJECT-TYPE
   SYNTAX  SEQUENCE OF Tl1snmpNMSEntry
   ACCESS  read-write
   STATUS  mandatory
   ::= { tl1snmp 5 }

tl1snmpNMSEntry OBJECT-TYPE
   SYNTAX  Tl1snmpNMSEntry
   ACCESS  read-write
   STATUS  mandatory
   ::= { tl1snmpNMSTable 1 }

Tl1snmpNMSEntry ::= SEQUENCE {
        tl1snmpNMSAddress
             IpAddress
}

tl1snmpNMSAddress OBJECT-TYPE
   SYNTAX  IpAddress
   ACCESS  read-write
   STATUS  mandatory
   ::= { tl1snmpNMSEntry 1 }

        -- the TL1 BRE Group

tl1breBridgeNumber OBJECT-TYPE
   SYNTAX  INTEGER (0..255)
   ACCESS  read-write
   STATUS  mandatory
   ::= { tl1breConfigParams 1 }

tl1breBridgeIpAddress OBJECT-TYPE
   SYNTAX  IpAddress
   ACCESS  read-write
   STATUS  mandatory
   ::= { tl1breConfigParams 2 }

tl1breForwardTableAgeingTime OBJECT-TYPE
   SYNTAX  INTEGER
   ACCESS  read-write
   STATUS  mandatory
   ::= { tl1breConfigParams 3 }                    

tl1breNumConfigBrdgLstEntries OBJECT-TYPE
   SYNTAX  INTEGER (0..32)
   ACCESS  read-write
   STATUS  mandatory
   ::= { tl1breConfigParams 4 }

tl1breConfigBridgeListTable OBJECT-TYPE
   SYNTAX  SEQUENCE OF Tl1breCBridgeListEntry
   ACCESS  read-write
   STATUS  mandatory
   ::= { tl1bre 2 }

tl1breCBridgeListEntry OBJECT-TYPE
   SYNTAX  Tl1breCBridgeListEntry
   ACCESS  read-write
   STATUS  mandatory
   ::= { tl1breConfigBridgeListTable 1 }

Tl1breCBridgeListEntry ::= SEQUENCE {
        tl1breCblBridgeNumber
             INTEGER, 
        tl1breCblVLanId 
             INTEGER,
        tl1breCblSrBridgeNumber
             INTEGER,
        tl1breCblIpAddress
             IpAddress
}

tl1breCblBridgeNumber OBJECT-TYPE
   SYNTAX  INTEGER (0..255)
   ACCESS  read-write
   STATUS  mandatory
   ::= { tl1breCBridgeListEntry 1 }

tl1breCblVLanId OBJECT-TYPE
   SYNTAX  INTEGER (0..4095)
   ACCESS  read-write
   STATUS  mandatory
   ::= { tl1breCBridgeListEntry 2 } 

tl1breCblSrBridgeNumber OBJECT-TYPE
   SYNTAX  INTEGER (0..15)
   ACCESS  read-write
   STATUS  mandatory
   ::= { tl1breCBridgeListEntry 3 }

tl1breCblIpAddress OBJECT-TYPE
   SYNTAX  IpAddress
   ACCESS  read-write
   STATUS  mandatory
   ::= { tl1breCBridgeListEntry 4 }
   
tl1breBridgeListTable OBJECT-TYPE
   SYNTAX  SEQUENCE OF Tl1breBridgeListEntry
   ACCESS  read-only
   STATUS  mandatory
   ::= { tl1bre 3 }
   
tl1breBridgeListEntry OBJECT-TYPE
   SYNTAX  Tl1breBridgeListEntry
   ACCESS  read-only
   STATUS  mandatory
   ::= { tl1breBridgeListTable 1 }
   
Tl1breBridgeListEntry ::= SEQUENCE {
        tl1breBlBridgeNumber
             INTEGER, 
        tl1breBlVLanId 
             INTEGER,
        tl1breBlSrBridgeNumber
             INTEGER,
        tl1breBlIpAddress
             IpAddress
}
    
tl1breBlBridgeNumber OBJECT-TYPE
   SYNTAX  INTEGER (0..255)
   ACCESS  read-only
   STATUS  mandatory
   ::= { tl1breBridgeListEntry 1 }
 
tl1breBlVLanId OBJECT-TYPE
   SYNTAX  INTEGER (0..4095)
   ACCESS  read-only
   STATUS  mandatory
   ::= { tl1breBridgeListEntry 2 } 

tl1breBlSrBridgeNumber OBJECT-TYPE
   SYNTAX  INTEGER (0..15)
   ACCESS  read-only
   STATUS  mandatory
   ::= { tl1breBridgeListEntry 3 }

tl1breBlIpAddress OBJECT-TYPE
   SYNTAX  IpAddress
   ACCESS  read-only
   STATUS  mandatory
   ::= { tl1breBridgeListEntry 4 }

tl1breForwardTable OBJECT-TYPE
   SYNTAX  SEQUENCE OF Tl1breForwardTableEntry
   ACCESS  read-only
   STATUS  mandatory
   ::= { tl1bre 4 }

tl1breForwardTableEntry OBJECT-TYPE
   SYNTAX  Tl1breForwardTableEntry
   ACCESS  read-only
   STATUS  mandatory
   ::= { tl1breForwardTable 1 }

Tl1breForwardTableEntry ::= SEQUENCE {
        tl1breFtMacAddress
             OCTET STRING, 
        tl1breFtIpAddress  
             IpAddress
}

tl1breFtMacAddress OBJECT-TYPE
   SYNTAX  OCTET STRING (SIZE (6))
   ACCESS  read-only
   STATUS  mandatory
   ::= { tl1breForwardTableEntry 1} 
    
tl1breFtIpAddress OBJECT-TYPE
   SYNTAX  IpAddress
   ACCESS  read-only
   STATUS  mandatory
   ::= { tl1breForwardTableEntry 2} 
    
tl1breStatTable OBJECT-TYPE
   SYNTAX  SEQUENCE OF Tl1breStatEntry
   ACCESS  read-only
   STATUS  mandatory
   ::= { tl1bre 5 }

tl1breStatEntry OBJECT-TYPE
   SYNTAX  Tl1breStatEntry
   ACCESS  read-only
   STATUS  mandatory
   ::= { tl1breStatTable 1 }

Tl1breStatEntry ::= SEQUENCE {
  	tl1breInTSFs
             Counter,
        tl1breInSRFs
             Counter,
        tl1breInEFs
             Counter,
        tl1breInBPDUs
             Counter,
        tl1breInErrors
             Counter,
        tl1breOutTSFs
             Counter,
        tl1breOutSRFs
             Counter,
        tl1breOutEFs
             Counter,
        tl1breOutBPDUs 
             Counter
}

tl1breInTSFs OBJECT-TYPE
   SYNTAX  Counter
   ACCESS  read-only
   STATUS  mandatory
   ::= { tl1breStatEntry 1 }

tl1breInSRFs OBJECT-TYPE
   SYNTAX  Counter
   ACCESS  read-only
   STATUS  mandatory
   ::= { tl1breStatEntry 2 }

tl1breInEFs OBJECT-TYPE
   SYNTAX  Counter
   ACCESS  read-only
   STATUS  mandatory
   ::= { tl1breStatEntry 3 }

tl1breInBPDUs OBJECT-TYPE
   SYNTAX  Counter
   ACCESS  read-only
   STATUS  mandatory
   ::= { tl1breStatEntry 4 }

tl1breInErrors OBJECT-TYPE
   SYNTAX  Counter
   ACCESS  read-only
   STATUS  mandatory
   ::= { tl1breStatEntry 5}

tl1breOutTSFs OBJECT-TYPE
   SYNTAX  Counter
   ACCESS  read-only
   STATUS  mandatory
   ::= { tl1breStatEntry 6 }
    
tl1breOutSRFs OBJECT-TYPE
   SYNTAX  Counter
   ACCESS  read-only
   STATUS  mandatory
   ::= { tl1breStatEntry 7 }

tl1breOutEFs OBJECT-TYPE
   SYNTAX  Counter
   ACCESS  read-only
   STATUS  mandatory
   ::= { tl1breStatEntry 8 }

tl1breOutBPDUs OBJECT-TYPE
   SYNTAX  Counter
   ACCESS  read-only
   STATUS  mandatory
   ::= { tl1breStatEntry 9 }

        -- the TL1 RIP Group
   
tl1ripInPkts OBJECT-TYPE
   SYNTAX  Counter
   ACCESS  read-only
   STATUS  mandatory
   ::= { tl1rip 1 }

tl1ripOutPkts OBJECT-TYPE
   SYNTAX  Counter
   ACCESS  read-only
   STATUS  mandatory
   ::= { tl1rip 2 }

tl1ripBadSize OBJECT-TYPE
   SYNTAX  Counter
   ACCESS  read-only
   STATUS  mandatory
   ::= { tl1rip 3 }

tl1ripBadVersion OBJECT-TYPE
   SYNTAX  Counter
   ACCESS  read-only
   STATUS  mandatory
   ::= { tl1rip 4 }

tl1ripNonZero OBJECT-TYPE
   SYNTAX  Counter
   ACCESS  read-only
   STATUS  mandatory
   ::= { tl1rip 5 }

tl1ripBadFamily OBJECT-TYPE
   SYNTAX  Counter
   ACCESS  read-only
   STATUS  mandatory
   ::= { tl1rip 6 }
   
tl1ripBadPort OBJECT-TYPE
   SYNTAX  Counter
   ACCESS  read-only
   STATUS  mandatory
   ::= { tl1rip 7 }

tl1ripBadMetric OBJECT-TYPE
   SYNTAX  Counter
   ACCESS  read-only
   STATUS  mandatory
   ::= { tl1rip 8 }

tl1ripBadAddr OBJECT-TYPE
   SYNTAX  Counter
   ACCESS  read-only
   STATUS  mandatory
   ::= { tl1rip 9 }

tl1ripBadCommand OBJECT-TYPE
   SYNTAX  Counter
   ACCESS  read-only
   STATUS  mandatory
   ::= { tl1rip 10 }

tl1ripBadClass OBJECT-TYPE
   SYNTAX  Counter
   ACCESS  read-only
   STATUS  mandatory
   ::= { tl1rip 11 }

tl1ripBadNbr OBJECT-TYPE
   SYNTAX  Counter
   ACCESS  read-only
   STATUS  mandatory
   ::= { tl1rip 12 }

tl1ripOwnAddr OBJECT-TYPE
   SYNTAX  Counter
   ACCESS  read-only
   STATUS  mandatory
   ::= { tl1rip 13 }

tl1ripConfigTable OBJECT-TYPE
   SYNTAX  SEQUENCE OF Tl1ripConfigEntry
   ACCESS  read-write
   STATUS  mandatory
   ::= { tl1rip 14 }

tl1ripConfigEntry OBJECT-TYPE
   SYNTAX  Tl1ripConfigEntry
   ACCESS  read-write
   STATUS  mandatory
   ::= { tl1ripConfigTable 1 }

Tl1ripConfigEntry ::= SEQUENCE {
        tl1ripMode
             INTEGER,             
         tl1ripSimple 
             INTEGER,             
         tl1ripAdverStatic 
             INTEGER,             
         tl1ripAdverIntf 
             INTEGER,             
         tl1ripHolddown
             INTEGER             
}

tl1ripMode OBJECT-TYPE
   SYNTAX  INTEGER {
                disabled(1),
                silent(2),
                fully-operational(3),
                deaf(4)
           }
   ACCESS  read-write
   STATUS  mandatory
   ::= { tl1ripConfigEntry 1 }
   
tl1ripSimple OBJECT-TYPE
   SYNTAX  INTEGER {
                simple-split-horizon(2),
                poisoned-reverse(1)
           }
   ACCESS  read-write
   STATUS  mandatory
   ::= { tl1ripConfigEntry 2 }

tl1ripAdverStatic OBJECT-TYPE
   SYNTAX  INTEGER {
                advertise(2),
                dont-advertise(1)
           }
   ACCESS  read-write
   STATUS  mandatory
   ::= { tl1ripConfigEntry 3 }

tl1ripAdverIntf OBJECT-TYPE
   SYNTAX  INTEGER {
                advertise(2),
                dont-advertise(1)
           }     
   ACCESS  read-write
   STATUS  mandatory
   ::= { tl1ripConfigEntry 4 } 

tl1ripHolddown OBJECT-TYPE
   SYNTAX  INTEGER
   ACCESS  read-write
   STATUS  mandatory
   ::= { tl1ripConfigEntry 5 }

        -- the TL1 X25 Group

tl1x25IfTable OBJECT-TYPE
   SYNTAX  SEQUENCE OF Tl1x25IfEntry
   ACCESS  read-write
   STATUS  mandatory
   ::= { tl1x25 1 }

tl1x25IfEntry OBJECT-TYPE
   SYNTAX  Tl1x25IfEntry
   ACCESS  read-write
   STATUS  mandatory
   ::= { tl1x25IfTable 1 }

Tl1x25IfEntry ::= SEQUENCE {
        tl1x25InPkts
             Counter,
        tl1x25OutPkts
             Counter,
        tl1x25GFI
             Counter,
        tl1x25PktInv
             Counter,
        tl1x25PinvR1
             Counter,
        tl1x25PinvR2
             Counter,
        tl1x25PinvR3
             Counter,
        tl1x25PinvP1
             Counter,
        tl1x25PinvP2
             Counter,
        tl1x25PinvP3 
             Counter,
        tl1x25PinvP4 
             Counter,
        tl1x25PinvP5 
             Counter,
        tl1x25PinvP6 
             Counter,
        tl1x25PinvP7 
             Counter,
        tl1x25PinvD1 
             Counter,
        tl1x25PinvD2 
             Counter,
        tl1x25PinvD3 
             Counter,
        tl1x25PktLong 
             Counter,
        tl1x25PktShort 
             Counter,
        tl1x25CallingAddr 
             Counter,
        tl1x25CalledAddr 
             Counter,
        tl1x25CallBad 
             Counter,
        tl1x25FacParam 
             Counter,
        tl1x25FacCode 
             Counter,
        tl1x25BadPkt 
             Counter,
        tl1x25RejInv 
             Counter,
        tl1x25LcRestr 
             Counter,
        tl1x25IntrCPkt 
             Counter,
        tl1x25CallTimer 
             Counter,
        tl1x25ResetTimer 
             Counter,
        tl1x25Service
             INTEGER,
        tl1x25Window
             INTEGER,
        tl1x25PktSize
             INTEGER
}

tl1x25InPkts OBJECT-TYPE
   SYNTAX  Counter
   ACCESS  read-only
   STATUS  mandatory
   ::= { tl1x25IfEntry 1 }

tl1x25OutPkts OBJECT-TYPE
   SYNTAX  Counter
   ACCESS  read-only
   STATUS  mandatory
   ::= { tl1x25IfEntry 2 }

tl1x25GFI OBJECT-TYPE
   SYNTAX  Counter
   ACCESS  read-only
   STATUS  mandatory
   ::= { tl1x25IfEntry 3 }
   
tl1x25PktInv OBJECT-TYPE
   SYNTAX  Counter
   ACCESS  read-only
   STATUS  mandatory
   ::= { tl1x25IfEntry 4 }

tl1x25PinvR1 OBJECT-TYPE
   SYNTAX  Counter
   ACCESS  read-only
   STATUS  mandatory
   ::= { tl1x25IfEntry 5 }

tl1x25PinvR2 OBJECT-TYPE
   SYNTAX  Counter
   ACCESS  read-only
   STATUS  mandatory
   ::= { tl1x25IfEntry 6 }
   
tl1x25PinvR3 OBJECT-TYPE
   SYNTAX  Counter
   ACCESS  read-only
   STATUS  mandatory
   ::= { tl1x25IfEntry 7 }

tl1x25PinvP1 OBJECT-TYPE
   SYNTAX  Counter
   ACCESS  read-only
   STATUS  mandatory
   ::= { tl1x25IfEntry 8 }
   
tl1x25PinvP2 OBJECT-TYPE
   SYNTAX  Counter
   ACCESS  read-only
   STATUS  mandatory
   ::= { tl1x25IfEntry 9 }

tl1x25PinvP3 OBJECT-TYPE
   SYNTAX  Counter
   ACCESS  read-only
   STATUS  mandatory
   ::= { tl1x25IfEntry 10 }
   
tl1x25PinvP4 OBJECT-TYPE
   SYNTAX  Counter
   ACCESS  read-only
   STATUS  mandatory
   ::= { tl1x25IfEntry 11 }

tl1x25PinvP5 OBJECT-TYPE
   SYNTAX  Counter
   ACCESS  read-only
   STATUS  mandatory
   ::= { tl1x25IfEntry 12 }

tl1x25PinvP6 OBJECT-TYPE
   SYNTAX  Counter
   ACCESS  read-only
   STATUS  mandatory
   ::= { tl1x25IfEntry 13 }

tl1x25PinvP7 OBJECT-TYPE
   SYNTAX  Counter
   ACCESS  read-only
   STATUS  mandatory
   ::= { tl1x25IfEntry 14 }

tl1x25PinvD1 OBJECT-TYPE
   SYNTAX  Counter
   ACCESS  read-only
   STATUS  mandatory
   ::= { tl1x25IfEntry 15 }

tl1x25PinvD2 OBJECT-TYPE
   SYNTAX  Counter
   ACCESS  read-only
   STATUS  mandatory
   ::= { tl1x25IfEntry 16 }

tl1x25PinvD3 OBJECT-TYPE
   SYNTAX  Counter
   ACCESS  read-only
   STATUS  mandatory
   ::= { tl1x25IfEntry 17 }

tl1x25PktLong OBJECT-TYPE
   SYNTAX  Counter
   ACCESS  read-only
   STATUS  mandatory
   ::= { tl1x25IfEntry 18 }

tl1x25PktShort OBJECT-TYPE
   SYNTAX  Counter
   ACCESS  read-only
   STATUS  mandatory
   ::= { tl1x25IfEntry 19 }

tl1x25CallingAddr OBJECT-TYPE
   SYNTAX  Counter
   ACCESS  read-only
   STATUS  mandatory
   ::= { tl1x25IfEntry 20 }

tl1x25CalledAddr OBJECT-TYPE
   SYNTAX  Counter
   ACCESS  read-only
   STATUS  mandatory
   ::= { tl1x25IfEntry 21 }

tl1x25CallBad OBJECT-TYPE
   SYNTAX  Counter
   ACCESS  read-only
   STATUS  mandatory
   ::= { tl1x25IfEntry 22 }

tl1x25FacParam OBJECT-TYPE
   SYNTAX  Counter
   ACCESS  read-only
   STATUS  mandatory
   ::= { tl1x25IfEntry 23 }

tl1x25FacCode OBJECT-TYPE
   SYNTAX  Counter
   ACCESS  read-only
   STATUS  mandatory
   ::= { tl1x25IfEntry 24 }

tl1x25BadPkt OBJECT-TYPE
   SYNTAX  Counter
   ACCESS  read-only
   STATUS  mandatory
   ::= { tl1x25IfEntry 25 }

tl1x25RejInv OBJECT-TYPE
   SYNTAX  Counter
   ACCESS  read-only
   STATUS  mandatory
   ::= { tl1x25IfEntry 26 }

tl1x25LcRestr OBJECT-TYPE
   SYNTAX  Counter
   ACCESS  read-only
   STATUS  mandatory
   ::= { tl1x25IfEntry 27 }

tl1x25IntrCPkt OBJECT-TYPE
   SYNTAX  Counter
   ACCESS  read-only
   STATUS  mandatory
   ::= { tl1x25IfEntry 28 }

tl1x25CallTimer OBJECT-TYPE
   SYNTAX  Counter
   ACCESS  read-only
   STATUS  mandatory
   ::= { tl1x25IfEntry 29 }

tl1x25ResetTimer OBJECT-TYPE
   SYNTAX  Counter
   ACCESS  read-only
   STATUS  mandatory
   ::= { tl1x25IfEntry 30 }

tl1x25Service OBJECT-TYPE
   SYNTAX  INTEGER {
		basic-service(1),
		standard-service(2)
           }
   ACCESS  read-write
   STATUS  mandatory
   ::= { tl1x25IfEntry 31 } 

tl1x25Window OBJECT-TYPE
   SYNTAX  INTEGER (2..7)
   ACCESS  read-write
   STATUS  mandatory
   ::= { tl1x25IfEntry 32 } 

tl1x25PktSize OBJECT-TYPE
   SYNTAX  INTEGER (7..11) 
   ACCESS  read-write
   STATUS  mandatory
   ::= { tl1x25IfEntry 33 } 

        -- the TL1 FDDI Group

tl1fddiMACStatTable OBJECT-TYPE
   SYNTAX  SEQUENCE OF Tl1fddiMACStatEntry
   ACCESS  read-only
   STATUS  mandatory
   ::= { tl1fddi 1 }

tl1fddiMACStatEntry OBJECT-TYPE
   SYNTAX  Tl1fddiMACStatEntry
   ACCESS  read-only
   STATUS  mandatory
   ::= { tl1fddiMACStatTable 1 }

Tl1fddiMACStatEntry ::= SEQUENCE {
        tl1fddiMACRcvAbort
             Counter,  
        tl1fddiMACRcvOverflow
             Counter,  
        tl1fddiMACRcvUnderflow
             Counter,
        tl1fddiMACRbcCollision
             Counter,
        tl1fddiMACTxSyncChain
             Counter,
        tl1fddiMACTxAsyncChain   
             Counter,    
        tl1fddiMACTxSyncFrm
             Counter,  
        tl1fddiMACTxAsyncFrm 
             Counter,  
        tl1fddiMACTxSyncDone  
             Counter,
        tl1fddiMACTxAsyncDone 
             Counter,
        tl1fddiMACTxBufEmpty 
             Counter,
        tl1fddiMACTxAbort        
             Counter,    
        tl1fddiMACRxFrmsRcvd
             Counter,  
        tl1fddiMACRxSmallGap 
             Counter,  
        tl1fddiMACDpcCollision
             Counter,
        tl1fddiMACBadSyncPtr  
             Counter,
        tl1fddiMACBadAsyncPtr
             Counter,
        tl1fddiMACOtherBecRcvd   
             Counter,    
        tl1fddiMACOwnBecRcvd
             Counter,  
        tl1fddiMACHighClmRcvd 
             Counter,
        tl1fddiMACLowClmRcvd  
             Counter,
        tl1fddiMACWonClaimBid
             Counter,
        tl1fddiMACPktsDetected    
             Counter,    
        tl1fddiMACTokenCt 
             Counter,  
        tl1fddiMACLateCt     
             Counter,  
        tl1fddiMACTvxExpiredCt
             Counter,
        tl1fddiMACEnterBeacontCt
             Counter,
        tl1fddiMACEnterClaimCt
             Counter,
        tl1fddiMACMultiTokens
             Counter,
        tl1fddiMACNotCopiedCt    
             Counter,    
        tl1fddiMACDuplicateAddr
             Counter,  
        tl1fddiMACRingOpCt   
             Counter,  
        tl1fddiMACFrameCt       
             Counter,
        tl1fddiMACLostCt         
             Counter,
        tl1fddiMACErrorCt    
             Counter,
        tl1fddiMACOutOfBuf       
             Counter,    
        tl1fddiMACReceiveCt
             Counter,  
        tl1fddiMACTransmitCt 
             Counter,  
        tl1fddiMACInternalErrorCt
             Counter,
        tl1fddiMACTneg        
             INTEGER
}

tl1fddiMACRcvAbort OBJECT-TYPE
   SYNTAX  Counter    
   ACCESS  read-only 
   STATUS  mandatory
   ::= { tl1fddiMACStatEntry 1 } 

tl1fddiMACRcvOverflow OBJECT-TYPE
   SYNTAX  Counter
   ACCESS  read-only
   STATUS  mandatory
   ::= { tl1fddiMACStatEntry 2 } 

tl1fddiMACRcvUnderflow OBJECT-TYPE
   SYNTAX  Counter
   ACCESS  read-only
   STATUS  mandatory
   ::= { tl1fddiMACStatEntry 3 } 

tl1fddiMACRbcCollision OBJECT-TYPE
   SYNTAX  Counter
   ACCESS  read-only
   STATUS  mandatory
   ::= { tl1fddiMACStatEntry 4 } 

tl1fddiMACTxSyncChain OBJECT-TYPE
   SYNTAX  Counter
   ACCESS  read-only
   STATUS  mandatory
   ::= { tl1fddiMACStatEntry 5 } 

tl1fddiMACTxAsyncChain OBJECT-TYPE
   SYNTAX  Counter
   ACCESS  read-only
   STATUS  mandatory
   ::= { tl1fddiMACStatEntry 6 } 

tl1fddiMACTxSyncFrm OBJECT-TYPE
   SYNTAX  Counter
   ACCESS  read-only
   STATUS  mandatory
   ::= { tl1fddiMACStatEntry 7 } 

tl1fddiMACTxAsyncFrm OBJECT-TYPE
   SYNTAX  Counter
   ACCESS  read-only
   STATUS  mandatory
   ::= { tl1fddiMACStatEntry 8 } 

tl1fddiMACTxSyncDone OBJECT-TYPE
   SYNTAX  Counter
   ACCESS  read-only
   STATUS  mandatory
   ::= { tl1fddiMACStatEntry 9 } 

tl1fddiMACTxAsyncDone OBJECT-TYPE
   SYNTAX  Counter
   ACCESS  read-only
   STATUS  mandatory
   ::= { tl1fddiMACStatEntry 10 }

tl1fddiMACTxBufEmpty OBJECT-TYPE
   SYNTAX  Counter
   ACCESS  read-only
   STATUS  mandatory
   ::= { tl1fddiMACStatEntry 11 } 

tl1fddiMACTxAbort OBJECT-TYPE
   SYNTAX  Counter
   ACCESS  read-only
   STATUS  mandatory
   ::= { tl1fddiMACStatEntry 12 } 

tl1fddiMACRxFrmsRcvd OBJECT-TYPE
   SYNTAX  Counter
   ACCESS  read-only
   STATUS  mandatory
   ::= { tl1fddiMACStatEntry 13 } 

tl1fddiMACRxSmallGap OBJECT-TYPE
   SYNTAX  Counter
   ACCESS  read-only
   STATUS  mandatory
   ::= { tl1fddiMACStatEntry 14 } 

tl1fddiMACDpcCollision OBJECT-TYPE
   SYNTAX  Counter
   ACCESS  read-only
   STATUS  mandatory
   ::= { tl1fddiMACStatEntry 15 } 

tl1fddiMACBadSyncPtr OBJECT-TYPE
   SYNTAX  Counter
   ACCESS  read-only
   STATUS  mandatory
   ::= { tl1fddiMACStatEntry 16 } 

tl1fddiMACBadAsyncPtr OBJECT-TYPE
   SYNTAX  Counter
   ACCESS  read-only
   STATUS  mandatory
   ::= { tl1fddiMACStatEntry 17 } 

tl1fddiMACOtherBecRcvd OBJECT-TYPE
   SYNTAX  Counter
   ACCESS  read-only
   STATUS  mandatory
   ::= { tl1fddiMACStatEntry 18 } 

tl1fddiMACOwnBecRcvd OBJECT-TYPE
   SYNTAX  Counter
   ACCESS  read-only
   STATUS  mandatory
   ::= { tl1fddiMACStatEntry 19 } 

tl1fddiMACHighClmRcvd OBJECT-TYPE
   SYNTAX  Counter
   ACCESS  read-only
   STATUS  mandatory
   ::= { tl1fddiMACStatEntry 20 } 

tl1fddiMACLowClmRcvd OBJECT-TYPE
   SYNTAX  Counter
   ACCESS  read-only
   STATUS  mandatory
   ::= { tl1fddiMACStatEntry 21 } 

tl1fddiMACWonClaimBid OBJECT-TYPE
   SYNTAX  Counter
   ACCESS  read-only
   STATUS  mandatory
   ::= { tl1fddiMACStatEntry 22 } 

tl1fddiMACPktsDetected OBJECT-TYPE
   SYNTAX  Counter
   ACCESS  read-only
   STATUS  mandatory
   ::= { tl1fddiMACStatEntry 23 } 

tl1fddiMACTokenCt OBJECT-TYPE
   SYNTAX  Counter
   ACCESS  read-only
   STATUS  mandatory
   ::= { tl1fddiMACStatEntry 24 } 

tl1fddiMACLateCt OBJECT-TYPE
   SYNTAX  Counter
   ACCESS  read-only
   STATUS  mandatory
   ::= { tl1fddiMACStatEntry 25 } 

tl1fddiMACTvxExpiredCt OBJECT-TYPE
   SYNTAX  Counter
   ACCESS  read-only
   STATUS  mandatory
   ::= { tl1fddiMACStatEntry 26 } 

tl1fddiMACEnterBeacontCt OBJECT-TYPE
   SYNTAX  Counter
   ACCESS  read-only
   STATUS  mandatory
   ::= { tl1fddiMACStatEntry 27 } 

tl1fddiMACEnterClaimCt OBJECT-TYPE
   SYNTAX  Counter
   ACCESS  read-only
   STATUS  mandatory
   ::= { tl1fddiMACStatEntry 28 } 

tl1fddiMACMultiTokens OBJECT-TYPE
   SYNTAX  Counter
   ACCESS  read-only
   STATUS  mandatory
   ::= { tl1fddiMACStatEntry 29 } 

tl1fddiMACNotCopiedCt OBJECT-TYPE
   SYNTAX  Counter
   ACCESS  read-only
   STATUS  mandatory
   ::= { tl1fddiMACStatEntry 30 } 

tl1fddiMACDuplicateAddr OBJECT-TYPE
   SYNTAX  Counter
   ACCESS  read-only
   STATUS  mandatory
   ::= { tl1fddiMACStatEntry 31 } 

tl1fddiMACRingOpCt OBJECT-TYPE
   SYNTAX  Counter
   ACCESS  read-only
   STATUS  mandatory
   ::= { tl1fddiMACStatEntry 32 } 

tl1fddiMACFrameCt OBJECT-TYPE
   SYNTAX  Counter
   ACCESS  read-only
   STATUS  mandatory
   ::= { tl1fddiMACStatEntry 33 } 

tl1fddiMACLostCt OBJECT-TYPE
   SYNTAX  Counter
   ACCESS  read-only
   STATUS  mandatory
   ::= { tl1fddiMACStatEntry 34 } 

tl1fddiMACErrorCt OBJECT-TYPE
   SYNTAX  Counter
   ACCESS  read-only
   STATUS  mandatory
   ::= { tl1fddiMACStatEntry 35 } 
   
tl1fddiMACOutOfBuf OBJECT-TYPE
   SYNTAX  Counter
   ACCESS  read-only
   STATUS  mandatory
   ::= { tl1fddiMACStatEntry 36 } 

tl1fddiMACReceiveCt OBJECT-TYPE
   SYNTAX  Counter
   ACCESS  read-only
   STATUS  mandatory
   ::= { tl1fddiMACStatEntry 37 } 

tl1fddiMACTransmitCt OBJECT-TYPE
   SYNTAX  Counter
   ACCESS  read-only
   STATUS  mandatory
   ::= { tl1fddiMACStatEntry 38 } 

tl1fddiMACInternalErrorCt OBJECT-TYPE
   SYNTAX  Counter
   ACCESS  read-only
   STATUS  mandatory
   ::= { tl1fddiMACStatEntry 39 } 

tl1fddiMACTneg OBJECT-TYPE
   SYNTAX  INTEGER
   ACCESS  read-only
   STATUS  mandatory
   ::= { tl1fddiMACStatEntry 40 } 

tl1fddiSMTStnStateTable OBJECT-TYPE
   SYNTAX  SEQUENCE OF Tl1fddiSMTStnStateEntry
   ACCESS  read-only
   STATUS  mandatory
   ::= { tl1fddi 2 }

tl1fddiSMTStnStateEntry OBJECT-TYPE
   SYNTAX  Tl1fddiSMTStnStateEntry
   ACCESS  read-only
   STATUS  mandatory
   ::= { tl1fddiSMTStnStateTable 1 }

Tl1fddiSMTStnStateEntry ::= SEQUENCE {
	tl1fddiSMTStnType
	     INTEGER,
	tl1fddiSMTVersionId
	     INTEGER,
	tl1fddiSMTMACCount
	     INTEGER,
	tl1fddiSMTAttachCount
	     INTEGER,
	tl1fddiSMTMasterCount
	     INTEGER,
	tl1fddiSMTDasScmState
	     INTEGER,
	tl1fddiSMTStnId
             OCTET STRING
}

tl1fddiSMTStnType OBJECT-TYPE
   SYNTAX  INTEGER {
		station(1),
		concentrator(2)
           }
   ACCESS  read-only
   STATUS  mandatory
   ::= { tl1fddiSMTStnStateEntry 1 }

tl1fddiSMTVersionId OBJECT-TYPE
   SYNTAX  INTEGER
   ACCESS  read-only
   STATUS  mandatory
   ::= { tl1fddiSMTStnStateEntry 2 }
   
tl1fddiSMTMACCount OBJECT-TYPE
   SYNTAX  INTEGER
   ACCESS  read-only
   STATUS  mandatory
   ::= { tl1fddiSMTStnStateEntry 3 }
   
tl1fddiSMTAttachCount OBJECT-TYPE
   SYNTAX  INTEGER
   ACCESS  read-only
   STATUS  mandatory
   ::= { tl1fddiSMTStnStateEntry 4 }

tl1fddiSMTMasterCount OBJECT-TYPE
   SYNTAX  INTEGER
   ACCESS  read-only
   STATUS  mandatory
   ::= { tl1fddiSMTStnStateEntry 5 }
   
tl1fddiSMTDasScmState OBJECT-TYPE
   SYNTAX  INTEGER {
                isolated(1),
                wrap-a(2),
                wrap-b(3),
                thru(4),
                cleave-a(6),
                cleave-b(7)
           }
   ACCESS  read-only
   STATUS  mandatory
   ::= { tl1fddiSMTStnStateEntry 6 }

tl1fddiSMTStnId OBJECT-TYPE
   SYNTAX  OCTET STRING (SIZE (6))
   ACCESS  read-only 
   STATUS  mandatory
   ::= { tl1fddiSMTStnStateEntry 7 }

tl1fddiPHYStateTable OBJECT-TYPE
   SYNTAX  SEQUENCE OF Tl1fddiPHYStateEntry
   ACCESS  read-only
   STATUS  mandatory
   ::= { tl1fddi 3 }

tl1fddiPHYStateEntry OBJECT-TYPE
   SYNTAX  Tl1fddiPHYStateEntry
   ACCESS  read-only
   STATUS  mandatory
   ::= { tl1fddiPHYStateTable 1 }

Tl1fddiPHYStateEntry ::= SEQUENCE {
	tl1fddiPHYType
	     INTEGER,
   	tl1fddiPHYConnectState
	     INTEGER,
   	tl1fddiPHYRemotePHYType
	     INTEGER,
   	tl1fddiPHYRemoteMACIndicated
	     INTEGER,
   	tl1fddiPHYResourceIndex
	     INTEGER,
   	tl1fddiPHYConnectedResId
	     INTEGER
}

tl1fddiPHYType OBJECT-TYPE
   SYNTAX  INTEGER {
		a(1),
		b(2),
		s(3),
		m(4)
	   }
   ACCESS  read-only
   STATUS  mandatory
   ::= { tl1fddiPHYStateEntry 1 }
   
tl1fddiPHYConnectState OBJECT-TYPE
   SYNTAX  INTEGER {
		disabled(1),
		connecting(2),
		standby(3),
		active(4)
	   }
   ACCESS  read-only
   STATUS  mandatory
   ::= { tl1fddiPHYStateEntry 2 }

tl1fddiPHYRemotePHYType OBJECT-TYPE
   SYNTAX  INTEGER {
		a(1),
		b(2),
		s(3),
		m(4),
		unknown(5)
	   }
   ACCESS  read-only
   STATUS  mandatory
   ::= { tl1fddiPHYStateEntry 3 }
   
tl1fddiPHYRemoteMACIndicated OBJECT-TYPE
   SYNTAX  INTEGER 
   ACCESS  read-only
   STATUS  mandatory
   ::= { tl1fddiPHYStateEntry 4 }

tl1fddiPHYResourceIndex OBJECT-TYPE
   SYNTAX  INTEGER
   ACCESS  read-only
   STATUS  mandatory
   ::= { tl1fddiPHYStateEntry 5 }

tl1fddiPHYConnectedResId OBJECT-TYPE
   SYNTAX  INTEGER
   ACCESS  read-only
   STATUS  mandatory
   ::= { tl1fddiPHYStateEntry 6 }

tl1fddiSMTOperationalTable OBJECT-TYPE
   SYNTAX  SEQUENCE OF Tl1fddiSMTOperationalEntry
   ACCESS  read-write
   STATUS  mandatory
   ::= { tl1fddi 4 }
   
tl1fddiSMTOperationalEntry OBJECT-TYPE
   SYNTAX  Tl1fddiSMTOperationalEntry
   ACCESS  read-write
   STATUS  mandatory
   ::= { tl1fddiSMTOperationalTable 1 }
   
Tl1fddiSMTOperationalEntry ::= SEQUENCE {
        tl1fddiSMTLinkErrorRateCutoff
             INTEGER,
        tl1fddiSMTLinkErrorRateAlarm
             INTEGER,
        tl1fddiSMTByPassSwitchPresent
             INTEGER,
        tl1fddiSMTAttachConfiguration
             INTEGER
}

tl1fddiSMTLinkErrorRateCutoff OBJECT-TYPE
   SYNTAX  INTEGER (1..10)
   ACCESS  read-write
   STATUS  mandatory
   ::= { tl1fddiSMTOperationalEntry 1 }
   
tl1fddiSMTLinkErrorRateAlarm OBJECT-TYPE
   SYNTAX  INTEGER (1..10)
   ACCESS  read-write
   STATUS  mandatory
   ::= { tl1fddiSMTOperationalEntry 2 }
   
tl1fddiSMTByPassSwitchPresent OBJECT-TYPE
   SYNTAX  INTEGER {
                true(1),
                false(0)     
           }
   ACCESS  read-write
   STATUS  mandatory
   ::= { tl1fddiSMTOperationalEntry 3 }
   
tl1fddiSMTAttachConfiguration OBJECT-TYPE
   SYNTAX  INTEGER {
		cleave-A(1),
		cleave-B(2),
		dualattach(3)
	   }
   ACCESS  read-write
   STATUS  mandatory
   ::= { tl1fddiSMTOperationalEntry 4 }
   
tl1fddiMACOperationalTable OBJECT-TYPE
   SYNTAX  SEQUENCE OF Tl1fddiMACOperationalEntry
   ACCESS  read-write
   STATUS  mandatory
   ::= { tl1fddi 5 }

tl1fddiMACOperationalEntry OBJECT-TYPE
   SYNTAX  Tl1fddiMACOperationalEntry
   ACCESS  read-write
   STATUS  mandatory
   ::= { tl1fddiMACOperationalTable 1 }

Tl1fddiMACOperationalEntry ::= SEQUENCE {
	tl1fddiMACTReq
	     INTEGER,
	tl1fddiMACTMax
	     INTEGER,
	tl1fddiMACTvxValue
	     INTEGER,
	tl1fddiMACTMin
	     INTEGER,
        tl1fddiMACRcvThrot
             INTEGER
}
   
tl1fddiMACTReq OBJECT-TYPE
   SYNTAX  INTEGER (4000..335540)
   ACCESS  read-write
   STATUS  mandatory
   ::= { tl1fddiMACOperationalEntry 1 }
   
tl1fddiMACTMax OBJECT-TYPE
   SYNTAX  INTEGER (4000..335540)
   ACCESS  read-write
   STATUS  mandatory
   ::= { tl1fddiMACOperationalEntry 2 }
   
tl1fddiMACTvxValue OBJECT-TYPE
   SYNTAX  INTEGER (1..5000)
   ACCESS  read-write
   STATUS  mandatory
   ::= { tl1fddiMACOperationalEntry 3 }
   
tl1fddiMACTMin OBJECT-TYPE
   SYNTAX  INTEGER (4000..335540)
   ACCESS  read-write
   STATUS  mandatory
   ::= { tl1fddiMACOperationalEntry 4 }
   
tl1fddiMACRcvThrot OBJECT-TYPE
   SYNTAX  INTEGER 
   ACCESS  read-write
   STATUS  mandatory
   ::= { tl1fddiMACOperationalEntry 5 }
   
tl1fddiPHYOperationalTable OBJECT-TYPE
   SYNTAX  SEQUENCE OF Tl1fddiPHYOperationalEntry
   ACCESS  read-write
   STATUS  mandatory
   ::= { tl1fddi 6 }
    
tl1fddiPHYOperationalEntry OBJECT-TYPE
   SYNTAX  Tl1fddiPHYOperationalEntry
   ACCESS  read-write
   STATUS  mandatory
   ::= { tl1fddiPHYOperationalTable 1 }
    
Tl1fddiPHYOperationalEntry ::= SEQUENCE {
        tl1fddiPHYAction
             INTEGER
}
   
tl1fddiPHYAction OBJECT-TYPE
   SYNTAX  INTEGER {
		enabled(0),
		disabled(1)
	   }
   ACCESS  read-write
   STATUS  mandatory
   ::= { tl1fddiPHYOperationalEntry 1 }

tl1fddiSMTNeighborTable OBJECT-TYPE
   SYNTAX  SEQUENCE OF Tl1fddiSMTNeighborEntry
   ACCESS  read-only
   STATUS  mandatory
   ::= { tl1fddi 7 }
    
tl1fddiSMTNeighborEntry OBJECT-TYPE
   SYNTAX  Tl1fddiSMTNeighborEntry
   ACCESS  read-only
   STATUS  mandatory
   ::= { tl1fddiSMTNeighborTable 1 }
    
Tl1fddiSMTNeighborEntry ::= SEQUENCE {
        tl1fddiSMTStnUpstreamNbr
             OCTET STRING,
        tl1fddiSMTStnDownstreamNbr
             OCTET STRING
}

tl1fddiSMTStnUpstreamNbr OBJECT-TYPE
   SYNTAX  OCTET STRING (SIZE (6))
   ACCESS  read-only
   STATUS  mandatory
   ::= { tl1fddiSMTNeighborEntry 1 }

tl1fddiSMTStnDownstreamNbr OBJECT-TYPE
   SYNTAX  OCTET STRING (SIZE (6))
   ACCESS  read-only
   STATUS  mandatory
   ::= { tl1fddiSMTNeighborEntry 2 }

        -- the TL1 STAP Group
   
tl1stapSpanningTreeEnabled OBJECT-TYPE
   SYNTAX  INTEGER {
                disabled(0),
                enabled(1)
           }
   ACCESS  read-write
   STATUS  mandatory
   ::= { tl1stapBridgeConfig 1 }

tl1stapCMaxBridgeTransDelay OBJECT-TYPE
   SYNTAX  INTEGER (1..4)
   ACCESS  read-write
   STATUS  mandatory
   ::= { tl1stapBridgeConfig 3 }

tl1stapCMaxBpduTransDelay OBJECT-TYPE
   SYNTAX  INTEGER (1..4)
   ACCESS  read-write
   STATUS  mandatory
   ::= { tl1stapBridgeConfig 4 }

tl1stapCBridgeHelloTime OBJECT-TYPE
   SYNTAX  INTEGER (1..10)
   ACCESS  read-write
   STATUS  mandatory
   ::= { tl1stapBridgeConfig 6 }
   
tl1stapCBridgeMaxAge OBJECT-TYPE
   SYNTAX  INTEGER (6..40)
   ACCESS  read-write
   STATUS  mandatory
   ::= { tl1stapBridgeConfig 7 }

tl1stapCForwardDelay OBJECT-TYPE
   SYNTAX  INTEGER (4..30)
   ACCESS  read-write
   STATUS  mandatory
   ::= { tl1stapBridgeConfig 8 }

tl1stapCBridgePriority OBJECT-TYPE
   SYNTAX  INTEGER (0..65535)
   ACCESS  read-write
   STATUS  mandatory
   ::= { tl1stapBridgeConfig 9 }
   
tl1stapPortConfigTable OBJECT-TYPE
   SYNTAX  SEQUENCE OF Tl1stapPortConfigEntry 
   ACCESS  read-write
   STATUS  mandatory
   ::= { tl1stap 2 }
   
tl1stapPortConfigEntry  OBJECT-TYPE
   SYNTAX  Tl1stapPortConfigEntry 
   ACCESS  read-write
   STATUS  mandatory
   ::= { tl1stapPortConfigTable 1 }
   
Tl1stapPortConfigEntry ::= SEQUENCE {
        tl1stapCPortState
             INTEGER,
        tl1stapCPortPriority
             INTEGER,
        tl1stapCPathCost
             INTEGER
}
   
tl1stapCPortState OBJECT-TYPE
   SYNTAX  INTEGER {
                disable(0),
                enabled(1)
           }
   ACCESS  read-write
   STATUS  mandatory
   ::= { tl1stapPortConfigEntry 1 }
   
tl1stapCPortPriority OBJECT-TYPE
   SYNTAX  INTEGER (0..255)
   ACCESS  read-write
   STATUS  mandatory
   ::= { tl1stapPortConfigEntry 2 }

tl1stapCPathCost OBJECT-TYPE
   SYNTAX  INTEGER  (1..65535)
   ACCESS  read-write
   STATUS  mandatory
   ::= { tl1stapPortConfigEntry 3 }

tl1stapBridgeIdentifier OBJECT-TYPE
   SYNTAX  OCTET STRING (SIZE (8))
   ACCESS  read-only
   STATUS  mandatory
   ::= { tl1stapBridgeState 1 }
   
tl1stapTimeSinceTopChange OBJECT-TYPE
   SYNTAX  TimeTicks
   ACCESS  read-only
   STATUS  mandatory
   ::= { tl1stapBridgeState 2 }

tl1stapTopologyChangeCount OBJECT-TYPE
   SYNTAX  Counter
   ACCESS  read-only
   STATUS  mandatory
   ::= { tl1stapBridgeState 3 }

tl1stapTopologyChange OBJECT-TYPE
   SYNTAX  INTEGER {
                true(1),
                false(0)
           }
   ACCESS  read-only
   STATUS  mandatory
   ::= { tl1stapBridgeState 4 }
   
tl1stapDesignatedRoot OBJECT-TYPE
   SYNTAX  OCTET STRING (SIZE (8))
   ACCESS  read-only
   STATUS  mandatory
   ::= { tl1stapBridgeState 5 }

tl1stapRootPathCost OBJECT-TYPE
   SYNTAX  INTEGER 
   ACCESS  read-only
   STATUS  mandatory
   ::= { tl1stapBridgeState 6 }

tl1stapRootPort OBJECT-TYPE
   SYNTAX  INTEGER
   ACCESS  read-only
   STATUS  mandatory
   ::= { tl1stapBridgeState 7 }
   
tl1stapMaxAge OBJECT-TYPE
   SYNTAX  INTEGER (6..40)
   ACCESS  read-only
   STATUS  mandatory
   ::= { tl1stapBridgeState 8 }
   
tl1stapHelloTime OBJECT-TYPE
   SYNTAX  INTEGER (1..10)
   ACCESS  read-only
   STATUS  mandatory
   ::= { tl1stapBridgeState 9 }

tl1stapForwardDelay OBJECT-TYPE
   SYNTAX  INTEGER (4..30)
   ACCESS  read-only
   STATUS  mandatory
   ::= { tl1stapBridgeState 10 }

tl1stapBridgeMaxAge OBJECT-TYPE
   SYNTAX  INTEGER (6..40)
   ACCESS  read-only
   STATUS  mandatory
   ::= { tl1stapBridgeState 11 }

tl1stapBridgeHelloTime OBJECT-TYPE
   SYNTAX  INTEGER (1..10)
   ACCESS  read-only
   STATUS  mandatory
   ::= { tl1stapBridgeState 12 }
   
tl1stapBridgeForwardDelay OBJECT-TYPE
   SYNTAX  INTEGER (4..30)
   ACCESS  read-only
   STATUS  mandatory
   ::= { tl1stapBridgeState 13 }

tl1stapHoldTime OBJECT-TYPE
   SYNTAX  INTEGER
   ACCESS  read-only
   STATUS  mandatory
   ::= { tl1stapBridgeState 14 }

tl1stapPortStateTable OBJECT-TYPE
   SYNTAX  SEQUENCE OF Tl1stapPortStateEntry 
   ACCESS  read-only
   STATUS  mandatory
   ::= { tl1stap 4 }

tl1stapPortStateEntry  OBJECT-TYPE
   SYNTAX  Tl1stapPortStateEntry 
   ACCESS  read-only
   STATUS  mandatory
   ::= { tl1stapPortStateTable 1 }

Tl1stapPortStateEntry ::= SEQUENCE {
        tl1stapPortIdentifier
             INTEGER,        
        tl1stapPortState
             INTEGER,
        tl1stapPathCost
             INTEGER,
        tl1stapPDesignatedRoot
             OCTET STRING,
        tl1stapPDesignatedCost
             INTEGER,
        tl1stapPDesignatedBridge        
             OCTET STRING,
        tl1stapPDesignatedPort          
             INTEGER,
        tl1stapPTopologyChangeAck        
             INTEGER,
        tl1stapPConfigPending
             INTEGER
}

tl1stapPortIdentifier OBJECT-TYPE
   SYNTAX  INTEGER
   ACCESS  read-only
   STATUS  mandatory
   ::= { tl1stapPortStateEntry 1 }
   
tl1stapPortState OBJECT-TYPE
   SYNTAX  INTEGER {
		disabled(0),
                listening(1),
                learning(2),
                forwarding(3),
                blocking(4)
           }
   ACCESS  read-only
   STATUS  mandatory
   ::= { tl1stapPortStateEntry 2 }

tl1stapPathCost OBJECT-TYPE
   SYNTAX  INTEGER (1..65535)
   ACCESS  read-only
   STATUS  mandatory
   ::= { tl1stapPortStateEntry 3 }
   
tl1stapPDesignatedRoot OBJECT-TYPE
   SYNTAX  OCTET STRING (SIZE (8))
   ACCESS  read-only
   STATUS  mandatory
   ::= { tl1stapPortStateEntry 4 }
   
tl1stapPDesignatedCost OBJECT-TYPE
   SYNTAX  INTEGER 
   ACCESS  read-only
   STATUS  mandatory
   ::= { tl1stapPortStateEntry 5 }

tl1stapPDesignatedBridge OBJECT-TYPE
   SYNTAX  OCTET STRING (SIZE (8))
   ACCESS  read-only
   STATUS  mandatory
   ::= { tl1stapPortStateEntry 6 }

tl1stapPDesignatedPort OBJECT-TYPE
   SYNTAX  INTEGER 
   ACCESS  read-only
   STATUS  mandatory
   ::= { tl1stapPortStateEntry 7 }
   
tl1stapPTopologyChangeAck OBJECT-TYPE
   SYNTAX  INTEGER {
                true(1),
                false(0)
           }
   ACCESS  read-only
   STATUS  mandatory
   ::= { tl1stapPortStateEntry 8 }

tl1stapPConfigPending OBJECT-TYPE
   SYNTAX  INTEGER {
                true(1),
                false(0)
           }
   ACCESS  read-only
   STATUS  mandatory
   ::= { tl1stapPortStateEntry 9 }

        -- the TL1 IDP Group
   
tl1idpInterfaceTable OBJECT-TYPE
   SYNTAX  SEQUENCE OF Tl1idpInterfaceEntry
   ACCESS  read-write
   STATUS  mandatory
   ::= { tl1idp 1 }

tl1idpInterfaceEntry OBJECT-TYPE
   SYNTAX  Tl1idpInterfaceEntry
   ACCESS  read-write
   STATUS  mandatory
   ::= { tl1idpInterfaceTable 1 }

Tl1idpInterfaceEntry ::= SEQUENCE {
       	tl1idpRouteSupplier
             INTEGER, 
        tl1idpGenChecksum
             INTEGER 
}

tl1idpRouteSupplier OBJECT-TYPE
   SYNTAX  INTEGER {
                true(1),
                false(0)
           }
   ACCESS  read-write
   STATUS  mandatory
   ::= { tl1idpInterfaceEntry 1 }

tl1idpGenChecksum OBJECT-TYPE
   SYNTAX  INTEGER {
                true(1),
                false(0)
           }
   ACCESS  read-write
   STATUS  mandatory
   ::= { tl1idpInterfaceEntry 2 }

tl1idpBroadcastInterval OBJECT-TYPE
   SYNTAX  INTEGER 
   ACCESS  read-write
   STATUS  mandatory
   ::= { tl1idp 2 }
   
tl1idpRouteTimeout OBJECT-TYPE
   SYNTAX  INTEGER 
   ACCESS  read-write
   STATUS  mandatory
   ::= { tl1idp 3 }

tl1idpWellKnownGatewayNet OBJECT-TYPE
   SYNTAX  INTEGER
   ACCESS  read-write
   STATUS  mandatory
   ::= { tl1idp 4 }

tl1idpWellKnownGatewayHost OBJECT-TYPE
   SYNTAX  OCTET STRING (SIZE (6))
   ACCESS  read-write
   STATUS  mandatory
   ::= { tl1idp 5 }
   
tl1idpNbrStaticRoutes OBJECT-TYPE
   SYNTAX  INTEGER
   ACCESS  read-write
   STATUS  mandatory
   ::= { tl1idp 6 }
   
tl1idpStaticRouteTable OBJECT-TYPE
   SYNTAX  SEQUENCE OF Tl1idpStaticRouteEntry
   ACCESS  read-write
   STATUS  mandatory
   ::= { tl1idp 7 }

tl1idpStaticRouteEntry OBJECT-TYPE
   SYNTAX  Tl1idpStaticRouteEntry
   ACCESS  read-write
   STATUS  mandatory
   ::= { tl1idpStaticRouteTable 1 }

Tl1idpStaticRouteEntry ::= SEQUENCE {
	tl1idpStaticRouteNetwork
	     INTEGER,
       	tl1idpStaticRouteGatewayNet
             INTEGER,
       	tl1idpStaticRouteGatewayHost
             OCTET STRING,
	tl1idpStaticRouteCost
             INTEGER,
	tl1idpStaticRouteOverride
             INTEGER
}

tl1idpStaticRouteNetwork OBJECT-TYPE
   SYNTAX  INTEGER
   ACCESS  read-only
   STATUS  mandatory
   ::= { tl1idpStaticRouteEntry 1 }

tl1idpStaticRouteGatewayNet OBJECT-TYPE
   SYNTAX  INTEGER
   ACCESS  read-write
   STATUS  mandatory
   ::= { tl1idpStaticRouteEntry 2 }

tl1idpStaticRouteGatewayHost OBJECT-TYPE
   SYNTAX  OCTET STRING (SIZE (6))
   ACCESS  read-write
   STATUS  mandatory
   ::= { tl1idpStaticRouteEntry 3 }

tl1idpStaticRouteCost OBJECT-TYPE
   SYNTAX  INTEGER (0..255)
   ACCESS  read-write
   STATUS  mandatory
   ::= { tl1idpStaticRouteEntry 4 }

tl1idpStaticRouteOverride OBJECT-TYPE
   SYNTAX  INTEGER {
                true(1),
                false(0)
           }
   ACCESS  read-write
   STATUS  mandatory
   ::= { tl1idpStaticRouteEntry 5 }

tl1idpNbrFilters OBJECT-TYPE
   SYNTAX  INTEGER
   ACCESS  read-write
   STATUS  mandatory
   ::= { tl1idp 8 }

tl1idpFilterTable OBJECT-TYPE
   SYNTAX  SEQUENCE OF Tl1idpFilterEntry
   ACCESS  read-write
   STATUS  mandatory
   ::= { tl1idp 9 }

tl1idpFilterEntry OBJECT-TYPE
   SYNTAX  Tl1idpFilterEntry
   ACCESS  read-write
   STATUS  mandatory
   ::= { tl1idpFilterTable 1 }

Tl1idpFilterEntry ::= SEQUENCE {
	tl1idpFilterSourceMask
	     INTEGER,
       	tl1idpFilterSourceNet
             INTEGER,
       	tl1idpFilterSourceHost
             OCTET STRING,
	tl1idpFilterDestinationMask
	     INTEGER,
       	tl1idpFilterDestinationNet
             INTEGER,
       	tl1idpFilterDestinationHost
             OCTET STRING,
	tl1idpFilterNbrExceptions
             INTEGER
}

tl1idpFilterSourceMask OBJECT-TYPE
   SYNTAX  INTEGER
   ACCESS  read-write
   STATUS  mandatory
   ::= { tl1idpFilterEntry 1 }

tl1idpFilterSourceNet OBJECT-TYPE
   SYNTAX  INTEGER
   ACCESS  read-write
   STATUS  mandatory
   ::= { tl1idpFilterEntry 2 }
   
tl1idpFilterSourceHost OBJECT-TYPE
   SYNTAX  OCTET STRING (SIZE (6))
   ACCESS  read-write
   STATUS  mandatory
   ::= { tl1idpFilterEntry 3 }

tl1idpFilterDestinationMask OBJECT-TYPE
   SYNTAX  INTEGER
   ACCESS  read-write
   STATUS  mandatory
   ::= { tl1idpFilterEntry 4 }
   
tl1idpFilterDestinationNet OBJECT-TYPE
   SYNTAX  INTEGER
   ACCESS  read-write
   STATUS  mandatory
   ::= { tl1idpFilterEntry 5 }
   
tl1idpFilterDestinationHost OBJECT-TYPE
   SYNTAX  OCTET STRING (SIZE (6))
   ACCESS  read-write
   STATUS  mandatory
   ::= { tl1idpFilterEntry 6 }

tl1idpFilterNbrExceptions OBJECT-TYPE
   SYNTAX  INTEGER
   ACCESS  read-write
   STATUS  mandatory
   ::= { tl1idpFilterEntry 7 }

tl1idpFilterExceptionTable OBJECT-TYPE
   SYNTAX  SEQUENCE OF Tl1idpFilterExceptionEntry
   ACCESS  read-write
   STATUS  mandatory
   ::= { tl1idp 10 }

tl1idpFilterExceptionEntry OBJECT-TYPE
   SYNTAX  Tl1idpFilterExceptionEntry
   ACCESS  read-write
   STATUS  mandatory
   ::= { tl1idpFilterExceptionTable 1 }

Tl1idpFilterExceptionEntry ::= SEQUENCE {
       	tl1idpFilterExceptionSrcNet
             INTEGER,
       	tl1idpFilterExceptionSrcHost
             OCTET STRING,
       	tl1idpFilterExceptionDstNet
             INTEGER,
       	tl1idpFilterExceptionDstHost
             OCTET STRING
}
   
tl1idpFilterExceptionSrcNet OBJECT-TYPE
   SYNTAX  INTEGER
   ACCESS  read-write
   STATUS  mandatory
   ::= { tl1idpFilterExceptionEntry 1 }

tl1idpFilterExceptionSrcHost OBJECT-TYPE
   SYNTAX  OCTET STRING (SIZE (6))
   ACCESS  read-write
   STATUS  mandatory
   ::= { tl1idpFilterExceptionEntry 2 }

tl1idpFilterExceptionDstNet OBJECT-TYPE
   SYNTAX  INTEGER
   ACCESS  read-write
   STATUS  mandatory
   ::= { tl1idpFilterExceptionEntry 3 }

tl1idpFilterExceptionDstHost OBJECT-TYPE
   SYNTAX  OCTET STRING (SIZE (6))
   ACCESS  read-write
   STATUS  mandatory
   ::= { tl1idpFilterExceptionEntry 4 }

tl1idpForwarding OBJECT-TYPE
   SYNTAX  INTEGER {
                gateway-thus-forward(1),
                host-thus-dont-forward(2)
           }
   ACCESS  read-only
   STATUS  mandatory
   ::= { tl1idp 11 }

tl1idpInReceives OBJECT-TYPE
   SYNTAX  Counter
   ACCESS  read-only
   STATUS  mandatory
   ::= { tl1idp 12 }
   
tl1idpInHdrErrors OBJECT-TYPE
   SYNTAX  Counter
   ACCESS  read-only
   STATUS  mandatory
   ::= { tl1idp 13 }

tl1idpForwDatagrams OBJECT-TYPE
   SYNTAX  Counter
   ACCESS  read-only
   STATUS  mandatory
   ::= { tl1idp 14 }

tl1idpOutNoRoutes OBJECT-TYPE
   SYNTAX  Counter
   ACCESS  read-only
   STATUS  mandatory
   ::= { tl1idp 15 }

tl1idpNumStatic OBJECT-TYPE
   SYNTAX  Counter
   ACCESS  read-only
   STATUS  mandatory
   ::= { tl1idp 16 }

tl1idpBadSize OBJECT-TYPE
   SYNTAX  Counter
   ACCESS  read-only
   STATUS  mandatory
   ::= { tl1idp 17 }

tl1idpInMsgs OBJECT-TYPE
   SYNTAX  Counter
   ACCESS  read-only
   STATUS  mandatory
   ::= { tl1idp 18 }
   
tl1idpErrInEchos OBJECT-TYPE
   SYNTAX  Counter
   ACCESS  read-only
   STATUS  mandatory
   ::= { tl1idp 19 }

tl1idpInEchos OBJECT-TYPE
   SYNTAX  Counter
   ACCESS  read-only
   STATUS  mandatory
   ::= { tl1idp 20 }

tl1idpInEchoReply OBJECT-TYPE
   SYNTAX  Counter
   ACCESS  read-only
   STATUS  mandatory
   ::= { tl1idp 21 }

tl1idpOutEchoReps OBJECT-TYPE
   SYNTAX  Counter
   ACCESS  read-only
   STATUS  mandatory
   ::= { tl1idp 22 }
   
tl1idpErrInUnspecified OBJECT-TYPE
   SYNTAX  Counter
   ACCESS  read-only
   STATUS  mandatory
   ::= { tl1idp 23 }

tl1idpErrInChecksum OBJECT-TYPE
   SYNTAX  Counter
   ACCESS  read-only
   STATUS  mandatory
   ::= { tl1idp 24 }

tl1idpErrInSocket OBJECT-TYPE
   SYNTAX  Counter
   ACCESS  read-only
   STATUS  mandatory
   ::= { tl1idp 25 }

tl1idpErrInResources OBJECT-TYPE
   SYNTAX  Counter
   ACCESS  read-only
   STATUS  mandatory
   ::= { tl1idp 26 }

tl1idpErrInNohost OBJECT-TYPE
   SYNTAX  Counter
   ACCESS  read-only
   STATUS  mandatory
   ::= { tl1idp 27 }

tl1idpErrInMaxhops OBJECT-TYPE
   SYNTAX  Counter
   ACCESS  read-only
   STATUS  mandatory
   ::= { tl1idp 28 }
   
tl1idpErrInSizetoobig OBJECT-TYPE
   SYNTAX  Counter
   ACCESS  read-only
   STATUS  mandatory
   ::= { tl1idp 29 }

tl1idpErrInErrors OBJECT-TYPE
   SYNTAX  Counter
   ACCESS  read-only
   STATUS  mandatory
   ::= { tl1idp 30 }

tl1idpInErrors OBJECT-TYPE
   SYNTAX  Counter
   ACCESS  read-only
   STATUS  mandatory
   ::= { tl1idp 31 }

tl1idpErrOutMsgs OBJECT-TYPE
   SYNTAX  Counter
   ACCESS  read-only
   STATUS  mandatory
   ::= { tl1idp 32 }

tl1idpErrOutErrors OBJECT-TYPE
   SYNTAX  Counter
   ACCESS  read-only
   STATUS  mandatory
   ::= { tl1idp 33 }

tl1idpErrOutUnspecified OBJECT-TYPE
   SYNTAX  Counter
   ACCESS  read-only
   STATUS  mandatory
   ::= { tl1idp 34 }
   
tl1idpErrOutChecksum OBJECT-TYPE
   SYNTAX  Counter
   ACCESS  read-only
   STATUS  mandatory
   ::= { tl1idp 35 }

tl1idpErrOutSocket OBJECT-TYPE
   SYNTAX  Counter
   ACCESS  read-only
   STATUS  mandatory
   ::= { tl1idp 36 }

tl1idpErrOutResources OBJECT-TYPE
   SYNTAX  Counter
   ACCESS  read-only
   STATUS  mandatory
   ::= { tl1idp 37 }

tl1idpErrOutNohost OBJECT-TYPE
   SYNTAX  Counter
   ACCESS  read-only
   STATUS  mandatory
   ::= { tl1idp 38 }

tl1idpErrOutMaxhops OBJECT-TYPE
   SYNTAX  Counter
   ACCESS  read-only
   STATUS  mandatory
   ::= { tl1idp 39 }

tl1idpErrOutSizetoobig OBJECT-TYPE
   SYNTAX  Counter
   ACCESS  read-only
   STATUS  mandatory
   ::= { tl1idp 40 }

tl1idpInOwnAddr OBJECT-TYPE
   SYNTAX  Counter
   ACCESS  read-only
   STATUS  mandatory
   ::= { tl1idp 41 }

tl1idpInNoRoutes OBJECT-TYPE
   SYNTAX  Counter
   ACCESS  read-only
   STATUS  mandatory
   ::= { tl1idp 42 }

tl1idpFilter OBJECT-TYPE
   SYNTAX  Counter
   ACCESS  read-only
   STATUS  mandatory
   ::= { tl1idp 43 }

tl1idpHashHit OBJECT-TYPE
   SYNTAX  Counter
   ACCESS  read-only
   STATUS  mandatory
   ::= { tl1idp 44 }

tl1idpHashMiss OBJECT-TYPE
   SYNTAX  Counter
   ACCESS  read-only
   STATUS  mandatory
   ::= { tl1idp 45 }

tl1idpBadMetric OBJECT-TYPE
   SYNTAX  Counter
   ACCESS  read-only
   STATUS  mandatory
   ::= { tl1idp 46 }

tl1idpBadAlloc OBJECT-TYPE
   SYNTAX  Counter
   ACCESS  read-only
   STATUS  mandatory
   ::= { tl1idp 47 }

tl1idpBadNbr OBJECT-TYPE
   SYNTAX  Counter
   ACCESS  read-only
   STATUS  mandatory
   ::= { tl1idp 48 }

tl1idpBadCommand OBJECT-TYPE
   SYNTAX  Counter
   ACCESS  read-only
   STATUS  mandatory
   ::= { tl1idp 49 }

tl1idpBadAddr OBJECT-TYPE
   SYNTAX  Counter
   ACCESS  read-only
   STATUS  mandatory
   ::= { tl1idp 50 }

tl1idpNetworkIntfTable OBJECT-TYPE
   SYNTAX  SEQUENCE OF Tl1idpNetworkIntfEntry
   ACCESS  read-write
   STATUS  mandatory
   ::= { tl1idp 51 }

tl1idpNetworkIntfEntry OBJECT-TYPE
   SYNTAX  Tl1idpNetworkIntfEntry
   ACCESS  read-write
   STATUS  mandatory
   ::= { tl1idpNetworkIntfTable 1 }

Tl1idpNetworkIntfEntry ::= SEQUENCE {
       	tl1idpNetworkMaximumPacket
             INTEGER,
       	tl1idpNetworkAddress
             INTEGER
}

tl1idpNetworkMaximumPacket OBJECT-TYPE
   SYNTAX  INTEGER
   ACCESS  read-write
   STATUS  mandatory
   ::= { tl1idpNetworkIntfEntry 1 }

tl1idpNetworkAddress OBJECT-TYPE
   SYNTAX  INTEGER
   ACCESS  read-write
   STATUS  mandatory
   ::= { tl1idpNetworkIntfEntry 2 }

        -- the TL1 PPP Group

tl1pppInfoTable OBJECT-TYPE
   SYNTAX  SEQUENCE OF Tl1pppInfoEntry 
   ACCESS  read-write
   STATUS  mandatory
   ::= { tl1ppp 1 }

tl1pppInfoEntry  OBJECT-TYPE
   SYNTAX  Tl1pppInfoEntry 
   ACCESS  read-write
   STATUS  mandatory
   ::= { tl1pppInfoTable 1 }

Tl1pppInfoEntry ::= SEQUENCE {
        tl1pppLcpAO
             INTEGER,
        tl1pppIpcpAO
             INTEGER,
        tl1pppIdpcpAO
             INTEGER,
        tl1pppIpxcpAO
             INTEGER,
        tl1pppLqdTimeout
             INTEGER
}

tl1pppLcpAO OBJECT-TYPE
   SYNTAX  INTEGER {
                true(1),
                false(0)
           }
   ACCESS  read-write
   STATUS  mandatory
   ::= { tl1pppInfoEntry 1 }
   
tl1pppIpcpAO OBJECT-TYPE
   SYNTAX  INTEGER {
                true(1),
                false(0)
           }
   ACCESS  read-write
   STATUS  mandatory
   ::= { tl1pppInfoEntry 2 }

tl1pppIdpcpAO OBJECT-TYPE
   SYNTAX  INTEGER {
                true(1),
                false(0)
           }
   ACCESS  read-write
   STATUS  mandatory
   ::= { tl1pppInfoEntry 3 }

tl1pppIpxcpAO OBJECT-TYPE
   SYNTAX  INTEGER {
                true(1),
                false(0)
           }
   ACCESS  read-write
   STATUS  mandatory
   ::= { tl1pppInfoEntry 4 }

tl1pppLqdTimeout OBJECT-TYPE
   SYNTAX  INTEGER
   ACCESS  read-write
   STATUS  mandatory
   ::= { tl1pppInfoEntry 5 }

tl1pppPhaseTable OBJECT-TYPE
   SYNTAX  SEQUENCE OF Tl1pppPhaseEntry
   ACCESS  read-write
   STATUS  mandatory
   ::= { tl1ppp 2 }

tl1pppPhaseEntry OBJECT-TYPE
   SYNTAX  Tl1pppPhaseEntry
   ACCESS  read-write
   STATUS  mandatory
   ::= { tl1pppPhaseTable 1 }

Tl1pppPhaseEntry ::= SEQUENCE { 
        tl1pppCrCount
             INTEGER,
        tl1pppTrCount
             INTEGER,
        tl1pppCtTimeout
             INTEGER,
        tl1pppRsTimeout
             INTEGER
}

tl1pppCrCount OBJECT-TYPE
   SYNTAX  INTEGER
   ACCESS  read-write
   STATUS  mandatory
   ::= { tl1pppPhaseEntry 1 }

tl1pppTrCount OBJECT-TYPE
   SYNTAX  INTEGER
   ACCESS  read-write
   STATUS  mandatory
   ::= { tl1pppPhaseEntry 2 }
   
tl1pppCtTimeout OBJECT-TYPE
   SYNTAX  INTEGER
   ACCESS  read-write
   STATUS  mandatory
   ::= { tl1pppPhaseEntry 3 }

tl1pppRsTimeout OBJECT-TYPE
   SYNTAX  INTEGER
   ACCESS  read-write
   STATUS  mandatory
   ::= { tl1pppPhaseEntry 4 }

tl1pppStatTable OBJECT-TYPE
   SYNTAX  SEQUENCE OF Tl1pppStatEntry 
   ACCESS  read-write
   STATUS  mandatory
   ::= { tl1ppp 3 }

tl1pppStatEntry OBJECT-TYPE
   SYNTAX  Tl1pppStatEntry 
   ACCESS  read-write
   STATUS  mandatory
   ::= { tl1pppStatTable 1 }

Tl1pppStatEntry ::= SEQUENCE { 
        tl1pppBadProtocol
             Counter,
        tl1pppBadAddress
             Counter,
        tl1pppBadLcp
             Counter,
        tl1pppBadIpcp
             Counter,
        tl1pppBadIdpcp
             Counter,
        tl1pppBadIpxcp
             Counter,
        tl1pppNumCrSent
             Counter,
        tl1pppNumCrRecd
             Counter,
        tl1pppNumTrRecd
             Counter
}

tl1pppBadProtocol OBJECT-TYPE
   SYNTAX  Counter
   ACCESS  read-only
   STATUS  mandatory
   ::= { tl1pppStatEntry 1 }

tl1pppBadAddress OBJECT-TYPE
   SYNTAX  Counter
   ACCESS  read-only
   STATUS  mandatory
   ::= { tl1pppStatEntry 2 }

tl1pppBadLcp OBJECT-TYPE
   SYNTAX  Counter
   ACCESS  read-only
   STATUS  mandatory
   ::= { tl1pppStatEntry 3 }
   
tl1pppBadIpcp OBJECT-TYPE
   SYNTAX  Counter
   ACCESS  read-only
   STATUS  mandatory
   ::= { tl1pppStatEntry 4 }

tl1pppBadIdpcp OBJECT-TYPE
   SYNTAX  Counter
   ACCESS  read-only
   STATUS  mandatory
   ::= { tl1pppStatEntry 5 }

tl1pppBadIpxcp OBJECT-TYPE
   SYNTAX  Counter
   ACCESS  read-only
   STATUS  mandatory
   ::= { tl1pppStatEntry 6 }

tl1pppNumCrSent OBJECT-TYPE
   SYNTAX  Counter
   ACCESS  read-only
   STATUS  mandatory
   ::= { tl1pppStatEntry 7 }

tl1pppNumCrRecd OBJECT-TYPE
   SYNTAX  Counter
   ACCESS  read-only
   STATUS  mandatory
   ::= { tl1pppStatEntry 8 }

tl1pppNumTrRecd OBJECT-TYPE
   SYNTAX  Counter
   ACCESS  read-only
   STATUS  mandatory
   ::= { tl1pppStatEntry 9 }

        -- the TL1 SRTB Group

tl1srtbInternalLanEnabled OBJECT-TYPE
   SYNTAX  INTEGER {
                disabled(0),
                enabled(1)
           }
   ACCESS  read-write
   STATUS  mandatory
   ::= { tl1srtb 1 }

tl1srtbInternalLanId OBJECT-TYPE
   SYNTAX  INTEGER (0..4095)
   ACCESS  read-write
   STATUS  mandatory
   ::= { tl1srtb 2 }

tl1srtbUpTime OBJECT-TYPE
   SYNTAX  TimeTicks
   ACCESS  read-only
   STATUS  mandatory
   ::= { tl1srtb 3 }

tl1srtbPortParamsTable OBJECT-TYPE
   SYNTAX  SEQUENCE OF Tl1srtbPortParamsEntry
   ACCESS  read-write
   STATUS  mandatory
   ::= { tl1srtb 4 }
   
tl1srtbPortParamsEntry OBJECT-TYPE
   SYNTAX  Tl1srtbPortParamsEntry
   ACCESS  read-write
   STATUS  mandatory
   ::= { tl1srtbPortParamsTable 1 }
   
Tl1srtbPortParamsEntry ::= SEQUENCE {
        tl1srtbBridgeNumber 
             INTEGER,
        tl1srtbRoutingType
             INTEGER,
        tl1srtbLanId
             INTEGER,
        tl1srtbIsVLan
             INTEGER,
        tl1srtbRdLimit
             INTEGER,
        tl1srtbOutUserPriority 
             INTEGER,
        tl1srtbOutAccessPriority 
             INTEGER
}
    
tl1srtbBridgeNumber OBJECT-TYPE
   SYNTAX  INTEGER (0..15)
   ACCESS  read-write
   STATUS  mandatory
   ::= { tl1srtbPortParamsEntry 1 }

tl1srtbRoutingType OBJECT-TYPE
   SYNTAX  INTEGER {
                none(-1),
                tb(0),
                srt(1),
                sr(2)
           }
   ACCESS  read-write
   STATUS  mandatory
   ::= { tl1srtbPortParamsEntry 2 }

tl1srtbLanId OBJECT-TYPE
   SYNTAX  INTEGER (0..4095)
   ACCESS  read-write
   STATUS  mandatory
   ::= { tl1srtbPortParamsEntry 3 }

tl1srtbIsVLan OBJECT-TYPE
   SYNTAX  INTEGER {
                false(0),
                true(1)
           }
   ACCESS  read-write
   STATUS  mandatory
   ::= { tl1srtbPortParamsEntry 4 }

tl1srtbRdLimit OBJECT-TYPE
   SYNTAX  INTEGER (0..14)
   ACCESS  read-write
   STATUS  mandatory
   ::= { tl1srtbPortParamsEntry 5 }

tl1srtbOutUserPriority OBJECT-TYPE
   SYNTAX  INTEGER (0..7)
   ACCESS  read-write
   STATUS  mandatory
   ::= { tl1srtbPortParamsEntry 6 }

tl1srtbOutAccessPriority OBJECT-TYPE
   SYNTAX  INTEGER (0..7)
   ACCESS  read-write
   STATUS  mandatory
   ::= { tl1srtbPortParamsEntry 7 }
   
tl1srtbPortCounterTable OBJECT-TYPE
   SYNTAX  SEQUENCE OF Tl1srtbPortCounterEntry
   ACCESS  read-only
   STATUS  mandatory
   ::= { tl1srtb 5 }

tl1srtbPortCounterEntry OBJECT-TYPE
   SYNTAX  Tl1srtbPortCounterEntry
   ACCESS  read-only
   STATUS  mandatory
   ::= { tl1srtbPortCounterTable 1 }

Tl1srtbPortCounterEntry ::= SEQUENCE {
        tl1srtbInTSFramesReceived 
                 Counter,
        tl1srtbInTSFramesDiscarded
                 Counter, 
        tl1srtbOutTSFramesFrwd
                 Counter,
        tl1srtbDiscardBuffers 
                 Counter,
        tl1srtbDiscardTransitDelay
                 Counter,
        tl1srtbDiscardOnError 
                 Counter,
        tl1srtbInvalidRi 
                 Counter,
        tl1srtbLanIdMismatch
                 Counter,
        tl1srtbDupLanIdOrTreeError
                 Counter,
        tl1srtbDiscardHopCountExcd
                 Counter,
        tl1srtbExplorerFramesFrwd
                 Counter,
        tl1srtbExplorerOctetsFrwd
                 Counter,
        tl1srtbNonExplorFramesFrwd 
                 Counter,
        tl1srtbNonExplorOctetsFrwd 
                 Counter,
        tl1srtbTotalSRFrwd
                 Counter,
        tl1srtbValidSRFramesReceived
                 Counter,
        tl1srtbValidExplorOctetsRcvd
                 Counter,
        tl1srtbValidSRDiscarded
                 Counter,
        tl1srtbTotalSRDiscarded
                 Counter
}

tl1srtbInTSFramesReceived OBJECT-TYPE
   SYNTAX  Counter
   ACCESS  read-only
   STATUS  mandatory
   ::= { tl1srtbPortCounterEntry 1 }

tl1srtbInTSFramesDiscarded OBJECT-TYPE
   SYNTAX  Counter
   ACCESS  read-only
   STATUS  mandatory
   ::= { tl1srtbPortCounterEntry 2 }

tl1srtbOutTSFramesFrwd OBJECT-TYPE
   SYNTAX  Counter
   ACCESS  read-only
   STATUS  mandatory
   ::= { tl1srtbPortCounterEntry 3 }

tl1srtbDiscardBuffers OBJECT-TYPE
   SYNTAX  Counter
   ACCESS  read-only
   STATUS  mandatory
   ::= { tl1srtbPortCounterEntry 4 }
   
tl1srtbDiscardTransitDelay OBJECT-TYPE
   SYNTAX  Counter
   ACCESS  read-only
   STATUS  mandatory
   ::= { tl1srtbPortCounterEntry 5 }

tl1srtbDiscardOnError OBJECT-TYPE
   SYNTAX  Counter
   ACCESS  read-only
   STATUS  mandatory
   ::= { tl1srtbPortCounterEntry 6 }

tl1srtbInvalidRi OBJECT-TYPE
   SYNTAX  Counter
   ACCESS  read-only
   STATUS  mandatory
   ::= { tl1srtbPortCounterEntry  7 }

tl1srtbLanIdMismatch OBJECT-TYPE
   SYNTAX  Counter
   ACCESS  read-only
   STATUS  mandatory
   ::= { tl1srtbPortCounterEntry 8 }

tl1srtbDupLanIdOrTreeError  OBJECT-TYPE
   SYNTAX  Counter
   ACCESS  read-only
   STATUS  mandatory
   ::= { tl1srtbPortCounterEntry 9 }

tl1srtbDiscardHopCountExcd OBJECT-TYPE
   SYNTAX  Counter
   ACCESS  read-only
   STATUS  mandatory
   ::= { tl1srtbPortCounterEntry 10 }

tl1srtbExplorerFramesFrwd OBJECT-TYPE
   SYNTAX  Counter
   ACCESS  read-only
   STATUS  mandatory
   ::= { tl1srtbPortCounterEntry 11 }

tl1srtbExplorerOctetsFrwd OBJECT-TYPE
   SYNTAX  Counter
   ACCESS  read-only
   STATUS  mandatory
   ::= { tl1srtbPortCounterEntry 12 }

tl1srtbNonExplorFramesFrwd OBJECT-TYPE
   SYNTAX  Counter
   ACCESS  read-only
   STATUS  mandatory
   ::= { tl1srtbPortCounterEntry 13 } 

tl1srtbNonExplorOctetsFrwd OBJECT-TYPE
   SYNTAX  Counter
   ACCESS  read-only
   STATUS  mandatory
   ::= { tl1srtbPortCounterEntry 14 }

tl1srtbTotalSRFrwd OBJECT-TYPE
   SYNTAX  Counter
   ACCESS  read-only
   STATUS  mandatory
   ::= { tl1srtbPortCounterEntry 15 }

tl1srtbValidSRFramesReceived OBJECT-TYPE
   SYNTAX  Counter
   ACCESS  read-only
   STATUS  mandatory
   ::= { tl1srtbPortCounterEntry 16 }

tl1srtbValidExplorOctetsRcvd OBJECT-TYPE
   SYNTAX  Counter
   ACCESS  read-only
   STATUS  mandatory
   ::= { tl1srtbPortCounterEntry 17 }

tl1srtbValidSRDiscarded OBJECT-TYPE
   SYNTAX  Counter
   ACCESS  read-only
   STATUS  mandatory
   ::= { tl1srtbPortCounterEntry 18 }

tl1srtbTotalSRDiscarded OBJECT-TYPE
   SYNTAX  Counter
   ACCESS  read-only
   STATUS  mandatory
   ::= { tl1srtbPortCounterEntry 19 }

tl1srtbFilterDbSize OBJECT-TYPE
   SYNTAX  INTEGER
   ACCESS  read-only
   STATUS  mandatory
   ::= { tl1srtbFilterDbParams 1 }
   
tl1srtbPermDbSize OBJECT-TYPE
   SYNTAX  INTEGER
   ACCESS  read-only
   STATUS  mandatory
   ::= { tl1srtbFilterDbParams 2 }

tl1srtbNumDynamicEntries OBJECT-TYPE
   SYNTAX  INTEGER
   ACCESS  read-only
   STATUS  mandatory
   ::= { tl1srtbFilterDbParams 3 }

tl1srtbFilterDbAgeingTime OBJECT-TYPE
   SYNTAX  INTEGER
   ACCESS  read-only
   STATUS  mandatory
   ::= { tl1srtbFilterDbParams 4 }

tl1srtbDynamicFilterDbTable OBJECT-TYPE
   SYNTAX  SEQUENCE OF Tl1srtbDynamicFilterDbEntry
   ACCESS  read-only
   STATUS  mandatory
   ::= { tl1srtb 7 }
   
tl1srtbDynamicFilterDbEntry OBJECT-TYPE
   SYNTAX  Tl1srtbDynamicFilterDbEntry
   ACCESS  read-only
   STATUS  mandatory
   ::= { tl1srtbDynamicFilterDbTable 1 }
   
Tl1srtbDynamicFilterDbEntry ::= SEQUENCE {
        tl1srtbDynamicMacAddr
             OCTET STRING,
        tl1srtbDynamicPortNumber
             INTEGER
}
   
tl1srtbDynamicMacAddr OBJECT-TYPE
   SYNTAX  OCTET STRING (SIZE (6))
   ACCESS  read-only
   STATUS  mandatory
   ::= { tl1srtbDynamicFilterDbEntry 1 }
   
tl1srtbDynamicPortNumber OBJECT-TYPE
   SYNTAX  INTEGER
   ACCESS  read-only
   STATUS  mandatory
   ::= { tl1srtbDynamicFilterDbEntry 2 }

tl1srtbStatEntMacAddrTable OBJECT-TYPE
   SYNTAX  SEQUENCE OF Tl1srtbStatEntMacAddrEntry
   ACCESS  read-write
   STATUS  mandatory
   ::= { tl1srtbStaticFilterDbParams 1 }

tl1srtbStatEntMacAddrEntry OBJECT-TYPE
   SYNTAX  Tl1srtbStatEntMacAddrEntry
   ACCESS  read-write
   STATUS  mandatory
   ::= { tl1srtbStatEntMacAddrTable 1 }

Tl1srtbStatEntMacAddrEntry ::= SEQUENCE {
        tl1srtbStaticEntryMacAddr
             OCTET STRING
}
   
tl1srtbStaticEntryMacAddr OBJECT-TYPE
   SYNTAX  OCTET STRING (SIZE (6))
   ACCESS  read-write
   STATUS  mandatory
   ::= { tl1srtbStatEntMacAddrEntry 1 }

tl1srtbStatEntPortArrayTable OBJECT-TYPE
   SYNTAX  SEQUENCE OF Tl1srtbStatEntPortArrayEntry
   ACCESS  read-write
   STATUS  mandatory
   ::= { tl1srtbStaticFilterDbParams 2 }

tl1srtbStatEntPortArrayEntry OBJECT-TYPE
   SYNTAX  Tl1srtbStatEntPortArrayEntry
   ACCESS  read-write
   STATUS  mandatory
   ::= { tl1srtbStatEntPortArrayTable 1 }

Tl1srtbStatEntPortArrayEntry ::= SEQUENCE {
         tl1srtbStaticEntryPermit
             INTEGER
}

tl1srtbStaticEntryPermit  OBJECT-TYPE
   SYNTAX  INTEGER  {
                deny(0),
                permit(1)
           }
   ACCESS  read-write
   STATUS  mandatory
   ::= { tl1srtbStatEntPortArrayEntry 1 }
   
tl1srtbStatEntSizeTable OBJECT-TYPE
   SYNTAX  SEQUENCE OF Tl1srtbStatEntSizeEntry
   ACCESS  read-write
   STATUS  mandatory
   ::= { tl1srtbStaticFilterDbParams 3 }

tl1srtbStatEntSizeEntry OBJECT-TYPE
   SYNTAX  Tl1srtbStatEntSizeEntry
   ACCESS  read-write
   STATUS  mandatory
   ::= { tl1srtbStatEntSizeTable 1 }

Tl1srtbStatEntSizeEntry ::= SEQUENCE {
         tl1srtbNumStaticEntries
             INTEGER
}

tl1srtbNumStaticEntries OBJECT-TYPE
   SYNTAX  INTEGER
   ACCESS  read-write
   STATUS  mandatory
   ::= { tl1srtbStatEntSizeEntry 1 }

tl1srtbNumMacAddrAcfEntrs OBJECT-TYPE
   SYNTAX  INTEGER
   ACCESS  read-write
   STATUS  mandatory
   ::= { tl1srtb 9 }

tl1srtbMacAddrAcfTable OBJECT-TYPE
   SYNTAX  SEQUENCE OF Tl1srtbMacAddrAcfEntry
   ACCESS  read-write
   STATUS  mandatory
   ::= { tl1srtb 10 }

tl1srtbMacAddrAcfEntry OBJECT-TYPE
   SYNTAX  Tl1srtbMacAddrAcfEntry
   ACCESS  read-write
   STATUS  mandatory
   ::= { tl1srtbMacAddrAcfTable 1 }

Tl1srtbMacAddrAcfEntry ::= SEQUENCE {
        tl1srtbAcfSrcMacAddr
             OCTET STRING,
        tl1srtbAcfDestMacAddr
             OCTET STRING
}

tl1srtbAcfSrcMacAddr OBJECT-TYPE
   SYNTAX  OCTET STRING (SIZE (6))
   ACCESS  read-write
   STATUS  mandatory
   ::= { tl1srtbMacAddrAcfEntry 1 }

tl1srtbAcfDestMacAddr OBJECT-TYPE
   SYNTAX  OCTET STRING (SIZE (6))
   ACCESS  read-write
   STATUS  mandatory
   ::= { tl1srtbMacAddrAcfEntry 2 }

tl1srtbMaskAcfParamsTable OBJECT-TYPE
   SYNTAX  SEQUENCE OF Tl1srtbMaskAcfParamsEntry
   ACCESS  read-write
   STATUS  mandatory
   ::= { tl1srtbMaskAcfInfo 1 }

tl1srtbMaskAcfParamsEntry OBJECT-TYPE
   SYNTAX  Tl1srtbMaskAcfParamsEntry
   ACCESS  read-write
   STATUS  mandatory
   ::= { tl1srtbMaskAcfParamsTable 1 }

Tl1srtbMaskAcfParamsEntry ::= SEQUENCE {
        tl1srtbNumMaskAcfEntries
             INTEGER,
        tl1srtbMaskAcfPermit 
             INTEGER
}

tl1srtbNumMaskAcfEntries OBJECT-TYPE
   SYNTAX  INTEGER
   ACCESS  read-write
   STATUS  mandatory
   ::= { tl1srtbMaskAcfParamsEntry 1 }

tl1srtbMaskAcfPermit OBJECT-TYPE
   SYNTAX  INTEGER  {
                deny(0),
                permit(1)
           }
   ACCESS  read-write
   STATUS  mandatory
   ::= { tl1srtbMaskAcfParamsEntry 2 }
   
tl1srtbMaskAcfTable OBJECT-TYPE
   SYNTAX  SEQUENCE OF Tl1srtbMaskAcfEntry
   ACCESS  read-write
   STATUS  mandatory
   ::= { tl1srtbMaskAcfInfo 2 }

tl1srtbMaskAcfEntry OBJECT-TYPE
   SYNTAX  Tl1srtbMaskAcfEntry
   ACCESS  read-write
   STATUS  mandatory
   ::= { tl1srtbMaskAcfTable 1 }

Tl1srtbMaskAcfEntry ::= SEQUENCE {
        tl1srtbAcfValue
             INTEGER,
        tl1srtbAcfMask
             INTEGER,
        tl1srtbAcfOffset
             INTEGER
}

tl1srtbAcfValue OBJECT-TYPE
   SYNTAX  INTEGER
   ACCESS  read-write
   STATUS  mandatory
   ::= { tl1srtbMaskAcfEntry 1 }

tl1srtbAcfMask OBJECT-TYPE
   SYNTAX  INTEGER
   ACCESS  read-write
   STATUS  mandatory
   ::= { tl1srtbMaskAcfEntry 2 }

tl1srtbAcfOffset OBJECT-TYPE
   SYNTAX  INTEGER
   ACCESS  read-write
   STATUS  mandatory
   ::= { tl1srtbMaskAcfEntry 3 }
        
tl1ospfRtrId OBJECT-TYPE
   SYNTAX  IpAddress
   ACCESS  read-write
   STATUS  mandatory
   ::= { tl1ospf 1 }

tl1ospfAreaTable OBJECT-TYPE
   SYNTAX  SEQUENCE OF Tl1ospfAreaEntry
   ACCESS  read-write
   STATUS  mandatory
   ::= { tl1ospf 2 }

tl1ospfAreaEntry OBJECT-TYPE
   SYNTAX  Tl1ospfAreaEntry
   ACCESS  read-write
   STATUS  mandatory
   ::= { tl1ospfAreaTable 1 }

Tl1ospfAreaEntry ::= SEQUENCE {
	tl1ospfAreaID
             INTEGER,
        tl1ospfAuthType
             INTEGER,
        tl1ospfNetCount
             INTEGER
}

tl1ospfAreaID OBJECT-TYPE
   SYNTAX  INTEGER (-1..65535)
   ACCESS  read-write
   STATUS  mandatory
   ::= { tl1ospfAreaEntry 1 }

tl1ospfAuthType OBJECT-TYPE
   SYNTAX  INTEGER (0..1)
   ACCESS  read-write
   STATUS  mandatory
   ::= { tl1ospfAreaEntry 2 }

tl1ospfNetCount OBJECT-TYPE
   SYNTAX  INTEGER (0..128)
   ACCESS  read-write
   STATUS  mandatory
   ::= { tl1ospfAreaEntry 3 }

tl1ospfAreaNetTable OBJECT-TYPE
   SYNTAX  SEQUENCE OF Tl1ospfAreaNetEntry
   ACCESS  read-write
   STATUS  mandatory
   ::= { tl1ospf 3 }

tl1ospfAreaNetEntry OBJECT-TYPE
   SYNTAX  Tl1ospfAreaNetEntry
   ACCESS  read-write
   STATUS  mandatory
   ::= { tl1ospfAreaNetTable 1 }

Tl1ospfAreaNetEntry ::= SEQUENCE {
	 tl1ospfNet
	      IpAddress,
         tl1ospfMask
              IpAddress
}

tl1ospfNet OBJECT-TYPE
   SYNTAX  IpAddress
   ACCESS  read-write
   STATUS  mandatory
   ::= { tl1ospfAreaNetEntry 1 }

tl1ospfMask OBJECT-TYPE
   SYNTAX  IpAddress
   ACCESS  read-write
   STATUS  mandatory
   ::= { tl1ospfAreaNetEntry 2 }

tl1ospfVirtualIfTable OBJECT-TYPE
   SYNTAX  SEQUENCE OF Tl1ospfVirtualIfEntry
   ACCESS  read-write
   STATUS  mandatory
   ::= { tl1ospf 4 }

tl1ospfVirtualIfEntry OBJECT-TYPE
   SYNTAX  Tl1ospfVirtualIfEntry
   ACCESS  read-write
   STATUS  mandatory
   ::= { tl1ospfVirtualIfTable 1 }

Tl1ospfVirtualIfEntry ::= SEQUENCE {
	tl1ospfNbrId
             IpAddress,
        tl1ospfTransArea
             INTEGER,
        tl1ospfTransDelay
             INTEGER,
 	tl1ospfRxmtIntvl
             INTEGER,
        tl1ospfHelloIntvl
             INTEGER,
        tl1ospfRtrDeadIntvl
             INTEGER,
        tl1ospfAuthKey
             OCTET STRING
}  

tl1ospfNbrId OBJECT-TYPE
   SYNTAX  IpAddress
   ACCESS  read-write
   STATUS  mandatory
   ::= { tl1ospfVirtualIfEntry 1 }

tl1ospfTransArea OBJECT-TYPE
   SYNTAX  INTEGER (0..65335)
   ACCESS  read-write
   STATUS  mandatory
   ::= { tl1ospfVirtualIfEntry 2 }

tl1ospfTransDelay OBJECT-TYPE
   SYNTAX  INTEGER (1..65335)
   ACCESS  read-write
   STATUS  mandatory
   ::= { tl1ospfVirtualIfEntry 3 }
   
tl1ospfRxmtIntvl OBJECT-TYPE
   SYNTAX  INTEGER (1..65335)
   ACCESS  read-write
   STATUS  mandatory
   ::= { tl1ospfVirtualIfEntry 4 }
   
tl1ospfHelloIntvl OBJECT-TYPE
   SYNTAX  INTEGER (1..65335)
   ACCESS  read-write
   STATUS  mandatory
   ::= { tl1ospfVirtualIfEntry 5 }
   
tl1ospfRtrDeadIntvl OBJECT-TYPE
   SYNTAX  INTEGER (1..65335)
   ACCESS  read-write
   STATUS  mandatory
   ::= { tl1ospfVirtualIfEntry 6 }
   
tl1ospfAuthKey OBJECT-TYPE
   SYNTAX  OCTET STRING (SIZE (8))
   ACCESS  read-write
   STATUS  mandatory
   ::= { tl1ospfVirtualIfEntry 7 }

tl1ospfIntfTable OBJECT-TYPE
   SYNTAX  SEQUENCE OF Tl1ospfIntfEntry
   ACCESS  read-write
   STATUS  mandatory
   ::= { tl1ospf 5 }

tl1ospfIntfEntry OBJECT-TYPE
   SYNTAX  Tl1ospfIntfEntry
   ACCESS  read-write
   STATUS  mandatory
   ::= { tl1ospfIntfTable 1 }

Tl1ospfIntfEntry ::= SEQUENCE {
        tl1ospfIntfRun
             INTEGER,
        tl1ospfIntfAreaID
             INTEGER,
	tl1ospfIntfType
             INTEGER,
        tl1ospfIntfTransDelay
             INTEGER,
        tl1ospfIntfRxmtIntvl
             INTEGER,
        tl1ospfIntfHelloIntvl
             INTEGER,
        tl1ospfIntfRtrDeadIntvl
             INTEGER,
        tl1ospfIntfPriority
             INTEGER,
	tl1ospfIntfAuthKey
             OCTET STRING,
        tl1ospfIntfPollIntvl
             INTEGER,
        tl1ospfIntfPtopIntAdd
             IpAddress
}
   
tl1ospfIntfRun OBJECT-TYPE
   SYNTAX  INTEGER {
                run(1),
                dont-run(0)
           }
   ACCESS  read-write
   STATUS  mandatory
   ::= { tl1ospfIntfEntry 1 }

tl1ospfIntfAreaID OBJECT-TYPE
   SYNTAX  INTEGER (0..65335)
   ACCESS  read-write
   STATUS  mandatory
   ::= { tl1ospfIntfEntry 2 }
   
tl1ospfIntfType OBJECT-TYPE
   SYNTAX  INTEGER (1..3)
   ACCESS  read-write
   STATUS  mandatory
   ::= { tl1ospfIntfEntry 3 }

tl1ospfIntfTransDelay OBJECT-TYPE
   SYNTAX  INTEGER (1..65335)
   ACCESS  read-write
   STATUS  mandatory
   ::= { tl1ospfIntfEntry 4 }
   
tl1ospfIntfRxmtIntvl OBJECT-TYPE
   SYNTAX  INTEGER (1..65335)
   ACCESS  read-write
   STATUS  mandatory
   ::= { tl1ospfIntfEntry 5 }
   
tl1ospfIntfHelloIntvl OBJECT-TYPE
   SYNTAX  INTEGER (1..65335)
   ACCESS  read-write
   STATUS  mandatory
   ::= { tl1ospfIntfEntry 6 }
   
tl1ospfIntfRtrDeadIntvl OBJECT-TYPE
   SYNTAX  INTEGER (1..65335)
   ACCESS  read-write
   STATUS  mandatory
   ::= { tl1ospfIntfEntry 7 }
   
tl1ospfIntfPriority OBJECT-TYPE
   SYNTAX  INTEGER (1..254)
   ACCESS  read-write
   STATUS  mandatory
   ::= { tl1ospfIntfEntry 8 }

tl1ospfIntfAuthKey OBJECT-TYPE
   SYNTAX  OCTET STRING (SIZE (8))
   ACCESS  read-write
   STATUS  mandatory
   ::= { tl1ospfIntfEntry 9 }
   
tl1ospfIntfPollIntvl OBJECT-TYPE
   SYNTAX  INTEGER (1..65335)
   ACCESS  read-write
   STATUS  mandatory
   ::= { tl1ospfIntfEntry 10 }
   
tl1ospfIntfPtopIntAddr OBJECT-TYPE
   SYNTAX  IpAddress
   ACCESS  read-write
   STATUS  mandatory
   ::= { tl1ospfIntfEntry 11 }
   
tl1ospfNBMATable OBJECT-TYPE
   SYNTAX  SEQUENCE OF Tl1ospfNBMAEntry
   ACCESS  read-write
   STATUS  mandatory
   ::= { tl1ospf 6 }

tl1ospfNBMAEntry OBJECT-TYPE
   SYNTAX  Tl1ospfNBMAEntry
   ACCESS  read-write
   STATUS  mandatory
   ::= { tl1ospfNBMATable 1 }

Tl1ospfNBMAEntry ::= SEQUENCE {
        tl1ospfAttRtrIpAddr
             IpAddress,
        tl1ospfArPriority
             INTEGER
}

tl1ospfAttRtrIpAddr OBJECT-TYPE
   SYNTAX  IpAddress
   ACCESS  read-write
   STATUS  mandatory
   ::= { tl1ospfNBMAEntry 1 }

tl1ospfPriority OBJECT-TYPE
   SYNTAX  INTEGER (1..254)
   ACCESS  read-write
   STATUS  mandatory
   ::= { tl1ospfNBMAEntry 2 }

tl1ospfCumlogTable OBJECT-TYPE
   SYNTAX  SEQUENCE OF Tl1ospfCumLogEntry
   ACCESS  read-only
   STATUS  mandatory
   ::= { tl1ospf 7 }

tl1ospfCumLogEntry OBJECT-TYPE
   SYNTAX  Tl1ospfCumLogEntry
   ACCESS  read-only
   STATUS  mandatory
   ::= { tl1ospfCumlogTable 1 }

Tl1ospfCumLogEntry ::= SEQUENCE {
        tl1ospfStat
      	     Counter
}
   
tl1ospfStat OBJECT-TYPE
   SYNTAX  Counter
   ACCESS  read-only
   STATUS  mandatory
   ::= { tl1ospfCumLogEntry 1 }

tl1ospfIntfTOSTable OBJECT-TYPE
   SYNTAX  SEQUENCE OF Tl1ospfIntfTOSEntry
   ACCESS  read-write
   STATUS  mandatory
   ::= { tl1ospf 8 }

tl1ospfIntfTOSEntry OBJECT-TYPE
   SYNTAX  Tl1ospfIntfTOSEntry
   ACCESS  read-write
   STATUS  mandatory
   ::= { tl1ospfIntfTOSTable 1 }

Tl1ospfIntfTOSEntry ::= SEQUENCE {
        tl1ospfIfTOSCost
             INTEGER
}

tl1ospfIfTOSCost OBJECT-TYPE
   SYNTAX  INTEGER (0..65335)
   ACCESS  read-write
   STATUS  mandatory
   ::= { tl1ospfIntfTOSEntry 1 }

        -- the TL1 TOK Group

tl1tokConfigTable OBJECT-TYPE
   SYNTAX  SEQUENCE OF Tl1tokConfigEntry
   ACCESS  read-write
   STATUS  mandatory
   ::= { tl1tok 1 }

tl1tokConfigEntry OBJECT-TYPE
   SYNTAX  Tl1tokConfigEntry
   ACCESS  read-write
   STATUS  mandatory
   ::= { tl1tokConfigTable 1 }

Tl1tokConfigEntry ::= SEQUENCE {
        tl1tokEarlyTokenRelease
             INTEGER,
        tl1tokRingSpeed
             INTEGER             
}

tl1tokEarlyTokenRelease OBJECT-TYPE
   SYNTAX  INTEGER {
                true(1),
                false(0)
           }
   ACCESS  read-write
   STATUS  mandatory
   ::= { tl1tokConfigEntry 2 }

tl1tokRingSpeed OBJECT-TYPE
   SYNTAX  INTEGER {       
                four-Mbps(0),
                sixteen-Mbps(1)
           }
   ACCESS  read-write
   STATUS  mandatory
   ::= { tl1tokConfigEntry 3 }

END
