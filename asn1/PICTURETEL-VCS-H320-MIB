PICTURETEL-VCS-H320-MIB DEFINITIONS ::= BEGIN

IMPORTS
	MODULE-IDENTITY, OBJECT-TYPE, OBJECT-IDENTITY, Gauge32, Integer32, enterprises
FROM SNMPv2-SMI
	TruthValue, DisplayString
FROM SNMPv2-TC
	CallBandwidthType, VideoAlgorithmType, AudioAlgorithmType, DataProtocolType, VideoResolutionType, ptH320
FROM PICTURETEL-VCS-MIB;

pictureTelVCSH320Module MODULE-IDENTITY
	LAST-UPDATED "0101030000Z"
	ORGANIZATION "PictureTel Corporation"
	CONTACT-INFO
		"
		Postal:	PictureTel Corporation
				100 Minuteman Drive
				Andover, MA 01810-1031
				USA"
	DESCRIPTION
		"Final version of the PictureTel H.320 MIB"
	REVISION	"0101030000Z"
	DESCRIPTION
		"Rev 0.0.13
		3 Jan 2001 12:00  
		Latest version of MIB module PICTURETEL-VCS-H320-MIB"

 ::= { ptH320 1 }


--
-- H.320 placeholders
--

ptH320Statistics           OBJECT-IDENTITY
	STATUS          current
	DESCRIPTION     "Subtree for H.320 statistics"
	::= { pictureTelVCSH320Module 1 }


ptH320CallStat             OBJECT-IDENTITY
	STATUS          current
	DESCRIPTION     "Subtree for H.320 call statistics"
	::= { ptH320Statistics 1 }


ptH320VideoStat             OBJECT-IDENTITY
	STATUS          current
	DESCRIPTION     "Subtree for H.320 video statistics"
	::= { ptH320Statistics 2 }


ptH320AudioStat             OBJECT-IDENTITY
	STATUS          current
	DESCRIPTION     "Subtree for H.320 audio statistics"
	::= { ptH320Statistics 3 }


ptH320DataStat             OBJECT-IDENTITY
	STATUS          current
	DESCRIPTION     "Subtree for H.320 data statistics"
	::= { ptH320Statistics 4 }

--
-- Call Statistics
--

ptH320CallBandwidth  OBJECT-TYPE
	SYNTAX CallBandwidthType
	MAX-ACCESS	read-only
	STATUS          current
	DESCRIPTION      "Current call bandwidth"
	::= { ptH320CallStat 1 }


ptH320CallRestricted  OBJECT-TYPE
	SYNTAX TruthValue
	MAX-ACCESS	read-only
	STATUS          current
	DESCRIPTION      "Call in restricted mode"
	::= { ptH320CallStat 2 }


ptH320CallNumberOfChannels  OBJECT-TYPE
	SYNTAX Gauge32
	MAX-ACCESS	read-only
	STATUS          current
	DESCRIPTION      "Number of network channels aggregated by H.221
	                  (a bonded call has only one channel from the
	                  H.221 perspective)"
	::= { ptH320CallStat 3 }


ptH320CallStatTable         OBJECT-TYPE
	SYNTAX SEQUENCE OF PtH320CallStatEntry
	MAX-ACCESS	not-accessible
	STATUS          current
	DESCRIPTION     "H.221 network channel statistics table"
	::= { ptH320CallStat 4 }


ptH320CallStatEntry         OBJECT-TYPE
	SYNTAX PtH320CallStatEntry
	MAX-ACCESS	not-accessible
	STATUS          current
	DESCRIPTION     "Logical row describing an entry in the H.221 
	                 network channel statistics table"
	INDEX	{ ptH320CallStatIndex }
	::= { ptH320CallStatTable 1 }


PtH320CallStatEntry ::= SEQUENCE {
	ptH320CallStatIndex                         Gauge32,
	ptH320CallH221FramesAligned                 TruthValue,
	ptH320CallH221FramesLost                    Gauge32,
	ptH320CallH221SMFTransmitted                Gauge32, 
	ptH320CallH221SMFReceived                   Gauge32,
	ptH320CallH221ReceivedEBitSet               Gauge32,
	ptH320CallH221ReceivedCRCError              Gauge32,
	ptH320CallH221ReceivedBASECCError           Gauge32,
	ptH320CallH221ReceivedBASProtocolViolation  Gauge32
	}

ptH320CallStatIndex  OBJECT-TYPE
	SYNTAX	Gauge32
	MAX-ACCESS	read-only
	STATUS	current
	DESCRIPTION    "Index of the H.221 network channel in the table"
	::= { ptH320CallStatEntry 1 }


ptH320CallH221FramesAligned  OBJECT-TYPE
	SYNTAX TruthValue
	MAX-ACCESS	read-only
	STATUS          current
	DESCRIPTION      "If the value of this object is true(1),
	                  then the multi-frames are aligned"
	::= { ptH320CallStatEntry 2 }


ptH320CallH221FramesLost  OBJECT-TYPE
	SYNTAX Gauge32
	MAX-ACCESS	read-only
	STATUS          current
	DESCRIPTION      "Number of times when framing was lost"
	::= { ptH320CallStatEntry 3 }


ptH320CallH221SMFTransmitted   OBJECT-TYPE
	SYNTAX Gauge32
	MAX-ACCESS	read-only
	STATUS          current
	DESCRIPTION      "Number of SMFs (submultiframes) transmitted"
	::= { ptH320CallStatEntry 4 }


ptH320CallH221SMFReceived   OBJECT-TYPE
	SYNTAX Gauge32
	MAX-ACCESS	read-only
	STATUS          current
	DESCRIPTION      "Number of SMFs (submultiframes) received"
	::= { ptH320CallStatEntry 5 }


ptH320CallH221ReceivedEBitSet   OBJECT-TYPE
	SYNTAX Gauge32
	MAX-ACCESS	read-only
	STATUS          current
	DESCRIPTION      "Number of SMFs (submultiframes) received
	                  with E bit set"
	::= { ptH320CallStatEntry 6 }


ptH320CallH221ReceivedCRCError   OBJECT-TYPE
	SYNTAX Gauge32
	MAX-ACCESS	read-only
	STATUS          current
	DESCRIPTION      "Number of SMFs (submultiframes) received
	                  with CRC error"
	::= { ptH320CallStatEntry 7 }


ptH320CallH221ReceivedBASECCError  OBJECT-TYPE
	SYNTAX Gauge32
	MAX-ACCESS	read-only
	STATUS          current
	DESCRIPTION      "Number of SMFs (submultiframes) received
	                  with BAS ECC error"
	::= { ptH320CallStatEntry 8 }


ptH320CallH221ReceivedBASProtocolViolation  OBJECT-TYPE
	SYNTAX  Gauge32
	MAX-ACCESS	read-only
	STATUS          current
	DESCRIPTION      "Number of SMFs (submultiframes) received with
	                  BAS that have a valid ECC, but are inappropriate 
	                  for current state (e.g., mode received during the 
	                  capability exchange)"
	::= { ptH320CallStatEntry 9 }




--
-- Video Statistics
--

ptH320VideoNumberOfEncoders   OBJECT-TYPE
	SYNTAX Integer32
	MAX-ACCESS	read-only
	STATUS          current
	DESCRIPTION      "Number of video encoders/decoders"
	::= { ptH320VideoStat 1 }


ptH320VideoStatTable         OBJECT-TYPE
	SYNTAX SEQUENCE OF PtH320VideoStatEntry
	MAX-ACCESS	not-accessible
	STATUS          current
	DESCRIPTION      "H.320 video statistics table"
	::= { ptH320VideoStat 2 }


ptH320VideoStatEntry         OBJECT-TYPE
	SYNTAX PtH320VideoStatEntry
	MAX-ACCESS	not-accessible
	STATUS          current
	DESCRIPTION      "Logical row describing an entry in the H.320 
	                  video statistics table"
	INDEX	{ ptH320VideoStatIndex }
	::= { ptH320VideoStatTable 1 }


PtH320VideoStatEntry ::= SEQUENCE {
	ptH320VideoStatIndex                   Gauge32,
	ptH320VideoTransmitAlgorithm           VideoAlgorithmType,
	ptH320VideoTransmitAnnex               DisplayString,
	ptH320VideoReceiveAlgorithm            VideoAlgorithmType,
	ptH320VideoReceiveAnnex                DisplayString,
	ptH320VideoTransmitTargetFrameRate     Gauge32,
	ptH320VideoTransmitActualFrameRate     Gauge32,
	ptH320VideoReceiveActualFrameRate      Gauge32,
	ptH320VideoTransmitPictureFormat       VideoResolutionType,
	ptH320VideoReceivePictureFormat        VideoResolutionType,
	ptH320VideoTransmitTargetBitRate       Gauge32,
	ptH320VideoReceiveTargetBitRate        Gauge32,
	ptH320VideoTransmitActualBitRate       Gauge32,
	ptH320VideoReceiveActualBitRate        Gauge32,
	ptH320VideoTransmittedKeyFrames        Gauge32,
	ptH320VideoReceivedKeyFrames           Gauge32,
	ptH320VideoTransmittedFECFrames        Gauge32,
	ptH320VideoReceivedFECFrames           Gauge32,
	ptH320VideoReceivedCorrectableFrames   Gauge32,
	ptH320VideoReceivedUncorrectableFrames Gauge32,
	ptH320VideoFramingLost                 Gauge32,
	ptH320VideoReceivedBitstreamErrors     Gauge32,
	ptH320VideoEncoderNoiseReductionFilter TruthValue,
	ptH320VideoDecoderPostFilters          TruthValue,
	ptH320VideoReceivedChecksumErrors      Gauge32,
	ptH320VideoTransmittedFrames           Gauge32,
	ptH320VideoReceivedFrames              Gauge32
	}


ptH320VideoStatIndex  OBJECT-TYPE
	SYNTAX	Gauge32
	MAX-ACCESS	read-only
	STATUS	current
	DESCRIPTION    "Index of H.320 video statistics in the table.
		            Indicates number of video encoders/decoders"
	::= { ptH320VideoStatEntry 1 }


ptH320VideoTransmitAlgorithm   OBJECT-TYPE
	SYNTAX VideoAlgorithmType
	MAX-ACCESS	read-only
	STATUS          current
	DESCRIPTION      "Current transmit video algorithm 
	                  (for active state only)"
	::= { ptH320VideoStatEntry 2 }


ptH320VideoTransmitAnnex   OBJECT-TYPE
	SYNTAX DisplayString
	MAX-ACCESS	read-only
	STATUS          current
	DESCRIPTION      "Current transmit video annex 
	                  (for active state only)
	                  BOOL AnnexFAdvancedPrediction         : 1 bit
	                  BOOL AnnexJDeblockingFilter           : 1 bit
	                  BOOL AnnexNReferencePictureSelection  : 1 bit
	                  BOOL AnnexPReferencePictureResampling : 1 bit
	                  BOOL AppendixIErrorTracking           : 1 bit
	                  BOOL CustomPicture640x480             : 1 bit
	                  BOOL CustomPicture704x480             : 1 bit
	                  BOOL CustomPicture800x600             : 1 bit
	                  BOOL CustomPicture1024x768            : 1 bit"
	::= { ptH320VideoStatEntry 3 }


ptH320VideoReceiveAlgorithm   OBJECT-TYPE
	SYNTAX VideoAlgorithmType
	MAX-ACCESS	read-only
	STATUS          current
	DESCRIPTION      "Current receive video algorithm 
	                  (for active state only)"
	::= { ptH320VideoStatEntry 4}


ptH320VideoReceiveAnnex   OBJECT-TYPE
	SYNTAX DisplayString
	MAX-ACCESS	read-only
	STATUS          current
	DESCRIPTION      "Current receive video annex 
	                  (for active state only)
	                  BOOL AnnexFAdvancedPrediction         : 1 bit
	                  BOOL AnnexJDeblockingFilter           : 1 bit
	                  BOOL AnnexNReferencePictureSelection  : 1 bit
	                  BOOL AnnexPReferencePictureResampling : 1 bit
	                  BOOL AppendixIErrorTracking           : 1 bit
	                  BOOL CustomPicture640x480             : 1 bit
	                  BOOL CustomPicture704x480             : 1 bit
	                  BOOL CustomPicture800x600             : 1 bit
	                  BOOL CustomPicture1024x768            : 1 bit"
	::= { ptH320VideoStatEntry 5 }


ptH320VideoTransmitTargetFrameRate   OBJECT-TYPE
	SYNTAX Gauge32
	MAX-ACCESS	read-only
	STATUS          current
	DESCRIPTION      "Target transmit frame rate (for active 
	                  state only) - frames/sec"
	::= { ptH320VideoStatEntry 6 }


ptH320VideoTransmitActualFrameRate   OBJECT-TYPE
	SYNTAX Gauge32
	MAX-ACCESS	read-only
	STATUS          current
	DESCRIPTION      "Current average transmit frame rate 
	                  (for active state only) - frames/sec"
	::= { ptH320VideoStatEntry 7 }


ptH320VideoReceiveActualFrameRate   OBJECT-TYPE
	SYNTAX Gauge32
	MAX-ACCESS	read-only
	STATUS          current
	DESCRIPTION      "Current average receive frame rate 
	                  (for active state only) - frames/sec"
	::= { ptH320VideoStatEntry 8 }


ptH320VideoTransmitPictureFormat   OBJECT-TYPE
	SYNTAX VideoResolutionType
	MAX-ACCESS	read-only
	STATUS          current
	DESCRIPTION      "Current video picture format transmitted 
	                  (for active state only)"
	::= { ptH320VideoStatEntry 9 }


ptH320VideoReceivePictureFormat   OBJECT-TYPE
	SYNTAX VideoResolutionType
	MAX-ACCESS	read-only
	STATUS          current
	DESCRIPTION      "Current video picture format received 
	                  (for active state only)"
	::= { ptH320VideoStatEntry 10 }


ptH320VideoTransmitTargetBitRate   OBJECT-TYPE
	SYNTAX Gauge32
	MAX-ACCESS	read-only
	STATUS          current
	DESCRIPTION      "Number of bits per second allocated for video Tx"
	::= { ptH320VideoStatEntry 11 }


ptH320VideoReceiveTargetBitRate   OBJECT-TYPE
	SYNTAX Gauge32
	MAX-ACCESS	read-only
	STATUS          current
	DESCRIPTION      "Number of bits per second allocated for video Rx"
	::= { ptH320VideoStatEntry 12 }

ptH320VideoTransmitActualBitRate   OBJECT-TYPE
	SYNTAX Gauge32
	MAX-ACCESS	read-only
	STATUS          current
	DESCRIPTION      "Number of actual bits per second transmitted"
	::= { ptH320VideoStatEntry 13 }


ptH320VideoReceiveActualBitRate   OBJECT-TYPE
	SYNTAX Gauge32
	MAX-ACCESS	read-only
	STATUS          current
	DESCRIPTION      "Number of actual bits per second received"
	::= { ptH320VideoStatEntry 14 }


ptH320VideoTransmittedKeyFrames   OBJECT-TYPE
	SYNTAX Gauge32
	MAX-ACCESS	read-only
	STATUS          current
	DESCRIPTION      "Number of key (intra) frames sent"
	::= { ptH320VideoStatEntry 15 }


ptH320VideoReceivedKeyFrames   OBJECT-TYPE
	SYNTAX Gauge32
	MAX-ACCESS	read-only
	STATUS          current
	DESCRIPTION      "Number of key (intra) frames received"
	::= { ptH320VideoStatEntry 16 }


ptH320VideoTransmittedFECFrames   OBJECT-TYPE
	SYNTAX Gauge32
	MAX-ACCESS	read-only
	STATUS          current
	DESCRIPTION      "Number of FEC frames transmitted"
	::= { ptH320VideoStatEntry 17 }


ptH320VideoReceivedFECFrames   OBJECT-TYPE
	SYNTAX Gauge32
	MAX-ACCESS	read-only
	STATUS          current
	DESCRIPTION      "Number of FEC frames received"
	::= { ptH320VideoStatEntry 18 }


ptH320VideoReceivedCorrectableFrames   OBJECT-TYPE
	SYNTAX Gauge32
	MAX-ACCESS	read-only
	STATUS          current
	DESCRIPTION      "Number of FEC frames received with
	                  correctable errors"
	::= { ptH320VideoStatEntry 19 }


ptH320VideoReceivedUncorrectableFrames   OBJECT-TYPE
	SYNTAX Gauge32
	MAX-ACCESS	read-only
	STATUS          current
	DESCRIPTION      "Number of FEC frames received with
	                  uncorrectable errors"
	::= { ptH320VideoStatEntry 20}


ptH320VideoFramingLost   OBJECT-TYPE
	SYNTAX Gauge32
	MAX-ACCESS	read-only
	STATUS          current
	DESCRIPTION      "Number of times when video framing was lost"
	::= { ptH320VideoStatEntry 21}


ptH320VideoReceivedBitstreamErrors   OBJECT-TYPE
	SYNTAX Gauge32
	MAX-ACCESS	read-only
	STATUS          current
	DESCRIPTION      "Number of bitstream errors received"
	::= { ptH320VideoStatEntry 22}


ptH320VideoEncoderNoiseReductionFilter   OBJECT-TYPE
	SYNTAX TruthValue
	MAX-ACCESS	read-only
	STATUS          current
	DESCRIPTION      "State of the noise reduction filter
	                  (true/false)"
	::= { ptH320VideoStatEntry 23}


ptH320VideoDecoderPostFilters   OBJECT-TYPE
	SYNTAX TruthValue
	MAX-ACCESS	read-only
	STATUS          current
	DESCRIPTION      "State of the decoder post filters
	                  (true/false)"
	::= { ptH320VideoStatEntry 24}


ptH320VideoReceivedChecksumErrors   OBJECT-TYPE
	SYNTAX Gauge32
	MAX-ACCESS	read-only
	STATUS          current
	DESCRIPTION      "Number of checksum errors received"
	::= { ptH320VideoStatEntry 25}


ptH320VideoTransmittedFrames   OBJECT-TYPE
	SYNTAX Gauge32
	MAX-ACCESS	read-only
	STATUS          current
	DESCRIPTION      "Number of transmitted frames"
	::= { ptH320VideoStatEntry 26}


ptH320VideoReceivedFrames   OBJECT-TYPE
	SYNTAX Gauge32
	MAX-ACCESS	read-only
	STATUS          current
	DESCRIPTION      "Number of received frames"
	::= { ptH320VideoStatEntry 27}



--
-- Audio Statistics
--

ptH320AudioTransmitAlgorithm         OBJECT-TYPE
	SYNTAX AudioAlgorithmType
	MAX-ACCESS	read-only
	STATUS          current
	DESCRIPTION      "Current transmit audio algorithm 
	                  (for all states except Idle Final)"
	::= { ptH320AudioStat 1 }


ptH320AudioReceiveAlgorithm         OBJECT-TYPE
	SYNTAX AudioAlgorithmType
	MAX-ACCESS	read-only
	STATUS          current
	DESCRIPTION      "Current receive audio algorithm 
	                  (for all states except Idle Final)"
	::= { ptH320AudioStat 2 }



--
-- Data Statistics
--

ptH320DataTransmitProtocol       OBJECT-TYPE
	SYNTAX DataProtocolType
	MAX-ACCESS	read-only
	STATUS          current
	DESCRIPTION      "Current transmit data protocol"
	::= { ptH320DataStat 1 }


ptH320DataReceiveProtocol        OBJECT-TYPE
	SYNTAX DataProtocolType
	MAX-ACCESS	read-only
	STATUS          current
	DESCRIPTION      "Current receive data protocol"
	::= { ptH320DataStat 2 }


ptH320DataTransmitLSDRate        OBJECT-TYPE
	SYNTAX Gauge32
	MAX-ACCESS	read-only
	STATUS          current
	DESCRIPTION      "Transmit LSD rate of data channels allocated 
	                  in MUX (bits/sec)"
	::= { ptH320DataStat 3 }


ptH320DataReceiveLSDRate         OBJECT-TYPE
	SYNTAX Gauge32
	MAX-ACCESS	read-only
	STATUS          current
	DESCRIPTION      "Receive LSD rate of data channels allocated 
	                  in MUX (bits/sec)"
	::= { ptH320DataStat 4 }


ptH320DataTransmitMLPRate        OBJECT-TYPE
	SYNTAX Gauge32
	MAX-ACCESS	read-only
	STATUS          current
	DESCRIPTION      "Transmit MLP rate of data channels allocated 
	                  in MUX (bits/sec)"
	::= { ptH320DataStat 5 }


ptH320DataReceiveMLPRate         OBJECT-TYPE
	SYNTAX Gauge32
	MAX-ACCESS	read-only
	STATUS          current
	DESCRIPTION      "Receive MLP rate of data channels allocated 
	                  in MUX (bits/sec)"
	::= { ptH320DataStat 6 }


ptH320DataReceiveLSDFramesWithCRCError  OBJECT-TYPE
	SYNTAX Gauge32
	MAX-ACCESS	read-only
	STATUS          current
	DESCRIPTION      "Number of LSD frames with CRC error received"
	::= { ptH320DataStat 7 }


ptH320DataReceiveLSDFramingError  OBJECT-TYPE
	SYNTAX Gauge32
	MAX-ACCESS	read-only
	STATUS          current
	DESCRIPTION      "Number of LSD frames with framing error received"
	::= { ptH320DataStat 8 }


ptH320DataTransmitLSDBytes  OBJECT-TYPE
	SYNTAX Gauge32
	MAX-ACCESS	read-only
	STATUS          current
	DESCRIPTION      "Number of LSD bytes transmitted"
	::= { ptH320DataStat 9 }


ptH320DataReceiveLSDBytes  OBJECT-TYPE
	SYNTAX Gauge32
	MAX-ACCESS	read-only
	STATUS          current
	DESCRIPTION      "Number of LSD bytes received"
	::= { ptH320DataStat 10 }

ptH320DataTransmitMLPBytes  OBJECT-TYPE
	SYNTAX Gauge32
	MAX-ACCESS	read-only
	STATUS          current
	DESCRIPTION      "Number of MLP bytes transmitted"
	::= { ptH320DataStat 11 }


ptH320DataReceiveMLPBytes  OBJECT-TYPE
	SYNTAX Gauge32
	MAX-ACCESS	read-only
	STATUS          current
	DESCRIPTION      "Number of MLP bytes received"
	::= { ptH320DataStat 12 }

ptH320DataTransmitLSDFrames  OBJECT-TYPE
	SYNTAX Gauge32
	MAX-ACCESS	read-only
	STATUS          current
	DESCRIPTION      "Number of LSD frames transmitted"
	::= { ptH320DataStat 13 }


ptH320DataReceiveLSDFrames  OBJECT-TYPE
	SYNTAX Gauge32
	MAX-ACCESS	read-only
	STATUS          current
	DESCRIPTION      "Number of LSD frames received"
	::= { ptH320DataStat 14 }

ptH320DataTransmitMLPFrames  OBJECT-TYPE
	SYNTAX Gauge32
	MAX-ACCESS	read-only
	STATUS          current
	DESCRIPTION      "Number of MLP frames transmitted"
	::= { ptH320DataStat 15 }


ptH320DataReceiveMLPFrames  OBJECT-TYPE
	SYNTAX Gauge32
	MAX-ACCESS	read-only
	STATUS          current
	DESCRIPTION      "Number of MLP frames received"
	::= { ptH320DataStat 16 }


ptH320DataReceiveMLPCRCErrors  OBJECT-TYPE
	SYNTAX Gauge32
	MAX-ACCESS	read-only
	STATUS          current
	DESCRIPTION      "Number of LSD frames with CRC errors received"
	::= { ptH320DataStat 17 }


ptH320DataReceiveMLPFramingErrors  OBJECT-TYPE
	SYNTAX Gauge32
	MAX-ACCESS	read-only
	STATUS          current
	DESCRIPTION      "Number of MLP frames with framing errors received"
	::= { ptH320DataStat 18 }


ptH320DataH224PacketsReceived  OBJECT-TYPE
	SYNTAX Gauge32
	MAX-ACCESS	read-only
	STATUS          current
	DESCRIPTION      "Number of H.224 packets received"
	::= { ptH320DataStat 19 }


ptH320DataH224PacketsTransmitted  OBJECT-TYPE
	SYNTAX Gauge32
	MAX-ACCESS	read-only
	STATUS          current
	DESCRIPTION      "Number of H.224 packets transmitted"
	::= { ptH320DataStat 20 }


ptH320DataTransmitT120Packets  OBJECT-TYPE
	SYNTAX Gauge32
	MAX-ACCESS	read-only
	STATUS          current
	DESCRIPTION      "Number of T.120 packets transmitted"
	::= { ptH320DataStat 21 }


ptH320DataReceiveT120Packets  OBJECT-TYPE
	SYNTAX Gauge32
	MAX-ACCESS	read-only
	STATUS          current
	DESCRIPTION      "Number of T.120 packets received"
	::= { ptH320DataStat 22 }

END
