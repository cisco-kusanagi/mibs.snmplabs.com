AVAYA-MPOA-MIB DEFINITIONS ::= BEGIN

   IMPORTS
	TEXTUAL-CONVENTION FROM SNMPv2-TC
       NOTIFICATION-TYPE, MODULE-IDENTITY, OBJECT-TYPE, Integer32, enterprises  FROM SNMPv2-SMI
       DisplayString, RowStatus                 FROM SNMPv2-TC
       --TextualConvention                        FROM SNMPv2-TC
       InterfaceIndex                           FROM IF-MIB
       lsg                                      FROM AVAYAGEN-MIB;
   
   atmAccess OBJECT IDENTIFIER ::= { lsg 4}


   mpoa MODULE-IDENTITY
       LAST-UPDATED "0110101700Z" -- October 10, 2001 5:00PM
       ORGANIZATION "Avaya Communications, Inc."
       CONTACT-INFO
               "   Technical Support
                   Avaya Communications, Inc.
                   Telephone from US:
                   800-237-0016
                   Telephone from North America:
                   1-800-242-2121"
       DESCRIPTION
               "The MIB module to implement RFC1483,MPOA/AAL5 protocol"
       REVISION      "0110101700Z" -- October 10, 2001 5:00PM
       DESCRIPTION
               "Initial version of the AVAYA-MPOA-MIB."
       ::= { atmAccess 1 }

    marconi OBJECT IDENTIFIER ::= { enterprises 1012}

    esrLsg OBJECT IDENTIFIER ::= { marconi 44}
                                             
    MpoaEnabledValue ::= TEXTUAL-CONVENTION
    STATUS       current
    DESCRIPTION
            "Represents either enabled or disabled."
    SYNTAX       INTEGER { enabled(1), disabled(2) }

    MpoaYesorNoValue ::= TEXTUAL-CONVENTION
    STATUS       current
    DESCRIPTION
            "Represents either YES or NO."
    SYNTAX       INTEGER { yes(1), no(2) }

    MpoaOperValue ::= TEXTUAL-CONVENTION
    STATUS       current
    DESCRIPTION
            "Represents the operational status of the vsp
             or link.  The value of initial is used
             when the VSP/link was administratively enabled
             but the configuration is incorrect, and the VSP/
             link cannot be activated."
    SYNTAX       INTEGER { up(1), down(2), initial(3) }

    MpoaResourceId ::= TEXTUAL-CONVENTION
    STATUS       current
    DESCRIPTION
            "Represents the resource id of either an MPOA link
             or PVC.  Before creating a link or PVC, a valid
             resource id is obtained via GETs for variables
             in the mpoaResourceMgmtGroup.  The resource id
             is one of the indicies in the mpoaAtmLinkTable
             and the mpoaPvcTable."
    SYNTAX       Integer32

	 mpoaResourceMgmtGroup	OBJECT IDENTIFIER ::= { mpoa 1 }

    mpoaNextLinkResourceId OBJECT-TYPE
        SYNTAX      Integer32
        MAX-ACCESS  read-only
        STATUS      current
        DESCRIPTION
               "This variable contains the next available
                Resource Id to be used when creating a link.
                Before creating a link, a GET of this variable
                must be requested.  This value should be used
                in the mpoaAtmLinkIndex variable."
        ::= { mpoaResourceMgmtGroup 1 }

    mpoaNextPvcResourceId OBJECT-TYPE
        SYNTAX      Integer32
        MAX-ACCESS  read-only
        STATUS      current
        DESCRIPTION
               "This variable contains the next available
                Resource Id to be used when creating a PVC.
                Before creating a PVC, a GET of this variable
                must be requested.  This value should be used
                in mpoaPvcResIndex variable."
        ::= { mpoaResourceMgmtGroup 2 }

    --
    -- The MPOA (1483) Virtual Switch Port Table
    --
    mpoaVirtualSwitchPortTable  OBJECT-TYPE
        SYNTAX      SEQUENCE OF MpoaVirtualSwitchPortEntry
        MAX-ACCESS  not-accessible
        STATUS      current
        DESCRIPTION
               "A table of all the VSPs created for aal5 traffic
                on the atm module. The maximum number of expected
                entries is 128."
        ::= { mpoa 2 }

    mpoaVirtualSwitchPortEntry OBJECT-TYPE
        SYNTAX      MpoaVirtualSwitchPortEntry
        MAX-ACCESS  not-accessible
        STATUS      current
        DESCRIPTION
               "An entry containing management information pertaining
                to an mpoa VSP."
        INDEX   { mpoaVspIndex }
        ::= { mpoaVirtualSwitchPortTable 1 }

    MpoaVirtualSwitchPortEntry ::=
        SEQUENCE {
         mpoaVspIndex				     Integer32,
		   --mpoaVspIfIndex             InterfaceIndex,
         mpoaVspAdminStatus           MpoaEnabledValue,
         mpoaVspOperStatus            MpoaOperValue,
         mpoaVspName                  DisplayString,
		   mpoaVspEncapsulationType     INTEGER,
		   mpoaVspPktReplication        MpoaYesorNoValue,
		   mpoaVspLoadShare             MpoaYesorNoValue,
         mpoaVspDefaultPort           Integer32,
		   mpoaVspDefaultVc-port1       MpoaResourceId,
		   mpoaVspDefaultVc-port2       MpoaResourceId,
         mpoaVspMulticastChan-port1   Integer32,
         mpoaVspMulticastChan-port2   Integer32,
         mpoaVspRowStatus			     RowStatus
		}

    mpoaVspIndex OBJECT-TYPE
        SYNTAX      Integer32 (1..128)
        MAX-ACCESS  read-only
        STATUS      current
        DESCRIPTION
               "The VSP Id number in the range of 1 to 128."
        ::= { mpoaVirtualSwitchPortEntry 1 }

    --mpoaVspIfIndex OBJECT-TYPE
      --  SYNTAX      InterfaceIndex
        --MAX-ACCESS  read-only
        --STATUS      current
        --DESCRIPTION
        --       "The value for this object is equal to the value
        --        of ifIndex from the Interfaces table of MIB II
        --        (RFC 1213)."
        --::= { mpoaVirtualSwitchPortEntry 2 }

    mpoaVspAdminStatus OBJECT-TYPE
        SYNTAX      MpoaEnabledValue
        MAX-ACCESS  read-write
        STATUS      current
        DESCRIPTION
               "This variable is used to administratively enable 
                or disable the VSP.  This variable must not be
                included with any other variables in a SET.  To 
                modify or delete the VSP, the admin state must 
                first be changed to disable.  Then a second PDU
                must be sent to handle the modify or delete."
        ::= { mpoaVirtualSwitchPortEntry 2 } 

    mpoaVspOperStatus OBJECT-TYPE
        SYNTAX  MpoaOperValue
        MAX-ACCESS  read-only
        STATUS      current
        DESCRIPTION
               "This variable gives the operational status
                of the vsp.  The value of initial is used
                when the VSP was administratively enabled
                but the configuration is incorrect, and the
                VSP cannot be activated."
        ::= { mpoaVirtualSwitchPortEntry 3 }

    mpoaVspName OBJECT-TYPE
        SYNTAX      DisplayString (SIZE (0..31))
        MAX-ACCESS  read-write
        STATUS      current
        DESCRIPTION
               "A unique 31-character ascii string used
                to name the VSP."
        ::= { mpoaVirtualSwitchPortEntry 4 }

    mpoaVspEncapsulationType OBJECT-TYPE
        SYNTAX  INTEGER {
              routed(1),
              simpleBridge(2),
              llcBridge(3)
            }
        MAX-ACCESS  read-write
        STATUS      current
        DESCRIPTION
               "The type of packets used on this VSP." 
        ::= { mpoaVirtualSwitchPortEntry 5 }

    mpoaVspPktReplication OBJECT-TYPE
        SYNTAX MpoaYesorNoValue
        MAX-ACCESS  read-write
        STATUS      current
        DESCRIPTION
               "This value can only be configured at the time of
                VSP creation.  Packet replication simulates multi-
                casting by sending a single packet to a default VC
                that copies the packet to multiple PVCs.  Choose yes
                only if there are multiple ATM links, with more than
                1 remote destination."
        ::= { mpoaVirtualSwitchPortEntry 6 }

    mpoaVspLoadShare OBJECT-TYPE
        SYNTAX MpoaYesorNoValue
        MAX-ACCESS  read-write
        STATUS      current
        DESCRIPTION
               "This value should be yes if load-sharing
                is desired between PVCs.  If load-sharing is
                desired, then both default PVCs should be 
                configured for this VSP."
        ::= { mpoaVirtualSwitchPortEntry 7}

    mpoaVspDefaultPort OBJECT-TYPE
        SYNTAX      Integer32 (1..2)
        MAX-ACCESS  read-write
        STATUS      current
        DESCRIPTION
               "This variable contains the preferred default port.  In
                case of fail-over or load-sharing, this port is the 
                primary port."
        ::= { mpoaVirtualSwitchPortEntry 8 } 

    mpoaVspDefaultVc-port1 OBJECT-TYPE
        SYNTAX      MpoaResourceId
        MAX-ACCESS  read-write
        STATUS      current
        DESCRIPTION
               "This variable is only applicable for non-replicating
                ports and should be ignored for replicating ports.
                This variable contains the pvc resource id of the  
                primary default VC if the default physical port is
                port 1.  It contains the pvc resource id of the 
                secondary default VC if load-sharing or fail-over has 
                been chosen and the default physical port is port 2.
                A secondary default VC must be configured if either
                load-sharing or fail-over has been chosen.

                The default VC is used to send packets with unknown 
                unicast and broadcast destination MAC addresses."
        ::= { mpoaVirtualSwitchPortEntry 9 }

    mpoaVspDefaultVc-port2 OBJECT-TYPE
        SYNTAX      MpoaResourceId
        MAX-ACCESS  read-write
        STATUS      current
        DESCRIPTION
               "This variable is only applicable for non-replicating
                ports and should be ignored for replicating ports.
                This variable contains the pvc resource id of the  
                primary default VC if the default physical port is
                port 2.  It contains the pvc resource id of the 
                secondary default VC if load-sharing or fail-over has 
                been chosen and the default physical port is port 1.
                A secondary default VC must be configured if either
                load-sharing or fail-over has been chosen."
        ::= { mpoaVirtualSwitchPortEntry 10 }

    mpoaVspMulticastChan-port1 OBJECT-TYPE
        SYNTAX      Integer32
        MAX-ACCESS  read-only
        STATUS      current
        DESCRIPTION
               "This variable is only applicable for replicating
                ports and should be ignored for non-replicating ports.
                This variable contains the channel id of the primary 
                default multicast channel if the default 
                physical port is port 1.  

                It contains the channel id of the secondary 
                multicast channel if load-sharing or fail-over has 
                been chosen and the default physical port is port 2."
        ::= { mpoaVirtualSwitchPortEntry 11 }

    mpoaVspMulticastChan-port2 OBJECT-TYPE
        SYNTAX      Integer32
        MAX-ACCESS  read-only
        STATUS      current
        DESCRIPTION
               "This variable is only applicable for replicating
                ports and should be ignored for non-replicating ports.
                This variable contains the channel id of the primary 
                default multicast channel if the default 
                physical port is port 2.  

                It contains the channel id of the secondary 
                multicast channel if load-sharing or fail-over has 
                been chosen and the default physical port is port 1."
        ::= { mpoaVirtualSwitchPortEntry 12 }

    mpoaVspRowStatus OBJECT-TYPE
        SYNTAX      RowStatus
        MAX-ACCESS  read-write
        STATUS      current
        DESCRIPTION
               "This variable is included with every SET PDU
                to indicate whether the SET PDU contains a create
                or delete transaction type."
        ::= { mpoaVirtualSwitchPortEntry 13 }
 
    --
    -- The mpoa (1483) ATM Link Table
    --
    mpoaAtmLinkTable  OBJECT-TYPE
        SYNTAX      SEQUENCE OF MpoaAtmLinkEntry
        MAX-ACCESS  not-accessible
        STATUS      current
        DESCRIPTION
               "A table of all the ATM links created for MPOA
                traffic on the ATM module. The maximum number of 
                expected entries is 16k."
        ::= { mpoa 3 }

    mpoaAtmLinkEntry OBJECT-TYPE
        SYNTAX      MpoaAtmLinkEntry
        MAX-ACCESS  not-accessible
        STATUS      current
        DESCRIPTION
               "An entry containing management information pertaining
                to an mpoa ATM Link.  This table is doubly-
                indexed by the VSP id (index) and the link
                id (index)."
        INDEX   { mpoaAtmLinkVspIndex, mpoaAtmLinkIndex }
        ::= { mpoaAtmLinkTable 1 }

    MpoaAtmLinkEntry ::=
        SEQUENCE {
           mpoaAtmLinkVspIndex		  Integer32,
		     mpoaAtmLinkIndex           MpoaResourceId,    
		     mpoaAtmLinkAdminStatus	  MpoaEnabledValue,
           mpoaAtmLinkOperStatus      MpoaOperValue,
           mpoaAtmLinkName            DisplayString,
           mpoaAtmLinkDefaultVc       MpoaResourceId,
           mpoaAtmLinkFailOverLink    MpoaResourceId,
           mpoaAtmLinkOutPriority-0   MpoaResourceId,
           mpoaAtmLinkOutPriority-1   MpoaResourceId,
           mpoaAtmLinkOutPriority-2   MpoaResourceId,
           mpoaAtmLinkOutPriority-3   MpoaResourceId,
           mpoaAtmLinkOutPriority-4   MpoaResourceId,
           mpoaAtmLinkOutPriority-5   MpoaResourceId,
           mpoaAtmLinkOutPriority-6   MpoaResourceId,
           mpoaAtmLinkOutPriority-7   MpoaResourceId,
           mpoaAtmLinkRowStatus		  RowStatus
		}

    mpoaAtmLinkVspIndex OBJECT-TYPE
        SYNTAX      Integer32 (1..128)
        MAX-ACCESS  read-only
        STATUS      current
        DESCRIPTION
               "Index of the VSP that this link is associated
                with."
        ::= { mpoaAtmLinkEntry 1 }

    mpoaAtmLinkIndex OBJECT-TYPE
        SYNTAX      MpoaResourceId
        MAX-ACCESS  read-only
        STATUS      current
        DESCRIPTION
               "The ATM link id number.  
                This variable comprises the second index in the link
                row entry.  To get a valid link index, application
                must first get value of mpoaNextLinkResourceId, 
                before creating a new entry."
        ::= { mpoaAtmLinkEntry 2 }


    mpoaAtmLinkAdminStatus OBJECT-TYPE
        SYNTAX      MpoaEnabledValue
        MAX-ACCESS  read-write
        STATUS      current
        DESCRIPTION
               "This variable is used to administratively enable
                or disable the link.  This variable must not be
                included with any other variables in a SET.  To 
                modify or delete the link, the admin state must 
                first be changed to disable.  Then a second PDU
                must be sent to handle the modify or delete."
        ::= { mpoaAtmLinkEntry 3 } 

    mpoaAtmLinkOperStatus OBJECT-TYPE
        SYNTAX  MpoaOperValue
        MAX-ACCESS  read-only
        STATUS      current
        DESCRIPTION
               "This variable gives the operational status
                of the link.  The value of initial is used
                when the link was administratively enabled
                but the configuration is incorrect, and the
                link cannot be activated."
        ::= { mpoaAtmLinkEntry 4 }

   mpoaAtmLinkName OBJECT-TYPE
        SYNTAX      DisplayString (SIZE (0..31))
        MAX-ACCESS  read-write
        STATUS      current
        DESCRIPTION
               "A unique 31-character ascii string used
                to name the link."
        ::= { mpoaAtmLinkEntry 5 }

    mpoaAtmLinkDefaultVc OBJECT-TYPE
        SYNTAX      MpoaResourceId
        MAX-ACCESS  read-write
        STATUS      current
        DESCRIPTION
               "Index of the PVC to be used as the default channel
                for broadcast destination and unicast traffic.  
                Not valid to set if the VSP is a non-replicating port."
        ::= { mpoaAtmLinkEntry 6 }

    mpoaAtmLinkFailOverLink OBJECT-TYPE
        SYNTAX      MpoaResourceId
        MAX-ACCESS  read-write
        STATUS      current
        DESCRIPTION
               "This variable contains the link id (link
                resource id) of the link to be used for fail
                over mode.  This variable must not be set
                unless fail over mode is desired.  The
                fail over link must have PVCs that are 
                associated with another physical port, 
                not the default port."  
        ::= { mpoaAtmLinkEntry 8 }

    mpoaAtmLinkOutPriority-0 OBJECT-TYPE
        SYNTAX      MpoaResourceId
        MAX-ACCESS  read-write
        STATUS      current
        DESCRIPTION
               "This variable contains the PVC Resource id 
                (index) of the PVC assigned to outbound  
                priority level 0.  In total, there are 8 priority
                levels and 8 PVCs to be assigned.  The same
                PVC can be specified for all levels."
        ::= { mpoaAtmLinkEntry 9 }

    mpoaAtmLinkOutPriority-1 OBJECT-TYPE
        SYNTAX      MpoaResourceId
        MAX-ACCESS  read-write
        STATUS      current
        DESCRIPTION
               "This variable contains the PVC resource id 
                (index) of the PVC assigned to outbound priority
                level 1."
        ::= { mpoaAtmLinkEntry 10 }

    mpoaAtmLinkOutPriority-2 OBJECT-TYPE
        SYNTAX      MpoaResourceId
        MAX-ACCESS  read-write
        STATUS      current
        DESCRIPTION
               "This variable contains the PVC resource id 
                (index) of the PVC assigned to outbound 
                priority level 2."  
        ::= { mpoaAtmLinkEntry 11 }

    mpoaAtmLinkOutPriority-3 OBJECT-TYPE
        SYNTAX      MpoaResourceId
        MAX-ACCESS  read-write
        STATUS      current
        DESCRIPTION
               "This variable contains the PVC resource id 
                (index) of the PVC assigned to outbound 
                priority level 3."
        ::= { mpoaAtmLinkEntry 12 }

    mpoaAtmLinkOutPriority-4 OBJECT-TYPE
        SYNTAX      MpoaResourceId
        MAX-ACCESS  read-write
        STATUS      current
        DESCRIPTION
               "This variable contains the PVC resource id 
                (index) of the PVC assigned to outbound 
                priority level 4."
        ::= { mpoaAtmLinkEntry 13 }

    mpoaAtmLinkOutPriority-5 OBJECT-TYPE
        SYNTAX      MpoaResourceId
        MAX-ACCESS  read-write
        STATUS      current
        DESCRIPTION
               "This variable contains the PVC resource id 
                (index) of the PVC assigned to outbound 
                priority level 5."
        ::= { mpoaAtmLinkEntry 14 }

    mpoaAtmLinkOutPriority-6 OBJECT-TYPE
        SYNTAX      MpoaResourceId
        MAX-ACCESS  read-write
        STATUS      current
        DESCRIPTION
               "This variable contains the PVC resource id 
                (index) of the PVC assigned to outbound 
                priority level 6."
        ::= { mpoaAtmLinkEntry 15 }

    mpoaAtmLinkOutPriority-7 OBJECT-TYPE
        SYNTAX      MpoaResourceId
        MAX-ACCESS  read-write
        STATUS      current
        DESCRIPTION
               "This variable contains the PVC resource id 
                (index) of the PVC assigned to outbound 
                priority level 7."
        ::= { mpoaAtmLinkEntry 16 }

    mpoaAtmLinkRowStatus OBJECT-TYPE
        SYNTAX      RowStatus
        MAX-ACCESS  read-write
        STATUS      current
        DESCRIPTION
               "This variable is included with every SET PDU
                to indicate whether the SET PDU contains a create
                or delete transaction type."
        ::= { mpoaAtmLinkEntry 17 } 


    --
    -- The mpoa (1483) PVC Table
    --
    mpoaPvcTable  OBJECT-TYPE
        SYNTAX      SEQUENCE OF MpoaPvcEntry
        MAX-ACCESS  not-accessible
        STATUS      current
        DESCRIPTION
               "A table of all the PVCs created for MPOA traffic
                on the ATM module. The maximum number of expected
                entries is 128k."
        ::= { mpoa 4 }

    mpoaPvcEntry OBJECT-TYPE
        SYNTAX      MpoaPvcEntry
        MAX-ACCESS  not-accessible
        STATUS      current
        DESCRIPTION
               "An entry containing management information pertaining
                to an MPOA PVC.  This table has 3 indicies: vsp id,
                link id and resource id."
        INDEX   { mpoaPvcVspIndex, mpoaPvcLinkIndex, mpoaPvcResIndex }
        ::= { mpoaPvcTable 1 }

    MpoaPvcEntry ::=
        SEQUENCE {
           mpoaPvcVspIndex            Integer32,
           mpoaPvcLinkIndex           MpoaResourceId,
           mpoaPvcResIndex            MpoaResourceId,
           mpoaPvcPort                Integer32,
		     mpoaPvcVpi                 Integer32,
           mpoaPvcVci                 Integer32,
           mpoaPvcInPriorityMap       Integer32,
           mpoaPvcTrafficClass        INTEGER,
           mpoaPvcCDVT                Integer32,
           mpoaPvcPCR                 Integer32,
           mpoaPvcSCR                 Integer32,
           mpoaPvcMBS                 Integer32,
           mpoaPvcRandomEarlyDetPktId Integer32,
           mpoaPvcRowStatus			  RowStatus
		}

    mpoaPvcVspIndex OBJECT-TYPE
        SYNTAX      Integer32 (1..128)
        MAX-ACCESS  read-only
        STATUS      current
        DESCRIPTION
               "Index of the VSP that this link and PVC is associated
                with."
        ::= { mpoaPvcEntry 1 }

    mpoaPvcLinkIndex OBJECT-TYPE
        SYNTAX      MpoaResourceId 
        MAX-ACCESS  read-only
        STATUS      current
        DESCRIPTION
               "The Link Id number of the link associated with this
                PVC."
        ::= { mpoaPvcEntry 2 }

    mpoaPvcResIndex OBJECT-TYPE
        SYNTAX      MpoaResourceId
        MAX-ACCESS  read-only
        STATUS      current
        DESCRIPTION
               "The Resource Id associated with the PVC.  It is
                associated with a port,vpi, and vci.  Resource Ids are
                re-assigned each time the switch is re-booted.  To get
                a valid resource id, application must first get value
                of mpoaNextPvcResourceId, before creating a new entry."
        ::= { mpoaPvcEntry 3 }

   mpoaPvcPort OBJECT-TYPE
        SYNTAX      Integer32 (1..2)
        MAX-ACCESS  read-write
        STATUS      current
        DESCRIPTION
               "Physical port that this PVC is associated
                with.  This variable is only modifiable at
                CREATE time."
        ::= { mpoaPvcEntry 4 }

    mpoaPvcVpi OBJECT-TYPE
        SYNTAX      Integer32 (0..255)
        MAX-ACCESS  read-write
        STATUS      current
        DESCRIPTION
               "The PVC virtual path identifier(VPI).  Must be unique
                among all VPIs configured for the ATM module.  This variable
                is only modifiable at CREATE time."
        ::= { mpoaPvcEntry 5 }

    mpoaPvcVci OBJECT-TYPE
        SYNTAX      Integer32 (32..65535)
        MAX-ACCESS  read-write
        STATUS      current
        DESCRIPTION
               "The PVC virtual circuit identifier(VCI).  Must be 
                unique among all VCIs configured for the ATM module.
                This variable is only modifiable at CREATE time."
        ::= { mpoaPvcEntry 6 }


    mpoaPvcInPriorityMap OBJECT-TYPE
        SYNTAX      Integer32 (0..7)
        MAX-ACCESS  read-write
        STATUS      current
        DESCRIPTION
               "The inbound priority map is the priority to
                be assigned to frames received on this PVC as they
                are passed on to the local VLAN segment."
        ::= { mpoaPvcEntry 7 }

    mpoaPvcTrafficClass OBJECT-TYPE
        SYNTAX  INTEGER {
              ubr(1),
              rtVbr(2),
              nrtVbr(3),
              cbr(4)
            }      
        MAX-ACCESS  read-write
        STATUS      current
        DESCRIPTION
               "The assigned service category for the PVC.  This variable
                is only modifiable at CREATE time."
        ::= { mpoaPvcEntry 8 }

    mpoaPvcCDVT OBJECT-TYPE
        SYNTAX      Integer32 (1..10000) 
        MAX-ACCESS  read-write
        STATUS      current
        DESCRIPTION
               "Cell Delay Variation Tolerance."
        ::= { mpoaPvcEntry 9 }


    mpoaPvcPCR OBJECT-TYPE
        SYNTAX      Integer32 (100..1412830)
        MAX-ACCESS  read-write
        STATUS      current
        DESCRIPTION
               "Peak cell rate in cells per second."
        ::= { mpoaPvcEntry 10 }

    mpoaPvcSCR OBJECT-TYPE
        SYNTAX      Integer32 (100..1412830) 
        MAX-ACCESS  read-write
        STATUS      current
        DESCRIPTION
               "Sustainable cell rate in cells per second.
                Ignored for UBR and CBR."
        ::= { mpoaPvcEntry 11 }

    mpoaPvcMBS OBJECT-TYPE
        SYNTAX      Integer32 (2..1048576) 
        MAX-ACCESS  read-write
        STATUS      current
        DESCRIPTION
               "Maximum Burst Size."
        ::= { mpoaPvcEntry 12 }

    mpoaPvcRandomEarlyDetPktId OBJECT-TYPE
        SYNTAX      Integer32 (1..4)
        MAX-ACCESS  read-write
        STATUS      current
        DESCRIPTION
               "Random Early Detection Packet Id."
        ::= { mpoaPvcEntry 13 }

    mpoaPvcRowStatus OBJECT-TYPE
        SYNTAX      RowStatus
        MAX-ACCESS  read-write
        STATUS      current
        DESCRIPTION
               "This variable must be included with every SET
                PDU to indicate whether the PDU contains a CREATE,
                DELETE, or MODIFY transaction type."
        ::= { mpoaPvcEntry 14 }

    -- MPOA proprietary traps
    mpoaTraps   OBJECT IDENTIFIER ::= { mpoa 5 }


    mpoaVspId OBJECT-TYPE
        SYNTAX      Integer32 (1..128)
        MAX-ACCESS  accessible-for-notify
        STATUS      current
        DESCRIPTION
               "Used in the mpoaTrapLinkChange trap.  Index of the VSP 
                that the trap represents.  If the link Id is non-zero
                than the vspId is the Id of the VSP associated with the 
                link whose operational state has changed.  If the link 
                Id is zero, then the vspId represents the VSP whose 
                operational state has changed."
        ::= { mpoaTraps 1 }

    mpoaLinkId OBJECT-TYPE
        SYNTAX      MpoaResourceId
        MAX-ACCESS  accessible-for-notify
        STATUS      current
        DESCRIPTION
               "Used in the mpoaTrapLinkChange trap.  Index of the link 
                that the trap represents.  If the link Id is non-zero
                than it is the Id of the link whose operational state has changed.  
                If the link Id is zero, then it should be ignored."
        ::= { mpoaTraps 2 }

    mpoaOperState OBJECT-TYPE
        SYNTAX  MpoaOperValue
        MAX-ACCESS  accessible-for-notify
        STATUS      current
        DESCRIPTION
               "This variable gives the operational status
                of the link or VSP.  The value of initial is used
                when the link/VSP was administratively enabled
                but the configuration is incorrect, and the
                link/VSP cannot be activated."
        ::= { mpoaTraps 3 }

    mpoaTrapLinkChange NOTIFICATION-TYPE
        OBJECTS      { mpoaVspId,
                       mpoaLinkId,
                       mpoaOperState
                     }
        STATUS       current
        DESCRIPTION
            "A mpoaTrapLinkChange trap is generated when
             a VSP or ATM link changes operational state."
        ::= { mpoaTraps 4 } 

END
