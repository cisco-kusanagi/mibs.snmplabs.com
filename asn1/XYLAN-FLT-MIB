XYLAN-FLT-MIB DEFINITIONS ::= BEGIN

     --  xylan-flt.mib
     --  Revision: 1.0
     --  Date: March 1999

     --  Alcatel Internetworking, Inc.
     --  26801 W. Agoura Road
     --  Calabasas, CA 91301
     --  (818) 880-3500
     --  support@ind.alcatel.com

     --  This module provides authoritative definitions for Alcatel Internetworking, Inc.
     --  HRE-X Filtering.

     --  This module will be extended, as needed.

     --  Alcatel Internetworking, Inc. reserves the right to make changes in 
     --  specification and other information contained in this document 
     --  without prior notice.  The reader should consult Alcatel Internetworking,
     --  Inc. to determine whether any such changes have been made.
     --  Current MIBs are availible from the following URLs:
     --			ftp://ftp.ind.alcatel.com/pub/products/mibs
     --			http://www.ind.alcatel.com

     --  In no event shall Alcatel Internetworking, Inc. be liable for any incidental, 
     --  indirect, special, or consequential damages whatsoever (including 
     --  but not limited to lost profits) arising out of or related to this
     --  document or the information contained in it, even if Alcatel Internetworking,
     --  Inc. has been advised of, known, or should have known, the 
     --  possibility of such damages.
     --  Alcatel Internetworking, Inc. grants vendors, end-users, and other interested
     --  parties a non-exclusive license to use this Specification in connection
     --  with the management of Alcatel Internetworking, Inc. products.

     --  Copyright (C) 1998, Alcatel Internetworking, Inc. All Rights Reserved.

     
     	IMPORTS
		OBJECT-TYPE
			FROM RFC-1212
		DisplayString 
			FROM RFC1213-MIB
		IpAddress 
			FROM RFC1155-SMI
	        xylanFltArch
			FROM XYLAN-BASE-MIB 
		MacAddress
			FROM BRIDGE-MIB
			;

--
--

     xylanFltStatus         OBJECT IDENTIFIER ::= { xylanFltArch 1 }
     xylanFltStaticConfig   OBJECT IDENTIFIER ::= { xylanFltArch 2 }
     xylanFltActiveConfig   OBJECT IDENTIFIER ::= { xylanFltArch 3 }
     xylanFltTraps          OBJECT IDENTIFIER ::= { xylanFltArch 4 }

--
--

-- Filtering Status

xylanFltActiveAdminState OBJECT-TYPE
	SYNTAX INTEGER {
		enabled (1),
		disabled (2)
	}
	ACCESS  read-only
	STATUS  mandatory
	DESCRIPTION "The current administrative state of the HRE-X filtering
	             software." 
	::= { xylanFltStatus 1 }

xylanFltActiveOperState OBJECT-TYPE
	SYNTAX INTEGER {
		initializing (0),
		active (1),
		deactivating (2),
		inactive (3)
	}
	ACCESS  read-only
	STATUS  mandatory
	DESCRIPTION "The current operational state of the HRE-X filtering
	             software.  This is independent of the administrative
	             state."
	::= { xylanFltStatus 2 }

xylanFltConfigAdminState OBJECT-TYPE
        SYNTAX INTEGER {
                enabled (1),
                disabled (2)
        }
        ACCESS  read-write
        STATUS  mandatory
        DESCRIPTION "The current configured administrative state of the 
		     HRE-X filtering software."
        ::= { xylanFltStatus 3 }


xylanFltCommit OBJECT-TYPE
        SYNTAX INTEGER 
        ACCESS  write-only
        STATUS  mandatory
        DESCRIPTION "Commits the current configuration."
        ::= { xylanFltStatus 4 }


--  Static Configuration

     xylanFltGroups         OBJECT IDENTIFIER ::= { xylanFltStaticConfig 1 }
     xylanFltServices       OBJECT IDENTIFIER ::= { xylanFltStaticConfig 2 }
     xylanFltGlobals        OBJECT IDENTIFIER ::= { xylanFltStaticConfig 3 }

xylanFltGroupTable OBJECT-TYPE
  SYNTAX       SEQUENCE OF FltGroupEntry
  ACCESS       not-accessible
  STATUS       mandatory
  DESCRIPTION  "Group entry for HRE-X filtering feature.  This object
		contains a collection of Group objects when contain a
		list of filtering rules."
  ::= {xylanFltGroups 1}

xylanFltGroupEntry OBJECT-TYPE
  SYNTAX      FltGroupEntry
  ACCESS      not-accessible
  STATUS      mandatory
  DESCRIPTION "Each entry corresponds to one Group."
  INDEX       {
              xylanFltGroupIndex
              }
  ::= {xylanFltGroupTable 1}

FltGroupEntry ::= SEQUENCE {
                xylanFltGroupIndex
                   OCTET STRING (SIZE(30)),
		xylanFltGroupAdminState
		   INTEGER,
                xylanFltGroupProtocol
                   INTEGER,
                xylanFltGroupAdrType
                   INTEGER
                }

xylanFltGroupIndex OBJECT-TYPE
        SYNTAX OCTET STRING (SIZE(30)) 
        ACCESS  read-only
        STATUS  mandatory
        DESCRIPTION     "The group index which is the octet string of 
			printable characters containing
			the name of the group."
        ::={ xylanFltGroupEntry 1 }

xylanFltGroupAdminState OBJECT-TYPE
  SYNTAX  INTEGER       {
                        active (1),
                        delete (2)
                        }
  ACCESS  read-write
  STATUS  mandatory
  DESCRIPTION   "The current status of this group.  active (1) means
                 the route is functioning, delete (2) tells SNMP to
                 delete the route "
  ::= { xylanFltGroupEntry 2 }

xylanFltGroupProtocol OBJECT-TYPE
   SYNTAX       INTEGER        {
			       na (0),
                               ip  (1),
                               ipx (2)
                               }
   ACCESS       read-write
   STATUS       mandatory
   DESCRIPTION  "The protocol type of the group.  This has
		significance with the index of the OIDs of
		the rules in the group."
   ::= {xylanFltGroupEntry 3}

xylanFltGroupAdrType OBJECT-TYPE
   SYNTAX       INTEGER        {
			       na (0),
                               destination  (1),
                               source (2)
                               }
   ACCESS       read-write
   STATUS       mandatory
   DESCRIPTION  "This indicates which address is designated first.
		e.g. If destination is specified, the addresses
		the OIDs of the rules are ordered <destination>
		<source>.  
		If the group is an IPX group, this indicator does 
		not affect the OID."
   ::= {xylanFltGroupEntry 4}

xylanFltRuleListTable OBJECT-TYPE
   SYNTAX       SEQUENCE OF FltRuleListEntry
   ACCESS       not-accessible
   STATUS       mandatory
   DESCRIPTION  "The address and rule pairings."
   ::= {xylanFltGroups 2}

xylanFltRuleListEntry OBJECT-TYPE
   SYNTAX       FltRuleListEntry
   ACCESS       not-accessible
   STATUS       mandatory
   DESCRIPTION  "Each entry corresponds to one rule."
   INDEX        {
                xylanFltGroupIndex, xylanFltRuleListIndex
                }
   ::= {xylanFltRuleListTable 1}

FltRuleListEntry ::= SEQUENCE {
        xylanFltRuleListIndex
	        OCTET STRING (SIZE(47)),
	xylanFltRuleListAdminState
		INTEGER,
        xylanFltRuleListRule
        	INTEGER

        }

xylanFltRuleListIndex OBJECT-TYPE
   SYNTAX       OCTET STRING (SIZE(47))
   ACCESS       read-only
   STATUS       mandatory
   DESCRIPTION  "Rule index is made up of the octets of the
		group name and the network addresses of the 
		rule.  It has the following format:
		IP  - <group_name>,0,<adr-4 bytes><mask-4 bytes><adr-4bytes><mask-4 bytes>
		IPX - <group_name>,0,<net-4 bytes><node-6 bytes> "
  ::= {xylanFltRuleListEntry 1}

xylanFltRuleListAdminState OBJECT-TYPE
  SYNTAX  INTEGER       {
                        active (1),
                        delete (2)
                        }
  ACCESS  read-write
  STATUS  mandatory
  DESCRIPTION   "The current status of this group.  active (1) means
                 the route is functioning, delete (2) tells SNMP to
                 delete the route "
  ::= { xylanFltRuleListEntry 2 }

xylanFltRuleListRule OBJECT-TYPE
   SYNTAX       INTEGER    {
                            allow (1),
                            deny  (2)
                            }
   ACCESS       read-write
   STATUS       mandatory
   DESCRIPTION  "The rule for the address pair.  1) allows traffic for the 
		addresses and 2) rejects all trafic for the pair."
   ::= {xylanFltRuleListEntry 3}

--

xylanFltServiceTable OBJECT-TYPE
   SYNTAX       SEQUENCE OF FltServiceEntry
   ACCESS       not-accessible
   STATUS       mandatory
   DESCRIPTION  "Service entry for HRE-X filtering feature.  This object
                contains a collection of IP port numbers and filtering
		Group objects.  Thus rules for different service such
		as FTP or Telnet may be defined."
   ::= {xylanFltServices 1}

xylanFltServiceEntry OBJECT-TYPE
   SYNTAX       FltServiceEntry
   ACCESS       not-accessible
   STATUS       mandatory
   DESCRIPTION  "Each entry corresponds to one service."
   INDEX        {
                xylanFltServiceIndex
                }
   ::= {xylanFltServiceTable 1}

FltServiceEntry ::= SEQUENCE {
                xylanFltServiceIndex
	                OCTET STRING (SIZE(20)),
		xylanFltServiceAdminState
			INTEGER
                }

xylanFltServiceIndex OBJECT-TYPE
   SYNTAX       OCTET STRING (SIZE(20))
   ACCESS       read-only
   STATUS       mandatory
   DESCRIPTION  "The index is made up of an octet string of ASCII
		characters containing the name of the service."
   ::= {xylanFltServiceEntry 1}

xylanFltServiceAdminState OBJECT-TYPE
  SYNTAX  INTEGER       {
                        active (1),
                        delete (2)
                        }
  ACCESS  read-write
  STATUS  mandatory
  DESCRIPTION   "The current status of this group.  active (1) means
                 the route is functioning, delete (2) tells SNMP to
                 delete the route "
  ::= { xylanFltServiceEntry 2 }

xylanFltServiceNumberTable OBJECT-TYPE
   SYNTAX       SEQUENCE OF FltServiceNumberEntry
   ACCESS       not-accessible
   STATUS       mandatory
   DESCRIPTION  "This table contains the port numbers associated 
		with a particular service."
   ::= {xylanFltServices 2}

xylanFltServiceNumberEntry OBJECT-TYPE
   SYNTAX       FltServiceNumberEntry
   ACCESS       not-accessible
   STATUS       mandatory
   DESCRIPTION  "Each entry corresponds to one port number."
   INDEX        {
                xylanFltServiceIndex, xylanFltServiceNumberIndex
                }
   ::= {xylanFltServiceNumberTable 1}

 FltServiceNumberEntry ::= SEQUENCE {
                xylanFltServiceNumberIndex
                OCTET STRING (SIZE(24)),
		xylanFltServiceNumberAdminState
			INTEGER
                }

xylanFltServiceNumberIndex OBJECT-TYPE
   SYNTAX       OCTET STRING (SIZE(24))
   ACCESS       read-only
   STATUS       mandatory
   DESCRIPTION  "Service number index is made up of the octets of the
                group name and the port number:
                <service_name>,0,<port number-4 bytes>"
   ::= {xylanFltServiceNumberEntry 1}

xylanFltServiceNumberAdminState OBJECT-TYPE
	SYNTAX  INTEGER {
                        active (1),
                        delete (2)
                        }
	ACCESS  read-write
	STATUS  mandatory
	DESCRIPTION   "The current status of this group.  active (1) means
                 the route is functioning, delete (2) tells SNMP to
                 delete the route "
	::= { xylanFltServiceNumberEntry 2 }

xylanFltServiceGroupTable OBJECT-TYPE
	SYNTAX       SEQUENCE OF FltServiceGroupEntry
	ACCESS       not-accessible
	STATUS       mandatory
	DESCRIPTION  "This table contains the groups associated
                with a particular service."
	::= {xylanFltServices 3}

xylanFltServiceGroupEntry OBJECT-TYPE
	SYNTAX       FltServiceGroupEntry
	ACCESS       not-accessible
	STATUS       mandatory
	DESCRIPTION  "Each entry corresponds to one group."
	INDEX   {
                xylanFltServiceIndex, xylanFltServiceGroupIndex
                }
	::= {xylanFltServiceGroupTable 1}

 FltServiceGroupEntry ::= SEQUENCE {
                xylanFltServiceGroupIndex
                OCTET STRING (SIZE(44)),
		xylanFltServiceGroupAdminState
			INTEGER
                }

xylanFltServiceGroupIndex OBJECT-TYPE
	SYNTAX       OCTET STRING (SIZE(44))
	ACCESS       read-only
	STATUS       mandatory
	DESCRIPTION  "Service group index is made up of the octets of the
                service name and the group name:
                <service_name>,0,<group name>"
	::= {xylanFltServiceGroupEntry 1}

xylanFltServiceGroupAdminState OBJECT-TYPE
	SYNTAX  INTEGER {
                        active (1),
                        delete (2)
                        }
	ACCESS  read-write
	STATUS  mandatory
	DESCRIPTION   "The current status of this group.  active (1) means
                 the route is functioning, delete (2) tells SNMP to
                 delete the route "
	::= { xylanFltServiceGroupEntry 2 }

xylanFltGlobalIPRule OBJECT-TYPE
	SYNTAX INTEGER {
		allow(1),
		deny(2)
		}
	ACCESS read-write
	STATUS mandatory
	DESCRIPTION "Global IP rule."
	::= { xylanFltGlobals 1 }

xylanFltGlobalIPXRule OBJECT-TYPE
        SYNTAX INTEGER {
               allow(1),
               deny(2)
               }
        ACCESS read-write
        STATUS mandatory
        DESCRIPTION "Global IPX rule."
        ::= { xylanFltGlobals 2 }

xylanFltGlobalPrecedence OBJECT-TYPE
        SYNTAX INTEGER {
               destination(1),
               source(2)
               }
        ACCESS read-write
        STATUS mandatory
        DESCRIPTION "Global rule precedence (tie breaker)."
        ::= { xylanFltGlobals 3 }

xylanFltGlobalGroupTable OBJECT-TYPE
        SYNTAX SEQUENCE OF FltGlobalGroupEntry
        ACCESS not-accessible
        STATUS mandatory
	DESCRIPTION "List of active groups."
        ::= { xylanFltGlobals 4 }

xylanFltGlobalGroupEntry OBJECT-TYPE
        SYNTAX FltGlobalGroupEntry
        ACCESS not-accessible
        STATUS mandatory
        DESCRIPTION  "Each entry corresponds to one group."
        INDEX  {
               xylanFltGlobalGroupIndex
               }
	::= {xylanFltGlobalGroupTable 1}

FltGlobalGroupEntry ::= SEQUENCE {
               xylanFltGlobalGroupIndex
               OCTET STRING (SIZE(44)),
               xylanFltGlobalGroupAdminState
                        INTEGER
               }

xylanFltGlobalGroupIndex OBJECT-TYPE
	SYNTAX OCTET STRING (SIZE(44))
	ACCESS read-only
	STATUS mandatory
	DESCRIPTION  "Global group index is made up of the octets of the
               group name."
	::= {xylanFltGlobalGroupEntry 1}

xylanFltGlobalGroupAdminState OBJECT-TYPE
	SYNTAX INTEGER {
                        active (1),
                        delete (2)
                        }
	ACCESS read-write
	STATUS mandatory
	DESCRIPTION  "The current status of this group.  active (1) means
               the route is functioning, delete (2) tells SNMP to
               delete the route "
	::= { xylanFltGlobalGroupEntry 2 }

xylanFltGlobalServiceTable OBJECT-TYPE
        SYNTAX SEQUENCE OF FltGlobalServiceEntry
        ACCESS not-accessible
        STATUS mandatory
        DESCRIPTION "List of active services."
        ::= { xylanFltGlobals 5 }

xylanFltGlobalServiceEntry OBJECT-TYPE
	SYNTAX FltGlobalServiceEntry
	ACCESS not-accessible
	STATUS mandatory
	DESCRIPTION  "Each entry corresponds to one service."
	INDEX  {
               xylanFltGlobalServiceIndex
               }
	::= {xylanFltGlobalServiceTable 1}

FltGlobalServiceEntry ::= SEQUENCE {
               xylanFltGlobalServiceIndex
               OCTET STRING (SIZE(44)),
               xylanFltGlobalServiceAdminState
                       INTEGER
               }

xylanFltGlobalServiceIndex OBJECT-TYPE
	SYNTAX OCTET STRING (SIZE(44))
	ACCESS read-only
	STATUS mandatory
	DESCRIPTION  "Global service index is made up of the octets of the
	       service name."
	::= {xylanFltGlobalServiceEntry 1}

xylanFltGlobalServiceAdminState OBJECT-TYPE
	SYNTAX  INTEGER       {
                        active (1),
                        delete (2)
                        }
	ACCESS read-write
	STATUS mandatory
	DESCRIPTION   "The current status of this service.  active (1) means
               the route is functioning, delete (2) tells SNMP to
               delete the route "
	::= { xylanFltGlobalServiceEntry 2 }



-- Active Configuration

xylanFltIpServicePortTbl OBJECT-TYPE 
	SYNTAX SEQUENCE OF FltIpServicePortTblEntry
	ACCESS not-accessible
	STATUS mandatory
	DESCRIPTION "Table that maps a service name to the list of TCP
	             ports it represents."
	::= { xylanFltActiveConfig 1 }

xylanFltIpServicePortTblEntry OBJECT-TYPE
	SYNTAX FltIpServicePortTblEntry
	ACCESS not-accessible
	STATUS mandatory
	DESCRIPTION "Entry in table that maps a service name to the list of
                     TCP ports it represents."
	INDEX { xylanFltIpServicePortName, xylanFltIpServicePortNumber }
	::= { xylanFltIpServicePortTbl 1 }

FltIpServicePortTblEntry ::= SEQUENCE {
	xylanFltIpServicePortName DisplayString(SIZE(20)), 
	xylanFltIpServicePortNumber INTEGER
	}

xylanFltIpServicePortName OBJECT-TYPE
   	SYNTAX  DisplayString (SIZE(20))
	ACCESS  read-only
	STATUS  mandatory
	DESCRIPTION "Name of service for HRE-X Filtering Engine."
	::= { xylanFltIpServicePortTblEntry 1 }

xylanFltIpServicePortNumber OBJECT-TYPE
   	SYNTAX  INTEGER
	ACCESS  read-only
	STATUS  mandatory
	DESCRIPTION "TCP port number assigned to a service for HRE-X Filtering 
	             Engine."
	::= { xylanFltIpServicePortTblEntry 2 }

xylanFltIpServiceRuleTbl OBJECT-TYPE
	SYNTAX SEQUENCE OF FltIpServiceRuleTblEntry
	ACCESS not-accessible
	STATUS mandatory
	DESCRIPTION "Table that maps a service name to the list of filtering 
	             rules.  This includes the special service, GLOBAL, which 
	             is comprised of the global rules."
	::= { xylanFltActiveConfig 2 }

xylanFltIpServiceRuleTblEntry OBJECT-TYPE
	SYNTAX FltIpServiceRuleTblEntry
	ACCESS not-accessible
	STATUS mandatory
	DESCRIPTION "Entry in table that maps a service name (or GLOBAL for global
	             rules to its list of filtering rules."
	INDEX { xylanFltIpServiceRuleName, xylanFltIpServiceRuleID }
	::= { xylanFltIpServiceRuleTbl 1 }

FltIpServiceRuleTblEntry ::= SEQUENCE {
	xylanFltIpServiceRuleName DisplayString(SIZE(20)), 
	xylanFltIpServiceRuleID INTEGER,
	xylanFltIpServiceRuleDest IpAddress,
	xylanFltIpServiceRuleDestMask OCTET STRING (SIZE(4)),
	xylanFltIpServiceRuleSrc IpAddress,
	xylanFltIpServiceRuleSrcMask OCTET STRING (SIZE(4)),
	xylanFltIpServiceRuleDisp INTEGER,
	xylanFltIpServiceRuleCount INTEGER,
	xylanFltIpServiceRuleGroup DisplayString(SIZE(20))
	}

xylanFltIpServiceRuleName OBJECT-TYPE
   	SYNTAX  DisplayString (SIZE(20))
	ACCESS  read-only
	STATUS  mandatory
	DESCRIPTION "Name of service (or Global for global rules) for HRE-X Filtering 
	             Engine."
	::= { xylanFltIpServiceRuleTblEntry 1 }

xylanFltIpServiceRuleID OBJECT-TYPE
   	SYNTAX  INTEGER
	ACCESS  read-only
	STATUS  mandatory
	DESCRIPTION "Rule ID for filtering rule."
	::= { xylanFltIpServiceRuleTblEntry 2 }

xylanFltIpServiceRuleDest OBJECT-TYPE
   	SYNTAX  IpAddress
	ACCESS  read-only
	STATUS  mandatory
	DESCRIPTION "Destination address for the filtering rule."
	::= { xylanFltIpServiceRuleTblEntry 3 }

xylanFltIpServiceRuleDestMask OBJECT-TYPE
   	SYNTAX  OCTET STRING (SIZE(4))
	ACCESS  read-only
	STATUS  mandatory
	DESCRIPTION "The destination address mask."
	::= { xylanFltIpServiceRuleTblEntry 4 }

xylanFltIpServiceRuleSrc OBJECT-TYPE
   	SYNTAX  IpAddress
	ACCESS  read-only
	STATUS  mandatory
	DESCRIPTION "Source address for the filtering rule."
	::= { xylanFltIpServiceRuleTblEntry 5 }

xylanFltIpServiceRuleSrcMask OBJECT-TYPE
   	SYNTAX  OCTET STRING (SIZE(4))
	ACCESS  read-only
	STATUS  mandatory
	DESCRIPTION "The source address mask."
	::= { xylanFltIpServiceRuleTblEntry 6 }

xylanFltIpServiceRuleDisp OBJECT-TYPE
   	SYNTAX  INTEGER {
		allow (1),
		deny (2)
	}
	ACCESS  read-only
	STATUS  mandatory
	DESCRIPTION "The disposition for the filtering rule."
	::= { xylanFltIpServiceRuleTblEntry 7 }

xylanFltIpServiceRuleCount OBJECT-TYPE
   	SYNTAX  INTEGER
	ACCESS  read-only
	STATUS  mandatory
	DESCRIPTION "The number of times the filtering rule has been applied."
	::= { xylanFltIpServiceRuleTblEntry 8 }

xylanFltIpServiceRuleGroup OBJECT-TYPE
   	SYNTAX  DisplayString (SIZE(20))
	ACCESS  read-only
	STATUS  mandatory
	DESCRIPTION "Name of group in which the filtering rule is defined."
	::= { xylanFltIpServiceRuleTblEntry 9 }

xylanFltIpxRuleTbl OBJECT-TYPE 
	SYNTAX SEQUENCE OF FltIpxRuleTblEntry
	ACCESS not-accessible
	STATUS mandatory
	DESCRIPTION "Table of IPX filtering rules."
	::= { xylanFltActiveConfig 3 }

xylanFltIpxRuleTblEntry OBJECT-TYPE
	SYNTAX FltIpxRuleTblEntry
	ACCESS not-accessible
	STATUS mandatory
	DESCRIPTION "Entry in table of IPX filtering rules."
	INDEX { xylanFltIpxRuleType, xylanFltIpxRuleID }
	::= { xylanFltIpxRuleTbl 1 }

FltIpxRuleTblEntry ::= SEQUENCE {
	xylanFltIpxRuleType INTEGER,
	xylanFltIpxRuleID INTEGER,
	xylanFltIpxRuleNet OCTET STRING (SIZE(4)),
	xylanFltIpxRuleNode OCTET STRING (SIZE(6)),
	xylanFltIpxRuleDisp INTEGER,
	xylanFltIpxRuleCount INTEGER,
	xylanFltIpxRuleGroup DisplayString (SIZE(20))
	}

xylanFltIpxRuleType OBJECT-TYPE
	SYNTAX INTEGER {
		invalid (0),
		full-address (1),
		node (2),
		network (3),
		global (4)
	}
	ACCESS  read-only
	STATUS  mandatory
	DESCRIPTION "IPX rules are categorized into four types:
	             Full Address - both the network number and node must
	                            match for the rule to be applied
	             Node - only the node must match for the rule to be
	                    applied
	             Network - only the network number must match for the
	                       rule to be applied
                     Global - this rule type always matches
	             Full Address has the highest precedence, followed by
	             Node, Network, and then Global."
	::= { xylanFltIpxRuleTblEntry 1 }
	
xylanFltIpxRuleID OBJECT-TYPE
   	SYNTAX  INTEGER
	ACCESS  read-only
	STATUS  mandatory
	DESCRIPTION "Rule ID for filtering rule."
	::= { xylanFltIpxRuleTblEntry 2 }

xylanFltIpxRuleNet OBJECT-TYPE
        SYNTAX  OCTET STRING (SIZE(4))
	ACCESS  read-only
	STATUS  mandatory
	DESCRIPTION "Destination IPX network."
	::= { xylanFltIpxRuleTblEntry 3 }

xylanFltIpxRuleNode OBJECT-TYPE
        SYNTAX  OCTET STRING (SIZE(6))
	ACCESS  read-only
	STATUS  mandatory
	DESCRIPTION "Destination IPX node."
	::= { xylanFltIpxRuleTblEntry 4 }

xylanFltIpxRuleDisp OBJECT-TYPE
   	SYNTAX  INTEGER {
		allow (1),
		deny (2)
	}
	ACCESS  read-only
	STATUS  mandatory
	DESCRIPTION "The disposition for the filtering rule."
	::= { xylanFltIpxRuleTblEntry 5 }

xylanFltIpxRuleCount OBJECT-TYPE
   	SYNTAX  INTEGER
	ACCESS  read-only
	STATUS  mandatory
	DESCRIPTION "The number of times the filtering rule has been applied."
	::= { xylanFltIpxRuleTblEntry 6 }

xylanFltIpxRuleGroup OBJECT-TYPE
   	SYNTAX  DisplayString (SIZE(20))
	ACCESS  read-only
	STATUS  mandatory
	DESCRIPTION "Name of group in which the filtering rule is defined."
	::= { xylanFltIpxRuleTblEntry 7 }

xylanFltIpQueries OBJECT-TYPE 
	SYNTAX SEQUENCE OF FltIpQuery
	ACCESS not-accessible
	STATUS mandatory
	DESCRIPTION "IP flow result queries."
	::= { xylanFltActiveConfig 4 }

xylanFltIpQuery OBJECT-TYPE
	SYNTAX FltIpQuery
	ACCESS not-accessible
	STATUS mandatory
	DESCRIPTION "IP flow result query."
	INDEX { xylanFltIpQueryDest, xylanFltIpQuerySrc, 
	        xylanFltIpQueryPort }
	::= { xylanFltIpQueries 1 }

FltIpQuery ::= SEQUENCE {
	xylanFltIpQueryDest IpAddress,
	xylanFltIpQuerySrc IpAddress,
	xylanFltIpQueryPort INTEGER,
	xylanFltIpQueryDisp INTEGER,
	xylanFltIpQueryService DisplayString (SIZE(20)),
	xylanFltIpQueryRuleID INTEGER
	}

xylanFltIpQueryDest OBJECT-TYPE
	SYNTAX IpAddress
	ACCESS  read-only
	STATUS  mandatory
	DESCRIPTION "Destination IP address to be used in the query."
	::= { xylanFltIpQuery 1 }
	
xylanFltIpQuerySrc OBJECT-TYPE
	SYNTAX IpAddress
	ACCESS  read-only
	STATUS  mandatory
	DESCRIPTION "Source IP address to be used in the query."
	::= { xylanFltIpQuery 2 }
	
xylanFltIpQueryPort OBJECT-TYPE
	SYNTAX INTEGER (0..65535)
	ACCESS  read-only
	STATUS  mandatory
	DESCRIPTION "Destination TCP port to be used in the query.  0
	             is an indication to not use the port."
	::= { xylanFltIpQuery 3 }
	
xylanFltIpQueryDisp OBJECT-TYPE
   	SYNTAX  INTEGER {
		allow (1),
		deny (2)
	}
	ACCESS  read-only
	STATUS  mandatory
	DESCRIPTION "The disposition that results from the query."
	::= { xylanFltIpQuery 4 }

xylanFltIpQueryService OBJECT-TYPE
   	SYNTAX  DisplayString (SIZE(20))
	ACCESS  read-only
	STATUS  mandatory
	DESCRIPTION "Service that contains the rule that is applied to
	             determine the disposition of the query.  The empty
	             string indicates no rule applied."
	::= { xylanFltIpQuery 5 }

xylanFltIpQueryRuleID OBJECT-TYPE
   	SYNTAX  INTEGER
	ACCESS  read-only
	STATUS  mandatory
	DESCRIPTION "Rule ID used to determine the disposition for the 
	             query. -1 indicates no rule applied."
	::= { xylanFltIpQuery 6 }

xylanFltIpxQueries OBJECT-TYPE 
	SYNTAX SEQUENCE OF FltIpxQuery
	ACCESS not-accessible
	STATUS mandatory
	DESCRIPTION "IPX flow result queries."
	::= { xylanFltActiveConfig 5 }

xylanFltIpxQuery OBJECT-TYPE
	SYNTAX FltIpxQuery
	ACCESS not-accessible
	STATUS mandatory
	DESCRIPTION "IPX flow result query."
	INDEX { xylanFltIpxQueryNetwork, xylanFltIpxQueryNode }
	::= { xylanFltIpxQueries 1 }

FltIpxQuery ::= SEQUENCE {
	xylanFltIpxQueryNetwork OCTET STRING (SIZE(4)),
	xylanFltIpxQueryNode OCTET STRING (SIZE(6)),
	xylanFltIpxQueryDisp INTEGER,
	xylanFltIpxQueryRuleType INTEGER,
	xylanFltIpxQueryRuleID INTEGER
	}

xylanFltIpxQueryNetwork OBJECT-TYPE
        SYNTAX  OCTET STRING (SIZE(4))
	ACCESS  read-only
	STATUS  mandatory
	DESCRIPTION "Destination IPX network for query."
	::= { xylanFltIpxQuery 1 }

xylanFltIpxQueryNode OBJECT-TYPE
        SYNTAX  OCTET STRING (SIZE(6))
	ACCESS  read-only
	STATUS  mandatory
	DESCRIPTION "Destination IPX node for query."
	::= { xylanFltIpxQuery 2 }

xylanFltIpxQueryDisp OBJECT-TYPE
   	SYNTAX  INTEGER {
		allow (1),
		deny (2)
	}
	ACCESS  read-only
	STATUS  mandatory
	DESCRIPTION "The disposition that results from the query."
	::= { xylanFltIpxQuery 3 }

xylanFltIpxQueryRuleType OBJECT-TYPE
	SYNTAX INTEGER {
		no-rule-applies (0),
		full-address (1),
		node (2),
		network (3),
		global (4)
	}
	ACCESS  read-only
	STATUS  mandatory
	DESCRIPTION "IPX rules are categorized into four types:
	             Full Address - both the network number and node must
	                            match for the rule to be applied
	             Node - only the node must match for the rule to be
	                    applied
	             Network - only the network number must match for the
	                       rule to be applied
                     Global - this rule type always matches
	             Full Address has the highest precedence, followed by
	             Node, Network, and then Global."
	::= { xylanFltIpxQuery 4 }
	
xylanFltIpxQueryRuleID OBJECT-TYPE
   	SYNTAX  INTEGER
	ACCESS  read-only
	STATUS  mandatory
	DESCRIPTION "Rule ID used to determine the disposition for the 
	             query. -1 is used when no rule applied."
	::= { xylanFltIpxQuery 5 }

xylanFltActDefaultIpDisp OBJECT-TYPE
	SYNTAX INTEGER {
		allow (1),
		deny (2)
	}
	ACCESS  read-only
	STATUS  mandatory
	DESCRIPTION "The current default IP disposition if no other rule applies."
	::= { xylanFltActiveConfig 6 }

xylanFltActIpPrecedence OBJECT-TYPE
	SYNTAX INTEGER {
		destination (1),
		source (2)
	}
	ACCESS  read-only
	STATUS  mandatory
	DESCRIPTION "The current precedence for IP rules."
	::= { xylanFltActiveConfig 7 }

xylanFltActDefaultIpxDisp OBJECT-TYPE
	SYNTAX INTEGER {
		allow (1),
		deny (2)
	}
	ACCESS  read-only
	STATUS  mandatory
	DESCRIPTION "The current default IPX disposition if no other rule applies."
	::= { xylanFltActiveConfig 8 }

xylanFltIpTrapInfo     OBJECT IDENTIFIER ::= { xylanFltTraps 1 }

xylanFltLastIpDenySrc OBJECT-TYPE
	SYNTAX  IpAddress
	ACCESS  read-only
	STATUS  mandatory
	DESCRIPTION "Source IP address for last denied route by HRE-X 
	             Filtering."
	::= { xylanFltIpTrapInfo 1 }

xylanFltLastIpDenyDest OBJECT-TYPE
	SYNTAX  IpAddress
	ACCESS  read-only
	STATUS  mandatory
	DESCRIPTION "Destination IP address for last denied route by HRE-X
	             Filtering."
	::= { xylanFltIpTrapInfo 2 }

xylanFltLastIpDenyPort OBJECT-TYPE
	SYNTAX  INTEGER
	ACCESS  read-only
	STATUS  mandatory
	DESCRIPTION "Destination IP address for last denied route by HRE-X
	             Filtering."
	::= { xylanFltIpTrapInfo 3 }

xylanFltIpxTrapInfo    OBJECT IDENTIFIER ::= { xylanFltTraps 2 }

xylanFltLastIpxDenyNet OBJECT-TYPE
        SYNTAX  OCTET STRING (SIZE(4))
	ACCESS  read-only
	STATUS  mandatory
	DESCRIPTION "Destination IPX network for last denied route by HRE-X
	             Filtering."
	::= { xylanFltIpxTrapInfo 1 }

xylanFltLastIpxDenyNode OBJECT-TYPE
        SYNTAX  OCTET STRING (SIZE(6))
	ACCESS  read-only
	STATUS  mandatory
	DESCRIPTION "Destination IPX node for last denied route by HRE-X
	             Filtering."
	::= { xylanFltIpxTrapInfo 2 }

xylanFltCommitTrapInfo OBJECT IDENTIFIER ::= { xylanFltTraps 3 }

xylanFltLastCommitTrapReason OBJECT-TYPE
        SYNTAX  INTEGER {
		no-trap-sent (0),
		service-not-found (1),
		group-not-found (2),
		ipx-in-non-global-group (3),
		port-in-two-services (4),
		duplicate-service-names (5),
		same-ipx-address-for-two-rules (6)
	}
	ACCESS  read-only
	STATUS  mandatory
	DESCRIPTION "The reason for the last HRE-X Filtering COMMIT trap; 
                     the valid reasons are:
	               0 - No trap has been sent.
	               1 - A service that was referenced from the global 
                           configuration could not be found.
	               2 - A group that was referenced from the GLOBAL
	                   level or some other service could not be found.
	               3 - An IPX rule was found in a group assigned to a
	                   service rather than the GLOBAL level.
	               4 - The same port was assigned to two services.
                       5 - The same service name appears twice.
	               6 - The same IPX address has two rules associated with
	                   it."
	::= { xylanFltCommitTrapInfo 1 }

xylanFltLastCommitTrapEntity1 OBJECT-TYPE
   	SYNTAX  DisplayString (SIZE(20))
	ACCESS  read-only
	STATUS  mandatory
	DESCRIPTION "An entity associated with the last HRE-X Filtering 
                     COMMIT trap; the value depends on the value of the last 
	             xylanFltLastCommitTrapReason.  These are:
	               0 - The data is invalid.
	               1 - The name of the service that was referenced.
	               2 - The name of the service that referenced the group.
	               3 - The name of the service that contained the IPX rule.
	               4 - The name of the first service to include the port.
                           This service will retain the port.
	               5 - The service name that appears twice.
	               6 - The name of the group that contains the second
	                   rule for the same IPX address."
	::= { xylanFltCommitTrapInfo 2 }

xylanFltLastCommitTrapEntity2 OBJECT-TYPE
   	SYNTAX  DisplayString (SIZE(20))
	ACCESS  read-only
	STATUS  optional
	DESCRIPTION "An entity associated with the last HRE-X Filtering 
                     COMMIT trap; the value depends on the value of the last 
	             xylanFltLastCommitTrapReason.  These are:
	               0 - The data is invalid.
	               1 - This data item is unused.
	               2 - The name of the group that could not be found.
	               3 - The name of the group that contained the IPX rule.
	               4 - The name of the second service to include the port.
                           This service will not retain the port.
	               5 - This data item is unused.
	               6 - The name of the group that contains the first rule
	                   for an IPX address for which there is a duplicate."
	::= { xylanFltCommitTrapInfo 3 }

xylanFltLastCommitTrapPort OBJECT-TYPE
   	SYNTAX  INTEGER
	ACCESS  read-only
	STATUS  optional
	DESCRIPTION "The port number associated with the last HRE-X Filtering
                     COMMIT trap; the value depends on the value of the last 
	             xylanFltLastCommitTrapReason.  These are:
	               0 - The data is invalid.
	               1 - This data item is unused.
	               2 - This data item is unused.
	               3 - This data item is unused.
	               4 - The port that was assigned to two services.
	               5 - This data item is unused.
	               6 - This data item is unused."
	::= { xylanFltCommitTrapInfo 4 }

xylanFltLastCommitTrapIpxNet OBJECT-TYPE
        SYNTAX  OCTET STRING (SIZE(4))
	ACCESS  read-only
	STATUS  optional
	DESCRIPTION "Destination IPX network for last HRE-X Filtering COMMIT
	             trap; the value depends on the value of the last 
	             xylanFltLastCommitTrapReason.  These are:
	               0 - The data is invalid.
	               1 - This data item is unused.
	               2 - This data item is unused.
	               3 - This data item is unused.
	               4 - This data item is unused.
	               5 - This data item is unused.
	               6 - Contains the IPX network number for which there
 	                   was a duplicate rule."
	::= { xylanFltCommitTrapInfo 5 }

xylanFltLastCommitTrapIpxNode OBJECT-TYPE
        SYNTAX  OCTET STRING (SIZE(6))
	ACCESS  read-only
	STATUS  optional
	DESCRIPTION "Destination IPX node for last HRE-X Filtering COMMIT
	             trap; the value depends on the value of the last 
	             xylanFltLastCommitTrapReason.  These are:
	               0 - The data is invalid.
	               1 - This data item is unused.
	               2 - This data item is unused.
	               3 - This data item is unused.
	               4 - This data item is unused.
	               5 - This data item is unused.
	               6 - Contains the IPX node address for which there
 	                   was a duplicate rule."
	::= { xylanFltCommitTrapInfo 6 }

END
