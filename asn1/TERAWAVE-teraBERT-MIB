TERAWAVE-teraBERT-MIB DEFINITIONS ::= BEGIN
        -- Created by sml2mib compiler 
        IMPORTS

 enterprises,  OBJECT-TYPE,  Counter,  Gauge,  TimeTicks
        FROM RFC1155-SMI
		  Gauge32 FROM SNMPv2-SMI;

terawave OBJECT IDENTIFIER ::=  { enterprises 4513 }

teraBERTGroup OBJECT IDENTIFIER ::=  { terawave 16 }

     -- teraBERTConfigureTable

teraBERTConfigureTable OBJECT-TYPE
     SYNTAX SEQUENCE OF TeraBERTConfigureTableEntryType
     ACCESS not-accessible
     STATUS mandatory
     DESCRIPTION
          " table teraBERTConfigureTable"
     ::= { teraBERTGroup 1 }

teraBERTConfigureTableEntry OBJECT-TYPE
          SYNTAX TeraBERTConfigureTableEntryType
          ACCESS not-accessible
          STATUS mandatory
          DESCRIPTION
               " table entry teraBERTConfigureTableEntry "
          INDEX {                   ifIndex }
     ::= { teraBERTConfigureTable 1 }

TeraBERTConfigureTableEntryType ::= SEQUENCE {
          teraBERTCommand   
             INTEGER,
          teraBERTTestTime   
             INTEGER (0..86400),
          teraBERTSynThreshold   
             INTEGER (0..65535),
          teraBERTSESThresholdMantissa   
             INTEGER (1..9),
          teraBERTSESThresholdExponent   
             INTEGER (1..9),
          teraBERTSynStatus   
             INTEGER,
          teraBERTElapsedTime   
             INTEGER,
          teraBERTPattern   
             INTEGER
}

teraBERTCommand OBJECT-TYPE
          SYNTAX INTEGER
                  {
                  none(0),
                  start(1),
                  stop(2),
                  clear(3),
                  insert-err(4),
                  timer(5)
                  }
          ACCESS read-write
          STATUS mandatory
          DESCRIPTION
               ""
          ::= { teraBERTConfigureTableEntry 1 }

teraBERTTestTime OBJECT-TYPE
          SYNTAX INTEGER (0..86400)
          ACCESS read-write
          STATUS mandatory
          DESCRIPTION
               ""
          ::= { teraBERTConfigureTableEntry 2 }

teraBERTSynThreshold OBJECT-TYPE
          SYNTAX INTEGER (0..65535)
          ACCESS read-write
          STATUS mandatory
          DESCRIPTION
               ""
          ::= { teraBERTConfigureTableEntry 3 }

teraBERTSESThresholdMantissa OBJECT-TYPE
          SYNTAX INTEGER (1..9)
          ACCESS read-write
          STATUS mandatory
          DESCRIPTION
               ""
          ::= { teraBERTConfigureTableEntry 4 }

teraBERTSESThresholdExponent OBJECT-TYPE
          SYNTAX INTEGER (1..9)
          ACCESS read-write
          STATUS mandatory
          DESCRIPTION
               ""
          ::= { teraBERTConfigureTableEntry 5 }

teraBERTSynStatus OBJECT-TYPE
          SYNTAX INTEGER
                  {
                  yes(0),
                  no(1)
                  }
          ACCESS read-only
          STATUS mandatory
          DESCRIPTION
               ""
          ::= { teraBERTConfigureTableEntry 6 }

teraBERTElapsedTime OBJECT-TYPE
          SYNTAX INTEGER
          ACCESS read-only
          STATUS mandatory
          DESCRIPTION
               ""
          ::= { teraBERTConfigureTableEntry 7 }

teraBERTPattern OBJECT-TYPE
          SYNTAX INTEGER
                  {
                  none(0),
                  twoE11MinusOne(1),
                  twoE15MinusOne(2),
                  twoE20MinusOne(3),
                  twoE23MinusOne(4),
                  allOnes(5),
                  allZeroes(6),
                  alternatingOneZero(7)
                  }
          ACCESS read-write
          STATUS mandatory
          DESCRIPTION
               ""
          ::= { teraBERTConfigureTableEntry 8 }

     -- teraBERTCurrentTable

teraBERTCurrentTable OBJECT-TYPE
     SYNTAX SEQUENCE OF TeraBERTCurrentTableEntryType
     ACCESS not-accessible
     STATUS mandatory
     DESCRIPTION
          " table teraBERTCurrentTable"
     ::= { teraBERTGroup 2 }

teraBERTCurrentTableEntry OBJECT-TYPE
          SYNTAX TeraBERTCurrentTableEntryType
          ACCESS not-accessible
          STATUS mandatory
          DESCRIPTION
               " table entry teraBERTCurrentTableEntry "
          INDEX {                   ifIndex }
     ::= { teraBERTCurrentTable 1 }

TeraBERTCurrentTableEntryType ::= SEQUENCE {
          teraBERTCurrentCountInSync   
             Gauge32,
          teraBERTCurrentRateInSync   
             Gauge32,
          teraBERTCurrentESCount   
             Gauge32,
          teraBERTCurrentSESCount   
             Gauge32,
          teraBERTCurrentCSESCount   
             Gauge32,
          teraBERTCurrentUASCount   
             Gauge32
}

teraBERTCurrentCountInSync OBJECT-TYPE
          SYNTAX Gauge32
          ACCESS read-only
          STATUS mandatory
          DESCRIPTION
               ""
          ::= { teraBERTCurrentTableEntry 1 }

teraBERTCurrentRateInSync OBJECT-TYPE
          SYNTAX Gauge32
          ACCESS read-only
          STATUS mandatory
          DESCRIPTION
               ""
          ::= { teraBERTCurrentTableEntry 2 }

teraBERTCurrentESCount OBJECT-TYPE
          SYNTAX Gauge32
          ACCESS read-only
          STATUS mandatory
          DESCRIPTION
               ""
          ::= { teraBERTCurrentTableEntry 3 }

teraBERTCurrentSESCount OBJECT-TYPE
          SYNTAX Gauge32
          ACCESS read-only
          STATUS mandatory
          DESCRIPTION
               ""
          ::= { teraBERTCurrentTableEntry 4 }

teraBERTCurrentCSESCount OBJECT-TYPE
          SYNTAX Gauge32
          ACCESS read-only
          STATUS mandatory
          DESCRIPTION
               ""
          ::= { teraBERTCurrentTableEntry 5 }

teraBERTCurrentUASCount OBJECT-TYPE
          SYNTAX Gauge32
          ACCESS read-only
          STATUS mandatory
          DESCRIPTION
               ""
          ::= { teraBERTCurrentTableEntry 6 }

END
