--
-- The Efficient Networks Enterprise MIB definition:
--

EFFICIENT-MIB DEFINITIONS ::= BEGIN

IMPORTS 
	OBJECT-TYPE FROM RFC1155-SMI
		MacAddress
				FROM BRIDGE-MIB
        enterprises, IpAddress
                FROM RFC1155-SMI
		Gauge32 FROM SNMPv2-SMI
        DisplayString
                FROM SNMPv2-TC;

efficient OBJECT IDENTIFIER ::= { enterprises  763 }

-- Below "efficient" are the namespace definitions for the various
-- products and the actual products' MIBs.  Note that the "product"
-- subtree is intended to contain product-specific managed objects.
-- MIB extensions that may be defined for a particular product
-- should be placed in the "mib-extensions" subtree.

product OBJECT IDENTIFIER ::= { efficient  1 }
mib-extensions OBJECT IDENTIFIER ::= { efficient  2 }
xMIB OBJECT IDENTIFIER ::= { efficient 3 }

-- The 5010 modem:
modem5010 OBJECT IDENTIFIER ::= { product  5010 }

-- The 5010 modem has does bridging or routing:
bridge OBJECT IDENTIFIER ::= { modem5010  1 }
router OBJECT IDENTIFIER ::= { modem5010  2 }

-- The router has two versions, ATU-R and ATU-C:
atu-R OBJECT IDENTIFIER ::= { router  1 }
atu-C OBJECT IDENTIFIER ::= { router  2 }

-- The 5621 modem:
modem5621 OBJECT IDENTIFIER ::= { product  5621 }

-- The 8600 IAD:
iad8600 OBJECT IDENTIFIER ::= { product  8600 }

-- Product specific mib-extensions
mibRouter5660 OBJECT IDENTIFIER ::= { mib-extensions  1 }
mibIad8600    OBJECT IDENTIFIER ::= { mib-extensions  2 }

 -- This is the 8600 IAD Groups
iad8600Info    OBJECT IDENTIFIER ::= { mibIad8600 1 }
iad8600Voice   OBJECT IDENTIFIER ::= { mibIad8600 2 }
iad8600Data    OBJECT IDENTIFIER ::= { mibIad8600 3 }
iad8600Wan     OBJECT IDENTIFIER ::= { mibIad8600 4 }
iad8600System  OBJECT IDENTIFIER ::= { mibIad8600 5 }

-- These are the 8600 IAD Configuration sub-groups
iad8600SystemCommunity OBJECT IDENTIFIER ::= { iad8600System 1 }
iad8600SystemTrapDest  OBJECT IDENTIFIER ::= { iad8600System 2 }
iad8600DataPppAuth     OBJECT IDENTIFIER ::= { iad8600Data 1 }

-- Start of description of SNMP configurable objects

iad8600SystemGetCommunityString OBJECT-TYPE
   SYNTAX   DisplayString
   ACCESS   read-write
   STATUS   mandatory
   DESCRIPTION
    "Community string for read only view of mib objects."
   ::= { iad8600SystemCommunity 1 }

--iad8600SystemSetCommunityString OBJECT-TYPE
   --SYNTAX   DisplayString
   --ACCESS   read-write
   --STATUS   mandatory
   --DESCRIPTION
    --"Community string for read-write view of mib objects."
   --::= { iad8600SystemCommunity 2 }

-- Trap Destination Configuration Objects

--iad8600SystemTrapTable OBJECT-TYPE
   --SYNTAX  SEQUENCE OF iad8600SystemTrapEntry
   --ACCESS  not-accessible
   --STATUS  mandatory
   --DESCRIPTION
       --"A list of Trap Desination Address Configuration Parameters."
   --::= { iad8600SystemTrapDest 1 }
--
--iad8600SystemTrapEntry OBJECT-TYPE
   --SYNTAX  TrapEntry
   --ACCESS  not-accessible
   --STATUS  mandatory
   --DESCRIPTION
       --"Trap Configuration Address parameter table entry keys."
   --INDEX { destAddr }
   --::= { iad8600SystemTrapTable 1 }
-- 
--iad8600SystemTrapEntry ::= SEQUENCE
    --{
        --iad8600SystemTrapDestAddr            IpAddress
    --}
--
  --iad8600SystemTrapDestAddr  OBJECT-TYPE
    --SYNTAX   IpAddress
    --ACCESS   read-write
    --STATUS   mandatory
    --DESCRIPTION
     --"IP address of a Network Management entity
     --that traps will be sent to."
    --DEFVAL { 0 }
    --::= { iad8600SystemTrapEntry 1 }
--

  iad8600SystemTrapDestAddr1  OBJECT-TYPE
    SYNTAX   IpAddress
    ACCESS   read-write
    STATUS   mandatory
    DESCRIPTION
     "IP address of the First Network Management entity that 
      traps will be sent to."
    DEFVAL { 0 }
    ::= { iad8600SystemTrapDest 1 }

  iad8600SystemTrapDestAddr2  OBJECT-TYPE
    SYNTAX   IpAddress
    ACCESS   read-write
    STATUS   mandatory
    DESCRIPTION
     "IP address of the Second Network Management entity that 
      traps will be sent to."
    DEFVAL { 0 }
    ::= { iad8600SystemTrapDest 2 }

  iad8600SystemTrapDestAddr3  OBJECT-TYPE
    SYNTAX   IpAddress
    ACCESS   read-write
    STATUS   mandatory
    DESCRIPTION
     "IP address of the Third Network Management entity that 
      traps will be sent to."
    DEFVAL { 0 }
    ::= { iad8600SystemTrapDest 3 }

  iad8600SystemTrapDestAddr4  OBJECT-TYPE
    SYNTAX   IpAddress
    ACCESS   read-write
    STATUS   mandatory
    DESCRIPTION
     "IP address of the Fourth Network Management entity that 
      traps will be sent to."
    DEFVAL { 0 }
    ::= { iad8600SystemTrapDest 4 }

-- Start of description of PPP Authenication configurable objects

  iad8600DataPppAuthUsername OBJECT-TYPE
    SYNTAX   DisplayString
    ACCESS   read-write
    STATUS   mandatory
    DESCRIPTION
     "PPP Authentication username."
    ::= { iad8600DataPppAuth 1 }

  iad8600DataPppAuthPassword OBJECT-TYPE
    SYNTAX   DisplayString
    ACCESS   read-write
    STATUS   mandatory
    DESCRIPTION
     "PPP Authenication password."
    ::= { iad8600DataPppAuth 2 }

-- *************************
-- Project X MIB Definitions
-- *************************

modem OBJECT IDENTIFIER ::= { xMIB 1 }
adsl  OBJECT IDENTIFIER ::= { xMIB 2 }
atm   OBJECT IDENTIFIER ::= { xMIB 3 }
ppp   OBJECT IDENTIFIER ::= { xMIB 4 }
pppoe OBJECT IDENTIFIER ::= { ppp 4 }
nvram OBJECT IDENTIFIER ::= { xMIB 5 }
nvsys OBJECT IDENTIFIER ::= { nvram 1 }
nvatm OBJECT IDENTIFIER ::= { nvram 2 }
nvwlan OBJECT IDENTIFIER ::= { nvram 3 }
nvsntp OBJECT IDENTIFIER ::= { nvram 4 } 

--
-- Modem Objects
--

modemClearCounters OBJECT-TYPE
    SYNTAX INTEGER
    MAX-ACCESS read-write
    STATUS current
    DESCRIPTION
        "Clear counters."
    ::= { modem 1 }

modemPartNumber OBJECT-TYPE
    SYNTAX DisplayString
    MAX-ACCESS read-only
    STATUS current
    DESCRIPTION
        "Part number"
    ::= { modem 2 }

modemConfigPartNumber OBJECT-TYPE
    SYNTAX DisplayString
    MAX-ACCESS read-only
    STATUS current
    DESCRIPTION
        "Configuration part number"
    ::= { modem 3 }

modemBuildNumber OBJECT-TYPE
    SYNTAX DisplayString
    MAX-ACCESS read-only
    STATUS current
    DESCRIPTION
        "Build number"
    ::= { modem 4 }

modemFirmwareVersion1 OBJECT-TYPE
    SYNTAX DisplayString
    MAX-ACCESS read-only
    STATUS current
    DESCRIPTION
        "First Firmware version entry"
    ::= { modem 5 }

modemFirmwareVersion2 OBJECT-TYPE
    SYNTAX DisplayString
    MAX-ACCESS read-only
    STATUS current
    DESCRIPTION
        "Second Firmware version entry"
    ::= { modem 6 }

modemFirmwareVersion3 OBJECT-TYPE
    SYNTAX DisplayString
    MAX-ACCESS read-only
    STATUS current
    DESCRIPTION
        "Third Firmware version entry"
    ::= { modem 7 }
    
modemReboot OBJECT-TYPE
    SYNTAX INTEGER {
    	 save (0),
	 reboot (1)
    }
    ACCESS write-only
    STATUS current
    DESCRIPTION
        "Reboot the modem.
	0 - save the nvram
	1 - reboot the modem"
    ::= { modem 8 }       

modemIsBridge OBJECT-TYPE
    SYNTAX INTEGER{
         bridge (1),
	     rtr    (2),
	     brtr   (3)
    }
    MAX-ACCESS read-only
    STATUS current
    DESCRIPTION
        "Is modem a bridge 
	 1 - bridge  
	 2 - rtr 
	 3 - brtr."
    ::= { modem 9 }           

modemNVRAMVersion OBJECT-TYPE
    SYNTAX OCTET STRING (SIZE (1))
    MAX-ACCESS read-only
    STATUS current
    DESCRIPTION
        "NVRAM version."
    ::= { modem 10 }          

modemMacAddress OBJECT-TYPE
    SYNTAX MacAddress	
    MAX-ACCESS read-only
    STATUS current
    DESCRIPTION
        "LAN MAC address."
    ::= { modem 11 }       

modemLANIpAddress OBJECT-TYPE
    SYNTAX IpAddress
    MAX-ACCESS read-write
    STATUS current
    DESCRIPTION
        "LAN IP address."
    ::= { modem 12 }           	

modemLANMask OBJECT-TYPE
    SYNTAX IpAddress
    MAX-ACCESS read-write
    STATUS current
    DESCRIPTION
        "LAN Subnet mask."
    ::= { modem 13 }
        
--
-- Extended ADSL Information
--
adslTrainedPath OBJECT-TYPE
    SYNTAX DisplayString
    MAX-ACCESS read-only
    STATUS current
    DESCRIPTION
        "Undefined,
	     No channel,
	     Fast,
	     Interleaved,
	     Fast or Interleaved,
	     Fast and Interleaved"
    ::= { adsl 1 }

adslTrainedMode OBJECT-TYPE
    SYNTAX DisplayString
    MAX-ACCESS read-only
    STATUS current
    DESCRIPTION
        "None, 
	     Multi, 
	     ANSI, 
	     DMT, 
	     G.lite"
    ::= { adsl 2 }

--
-- Extended ATM VCL Information
--

atmVcl2-Table OBJECT-TYPE
    SYNTAX SEQUENCE OF AtmVclEntry2
    ACCESS not-accessible
    STATUS mandatory
    DESCRIPTION
        "An extension to the atmVclTable."
    ::= { atm 1 }

atmVclEntry2 OBJECT-TYPE
    SYNTAX AtmVclEntry2
    ACCESS not-accessible
    STATUS mandatory
    DESCRIPTION
        "An entry in the extension VCL Table."
    INDEX { ifIndex, ifIndex, ifIndex }
    ::= { atmVcl2-Table 1 }

AtmVclEntry2 ::=
    SEQUENCE {
        atmVcl2Vpi INTEGER,
        atmVcl2Vci INTEGER,
        atmVcl2Protocol INTEGER,
        atmVcl2RxRate Gauge32,
        atmVcl2TxRate Gauge32,
        atmVcl2TxPDUs Gauge32,
        atmVcl2RxPDUs Gauge32,
        atmVcl2TxErrs Gauge32,
        atmVcl2RxErrs Gauge32,
	    atmVcl2PCR    INTEGER,
	    atmVcl2SCR    INTEGER,
	    atmVcl2RxSdu  INTEGER,
	    atmVcl2TxSdu  INTEGER
    }

atmVcl2Vpi OBJECT-TYPE
    SYNTAX INTEGER (0..4095)
    ACCESS not-accessible
    STATUS optional
    DESCRIPTION
        "The VPI value of the VCL.  The maximum VPI value
        cannot exceed the value allowable by the
        atmInterfaceMaxVpiBits."
    ::= { atmVclEntry2 1 }

atmVcl2Vci OBJECT-TYPE
    SYNTAX INTEGER (0..65535)
    ACCESS not-accessible
    STATUS optional
    DESCRIPTION
        "The VCI value of the VCL.  The maximum VCI value
        cannot exceed the value allowable by the
        atmInterfaceMaxVciBits."
    ::= { atmVclEntry2 2 }
    
atmVcl2Protocol OBJECT-TYPE
    SYNTAX INTEGER {
        none(0),
        bridged1483(1),
        pppoavcmux(2),
        pppoallc(4),
        pppoe(8),
        routed1483(2048)
    }
    MAX-ACCESS read-only
    STATUS current
    DESCRIPTION
        "Indicates the VCL encapsulated protocol type."
    ::= { atmVclEntry2 3 }

atmVcl2RxRate OBJECT-TYPE
    SYNTAX Gauge32
    UNITS "bps"
    MAX-ACCESS read-only
    STATUS current
    DESCRIPTION
        "Receive rate."
    ::= { atmVclEntry2 4 }

atmVcl2TxRate OBJECT-TYPE
    SYNTAX Gauge32
    UNITS "bps"
    MAX-ACCESS read-only
    STATUS current
    DESCRIPTION
        "Transmit rate."
    ::= { atmVclEntry2 5 }

atmVcl2TxPDUs OBJECT-TYPE
    SYNTAX Gauge32
    UNITS "PDUs"
    MAX-ACCESS read-only
    STATUS current
    DESCRIPTION
        "Transmitted PDUs."
    ::= { atmVclEntry2 6 }

atmVcl2RxPDUs OBJECT-TYPE
    SYNTAX Gauge32
    UNITS "PDUs"
    MAX-ACCESS read-only
    STATUS current
    DESCRIPTION
        "Received PDUs."
    ::= { atmVclEntry2 7 }

atmVcl2TxErrs OBJECT-TYPE
    SYNTAX Gauge32
    UNITS "PDUs"
    MAX-ACCESS read-only
    STATUS current
    DESCRIPTION
        "Transmit Errors."
    ::= { atmVclEntry2 8 }    

atmVcl2RxErrs OBJECT-TYPE
    SYNTAX Gauge32
    UNITS "PDUs"
    MAX-ACCESS read-only
    STATUS current
    DESCRIPTION
        "Receive Errors."
    ::= { atmVclEntry2 9 }    

atmVcl2PCR OBJECT-TYPE
    SYNTAX INTEGER
    MAX-ACCESS read-write
    STATUS current
    DESCRIPTION
        "Peak Cell Rate."
    ::= { atmVclEntry2 10 }    

atmVcl2SCR OBJECT-TYPE
    SYNTAX INTEGER
    MAX-ACCESS read-only
    STATUS current
    DESCRIPTION
        "Sustained Cell Rate."
    ::= { atmVclEntry2 11 }    

atmVcl2RxSdu OBJECT-TYPE
    SYNTAX INTEGER
    MAX-ACCESS read-only
    STATUS current
    DESCRIPTION
        "Rx SDU Size."
    ::= { atmVclEntry2 12 }    

atmVcl2TxSdu OBJECT-TYPE
    SYNTAX INTEGER
    MAX-ACCESS read-only
    STATUS current
    DESCRIPTION
        "Tx SDU Size."
    ::= { atmVclEntry2 13 }
        

--
-- PPP Information
--
pppConnect OBJECT-TYPE
    SYNTAX INTEGER
    ACCESS write-only
    STATUS current
    DESCRIPTION
        "WAN connect."
    ::= { ppp 1 }

pppDisconnect OBJECT-TYPE
    SYNTAX INTEGER
    ACCESS write-only
    STATUS current
    DESCRIPTION
        "WAN disconnect."
    ::= { ppp 2 }

pppTable  OBJECT-TYPE
    SYNTAX SEQUENCE OF PppEntry
    ACCESS not-accessible
    STATUS mandatory
    DESCRIPTION
        "A list of PPP related parameters."
    ::= { ppp 3 }

pppEntry  OBJECT-TYPE
    SYNTAX PppEntry
    ACCESS not-accessible
    STATUS mandatory
    DESCRIPTION
        "An interface entry containing PPP states."
    INDEX { ifIndex }
    ::= { pppTable 1 }

PppEntry ::=
    SEQUENCE {
    	pppLCPState	    	DisplayString,
		pppIPCPState 	    DisplayString,
    	pppAUTHState 	    DisplayString,
		pppLCPOldState      DisplayString,
		pppIPCPOldState     DisplayString,
		pppAUTHOldState     DisplayString,
		pppConnect          INTEGER
    }

pppLCPState OBJECT-TYPE
    SYNTAX DisplayString
    MAX-ACCESS read-only
    STATUS current
    DESCRIPTION
        "Current state of LCP."
    ::= { pppEntry 1 }

pppIPCPState OBJECT-TYPE
    SYNTAX DisplayString
    MAX-ACCESS read-only
    STATUS current
    DESCRIPTION
        "Current state of IPCP."
    ::= { pppEntry 2 }

pppAUTHState OBJECT-TYPE
    SYNTAX DisplayString
    MAX-ACCESS read-only
    STATUS current
    DESCRIPTION
        "Current state of AUTH."
    ::= { pppEntry 3 }

pppLCPOldState OBJECT-TYPE
    SYNTAX DisplayString
    MAX-ACCESS read-only
    STATUS current
    DESCRIPTION
        "Prior state of LCP."
    ::= { pppEntry 4 }

pppIPCPOldState OBJECT-TYPE
    SYNTAX DisplayString
    MAX-ACCESS read-only
    STATUS current
    DESCRIPTION
        "Prior state of IPCP."
    ::= { pppEntry 5 }

pppAUTHOldState OBJECT-TYPE
    SYNTAX DisplayString
    MAX-ACCESS read-only
    STATUS current
    DESCRIPTION
        "prior state of AUTH."
    ::= { pppEntry 6 }

      
--
-- PPPoE Information
--
pppoeTable  OBJECT-TYPE
    SYNTAX SEQUENCE OF PppoeEntry
    ACCESS not-accessible
    STATUS mandatory
    DESCRIPTION
        "A list of PPPoE related parameters."
    ::= { pppoe 1 }

pppoeEntry  OBJECT-TYPE
    SYNTAX PppoeEntry
    ACCESS not-accessible
    STATUS mandatory
    DESCRIPTION
        "An interface entry containing negotiated PPPoE parameters."
    INDEX { ifIndex }
    ::= { pppoeTable 1 }

PppoeEntry ::=
    SEQUENCE {
        pppoeAccessConcentratorName DisplayString,
        pppoeServiceName DisplayString
    }

pppoeAccessConcentratorName OBJECT-TYPE
    SYNTAX DisplayString
    MAX-ACCESS read-only
    STATUS current
    DESCRIPTION
        "Name of the attached access concentrator."
    ::= { pppoeEntry 1 }

pppoeServiceName OBJECT-TYPE
    SYNTAX DisplayString
    MAX-ACCESS read-only
    STATUS current
    DESCRIPTION
        "Name of the connected service."
    ::= { pppoeEntry 2 }

--
-- nvram configuration objects
--


--
-- atmvcc objects
--


nvatmVccTable  OBJECT-TYPE
    SYNTAX SEQUENCE OF NvatmVccEntry
    ACCESS not-accessible
    STATUS mandatory
    DESCRIPTION
        "A list of PPP related parameters."
    ::= { nvatm 1 }

nvatmVccEntry  OBJECT-TYPE
    SYNTAX NvatmVccEntry
    ACCESS not-accessible
    STATUS mandatory
    DESCRIPTION
        "NVRAM configuration for ATM."
    INDEX { vccIndex }
    ::= { nvatmVccTable 1 }

NvatmVccEntry ::=
    SEQUENCE {  
       vccIndex    INTEGER,
       nvatmVccVpi INTEGER,
       nvatmVccVci INTEGER,
       nvatmVccAalType INTEGER,
       nvatmVccEncType INTEGER                    
    }
       
vccIndex OBJECT-TYPE
    SYNTAX INTEGER (0..7)
    ACCESS not-accessible
    STATUS current
    DESCRIPTION
        " "
    ::= { nvatmVccEntry 1 }
	
nvatmVccVpi OBJECT-TYPE
    SYNTAX INTEGER (0..4095)
    ACCESS read-write
    STATUS optional
    DESCRIPTION
        "The VPI value of the VCL.  The maximum VPI value
        cannot exceed the value allowable by the
        atmInterfaceMaxVpiBits."
    ::= { nvatmVccEntry 2 }

nvatmVccVci OBJECT-TYPE
    SYNTAX INTEGER (0..65535)
    ACCESS read-write
    STATUS optional
    DESCRIPTION
        "The VCI value of the VCL.  The maximum VCI value
        cannot exceed the value allowable by the
        atmInterfaceMaxVciBits."
    ::= { nvatmVccEntry 3 }

nvatmVccAalType OBJECT-TYPE
    SYNTAX      INTEGER (1..5)
    MAX-ACCESS    read-write
    STATUS        current
    DESCRIPTION
    "An instance of this object only exists when the
    local VCL end-point is also the VCC end-point,
    and AAL is in use.
    The type of AAL used on this VCC."
    ::= { nvatmVccEntry 4 }

nvatmVccEncType OBJECT-TYPE
    SYNTAX      INTEGER { 
                 llc(1), 
                 vcm(2)} 
    MAX-ACCESS    read-write
    STATUS        current
    DESCRIPTION
    "Encapsulation type."
    ::= { nvatmVccEntry 5 }

nvatmVccPoeTable  OBJECT-TYPE
    SYNTAX SEQUENCE OF NvatmVccPoeEntry
    ACCESS not-accessible
    STATUS mandatory
    DESCRIPTION
        "A list of PPPoe related configs."
    ::= { nvatm 2 }

nvatmVccPoeEntry  OBJECT-TYPE
    SYNTAX NvatmVccPoeEntry
    ACCESS not-accessible
    STATUS mandatory
    DESCRIPTION
        "NVRAM configuration for ATM."
    INDEX { vccIndex, poeIndex }
    ::= { nvatmVccPoeTable 1 }

NvatmVccPoeEntry ::=
    SEQUENCE {
       vccIndex       INTEGER,
       poeIndex       INTEGER,
       pppUsrUsername DisplayString,
       pppUsrPassword DisplayString                 
    }
         
vccIndex2 OBJECT-TYPE
    SYNTAX INTEGER (0..7)
    ACCESS not-accessible
    STATUS current
   
    ::= { nvatmVccPoeEntry 1 }
    
poeIndex OBJECT-TYPE
    SYNTAX INTEGER (0..4)
    ACCESS not-accessible
    STATUS current
    
    ::= { nvatmVccPoeEntry 2 }

pppUsrUsername OBJECT-TYPE
    SYNTAX DisplayString
    MAX-ACCESS read-write
    STATUS current
    DESCRIPTION
        "Username for the pppoe session."
    ::= { nvatmVccPoeEntry 3 }
 
pppUsrPassword OBJECT-TYPE
    SYNTAX DisplayString
    MAX-ACCESS read-write
    STATUS current
    DESCRIPTION
        "Password for the pppoe session."
    ::= { nvatmVccPoeEntry 4 }
    
--
-- Wireless Configuration
--

nvwlanMacAddress OBJECT-TYPE
    SYNTAX  MacAddress
    MAX-ACCESS read-write
    STATUS current
    DESCRIPTION
        "Mac address for the Wireless LAN card"
    ::= { nvwlan 1 }

nvwlanChannel OBJECT-TYPE
	SYNTAX INTEGER    
    MAX-ACCESS read-write
    STATUS current
    DESCRIPTION
    	"Channel number"
    ::= { nvwlan 2 }
    
nvwlanSsid OBJECT-TYPE
    SYNTAX OCTET STRING
    MAX-ACCESS read-write
    STATUS current
    DESCRIPTION
    	"SSID"
    ::= { nvwlan 3 }
    
nvwlanSecurity OBJECT-TYPE
	SYNTAX INTEGER { 
	        off(0), 
	        w64(1), 
	        w128(2), 
	        wpa(3) }
	MAX-ACCESS read-write
    STATUS current
    DESCRIPTION
    	"Type of security employed
    	 0 - off
    	 1 - w64
    	 2 - w128
    	 3 - wpa."        
    ::= { nvwlan 4 }
    
nvwlanKey OBJECT-TYPE
    SYNTAX INTEGER (1..4)
    MAX-ACCESS read-write
    STATUS current
    DESCRIPTION
    	"Encryption Key to use"    
    ::= { nvwlan 5 }
    
nvwlanK64-1 OBJECT-TYPE
	SYNTAX  OCTET STRING
    MAX-ACCESS read-write
    STATUS current
    DESCRIPTION
    	"64 bit encryption key 1"	
	::= { nvwlan 6 }
	        
nvwlanK64-2 OBJECT-TYPE
	SYNTAX  OCTET STRING
    MAX-ACCESS read-write
    STATUS current
    DESCRIPTION
    	"64 bit encryption key 2"	
	::= { nvwlan 7 } 
	
nvwlanK64-3 OBJECT-TYPE
	SYNTAX OCTET STRING
    MAX-ACCESS read-write
    STATUS current
    DESCRIPTION
    	"64 bit encryption key 3"	
	::= { nvwlan 8 }
	
nvwlanK64-4 OBJECT-TYPE
	SYNTAX  OCTET STRING
    MAX-ACCESS read-write
    STATUS current
    DESCRIPTION
    	"64 bit encryption key 4"	
	::= { nvwlan 9 }
    	
nvwlanK128 OBJECT-TYPE
	SYNTAX  OCTET STRING
    MAX-ACCESS read-write
    STATUS current
    DESCRIPTION
    	"128 bit encryption key"	
	::= { nvwlan 10 }

nvwlanWpaAlgorithm OBJECT-TYPE
	SYNTAX INTEGER { 
	       tkip(0), 
	       aes(1) }
    MAX-ACCESS read-write
    STATUS current
    DESCRIPTION
    	"WPA algorithm
    	 0 - tkip
    	 1 - aes."	
	::= { nvwlan 11 }

nvwlanWpaKey OBJECT-TYPE
	SYNTAX OCTET STRING 
    MAX-ACCESS read-write
    STATUS current
    DESCRIPTION
    	"wpa key"	
	::= { nvwlan 12 }
          
nvwlanWpaRenewal OBJECT-TYPE
	SYNTAX INTEGER
	UNITS "seconds" 
    MAX-ACCESS read-write
    STATUS current
    DESCRIPTION
    	"WPA key renewal time"	
	::= { nvwlan 13 }

nvwlanRate OBJECT-TYPE
	SYNTAX INTEGER {
		auto(0),
		r54(1),
		r48(2),
		r36(3),
		r24(4),
		r18(5),
		r12(6),
		r11(7),
		 r9(8),
		 r5(9),
		 r2(10),
		 r1(11)}
    MAX-ACCESS read-write
    STATUS current
    DESCRIPTION
    	"Data Rate"
	::= { nvwlan 14 }

nvwlanRts OBJECT-TYPE
	SYNTAX INTEGER
    MAX-ACCESS read-write
    STATUS current
    DESCRIPTION
    	"rts-cts-threshold"	
	::= { nvwlan 15 }

nvwlanFragmentation OBJECT-TYPE
	SYNTAX INTEGER
    MAX-ACCESS read-write
    STATUS current
    DESCRIPTION
    	"Fragmentation threshold "	
    ::= { nvwlan 16 }

nvwlanLocale OBJECT-TYPE
	SYNTAX INTEGER
    MAX-ACCESS read-write
    STATUS current
    DESCRIPTION
    	"Locale descriptor"	
    ::= { nvwlan 17 }	   
    
nvwlanEnableFilters OBJECT-TYPE
	SYNTAX INTEGER {
	    off(0),
	    on(1)
	    }
    MAX-ACCESS read-write
    STATUS current
    DESCRIPTION
    	"Enable filtering"
    ::= { nvwlan 18 }
    
nvwlanFilterIsDeny OBJECT-TYPE
	SYNTAX INTEGER {
	    off(0),
	    on(1)
	    }
    MAX-ACCESS read-write
    STATUS current
    DESCRIPTION
    	"Filter type"                 
    ::= { nvwlan 19 }
    
nvwlanDisableSsidBroadcast OBJECT-TYPE
	SYNTAX INTEGER {
	    disable(0),
	    enable(1)
	    }
    MAX-ACCESS read-write
    STATUS current
    DESCRIPTION
    	"Disable the SSID broadcast"
    ::= { nvwlan 20 }
        
nvwlanDisabled OBJECT-TYPE
	SYNTAX INTEGER {
	    disable(0),
	    enable(1)
	    }
    MAX-ACCESS read-write
    STATUS current
    DESCRIPTION
    	"Disable the wlan interface"
	::= { nvwlan 21 }
	
nvwlanSharedKeyAuth OBJECT-TYPE
	SYNTAX INTEGER {
	    off(0),
	    on(1)
	    }
    MAX-ACCESS read-write
    STATUS current
    DESCRIPTION
    	"Shared Key Authorization"    
    ::= { nvwlan 22 }
    
nvwlanInitialSetup OBJECT-TYPE
	SYNTAX INTEGER {
	    off(0),
	    on(1)
	    }
    MAX-ACCESS read-write
    STATUS current
    DESCRIPTION
    	"Initial Setup
    	 - I have no idea what this is "    
    ::= { nvwlan 23 }

--filtIndex OBJECT IDENTIFIER
--    SYNTAX INTEGER (0..19)

nvwlanFiltTable  OBJECT-TYPE
    SYNTAX SEQUENCE OF NvwlanFiltEntry
    ACCESS not-accessible
    STATUS mandatory
    DESCRIPTION
        "A list of PPP related parameters."
    ::= { nvwlan 24 }

nvwlanFiltEntry  OBJECT-TYPE
    SYNTAX NvwlanFiltEntry
    ACCESS not-accessible
    STATUS mandatory
    DESCRIPTION
        "NVRAM configuration for ATM."
    INDEX { filtIndex }
    ::= { nvwlanFiltTable 1 }

NvwlanFiltEntry ::=
    SEQUENCE {  
       filtIndex    INTEGER,
       nvwlanFiltUsername DisplayString,
       nvwlanFiltMac  MacAddress                   
    }
       
filtIndex OBJECT-TYPE
    SYNTAX INTEGER (0..19)
    ACCESS not-accessible
    STATUS current
    DESCRIPTION
        "Filter Number Index."
    ::= { nvwlanFiltEntry 1 }

nvwlanFiltUsername OBJECT-TYPE
    SYNTAX DisplayString
    ACCESS read-write
    STATUS current
    DESCRIPTION
        "Filter Usernames."
    ::= { nvwlanFiltEntry 2 }
    
nvwlanFiltMac OBJECT-TYPE
	SYNTAX MacAddress
	ACCESS read-write
	STATUS current
	DESCRIPTION
		"Filter MAC address"
	::= { nvwlanFiltEntry 3 }	        


-- 
-- sntp configuration
--

nvSntpPrimaryServer OBJECT-TYPE
    SYNTAX DisplayString
    ACCESS read-write
    STATUS current
    DESCRIPTION
        "SNTP primary server"
    ::= { nvsntp 1 }

nvSntpBackupServer OBJECT-TYPE
    SYNTAX DisplayString
    ACCESS read-write
    STATUS current
    DESCRIPTION
        "SNTP backup server "
    ::= { nvsntp 2 }
                  
nvSntpTimezone OBJECT-TYPE
	SYNTAX INTEGER 
    MAX-ACCESS read-write
    STATUS current
    DESCRIPTION
    	"Timezone plus or minus hours 
    	 from UTC "    
    ::= { nvsntp 3 }
	                   
END
