CXDial-MIB DEFINITIONS ::= BEGIN

--#CURRENT_VERSION 1

IMPORTS
   OBJECT-TYPE FROM RFC-1212
   cxDial, Alias   
            FROM CXProduct-SMI;

cxDialTable OBJECT-TYPE
   SYNTAX   SEQUENCE  OF CxDialEntry
   ACCESS   not-accessible
   STATUS   mandatory
   DESCRIPTION
"Table containing configuration information about dial functionality. This 
table acts as a focal point to configure the dial capability. Each protocol 
providing dial incorporates an object which point to one row of this table."
   ::= { cxDial 1 }

   cxDialEntry OBJECT-TYPE
      SYNTAX   CxDialEntry
      ACCESS   not-accessible
      STATUS   mandatory
      DESCRIPTION
        "This row holds all the parameters related to the dial functionality."
      INDEX { cxDialEntryIndex }
      ::= { cxDialTable 1 }

   CxDialEntry ::= SEQUENCE
   {
      cxDialEntryIndex              
INTEGER,
      cxDialPhysicalType            INTEGER,
      
cxDialFunctionType            INTEGER,
      cxDialRowStatus               
INTEGER,
      cxDialInactivityTimer         INTEGER,
      
cxDialBackupPollingTimer      INTEGER,
cxDialDelayTimer        INTEGER,
      cxDialIsdnBcmUSapAlias        
Alias,
      cxDialIsdnBcmNbrOfBChannels   INTEGER,
      
cxDialIsdnBcmDirectoryId      INTEGER
   }

   cxDialEntryIndex OBJECT-TYPE
      SYNTAX   INTEGER
      ACCESS   read-only
      STATUS   mandatory
      DESCRIPTION

"Local table index. Used to manage this table and by application implementing 
dial functions."
      ::= { cxDialEntry 1 }

   cxDialPhysicalType OBJECT-TYPE
      SYNTAX   INTEGER {
               dtr (1),
               isdn (2)
            }
      
ACCESS   read-write
      STATUS   mandatory
      DESCRIPTION
"Determines how the dial function is physically supported.

Options:
dtr (1): Data Terminal Ready

isdn (2): ISDN
                 
Default Value: dtr (1)

Configuration Changed: administrative "

      DEFVAL { dtr }
      ::= { cxDialEntry 2 }

   
cxDialFunctionType OBJECT-TYPE
      SYNTAX   INTEGER {
                onDemand (1),
                onCongestion (2)
            }
      ACCESS   read-write
      STATUS   mandatory
      DESCRIPTION
"Determines when the dial function is used.

Options:
onDemand (1): used on demand

onCongestion (2): not currently used
           
   
   
Default Value: onDemand (1)

Configuration Changed: administrative"

      DEFVAL { onDemand }
      ::= { cxDialEntry 3 }


   cxDialRowStatus OBJECT-TYPE
      SYNTAX   INTEGER {
 
              invalid (1),
               valid    (2)
            }
      
ACCESS   read-write
      STATUS   mandatory
      DESCRIPTION
"Determines whether this dial function is to be removed from service 
(i.e. invalidated) within the Dial software layer.

Options:
invalid (1): row is flagged; after next reset values will be disabled and row 
will be deleted from table

valid (2): values are enabled

Default Value: valid (2)

Configuration Changed: administrative "
      DEFVAL { valid }
      ::= { cxDialEntry 6 }

   
cxDialInactivityTimer    OBJECT-TYPE
      SYNTAX  INTEGER (0..65535)
     
 ACCESS  read-write
      STATUS  mandatory
      DESCRIPTION
"Determines the time in seconds that can pass before a SAP providing dial 
access drops its connection due to inactivity.

Range of Values: 0 - 65,535

Default Value: 20

Configuration Changed: administrative "
          DEFVAL {20 }
          ::= { cxDialEntry 10 }

   cxDialBackupPollingTimer             OBJECT-TYPE
     
 SYNTAX  INTEGER (0..65535)
      ACCESS  read-write
      STATUS  mandatory
      DESCRIPTION
"Determines the interval in seconds that the Frame Relay software layer will 
wait before polling and terminating connections of dial backup ports when 
primary route partners related to these ports have become active.

Range of Values: 0 - 65,535

Default Value: 0

Configuration Changed: administrative "

          DEFVAL {0 }
          ::= { cxDialEntry 11 }

   cxDialDelayTimer             OBJECT-TYPE
     
 SYNTAX  INTEGER (0..65535)
      ACCESS  read-write
      STATUS  mandatory
      DESCRIPTION
"Determines the number of seconds that the Frame Relay software layer 
waits before requesting the lower layer to bring up the dialup line.

Range of Values: 0 - 65,535

Default Value: 0

Configuration Changed: operative "

          DEFVAL {0 }
	  --#STARTING_VERSION 1
          ::= { cxDialEntry 12 }

   cxDialIsdnBcmUSapAlias OBJECT-TYPE
      SYNTAX   Alias
      ACCESS   read-write
      STATUS   mandatory
      DESCRIPTION
"Determines the textual name uniquely identifying this upper SAP. This object 
is meaningful only if 'cxDialPhysicalType' is set to 'isdn'.

Range of Values: 0-16 alphanumeric characters beginning with a letter 

Default Value: none

Configuration Changed: administrative "

      DEFVAL { "" }
      ::= { cxDialEntry 15 }

   
cxDialIsdnBcmNbrOfBChannels OBJECT-TYPE
      SYNTAX   INTEGER
      ACCESS   read-write
      STATUS   mandatory
      DESCRIPTION
"Determines the number of ISDN B channels that have dial funtionality.
This object is meaningful only if 'cxDialPhysicalType' is set to 'isdn'.

Range of Values: 1-2 (locked at 1)

Default Value: 1

Configuration Changed:  administrative "

      DEFVAL { 1 }
      ::= { cxDialEntry 16 }

   cxDialIsdnBcmDirectoryId OBJECT-TYPE
 
     SYNTAX   INTEGER
      ACCESS   read-write
      STATUS   mandatory
  
DESCRIPTION
"Determines the ISDN access point having dial funtionality. This object is 
meaningful only if 'cxDialPhysicalType' is set to 'isdn'.

Range of Values: 1-40

Default Value: 1

Configuration Changed: administrative "
      DEFVAL { 1 }
      ::= { cxDialEntry 17 }

cxDialMibLevel OBJECT-TYPE
	SYNTAX	INTEGER
	ACCESS	read-only
	STATUS	mandatory
	DESCRIPTION
"Used to determine current MIB module release supported
by the agent. Object is in decimal."
	DEFVAL { 0 }
	--#STARTING_VERSION 1
	::= { cxDial 2 }

END
