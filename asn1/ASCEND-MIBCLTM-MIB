--			Ascend mibcltm MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBCLTM-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibcltmCmd  OBJECT IDENTIFIER ::= { configuration 66}

	-- The mibcltmCmd table
	--
	-- This table contains parameters for the mibcltmCmd profile
	--

    mibcltmCmdTable	OBJECT-TYPE
	SYNTAX		SEQUENCE OF MibcltmCmdEntry
	ACCESS		not-accessible
	STATUS		mandatory
	DESCRIPTION	"A list of mibcltmCmd profile entries."
	::= { mibcltmCmd 1 }

    mibcltmCmdEntry	OBJECT-TYPE
	SYNTAX		MibcltmCmdEntry
	ACCESS		not-accessible
	STATUS		mandatory
	DESCRIPTION	"A mibcltmCmd entry containing objects that
			 maps to the parameters of mibcltmCmd profile."
	INDEX		{ cltmCmd-Index-o }
	::= { mibcltmCmdTable 1 }

    MibcltmCmdEntry ::=
	SEQUENCE {
	    cltmCmd-Index-o
		INTEGER,
	    cltmCmd-CltmSlot
		INTEGER,
	    cltmCmd-TestTimeStamp
		INTEGER,
	    cltmCmd-TestSequence
		INTEGER,
	    cltmCmd-TestOperation
		INTEGER,
	    cltmCmd-DmmType
		INTEGER,
	    cltmCmd-DmmLead
		INTEGER,
	    cltmCmd-BackgroundNoiseFilter
		INTEGER,
	    cltmCmd-BackgroundNoiseTermination
		INTEGER,
	    cltmCmd-LoopResistanceUnit
		INTEGER,
	    cltmCmd-LoopResistanceTemp
		INTEGER,
	    cltmCmd-ImpulseNoiseStartThresh
		INTEGER,
	    cltmCmd-ImpulseNoiseStartDelta
		INTEGER,
	    cltmCmd-ImpulseNoiseStartMaxCount
		INTEGER,
	    cltmCmd-ImpulseNoiseStartDeadTime
		INTEGER,
	    cltmCmd-ImpulseNoiseStartTimer
		INTEGER,
	    cltmCmd-CalibrationType
		INTEGER,
	    cltmCmd-ToneSendFreq
		INTEGER,
	    cltmCmd-ToneSendLevel
		INTEGER,
	    cltmCmd-ToneSendPeriod
		INTEGER,
	    cltmCmd-TdrUnit
		INTEGER,
	    cltmCmd-TdrGauge
		INTEGER,
	    cltmCmd-TdrVp
		INTEGER,
	    cltmCmd-TdrAvg
		INTEGER,
	    cltmCmd-TdrGetType
		INTEGER,
	    cltmCmd-TdrStartDistance
		INTEGER,
	    cltmCmd-TdrMeasurementLength
		INTEGER,
	    cltmCmd-DmmdcdPeriod
		INTEGER,
	    cltmCmd-DmmdcdVoltage
		INTEGER,
	    cltmCmd-DmmdcdImpedance
		INTEGER,
	    cltmCmd-DmmcapPeriod
		INTEGER,
	    cltmCmd-DmmallType
		INTEGER,
	    cltmCmd-DmmallPeriod
		INTEGER,
	    cltmCmd-DmmallInputImp
		INTEGER,
	    cltmCmd-CtoneType
		INTEGER,
	    cltmCmd-CtoneTone
		INTEGER,
	    cltmCmd-TtoneLead
		INTEGER,
	    cltmCmd-TtoneLevel
		INTEGER,
	    cltmCmd-TtonePeriod
		INTEGER,
	    cltmCmd-BtapStartLength
		INTEGER,
	    cltmCmd-BtapMeasureLength
		INTEGER,
	    cltmCmd-FcllocUnit
		INTEGER,
	    cltmCmd-FcllocGauge
		INTEGER,
	    cltmCmd-ShortlocUnit
		INTEGER,
	    cltmCmd-ShortlocGauge
		INTEGER,
	    cltmCmd-ShortlocType
		INTEGER,
	    cltmCmd-Action-o
		INTEGER
	}

    cltmCmd-Index-o	OBJECT-TYPE
	SYNTAX	INTEGER
	ACCESS	read-only
	STATUS	mandatory
	DESCRIPTION	""
	::= { mibcltmCmdEntry 1 }

    cltmCmd-CltmSlot	OBJECT-TYPE
	SYNTAX	INTEGER {
		    anySlot (1),
		    slot1 (2),
		    slot2 (3),
		    slot3 (4),
		    slot4 (5),
		    slot5 (6),
		    slot6 (7),
		    slot7 (8),
		    slot10 (11),
		    slot11 (12),
		    slot12 (13),
		    slot13 (14),
		    slot14 (15),
		    slot15 (16),
		    slot16 (17)
		}
	ACCESS	read-only
	STATUS	mandatory
	DESCRIPTION	"Identify the CLTM slot within the system."
	::= { mibcltmCmdEntry 2 }

    cltmCmd-TestTimeStamp	OBJECT-TYPE
	SYNTAX	INTEGER
	ACCESS	read-only
	STATUS	mandatory
	DESCRIPTION	"Value of the sysUpTime when the last test command was issued. This parameter is cleared when any of the test parameters are changed."
	::= { mibcltmCmdEntry 3 }

    cltmCmd-TestSequence	OBJECT-TYPE
	SYNTAX	INTEGER
	ACCESS	read-only
	STATUS	mandatory
	DESCRIPTION	"Sequence of the last issued test command."
	::= { mibcltmCmdEntry 4 }

    cltmCmd-TestOperation	OBJECT-TYPE
	SYNTAX	INTEGER {
		    none (1),
		    dmmTest (2),
		    lineInlsTest (3),
		    lineBgnsTest (4),
		    lineSignsTest (5),
		    lineLpresTest (6),
		    lineCldetTest (7),
		    lineImpstartTest (8),
		    lineImpstopTest (9),
		    lineImpreadTest (10),
		    calibTest (11),
		    toneSend (12),
		    toneRecv (13),
		    tdrSet (14),
		    tdrGet (15),
		    cltmReset (16),
		    cltmVersion (17),
		    cltmDownload (18),
		    dmmDcdelTest (19),
		    dmmCapeTest (20),
		    dmmAllTest (21),
		    txCtrlToneTest (22),
		    txTraceToneTest (23),
		    stopToneTest (24),
		    detRingerTest (25),
		    detAturTest (26),
		    btapTest (27),
		    voiceDetTest (28),
		    lineFcllocTest (29),
		    lineShortlocTest (30),
		    setResponderTest (31),
		    setBypassTest (32),
		    splitterDetectTest (33),
		    dmmAcdelTest (34),
		    dmmLbalTest (35),
		    dmmSoakTest (36),
		    sendVoiceTest (37),
		    measVoiceTest (38),
		    measDtaTest (39),
		    detaptorTest (40)
		}
	ACCESS	read-write
	STATUS	mandatory
	DESCRIPTION	"The current operation that is active on the CLT Module. Defaultls to 'none'. Set to 'none' to stop the test procedure."
	::= { mibcltmCmdEntry 5 }

    cltmCmd-DmmType	OBJECT-TYPE
	SYNTAX	INTEGER {
		    resistance (1),
		    dcVoltage (2),
		    acVoltage (3),
		    capacitance (4)
		}
	ACCESS	read-write
	STATUS	mandatory
	DESCRIPTION	"DMM Measurement Type."
	::= { mibcltmCmdEntry 6 }

    cltmCmd-DmmLead	OBJECT-TYPE
	SYNTAX	INTEGER {
		    tipRing (1),
		    tipSleeve (2),
		    ringSleeve (3)
		}
	ACCESS	read-write
	STATUS	mandatory
	DESCRIPTION	"DMM Measurement Leads."
	::= { mibcltmCmdEntry 7 }

    cltmCmd-BackgroundNoiseFilter	OBJECT-TYPE
	SYNTAX	INTEGER {
		    psd (1),
		    e (2),
		    f (3),
		    g (4)
		}
	ACCESS	read-write
	STATUS	mandatory
	DESCRIPTION	"Line Filter Type for Background Noise Test."
	::= { mibcltmCmdEntry 8 }

    cltmCmd-BackgroundNoiseTermination	OBJECT-TYPE
	SYNTAX	INTEGER {
		    term100 (1),
		    term135 (2),
		    bridge100 (3),
		    bridge135 (4)
		}
	ACCESS	read-write
	STATUS	mandatory
	DESCRIPTION	"Line Termination Type for Background Noise Test."
	::= { mibcltmCmdEntry 9 }

    cltmCmd-LoopResistanceUnit	OBJECT-TYPE
	SYNTAX	INTEGER {
		    metric (1),
		    english (2)
		}
	ACCESS	read-write
	STATUS	mandatory
	DESCRIPTION	"Measurement System for Loop Resistance Test."
	::= { mibcltmCmdEntry 10 }

    cltmCmd-LoopResistanceTemp	OBJECT-TYPE
	SYNTAX	INTEGER
	ACCESS	read-write
	STATUS	mandatory
	DESCRIPTION	"Line Temperature for Loop Resistance Test. Assigned in degree celsius/fahrenheit."
	::= { mibcltmCmdEntry 11 }

    cltmCmd-ImpulseNoiseStartThresh	OBJECT-TYPE
	SYNTAX	INTEGER
	ACCESS	read-write
	STATUS	mandatory
	DESCRIPTION	"Threshold for Impulse Noise Test. The Range is 50-100 dBrm."
	::= { mibcltmCmdEntry 12 }

    cltmCmd-ImpulseNoiseStartDelta	OBJECT-TYPE
	SYNTAX	INTEGER
	ACCESS	read-write
	STATUS	mandatory
	DESCRIPTION	"Delta Value for Impulse Noise Test. The delta range is 2-6 dB"
	::= { mibcltmCmdEntry 13 }

    cltmCmd-ImpulseNoiseStartMaxCount	OBJECT-TYPE
	SYNTAX	INTEGER
	ACCESS	read-write
	STATUS	mandatory
	DESCRIPTION	"Max Count for Impulse Noise Test. The range of the value is 1-1999."
	::= { mibcltmCmdEntry 14 }

    cltmCmd-ImpulseNoiseStartDeadTime	OBJECT-TYPE
	SYNTAX	INTEGER
	ACCESS	read-write
	STATUS	mandatory
	DESCRIPTION	"Dead Time Value for Impulse Noise Start Test. The value is assigned in 0.1 ms increments."
	::= { mibcltmCmdEntry 15 }

    cltmCmd-ImpulseNoiseStartTimer	OBJECT-TYPE
	SYNTAX	INTEGER
	ACCESS	read-write
	STATUS	mandatory
	DESCRIPTION	"Timer values for Impulse Noise Start Test. The value is assigned in 1 minute increment."
	::= { mibcltmCmdEntry 16 }

    cltmCmd-CalibrationType	OBJECT-TYPE
	SYNTAX	INTEGER {
		    insertionLoss (1),
		    backgroundNoise (2)
		}
	ACCESS	read-write
	STATUS	mandatory
	DESCRIPTION	"Calibration Type"
	::= { mibcltmCmdEntry 17 }

    cltmCmd-ToneSendFreq	OBJECT-TYPE
	SYNTAX	INTEGER
	ACCESS	read-write
	STATUS	mandatory
	DESCRIPTION	"Tone Send Frequency in KHz."
	::= { mibcltmCmdEntry 18 }

    cltmCmd-ToneSendLevel	OBJECT-TYPE
	SYNTAX	INTEGER
	ACCESS	read-write
	STATUS	mandatory
	DESCRIPTION	"Tone Send Level in dBm."
	::= { mibcltmCmdEntry 19 }

    cltmCmd-ToneSendPeriod	OBJECT-TYPE
	SYNTAX	INTEGER
	ACCESS	read-write
	STATUS	mandatory
	DESCRIPTION	"Amount of time a tone is sent (1-20 Minutes)."
	::= { mibcltmCmdEntry 20 }

    cltmCmd-TdrUnit	OBJECT-TYPE
	SYNTAX	INTEGER {
		    metric (1),
		    english (2)
		}
	ACCESS	read-write
	STATUS	mandatory
	DESCRIPTION	"Measurement System for TDR Test."
	::= { mibcltmCmdEntry 21 }

    cltmCmd-TdrGauge	OBJECT-TYPE
	SYNTAX	INTEGER
	ACCESS	read-write
	STATUS	mandatory
	DESCRIPTION	"TDR gauge. This is either 22/24/26 AWG for English system or 6/5/4 (0.1mm) for the metric system."
	::= { mibcltmCmdEntry 22 }

    cltmCmd-TdrVp	OBJECT-TYPE
	SYNTAX	INTEGER
	ACCESS	read-write
	STATUS	mandatory
	DESCRIPTION	"TDR VP as percentage of the speed of light."
	::= { mibcltmCmdEntry 23 }

    cltmCmd-TdrAvg	OBJECT-TYPE
	SYNTAX	INTEGER
	ACCESS	read-write
	STATUS	mandatory
	DESCRIPTION	"Number of trials to get the avarage."
	::= { mibcltmCmdEntry 24 }

    cltmCmd-TdrGetType	OBJECT-TYPE
	SYNTAX	INTEGER {
		    automatic (1),
		    manual (2)
		}
	ACCESS	read-write
	STATUS	mandatory
	DESCRIPTION	"TDR Test Range Measurement Type. If set to automatic cltmCmdTdrStartLen and cltmCmdTdrMeasureLen do not need to be set."
	::= { mibcltmCmdEntry 25 }

    cltmCmd-TdrStartDistance	OBJECT-TYPE
	SYNTAX	INTEGER
	ACCESS	read-write
	STATUS	mandatory
	DESCRIPTION	"TDR Start Length for MANUAL mode, the value is given in feet (15..20000) for the English system and cm (460..609750) for the metric system."
	::= { mibcltmCmdEntry 26 }

    cltmCmd-TdrMeasurementLength	OBJECT-TYPE
	SYNTAX	INTEGER
	ACCESS	read-write
	STATUS	mandatory
	DESCRIPTION	"TDR Measurement Length for MANUAL mode, the value is given in feet (300..20000) for the English system and cm (9150..609750) for the metric system."
	::= { mibcltmCmdEntry 27 }

    cltmCmd-DmmdcdPeriod	OBJECT-TYPE
	SYNTAX	INTEGER
	ACCESS	read-write
	STATUS	mandatory
	DESCRIPTION	"Amount of time measurement is made (0,1-5 100ms;0=MAX)."
	::= { mibcltmCmdEntry 28 }

    cltmCmd-DmmdcdVoltage	OBJECT-TYPE
	SYNTAX	INTEGER
	ACCESS	read-write
	STATUS	mandatory
	DESCRIPTION	"Test voltage to be used (-230 to 230 Volts)."
	::= { mibcltmCmdEntry 29 }

    cltmCmd-DmmdcdImpedance	OBJECT-TYPE
	SYNTAX	INTEGER
	ACCESS	read-write
	STATUS	mandatory
	DESCRIPTION	"Output Impedance to be used (10 to 1000 Kohms)."
	::= { mibcltmCmdEntry 30 }

    cltmCmd-DmmcapPeriod	OBJECT-TYPE
	SYNTAX	INTEGER
	ACCESS	read-write
	STATUS	mandatory
	DESCRIPTION	"Amount of time measurement is made (0,1-5 100ms;0=MAX)."
	::= { mibcltmCmdEntry 31 }

    cltmCmd-DmmallType	OBJECT-TYPE
	SYNTAX	INTEGER {
		    resistance (1),
		    dcVoltage (2),
		    acVoltage (3),
		    capacitance (4)
		}
	ACCESS	read-write
	STATUS	mandatory
	DESCRIPTION	"DMM Measurement Type."
	::= { mibcltmCmdEntry 32 }

    cltmCmd-DmmallPeriod	OBJECT-TYPE
	SYNTAX	INTEGER
	ACCESS	read-write
	STATUS	mandatory
	DESCRIPTION	"Amount of time measurement is made (0,1-5 100ms;0=MAX)."
	::= { mibcltmCmdEntry 33 }

    cltmCmd-DmmallInputImp	OBJECT-TYPE
	SYNTAX	INTEGER
	ACCESS	read-write
	STATUS	mandatory
	DESCRIPTION	"Input Impedance (100, 1000 Kohm)."
	::= { mibcltmCmdEntry 34 }

    cltmCmd-CtoneType	OBJECT-TYPE
	SYNTAX	INTEGER {
		    adsl (1),
		    glite (2)
		}
	ACCESS	read-write
	STATUS	mandatory
	DESCRIPTION	"Control tone, type of DSL service (ADSL, GLITE)."
	::= { mibcltmCmdEntry 35 }

    cltmCmd-CtoneTone	OBJECT-TYPE
	SYNTAX	INTEGER {
		    quiet (1),
		    restore (2)
		}
	ACCESS	read-write
	STATUS	mandatory
	DESCRIPTION	"Control tone, type of Tone (QUIET, RESTORE)."
	::= { mibcltmCmdEntry 36 }

    cltmCmd-TtoneLead	OBJECT-TYPE
	SYNTAX	INTEGER {
		    tipRing (1),
		    tipSleeve (2),
		    ringSleeve (3)
		}
	ACCESS	read-write
	STATUS	mandatory
	DESCRIPTION	"trace tone, Measurement Leads."
	::= { mibcltmCmdEntry 37 }

    cltmCmd-TtoneLevel	OBJECT-TYPE
	SYNTAX	INTEGER
	ACCESS	read-write
	STATUS	mandatory
	DESCRIPTION	"trace tone, Tone Send Level in dBm."
	::= { mibcltmCmdEntry 38 }

    cltmCmd-TtonePeriod	OBJECT-TYPE
	SYNTAX	INTEGER
	ACCESS	read-write
	STATUS	mandatory
	DESCRIPTION	"trace tone, Amount of time a tone is sent (1-20 Minutes)."
	::= { mibcltmCmdEntry 39 }

    cltmCmd-BtapStartLength	OBJECT-TYPE
	SYNTAX	INTEGER
	ACCESS	read-write
	STATUS	mandatory
	DESCRIPTION	"Measurement start length (15 - 20000 ft. or 5 - 6097 meter)."
	::= { mibcltmCmdEntry 40 }

    cltmCmd-BtapMeasureLength	OBJECT-TYPE
	SYNTAX	INTEGER
	ACCESS	read-write
	STATUS	mandatory
	DESCRIPTION	"Measurement length (100 - 20000 ft. or 32 - 6097 meter)."
	::= { mibcltmCmdEntry 41 }

    cltmCmd-FcllocUnit	OBJECT-TYPE
	SYNTAX	INTEGER {
		    metric (1),
		    english (2)
		}
	ACCESS	read-write
	STATUS	mandatory
	DESCRIPTION	"Measurement System for FCLLOC Test."
	::= { mibcltmCmdEntry 43 }

    cltmCmd-FcllocGauge	OBJECT-TYPE
	SYNTAX	INTEGER
	ACCESS	read-write
	STATUS	mandatory
	DESCRIPTION	"FCLLOC gauge. This is either 22/24/26 AWG for English system or 6/5/4 (0.1mm) for the metric system."
	::= { mibcltmCmdEntry 44 }

    cltmCmd-ShortlocUnit	OBJECT-TYPE
	SYNTAX	INTEGER {
		    metric (1),
		    english (2)
		}
	ACCESS	read-write
	STATUS	mandatory
	DESCRIPTION	"Measurement System for SHORTLOC Test."
	::= { mibcltmCmdEntry 45 }

    cltmCmd-ShortlocGauge	OBJECT-TYPE
	SYNTAX	INTEGER
	ACCESS	read-write
	STATUS	mandatory
	DESCRIPTION	"SHORTLOC gauge. This is either 22/24/26 AWG for English system or 6/5/4 (0.1mm) for the metric system."
	::= { mibcltmCmdEntry 46 }

    cltmCmd-ShortlocType	OBJECT-TYPE
	SYNTAX	INTEGER {
		    detect (1),
		    noDetect (2)
		}
	ACCESS	read-write
	STATUS	mandatory
	DESCRIPTION	"SHORTLOC test type."
	::= { mibcltmCmdEntry 47 }

    cltmCmd-Action-o	OBJECT-TYPE
	SYNTAX	INTEGER {
		    noAction (1),
		    createProfile (2),
		    deleteProfile (3)
		}
	ACCESS	read-write
	STATUS	mandatory
	DESCRIPTION	""
	::= { mibcltmCmdEntry 42 }

END
