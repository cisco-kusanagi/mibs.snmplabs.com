PAIRGAIN-SDSL-MIB

-- PairGain SDSL MIB Release 1.1
-- Revision Date:  09/01/1999
--
-- Copyright 1999 PairGain Technologies, Inc.  All Rights
-- Reserved.  Reproduction of this document is authorized on
-- condition that the foregoing copyright notice is included.
-- This PairGain SNMP Management Information Base Specification
-- (Specification) embodies PairGain's confidential and
-- proprietary intellectual property.  PairGain retains all
-- title and ownership in the Specification, including any
-- revisions.
--
-- It is PairGain's intent to encourage the widespread use of
-- this Specification in connection with the management of
-- PairGain products. PairGain grants vendors, end-users,
-- and other interested parties a non-exclusive license to
-- use this Specification in connection with the management
-- of PairGain products.
--
-- This Specification is supplied "AS IS," and PairGain makes
-- no warranty, either expressed or implied, as to the use,
-- operation, condition, or performance of the Specification.
--
-- Revision History
--------------------------------------------------------------
-- Date            Ver     Programmer  Description
--------------------------------------------------------------
-- 06/24/1999      1.0     R. Wada     Initial Checkin
-- 09/01/1999	   1.1     R. Wada     Add support for in-band
--									   proxy modem statistics
-- 10/07/1999      1.1a    R. Wada     Modified for HPOV compatibility.

DEFINITIONS ::= BEGIN

-- SECTION 1: Top Level Definitions

IMPORTS
    Counter32, Integer32, MODULE-IDENTITY, OBJECT-TYPE, NOTIFICATION-TYPE
        FROM SNMPv2-SMI
    OBJECT-TYPE
        FROM RFC-1212
    pgainSDSL
        FROM PAIRGAIN-COMMON-HD-MIB
    ifIndex
        FROM RFC1213-MIB
    DisplayString, RowStatus, TruthValue
		FROM SNMPv2-TC;


-- Module Identity SDSL (required for SNMP v2)
pgsdslMIB MODULE-IDENTITY
    LAST-UPDATED    "9910070000Z"
    ORGANIZATION    "Pairgain Technologies Inc."
        CONTACT-INFO    "
                    14402 Franklin Avenue
                    Tustin, CA  92780
                    "
    DESCRIPTION "The module defines the SDSL MIB "
    ::= {pgainSDSL 1}

sdslMibObjects        OBJECT IDENTIFIER ::= { pgsdslMIB 1 }

-- Define a one byte integer
    Byte ::= INTEGER (0..255)

-- Define a two bytes integer
    Short ::= INTEGER (0..65535)

    SdslLineProfileType ::= INTEGER (0..65535)


-- Define a time stamp structure. The time stamp consists of 8 bytes,
-- with the following format :
--     byte 1    : reserved
--     bytes 2,3 : four digit year for y2k compliance,
--     byte 4    : month of year,
--     byte 5    : day of month,
--     byte 6    : hour (24 hour format)
--     byte 7    : minutes
--     byte 8    : seconds


    PgSdslTimeStamp ::= OCTET STRING (SIZE(8))

    PgSdslAlarmSeverityMode ::=
       INTEGER {
               disable(1),
               enable(2),
               notAvailable(3)
       }



    ----------------------------------------------------
    -- SDSL 15-minute Performance History
    ----------------------------------------------------
    sdsl15mPerformanceTable  OBJECT-TYPE
        SYNTAX      SEQUENCE OF Sdsl15mPerformanceEntry
        MAX-ACCESS  not-accessible
        STATUS      current
        DESCRIPTION
            "This table provides the 15-minute performance history monitoring
             of the last 24 hours for all SDSL Errored Seconds (ES),
             and Unavailable Seconds (UAS)."
        ::= {sdslMibObjects 1}

    sdsl15mPerformanceEntry  OBJECT-TYPE
        SYNTAX      Sdsl15mPerformanceEntry
        MAX-ACCESS  not-accessible
        STATUS      current
        DESCRIPTION
            "Entries of the SDSL 15-min performance table.  All 96 entries for a
            24 hour period are zeroed out and available at power up.  Not all
            of the returned values are legitimate until the appropriate amount of time
            has elapsed."
        INDEX       {ifIndex, sdsl15mHistoryId}
        ::= {sdsl15mPerformanceTable 1}

    Sdsl15mPerformanceEntry ::= SEQUENCE {
        sdsl15mHistoryId
                Short,
        sdsl15mESNet
                Short,
        sdsl15mUASNet
                Short,
        sdsl15mESCust
                Short,
        sdsl15mUASCust
                Short
        }


    sdsl15mHistoryId  OBJECT-TYPE
        SYNTAX      Short
        MAX-ACCESS  read-only
        STATUS      current
        DESCRIPTION
            "Identifies the history ID within the 96 15-minute performance
             history.
            "
        ::= {sdsl15mPerformanceEntry 1}

    sdsl15mESNet  OBJECT-TYPE
        SYNTAX      Short
        MAX-ACCESS  read-only
        STATUS      current
        DESCRIPTION
            "SDSL 15-min ES count on Network side of the span."
        ::= {sdsl15mPerformanceEntry 2}

    sdsl15mUASNet OBJECT-TYPE
        SYNTAX      Short
        MAX-ACCESS  read-only
        STATUS      current
        DESCRIPTION
            "SDSL 15-min UAS count on Network side of the span."
        ::= {sdsl15mPerformanceEntry 3}

    sdsl15mESCust OBJECT-TYPE
        SYNTAX      Short
        MAX-ACCESS  read-only
        STATUS      current
        DESCRIPTION
            "SDSL 15-min ES count on the Customer side of the span."
        ::= {sdsl15mPerformanceEntry 4}


    sdsl15mUASCust OBJECT-TYPE
        SYNTAX      Short
        MAX-ACCESS  read-only
        STATUS      current
        DESCRIPTION
            "SDSL 15-min UAS count on the Customer side of the span."
        ::= {sdsl15mPerformanceEntry 5}




    ----------------------------------------------------
    -- SDSL 24-Hour Performance History
    ----------------------------------------------------
    sdsl24hPerformanceTable  OBJECT-TYPE
        SYNTAX      SEQUENCE OF Sdsl24hPerformanceEntry
        MAX-ACCESS  not-accessible
        STATUS      current
        DESCRIPTION
            "This table provides 24-hour performance history monitoring of the
             last 7 days for all SDSL Errored Seconds (ES), and Unavailable
             Seconds (UAS). All 7 entries for the 7-day history are zeroed out
             and available at power up.  Not all of the returned values are
             legitimate until the appropriate number of days has elapsed."
        ::= {sdslMibObjects 2}

    sdsl24hPerformanceEntry  OBJECT-TYPE
        SYNTAX      Sdsl24hPerformanceEntry
        MAX-ACCESS  not-accessible
        STATUS      current
        DESCRIPTION
            "Entries of the SDSL 24-hour performance table "
        INDEX	{ifIndex, sdsl24hHistoryId}
        ::= {sdsl24hPerformanceTable 1}

    Sdsl24hPerformanceEntry ::= SEQUENCE {
        sdsl24hHistoryId
                Short,
        sdsl24hESNet
                Short,
        sdsl24hUASNet
                Short,
        sdsl24hESCust
                Short,
        sdsl24hUASCust
                Short
        }



    sdsl24hHistoryId  OBJECT-TYPE
        SYNTAX      Short
        MAX-ACCESS  read-only
        STATUS      current
        DESCRIPTION
            "Identify the history ID within the 7 24-hour performance
             history.
            "
        ::= {sdsl24hPerformanceEntry 1}

    sdsl24hESNet  OBJECT-TYPE
        SYNTAX      Short
        MAX-ACCESS  read-only
        STATUS      current
        DESCRIPTION
            "SDSL 24-hour ES count on the Network side of the span."
        ::= {sdsl24hPerformanceEntry 2}


    sdsl24hUASNet OBJECT-TYPE
        SYNTAX      Short
        MAX-ACCESS  read-only
        STATUS      current
        DESCRIPTION
            "SDSL 24-hour UAS count on the Network side of the span."
        ::= {sdsl24hPerformanceEntry 3}



    sdsl24hESCust OBJECT-TYPE
        SYNTAX      Short
        MAX-ACCESS  read-only
        STATUS      current
        DESCRIPTION
            "SDSL 24-hour ES count on the Customer side of the span."
        ::= {sdsl24hPerformanceEntry 4}


    sdsl24hUASCust OBJECT-TYPE
        SYNTAX      Short
        MAX-ACCESS  read-only
        STATUS      current
        DESCRIPTION
            "SDSL 24-hour UAS count on the Customer side of the span."
        ::= {sdsl24hPerformanceEntry 5}




    ----------------------------------------------------
    -- SDSL Current 24-Hour Performance Counts
    ----------------------------------------------------
    sdslCurr24hPerformanceTable  OBJECT-TYPE
        SYNTAX      SEQUENCE OF SdslCurr24hPerformanceEntry
        MAX-ACCESS  not-accessible
        STATUS      current
        DESCRIPTION
            "This table provides the current 24-hour performance history
             monitoring for all SDSL Errored Seconds (ES),
             and Unavailable Seconds (UAS)."
        ::= {sdslMibObjects 3}

    sdslCurr24hPerformanceEntry  OBJECT-TYPE
        SYNTAX      SdslCurr24hPerformanceEntry
        MAX-ACCESS  not-accessible
        STATUS      current
        DESCRIPTION
            "Entries of the SDSL Current 24-hour PM counts table "
        INDEX       {ifIndex}
        ::= {sdslCurr24hPerformanceTable 1}

    SdslCurr24hPerformanceEntry ::= SEQUENCE {
        sdslCurr24hESNet
                Short,
        sdslCurr24hUASNet
                Short,
        sdslCurr24hESCust
                Short,
        sdslCurr24hUASCust
                Short
        }

    sdslCurr24hESNet  OBJECT-TYPE
        SYNTAX      Short
        MAX-ACCESS  read-only
        STATUS      current
        DESCRIPTION
            "SDSL Current 24-hour ES count on the Network side of the span."
        ::= {sdslCurr24hPerformanceEntry 1}

    sdslCurr24hUASNet OBJECT-TYPE
        SYNTAX      Short
        MAX-ACCESS  read-only
        STATUS      current
        DESCRIPTION
            "SDSL 24-hour UAS count on the Network side of the span."
        ::= {sdslCurr24hPerformanceEntry 2}

    sdslCurr24hESCust OBJECT-TYPE
        SYNTAX      Short
        MAX-ACCESS  read-only
        STATUS      current
        DESCRIPTION
            "SDSL 24-hour ES count on the Customer side of the span."
        ::= {sdslCurr24hPerformanceEntry 3}

    sdslCurr24hUASCust OBJECT-TYPE
        SYNTAX      Short
        MAX-ACCESS  read-only
        STATUS      current
        DESCRIPTION
            "SDSL 24-hour UAS count on the Customer side of the span."
        ::= {sdslCurr24hPerformanceEntry 4}

    ----------------------------------------------------
    -- SDSL Statistics
    ----------------------------------------------------
    sdslStatisticsTable  OBJECT-TYPE
        SYNTAX      SEQUENCE OF SdslStatisticsEntry
        MAX-ACCESS  not-accessible
        STATUS      current
        DESCRIPTION
            "This table lists statistics for margin, and pulse attenuation,
            of the SDSL loop."
        ::= {sdslMibObjects 4}

    sdslStatisticsEntry  OBJECT-TYPE
        SYNTAX      SdslStatisticsEntry
        MAX-ACCESS  not-accessible
        STATUS      current
        DESCRIPTION
            "Entries of the SDSL line statistics table "
        INDEX       {ifIndex}
        ::= {sdslStatisticsTable 1}

    SdslStatisticsEntry ::= SEQUENCE {
        sdslTipRingReversal
            Byte,
        sdslUpState
            Byte,
        sdslMarginNet
            Byte,
        sdslMarginHighNet
            Byte,
        sdslMarginLowNet
            Byte,
        sdslPulseAttenuationNet
            Byte,
        sdslMarginCust
            Byte,
        sdslMarginHighCust
            Byte,
        sdslMarginLowCust
            Byte,
        sdslPulseAttenuationCust
            Byte
	}

    sdslTipRingReversal OBJECT-TYPE
        SYNTAX      Byte
        MAX-ACCESS  read-only
        STATUS      current
        DESCRIPTION
            "Current TIP/RING state on the SDSL span:
                 0 - TIP/RING is not reversed.
                 1 - TIP/RING is reversed.
            "
        ::= {sdslStatisticsEntry 1}

    sdslUpState  OBJECT-TYPE
        SYNTAX      Byte
        MAX-ACCESS  read-only
        STATUS      current
        DESCRIPTION
            "Current loop state of the span:
                 0 - loop is up.
                 1 - loop is acquiring/converging.
                 2 - loop is signaling.
            "
        ::= {sdslStatisticsEntry 2}

    sdslMarginNet  OBJECT-TYPE
        SYNTAX      Byte
        MAX-ACCESS  read-only
        STATUS      current
        DESCRIPTION
            "Current Margin on the Network side of the span."
        ::= {sdslStatisticsEntry 3}

    sdslMarginHighNet  OBJECT-TYPE
        SYNTAX      Byte
        MAX-ACCESS  read-only
        STATUS      current
        DESCRIPTION
            "Highest Margin on the Network side of the span."
        ::= {sdslStatisticsEntry 4}

    sdslMarginLowNet  OBJECT-TYPE
        SYNTAX      Byte
        MAX-ACCESS  read-only
        STATUS      current
        DESCRIPTION
            "Lowest Margin on the Network side of the span."
        ::= {sdslStatisticsEntry 5}

    sdslPulseAttenuationNet  OBJECT-TYPE
        SYNTAX      Byte
        MAX-ACCESS  read-only
        STATUS      current
        DESCRIPTION
            "Pulse Attenuation on the Network side of the span."
        ::= {sdslStatisticsEntry 6}

    sdslMarginCust  OBJECT-TYPE
        SYNTAX      Byte
        MAX-ACCESS  read-only
        STATUS      current
        DESCRIPTION
            "Current Margin on the Customer side of the span."
        ::= {sdslStatisticsEntry 7}

    sdslMarginHighCust  OBJECT-TYPE
        SYNTAX      Byte
        MAX-ACCESS  read-only
        STATUS      current
        DESCRIPTION
            "Highest Margin on the Customer side of the span."
        ::= {sdslStatisticsEntry 8}

    sdslMarginLowCust  OBJECT-TYPE
        SYNTAX      Byte
        MAX-ACCESS  read-only
        STATUS      current
        DESCRIPTION
            "Lowest Margin on the Customer side of the span."
        ::= {sdslStatisticsEntry 9}

    sdslPulseAttenuationCust  OBJECT-TYPE
        SYNTAX      Byte
        MAX-ACCESS  read-only
        STATUS      current
        DESCRIPTION
            "Pulse Attenuation on the Customer side of the span."
        ::= {sdslStatisticsEntry 10}


----------------------------------------------------------------------
-- SDSL Line Settings Descriptions.
-- This table assigns the profile (stored on the AMC) for a particular Line.
----------------------------------------------------------------------
    sdslLineTable  OBJECT-TYPE
        SYNTAX      SEQUENCE OF SdslLineEntry
        MAX-ACCESS  not-accessible
        STATUS      current
        DESCRIPTION
            "This table lists which Profiles (located at the AMC)  are
            assigned to the particular SDSL Line."
        ::= {sdslMibObjects 5}

    sdslLineEntry  OBJECT-TYPE
        SYNTAX      SdslLineEntry
        MAX-ACCESS  not-accessible
        STATUS      current
        DESCRIPTION
            "Entries of the SDSL line table "
        INDEX       {ifIndex}
        ::= {sdslLineTable 1}

    SdslLineEntry ::= SEQUENCE {
        sdslLineConfProfile
            SdslLineProfileType,
        sdslLineAlarmConfProfile
            SdslLineProfileType
	}


    sdslLineConfProfile OBJECT-TYPE
        SYNTAX      SdslLineProfileType
        MAX-ACCESS  read-write
        STATUS      current
        DESCRIPTION
        	"The value of this object identifies the row
            in the SDSL Line Configuration Profile Table,
            (sdslLineConfProfileTable), which applies for this
            SDSL line.  The Profiles are stored on the Management
			card.  In the case which the configuration
			profile has not been set, the value will be set to '0'."
        ::= { sdslLineEntry 1 }

	sdslLineAlarmConfProfile OBJECT-TYPE
        SYNTAX      SdslLineProfileType
        MAX-ACCESS  read-write
        STATUS      current
        DESCRIPTION
        	"The value of this object identifies the row
            in the SDSL Line Alarm Configuration Profile Table,
       		(sdslLineAlarmConfProfileTable), which applies for this
       		SDSL line.  In the case which the configuration
			profile has not been set, the value will be set to '0'."
        ::= { sdslLineEntry 2 }




    ----------------------------------------------------
    -- SDSL Alarms Table
	----------------------------------------------------
    sdslAlarmTable  OBJECT-TYPE
        SYNTAX      SEQUENCE OF SdslAlarmEntry
        MAX-ACCESS  not-accessible
        STATUS      current
        DESCRIPTION
            "This table provides the SDSL alarms indication."
        ::= {sdslMibObjects 6}

    sdslAlarmEntry  OBJECT-TYPE
        SYNTAX      SdslAlarmEntry
        MAX-ACCESS  not-accessible
        STATUS      current
        DESCRIPTION
            "Entries of the SDSL span alarm table "
        INDEX       {ifIndex}
        ::= {sdslAlarmTable 1}

    SdslAlarmEntry ::= SEQUENCE {
        sdslMarginAlarmNet
            Byte,
        sdslESAlarmNet
            Byte,
        sdslUASAlarmNet
            Byte,
        sdslMarginAlarmCust
            Byte,
        sdslESAlarmCust
            Byte,
        sdslUASAlarmCust
            Byte,
        sdslLOSWAlarm
            Byte
    }

    sdslMarginAlarmNet OBJECT-TYPE
        SYNTAX      Byte
        MAX-ACCESS  read-only
        STATUS      current
        DESCRIPTION
            "Margin Threshold Exceeded on the Network side of the span."
        ::= {sdslAlarmEntry 1}

    sdslESAlarmNet OBJECT-TYPE
        SYNTAX      Byte
        MAX-ACCESS  read-only
        STATUS      current
        DESCRIPTION
            "Errored Seconds threshold exceeded on the Network side
             of the span."
        ::= {sdslAlarmEntry 2}

    sdslUASAlarmNet OBJECT-TYPE
        SYNTAX      Byte
        MAX-ACCESS  read-only
        STATUS      current
        DESCRIPTION
            "Unavailable Seconds threshold exceeded on the Network
             side of the span."
        ::= {sdslAlarmEntry 3}

    sdslMarginAlarmCust OBJECT-TYPE
        SYNTAX      Byte
        MAX-ACCESS  read-only
        STATUS      current
        DESCRIPTION
            "Margin Threshold Exceeded on the Customer side of the span."
        ::= {sdslAlarmEntry 4}


    sdslESAlarmCust OBJECT-TYPE
        SYNTAX      Byte
        MAX-ACCESS  read-only
        STATUS      current
        DESCRIPTION
            "Errored Seconds Exceeded on the Customer side of the span."
        ::= {sdslAlarmEntry 5}

    sdslUASAlarmCust OBJECT-TYPE
        SYNTAX      Byte
        MAX-ACCESS  read-only
        STATUS      current
        DESCRIPTION
            "Unavailable Seconds threshold exceeded on the customer side
			of the span."
        ::= {sdslAlarmEntry 6}

    sdslLOSWAlarm  OBJECT-TYPE
        SYNTAX      Byte
        MAX-ACCESS  read-only
        STATUS      current
        DESCRIPTION
            "Loss of Sync Word (LOSW) occurred on the Network side of
			the SDSL loop.
            "
        ::= {sdslAlarmEntry 7}


    ----------------------------------------------------
    -- SDSL Alarms History Table for SDSL
    ----------------------------------------------------
    sdslAlarmHistoryTable  OBJECT-TYPE
        SYNTAX      SEQUENCE OF SdslAlarmHistoryEntry
        MAX-ACCESS  not-accessible
        STATUS      current
        DESCRIPTION
            "This table provides the SDSL alarms history"
        ::= {sdslMibObjects 7}

    sdslAlarmHistoryEntry  OBJECT-TYPE
        SYNTAX      SdslAlarmHistoryEntry
        MAX-ACCESS  not-accessible
        STATUS      current
        DESCRIPTION
            "Entries of the SDSL Alarm History table "
        INDEX       {ifIndex}
        ::= {sdslAlarmHistoryTable 1}

    SdslAlarmHistoryEntry ::= SEQUENCE {
        sdslMarginAlarmFirst
            PgSdslTimeStamp,
        sdslMarginAlarmLast
            PgSdslTimeStamp,
        sdslMarginAlarmCount
            Short,
        sdslESAlarmFirst
            PgSdslTimeStamp,
        sdslESAlarmLast
            PgSdslTimeStamp,
        sdslESAlarmCount
            Short,
        sdslUASAlarmFirst
            PgSdslTimeStamp,
        sdslUASAlarmLast
            PgSdslTimeStamp,
        sdslUASAlarmCount
            Short,
        sdslLOSWAlarmFirst
            PgSdslTimeStamp,
        sdslLOSWAlarmLast
            PgSdslTimeStamp,
        sdslLOSWAlarmCount
            Short
    }


    sdslMarginAlarmFirst  OBJECT-TYPE
        SYNTAX      PgSdslTimeStamp
        MAX-ACCESS  read-only
        STATUS      current
        DESCRIPTION
            "Date and time Margin threshold exceeded alarm first occurred"
        ::= {sdslAlarmHistoryEntry 1}

    sdslMarginAlarmLast  OBJECT-TYPE
        SYNTAX      PgSdslTimeStamp
        MAX-ACCESS  read-only
        STATUS      current
        DESCRIPTION
            "Date and time Margin threshold exceeded alarm last occurred"
        ::= {sdslAlarmHistoryEntry 2}

    sdslMarginAlarmCount  OBJECT-TYPE
        SYNTAX      Short
        MAX-ACCESS  read-only
        STATUS      current
        DESCRIPTION
            "The number of times the Margin threshold exceeded alarm has
			occurred
            "
        ::= {sdslAlarmHistoryEntry 3}

    sdslESAlarmFirst OBJECT-TYPE
        SYNTAX      PgSdslTimeStamp
        MAX-ACCESS  read-only
        STATUS      current
        DESCRIPTION
            "Date and time Errored Seconds threshold exceeded alarm first occurred
             "
        ::= {sdslAlarmHistoryEntry 4}

    sdslESAlarmLast OBJECT-TYPE
        SYNTAX      PgSdslTimeStamp
        MAX-ACCESS  read-only
        STATUS      current
        DESCRIPTION
            "Date and time Errored Seconds threshold exceeded alarm last occurred
             "
        ::= {sdslAlarmHistoryEntry 5}

     sdslESAlarmCount OBJECT-TYPE
        SYNTAX      Short
        MAX-ACCESS  read-only
        STATUS      current
        DESCRIPTION
            "The number of times the Errored Seconds threshold exceeded alarm has
             occurred"
        ::= {sdslAlarmHistoryEntry 6}


    sdslUASAlarmFirst OBJECT-TYPE
        SYNTAX      PgSdslTimeStamp
        MAX-ACCESS  read-only
        STATUS      current
        DESCRIPTION
            "Date and time Unavailable Seconds threshold exceeded alarm
             occurred"
        ::= {sdslAlarmHistoryEntry 7}

    sdslUASAlarmLast OBJECT-TYPE
        SYNTAX      PgSdslTimeStamp
        MAX-ACCESS  read-only
        STATUS      current
        DESCRIPTION
            "Date and time Unavailable Seconds threshold exceeded alarm
             last occurred "
        ::= {sdslAlarmHistoryEntry 8}

     sdslUASAlarmCount OBJECT-TYPE
        SYNTAX      Short
        MAX-ACCESS  read-only
        STATUS      current
        DESCRIPTION
            "The number of times the Unavailable Seconds threshold exceeded alarm
             has occurred"
        ::= {sdslAlarmHistoryEntry 9}

    sdslLOSWAlarmFirst  OBJECT-TYPE
        SYNTAX      PgSdslTimeStamp
        MAX-ACCESS  read-only
        STATUS      current
        DESCRIPTION
            "Date and time the Loss of Sync Word alarm first occurred
             "
        ::= {sdslAlarmHistoryEntry 10}

    sdslLOSWAlarmLast   OBJECT-TYPE
        SYNTAX      PgSdslTimeStamp
        MAX-ACCESS  read-only
        STATUS      current
        DESCRIPTION
            "Date and time the Loss of Sync Word alarm last occurred
             "
        ::= {sdslAlarmHistoryEntry 11}

    sdslLOSWAlarmCount  OBJECT-TYPE
        SYNTAX      Short
        MAX-ACCESS  read-only
        STATUS      current
        DESCRIPTION
            "The number of times the Loss of Sync Word alarm
             has occurred."
        ::= {sdslAlarmHistoryEntry 12}



----------------------------------------------------------
--- The following sdslLineConfProfile will support rate
--  selection.  The multi-rate selection is modeled after the
--- Campus rate selection which has a fixed rate manual mode
--- where both sides must set the rate and a semi-automatic
--- rate selection where the CO selects the rate.
----------------------------------------------------------
	sdslLineConfProfileIndexNext OBJECT-TYPE
        SYNTAX          INTEGER(0..65535)
        MAX-ACCESS      read-only
        STATUS          current
        DESCRIPTION
            " This object contains an appropriate value to
            be used for sdslLineConfProfileIndex when creating
            entries in the sdslLineConfProfileTable. The value
            '0' indicates that no unassigned entries are
            available. To obtain the sdslLineConfProfileIndexNext
            value for a new entry, the manager issues a
            management protocol retrieval operation to obtain
            the current value of this object.  After each
            retrieval, the agent should modify the value to
            the next unassigned index.

            If the implementator of this MIB has choosen not
            to implement 'dynamic assignment' of profiles, this
            object is not useful and should return noSuchName
            upon SNMP request."
        ::= { sdslMibObjects 8}

    sdslLineConfProfileTable    OBJECT-TYPE
        SYNTAX          SEQUENCE OF SdslLineConfProfileEntry
        MAX-ACCESS      not-accessible
        STATUS          current
        DESCRIPTION
            "This table contains information on the sdsl line
            configuration.  One entry in this table reflects a
            profile defined by a manager which can be used to
            configure the sdsl line."
        ::= { sdslMibObjects 9}

    sdslLineConfProfileEntry    OBJECT-TYPE
        SYNTAX          SdslLineConfProfileEntry
        MAX-ACCESS      not-accessible
        STATUS          current
        DESCRIPTION
        	"Each entry consists of a list of parameters that
            represents the configuration of an sdsl port.  A
            profile is created in one step with all necessary
            parameter values and sdslLineProfileRowStatus set to
            createAndGo.  This RowStatus object is also used
            to delete destroy profiles."
        INDEX { sdslLineConfProfileIndex}
    ::= { sdslLineConfProfileTable 1}

    SdslLineConfProfileEntry ::=
    	SEQUENCE {
            sdslLineConfProfileIndex                SdslLineProfileType,
            sdslRateMode                            INTEGER(1..32000),
            sdslRemFeatures                         Short,
            sdslRate                                INTEGER(1..32000),
            sdslLineConfProfileRowStatus            RowStatus
            }

	sdslLineConfProfileIndex    OBJECT-TYPE
        SYNTAX          SdslLineProfileType
        MAX-ACCESS      not-accessible
        STATUS          current
        DESCRIPTION
        	"This object is used by the line configuration
            table in order to identify a row of this table"
        ::= { sdslLineConfProfileEntry 1}

	sdslRateMode	OBJECT-TYPE
        SYNTAX      INTEGER(1..32000)
        MAX-ACCESS  read-write
        STATUS      current
        DESCRIPTION
        	"Rate Mode defined in Rate Selective/Adaptive Specification
            for SDSL Products.
            Mode 1 - Fixed Rate (FR) - The channel shall operate at the
            rate set by the sdslRate parameter and supported at the remote unit
            either by default, manual switch setting, or Smart Manual mode on
            the modem.  Support of the two-level signalling mechanism at the
            remote is known as Smart Manual mode.  The remote unit is
            configured via a two-level signaling mechanism prior to the normal
            startup sequence.   This mechanism allows the link rate to be
            controlled by the Central Office shelf.
            If the remote modem does not support the two-level signaling
            mechanism, the system will timeout and the default startup sequence
            will begin.
            Mode 2 - Rate Adaptive (RA) - NOT supported in this MIB yet.
			Allows the unit to evaluate the characteristics of the SDSL
			channel and adapt the data rate based upon user-defined performance
            criteria."
        ::= { sdslLineConfProfileEntry 2 }

 	sdslRemFeatures	OBJECT-TYPE
        SYNTAX      Short
        MAX-ACCESS  read-write
        STATUS      current
        DESCRIPTION
        	"This will variable will reflect the features supported by
            the remote unit (modem) which are received during the two-level signaling
            mechanism that occurs before the start-up sequence.
            "
        ::= { sdslLineConfProfileEntry 3 }

	sdslRate	OBJECT-TYPE
        SYNTAX      INTEGER(1..32000)
        UNITS       "kbps"
        MAX-ACCESS  read-write
        STATUS      current
        DESCRIPTION
            "The desired rate for the particular SDSL span. Set at the CO using
            management software "
		::= { sdslLineConfProfileEntry 4 }

    sdslLineConfProfileRowStatus OBJECT-TYPE
    	SYNTAX          RowStatus
        MAX-ACCESS      read-create
        STATUS          current
        DESCRIPTION
        	"This object is used to create a new row or modify or
            delete an existing row in this table.

            If the implementator of this MIB has choosen not
            to implement 'dynamic assignment' of profiles, this
            object is not useful and should return noSuchName
            upon SNMP request."
        ::= { sdslLineConfProfileEntry 5 }


----------------------------------------------------------
--- In order to support the Line Profiles, the SDSLAlarm
--- Severity Table is replaced with the sdslLineAlarmConfProfile
--- below r.w.
----------------------------------------------------------
	sdslLineAlarmConfProfileIndexNext OBJECT-TYPE
         SYNTAX          INTEGER(0..65535)
         MAX-ACCESS      read-only
         STATUS          current
         DESCRIPTION
            " This object contains an appropriate value to
            be used for sdslLineAlarmConfProfileIndex when creating
            entries in the sdslLineAlarmConfTable. The value
            '0' indicates that no unassigned entries are available.
            To obtain the sdslLineAlarmConfProfileIndexNext
            value for a new entry, the manager issues a
            management protocol retrieval operation to obtain
            the current value of this object.  After each
            retrieval, the agent should modify the value to
            the next unassigned index.

            If the implementator of this MIB has choosen not
            to implement 'dynamic assignment' of profiles, this
            object is not useful and should return noSuchName
            upon SNMP request."
        ::= { sdslMibObjects 10 }

    sdslLineAlarmConfProfileTable    OBJECT-TYPE
        SYNTAX          SEQUENCE OF SdslLineAlarmConfProfileEntry
        MAX-ACCESS      not-accessible
        STATUS          current
        DESCRIPTION
            "This table contains information on the sdsl line
            configuration.  One entry in this table reflects a
            profile defined by a manager which can be used to
            configure the modem for a physical line"
        ::= { sdslMibObjects 11 }

    sdslLineAlarmConfProfileEntry    OBJECT-TYPE
        SYNTAX          SdslLineAlarmConfProfileEntry
        MAX-ACCESS      not-accessible
        STATUS          current
        DESCRIPTION
        	"Each entry consists of a list of parameters that
            represents the alarm configuration for one sdsl line.  A
            profile is created in one step with all necessary
            parameter values and sdslLineAlarmConfProfileRowStatus
            set to createAndGo.  This RowStatus object is also
            used to delete destroy profiles.
			Each entry is taken from the original Pairgain SDSL MIB called
			sdslAlarmSeverityEntry which provided: severity settings
            for SDSL alarms reporting and threshold settings for
            Errored Second(ES), Margin(MAR), Unavailable Seconds(UAS).
            "

        INDEX           {sdslLineAlarmConfProfileIndex}
    ::= { sdslLineAlarmConfProfileTable 1}

    SdslLineAlarmConfProfileEntry ::=
		SEQUENCE {
			sdslLineAlarmConfProfileIndex
                SdslLineProfileType,
			sdslLOSWAlarmSetting
                PgSdslAlarmSeverityMode,
	        sdslMarginThreshold
	            Byte,
	        sdslMarginAlarmSetting
                PgSdslAlarmSeverityMode,
	        sdslESThreshold
	            Byte,
	        sdslESAlarmSetting
                PgSdslAlarmSeverityMode,
	        sdslUASThreshold
	            Byte,
	        sdslUASAlarmSetting
	            PgSdslAlarmSeverityMode,
            sdslLineAlarmConfProfileRowStatus
				RowStatus
	    }

	sdslLineAlarmConfProfileIndex    OBJECT-TYPE
        SYNTAX          SdslLineProfileType
        MAX-ACCESS      not-accessible
        STATUS          current
        DESCRIPTION
        	"This object is used by the line alarm configuration
            table in order to identify a row of this table"
        ::= { sdslLineAlarmConfProfileEntry 1}

    sdslLOSWAlarmSetting OBJECT-TYPE
        SYNTAX      PgSdslAlarmSeverityMode
        MAX-ACCESS  read-write
        STATUS      current
        DESCRIPTION
            "Sets the severity for Loss of Sync Word alarm."
        ::= {sdslLineAlarmConfProfileEntry 2}

    sdslMarginThreshold  OBJECT-TYPE
        SYNTAX      Byte
        MAX-ACCESS  read-write
        STATUS      current
        DESCRIPTION
            "Sets the SDSL Margin threshold value."
        ::= {sdslLineAlarmConfProfileEntry 3}

    sdslMarginAlarmSetting OBJECT-TYPE
        SYNTAX      PgSdslAlarmSeverityMode
        MAX-ACCESS  read-write
        STATUS      current
        DESCRIPTION
            "Sets the severity for Margin threshold exceeded alarm."
        ::= {sdslLineAlarmConfProfileEntry 4}

    sdslESThreshold OBJECT-TYPE
        SYNTAX      Byte
        MAX-ACCESS  read-write
        STATUS      current
        DESCRIPTION
            "Sets the SDSL Errored Seconds threshold value."
        ::= {sdslLineAlarmConfProfileEntry 5}

    sdslESAlarmSetting OBJECT-TYPE
        SYNTAX      PgSdslAlarmSeverityMode
        MAX-ACCESS  read-write
        STATUS      current
        DESCRIPTION
            "Sets the severity for Errored Seconds threshold exceeded alarm."
        ::= {sdslLineAlarmConfProfileEntry 6}

    sdslUASThreshold OBJECT-TYPE
        SYNTAX      Byte
        MAX-ACCESS  read-write
        STATUS      current
        DESCRIPTION
            "Sets the SDSL Unavailable Seconds threshold value."
        ::= {sdslLineAlarmConfProfileEntry 7}

    sdslUASAlarmSetting OBJECT-TYPE
        SYNTAX      PgSdslAlarmSeverityMode
        MAX-ACCESS  read-write
        STATUS      current
        DESCRIPTION
            "Sets the severity for UAS threshold exceeded alarm."
        ::= {sdslLineAlarmConfProfileEntry 8}

 	sdslLineAlarmConfProfileRowStatus OBJECT-TYPE
    	SYNTAX          RowStatus
        MAX-ACCESS      read-create
        STATUS          current
        DESCRIPTION
        	"This object is used to create a new row or modify or
            delete an existing row in this table.

            If the implementator of this MIB has choosen not
            to implement 'dynamic assignment' of profiles, this
            object is not useful and should return noSuchName
            upon SNMP request."
        ::= { sdslLineAlarmConfProfileEntry 9}

    ----------------------------------------------------
    -- SDSL Proxy Modem Section
	-- System engineering decided that modem statistics
	-- will be stored in a local Pairgain proprietary
	-- MIB rather than one of the standard MIBs with a modified
	-- ifIndex.  These MIB objects contain informatiion gathered
	-- from the modem through the HDSL EOC.
    ----------------------------------------------------

	----------------------------------------------------
	-- SDSL Modem General Info
	-- Vendor ID number different for each modem type,
	-- list number, SW version number, etc.
	----------------------------------------------------
    pgSdslModGenTable  OBJECT-TYPE
        SYNTAX      SEQUENCE OF PgSdslModGenEntry
        MAX-ACCESS  not-accessible
        STATUS      current
        DESCRIPTION
            "This table provides general information about the SDSL
			modem.
        	pgSdslModGenVersionNum:  Contains the Modem software version number
			pgSdslModGenListNum: 	 When used with the vendor number the list
			   number provides a unique model number identifier for the modem.
			pgSdslModGenVendNum:	 A unique number given to every Pairgain product.
			pgSdslModGenFeatures	 A 32 bit flag that has bits set according to
			   feature supported by the modem.
			pgSdslModGenSerialNum    16 bits, used with manufacturing date to give unique
									 identifier for the modem.
        	pgSdslModGenMfgDate      16 bit, used with the Serial number to give a unique
									 identifier for the modem.
			"
        ::= {sdslMibObjects 12}

    pgSdslModGenEntry  OBJECT-TYPE
        SYNTAX      PgSdslModGenEntry
        MAX-ACCESS  not-accessible
        STATUS      current
        DESCRIPTION
            "Entries (one per port) for general modem information."
        INDEX       {ifIndex}
        ::= {pgSdslModGenTable 1}

    PgSdslModGenEntry ::= SEQUENCE {
        pgSdslModGenVersionNum     Byte,
        pgSdslModGenListNum        Byte,
		pgSdslModGenVendNum        Byte,
		pgSdslModGenFeatures	   Integer32,
		pgSdslModGenSerialNum      Short,
        pgSdslModGenMfgDate        Short
	}

	pgSdslModGenVersionNum  	OBJECT-TYPE
        SYNTAX      Byte
        MAX-ACCESS  read-only
        STATUS      current
        DESCRIPTION
            "Identifies the software version number of the modem.
            "
        ::= {pgSdslModGenEntry 1}

	pgSdslModGenListNum  	OBJECT-TYPE
        SYNTAX      Byte
        MAX-ACCESS  read-only
        STATUS      current
        DESCRIPTION
            "Identifies the list number of the modem.
            "
        ::= {pgSdslModGenEntry 2}


	pgSdslModGenVendNum  	OBJECT-TYPE
        SYNTAX      Byte
        MAX-ACCESS  read-only
        STATUS      current
        DESCRIPTION
            "Identifies the vendor number of the modem.  The vendor number
			is a Pair Gain product unique identifier.
            "
        ::= {pgSdslModGenEntry 3}

	pgSdslModGenFeatures  	OBJECT-TYPE
        SYNTAX      Integer32
        MAX-ACCESS  read-only
        STATUS      current
        DESCRIPTION
            "Contains the feature bytes from the modem.
            "
        ::= {pgSdslModGenEntry 4}

	pgSdslModGenSerialNum  	OBJECT-TYPE
        SYNTAX      Short
        MAX-ACCESS  read-only
        STATUS      current
        DESCRIPTION
            "Contains the Serial number of the modem read from the
			modem's NVRAM.
            "
        ::= {pgSdslModGenEntry 5}


	pgSdslModGenMfgDate  	OBJECT-TYPE
        SYNTAX      Short
        MAX-ACCESS  read-only
        STATUS      current
        DESCRIPTION
            "Contains the Manufacturing date of the modem read from the
			modem's NVRAM.
            "
        ::= {pgSdslModGenEntry 6}



	----------------------------------------------------
	-- SDSL Modem Statistics
	-- Proxy statistics kept for the general ifTable
	-- entries for the modem.
	----------------------------------------------------

	pgSdslModStatTable  OBJECT-TYPE
        SYNTAX      SEQUENCE OF PgSdslModStatEntry
        MAX-ACCESS  not-accessible
        STATUS      current
        DESCRIPTION
            "This table provides modem statistics gathered
			from the modem through EOC messages.  These statistics
			correspond to a subset of those in the standard ifTable.

			Ethernet port statistics are given in the following objects:

			pgSdslModEthOperStatus:  the status of the ethernet link.
        	pgSdslModEthInOctets
        	pgSdslModEthInUcastPkts
        	pgSdslModEthInNUcastPkts
        	pgSdslModEthInDiscards
        	pgSdslModEthInErrors
        	pgSdslModEthOutOctets
        	pgSdslModEthOutUcastPkts
	        pgSdslModEthOutNUcastPkts
	        pgSdslModEthOutErrors

			SDSL port statistics are given in the following objects:

			pgSdslModDslInOctets
        	pgSdslModDslInUcastPkts
        	pgSdslModDslInNUcastPkts
        	pgSdslModDslInDiscards
        	pgSdslModDslInErrors
        	pgSdslModDslOutOctets
        	pgSdslModDslOutUcastPkts
        	pgSdslModDslOutNUcastPkts
        	pgSdslModDslOutErrors
			"
        ::= {sdslMibObjects 13}

    pgSdslModStatEntry  OBJECT-TYPE
        SYNTAX      PgSdslModStatEntry
        MAX-ACCESS  not-accessible
        STATUS      current
        DESCRIPTION
            "Entries (one per port) for the modem statistics."
        INDEX       {ifIndex}
        ::= {pgSdslModStatTable 1}

    PgSdslModStatEntry ::= SEQUENCE {
        pgSdslModEthOperStatus         	INTEGER,
        pgSdslModEthInOctets           	Counter32,
        pgSdslModEthInUcastPkts        	Counter32,
        pgSdslModEthInNUcastPkts       	Counter32,
        pgSdslModEthInDiscards         	Counter32,
        pgSdslModEthInErrors           	Counter32,
        pgSdslModEthOutOctets          	Counter32,
        pgSdslModEthOutUcastPkts       	Counter32,
        pgSdslModEthOutNUcastPkts      	Counter32,
        pgSdslModEthOutErrors          	Counter32,
        pgSdslModDslInOctets           	Counter32,
        pgSdslModDslInUcastPkts        	Counter32,
        pgSdslModDslInNUcastPkts       	Counter32,
        pgSdslModDslInDiscards         	Counter32,
        pgSdslModDslInErrors           	Counter32,
        pgSdslModDslOutOctets          	Counter32,
        pgSdslModDslOutUcastPkts       	Counter32,
        pgSdslModDslOutNUcastPkts      	Counter32,
        pgSdslModDslOutErrors          	Counter32
		}

--- Modem's Ethernet Stastistics

	pgSdslModEthOperStatus  	OBJECT-TYPE
       SYNTAX  INTEGER {
                   up(1),       -- ready to pass packets
                   down(2),
                   testing(3),  -- in some test mode
                   unknown(4),  -- status can not be determined
                                -- for some reason.
                   dormant(5)
               }
        MAX-ACCESS  read-only
        STATUS      current
        DESCRIPTION
            "Identifies the status of the modem's ethernet port. Up or Down
			"
        ::= {pgSdslModStatEntry 1}

	pgSdslModEthInOctets  	OBJECT-TYPE
        SYNTAX      Counter32
        MAX-ACCESS  read-only
        STATUS      current
        DESCRIPTION
            "modem's Ethernet ifInOctet count
			"
        ::= {pgSdslModStatEntry 2}

	pgSdslModEthInUcastPkts  	OBJECT-TYPE
        SYNTAX      Counter32
        MAX-ACCESS  read-only
        STATUS      current
        DESCRIPTION
            "modem's Ethernet ifInUcastPkts count
			"
        ::= {pgSdslModStatEntry 3}

	pgSdslModEthInNUcastPkts  	OBJECT-TYPE
        SYNTAX      Counter32
        MAX-ACCESS  read-only
        STATUS      current
        DESCRIPTION
            "modem's Ethernet ifNUcastPkts count
			"
        ::= {pgSdslModStatEntry 4}

	pgSdslModEthInDiscards  	OBJECT-TYPE
        SYNTAX      Counter32
        MAX-ACCESS  read-only
        STATUS      current
        DESCRIPTION
            "modem's Ethernet ifInDiscards count
			"
        ::= {pgSdslModStatEntry 5}

	pgSdslModEthInErrors  	OBJECT-TYPE
        SYNTAX      Counter32
        MAX-ACCESS  read-only
        STATUS      current
        DESCRIPTION
            "modem's Ethernet ifInErrors count
			"
        ::= {pgSdslModStatEntry 6}


	pgSdslModEthOutOctets  	OBJECT-TYPE
        SYNTAX      Counter32
        MAX-ACCESS  read-only
        STATUS      current
        DESCRIPTION
            "modem's Ethernet ifOutOctets count
			"
        ::= {pgSdslModStatEntry 7}

	pgSdslModEthOutUcastPkts  	OBJECT-TYPE
        SYNTAX      Counter32
        MAX-ACCESS  read-only
        STATUS      current
        DESCRIPTION
            "modem's Ethernet ifOutUcastPkts count
			"
        ::= {pgSdslModStatEntry 8}

	pgSdslModEthOutNUcastPkts  	OBJECT-TYPE
        SYNTAX      Counter32
        MAX-ACCESS  read-only
        STATUS      current
        DESCRIPTION
            "modem's Ethernet ifOutNUcastPkts count
			"
        ::= {pgSdslModStatEntry 9}


	pgSdslModEthOutErrors  	OBJECT-TYPE
        SYNTAX      Counter32
        MAX-ACCESS  read-only
        STATUS      current
        DESCRIPTION
            "modem's Ethernet ifOutErrors count
			"
        ::= {pgSdslModStatEntry 10}

--- Modems DSL Stastistics

	pgSdslModDslInOctets  	OBJECT-TYPE
        SYNTAX      Counter32
        MAX-ACCESS  read-only
        STATUS      current
        DESCRIPTION
            "modem's Dsl ifInOctets count
			"
        ::= {pgSdslModStatEntry 11}

	pgSdslModDslInUcastPkts  	OBJECT-TYPE
        SYNTAX      Counter32
        MAX-ACCESS  read-only
        STATUS      current
        DESCRIPTION
            "modem's Dsl ifInUcastPkts count
			"
        ::= {pgSdslModStatEntry 12}


	pgSdslModDslInNUcastPkts  	OBJECT-TYPE
        SYNTAX      Counter32
        MAX-ACCESS  read-only
        STATUS      current
        DESCRIPTION
            "modem's Dsl ifInNUcastPkts count
			"
        ::= {pgSdslModStatEntry 13}

	pgSdslModDslInDiscards  	OBJECT-TYPE
        SYNTAX      Counter32
        MAX-ACCESS  read-only
        STATUS      current
        DESCRIPTION
            "modem's Dsl ifInDiscards count
			"
        ::= {pgSdslModStatEntry 14}

	pgSdslModDslInErrors  	OBJECT-TYPE
        SYNTAX      Counter32
        MAX-ACCESS  read-only
        STATUS      current
        DESCRIPTION
            "modem's Dsl ifInErrors count
			"
        ::= {pgSdslModStatEntry 15}

	pgSdslModDslOutOctets  	OBJECT-TYPE
        SYNTAX      Counter32
        MAX-ACCESS  read-only
        STATUS      current
        DESCRIPTION
            "modem's Dsl ifOutOctets count
			"
        ::= {pgSdslModStatEntry 16}

	pgSdslModDslOutUcastPkts  	OBJECT-TYPE
        SYNTAX      Counter32
        MAX-ACCESS  read-only
        STATUS      current
        DESCRIPTION
            "modem's Dsl ifOutUcastPkts count
			"
        ::= {pgSdslModStatEntry 17}

	pgSdslModDslOutNUcastPkts  	OBJECT-TYPE
        SYNTAX      Counter32
        MAX-ACCESS  read-only
        STATUS      current
        DESCRIPTION
            "modem's Dsl ifOutNUcastPkts count
			"
        ::= {pgSdslModStatEntry 18}

	pgSdslModDslOutErrors  	OBJECT-TYPE
        SYNTAX      Counter32
        MAX-ACCESS  read-only
        STATUS      current
        DESCRIPTION
            "modem's Dsl ifOutErrors count
			"
        ::= {pgSdslModStatEntry 19}


END
