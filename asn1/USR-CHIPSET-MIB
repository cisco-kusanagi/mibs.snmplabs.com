USR-CHIPSET-MIB DEFINITIONS ::= BEGIN

IMPORTS
        OBJECT-TYPE
                FROM SNMPv2-SMI

        usrADI
                FROM USR-DEFINITIONS-MIB;

adi918Interleaving	OBJECT-TYPE
		SYNTAX	INTEGER {
						off(1),
						on(2)
						}
		MAX-ACCESS	read-write
		STATUS	current
		DESCRIPTION	
				"This setting determines how interleaving is configured  
					for the ADI 918 chipset (bit 20 of Utopia register)."
		DEFVAL{  2   }
		--CONFIGURABLE
		::= { usrADI 1 }

adiOptionsSettings		OBJECT-TYPE
		SYNTAX  INTEGER 	
		MAX-ACCESS read-write
		STATUS     current
		DESCRIPTION
				"This value is written to the OPTN.options register of the
						910/918 chipset."
		--CONFIGURABLE
		::= { usrADI 2 }

adiPSDMSettings OBJECT-TYPE
		SYNTAX  INTEGER
		MAX-ACCESS  read-write
		STATUS      current
		DESCRIPTION
			" Setting for the PSDM.config register. "
		--CONFIGURABLE
		::= { usrADI 3 }

adiActualPSDMSettings OBJECT-TYPE
		SYNTAX INTEGER
		MAX-ACCESS read-only
		STATUS     current
		DESCRIPTION
		   "Setting for the PSDM.actual register."
		::= { usrADI  4 }

adiGLiteFlag    OBJECT-TYPE
		SYNTAX  INTEGER {
				t1413(1),
				glite(2),
				dmt(3),
				multimode(4)
					    }
		MAX-ACCESS  read-write
		STATUS  current
		DESCRIPTION
			"This setting controls what Standards we are in, G. Lite or
		   full rate T1.413, G.Dmt, or Multimode  modes ."
		DEFVAL{  1   }
		--CONFIGURABLE
		::= { usrADI 5 }

adiManualRetrain OBJECT-TYPE
		SYNTAX INTEGER
		MAX-ACCESS read-write
		STATUS current
		DESCRIPTION
		"Force manual retrain in G-Lite mode "
		::= { usrADI 6 }

adiClearProfiles OBJECT-TYPE
		SYNTAX INTEGER
		MAX-ACCESS read-write
		STATUS current
		DESCRIPTION
		"Clear profiles in G-Lite mode "
		::= { usrADI 7 }

adiUtopiaSetting		OBJECT-TYPE
		SYNTAX  INTEGER 	
		MAX-ACCESS read-write
		STATUS     current
		DESCRIPTION
				"This value is written to the Utopia register of the
						918 chipset."
		--CONFIGURABLE
		::= { usrADI 8 }

adiEocFlag      OBJECT-TYPE
		SYNTAX  INTEGER
		MAX-ACCESS read-write
		STATUS     current
		DESCRIPTION
			"This flag controls whether or not EOC
			 processing is enabled."
	    --CONFIGURABLE
	    ::= { usrADI 9 }

adiPFCL1Settings      OBJECT-TYPE
		SYNTAX  INTEGER
		MAX-ACCESS read-write
		STATUS     current
		DESCRIPTION
			"This value is written to the PFCL 1 register of the
			910/918 chipset."
		--CONFIGURABLE
		::= { usrADI 10 }

adiOPT4Settings      OBJECT-TYPE
        SYNTAX  INTEGER
        MAX-ACCESS read-write
        STATUS     current
        DESCRIPTION
            "This value is written to the OPTN 4 register of the
            918 chipset."
        --CONFIGURABLE
        ::= { usrADI 11 }
 
adiOPT5Settings      OBJECT-TYPE
        SYNTAX  INTEGER
        MAX-ACCESS read-write
        STATUS     current
        DESCRIPTION
            "This value is written to the OPTN 5 register of the
            918 chipset."
        --CONFIGURABLE
        ::= { usrADI 12 }
END
