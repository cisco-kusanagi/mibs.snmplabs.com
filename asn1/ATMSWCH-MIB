------------------------------------------------------------------------------
--
-- MIB      : Atm Switch			Lucent Technologies
--
-- Version  : 2.1.4 			08 Aug. 2000
--
-- RCS Id   : Gidi
--
------------------------------------------------------------------------------
--
-- Copyright 2000 Lucent Technologies, Ltd.
-- All Rights Reserved.
--
-- Reproduction of this document is authorized on condition
-- that the foregoing copyright notice is included.
--
-- This Lucent Technologies SNMP Management Information Base 
-- Specification embodies Lucent Technologies confidential and
-- proprietary intellectual property.  Lucent Technologies retains all
-- title and ownership in the Specification, including any revisions
--
-- It is Lucent Technologies intent to encourage the widespread use of this
-- Specification in connection with the management of Lucent Technologies
-- products.
-- Lucent Technologies grants vendors, end-users, and other interested parties
-- a non-exclusive license to use this Specification in connection
-- with the management of Lucent Technologies products.
--
-- This Specification is supplied "as is," and Lucent Technologies makes
-- no warranty, either express or implied, as to the use,
-- operation, condition, or performance of the Specification.
--
------------------------------------------------------------------------------
--
-- RCS
--
-- Version 2.1.4
-- 08 July 00
-- 1. Change enumeration APSFail to notActive - Michal R.
--
-- Version 2.1.3
-- 09 July 00
-- 1. Add new enumeration doNotRevert, noAPS and APSFail to atmSwchSlotAPSCurrentState - Michal R.
--
-- Version 2.1.2
-- 28 May 00
-- 1. Add new APS objects to atmSwchSlot group - Michal R.
--
-- Version 2.1.1
-- 4 April 00
-- 1. Add new MIB to atmSwchBase group: atmSwchBaseAmonAdminState - Gidi N.
-- 
-- Version 2.1.0
-- 7 March 00
-- 1. Add new MIB to port table: atmSwchPortdsx3CellMaping - Gidi N.
-- 2. Add new MIBs to Vport table: atmSwchVPortPcr, atmSwchVPortRowStatus
-- 3. Update description for atmSwchVPortConfMinVpi and atmSwchVPortConfMaxVpi
-- 
-- Version 1.1.1
-- 2 August 99
-- 1. Add new MIB to Vport table: atmSwchVPortNeighbourIpAddress - Gidi N.
--
-- Version 1.1.0
-- 20 April 99
-- 1. Add new table atmSwchSlotAddrVcl - Gidi N.
-- 2. Add uni40 enum to atmSwchVPortCurrentLinkType and
--    atmSwchVPortConfigLinkType - Gidi N. 
-- 3. Add new MIBs to Cpu table: atmSwchCpuSvcPtPtInConns,
--    atmSwchCpuSvcPtPtOutConns, atmSwchCpuSvcPtMptRootConns,
--    atmSwchCpuSvcPtMptLeafConns, atmSwchCpuPvcPtPtConns - Gidi N. 
--
-- 
-- Version 1.0.8
-- 29 Mar. 99
-- 1. Add new enumeration to atmSwchVPortNeighbourUNIVersion - Gidi N. 
-- 
-- Version 1.0.7
-- 16 Feb 99
-- 1. Add atmSwchCpuSysUpTime to atmSwchCpu table - Gidi N. 
-- 
-- Version 1.0.6
-- 30 Oct 98
-- 1. Add atmSwchVPortConfMinVpi, atmSwchVPortConfMaxVpi
--    to atmSwchVPort table - Gidi N. 
--
-- Version 1.0.5
-- 15 Oct 98
-- 1. Remove atmSwchSlotEpdThreshold, atmSwchSlotPpdThreshold
--     atmSwchSlotCbrVbrThreshold	 - Gidi N. 
-- 2.  Add atmSwchBaseEpdThreshold - Gidi N.
--
-- Version 1.0.4
-- 7 Oct 98
-- 1. Remove atmSwchVPortConfMinSvccVpi,
--     atmSwchVPortConfMaxSvccVpi, atmSwchVPortConfMinVpi, 
--     atmSwchVPortConfMaxVpi   from atmSwchVPort table
--     as they are curently not supported					- Gidi N.
--
-- Version 1.0.3
-- 17 Sept 98
-- 1. Remove atmSwchPortIdleCell mib from atmSwchPort table
--     and change the order of other items in this table		- Gidi N.
-- 2. Change atmSwchVPortCurrentLinkType and
--     atmSwchVPortConfigLinkType to include pnni10 enum		- Gidi N.
-- 3. Change atmSwchSlotRouteSlot to (1.255)				- Gidi N.
--
-- Version 1.0.2
-- 21 July 98
-- 1. Remove atmSwchPortIfIndexMap mib from atmSwchPort table
--     and change the order of other items in this table		- Gidi N.
--
-- Version 1.0.1
-- 2 April 98
-- 1. Move atmSwchSlotRouteNextId to atmSwch Slot Table.
-- 2. Change atmSwchSlotRouteStatus to atmSwchSlotRouteRowStatus
--     which uses the standard Row Status

-- Version 1.0.0
-- 22 March 98
-- 1. Base on Madge atmSwch MIB.
--
------------------------------------------------------------------------------
--
-- Overview :
--
-- The ATM switch MIB defines manageable objects used by the following 
-- devices -
--
--	Cajun M770 ATM Switch
--
-- The ATM switch MIB contains the following groups:
--
-- atmSwchBase	- This group contains basic device info.
--
-- atmSwchCpu	- This group contains information about the CPU module,
-- 			HW and SW status and versions, resources and statistics
-- 			concerning the CPU and memory.
--
-- atmSwchSlot	- This group contains information about a Slot in
--			the ATM Switch. 
--
-- atmSwchPort	- This group contains a table of port information.
--			Indexed on both PortIndex and SlotIndex, also gives IfTable
--			mappings.
--
-- atmSwchVPort	- This group contains a table of virtual port information.
--			Indexed on both VPortIndex, PortIndex and SlotIndex. 
--
-- atmSwchSlotRoute	- This group contains the ATM static routing table for
--				 a Slot.
--
-- atmSwchSlotAddrVcl - This 	group contains a table which maps Slot and ATM
-- 				Address to a Vcl. Based on  the standard atmAddrVclTable
--				with SlotIndex. 
-- 
------------------------------------------------------------------------------

ATMSWCH-MIB DEFINITIONS ::= BEGIN

IMPORTS
	OBJECT-TYPE				FROM RFC-1212
	Gauge32, TimeTicks, IpAddress		FROM SNMPv2-SMI
	DisplayString, RowStatus			FROM SNMPv2-TC
	lannet					FROM GEN-MIB;


-- useful types

	AtmAddress ::= OCTET STRING (SIZE(20))   
	AtmPrefix  ::= OCTET STRING (SIZE(13))


-- the ATM Switch MIB

-- The atmSwch MIB forms part of the general LANNET MIB as follows:
-- LANNET-MIB { iso org(3) dod(6) internet(1) private(4) enterprises(1) 81 }

	atmSwch         OBJECT IDENTIFIER ::= { lannet 33 }


-- groups in the ATM Switch MIB

	atmSwchBase		OBJECT IDENTIFIER ::= { atmSwch 1 }
	atmSwchCpu		OBJECT IDENTIFIER ::= { atmSwch 2 }
	atmSwchSlot		OBJECT IDENTIFIER ::= { atmSwch 5 }
	atmSwchPort		OBJECT IDENTIFIER ::= { atmSwch 6 }
	atmSwchVPort		OBJECT IDENTIFIER ::= { atmSwch 7 }
	atmSwchSlotRoute	OBJECT IDENTIFIER ::= { atmSwch 8 }
	atmSwchSlotAddrVcl	OBJECT IDENTIFIER ::= { atmSwch 9 }


--------------------------------------------------------------------------

-- the atmSwchBase group

atmSwchBaseCurrentPrefix OBJECT-TYPE
	SYNTAX  AtmPrefix
	ACCESS  read-only
	STATUS  mandatory
	DESCRIPTION
		"The ATM prefix currently in use for the switch."
	::= {atmSwchBase 1 }

atmSwchBaseConfigPrefix OBJECT-TYPE
	SYNTAX  AtmPrefix
	ACCESS  read-write
	STATUS  mandatory
	DESCRIPTION
		"The ATM prefix to be used at the next reboot."
	::= {atmSwchBase 2 }

atmSwchBaseEpdThreshold OBJECT-TYPE
	SYNTAX INTEGER (50..100)
	ACCESS read-write
	STATUS mandatory
	DESCRIPTION
		"The percentage of the maximum buffer allocation used in
		 the switch fabric before EPD is invoked. Default is 80%."
	::= { atmSwchBase 3 }

atmSwchBaseAmonAdminState OBJECT-TYPE
	SYNTAX INTEGER
		{
		on   (1),
		off  (2)
		}
	ACCESS  read-write
	STATUS  mandatory
	DESCRIPTION
	"This enable or disable the AMON statistics gathering
	in the switch. For Some applications, like Host Statistics,
	you also need to create a Control Table in order to start the
	statistics gathering"
	::= {atmSwchBase 4 }



-- the atmSwchCpu group

atmSwchCpuTable OBJECT-TYPE
	SYNTAX SEQUENCE OF AtmSwchCpuEntry
	ACCESS not-accessible
	STATUS mandatory
	DESCRIPTION
		" A table containing information about each CPU in the hub "
	::= { atmSwchCpu 1 }

atmSwchCpuEntry OBJECT-TYPE
	SYNTAX AtmSwchCpuEntry
	ACCESS not-accessible
	STATUS mandatory
	DESCRIPTION
		" An entry containing information about a particular 
		CPU in the hub "
	INDEX { atmSwchCpuIndex }
	::= { atmSwchCpuTable 1}

AtmSwchCpuEntry ::= SEQUENCE  
	{
	atmSwchCpuIndex		INTEGER,
	atmSwchCpuHwVersion	OCTET STRING,
	atmSwchCpuSoftErrCode	INTEGER,
	atmSwchCpuSoftErrString	DisplayString,
	atmSwchCpuUtilization	INTEGER,
	atmSwchCpuRamSize		Gauge32,
	atmSwchCpuRamUsed		Gauge32,
	atmSwchCpuFlashSize	Gauge32,
	atmSwchCpuFlashUsed	Gauge32,
	atmSwchCpuEepromSize	Gauge32,
	atmSwchCpuEepromUsed	Gauge32,
	atmSwchCpuTime		INTEGER,
	atmSwchCpuSysUpTime	TimeTicks,
	atmSwchCpuSvcPtPtInConns	INTEGER,
	atmSwchCpuSvcPtPtOutConns	INTEGER,
	atmSwchCpuSvcPtMptRootConns	INTEGER,
	atmSwchCpuSvcPtMptLeafConns	INTEGER,
	atmSwchCpuPvcPtPtConns		INTEGER

	}

atmSwchCpuIndex OBJECT-TYPE
	SYNTAX INTEGER
	ACCESS read-only
	STATUS mandatory
	DESCRIPTION
		"Index into this table."
	::= { atmSwchCpuEntry 1 }

atmSwchCpuHwVersion OBJECT-TYPE
	SYNTAX OCTET STRING (SIZE (3))
	ACCESS read-only
	STATUS mandatory
	DESCRIPTION
		"CPU Hardware version. Stored in the format :-
		first Byte - hardware major version number
			- hardware minor version number
		last Byte  - hardware debug version number."
	::= { atmSwchCpuEntry 2 }

atmSwchCpuSoftErrCode OBJECT-TYPE
	SYNTAX INTEGER
	ACCESS read-only
	STATUS mandatory
	DESCRIPTION
		" Software Error Code. This variable contain a copy of the error
		code of the last event to have a trap sent."
	::= { atmSwchCpuEntry 3 }

atmSwchCpuSoftErrString OBJECT-TYPE
	SYNTAX DisplayString (SIZE (0..128))
	ACCESS read-only
	STATUS mandatory
	DESCRIPTION
		" Software Error Description. This variable contain a copy of the
		error string of the last event to have a trap sent."
	::= { atmSwchCpuEntry 4 }


atmSwchCpuUtilization OBJECT-TYPE
	SYNTAX INTEGER (0..10000)
	ACCESS read-only
	STATUS mandatory
	DESCRIPTION
		"An estimate of the current CPU utilization in 
		one-hundredths of a percent."
	::= { atmSwchCpuEntry 5 }

atmSwchCpuRamSize OBJECT-TYPE
	SYNTAX Gauge32
	ACCESS read-only
	STATUS mandatory
	DESCRIPTION
		"DRAM plus SIMM size on the processor board, in bytes"
	::= { atmSwchCpuEntry 6 }

atmSwchCpuRamUsed OBJECT-TYPE
	SYNTAX Gauge32
	ACCESS read-only
	STATUS mandatory
	DESCRIPTION
		"An estimate of the amount of DRAM plus SIMM 
		currently in use, in bytes."
	::= { atmSwchCpuEntry 7 }

atmSwchCpuFlashSize OBJECT-TYPE
	SYNTAX Gauge32
	ACCESS read-only
	STATUS mandatory
	DESCRIPTION
		"Flash memory size, in bytes."
	::= { atmSwchCpuEntry 8 }

atmSwchCpuFlashUsed OBJECT-TYPE
	SYNTAX Gauge32
	ACCESS read-only
	STATUS mandatory
	DESCRIPTION
		"Flash memory used, in bytes."
	::= { atmSwchCpuEntry 9 }

atmSwchCpuEepromSize OBJECT-TYPE
	SYNTAX Gauge32
	ACCESS read-only
	STATUS mandatory
	DESCRIPTION
		"EEPROM memory size, in bytes."
	::= { atmSwchCpuEntry 10 }


atmSwchCpuEepromUsed OBJECT-TYPE
	SYNTAX Gauge32
	ACCESS read-only
	STATUS mandatory
	DESCRIPTION
		"EEPROM memory used, in bytes."
	::= { atmSwchCpuEntry 11 }


atmSwchCpuTime OBJECT-TYPE
	SYNTAX INTEGER
	ACCESS read-write		
	STATUS mandatory
	DESCRIPTION
		"Host time measured in seconds since midnight,
		 1st January, 1970."
	::= { atmSwchCpuEntry 12 }

atmSwchCpuSysUpTime OBJECT-TYPE
	SYNTAX TimeTicks
	ACCESS read-only		
	STATUS mandatory
	DESCRIPTION
		"The time (in hundredths of a second) since the
		network management portion of the module was last
		re-initialized.
		This is like the MIB-2 sysUpTime but for a specific module.
		In the Master Agent it should be equal to sysUpTime"
	::= { atmSwchCpuEntry 13 }

atmSwchCpuSvcPtPtInConns OBJECT-TYPE
	SYNTAX INTEGER (0..65535)
	ACCESS read-only
	STATUS mandatory
	DESCRIPTION
		"The number of switched virtual point to point 
		connections through this port, where this
		port is the point of entry for the call setup."
	::= { atmSwchCpuEntry 14 }

atmSwchCpuSvcPtPtOutConns OBJECT-TYPE
	SYNTAX INTEGER (0..65535)
	ACCESS read-only
	STATUS mandatory
	DESCRIPTION
		"The number of switched virtual point to point 
		connections through this port, where this
		port is the point of exit for the call setup."
	::= { atmSwchCpuEntry 15 }

atmSwchCpuSvcPtMptRootConns OBJECT-TYPE
	SYNTAX INTEGER (0..65535)
	ACCESS read-only
	STATUS mandatory
	DESCRIPTION
		"The number of switched virtual point to multipoint 
		connections through this port, where this
		port is the point of entry for the call setup."
	::= { atmSwchCpuEntry 16 }

atmSwchCpuSvcPtMptLeafConns OBJECT-TYPE
	SYNTAX INTEGER (0..65535)
	ACCESS read-only
	STATUS mandatory
	DESCRIPTION
		"The number of switched virtual point to multipoint 
		connections through this port, where this
		port is the point of exit for the call setup."
	::= { atmSwchCpuEntry 17 }

atmSwchCpuPvcPtPtConns OBJECT-TYPE
	SYNTAX INTEGER (0..65535)
	ACCESS read-only
	STATUS mandatory
	DESCRIPTION
		"The number of permanent virtual point to point 
		connections through this port."
	::= { atmSwchCpuEntry 18 }



-- the atmSwchSlot Group

atmSwchSlotTable OBJECT-TYPE
	SYNTAX SEQUENCE OF AtmSwchSlotEntry
	ACCESS not-accessible
	STATUS mandatory
	DESCRIPTION
		"A table containing information about each slot in 
		the switch."
	::= { atmSwchSlot 1 }

atmSwchSlotEntry OBJECT-TYPE
	SYNTAX AtmSwchSlotEntry
	ACCESS not-accessible
	STATUS mandatory
	DESCRIPTION
		"An entry containing information about a particular 
		slot in the switch."
	INDEX {atmSwchSlotIndex }
	::= { atmSwchSlotTable 1 }

AtmSwchSlotEntry ::= SEQUENCE
	{
	atmSwchSlotIndex			INTEGER,
	atmSwchSlotRxCellDiscards		INTEGER,
	atmSwchSlotRouteNextId			INTEGER,
	atmSwchSlotAPSMode			INTEGER,
	atmSwchSlotAPSCurrentState		INTEGER,
	atmSwchSlotAPSSwitchCommand		INTEGER,
	atmSwchSlotAPSSFBerThreshold		INTEGER,
	atmSwchSlotAPSSDBerThreshold		INTEGER,
	atmSwchSlotAPSDecision			INTEGER
	}

atmSwchSlotIndex OBJECT-TYPE
	SYNTAX INTEGER
	ACCESS read-only
	STATUS mandatory
	DESCRIPTION
	"Index into this table, by slot number."
	::= { atmSwchSlotEntry 1 }

atmSwchSlotRxCellDiscards OBJECT-TYPE
	SYNTAX INTEGER
	ACCESS read-only
	STATUS mandatory
	DESCRIPTION
		"cell discard counter for the Rx path (line to switch)."
	 ::= { atmSwchSlotEntry 2 }

atmSwchSlotRouteNextId OBJECT-TYPE
	SYNTAX  INTEGER
	ACCESS  read-only
	STATUS  mandatory
	DESCRIPTION
		"The next available Route index in this Slot.
		 The value of this object can be used as the index by the
		network manager to create an entry in the atmSwchSlotRouteTable."
	::= { atmSwchSlotEntry 3}

atmSwchSlotAPSMode OBJECT-TYPE
	SYNTAX INTEGER
		{
		uniDirectionalNonRevertive (1)
		}
	ACCESS read-only
	STATUS mandatory
	DESCRIPTION
	"The operation mode of APS.

              Uni-directional:
                  The uni-directional mode provides protection in
                  one direction.
              Non-revertive:
		    When the condition that caused a switch to the protection
                line has been cleared, a non-revertive system remains on the             
                Protection line until another switch request is received. "
	::= { atmSwchSlotEntry 4 }

atmSwchSlotAPSCurrentState  OBJECT-TYPE
	SYNTAX       INTEGER
		{
		noRequest(1),
		sf(2),
		sd(3),
		forcedSwitch(4),
		manualSwitch(5),
		doNotRevert(6),
		noAPS(7),
		notActive(8)
		}
	ACCESS read-only
	STATUS mandatory
	DESCRIPTION
	"Current state of APS. 

	Sd			A signal degrade condition is in effect.
	Sf			A signal failure condition is in effect.
	Forced switched		The current APS transmitting link is a result of a forced switched command
	Manual Switched		The current APS transmitting link is a result of a manual switched command.
	DoNotRevert		Working channel repaired.
	NoAPS			Protection line is not available.
	notActive		No available channels."
	::= { atmSwchSlotEntry 5 }

atmSwchSlotAPSSwitchCommand  OBJECT-TYPE
SYNTAX       INTEGER 
	{
	noCmd(1),
	clear(2),
	forcedSwitchWorkToProtect(3),
	forcedSwitchProtectToWork(4),
	manualSwitchWorkToProtect(5),
	manualSwitchProtectToWork(6)
	}
	ACCESS read-write
	STATUS mandatory
	DESCRIPTION
	"Allows the initiation of an APS switch command.
             The Switch command values are:
             noCmd(1)
              This value should be returned by a read request when no switch
              Command has been written to APS since the last Non-Volatile 
              Memory reset.  This value may not be used in a write operation.
             clear(2)
              Clears all of the switch commands listed below.
             forcedSwitchWorkToProtect(3)
              Switches from the working link to the protection link.
              This command has higher priority over the manual switch commands.
             forcedSwitchProtectToWork(5)
              Switches from the protection link to the working link.
	        This command has higher priority over the manual switch commands.
             manualSwitchWorkToProtect(6)
              Switches the working link to the protection link.
             manualSwitchProtectToWork(7)
              Switches from the protection link to the working link.

              When read this object returns the last command written
	        or noCmd(1) if no command has been written  since the last 
              Non-Volatile Memory reset. The return of the last command
	        written does not imply that this command is currently in effect.
	        This request may have been preempted by a higher priority
	        local or remote request. In order to determine the
	        current state of the APS group it is necessary to read
	        the object atmSwchSlotAPSCurrentState. "
	::= { atmSwchSlotEntry 6 }

atmSwchSlotAPSSFBerThreshold OBJECT-TYPE
	SYNTAX INTEGER (5..9) 
	ACCESS read-only
	STATUS mandatory
	DESCRIPTION
	"The Signal Failure Bit Error Rate.
      	The negated value of this number is used as the exponent of
             10 for computing the threshold value for the Bit Error Rate
             (BER). For example, a value of 5 indicates a BER threshold of
             10^-5.
              Default value is 5."
	::= { atmSwchSlotEntry 7 }

atmSwchSlotAPSSDBerThreshold OBJECT-TYPE
	SYNTAX INTEGER (5..9)
	ACCESS read-write
	STATUS mandatory
	DESCRIPTION
		"The Signal Degrade Bit Error Rate. 
             The negated value of this number is used as the exponent of
             10 for computing the threshold value for the Bit Error Rate
             (BER). For example, a value of 5 indicates a BER threshold of
             10^-5.
             Default value is 5. "
	::= { atmSwchSlotEntry 8 }

atmSwchSlotAPSDecision OBJECT-TYPE

	SYNTAX INTEGER 
		{
		working     (1),
		protection  (2),
		not-Active  (3)
		}
	ACCESS read-only
	STATUS mandatory
	DESCRIPTION
	" APS Decision.
              The receiving link can be either the working link 
              or the protection link. When both links are down,
              Not-active value is returned."
	::= { atmSwchSlotEntry 9 }


-- The atmSwchPort group

atmSwchPortTable OBJECT-TYPE
	SYNTAX SEQUENCE OF AtmSwchPortEntry
	ACCESS not-accessible
	STATUS mandatory
	DESCRIPTION
		"A table containing information about all the physical
		ports on the switch. Indexed on atmSwchSlotIndex and
		atmSwchPortIndex."
	::= { atmSwchPort 1 }

atmSwchPortEntry OBJECT-TYPE
	SYNTAX AtmSwchPortEntry
	ACCESS not-accessible
	STATUS mandatory
	DESCRIPTION
		"An entry containing information about a port on
		a particular card in the switch."
	INDEX {atmSwchSlotIndex , atmSwchPortIndex}
	::= { atmSwchPortTable 1 }

AtmSwchPortEntry ::= SEQUENCE
	{
	atmSwchPortIndex		INTEGER,
	atmSwchPortRootVportIndex	INTEGER,
	atmSwchPortNumVPorts		INTEGER,
	atmSwchPortPayloadScramble	INTEGER, 
	atmSwchPortPhysicalType		INTEGER,
	atmSwchPortMaxTxRate		INTEGER,
	atmSwchPortSvcPtPtInConns	INTEGER,
	atmSwchPortSvcPtPtOutConns	INTEGER,
	atmSwchPortSvcPtMptRootConns	INTEGER,
	atmSwchPortSvcPtMptLeafConns	INTEGER,
	atmSwchPortPvcPtPtConns	INTEGER,
	atmSwchPortPvcPtMptRootConns	INTEGER,
	atmSwchPortPvcPtMptLeafConns	INTEGER,
	atmSwchPortPvpPtPtConns	INTEGER,
	atmSwchPortPvpPtMptRootConns	INTEGER,
	atmSwchPortPvpPtMptLeafConns	INTEGER,
	atmSwchPortdsx3CellMaping	INTEGER
	}

atmSwchPortIndex OBJECT-TYPE
	SYNTAX INTEGER
	ACCESS read-only
	STATUS mandatory
	DESCRIPTION
		"The index of this port within the card."
	::= { atmSwchPortEntry 1 }

atmSwchPortRootVportIndex OBJECT-TYPE
	SYNTAX INTEGER
	ACCESS read-only
	STATUS mandatory
	DESCRIPTION
		"The index of the root vport in the vport table."
	::= { atmSwchPortEntry 2 }

atmSwchPortNumVPorts OBJECT-TYPE
	SYNTAX INTEGER
	ACCESS read-only
	STATUS mandatory
	DESCRIPTION
		"The count of the number of Vports on this physical
		port."
	::= { atmSwchPortEntry 3 }

atmSwchPortPayloadScramble OBJECT-TYPE
	SYNTAX INTEGER
		{
		on   (1),
		off  (2)
		}
	ACCESS read-write
	STATUS mandatory
	DESCRIPTION
		"Payload Scramble for a port."
	::= { atmSwchPortEntry 4 }

atmSwchPortPhysicalType OBJECT-TYPE
	SYNTAX INTEGER
		{
		sonet     (1),
		sdh       (2)
		}
	ACCESS read-write
	STATUS mandatory
	DESCRIPTION
		"This variable identifies whether a SONET or a 
		SDH signal is used across this interface."
	::= { atmSwchPortEntry 5 }

atmSwchPortMaxTxRate OBJECT-TYPE
	SYNTAX INTEGER
	ACCESS read-write
	STATUS mandatory
	DESCRIPTION
		"The Maximum transmit rate (in 1000bits per
		second) for that port."
	::= { atmSwchPortEntry 6 }	 

atmSwchPortSvcPtPtInConns OBJECT-TYPE
	SYNTAX INTEGER (0..65535)
	ACCESS read-only
	STATUS mandatory
	DESCRIPTION
		"The number of switched virtual point to point 
		connections through this port, where this
		port is the point of entry for the call setup."
	::= { atmSwchPortEntry 7 }

atmSwchPortSvcPtPtOutConns OBJECT-TYPE
	SYNTAX INTEGER (0..65535)
	ACCESS read-only
	STATUS mandatory
	DESCRIPTION
		"The number of switched virtual point to point 
		connections through this port, where this
		port is the point of exit for the call setup."
	::= { atmSwchPortEntry 8 }

atmSwchPortSvcPtMptRootConns OBJECT-TYPE
	SYNTAX INTEGER (0..65535)
	ACCESS read-only
	STATUS mandatory
	DESCRIPTION
		"The number of switched virtual point to multipoint 
		connections through this port, where this
		port is the point of entry for the call setup."
	::= { atmSwchPortEntry 9 }

atmSwchPortSvcPtMptLeafConns OBJECT-TYPE
	SYNTAX INTEGER (0..65535)
	ACCESS read-only
	STATUS mandatory
	DESCRIPTION
		"The number of switched virtual point to multipoint 
		connections through this port, where this
		port is the point of exit for the call setup."
	::= { atmSwchPortEntry 10 }

atmSwchPortPvcPtPtConns OBJECT-TYPE
	SYNTAX INTEGER (0..65535)
	ACCESS read-only
	STATUS mandatory
	DESCRIPTION
		"The number of permanent virtual point to point 
		connections through this port."
	::= { atmSwchPortEntry 11 }

atmSwchPortPvcPtMptRootConns OBJECT-TYPE
	SYNTAX INTEGER (0..65535)
	ACCESS read-only
	STATUS mandatory
	DESCRIPTION
		"The number of permanent virtual point to multipoint 
		connections through this port, where this
		port is the point of entry for the call setup."
	::= { atmSwchPortEntry 12 }

atmSwchPortPvcPtMptLeafConns OBJECT-TYPE
	SYNTAX INTEGER (0..65535)
	ACCESS read-only
	STATUS mandatory
	DESCRIPTION
		"The number of permanent virtual point to multipoint 
		connections through this port, where this
		port is the point of exit for the call setup."
	::= { atmSwchPortEntry 13 }

atmSwchPortPvpPtPtConns OBJECT-TYPE
	SYNTAX INTEGER (0..65535)
	ACCESS read-only
	STATUS mandatory
	DESCRIPTION
		"The number of permanent virtual point to point 
		path connections through this port."
	::= { atmSwchPortEntry 14 }

atmSwchPortPvpPtMptRootConns OBJECT-TYPE
	SYNTAX INTEGER (0..65535)
	ACCESS read-only
	STATUS mandatory
	DESCRIPTION
		"The number of permanent virtual point to multi-point 
		root path connections through this port."
	::= { atmSwchPortEntry 15 }

atmSwchPortPvpPtMptLeafConns OBJECT-TYPE
	SYNTAX INTEGER (0..65535)
	ACCESS read-only
	STATUS mandatory
	DESCRIPTION
		"The number of permanent virtual point to multi-point 
		leaf path connections through this port."
	::= { atmSwchPortEntry 16 }

atmSwchPortdsx3CellMaping  OBJECT-TYPE
	SYNTAX INTEGER
		{
		dsx3ADM(1),
		dsx3PLCP(2)
		}
	ACCESS read-write
	STATUS mandatory
	DESCRIPTION
		"This variable describes two different mapping schemes
		for transporting ATM cells over DS3 transmission
		systems: a PLCP-based system and a direct mapping
		system (ADM - Atm Direct Mapping).
		The two mappings are not compatible although both use
		DS3 as the underlying transmission system.
		Default value is ADM."
	::= { atmSwchPortEntry 17 }


-- The atmSwchVPort group

atmSwchVPortTable OBJECT-TYPE
	SYNTAX SEQUENCE OF AtmSwchVPortEntry
	ACCESS not-accessible
	STATUS mandatory
	DESCRIPTION
		"A table containing information about all the virtual
		ports on the switch. Indexed on atmSwchSlotIndex,
		atmSwchPortIndex and atmSwchVPortIndex."
	::= { atmSwchVPort 1 }

atmSwchVPortEntry OBJECT-TYPE
	SYNTAX AtmSwchVPortEntry
	ACCESS not-accessible
	STATUS mandatory
	DESCRIPTION
		"An entry containing information about a VPort on
		a particular card in a switch."
	INDEX {atmSwchSlotIndex , atmSwchPortIndex, atmSwchVPortIndex}
		::= { atmSwchVPortTable 1 }

AtmSwchVPortEntry ::= SEQUENCE
	{
	atmSwchVPortIndex				INTEGER,
	atmSwchVPortIsRoot			INTEGER,
	atmSwchVPortAdminStatus			INTEGER,
	atmSwchVPortOperStatus			INTEGER,
	atmSwchVPortCurrentSignallingState	INTEGER,
	atmSwchVPortCurrentILMIState		INTEGER,
	atmSwchVPortCurrentAddrRegEn		INTEGER,
	atmSwchVPortCurrentLinkType		INTEGER,
	atmSwchVPortCurrentTermType		INTEGER,
	atmSwchVPortConfigILMIState		INTEGER,
	atmSwchVPortConfigAddrRegEn		INTEGER,
	atmSwchVPortConfigLinkType		INTEGER,
	atmSwchVPortConfigTermType		INTEGER,
	atmSwchVPortNeighbourSysName		DisplayString,
	atmSwchVPortNeighbourUNIVersion	INTEGER,
	atmSwchVPortNeighbourATMAddress	AtmAddress,
	atmSwchVPortNeighbourIfName		DisplayString,
	atmSwchVPortMibProbe			INTEGER,
	atmSwchVPortConfMinSvccVci		INTEGER,
	atmSwchVPortConfMaxSvccVci		INTEGER,
	atmSwchVPortConfMinVpi 			INTEGER, 
	atmSwchVPortConfMaxVpi 			INTEGER,
	atmSwchVPortNeighbourIpAddress	IpAddress,
	atmSwchVPortPcr 				INTEGER,
	atmSwchVPortRowStatus 			RowStatus
	}

atmSwchVPortIndex OBJECT-TYPE
	SYNTAX INTEGER
	ACCESS read-only
	STATUS mandatory
	DESCRIPTION
		"The index of this vport within the card/port.
		This is defined as being the vport identifier + 1."
	::= { atmSwchVPortEntry 1 }

atmSwchVPortIsRoot OBJECT-TYPE
	SYNTAX INTEGER
		{
		isRoot     (1),
		notRoot    (2)
		}
	ACCESS read-only
	STATUS mandatory
	DESCRIPTION
		"Indicates whether this Vport is the root vport on a
		given physical port."
	::= { atmSwchVPortEntry 2 }

atmSwchVPortAdminStatus OBJECT-TYPE
	SYNTAX INTEGER
		{
		enable     (1),
		disable    (2)
		}
	ACCESS read-write
	STATUS mandatory
	DESCRIPTION
		"The admin state of this interface. Note that an
		interface must be down in order to change the
		configuration of that interface."
	::= { atmSwchVPortEntry 3 }

atmSwchVPortOperStatus OBJECT-TYPE
	SYNTAX INTEGER
		{
		up     (1),
		down   (2)
		}
	ACCESS read-only
	STATUS mandatory
	DESCRIPTION
		"The operational state of this interface. Note that an
		interface must be down in order to change the
		configuration of that interface."
		::= { atmSwchVPortEntry 4 }

atmSwchVPortCurrentSignallingState OBJECT-TYPE
	SYNTAX INTEGER
		{
		unknown     (1),
		up          (2),
		down        (3)
		}
	ACCESS read-only
	STATUS mandatory
	DESCRIPTION
		"The state of the signalling stack for this interface."
                ::= { atmSwchVPortEntry 5 }

atmSwchVPortCurrentILMIState OBJECT-TYPE
	SYNTAX INTEGER
		{
		up       (1),
		down     (2),
		stackOff (3)
		}
	ACCESS read-only
	STATUS mandatory
	DESCRIPTION
		"The current state of the ILMI link for this port. 
		stack_off means the ILMI link is up but the protocol
		stack that retrieves neighbor information is off."
	::= { atmSwchVPortEntry 6 }

atmSwchVPortCurrentAddrRegEn OBJECT-TYPE
	SYNTAX INTEGER
		{
		unknown     (1),
		enabled     (2),
		disabled    (3)
		}
	ACCESS read-only
	STATUS mandatory
	DESCRIPTION
		"Indicates whether address registration is enabled
		on this interface."
	::= { atmSwchVPortEntry 7 }

atmSwchVPortCurrentLinkType OBJECT-TYPE
	SYNTAX INTEGER
		{
		unknown    (1),
		uni30      (2),
		uni31      (3),
		iisp30     (4),
		iisp31     (5),
		pnni10     (6),
		uni40     (7)
		}
	ACCESS read-only
	STATUS mandatory
	DESCRIPTION
		"The type of signalling used on this interface."
	::= { atmSwchVPortEntry 8 }

atmSwchVPortCurrentTermType OBJECT-TYPE
	SYNTAX INTEGER
		{
		unknown     (1),
		user        (2),
		network     (3)
		}
	ACCESS read-only
	STATUS mandatory
	DESCRIPTION
		"The type of link termination currently in use at
		this interface."
	::= { atmSwchVPortEntry 9 }

atmSwchVPortConfigILMIState OBJECT-TYPE
	SYNTAX INTEGER
		{
		stackEnabled  (1),
		stackDisabled (2)
		}
	ACCESS read-write
	STATUS mandatory
	DESCRIPTION
		"The configured state of the ILMI protocol stack."
	::= { atmSwchVPortEntry 10 }

atmSwchVPortConfigAddrRegEn OBJECT-TYPE
	SYNTAX INTEGER
		{
		automatic   (1),
		enabled     (2),
		disabled    (3)
		}
	ACCESS read-write
	STATUS mandatory
	DESCRIPTION
		"Indicates whether address registration is to be
		performed on this interface."
	::= { atmSwchVPortEntry 11 }

atmSwchVPortConfigLinkType OBJECT-TYPE
	SYNTAX INTEGER
		{
		automatic  (1),
		unknown    (2),
		uni30      (3),
		uni31      (4),
		iisp30     (5),
		iisp31     (6),
		pnni10     (7),
		uni40     (8)
		}
	ACCESS read-write
	STATUS mandatory
	DESCRIPTION
		"The configured type of signalling used on this 
		interface. Attempts to set the unknown state will
		be rejected."
	::= { atmSwchVPortEntry 12 }

atmSwchVPortConfigTermType OBJECT-TYPE
	SYNTAX INTEGER
		{
		automatic   (1),
		user        (2),
		network     (3)
		}
	ACCESS read-write
	STATUS mandatory
	DESCRIPTION
		"The type of link termination configured for use at
		this interface."
                ::= { atmSwchVPortEntry 13 }

atmSwchVPortNeighbourSysName OBJECT-TYPE
	SYNTAX DisplayString (SIZE (0..32))
	ACCESS read-only
	STATUS mandatory
	DESCRIPTION
		"The sysName for the device at the remote end of
		the link to this interface."
	::= { atmSwchVPortEntry 14 }

atmSwchVPortNeighbourUNIVersion OBJECT-TYPE
	SYNTAX INTEGER
		{
		notKnown	(1),
		uni30		(2),
		uni31		(3),
		uni40		(4),
		iisp		(5),
		pnni10	(6)
		}
	ACCESS read-only
	STATUS mandatory
	DESCRIPTION
	"The highest version of stack type usable by the interface 
	at the remote end of the link to this interface."
	::= { atmSwchVPortEntry 15 }

atmSwchVPortNeighbourATMAddress OBJECT-TYPE
	SYNTAX AtmAddress
	ACCESS read-only
	STATUS mandatory
	DESCRIPTION
		"The ifPhysAddress used by the interface at the 
		remote end of the link to this interface."
	::= { atmSwchVPortEntry 16 }

atmSwchVPortNeighbourIfName OBJECT-TYPE
	SYNTAX DisplayString
	ACCESS read-only
	STATUS mandatory
	DESCRIPTION
		"The ifName used by the interface at the 
		remote end of the link to this interface."
	::= { atmSwchVPortEntry 17 }

atmSwchVPortMibProbe OBJECT-TYPE
	SYNTAX INTEGER
		{
		on   (1),
		off  (2)
		}
	ACCESS read-write
	STATUS mandatory
	DESCRIPTION
		"Whether the ability to find out proprietary
		features via the probe MIB (ILMI extensions)
		is switched on or off."
	::= { atmSwchVPortEntry 18 }

atmSwchVPortConfMinSvccVci    OBJECT-TYPE
	SYNTAX             INTEGER  (0..65535)
	ACCESS             read-write
	STATUS             mandatory
	DESCRIPTION
		"The minimum VCI that the signalling stack on
		the vport is configured to support for allocation
		to switched virtual channel connections."
	::= { atmSwchVPortEntry 19 }

atmSwchVPortConfMaxSvccVci    OBJECT-TYPE
	SYNTAX             INTEGER  (0..65535)
	ACCESS             read-write
	STATUS             mandatory
	DESCRIPTION
		"The maximum VCI that the signalling stack on
		the vport is configured to support for
		allocation to switched virtual channel connections."
	::= { atmSwchVPortEntry 20 }


atmSwchVPortConfMinVpi        OBJECT-TYPE
	SYNTAX             INTEGER  (0..4095)
	ACCESS             read-write
	STATUS             mandatory
	DESCRIPTION
		"The minimum VPI available for use by any connection
		on this virtual port.
		Curently, this is always 0 for the root vport, while 
		non-root vports take a value greater than the MaxVpi 
		of the root vport. 
		For Non-root vports MinVpi==MaxVpi."
	::= { atmSwchVPortEntry 21 }

atmSwchVPortConfMaxVpi        OBJECT-TYPE
	SYNTAX             INTEGER  (0..4095)
	ACCESS             read-write
	STATUS             mandatory
	DESCRIPTION
		"The maximum VPI available for use by any connection
		on this virtual port. Curently possible values are:
		0, 1, 3 and 7,
		For Non-root vports MinVpi==MaxVpi."
	::= { atmSwchVPortEntry 22 }


atmSwchVPortNeighbourIpAddress OBJECT-TYPE
	SYNTAX IpAddress 
	ACCESS read-only
	STATUS mandatory
	DESCRIPTION
		"The IP address used by the interface at the 
		remote end of the link to this interface."
	::= { atmSwchVPortEntry 23 }


atmSwchVPortPcr OBJECT-TYPE
	SYNTAX INTEGER
	ACCESS read-write
	STATUS mandatory
	DESCRIPTION
		"The Peak Cell Rate (in 1000bits per second)
		for that Vport. Available only for non-root Vports.
		The root-vport will always return the value of 0"
	::= { atmSwchVPortEntry 24 }	 


atmSwchVPortRowStatus OBJECT-TYPE
	SYNTAX RowStatus
	ACCESS read-write

	STATUS mandatory
	DESCRIPTION
	"This object is used to create, delete or modify a row in this table.
	To create a new Vport, this object is initially set to 'createAndWait'
	or 'createAndGo'. This object should not be set to 'active' unless
	the following columnar objects have been set to their desired value
	in this row:
	atmSwchVPortIndex  with the value of vport identifier + 1.
	The root Vport always exists and cannot be deleted
	atmSwchVPortConfMinVpi  = atmSwchVPortConfMaxVpi with
	the VPI value associated with the Vport.
	This VPI should be not be used by other Vports."
	::= { atmSwchVPortEntry 25 }




-- the atmSwchSlotRoute group  based on  the atmSwchRoute group with SlotIndex


atmSwchSlotRouteTable OBJECT-TYPE
	SYNTAX  SEQUENCE OF AtmSwchSlotRouteEntry
	ACCESS  not-accessible
	STATUS  mandatory
	DESCRIPTION
		"a list of ATM routing table addresses"
	::= { atmSwchSlotRoute 1}

atmSwchSlotRouteEntry  OBJECT-TYPE
	SYNTAX  AtmSwchSlotRouteEntry
	ACCESS  not-accessible
	STATUS  mandatory
	DESCRIPTION
		"ATM address routing entry: ATM Address to Port"
	INDEX   { atmSwchSlotIndex, atmSwchSlotRouteId }
	 ::= {atmSwchSlotRouteTable 1}

AtmSwchSlotRouteEntry ::= SEQUENCE
	{
	atmSwchSlotRouteId		INTEGER,
	atmSwchSlotRouteRowStatus	RowStatus,
	atmSwchSlotRouteAddressPrefix	AtmAddress,
	atmSwchSlotRoutePrefixLength	INTEGER,
	atmSwchSlotRoutePriority		INTEGER,
	atmSwchSlotRouteSlot		INTEGER,
	atmSwchSlotRoutePort		INTEGER,
	atmSwchSlotRouteVport		INTEGER,
	atmSwchSlotRouteOrigin		INTEGER,
	atmSwchSlotRouteOperStatus	INTEGER
	}

atmSwchSlotRouteId     OBJECT-TYPE
	SYNTAX  INTEGER
	ACCESS  read-only
	STATUS  mandatory
	DESCRIPTION
		"Unique identifier for this row.
		This value will always match the OID leaf value."
	 ::= {atmSwchSlotRouteEntry 1}

atmSwchSlotRouteRowStatus OBJECT-TYPE
	SYNTAX  RowStatus
	ACCESS  read-write
	STATUS  mandatory
	DESCRIPTION
		"This objest is used to create or delete entries in the
		atmSwchSlotRouteTable. See Textual Convention in RFC 1903.
		Next available index is: atmSwchSlotRouteNextId 
		active (1),
		notInService (2),
		notReady (3),
		createAndGo (4) - not supported tbd,
		createAndWait (5)
		destroy (6)
		"
	::= {atmSwchSlotRouteEntry 2}

atmSwchSlotRouteAddressPrefix  OBJECT-TYPE
	SYNTAX  AtmAddress
	ACCESS  read-write
	STATUS  mandatory
	DESCRIPTION
		"The ATM address to be used for routing."
	::= {atmSwchSlotRouteEntry 3}

atmSwchSlotRoutePrefixLength   OBJECT-TYPE
	SYNTAX  INTEGER (0..152)
	ACCESS  read-write
	STATUS  mandatory
	DESCRIPTION
		"The number of bits used in the Address Prefix"
	::= {atmSwchSlotRouteEntry 4}

atmSwchSlotRoutePriority       OBJECT-TYPE
	SYNTAX  INTEGER (0..999)
	ACCESS  read-write
	STATUS  mandatory
	DESCRIPTION
		"The priority of this route entry (not used at this time)"
	::= {atmSwchSlotRouteEntry 5}

atmSwchSlotRouteSlot   OBJECT-TYPE
	SYNTAX  INTEGER (1..255)
	ACCESS  read-write
	STATUS  mandatory
	DESCRIPTION
		"Identifier for the slot used by the route"
	::= {atmSwchSlotRouteEntry 6}

atmSwchSlotRoutePort   OBJECT-TYPE
	SYNTAX  INTEGER (1..255)
	ACCESS  read-write
	STATUS  mandatory
	DESCRIPTION
		"Identifier for the port on the above slot to be
		used by the route"
	::= {atmSwchSlotRouteEntry 7}

atmSwchSlotRouteVport  OBJECT-TYPE
	SYNTAX  INTEGER (0..255)
	ACCESS  read-write
	STATUS  mandatory
	DESCRIPTION
		"Identifier for the virtual port on the above port
		 to be used by the route."
	::= {atmSwchSlotRouteEntry 8}

atmSwchSlotRouteOrigin OBJECT-TYPE
	SYNTAX  INTEGER
	{ 
		nonVolatile    (1),
		snmp           (2),
		ilmi           (3),
		lane           (4),
		dynamic        (5)
	}
	ACCESS  read-only
	STATUS  mandatory
	DESCRIPTION
		"Indicates origin of route"
	::= {atmSwchSlotRouteEntry 9}

		
atmSwchSlotRouteOperStatus OBJECT-TYPE
	SYNTAX  INTEGER
		{
		 up              (1),
		 down            (2)
		}
	ACCESS  read-only
	STATUS  mandatory
	DESCRIPTION
		"Indication of route's operational status"
	::= {atmSwchSlotRouteEntry 10}



-- the atmSwchSlotAddrVcl table: Slot/ATM Address to VPI/VCI Mapping Table
--
-- This table provides an alternative way to access
-- a row in the atmVclAddrTable by using
-- a slot number and an ATM address as an index, instead of
-- the ifIndex.
-- Based on  the standard atmAddrVclTable with SlotIndex

atmSwchSlotAddrVclTable   OBJECT-TYPE
	SYNTAX       SEQUENCE OF AtmSwchSlotAddrVclEntry
	ACCESS   not-accessible
	STATUS       mandatory
	DESCRIPTION
		"This table provides an alternative way to
		retrieve the atmVclTable.  This table can be used
		to retrieve the indexing to the atmVclTable by an
		ATM address.
		Based on  the standard atmAddrVclTable with a SlotIndex."
	::= { atmSwchSlotAddrVcl 1 }

atmSwchSlotAddrVclEntry    OBJECT-TYPE
	SYNTAX       AtmSwchSlotAddrVclEntry
	ACCESS   not-accessible
	STATUS       mandatory
	DESCRIPTION
		"Each entry in this table represents an entry in
		the atmVclTable of the ATM-MIB by its ATM
		address.  The ATM address is either the calling or
		called party ATM address of the call.  Entries in
		this table are read only.  They show up when
		entries are created in the atmVclAddrTable."
	INDEX { atmSwchSlotIndex, atmSwchSlotAddrVclAddr,
		atmSwchSlotAddrVclAtmIfIndex,
		atmSwchSlotAddrVclVpi, atmSwchSlotAddrVclVci }
	::= { atmSwchSlotAddrVclTable 1 }

AtmSwchSlotAddrVclEntry ::=
	SEQUENCE {
		atmSwchSlotAddrVclAddr	AtmAddress,	
		atmSwchSlotAddrVclAtmIfIndex    INTEGER,
		atmSwchSlotAddrVclVpi           INTEGER,
		atmSwchSlotAddrVclVci           INTEGER,
		atmSwchSlotAddrVclAddrType      INTEGER
		}

atmSwchSlotAddrVclAddr OBJECT-TYPE
	SYNTAX     AtmAddress
	ACCESS 	read-only
	STATUS	mandatory
	DESCRIPTION
		"An ATM address on one end of the VCL."
	::= { atmSwchSlotAddrVclEntry 1 } 

atmSwchSlotAddrVclAtmIfIndex     OBJECT-TYPE
	SYNTAX	INTEGER
	ACCESS	read-only 
	STATUS	mandatory
	DESCRIPTION
		"The interface index of the ATM interface to which
		this VCL pertains.  This object combined with the
		atmAddrVclVpi and atmAddrVclVci objects serves as
		an index to the atmVclTable."
	::= { atmSwchSlotAddrVclEntry 2 }

atmSwchSlotAddrVclVpi     OBJECT-TYPE
	SYNTAX	INTEGER (0..4095)
	ACCESS	read-only
	STATUS	mandatory
	DESCRIPTION
		"The VPI value of the VCL.  This object combined
		with the atmAddrVclAtmIfIndex and atmAddrVclVci
		objects serves as an index to the atmVclTable."
	::= { atmSwchSlotAddrVclEntry 3 }

atmSwchSlotAddrVclVci     OBJECT-TYPE
	SYNTAX	INTEGER (0..65535)
	ACCESS	read-only 
	STATUS	mandatory
	DESCRIPTION
		"The VCI value of the VCL.  This object combined
		with the atmAddrVclAtmIfIndex and atmAddrVclVpi
		objects serves as an index to the atmVclTable."
	::= { atmSwchSlotAddrVclEntry 4 }

atmSwchSlotAddrVclAddrType     OBJECT-TYPE
	SYNTAX	INTEGER {
			callingParty(1),
			calledParty(2) }
	ACCESS	read-only
	STATUS	mandatory
	DESCRIPTION
		"The type of ATM Address represented by the object
		atmVclAddrAddr.  Choices are either calling party
		address or called party address."
	::= { atmSwchSlotAddrVclEntry 5 }

END
