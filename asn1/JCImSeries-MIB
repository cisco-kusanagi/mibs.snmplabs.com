-- **************************************************************************
-- *            SNMP Private MIB  
-- *
-- *   Copyright(c) - Johnson Controls, Inc, 2001
-- *   Use or copying of all or any part of the document, except as
-- *   permitted by the License Agreement is prohibited.
-- * 
-- * 
-- *   
-- *
-- *            
-- * HISTORY
-- * Date      Name     Rel    EC/PT#  Task# Reason for change
-- * _________ _______ _______ ______ _________________________________
-- * 01 APR 18 kehossm  1.00                 Develop Prototype  Use function prototypes from rtos_ex.h
-- * 01 JUL 13 perryt   1.00          23461  Update for SNMP v2.0 and
-- *                                         add condition related Bacnet traps 
-- * 01 JUL 16 kehossm  1.00          23463  update trap descriptions   
-- * 01 JUL 25 perryt	1.00          23708  Update attribute names, change parent of
-- *                                         n1 and bacnet traps, split mib
-- * 01 Aug 01 perryt   1.00          23570  Modify attributes
-- * 01 Aug 17 perryt	1.00          24008  Update order of objects within traps, change
-- *                                         spelling of attribute, remove/add attributes
-- * 01 Aug 29 perryt   1.00   113689 24098  Remove transactiontype attribute from traps
-- * 01 Sep 07 kehossm  1.00                 Update traps based on comments from Travellers:
-- *                                           put common OIDs first into trap
-- *                                           fix transaction user descriptor
-- * 01 Sep 28 perryt   1.00   114135 24365  Change syntax of opcchangemask from integer to string
-- *                                         Reorder Bacnet attributes
-- * 01 Oct 04 kehossm  1.00                 Update from walkthrough comments
-- *                                            Add ActorID for n1 and include only
-- *                                            Create new branch for OPC Standard Traps 
-- * 01 Oct 25 perryt	1.00          24766  Replace opcChangeMask to opcChangeMaskText within Traps                                           
-- **************************************************************************

JCImSeries-MIB  DEFINITIONS ::= BEGIN


IMPORTS
    OBJECT-TYPE,                         -- FROM RFC-1212 
--    mib-2, 
    Integer32,
    NOTIFICATION-TYPE,
    MODULE-IDENTITY                      FROM SNMPv2-SMI
--    PhysAddress,
    DisplayString                        FROM SNMPv2-TC                            
--    ifTable                    
    ifIndex                              FROM RFC1213-MIB
    mSeries                              FROM JCIControlsGroup-MIB;  


-- This is our private MIB 
-- johnsonControlsInc      OBJECT IDENTIFIER ::= { enterprises(4399) }

-- Johnson Controls module identity

jcimSeriesMIB MODULE-IDENTITY
    LAST-UPDATED "0110251448Z"    --Oct. 25, 2001 at 14:48
    ORGANIZATION "Johnson Controls"
    CONTACT-INFO
            "       Mary Kehoss
            Postal: Johnson Controls, Inc.
                    507 East Michigan Street
                    Milwaukee, WI  53201
                    US

               Fax: +1 414-524-4400
             Email: mary.e.kehoss@jci.com"
    DESCRIPTION
            "This MIB module describes all attributes included in 
             traps created from Metasys OPC Event Data."
    ::= { mSeries 1 }
    
-- This node contains all the stuff related to our JohnsonControls software

-- In this node we will store the data types used by our johnsonControls-Traps
opcTypes                   OBJECT IDENTIFIER ::= { mSeries 2 }

-- This node contains the traps fired off by our Building-Manager
opcTraps                   OBJECT IDENTIFIER ::= { mSeries 3 }

--This node contains N1 traps      
opcN1Traps                 OBJECT IDENTIFIER ::= { opcTraps 1 }

--This node contains Bacnet traps
opcBacnetTraps             OBJECT IDENTIFIER ::= { opcTraps 2 }

opcStandardTraps           OBJECT IDENTIFIER ::= {opcTraps 3 }

-- **************************************************************************
-- *                                                                       
-- *    Data-Types of OPC-Events                                                        
-- *    This is the list of data types used by traps representing OPC-Events.
-- *      Start with the most common attributes.
-- *                                                                        
-- **************************************************************************

-- =================================================================
-- The following standard attributes apply to all OPC messages
-- =================================================================

--
-- opcSeverity
-- ===========
--
-- How urgent is the event ?
--
opcSeverity   OBJECT-TYPE
             SYNTAX          INTEGER (0..1000)
             MAX-ACCESS      read-only
             STATUS          current
             DESCRIPTION
        "Indicates the severity of the OPCEvent represented by the trap where a
         values of 1-333 are low, 334-666 are medium and 667-1000 are high."
             ::= { opcTypes 1 }

--
-- opcSource
-- =========
--
-- The name of the device or system that has generated this event.
--
opcSource OBJECT-TYPE
             SYNTAX           DisplayString
             MAX-ACCESS      read-only
             STATUS           current
             DESCRIPTION
                 "The name of the device or system that has sent the event."
             ::= { opcTypes 2 }


--
-- opcTimeStamp
-- ============
--
-- The UTC time this event has occured.
--
opcTimeStamp   OBJECT-TYPE
             SYNTAX          DisplayString
             MAX-ACCESS      read-only
             STATUS          current
             DESCRIPTION
                 "A string identifying the time the OPC-Event has occured. Note that
                        the time is given as UTC-time."
             ::= { opcTypes 3 }


--
-- opcMessage
-- ==========
--
-- Describes the event.
--
opcMessage OBJECT-TYPE
             SYNTAX           DisplayString
             MAX-ACCESS      read-only
             STATUS           current
             DESCRIPTION
                 "A string that contains further information about the event.
                  Often this string is used to specify the action that the operator
                  should take."
             ::= { opcTypes 4 }


--
-- opcEventCategory
-- ================
--
-- The name of the category this event belongs to
--
opcEventCategory OBJECT-TYPE
             SYNTAX           DisplayString
             MAX-ACCESS      read-only
             STATUS           current
             DESCRIPTION
                 "Describes the category this event belongs, for example, Fire or General."
             ::= { opcTypes 5 }

opcEventCategoryText OBJECT-TYPE
             SYNTAX           DisplayString
             MAX-ACCESS      read-only
             STATUS           current
             DESCRIPTION
                 "Describes the category this event belongs, for example, Fire or General."
             ::= { opcTypes 6 }


--
-- opcEventType
-- ============
--
-- Tells us about the type of event. You have simple events, tracking event (caused by operators changing
-- some settings) and condition-related events (which are often alarms).
--

-- the raw event-type number as specified in the OPC AE spec.
opcEventType   OBJECT-TYPE
             SYNTAX          INTEGER {
                                        simpleEvent(1),
                                        trackingEvent(2),
                                        conditionEvent(4) -- or should we call it alarm-event ?
                                        }
             MAX-ACCESS      read-only
             STATUS          current
             DESCRIPTION
                 "Indicates the type of OPC-Event represented by the trap."
             ::= { opcTypes  7}

-- this attribute is for display purpose
opcEventTypeText   OBJECT-TYPE
             SYNTAX          DisplayString
             MAX-ACCESS      read-only
             STATUS          current
             DESCRIPTION
                 "The same as opcEventType except that it will return a humand readable text
                  describing the type of the event. The possible event types are: 
                  Conditional, Simple or Tracking-Event."
             ::= { opcTypes 8 }



-- =================================================================
-- The following standard attributes apply to Conditional Traps
-- =================================================================

--
-- opcConditionName
-- ============
--
-- The name of the active sub-condition for conditional reports.
--


opcCondition OBJECT-TYPE
             SYNTAX          DisplayString
             MAX-ACCESS      read-only
             STATUS          current
             DESCRIPTION
                 "Indicates the condition type of the OPCEvent represented by the trap, for
                  example, Alarm or Normal."
             ::= { opcTypes 20 }


--
-- opcSubConditionName
-- ============
--
-- The name of the active sub-condition for conditional reports.
--

opcSubCondition OBJECT-TYPE
            SYNTAX          DisplayString
             MAX-ACCESS      read-only
             STATUS          current
             DESCRIPTION
                 "Indicates the subcondition status of the OPCEvent represented by the trap,
                   for example, a subcondition of an alarm is low alarm."
             ::= { opcTypes 21 }
--
-- ActiveTime
-- ==========
-- 
-- The time this alarms became active.
--
opcActiveTime   OBJECT-TYPE
             SYNTAX          DisplayString
             MAX-ACCESS      read-only
             STATUS          current
             DESCRIPTION
                 "Shows the UTC-time this event became active."
             ::= { opcTypes 22 }

--
-- Quality
-- =======
--
-- This attribute indicates the quality of the data the alarm is based upon. For example if the controller
-- which reported the alarm reports offline, the quality will become bad...
--

-- the raw event category ID
opcQuality OBJECT-TYPE
             SYNTAX          INTEGER (0..255)
             MAX-ACCESS      read-only
             STATUS          current
             DESCRIPTION
                 "The raw value of the OPC-quality according to the OPC DA specificatoin."
             ::= { opcTypes 23 }

-- this attribute is for display purpose
opcQualityText OBJECT-TYPE
             SYNTAX          DisplayString
             MAX-ACCESS      read-only
             STATUS          current
             DESCRIPTION
                 "The same as opcQuality except that it contains a human readable text."
             ::= { opcTypes 24 }

--
-- NewState attribute
-- ==================
--
-- This information tells the user the new state of the alarm (e.g. if the alarm is active, has
-- been acknowledged). This is also very specialized information. It is only added to be complete.
--
opcNewState   OBJECT-TYPE
             SYNTAX          INTEGER {
                                        opcConditionEnabled(1), -- indicates if the OPC server will check for this alarm
                                        opcConditionActive(2),  -- set if the condition is active
                                        opcConditionAcked(4)    -- set if the condition is acknowledged
                                        }
             MAX-ACCESS      read-only
             STATUS          current
             DESCRIPTION
                 "Indicates the new state of the alarm."
             ::= { opcTypes 25 }

opcNewStateText   OBJECT-TYPE
             SYNTAX          DisplayString  -- 1 = ENA, 2= ACK, 3=ENAACT, 5= ACK 
             MAX-ACCESS      read-only
             STATUS          current
             DESCRIPTION
                 "Indicates the new state of the alarm."
             ::= { opcTypes 26 }

--
-- AckRequired
-- ===========
-- 
-- Indicates whether this alarm needs to be acknowledged.
--
opcAckRequired   OBJECT-TYPE
             SYNTAX          INTEGER (0..1)
             MAX-ACCESS      read-only
             STATUS          current
             DESCRIPTION
                 "Indicates whether this alarm has to be acknowledged or not."
             ::= { opcTypes 27 }

opcAckRequiredText   OBJECT-TYPE
             SYNTAX          DisplayString
             MAX-ACCESS      read-only
             STATUS          current
             DESCRIPTION
                 "Outputs ACKNOWLEDGE REQUIRED if integer value is 1."
             ::= { opcTypes 28 }


--
-- Cookie
-- ======
-- 
-- A unique ID identifying this event. This is required to support acknowledge. 
-- SNMP does not currently support acknowledgement.  Therefore, this attribute
-- will not be include in traps.
--
opcCookie    OBJECT-TYPE
             SYNTAX          Integer32
             MAX-ACCESS      read-only
             STATUS          current
             DESCRIPTION
                 "A unique ID for this event, normally for internal use only."
             ::= { opcTypes 29 }

--
-- changeMask
-- ==========
--
-- This is very specialized information that is not useful for the "normal" user.

opcChangeMask   OBJECT-TYPE
     SYNTAX INTEGER (0..512)
     MAX-ACCESS      read-only
     STATUS          current
     DESCRIPTION
                 "A set of bit flags indicating which properties of the alarm or event have changed:
      Bit 0 set = active state of the alarm.
      Bit 1 set = alarm has been acknowledged.
      Bit 2 set = alarm condition has been enabled or disabled.
      Bit 4 set = the quality of the data the alarm is based upon, has changed.
      Bit 5 set = the severity of the alarm has changed.
      Bit 6 set = the alarm has changed to another subcondition.
      Bit 7 set = the alarm message has changed.
      Bit 8 set = an attribute of the alarm has changed."
             ::= { opcTypes 32 }

opcChangeMaskText   OBJECT-TYPE

     SYNTAX DisplayString
     MAX-ACCESS      read-only
     STATUS          current
     DESCRIPTION
                 "A list of properties of the alarm or event have changed  For example, 
                  the event has become inactive and acknowledged."
             ::= { opcTypes 30 }


---
--- The following attributes apply only to both Condition and Tracking Traps
---

--
-- opcActorID
-- ==========
--
-- For Conditional events, the name of the operator (or software) that has acknowledged the 
-- alarm and is now responsible to take the appropiate actions.
-- For tracking events, the name of the opearator who specified the change.
--
opcActorID OBJECT-TYPE
             SYNTAX          DisplayString
             MAX-ACCESS      read-only
             STATUS          current
             DESCRIPTION
                 "For conditional events, this is the operator or software
                  that has acknowledged the event.  
                  For tracking events, this is the actor ID."
             ::= { opcTypes 31 }


--
-- =================================================================
-- The following attributes apply only all Metasys Traps
-- =================================================================
--

--
-- originalDate
-- ==========
-- Date in the format of the original Metasys Report, for exmaple, MM/DD/YYYY.  
-- The format will follow the currently defined windows format.

originalDate OBJECT-TYPE
             SYNTAX          DisplayString
             MAX-ACCESS      read-only
             STATUS          current
             DESCRIPTION
                 "Identifies the date of the original event."
             ::= { opcTypes 40 }

--
-- originalTime
-- ==========
-- Time in the format of the original Metasys Report.
-- The format will follow the currently defined windows format.

originalTime OBJECT-TYPE
             SYNTAX           DisplayString
             MAX-ACCESS      read-only
             STATUS           current
             DESCRIPTION
                 "Identifies the time of the original event."
             ::= { opcTypes 41 }


networkName OBJECT-TYPE
             SYNTAX          DisplayString
             MAX-ACCESS      read-only
             STATUS          current
             DESCRIPTION
                 "The Metasys network which is the source of the event,
                  this string is also included in the OPCsource."
             ::= { opcTypes 43 }


ncmName      OBJECT-TYPE      -- requires n1_alarm_and_event_server v2.0         
             SYNTAX           DisplayString
             MAX-ACCESS      read-only
             STATUS           current
             DESCRIPTION
                 "The Metasys network controller which is the source of the event,
                  this string is also included in the OPCsource."
             ::= { opcTypes 44 }


systemID OBJECT-TYPE              -- will be a unique attribute in n1_alarm_and_event_server v2.0         
             SYNTAX           DisplayString
             MAX-ACCESS      read-only
             STATUS           current
             DESCRIPTION
                 "The system which is the source of the event,
                  this string is also included in the OPCsource."
             ::= { opcTypes 45 }

id OBJECT-TYPE              -- will be a unique attribute in n1_alarm_and_event_server v2.0
             SYNTAX           DisplayString
             MAX-ACCESS      read-only
             STATUS           current
             DESCRIPTION
                 "The object which is the source of the event,
                  this string is also included in the OPCsource."
             ::= { opcTypes 46 }

expandedID OBJECT-TYPE       -- requires n1_alarm_and_event_server v2.0
             SYNTAX           DisplayString
             MAX-ACCESS      read-only
             STATUS           current
             DESCRIPTION
                 "The long name of the object which is the source of the event."
             ::= { opcTypes 47 }
             
presentvalue OBJECT-TYPE         
             SYNTAX           DisplayString
             MAX-ACCESS      read-only
             STATUS           current
             DESCRIPTION
                 "The value of the object when the event occurred."
             ::= { opcTypes 48 }
             
units OBJECT-TYPE         
             SYNTAX           DisplayString
             MAX-ACCESS      read-only
             STATUS           current
             DESCRIPTION
                 "The engineering units asssigned to the object."
             ::= { opcTypes 49 }
              
reportType OBJECT-TYPE         
             SYNTAX           DisplayString
             MAX-ACCESS       read-only
             STATUS           current
             DESCRIPTION
                 "The report type of the event, CRITICAL, STATUS or FOLLOWUP."
             ::= { opcTypes 50 }
              
              
              
alarmType OBJECT-TYPE         
             SYNTAX           DisplayString
             MAX-ACCESS      read-only
             STATUS           current
             DESCRIPTION
                 "The report type of the event, CRITICAL, STATUS or FOLLOWUP."
             ::= { opcTypes 51 }
              
availattribute1 OBJECT-TYPE         
             SYNTAX           DisplayString
             MAX-ACCESS      read-only
             STATUS           current
             DESCRIPTION
                 "Available for future use."
             ::= { opcTypes 52 }

alarmPriority OBJECT-TYPE         
             SYNTAX           DisplayString
             MAX-ACCESS      read-only
             STATUS           current
             DESCRIPTION
                 "The original Metasys Report severity (1-4)"
             ::= { opcTypes 53 }
             
--
-- Vendor Tracking Event attributes
-- ===========================

featureStatus  OBJECT-TYPE       -- also applies to security    
             SYNTAX           DisplayString
             MAX-ACCESS      read-only
             STATUS           current
             DESCRIPTION
                 "For feature related transactions, the name of the feature. 
                  For operator commands, the status of the object. "
             ::= { opcTypes 60 }
            

reportDate  OBJECT-TYPE           
             SYNTAX           DisplayString
             MAX-ACCESS      read-only
             STATUS           current
             DESCRIPTION
                 "The date the transaction occurred."
                   ::= { opcTypes 61 }
            
reportTime  OBJECT-TYPE           -- see if this attribute is combined with date
             SYNTAX           DisplayString
             MAX-ACCESS      read-only
             STATUS           current
             DESCRIPTION
                 "The time the transaction occurred."
             ::= { opcTypes 62 }

transactionType OBJECT-TYPE           -- see if enumeration value is output as a string
             SYNTAX           INTEGER
                              {
--                            report(0),  zero is not a valid enumeration
                              logonLogoff(1),
                              object(2),
                              feature(3)
                              }
                                       
             MAX-ACCESS      read-only
             STATUS           current
             DESCRIPTION
                 "Transaction Type as an enumeration"
             ::= { opcTypes 63 }
             
 

transactionTypeText OBJECT-TYPE         
             SYNTAX           DisplayString
             MAX-ACCESS      read-only
             STATUS           current
             DESCRIPTION
                 "Transaction Type "
             ::= { opcTypes 64 }
             
location  OBJECT-TYPE   
             SYNTAX           DisplayString
             MAX-ACCESS      read-only
             STATUS           current
             DESCRIPTION
                 "Location. "
             ::= { opcTypes 65 }
             
deviceName OBJECT-TYPE    
             SYNTAX           DisplayString
             MAX-ACCESS      read-only
             STATUS           current
             DESCRIPTION
                 "The name of the operator device where the transaction occurred."
             ::= { opcTypes 66 }
             
userID    OBJECT-TYPE
             SYNTAX           DisplayString
             MAX-ACCESS      read-only
             STATUS           current
             DESCRIPTION
                 "The three character password ID of 
                  the operator who performed the transaction."
             ::= { opcTypes 67 }
             
accssLevel OBJECT-TYPE            
             SYNTAX           DisplayString
             MAX-ACCESS      read-only
             STATUS           current
             DESCRIPTION
                  "For logon, the users access level.
                   For logoff, 0.
                   Otherwise, the access level required to perform the transaction."
             ::= { opcTypes 68 }
             
              
transactionText OBJECT-TYPE            
             SYNTAX           DisplayString
             MAX-ACCESS      read-only
             STATUS           current
             DESCRIPTION
                  "A description of the transaction."
             ::= { opcTypes 69 }
             
 
--
-- Attributes specific to Security reports
-- ========================================

--n1FeatureStatus is defined above   
--Applicable to n1 and bacnet
firstName   OBJECT-TYPE            
             SYNTAX           DisplayString
             MAX-ACCESS      read-only
             STATUS           current
             DESCRIPTION
                  "First Name of the operator who performed a transaction."
             ::= { opcTypes 70 }
             
lastName    OBJECT-TYPE            
             SYNTAX           DisplayString
             MAX-ACCESS      read-only
             STATUS           current
             DESCRIPTION
                  "Last Name of the operator who performed a transaction."
             ::= { opcTypes 71 }
             
spclText   OBJECT-TYPE            
             SYNTAX           DisplayString
             MAX-ACCESS      read-only
             STATUS           current
             DESCRIPTION
                  "Information about the event."
             ::= { opcTypes 72 }
             
cardNumber    OBJECT-TYPE            
             SYNTAX           DisplayString
             MAX-ACCESS      read-only
             STATUS           current
             DESCRIPTION
                  "Card Number used in the transaction."
             ::= { opcTypes 73 }

deviceTimePresent  OBJECT-TYPE            
             SYNTAX           DisplayString
             MAX-ACCESS      read-only
             STATUS           current
             DESCRIPTION
                  "If true, the reported time is from the device. "
             ::= { opcTypes 74 } 
             
esjAckComment   OBJECT-TYPE            
             SYNTAX           DisplayString
             MAX-ACCESS      read-only
             STATUS           current
             DESCRIPTION
                  "A comment entered by the operator acknowledging the event."
             ::= { opcTypes 75 }
                       
--
-- ========================================
-- The following attributes apply only to Bacnet Traps
-- ========================================
--
propertyValue   OBJECT-TYPE            
             SYNTAX           DisplayString
             MAX-ACCESS      read-only
             STATUS           current
             DESCRIPTION
                  "The current value of the attribute."
             ::= { opcTypes 100 }
             
unit   OBJECT-TYPE            
             SYNTAX           DisplayString
             MAX-ACCESS      read-only
             STATUS           current
             DESCRIPTION
                  "The unit of the value."
             ::= { opcTypes 101 }
            
propertyName   OBJECT-TYPE            
             SYNTAX           DisplayString
             MAX-ACCESS      read-only
             STATUS           current
             DESCRIPTION
                  "The name of the attribute."
             ::= { opcTypes 102 }
                                            
fromState   OBJECT-TYPE            
             SYNTAX           DisplayString
             MAX-ACCESS      read-only
             STATUS           current
             DESCRIPTION
                  "The previous state before the transition occurred."
             ::= { opcTypes 103 }

vendorIdentifier   OBJECT-TYPE            
             SYNTAX           DisplayString
             MAX-ACCESS      read-only
             STATUS           current
             DESCRIPTION
                  "The Bacnet Vendor Identifier number.  5 will be set for JC devices."
             ::= { opcTypes 104 }

areas   OBJECT-TYPE            
             SYNTAX           DisplayString
             MAX-ACCESS      read-only
             STATUS           current
             DESCRIPTION
                  "The Query Filter String."
             ::= { opcTypes 105 }

bacnetEventType   OBJECT-TYPE            
             SYNTAX           DisplayString
             MAX-ACCESS      read-only
             STATUS           current
             DESCRIPTION
                  "The Bacnet defined event type."
             ::= { opcTypes 106 }

ackComment OBJECT-TYPE         -- actual attribute is ack.comment          
             SYNTAX           DisplayString
             MAX-ACCESS      read-only
             STATUS           current
             DESCRIPTION
                  "A comment entered by the operator acknowledging the event."
             ::= { opcTypes 107}


completeAcknowledge   OBJECT-TYPE            
             SYNTAX           DisplayString
             MAX-ACCESS      read-only
             STATUS           current
             DESCRIPTION
                  "A indication of whether the controller needs complete acknowledgement."
             ::= { opcTypes 108 }

badgeNumber   OBJECT-TYPE            
             SYNTAX           DisplayString
             MAX-ACCESS      read-only
             STATUS           current
             DESCRIPTION
                  "The badge number of the badge holder."
             ::= { opcTypes 109 }
                                            
badgeTrace   OBJECT-TYPE            
             SYNTAX           DisplayString
             MAX-ACCESS      read-only
             STATUS           current
             DESCRIPTION
                  "Specifies if the card event set to be part of trace."
             ::= { opcTypes 110 }

issueLevel   OBJECT-TYPE            
             SYNTAX           DisplayString
             MAX-ACCESS      read-only
             STATUS           current
             DESCRIPTION
                  "The current issue of badge that created event."
             ::= { opcTypes 111 }

timedOverride   OBJECT-TYPE            
             SYNTAX           DisplayString
             MAX-ACCESS      read-only
             STATUS           current
             DESCRIPTION
                  "Timed Override"
             ::= { opcTypes 112 }

facilityCode   OBJECT-TYPE            
             SYNTAX           DisplayString
             MAX-ACCESS      read-only
             STATUS           current
             DESCRIPTION
                  "The facility code of badge."
             ::= { opcTypes 113 }  
             
direction   OBJECT-TYPE            
             SYNTAX           DisplayString
             MAX-ACCESS      read-only
             STATUS           current
             DESCRIPTION
                  "Enum=in,out,toggle,unknown,muster."
             ::= { opcTypes 114 }  
             
functionKey   OBJECT-TYPE            
             SYNTAX           DisplayString
             MAX-ACCESS      read-only
             STATUS           current
             DESCRIPTION
                  "Function Key"
             ::= { opcTypes 115 }
             
barcodeAttach   OBJECT-TYPE            
             SYNTAX           DisplayString
             MAX-ACCESS      read-only
             STATUS           current
             DESCRIPTION
                 "32 character string- NULL if N/A."
             ::= { opcTypes 116 }

terminalName   OBJECT-TYPE            
             SYNTAX           DisplayString
             MAX-ACCESS      read-only
             STATUS           current
             DESCRIPTION
                  "Terminal Name"
             ::= { opcTypes 117 }

userName   OBJECT-TYPE            
             SYNTAX           DisplayString
             MAX-ACCESS      read-only
             STATUS           current
             DESCRIPTION
                  "User Name"
             ::= { opcTypes 118 }

auditItemName   OBJECT-TYPE            
             SYNTAX           DisplayString
             MAX-ACCESS      read-only
             STATUS           current
             DESCRIPTION
                  "Audit Item Name"
             ::= { opcTypes 119 } 
             
pegasysEventName   OBJECT-TYPE            
             SYNTAX           DisplayString
             MAX-ACCESS      read-only
             STATUS           current
             DESCRIPTION
                  "Pegasys Event Name"
             ::= { opcTypes 120 } 
             
errorLogType   OBJECT-TYPE            
             SYNTAX           DisplayString
             MAX-ACCESS      read-only
             STATUS           current
             DESCRIPTION
                  "Error Log Type"
             ::= { opcTypes 121 }
             
triggerCode   OBJECT-TYPE            
             SYNTAX           DisplayString
             MAX-ACCESS      read-only
             STATUS           current
             DESCRIPTION
                  "Trigger Code"
             ::= { opcTypes 122 } 
             
triggerText   OBJECT-TYPE            
             SYNTAX           DisplayString
             MAX-ACCESS      read-only
             STATUS           current
             DESCRIPTION
                  "Trigger Text"
             ::= { opcTypes 123 }

triggerValue   OBJECT-TYPE            
             SYNTAX           DisplayString
             MAX-ACCESS      read-only
             STATUS           current
             DESCRIPTION
                  "Trigger Value"
             ::= { opcTypes 124 }

reliability   OBJECT-TYPE            
             SYNTAX           DisplayString
             MAX-ACCESS      read-only
             STATUS           current
             DESCRIPTION
                  "Reliability"
             ::= { opcTypes 125 }
   

                    
-- **************************************************************************
-- *    Traps                                                               *
-- *                                                                        *
-- **************************************************************************
-- *                                                                        
-- * following Traps are supported for n1 and Bacnet OPC messages
-- * conditionalEventNotification
-- * simpleEventNotification
-- * conditionalEventAcknowledged
-- * trackingEventNotification
-- * conditional traps support the ifindex variable to allow the value to be polled
-- * by the Network Management software
-- *
-- **************************************************************************

n1HvacActiveConditionalEvent NOTIFICATION-TYPE     -- all CRIT and FOLLOWUP reports are Conditional
 
    OBJECTS   { opcSeverity, opcCondition, opcSource, 
    opcMessage, opcTimeStamp, opcEventTypeText, opcEventCategoryText, 
    opcActiveTime, opcQualityText,     -- subCondition not used by the n1
    opcNewStateText, opcChangeMaskText, opcAckRequired,  
    presentvalue, units,
    spclText, deviceTimePresent, expandedID,                   
    ifIndex                         -- ifIndex & ifTable are reference ids if present
    }                                         
    STATUS current
    DESCRIPTION "This trap is sent when a n1 HVAC conditional event becomes active."
    ::= { opcN1Traps 0 1 }

n1HvacInactiveConditionalEvent NOTIFICATION-TYPE     -- all CRIT and FOLLOWUP reports are Conditional
 
    OBJECTS   { opcSeverity, opcCondition, opcSource, 
    opcMessage, opcTimeStamp, opcEventTypeText, opcEventCategoryText, 
    opcActiveTime, opcQualityText,     -- subCondition not used by the n1
    opcNewStateText, opcChangeMaskText, opcAckRequired,  
    presentvalue, units,
    spclText, deviceTimePresent, expandedID,                   
    ifIndex                                   -- ifIndex is a reference id if present
    }  
    STATUS current
    DESCRIPTION "This trap is sent if when a n1 HVAC conditional event becomes inactive."
    ::= { opcN1Traps 0 2 } 
    
n1HvacConditionalEventAcknowledged NOTIFICATION-TYPE     -- all CRIT and FOLLOWUP reports are Conditional
 
    OBJECTS   { opcSeverity, opcCondition, opcSource, 
    opcMessage, opcTimeStamp, opcEventTypeText, opcEventCategoryText, 
    opcActiveTime, opcQualityText,     -- subCondition not used by the n1
    opcNewStateText, opcChangeMaskText, opcActorID, 
    presentvalue, units,
    spclText, deviceTimePresent, expandedID, esjAckComment,                 
    ifIndex                       -- ifIndex & ifTable are reference ids if present
    }  
    STATUS current
    DESCRIPTION "This trap is sent when a n1 HVAC conditional event is acknowledged by a Metasys operator."
    ::= { opcN1Traps 0 3 }

n1FireActiveConditionalEvent NOTIFICATION-TYPE     -- all CRIT and FOLLOWUP reports are Conditional
 
    OBJECTS   { opcSeverity, opcCondition, opcSource, presentvalue, units,
    opcMessage, opcTimeStamp, opcEventTypeText, opcEventCategoryText, 
    opcActiveTime, opcQualityText,     -- subCondition not used by the n1
    opcNewStateText, opcChangeMaskText, opcAckRequired,  
    spclText, deviceTimePresent, expandedID,                   
    ifIndex                                   -- ifIndex is a reference id if present
    }  
    STATUS current
    DESCRIPTION "This trap is sent if when a n1 fire conditional event becomes active."
    ::= { opcN1Traps 0 4 }

n1FireInactiveConditionalEvent NOTIFICATION-TYPE     -- all CRIT and FOLLOWUP reports are Conditional
 
    OBJECTS   { opcSeverity, opcCondition, opcSource, 
    opcMessage, opcTimeStamp, opcEventTypeText, opcEventCategoryText, 
    opcActiveTime, opcQualityText,     -- subCondition not used by the n1
    opcNewStateText, opcChangeMaskText, opcAckRequired,  
    presentvalue, units,
    spclText, deviceTimePresent, expandedID,                   
    ifIndex                       -- ifIndex & ifTable are reference ids if present
    }  
    STATUS current
    DESCRIPTION "This trap is sent if when a n1 fire conditional event becomes inactive."
    ::= { opcN1Traps 0 5 } 
    
n1FireConditionalEventAcknowledged NOTIFICATION-TYPE     -- all CRIT and FOLLOWUP reports are Conditional
 
    OBJECTS   { opcSeverity, opcCondition, opcSource, 
    opcMessage, opcTimeStamp, opcEventTypeText, opcEventCategoryText, 
    opcActiveTime, opcQualityText,     -- subCondition not used by the n1
    opcNewStateText, opcChangeMaskText, opcActorID,  
    presentvalue, units,
    spclText, deviceTimePresent, expandedID, esjAckComment,                  
    ifIndex                       -- ifIndex & ifTable are reference ids if present
    }  
    STATUS current
    DESCRIPTION "This trap is sent when a n1 fire conditional event is acknowledged by a Metasys operator."
    ::= { opcN1Traps 0 6 }
    
n1ServicesActiveConditionalEvent NOTIFICATION-TYPE     -- all CRIT and FOLLOWUP reports are Conditional
 
    OBJECTS   { opcSeverity, opcCondition, opcSource, 
    opcMessage, opcTimeStamp, opcEventTypeText, opcEventCategoryText, 
    opcActiveTime, opcQualityText,     -- subCondition not used by the n1
    opcNewStateText, opcChangeMaskText, opcAckRequired,  
    presentvalue, units,
    spclText, deviceTimePresent, expandedID,                   
    ifIndex                         -- ifIndex & ifTable are reference ids if present
    }  
    STATUS current
    DESCRIPTION "This trap is sent if when a n1 services conditional event becomes active."
    ::= { opcN1Traps 0 7 }

n1ServicesInactiveConditionalEvent NOTIFICATION-TYPE     -- all CRIT and FOLLOWUP reports are Conditional
 
    OBJECTS   { opcSeverity, opcCondition, opcSource, 
    opcMessage, opcTimeStamp, opcEventTypeText, opcEventCategoryText, 
    opcActiveTime, opcQualityText,     -- subCondition not used by the n1
    opcNewStateText, opcChangeMaskText, opcAckRequired,  
    presentvalue, units,
    spclText, deviceTimePresent, expandedID,                   
    ifIndex                        -- ifIndex & ifTable are reference ids if present
    }  
    STATUS current
    DESCRIPTION "This trap is sent if when a n1 services conditional event becomes inactive."
    ::= { opcN1Traps 0 8 } 
    
n1ServicesConditionalEventAcknowledged NOTIFICATION-TYPE     -- all CRIT and FOLLOWUP reports are Conditional
 
    OBJECTS   { opcSeverity, opcCondition, opcSource, 
    opcMessage, opcTimeStamp, opcEventTypeText, opcEventCategoryText, 
    opcActiveTime, opcQualityText,     -- subCondition not used by the n1
    opcNewStateText, opcChangeMaskText, opcActorID, 
    presentvalue, units,
    spclText, deviceTimePresent, expandedID,  esjAckComment,                  
    ifIndex                         -- ifIndex & ifTable are reference ids if present
    }  
    STATUS current
    DESCRIPTION "This trap is sent when a n1 services conditional event is acknowledged by a Metasys operator."
    ::= { opcN1Traps 0 9 }
    
n1SecurityActiveConditionalEvent NOTIFICATION-TYPE     -- all CRIT and FOLLOWUP reports are Conditional
 
    OBJECTS   { opcSeverity, opcCondition, opcSource, 
    opcMessage, opcTimeStamp, opcEventTypeText, opcEventCategoryText, 
    opcActiveTime, opcQualityText,     -- subCondition not used by the n1
    opcNewStateText, opcChangeMaskText, opcAckRequired,  
    presentvalue, units,
    spclText, deviceTimePresent, expandedID,                   
    ifIndex                         -- ifIndex & ifTable are reference ids if present
    }  
    STATUS current
    DESCRIPTION "This trap is sent if when a n1 security conditional event becomes active."
    ::= { opcN1Traps 0 10 }

n1SecurityInactiveConditionalEvent NOTIFICATION-TYPE     -- all CRIT and FOLLOWUP reports are Conditional
 
    OBJECTS   { opcSeverity, opcCondition, opcSource, 
    opcMessage, opcTimeStamp, opcEventTypeText,opcEventCategoryText, 
    opcActiveTime, opcQualityText,     -- subCondition not used by the n1
    opcNewStateText, opcChangeMaskText, opcAckRequired,   
    lastName, firstName, spclText, cardNumber, deviceTimePresent,  featureStatus,
    ifIndex                                   -- ifIndex is a reference id if present
    }  
    STATUS current
    DESCRIPTION "This trap is sent if when a n1 security conditional event becomes inactive."
    ::= { opcN1Traps 0 11 }
    
n1SecurityConditionalEventAcknowledged NOTIFICATION-TYPE     -- all CRIT and FOLLOWUP reports are Conditional
 
    OBJECTS   { opcSeverity,opcCondition, opcSource, 
    opcMessage, opcTimeStamp, opcEventTypeText, opcEventCategoryText, 
    opcActiveTime, opcQualityText,     -- subCondition not used by the n1
    opcNewStateText, opcChangeMaskText, opcActorID, 
    lastName, firstName, spclText, cardNumber, deviceTimePresent, featureStatus,
    esjAckComment,
    ifIndex                                   -- ifIndex is a reference id if present
    }  
    STATUS current
    DESCRIPTION "This trap is sent when a n1 security conditional event is acknowledged by a Metasys operator."
    ::= { opcN1Traps 0 12 }

n1AdminActiveConditionalEvent NOTIFICATION-TYPE     -- all CRIT and FOLLOWUP reports are Conditional
 
    OBJECTS   { opcSeverity, opcCondition, opcSource, 
    opcMessage, opcTimeStamp, opcEventTypeText, opcEventCategoryText, 
    opcActiveTime, opcQualityText,     -- subCondition not used by the n1
    opcNewStateText, opcChangeMaskText, opcAckRequired,  
    presentvalue, units,
    spclText, deviceTimePresent, expandedID,                   
    ifIndex                        -- ifIndex & ifTable are reference ids if present
    }  
    STATUS current
    DESCRIPTION "This trap is sent if when an n1 administrative conditional event becomes active."
    ::= { opcN1Traps 0 13 }

n1AdminInactiveConditionalEvent NOTIFICATION-TYPE     -- all CRIT and FOLLOWUP reports are Conditional

    OBJECTS   { opcSeverity, opcCondition, opcSource, 
    opcMessage, opcTimeStamp, opcEventTypeText, opcEventCategoryText, 
    opcActiveTime, opcQualityText,     -- subCondition not used by the n1
    opcNewStateText, opcChangeMaskText, opcAckRequired,  
    presentvalue, units,
    spclText, deviceTimePresent, expandedID,               
    ifIndex                        -- ifIndex & ifTable are reference ids if present
    }  
    STATUS current
    DESCRIPTION "This trap is sent if when a n1 administrative conditional event becomes inactive."
    ::= { opcN1Traps 0 14 } 
    
n1AdminConditionalEventAcknowledged NOTIFICATION-TYPE     -- all CRIT and FOLLOWUP reports are Conditional
 
    OBJECTS   { opcSeverity, opcCondition, opcSource, 
    opcMessage, opcTimeStamp, opcEventTypeText, opcEventCategoryText, 
    opcActiveTime, opcQualityText,     -- subCondition not used by the n1
    opcNewStateText, opcChangeMaskText, opcActorID, 
    presentvalue, units,
    spclText, deviceTimePresent, expandedID, esjAckComment,                  
    ifIndex                        -- ifIndex & ifTable are reference ids if present
    }  
    STATUS current
    DESCRIPTION "This trap is sent when a n1 administrative conditional event is acknowledged by a Metasys operator."
    ::= { opcN1Traps 0 15 }

    
n1GeneralActiveConditionalEvent NOTIFICATION-TYPE     -- all CRIT and FOLLOWUP reports are Conditional
   
    OBJECTS   { opcSeverity, opcCondition, opcSource, 
    opcMessage, opcTimeStamp, opcEventTypeText, opcEventCategoryText, 
    opcActiveTime, opcQualityText,     -- subCondition not used by the n1
    opcNewStateText, opcChangeMaskText, opcAckRequired,  
    presentvalue, units,
    spclText, deviceTimePresent, expandedID,                   
    ifIndex                        -- ifIndex & ifTable are reference ids if present
    }  
    STATUS current
    DESCRIPTION "This trap is sent if when a n1 general conditional event becomes active."
    ::= { opcN1Traps 0 16 }

n1GeneralInactiveConditionalEvent NOTIFICATION-TYPE   -- all CRIT and FOLLOWUP reports are Conditional
   
    OBJECTS   { opcSeverity, opcCondition, opcSource, 
    opcMessage, opcTimeStamp, opcEventTypeText, opcEventCategoryText, 
    opcActiveTime, opcQualityText,     -- subCondition not used by the n1
    opcNewStateText, opcChangeMaskText, opcAckRequired,  
    presentvalue, units,
    spclText, deviceTimePresent, expandedID,                   
    ifIndex                        -- ifIndex & ifTable are reference ids if present
    }  
    STATUS current
    DESCRIPTION "This trap is sent when a n1 general conditional event becomes inactive."
    ::= { opcN1Traps 0 17 }
    
n1GeneralConditionalEventAcknowledged NOTIFICATION-TYPE   -- all CRIT and FOLLOWUP reports are Conditional
   
    OBJECTS   { opcSeverity, opcCondition, opcSource, 
    opcMessage, opcTimeStamp, opcEventTypeText, opcEventCategoryText, 
    opcActiveTime, opcQualityText,     -- subCondition not used by the n1
    opcNewStateText, opcChangeMaskText, opcActorID, 
    presentvalue, units,
    spclText, deviceTimePresent, expandedID, esjAckComment,                  
    ifIndex                        -- ifIndex & ifTable are reference ids if present
    }  
    STATUS current
    DESCRIPTION "This trap is sent when a n1 general conditional event is acknowledged by a Metasys operator."
    ::= { opcN1Traps 0 18 }

n1HvacSimpleEvent NOTIFICATION-TYPE         -- all n1 status reports are Simple
      
    OBJECTS   { opcSeverity, opcCondition, opcSource, 
    opcMessage, opcTimeStamp, opcEventTypeText, opcEventCategoryText, 
    opcActiveTime, opcQualityText,     -- subCondition not used by the n1
    presentvalue, units,
    spclText, deviceTimePresent, expandedID,  
    ifIndex                                   -- ifIndex is a reference id if present
    }
    STATUS current
    DESCRIPTION "This is a n1 HVAC information trap."
    ::= { opcN1Traps 0 19 }
    
n1FireSimpleEvent NOTIFICATION-TYPE         -- all n1 status reports are Simple
      
    OBJECTS   { opcSeverity, opcCondition, opcSource, 
    opcMessage, opcTimeStamp, opcEventTypeText, opcEventCategoryText, 
    opcActiveTime, opcQualityText,     -- subCondition not used by the n1
    presentvalue, units,
    spclText, deviceTimePresent, expandedID,  
    ifIndex                                   -- ifIndex is a reference id if present
    }
    STATUS current
    DESCRIPTION "This is a n1 fire information trap."
    ::= { opcN1Traps 0 20 }

n1ServicesSimpleEvent NOTIFICATION-TYPE         -- all n1 status reports are Simple
      
    OBJECTS   { opcSeverity, opcCondition, opcSource, 
    opcMessage, opcTimeStamp, opcEventTypeText, opcEventCategoryText, 
    opcActiveTime, opcQualityText,     -- subCondition not used by the n1
    presentvalue, units,
    spclText, deviceTimePresent, expandedID,  
    ifIndex                                   -- ifIndex is a reference id if present
    }
    STATUS current
    DESCRIPTION "This is a n1 services information trap."
    ::= { opcN1Traps 0 21 }
       
n1SecuritySimpleEvent NOTIFICATION-TYPE         -- all n1 status reports are Simple
      
    OBJECTS   { opcSeverity, opcCondition, opcSource, 
    opcMessage, opcTimeStamp, opcEventTypeText, opcEventCategoryText, 
    opcActiveTime, opcQualityText,     -- subCondition not used by the n1
    presentvalue, units,
    spclText, deviceTimePresent, expandedID,  
    ifIndex                                   -- ifIndex is a reference id if present
    } 
    STATUS current
    DESCRIPTION "This is a n1 security information trap."
    ::= { opcN1Traps 0 22 } 
    
n1AdminSimpleEvent NOTIFICATION-TYPE         -- all n1 status reports are Simple
      
    OBJECTS   { opcSeverity, opcCondition, opcSource, 
    opcMessage, opcTimeStamp, opcEventTypeText, opcEventCategoryText, 
    opcActiveTime, opcQualityText,     -- subCondition not used by the n1
    presentvalue, units,
    spclText, deviceTimePresent, expandedID,                   
    ifIndex                                   -- ifIndex is a reference id if present
    }
    STATUS current
    DESCRIPTION "This is a n1 administrative information trap."
    ::= { opcN1Traps 0 23 } 
    

n1GeneralSimpleEvent NOTIFICATION-TYPE         -- all n1 status reports are Simple
      
    OBJECTS   { opcSeverity, opcCondition, opcSource, 
    opcMessage, opcTimeStamp, opcEventTypeText, opcEventCategoryText, 
    opcActiveTime, opcQualityText,     -- subCondition not used by the n1
    presentvalue, units,
    spclText, deviceTimePresent, expandedID,                   
    ifIndex                                   -- ifIndex is a reference id if present
    }
    STATUS current
    DESCRIPTION "This is a n1 general information trap."
    ::= { opcN1Traps 0 24 } 
                
n1HvacTrackingEvent NOTIFICATION-TYPE
    
    OBJECTS   { opcSeverity, opcCondition, opcSource, 
    opcMessage, opcTimeStamp, opcEventTypeText, opcEventCategoryText, 
    opcActiveTime, opcQualityText, opcActorID,
    presentvalue, units,
    spclText, deviceTimePresent, expandedID,                   
    originalDate, originalTime, 
    featureStatus, reportDate, reportTime, 
    location, deviceName, userID, accssLevel,   
    ifIndex                                   -- ifIndex is a reference id if present
    }
    STATUS current
    DESCRIPTION "This is a n1 HVAC tracking trap."
    ::= { opcN1Traps 0 25 }      
 
n1FireTrackingEvent NOTIFICATION-TYPE
    
    OBJECTS   { opcSeverity, opcCondition, opcSource,  
    opcMessage, opcTimeStamp, opcEventTypeText, opcEventCategoryText, 
    opcActiveTime, opcQualityText, opcActorID,
    presentvalue, units,
    spclText, deviceTimePresent,
    spclText, deviceTimePresent, expandedID,                   
    featureStatus, reportDate, reportTime,
    location, deviceName, userID, accssLevel,   
    ifIndex                                   -- ifIndex is a reference id if present
    }
    STATUS current
    DESCRIPTION "This is a n1 fire tracking trap."
    ::= { opcN1Traps 0 26 }  
                          
n1ServicesTrackingEvent NOTIFICATION-TYPE
    
    OBJECTS   { opcSeverity, opcCondition, opcSource, 
    opcMessage, opcTimeStamp, opcEventTypeText, opcEventCategoryText, 
    opcActiveTime, opcQualityText, opcActorID,
    spclText, deviceTimePresent,
    presentvalue, units,
    expandedID,  originalDate, originalTime, 
    featureStatus, reportDate, reportTime, 
    location, deviceName, userID, accssLevel,   
    ifIndex                                   -- ifIndex is a reference id if present
    }
    STATUS current
    DESCRIPTION "This is a n1 service tracking trap."
    ::= { opcN1Traps 0 27 }  
                         
n1SecurityTrackingEvent NOTIFICATION-TYPE
    
    OBJECTS   { opcSeverity, opcCondition, opcSource, 
    opcMessage, opcTimeStamp, opcEventTypeText, opcEventCategoryText, 
    opcActiveTime, opcQualityText,   opcActorID,
    lastName, firstName,   
    spclText, deviceTimePresent, expandedID,                   
    cardNumber, featureStatus,
    ifIndex                                   -- ifIndex is a reference id if present
    }
    STATUS current
    DESCRIPTION "This is a n1 security tracking trap."
    ::= { opcN1Traps 0 28 }    

    
n1AdminTrackingEvent NOTIFICATION-TYPE
    
    OBJECTS   { opcSeverity, opcCondition, opcSource, 
    opcMessage, opcTimeStamp, opcEventTypeText, opcEventCategoryText, 
    opcActiveTime, opcQualityText, opcActorID,
    presentvalue, units,
    spclText, deviceTimePresent, expandedID,                   
    originalDate, originalTime, 
    featureStatus, reportDate, reportTime, 
    location, deviceName, userID, accssLevel,   
    ifIndex                                   -- ifIndex is a reference id if present
    }
    STATUS current
    DESCRIPTION "This is a n1 administrative tracking trap."
    ::= { opcN1Traps 0 29 }  
       
n1GeneralTrackingEvent NOTIFICATION-TYPE         
      
    OBJECTS   { opcSeverity, opcCondition, opcSource, 
    opcMessage, opcTimeStamp, opcEventTypeText, opcEventCategoryText, 
    opcActiveTime, opcQualityText,  opcActorID,
    presentvalue, units, 
    spclText, deviceTimePresent, expandedID,                   
    originalDate, originalTime, 
    featureStatus, reportDate, reportTime,
    location, deviceName, userID, accssLevel,   
    ifIndex                                   -- ifIndex is a reference id if present
    } 
    STATUS current
    DESCRIPTION "This is a n1 general tracking trap."
    ::= { opcN1Traps 0 30 }             


                       
bacnetDeviceFailureActiveConditionalEvent NOTIFICATION-TYPE
    
    OBJECTS   { opcSeverity, opcCondition, opcSource, 
    opcMessage, opcTimeStamp, opcEventTypeText, opcEventCategoryText,
    opcSubCondition, opcActiveTime, opcQualityText,
    opcNewStateText, opcChangeMaskText, opcAckRequired,      -- no vendor specific attributes
    ifIndex                                         -- ifIndex is a reference id if present
    }
    STATUS current
    DESCRIPTION "This trap is sent when a bacnet device failure conditional event becomes active."
    ::= { opcBacnetTraps 0 1 }

bacnetDeviceFailureInactiveConditionalEvent NOTIFICATION-TYPE
        
    OBJECTS   { opcSeverity, opcCondition, opcSource, 
    opcMessage, opcTimeStamp, opcEventTypeText, opcEventCategoryText,
    opcSubCondition, opcActiveTime, opcQualityText,
    opcNewStateText,  opcChangeMaskText, opcAckRequired,-- no vendor specific attributes
    ifIndex                                         -- ifIndex is a reference id if present
    }
    STATUS current
    DESCRIPTION "This trap is sent when a bacnet device failure conditional event becomes inactive."
    ::= { opcBacnetTraps 0 2 }

bacnetDeviceFailureConditionalEventAcknowledged NOTIFICATION-TYPE
      
    OBJECTS   { opcSeverity, opcCondition, opcSource, 
    opcMessage, opcTimeStamp, opcEventTypeText,opcEventCategoryText, 
    opcSubCondition, opcActiveTime, opcQualityText,
    opcNewStateText, opcChangeMaskText, opcActorID, -- no vendor specific attributes
    ifIndex       
    }    
    STATUS current
    DESCRIPTION "This trap is sent when a bacnet device failure condition is acknowledged by a Metasys operator."
    ::= { opcBacnetTraps 0 3 }


bacnetHvacActiveConditionalEvent NOTIFICATION-TYPE
        
    OBJECTS   { opcSeverity, opcCondition, opcSource, 
    opcMessage, opcTimeStamp, opcEventTypeText, opcEventCategoryText,
    opcSubCondition, opcActiveTime, opcQualityText,
    opcNewStateText, opcChangeMaskText, opcAckRequired, 
    bacnetEventType, propertyValue, propertyName, unit,vendorIdentifier, 
    areas, fromState,  ackComment, completeAcknowledge, reliability,  
    ifIndex                                         -- ifIndex is a reference id if present
	
    }
    STATUS current
    DESCRIPTION "This trap is sent when a bacnet HVAC conditional event becomes active."
    ::= { opcBacnetTraps 0 4 }
 
 bacnetHvacInactiveConditionalEvent NOTIFICATION-TYPE
        
    OBJECTS   { opcSeverity, opcCondition, opcSource, 
    opcMessage, opcTimeStamp, opcEventTypeText, opcEventCategoryText,
    opcSubCondition, opcActiveTime, opcQualityText,
    opcNewStateText, opcChangeMaskText, opcAckRequired, 
    bacnetEventType, propertyValue, propertyName, unit, 
    vendorIdentifier, areas, fromState, ackComment, completeAcknowledge, reliability,         
    ifIndex                                         -- ifIndex is a reference id if present
    }   
    STATUS current
    DESCRIPTION "This trap is sent when a bacnet HVAC conditional event becomes inactive."
    ::= { opcBacnetTraps 0 5 }   
    
bacnetHvacConditionalEventAcknowledged NOTIFICATION-TYPE
      
    OBJECTS   { opcSeverity, opcCondition, opcSource,
    opcMessage, opcTimeStamp, opcEventTypeText,opcEventCategoryText,
    opcSubCondition, opcActiveTime, opcQualityText,
    opcNewStateText, opcChangeMaskText, opcActorID, 
    bacnetEventType, propertyValue, propertyName, unit,
    vendorIdentifier, areas, fromState,  ackComment, completeAcknowledge,reliability, 
    ifIndex       
    }        
    STATUS current
    DESCRIPTION "This trap is sent when a bacnet HVAC condition is acknowledged by a Metasys operator."
    ::= { opcBacnetTraps 0 6 }

bacnetFireActiveConditionalEvent NOTIFICATION-TYPE
      
    OBJECTS   { opcSeverity, opcCondition, opcSource, 
    opcMessage, opcTimeStamp, opcEventTypeText, opcEventCategoryText,
    opcSubCondition, opcActiveTime, opcQualityText,
    opcNewStateText, opcChangeMaskText, opcAckRequired, 
    bacnetEventType, propertyValue, propertyName, unit,  vendorIdentifier, 
    areas, fromState, ackComment, completeAcknowledge, reliability, 
    ifIndex       
    }        
    STATUS current
    DESCRIPTION "This trap is sent when a bacnet fire conditional event becomes active."
    ::= { opcBacnetTraps 0 7 }  
    
bacnetFireInactiveConditionalEvent NOTIFICATION-TYPE
      
      
    OBJECTS   { opcSeverity, opcCondition, opcSource, 
    opcMessage, opcTimeStamp, opcEventTypeText, opcEventCategoryText,
    opcSubCondition, opcActiveTime, opcQualityText,
    opcNewStateText, opcChangeMaskText, opcAckRequired, 
    bacnetEventType,propertyValue,propertyName, unit, 
    vendorIdentifier, areas, fromState,  ackComment, completeAcknowledge,reliability, 
    ifIndex       
    }        
    STATUS current
    DESCRIPTION "This trap is sent when a bacnet fire conditional event becomes inactive."
    ::= { opcBacnetTraps 0 8 }

bacnetFireConditionalEventAcknowledged NOTIFICATION-TYPE
      
    OBJECTS   { opcSeverity, opcCondition, opcSource,
    opcMessage, opcTimeStamp, opcEventTypeText,opcEventCategoryText,
    opcSubCondition, opcActiveTime, opcQualityText,
    opcNewStateText, opcChangeMaskText, opcActorID, 
    bacnetEventType, propertyValue, propertyName, unit,
    vendorIdentifier, areas, fromState, ackComment, completeAcknowledge, reliability, 
    ifIndex       
    }        
    STATUS current
    DESCRIPTION "This trap is sent when a bacnet fire condition is acknowledged by a Metasys operator."
    ::= { opcBacnetTraps 0 9 }
                          
bacnetSecurityActiveConditionalEvent NOTIFICATION-TYPE
      
      
    OBJECTS   { opcSeverity, opcCondition, opcSource, 
    opcMessage, opcTimeStamp, opcEventTypeText, opcEventCategoryText,
    opcSubCondition, opcActiveTime, opcQualityText,
    opcNewStateText, opcChangeMaskText, opcAckRequired, 
    bacnetEventType, propertyValue, propertyName, unit,
    vendorIdentifier, areas, fromState, ackComment, completeAcknowledge,reliability, 
    ifIndex       
    }        
    STATUS current
    DESCRIPTION "This trap is sent when a security conditional event becomes active."
    ::= { opcBacnetTraps 0 10 }  
    
bacnetSecurityInactiveConditionalEvent NOTIFICATION-TYPE
            
    OBJECTS   { opcSeverity, opcCondition, opcSource, 
    opcMessage, opcTimeStamp, opcEventTypeText, opcEventCategoryText,
    opcSubCondition, opcActiveTime, opcQualityText,
    opcNewStateText, opcChangeMaskText, opcAckRequired, 
    bacnetEventType, propertyValue, propertyName, unit,
    vendorIdentifier, areas, fromState,  ackComment, completeAcknowledge,reliability, 
    ifIndex       
    }        
    STATUS current
    DESCRIPTION "This trap is sent when a security conditional event becomes inactive."
    ::= { opcBacnetTraps 0 11 }

bacnetSecurityConditionalEventAcknowledged NOTIFICATION-TYPE
      
    OBJECTS   { opcSeverity, opcCondition, opcSource,
    opcMessage, opcTimeStamp, opcEventTypeText,opcEventCategoryText,
    opcSubCondition, opcActiveTime, opcQualityText,
    opcNewStateText, opcChangeMaskText, opcActorID, 
    bacnetEventType, propertyValue, propertyName, unit, 
    vendorIdentifier, areas, fromState,  ackComment, completeAcknowledge,reliability, 
    ifIndex       
    }        
    STATUS current
    DESCRIPTION "This trap is sent when a bacnet security condition is acknowledged by a Metasys operator."
    ::= { opcBacnetTraps 0 12 }                         
                          
                          
bacnetServicesActiveConditionalEvent NOTIFICATION-TYPE
            
    OBJECTS   { opcSeverity, opcCondition, opcSource, 
    opcMessage, opcTimeStamp, opcEventTypeText, opcEventCategoryText,
    opcSubCondition, opcActiveTime, opcQualityText,
    opcNewStateText, opcChangeMaskText, opcAckRequired, 
    bacnetEventType, propertyValue, propertyName, unit, 
    vendorIdentifier, areas, fromState,  ackComment, completeAcknowledge, reliability, 
    ifIndex       
    }        
    STATUS current
    DESCRIPTION "This trap is sent when a bacnet services condition becomes active."
    ::= { opcBacnetTraps 0 13 }  
    
bacnetServicesInactiveConditionalEvent NOTIFICATION-TYPE
            
    OBJECTS   { opcSeverity, opcCondition, opcSource, 
    opcMessage, opcTimeStamp, opcEventTypeText, opcEventCategoryText,
    opcSubCondition, opcActiveTime, opcQualityText,
    opcNewStateText, opcChangeMaskText, opcAckRequired, 
    bacnetEventType, propertyValue, propertyName, unit,
    vendorIdentifier, areas, fromState,  ackComment, completeAcknowledge, reliability, 
    ifIndex       
    }        
    STATUS current
    DESCRIPTION "This trap is sent when a bacnet services condition becomes inactive."
    ::= { opcBacnetTraps 0 14 }

bacnetServicesConditionalEventAcknowledged NOTIFICATION-TYPE
      
    OBJECTS   { opcSeverity, opcCondition, opcSource,
    opcMessage, opcTimeStamp, opcEventTypeText,opcEventCategoryText,
    opcSubCondition, opcActiveTime, opcQualityText,
    opcNewStateText, opcChangeMaskText, opcActorID, 
    bacnetEventType, propertyValue, propertyName, unit,
    vendorIdentifier, areas, fromState,  ackComment, completeAcknowledge, reliability, 
    ifIndex       
    }        
    STATUS current
    DESCRIPTION "This trap is sent when a bacnet services condition is acknowledged by a Metasys operator."
    ::= { opcBacnetTraps 0 15 }
                     
                          
bacnetAdminActiveConditionalEvent NOTIFICATION-TYPE
            
    OBJECTS   { opcSeverity, opcCondition, opcSource, 
    opcMessage, opcTimeStamp, opcEventTypeText, opcEventCategoryText,
    opcSubCondition, opcActiveTime, opcQualityText,
    opcNewStateText, opcChangeMaskText, opcAckRequired, 
    bacnetEventType, propertyValue, propertyName, unit,
    vendorIdentifier, areas, fromState,  ackComment, completeAcknowledge, reliability, 
    ifIndex       
    }        
    STATUS current
    DESCRIPTION "This trap is sent when a bacnet administrative condition becomes active"
    ::= { opcBacnetTraps 0 16 }  
    
bacnetAdminInactiveConditionalEvent NOTIFICATION-TYPE
           
    OBJECTS   { opcSeverity, opcCondition, opcSource, 
    opcMessage, opcTimeStamp, opcEventTypeText, opcEventCategoryText,
    opcSubCondition, opcActiveTime, opcQualityText,
    opcNewStateText, opcChangeMaskText, opcAckRequired, 
    bacnetEventType, propertyValue, propertyName, unit, 
    vendorIdentifier, areas, fromState,  ackComment, completeAcknowledge, reliability, 
    ifIndex       
    }        
    STATUS current
    DESCRIPTION "This trap is sent when a bacnet administrative condition becomes inactive."
    ::= { opcBacnetTraps 0 17 }

bacnetAdminConditionalEventAcknowledged NOTIFICATION-TYPE
      
    OBJECTS   { opcSeverity, opcCondition, opcSource,
    opcMessage, opcTimeStamp, opcEventTypeText,opcEventCategoryText,
    opcSubCondition, opcActiveTime, opcQualityText,
    opcNewStateText, opcChangeMaskText, opcActorID, 
    bacnetEventType, propertyValue, propertyName, unit, 
    vendorIdentifier, areas, fromState,  ackComment, completeAcknowledge, reliability, 
    ifIndex       
    }        
    STATUS current
    DESCRIPTION "This trap is sent when a bacnet administrative condition
 is acknowledged by a Metasys operator."
    ::= { opcBacnetTraps 0 18 }                     
  
bacnetGeneralAlarmActiveConditionalEvent NOTIFICATION-TYPE
          
    OBJECTS   { opcSeverity, opcCondition, opcSource, 
    opcMessage, opcTimeStamp, opcEventTypeText, opcEventCategoryText,
    opcSubCondition, opcActiveTime, opcQualityText,
    opcNewStateText, opcChangeMaskText, opcAckRequired, 
    bacnetEventType, vendorIdentifier, areas, fromState, ackComment, 
    completeAcknowledge, deviceTimePresent, reliability,  
    ifIndex                                         -- ifIndex is a reference id if present
    }
    STATUS current
    DESCRIPTION "This trap is sent when a bacnet general alarm is active."
    ::= { opcBacnetTraps 0 19 }

bacnetGeneralAlarmInactiveConditionalEvent NOTIFICATION-TYPE
    
    OBJECTS   { opcSeverity, opcCondition, opcSource, 
    opcMessage, opcTimeStamp, opcEventTypeText, opcEventCategoryText,
    opcSubCondition, opcActiveTime, opcQualityText,
    opcNewStateText, opcChangeMaskText, opcAckRequired, 
    bacnetEventType, vendorIdentifier, areas, fromState, ackComment, 
    completeAcknowledge, deviceTimePresent, reliability,     
    ifIndex                                         -- ifIndex is a reference id if present
    }
    STATUS current
    DESCRIPTION "This trap is sent when a bacnet general alarm becomes inactive."
    ::= { opcBacnetTraps 0 20 }

bacnetGeneralAlarmConditionalEventAcknowledged NOTIFICATION-TYPE
      
    OBJECTS   { opcSeverity, opcCondition, opcSource,
    opcMessage, opcTimeStamp, opcEventTypeText,opcEventCategoryText,
    opcSubCondition, opcActiveTime, opcQualityText,
    opcNewStateText, opcChangeMaskText, opcActorID, 
    bacnetEventType, vendorIdentifier, areas, fromState, ackComment, 
    completeAcknowledge, deviceTimePresent, reliability,
    ifIndex       
    }    
    STATUS current
    DESCRIPTION "This trap is sent when a bacnet general alarm is
     acknowledged by a Metasys operator."
    ::= { opcBacnetTraps 0 21 }

bacnetGeneralEventActiveConditionalEvent NOTIFICATION-TYPE
          
    OBJECTS   { opcSeverity, opcCondition, opcSource, 
    opcMessage, opcTimeStamp, opcEventTypeText, opcEventCategoryText,
    opcSubCondition, opcActiveTime, opcQualityText,
    opcNewStateText, opcChangeMaskText, opcAckRequired, 
    bacnetEventType, vendorIdentifier, areas, fromState, ackComment, 
    completeAcknowledge, deviceTimePresent, reliability,  
    ifIndex                                         -- ifIndex is a reference id if present
    }
    STATUS current
    DESCRIPTION "This trap is sent when a device failure alarm is activated."
    ::= { opcBacnetTraps 0 22 }

bacnetGeneralEventInactiveConditionalEvent NOTIFICATION-TYPE
              
    OBJECTS   { opcSeverity, opcCondition, opcSource, 
    opcMessage, opcTimeStamp, opcEventTypeText, opcEventCategoryText,
    opcSubCondition, opcActiveTime, opcQualityText,
    opcNewStateText, opcChangeMaskText, opcAckRequired, 
    bacnetEventType, vendorIdentifier, areas, fromState, ackComment, 
    completeAcknowledge, deviceTimePresent, reliability,     
    ifIndex                                         -- ifIndex is a reference id if present
    }
    STATUS current
    DESCRIPTION "This trap is sent when a device failure alarm is no longer active."
    ::= { opcBacnetTraps 0 23 }

bacnetGeneralEventConditionalEventAcknowledged NOTIFICATION-TYPE
      
    OBJECTS   { opcSeverity, opcCondition, opcSource,
    opcMessage, opcTimeStamp, opcEventTypeText,opcEventCategoryText,
    opcSubCondition, opcActiveTime, opcQualityText,
    opcNewStateText, opcChangeMaskText, opcActorID, 
    bacnetEventType, vendorIdentifier, areas, fromState, ackComment, 
    completeAcknowledge, deviceTimePresent, reliability,
    ifIndex       
    }    
    STATUS current
    DESCRIPTION "This trap is sent when a device failure alarm has been
     acknowledged by an operator."
    ::= { opcBacnetTraps 0 24 }  
                  
bacnetPanelEventActiveConditionalEvent NOTIFICATION-TYPE
          
    OBJECTS   { opcSeverity, opcCondition, opcSource, 
    opcMessage, opcTimeStamp, opcEventTypeText, opcEventCategoryText,
    opcSubCondition, opcActiveTime, opcQualityText,
    opcNewStateText, opcChangeMaskText, opcAckRequired, 
    bacnetEventType, vendorIdentifier, areas, fromState, terminalName,
    ackComment, completeAcknowledge, reliability,  
    ifIndex                                         -- ifIndex is a reference id if present
    }
    STATUS current
    DESCRIPTION "This trap is sent when a bacnet panel event condition becomes active."
    ::= { opcBacnetTraps 0 25 }

bacnetPanelEventInactiveConditionalEvent NOTIFICATION-TYPE
        
    OBJECTS   { opcSeverity, opcCondition, opcSource, 
    opcMessage, opcTimeStamp, opcEventTypeText, opcEventCategoryText,
    opcSubCondition, opcActiveTime, opcQualityText,
    opcNewStateText, opcChangeMaskText, opcAckRequired, 
    bacnetEventType, vendorIdentifier, areas, fromState, terminalName,
    ackComment, completeAcknowledge, reliability,     
    ifIndex                                         -- ifIndex is a reference id if present
    }
    STATUS current
    DESCRIPTION "This trap is sent when a bacnet panel event condition becomes inactive."
    ::= { opcBacnetTraps 0 26 }

bacnetPanelEventConditionalEventAcknowledged NOTIFICATION-TYPE
      
    OBJECTS   { opcSeverity, opcCondition, opcSource,
    opcMessage, opcTimeStamp, opcEventTypeText,opcEventCategoryText,
    opcSubCondition, opcActiveTime, opcQualityText,
    opcNewStateText, opcChangeMaskText, opcActorID, 
    bacnetEventType, vendorIdentifier, areas, fromState, terminalName,
    ackComment, completeAcknowledge, reliability,
    ifIndex       
    }    
    STATUS current
    DESCRIPTION "This trap is sent when a bacnet panel event condition is
    acknowledged by a Metasys operator."
    ::= { opcBacnetTraps 0 27 }
                  
bacnetPanelHWStatusActiveConditionalEvent NOTIFICATION-TYPE
      
    OBJECTS   { opcSeverity, opcCondition, opcSource, 
    opcMessage, opcTimeStamp, opcEventTypeText, opcEventCategoryText,
    opcSubCondition, opcActiveTime, opcQualityText,
    opcNewStateText, opcChangeMaskText, opcAckRequired, 
    bacnetEventType, vendorIdentifier, areas, fromState, terminalName,
    ackComment, completeAcknowledge, reliability,  
    ifIndex                                         -- ifIndex is a reference id if present
    }
    STATUS current
    DESCRIPTION "This trap is sent when a bacnet panel hardware status conditional
    event has becomes active."
    ::= { opcBacnetTraps 0 28 }

bacnetPanelHWStatusInactiveConditionalEvent NOTIFICATION-TYPE
             
    OBJECTS   { opcSeverity, opcCondition, opcSource, 
    opcMessage, opcTimeStamp, opcEventTypeText, opcEventCategoryText,
    opcSubCondition, opcActiveTime, opcQualityText,
    opcNewStateText, opcChangeMaskText, opcAckRequired, 
    bacnetEventType, vendorIdentifier, areas, fromState, terminalName,
    ackComment, completeAcknowledge, reliability,     
    ifIndex                                         -- ifIndex is a reference id if present
    }
    STATUS current
    DESCRIPTION "This trap is sent when a bacnet panel hardware status conditional
     event has becomes inactive."
    ::= { opcBacnetTraps 0 29 }

bacnetPanelHWStatusConditionalEventAcknowledged NOTIFICATION-TYPE
      
    OBJECTS   { opcSeverity, opcCondition, opcSource,
    opcMessage, opcTimeStamp, opcEventTypeText,opcEventCategoryText,
    opcSubCondition, opcActiveTime, opcQualityText,
    opcNewStateText, opcChangeMaskText, opcActorID, 
    bacnetEventType, vendorIdentifier, areas, fromState, terminalName,
    ackComment, completeAcknowledge, reliability,
    ifIndex       
    }    
    STATUS current
    DESCRIPTION "This trap is sent when a panel hardware status conditional event has been
    acknowledged by an operator."
    ::= { opcBacnetTraps 0 30 }

bacnetHostLogActiveConditionalEvent NOTIFICATION-TYPE
      
    OBJECTS   { opcSeverity, opcCondition, opcSource, 
    opcMessage, opcTimeStamp, opcEventTypeText, opcEventCategoryText,
    opcSubCondition, opcActiveTime, opcQualityText,
    opcNewStateText, opcChangeMaskText, opcAckRequired, 
    bacnetEventType, vendorIdentifier, areas, fromState, userName,
    auditItemName, pegasysEventName, errorLogType, 
    ackComment, completeAcknowledge, reliability,  
    ifIndex                                         -- ifIndex is a reference id if present
    }
    STATUS current
    DESCRIPTION "This trap is sent when a bacnet host log condition becomes active."
    ::= { opcBacnetTraps 0 31 }

bacnetHostLogInactiveConditionalEvent NOTIFICATION-TYPE
          
    OBJECTS   { opcSeverity, opcCondition, opcSource, 
    opcMessage, opcTimeStamp, opcEventTypeText, opcEventCategoryText,
    opcSubCondition, opcActiveTime, opcQualityText,
    opcNewStateText, opcChangeMaskText, opcAckRequired, 
    bacnetEventType, vendorIdentifier, areas, fromState, userName,
    auditItemName, pegasysEventName, errorLogType, 
    ackComment, completeAcknowledge, reliability,  
    ifIndex                                         -- ifIndex is a reference id if present
    }
    STATUS current
    DESCRIPTION "This trap is sent when a bacnet host log condition becomes inactive."
    ::= { opcBacnetTraps 0 32 }        
                
bacnetHostLogConditionalEventAcknowledged NOTIFICATION-TYPE

    OBJECTS   { opcSeverity, opcCondition, opcSource,
    opcMessage, opcTimeStamp, opcEventTypeText,opcEventCategoryText,
    opcSubCondition, opcActiveTime, opcQualityText,
    opcNewStateText, opcChangeMaskText, opcActorID, 
    bacnetEventType, vendorIdentifier, areas, fromState, userName,
    auditItemName, pegasysEventName, errorLogType, 
    ackComment, completeAcknowledge, reliability,  
    ifIndex                                         -- ifIndex is a reference id if present
    }
    STATUS current
    DESCRIPTION "This trap is sent when a bacnet host log condition has been
     acknowledged by an operator."
    ::= { opcBacnetTraps 0 33 }                
                                         

bacnetOutputPointStatusActiveConditionalEvent NOTIFICATION-TYPE
 
    OBJECTS   { opcSeverity, opcCondition, opcSource, 
    opcMessage, opcTimeStamp, opcEventTypeText, opcEventCategoryText,
    opcSubCondition, opcActiveTime, opcQualityText,
    opcNewStateText, opcChangeMaskText, opcAckRequired, 
    bacnetEventType, vendorIdentifier, areas, fromState, propertyValue, 
    ackComment, completeAcknowledge, reliability,  
    ifIndex                                         -- ifIndex is a reference id if present
    }
    STATUS current
    DESCRIPTION "This trap is sent when a bacnet output point status conditional event is activated."
    ::= { opcBacnetTraps 0 34 }

bacnetOutputPointStatusInactiveConditionalEvent NOTIFICATION-TYPE
    
    OBJECTS   { opcSeverity, opcCondition, opcSource, 
    opcMessage, opcTimeStamp, opcEventTypeText, opcEventCategoryText,
    opcSubCondition, opcActiveTime, opcQualityText,
    opcNewStateText, opcChangeMaskText, opcAckRequired, 
    bacnetEventType,  areas, fromState, propertyValue, vendorIdentifier,
    ackComment, completeAcknowledge, reliability,  
    ifIndex                                         -- ifIndex is a reference id if present
    }
    STATUS current
    DESCRIPTION "This trap is sent when a bacnet output point status conditional event is no longer active."
    ::= { opcBacnetTraps 0 35 }

bacnetOutputPointStatusConditionalEventAcknowledged NOTIFICATION-TYPE
    
    OBJECTS   { opcSeverity, opcCondition, opcSource,
    opcMessage, opcTimeStamp, opcEventTypeText,opcEventCategoryText,
    opcSubCondition, opcActiveTime, opcQualityText,
    opcNewStateText, opcChangeMaskText, opcActorID, 
    bacnetEventType, propertyValue, vendorIdentifier, areas, fromState, 
    ackComment, completeAcknowledge, reliability,  
    ifIndex                                         -- ifIndex is a reference id if present
    }
    STATUS current
    DESCRIPTION "This trap is sent when a bacnet output point status condition has been
     acknowledged by an operator."
    ::= { opcBacnetTraps 0 36 }     
    

bacnetInputPointStatusActiveConditionalEvent NOTIFICATION-TYPE
    
    OBJECTS   { opcSeverity, opcCondition, opcSource, 
    opcMessage, opcTimeStamp, opcEventTypeText, opcEventCategoryText,
    opcSubCondition, opcActiveTime, opcQualityText,
    opcNewStateText, opcChangeMaskText, opcAckRequired, 
    bacnetEventType, vendorIdentifier,  propertyValue, areas, fromState, 
    ackComment, completeAcknowledge, reliability,  
    ifIndex                                         -- ifIndex is a reference id if present
    }
    STATUS current
    DESCRIPTION "This trap is sent when a bacnet input point status event becomes active."
    ::= { opcBacnetTraps 0 37 }
    
bacnetInputPointStatusInactiveConditionalEvent NOTIFICATION-TYPE
    
    OBJECTS   { opcSeverity, opcCondition, opcSource, 
    opcMessage, opcTimeStamp, opcEventTypeText, opcEventCategoryText,
    opcSubCondition, opcActiveTime, opcQualityText,
    opcNewStateText, opcChangeMaskText, opcAckRequired, 
    bacnetEventType, vendorIdentifier, propertyValue, areas, fromState,
    ackComment, completeAcknowledge, reliability,  
    ifIndex                                         -- ifIndex is a reference id if present
    }
    STATUS current
    DESCRIPTION "This trap is sent when a bacnet input point status event is no longer active."
    ::= { opcBacnetTraps 0 38 }
    
bacnetInputPointStatusConditionalEventAcknowledged NOTIFICATION-TYPE
    
    OBJECTS   { opcSeverity, opcCondition, opcSource,
    opcMessage, opcTimeStamp, opcEventTypeText,opcEventCategoryText,
    opcSubCondition, opcActiveTime, opcQualityText,
    opcNewStateText, opcChangeMaskText, opcActorID, 
    bacnetEventType, vendorIdentifier, propertyValue, areas, fromState,  
    ackComment, completeAcknowledge, reliability,  
    ifIndex                                         -- ifIndex is a reference id if present
    }
    STATUS current
    DESCRIPTION "This trap is sent when a bacnet input point status event has been
     acknowledged by an operator."
    ::= { opcBacnetTraps 0 39 }

       
bacnetHvacSimpleEvent NOTIFICATION-TYPE
        
    OBJECTS   { opcSeverity, opcCondition, opcSource, opcMessage, opcTimeStamp, opcEventTypeText, 
    opcEventCategoryText, opcSubCondition, opcActiveTime, opcQualityText,
    bacnetEventType, vendorIdentifier, areas, fromState, propertyValue,
    propertyName, unit, 
    ifIndex                                         -- ifIndex is a reference id if present
    }
    STATUS current   
    DESCRIPTION "This is a bacnet HVAC information trap."
    ::= { opcBacnetTraps 0 40  }    
       
bacnetFireSimpleEvent NOTIFICATION-TYPE
        
    OBJECTS   { opcSeverity, opcCondition, opcSource, opcMessage, opcTimeStamp, opcEventTypeText,
    opcEventCategoryText, opcSubCondition, opcActiveTime, opcQualityText,
    bacnetEventType, vendorIdentifier, areas, fromState, propertyValue,
    propertyName, unit, 
    ifIndex                                         -- ifIndex is a reference id if present
    }
    STATUS current   
    DESCRIPTION "This is a bacnet fire information trap."
    ::= { opcBacnetTraps 0 41  }
 
bacnetSecuritySimpleEvent NOTIFICATION-TYPE
        
    OBJECTS   { opcSeverity, opcCondition, opcSource,  opcMessage, opcTimeStamp, opcEventTypeText,
    opcEventCategoryText, opcSubCondition, opcActiveTime, opcQualityText,
    bacnetEventType, vendorIdentifier, areas, fromState, propertyValue,
    propertyName, unit,
    ifIndex                                         -- ifIndex is a reference id if present
    }
    STATUS current   
    DESCRIPTION "This is a bacnet security information trap."
    ::= { opcBacnetTraps 0 42 }    
   
bacnetServicesSimpleEvent NOTIFICATION-TYPE
        
    OBJECTS   { opcSeverity, opcCondition, opcSource, opcMessage, opcTimeStamp, opcEventTypeText,
    opcEventCategoryText, opcSubCondition, opcActiveTime, opcQualityText,
    bacnetEventType, vendorIdentifier, areas, fromState, propertyValue,
    propertyName, unit, 
    ifIndex                                         -- ifIndex is a reference id if present
    }
    STATUS current   
    DESCRIPTION "This is a bacnet services information trap."
    ::= { opcBacnetTraps 0 43 }
    
bacnetAdminSimpleEvent NOTIFICATION-TYPE
        
    OBJECTS   { opcSeverity, opcCondition, opcSource,  opcMessage, opcTimeStamp, opcEventTypeText,
    opcEventCategoryText, opcSubCondition, opcActiveTime, opcQualityText,
    bacnetEventType, vendorIdentifier, areas, fromState, propertyValue,
    propertyName, unit,
    ifIndex                                         -- ifIndex is a reference id if present
    }
    STATUS current   
    DESCRIPTION "This is a bacnet administrative information trap."
    ::= { opcBacnetTraps 0 44 }

bacnetAccessGrantSimpleEvent NOTIFICATION-TYPE
        
    OBJECTS   { opcSeverity, opcCondition, opcSource, 
    opcMessage, opcTimeStamp, opcEventTypeText,opcEventCategoryText,
    opcSubCondition, opcActiveTime, opcQualityText,
    bacnetEventType, vendorIdentifier, areas, fromState, badgeTrace,
    badgeNumber, lastName, firstName, issueLevel, timedOverride,
    facilityCode, direction, 
    ifIndex                                         -- ifIndex is a reference id if present
    }
    STATUS current   
    DESCRIPTION "This is a bacnet access granted information trap."
    ::= { opcBacnetTraps 0 45 }   
 
bacnetAccessDenySimpleEvent NOTIFICATION-TYPE
        
    OBJECTS   { opcSeverity, opcCondition, opcSource, 
    opcMessage, opcTimeStamp, opcEventTypeText, opcEventCategoryText,
    opcSubCondition, opcActiveTime, opcQualityText,
    bacnetEventType, vendorIdentifier, areas, fromState, badgeTrace,
    badgeNumber, lastName, firstName, issueLevel, timedOverride,
    facilityCode, direction, 
    ifIndex                                         -- ifIndex is a reference id if present
    }
    STATUS current   
    DESCRIPTION "This is a bacnet access denied information trap."
    ::= { opcBacnetTraps 0 46 }  
    
bacnetCardTraceSimpleEvent NOTIFICATION-TYPE
        
    OBJECTS   { opcSeverity, opcCondition, opcSource, 
    opcMessage, opcTimeStamp, opcEventTypeText, opcEventCategoryText,
    opcSubCondition, opcActiveTime, opcQualityText,
    bacnetEventType, vendorIdentifier, areas, fromState, badgeTrace,
    badgeNumber, lastName, firstName, issueLevel, timedOverride,
    facilityCode, direction, 
    ifIndex                                         -- ifIndex is a reference id if present
    }
    STATUS current   
    DESCRIPTION "This is a bacnet card trace information trap."
    ::= { opcBacnetTraps 0 47 }  
    
bacnetTAAccessGrantSimpleEvent NOTIFICATION-TYPE
        
    OBJECTS   { opcSeverity, opcCondition, opcSource,
    opcMessage, opcTimeStamp,opcEventTypeText,opcEventCategoryText,
    opcSubCondition, opcActiveTime, opcQualityText,
    bacnetEventType, vendorIdentifier, areas, fromState, badgeTrace,
    badgeNumber, lastName, firstName, timedOverride,
    direction, functionKey, barcodeAttach, 
    ifIndex                                         -- ifIndex is a reference id if present
    }
    STATUS current   
    DESCRIPTION "This is a bacnet granted information trap."
    ::= { opcBacnetTraps 0 48 }
                             
bacnetOutputPointStatusSimpleEvent NOTIFICATION-TYPE
    
    OBJECTS   { opcSeverity, opcCondition, opcSource, 
    opcMessage, opcTimeStamp, opcEventTypeText, opcEventCategoryText,
    opcSubCondition, opcActiveTime, opcQualityText, propertyValue,
    bacnetEventType, vendorIdentifier, areas, fromState,   
    ifIndex                                         -- ifIndex is a reference id if present
    }
    STATUS current
    DESCRIPTION "This is a bacnet output point status information trap."
    ::= { opcBacnetTraps 0 49   }

bacnetInputPointStatusSimpleEvent NOTIFICATION-TYPE
    
    OBJECTS   { opcSeverity, opcCondition, opcSource, 
    opcMessage, opcTimeStamp, opcEventTypeText, opcEventCategoryText,
    opcSubCondition, opcActiveTime, opcQualityText, propertyValue,
    bacnetEventType, vendorIdentifier, areas, fromState,   
    ifIndex                                         -- ifIndex is a reference id if present
    }
    STATUS current
    DESCRIPTION "This is a bacnet input point status information trap."
    ::= { opcBacnetTraps 0 50   }                         

bacnetAuditSimpleEvent NOTIFICATION-TYPE
    
    OBJECTS   { opcSeverity, opcCondition, opcSource, 
    opcMessage, opcTimeStamp, opcEventTypeText, opcEventCategoryText,
    opcSubCondition, opcActiveTime, opcQualityText,
    bacnetEventType, vendorIdentifier, areas, fromState, userName,
    auditItemName, pegasysEventName, errorLogType,  
    ifIndex                                         -- ifIndex is a reference id if present
    }
    STATUS current
    DESCRIPTION "This is a bacnet audit information trap."
    ::= { opcBacnetTraps 0 51 } 
 
bacnetHostEventSimpleEvent NOTIFICATION-TYPE
    
    OBJECTS   { opcSeverity, opcCondition, opcSource,
    opcMessage, opcTimeStamp, opcEventTypeText, opcEventCategoryText,
    opcSubCondition, opcActiveTime, opcQualityText,
    bacnetEventType, vendorIdentifier, areas, fromState, userName,
    auditItemName, pegasysEventName, errorLogType,  
    ifIndex                                         -- ifIndex is a reference id if present
    }
    STATUS current
    DESCRIPTION "This is a bacnet host event information trap."
    ::= { opcBacnetTraps 0 52 } 
 
bacnetHostLogSimpleEvent NOTIFICATION-TYPE
    
    OBJECTS   { opcSeverity, opcCondition, opcSource, 
    opcMessage, opcTimeStamp, opcEventTypeText, opcEventCategoryText,
    opcSubCondition, opcActiveTime, opcQualityText,
    bacnetEventType, vendorIdentifier, areas, fromState, userName,
    auditItemName, pegasysEventName, errorLogType,  
    ifIndex                                         -- ifIndex is a reference id if present
    }
    STATUS current
    DESCRIPTION "This is a bacnet host log information trap."
    ::= { opcBacnetTraps 0 53 } 
 
bacnetHostLogicSimpleEvent NOTIFICATION-TYPE
    
    OBJECTS   { opcSeverity, opcCondition, opcSource, 
    opcMessage, opcTimeStamp, opcEventTypeText, opcEventCategoryText,
    opcSubCondition, opcActiveTime, opcQualityText,
    bacnetEventType, vendorIdentifier, areas, fromState, triggerCode,
    triggerText, triggerValue,  
    ifIndex                                         -- ifIndex is a reference id if present
    }
    STATUS current
    DESCRIPTION "This is a bacnet host logic information trap."
    ::= { opcBacnetTraps 0 54 }  
    
bacnetPanelEventSimpleEvent NOTIFICATION-TYPE
    
    OBJECTS   { opcSeverity, opcCondition, opcSource, 
    opcMessage, opcTimeStamp, opcEventTypeText, opcEventCategoryText,
    opcSubCondition, opcActiveTime, opcQualityText,
    bacnetEventType, vendorIdentifier, areas, fromState, terminalName,  
    ifIndex                                         -- ifIndex is a reference id if present
    }
    STATUS current
    DESCRIPTION "This is a bacnet panel event information trap."
    ::= { opcBacnetTraps 0 55 }  
    
bacnetPanelHWStatusSimpleEvent NOTIFICATION-TYPE
    
    OBJECTS   { opcSeverity, opcCondition, opcSource, 
    opcMessage, opcTimeStamp, opcEventTypeText, opcEventCategoryText,
    opcSubCondition, opcActiveTime, opcQualityText,
    bacnetEventType, vendorIdentifier, areas, fromState, terminalName,  
    ifIndex                                         -- ifIndex is a reference id if present
    }
    STATUS current
    DESCRIPTION "This is a bacnet panel hardware status information trap."
    ::= { opcBacnetTraps 0 56 }  
    
bacnetCommErrorSimpleEvent NOTIFICATION-TYPE
    
    OBJECTS   { opcSeverity, opcCondition, opcSource, 
    opcMessage, opcTimeStamp, opcEventTypeText,opcEventCategoryText,
    opcSubCondition, opcActiveTime, opcQualityText,
     -- no vendor specific attributes
    ifIndex                                         -- ifIndex is a reference id if present
    }
    STATUS current
    DESCRIPTION "This is a bacnet communication error information trap."
    ::= { opcBacnetTraps 0 57 }  
        
bacnetGeneralSimpleEvent NOTIFICATION-TYPE
    
    OBJECTS   { opcSeverity, opcCondition,  opcSource, opcMessage, opcTimeStamp,
    opcEventTypeText,opcEventCategoryText,
    opcSubCondition, opcActiveTime, opcQualityText,
     -- no vendor specific attributes
    ifIndex                                         -- ifIndex is a reference id if present
    }
    STATUS current
    DESCRIPTION "This is a bacnet general information trap."
    ::= { opcBacnetTraps 0 58 }  
    
                                 
-- There is no Bacnet Tracking Event type specified

opcStandardActiveGeneralConditionalEvent NOTIFICATION-TYPE
        
    OBJECTS   { opcSeverity, opcCondition, opcSource, 
    opcMessage, opcTimeStamp, opcEventTypeText, opcEventCategoryText,
    opcSubCondition, opcActiveTime, opcQualityText,
    opcNewStateText, opcChangeMaskText, opcAckRequired, 
    ifIndex                                   -- ifIndex is a reference id if present
    }             
    STATUS current
    DESCRIPTION "This trap is sent when an opc conditional event occurs."
    ::= { opcStandardTraps 0 1  }

opcStandardInactiveConditionalEvent NOTIFICATION-TYPE
        
    OBJECTS   { opcSeverity, opcCondition, opcSource, 
    opcMessage, opcTimeStamp, opcEventTypeText, opcEventCategoryText,
    opcSubCondition, opcActiveTime, opcQualityText,
    opcNewStateText, opcChangeMaskText, opcAckRequired, 
    ifIndex                                   -- ifIndex is a reference id if present
    } 
    STATUS current
    DESCRIPTION "This trap is sent when an opc conditional event becomes inactive."
    ::= { opcStandardTraps 0 2 }

opcStandardGeneralConditionalEventAcknowledged NOTIFICATION-TYPE
     
    OBJECTS   { opcSeverity, opcCondition, opcSource, 
    opcMessage, opcTimeStamp, opcEventTypeText, opcEventCategoryText,
    opcSubCondition, opcActiveTime, opcQualityText,
    opcNewStateText, opcChangeMaskText, opcActorID, 
    ifIndex                                   -- ifIndex is a reference id if present
    }    
    STATUS current
    DESCRIPTION "This trap is sent when an opc conditional event is acknowledged."
    ::= { opcStandardTraps 0 3 }

 
opcStandardSimpleNotification NOTIFICATION-TYPE
     
    OBJECTS   { opcSeverity, opcCondition, opcSource, opcMessage, opcTimeStamp,
    opcEventTypeText,opcEventCategoryText, 
    opcCondition, opcActiveTime, opcQualityText, opcChangeMaskText,  
    ifIndex                                   -- ifIndex is a reference id if present
    }         
    STATUS current
    DESCRIPTION "This trap is sent for information purposes when an opc Simple event occurs."
    ::= { opcStandardTraps 0 4 }

 
opcStandardTrackingEvent NOTIFICATION-TYPE
      
    OBJECTS   { opcSeverity, opcCondition, opcSource, opcMessage, opcTimeStamp,
    opcEventTypeText,opcEventCategoryText, opcActiveTime, opcQualityText,     
    opcNewStateText, opcChangeMaskText, opcAckRequired,  
    ifIndex                                   -- ifIndex is a reference id if present
    }
    STATUS current
    DESCRIPTION "This is a generic opc Tracking notification sent for information purposes."
    ::= { opcStandardTraps 0 5 }
    
    
END
