Wellfleet-TOKEN-RING-MIB DEFINITIONS ::= BEGIN

-- Created by mdl2asn version 3.1
-- Creation date: Wed Aug 30 16:49:40 EDT 1995


    IMPORTS

      Counter, Gauge, TimeTicks 
        FROM RFC1155-SMI
      OBJECT-TYPE
        FROM RFC-1212
      DisplayString
        FROM RFC1213-MIB
      wfLine
        FROM Wellfleet-COMMON-MIB;


    wfTokenRingTable OBJECT-TYPE
        SYNTAX	SEQUENCE OF WfTokenRingEntry
        ACCESS	not-accessible
        STATUS	mandatory
        DESCRIPTION
                "TOKEN RING line record"
        ::= { wfLine 2 }

    wfTokenRingEntry OBJECT-TYPE
        SYNTAX	WfTokenRingEntry
        ACCESS	not-accessible
        STATUS	mandatory
        DESCRIPTION
                "An entry in the token table"
        INDEX	{ wfTokenRingSlot,
    		  wfTokenRingConnector }
        ::= { wfTokenRingTable 1 }

    WfTokenRingEntry ::= SEQUENCE {
    	    wfTokenRingDelete
    		INTEGER,
    	    wfTokenRingDisable
    		INTEGER,
    	    wfTokenRingState
    		INTEGER,
    	    wfTokenRingSlot
    		INTEGER,
    	    wfTokenRingConnector
    		INTEGER,
    	    wfTokenRingCct
    		INTEGER,
    	    wfTokenRingMtu
    		INTEGER,
    	    wfTokenRingMadr
    		OCTET STRING,
    	    wfTokenRingCfgMadr
    		OCTET STRING,
    	    wfTokenRingMadrSelect
    		INTEGER,
    	    wfTokenRingSpeed
    		INTEGER,
    	    wfTokenRingEarlyTokenRelease
    		INTEGER,
    	    wfTokenRingStatus
    		INTEGER,
    	    wfTokenRingOpenState
    		INTEGER,
    	    wfTokenRingOpenStatus
    		INTEGER,
    	    wfTokenRingUpStream
    		OCTET STRING,
    	    wfTokenRingRxOctets
    		Counter,
    	    wfTokenRingRxFrames
    		Counter,
    	    wfTokenRingTxOctets
    		Counter,
    	    wfTokenRingTxFrames
    		Counter,
    	    wfTokenRingInDiscards
    		Counter,
    	    wfTokenRingInErrors
    		Counter,
    	    wfTokenRingOutDiscards
    		Counter,
    	    wfTokenRingOutErrors
    		Counter,
    	    wfTokenRingTxClipFrames
    		Counter,
    	    wfTokenRingRxReplenMisses
    		Counter,
    	    wfTokenRingSignalLosses
    		Counter,
    	    wfTokenRingHardErrors
    		Counter,
    	    wfTokenRingSoftErrors
    		Counter,
    	    wfTokenRingTransmitBeacons
    		Counter,
    	    wfTokenRingLobeWireFaults
    		Counter,
    	    wfTokenRingAutoRemovalErrors
    		Counter,
    	    wfTokenRingRequestRemoves
    		Counter,
    	    wfTokenRingCounterOverflows
    		Counter,
    	    wfTokenRingSingleStations
    		Counter,
    	    wfTokenRingRingRecoveries
    		Counter,
    	    wfTokenRingAdapterChecks
    		Counter,
    	    wfTokenRingFirstAdapterCheckCode
    		INTEGER,
    	    wfTokenRingLastAdapterCheckCode
    		INTEGER,
    	    wfTokenRingLineErrors
    		Counter,
    	    wfTokenRingBurstErrors
    		Counter,
    	    wfTokenRingAriFciErrors
    		Counter,
    	    wfTokenRingLostFrameErrors
    		Counter,
    	    wfTokenRingRxCongestionErrors
    		Counter,
    	    wfTokenRingFrameCopiedErrors
    		Counter,
    	    wfTokenRingTokenErrors
    		Counter,
    	    wfTokenRingDmaBusErrors
    		Counter,
    	    wfTokenRingDmaParityErrors
    		Counter,
    	    wfTokenRingSrbNotFreeCmdAborts
    		Counter,
    	    wfTokenRingRxProcessings
    		Counter,
    	    wfTokenRingTxProcessings
    		Counter,
    	    wfTokenRingTxCmplProcessings
    		Counter,
    	    wfTokenRingRxTimeouts
    		Counter,
    	    wfTokenRingCmdTimeouts
    		Counter,
    	    wfTokenRingRxHostIntErrors
    		Counter,
    	    wfTokenRingRxTxBufferSize
    		INTEGER,
    	    wfTokenRingCfgTxQueueLength
    		INTEGER,
    	    wfTokenRingCfgRxQueueLength
    		INTEGER,
    	    wfTokenRingTxQueueLength
    		INTEGER,
    	    wfTokenRingRxQueueLength
    		INTEGER,
    	    wfTokenRingMacRxOctets
    		Counter,
    	    wfTokenRingMacRxFrames
    		Counter,
    	    wfTokenRingCfgFunctionalAddress
    		INTEGER,
    	    wfTokenRingFunctionalAddress
    		INTEGER,
    	    wfTokenRingGroupAddress
    		INTEGER,
    	    wfTokenRingLineNumber
    		INTEGER,
    	    wfTokenRingMacCode
    		DisplayString,
    	    wfTokenRingModule
    		INTEGER,
    	    wfTokenRingActualConnector
    		INTEGER,
    	    wfTokenRingLastChange
    		TimeTicks,
    	    wfTokenRingOutQLen
    		Gauge,
    	    wfTokenRingForceMacCode
    		INTEGER,
    	    wfTokenRingMSBMadr
    		OCTET STRING,
    	    wfTokenRingTurboBoflDebug
    		INTEGER,
    	    wfTokenRingSingleStatDis
    		INTEGER
        }

    wfTokenRingDelete OBJECT-TYPE
        SYNTAX	INTEGER {
    		    created(1),
    		    deleted(2)
    		}
        ACCESS	read-write
        STATUS	mandatory
        DESCRIPTION
                "create/delete parameter."
        DEFVAL	{ created }
        ::= { wfTokenRingEntry 1 }

    wfTokenRingDisable OBJECT-TYPE
        SYNTAX	INTEGER {
    		    enabled(1),
    		    disabled(2)
    		}
        ACCESS	read-write
        STATUS	mandatory
        DESCRIPTION
                "enable/disable parameter."
        DEFVAL	{ enabled }
        ::= { wfTokenRingEntry 2 }

    wfTokenRingState OBJECT-TYPE
        SYNTAX	INTEGER {
    		    up(1),
    		    down(2),
    		    init(3),
    		    notpresent(4)
    		}
        ACCESS	read-only
        STATUS	mandatory
        DESCRIPTION
                "line driver state variable, Not Present, Init, Down, Up"
        DEFVAL	{ notpresent }
        ::= { wfTokenRingEntry 3 }

    wfTokenRingSlot OBJECT-TYPE
        SYNTAX	INTEGER
        ACCESS	read-only
        STATUS	mandatory
        DESCRIPTION
                "instance ID Slot, filled in by driver"
        ::= { wfTokenRingEntry 4 }

    wfTokenRingConnector OBJECT-TYPE
        SYNTAX	INTEGER
        ACCESS	read-only
        STATUS	mandatory
        DESCRIPTION
                "instance ID Connector, filled in by driver. For the ASN
                this attribute is an encoded value and is equal to
                'module'*10 + 'connector'. Where 'module' is defined in
                attribute 70 and 'connector' is defined in attribute 71
                of this table. For non-ASN platforms this attribute is the
                phisical connector number on the slot"
        ::= { wfTokenRingEntry 5 }

    wfTokenRingCct OBJECT-TYPE
        SYNTAX	INTEGER(1..1023)
        ACCESS	read-write
        STATUS	mandatory
        DESCRIPTION
                "cct number for this line instance, configuration required"
        ::= { wfTokenRingEntry 6 }

    wfTokenRingMtu OBJECT-TYPE
        SYNTAX	INTEGER {
    		    default(4568)
    		}
        ACCESS	read-only
        STATUS	mandatory
        DESCRIPTION
                "mtu parameter, fixed. This mtu of 4568 allows a type 3 Source Route
                Frame (info=4472) to be IP encapsulated over Token Ring.
                The components are:
                     AC_FC      (2) +
                     SNAP       (12+8) +
                     SNAP_IP    (12+8+20) +
                     SR         (12+18) +
                     TYPE3_INFO (4472) +
                     FCS        (4)
                     ---------------------
                     total      4568 bytes"
        DEFVAL	{ default }
        ::= { wfTokenRingEntry 7 }

    wfTokenRingMadr OBJECT-TYPE
        SYNTAX	OCTET STRING
        ACCESS	read-only
        STATUS	mandatory
        DESCRIPTION
                "line MAC address, line driver fills in the currently used 48 bit
                MAC address."
        ::= { wfTokenRingEntry 8 }

    wfTokenRingCfgMadr OBJECT-TYPE
        SYNTAX	OCTET STRING
        ACCESS	read-write
        STATUS	mandatory
        DESCRIPTION
                "Configured line MAC address. Only used if wfTokenRingMadrSelect
                is set appropriately."
        ::= { wfTokenRingEntry 9 }

    wfTokenRingMadrSelect OBJECT-TYPE
        SYNTAX	INTEGER {
    		    boxwide(1),
    		    prom(2),
    		    cnfg(3)
    		}
        ACCESS	read-write
        STATUS	mandatory
        DESCRIPTION
                "Selector determines which MAC address the interface will use."
        DEFVAL	{ prom }
        ::= { wfTokenRingEntry 10 }

    wfTokenRingSpeed OBJECT-TYPE
        SYNTAX	INTEGER {
    		    mbps4(4194304),
    		    mbps16(16777216)
    		}
        ACCESS	read-write
        STATUS	mandatory
        DESCRIPTION
                "Token Ring speed parameter - 4 and 16 Mbps are only valid values"
        DEFVAL	{ mbps16 }
        ::= { wfTokenRingEntry 11 }

    wfTokenRingEarlyTokenRelease OBJECT-TYPE
        SYNTAX	INTEGER {
    		    enabled(1),
    		    disabled(2)
    		}
        ACCESS	read-write
        STATUS	mandatory
        DESCRIPTION
                "Early Token Release parameter, only valid with 16Mbps"
        DEFVAL	{ enabled }
        ::= { wfTokenRingEntry 12 }

    wfTokenRingStatus OBJECT-TYPE
        SYNTAX	INTEGER
        ACCESS	read-only
        STATUS	mandatory
        DESCRIPTION
                "The current interface status. This attribute is only valid when the
                wfTokenRingOpenState attribute is set to OPENED.  The attribute's
                value is a sum of values,  one for each currently applicable condition
                (ie, bit positions indicate active conditions).  Occurrences of each
                condition are separately counted and the counts are included in this
                MIB as attributes wfTokenRingSignalLosses through
                wfTokenRingRingRecoveries.  The following values are defined:

                     32768 = Signal Losses
                     16384 = Hard Errors
                     8192  = Soft Errors
                     4096  = Transmit Beacons
                     2048  = Lobe Wire Faults
                     1024  = Auto-Removal Errors
                     256   = Remove Received
                     128   = Counter Overflows
                     64    = Single Stations
                     32    = Ring Recoveries

                This attribute is the most recent sum of these conditions.  More
                information on each condition is include in the descriptions of the
                individual counter attributes."
        ::= { wfTokenRingEntry 13 }

    wfTokenRingOpenState OBJECT-TYPE
        SYNTAX	INTEGER {
    		    opened(1),
    		    opening(2),
    		    closing(3),
    		    openfailure(4),
    		    ringfailure(5),
    		    closed(6)
    		}
        ACCESS	read-only
        STATUS	mandatory
        DESCRIPTION
                "The current interface state with respect to entering or leaving
                the ring."
        DEFVAL	{ closed }
        ::= { wfTokenRingEntry 14 }

    wfTokenRingOpenStatus OBJECT-TYPE
        SYNTAX	INTEGER {
    		    open(1),
    		    badparam(2),
    		    lobefailed(3),
    		    signalloss(4),
    		    insertiontimeout(5),
    		    ringfailed(6),
    		    beaconing(7),
    		    duplicatemac(8),
    		    requestfailed(9),
    		    removereceived(10),
    		    unkerror(11),
    		    noopen(12)
    		}
        ACCESS	read-only
        STATUS	mandatory
        DESCRIPTION
                "Indicates the success, or the reason for failure, of the station's
                most recent attempt to enter the ring."
        DEFVAL	{ noopen }
        ::= { wfTokenRingEntry 15 }

    wfTokenRingUpStream OBJECT-TYPE
        SYNTAX	OCTET STRING
        ACCESS	read-only
        STATUS	mandatory
        DESCRIPTION
                "MAC address of Up Stream neighbor. Only valid when 'opened'."
        ::= { wfTokenRingEntry 16 }

    wfTokenRingRxOctets OBJECT-TYPE
        SYNTAX	Counter
        ACCESS	read-only
        STATUS	mandatory
        DESCRIPTION
                "Number of octets received without error."
        ::= { wfTokenRingEntry 17 }

    wfTokenRingRxFrames OBJECT-TYPE
        SYNTAX	Counter
        ACCESS	read-only
        STATUS	mandatory
        DESCRIPTION
                "Number of frames received without error."
        ::= { wfTokenRingEntry 18 }

    wfTokenRingTxOctets OBJECT-TYPE
        SYNTAX	Counter
        ACCESS	read-only
        STATUS	mandatory
        DESCRIPTION
                "Number of octets transmitted without error."
        ::= { wfTokenRingEntry 19 }

    wfTokenRingTxFrames OBJECT-TYPE
        SYNTAX	Counter
        ACCESS	read-only
        STATUS	mandatory
        DESCRIPTION
                "Number of frames transmitted without error."
        ::= { wfTokenRingEntry 20 }

    wfTokenRingInDiscards OBJECT-TYPE
        SYNTAX	Counter
        ACCESS	read-only
        STATUS	mandatory
        DESCRIPTION
                "Number of error-free inbound packets discarded. Usually due to lack of
                memory resources. This is equivalent to wfTokenRingRxCongestionErrors."
        ::= { wfTokenRingEntry 21 }

    wfTokenRingInErrors OBJECT-TYPE
        SYNTAX	Counter
        ACCESS	read-only
        STATUS	mandatory
        DESCRIPTION
                "Number of inbound packets not delivered to higher-layer protocol due to
                errors.  The sum of wfTokenRingLineErrors and wfTokenRingBurstErrors."
        ::= { wfTokenRingEntry 22 }

    wfTokenRingOutDiscards OBJECT-TYPE
        SYNTAX	Counter
        ACCESS	read-only
        STATUS	mandatory
        DESCRIPTION
                "Number of error-free outbound packets discarded. Usually due to lack of
                transmission bandwidth. This is equivalent to wfTokenRingTxClipFrames."
        ::= { wfTokenRingEntry 23 }

    wfTokenRingOutErrors OBJECT-TYPE
        SYNTAX	Counter
        ACCESS	read-only
        STATUS	mandatory
        DESCRIPTION
                "Number of outbound packets that could not be transmitted because of
                errors. This is equivalent to wfTokenRingLostFrameErrors."
        ::= { wfTokenRingEntry 24 }

    wfTokenRingTxClipFrames OBJECT-TYPE
        SYNTAX	Counter
        ACCESS	read-only
        STATUS	mandatory
        DESCRIPTION
                "Number of frames clipped in driver's transmit routine due to transmit
                congestion."
        ::= { wfTokenRingEntry 25 }

    wfTokenRingRxReplenMisses OBJECT-TYPE
        SYNTAX	Counter
        ACCESS	read-only
        STATUS	mandatory
        DESCRIPTION
                "Number of packet buffer misses while attempting to replenish driver
                receive ring."
        ::= { wfTokenRingEntry 26 }

    wfTokenRingSignalLosses OBJECT-TYPE
        SYNTAX	Counter
        ACCESS	read-only
        STATUS	mandatory
        DESCRIPTION
                "Number of ring signal losses detected."
        ::= { wfTokenRingEntry 27 }

    wfTokenRingHardErrors OBJECT-TYPE
        SYNTAX	Counter
        ACCESS	read-only
        STATUS	mandatory
        DESCRIPTION
                "Number of events causing the adapter to transmit or receive beacon
                MAC frames."
        ::= { wfTokenRingEntry 28 }

    wfTokenRingSoftErrors OBJECT-TYPE
        SYNTAX	Counter
        ACCESS	read-only
        STATUS	mandatory
        DESCRIPTION
                "Number of soft errors. Corresponds to the number of Report Error MAC
                frames transmitted by this station."
        ::= { wfTokenRingEntry 29 }

    wfTokenRingTransmitBeacons OBJECT-TYPE
        SYNTAX	Counter
        ACCESS	read-only
        STATUS	mandatory
        DESCRIPTION
                "Number of events causing the adapter to transmit beacon frames."
        ::= { wfTokenRingEntry 30 }

    wfTokenRingLobeWireFaults OBJECT-TYPE
        SYNTAX	Counter
        ACCESS	read-only
        STATUS	mandatory
        DESCRIPTION
                "Number of opens or shorts (cable faults) between the adapter and
                the MAU."
        ::= { wfTokenRingEntry 31 }

    wfTokenRingAutoRemovalErrors OBJECT-TYPE
        SYNTAX	Counter
        ACCESS	read-only
        STATUS	mandatory
        DESCRIPTION
                "Number of lobe wrap test failures during beacon auto_removal process."
        ::= { wfTokenRingEntry 32 }

    wfTokenRingRequestRemoves OBJECT-TYPE
        SYNTAX	Counter
        ACCESS	read-only
        STATUS	mandatory
        DESCRIPTION
                "Number of Remove Ring Station MAC frames received. Each frame causes
                this station to leave the ring."
        ::= { wfTokenRingEntry 33 }

    wfTokenRingCounterOverflows OBJECT-TYPE
        SYNTAX	Counter
        ACCESS	read-only
        STATUS	mandatory
        DESCRIPTION
                "Number of adapter error counter overflows."
        ::= { wfTokenRingEntry 34 }

    wfTokenRingSingleStations OBJECT-TYPE
        SYNTAX	Counter
        ACCESS	read-only
        STATUS	mandatory
        DESCRIPTION
                "Number of ring status change interrupts while adapter is only station
                on the ring."
        ::= { wfTokenRingEntry 35 }

    wfTokenRingRingRecoveries OBJECT-TYPE
        SYNTAX	Counter
        ACCESS	read-only
        STATUS	mandatory
        DESCRIPTION
                "Number of claim token MAC frames (ring recoveries) observed on
                the ring."
        ::= { wfTokenRingEntry 36 }

    wfTokenRingAdapterChecks OBJECT-TYPE
        SYNTAX	Counter
        ACCESS	read-only
        STATUS	mandatory
        DESCRIPTION
                "Number of internal adapter errors that result in adapter crashes."
        ::= { wfTokenRingEntry 37 }

    wfTokenRingFirstAdapterCheckCode OBJECT-TYPE
        SYNTAX	INTEGER
        ACCESS	read-only
        STATUS	mandatory
        DESCRIPTION
                "Adapter Check Code of first occurrence."
        ::= { wfTokenRingEntry 38 }

    wfTokenRingLastAdapterCheckCode OBJECT-TYPE
        SYNTAX	INTEGER
        ACCESS	read-only
        STATUS	mandatory
        DESCRIPTION
                "Adapter Check Code of most recent (last) occurrence."
        ::= { wfTokenRingEntry 39 }

    wfTokenRingLineErrors OBJECT-TYPE
        SYNTAX	Counter
        ACCESS	read-only
        STATUS	mandatory
        DESCRIPTION
                "Number of frames copied or repeated by this station with bad
                format or an FCS error."
        ::= { wfTokenRingEntry 40 }

    wfTokenRingBurstErrors OBJECT-TYPE
        SYNTAX	Counter
        ACCESS	read-only
        STATUS	mandatory
        DESCRIPTION
                "Number of errored frames with no transition for 5 1/2 bit times."
        ::= { wfTokenRingEntry 41 }

    wfTokenRingAriFciErrors OBJECT-TYPE
        SYNTAX	Counter
        ACCESS	read-only
        STATUS	mandatory
        DESCRIPTION
                "Number of occurrences of this station receiving both an AMP MAC
                frame and a SMP MAC frame with the a & c bits clear or more than
                one SMP MAC frame with the a & c bits clear without an intervening
                AMP MAC frame.  This condition indicates that the up-stream
                neighbor is unable to set the a & c bits in a frame that it has
                copied."
        ::= { wfTokenRingEntry 42 }

    wfTokenRingLostFrameErrors OBJECT-TYPE
        SYNTAX	Counter
        ACCESS	read-only
        STATUS	mandatory
        DESCRIPTION
                "Number of frames being stripped which are missing their tails."
        ::= { wfTokenRingEntry 43 }

    wfTokenRingRxCongestionErrors OBJECT-TYPE
        SYNTAX	Counter
        ACCESS	read-only
        STATUS	mandatory
        DESCRIPTION
                "Number of frames dropped due to receive congestion."
        ::= { wfTokenRingEntry 44 }

    wfTokenRingFrameCopiedErrors OBJECT-TYPE
        SYNTAX	Counter
        ACCESS	read-only
        STATUS	mandatory
        DESCRIPTION
                "Number of specifically addressed frames for this station that had
                their a & c bits previously set."
        ::= { wfTokenRingEntry 45 }

    wfTokenRingTokenErrors OBJECT-TYPE
        SYNTAX	Counter
        ACCESS	read-only
        STATUS	mandatory
        DESCRIPTION
                "Number of token protocol errors. Only relevant when this station is
                the active monitor."
        ::= { wfTokenRingEntry 46 }

    wfTokenRingDmaBusErrors OBJECT-TYPE
        SYNTAX	Counter
        ACCESS	read-only
        STATUS	mandatory
        DESCRIPTION
                "Number of bus errors during DMA that do not exceed threshold."
        ::= { wfTokenRingEntry 47 }

    wfTokenRingDmaParityErrors OBJECT-TYPE
        SYNTAX	Counter
        ACCESS	read-only
        STATUS	mandatory
        DESCRIPTION
                "Number of parity errors during DMA that do not exceed threshold."
        ::= { wfTokenRingEntry 48 }

    wfTokenRingSrbNotFreeCmdAborts OBJECT-TYPE
        SYNTAX	Counter
        ACCESS	read-only
        STATUS	mandatory
        DESCRIPTION
                "Number of host to adapter commands aborted because of in-completed in
                process commands."
        ::= { wfTokenRingEntry 49 }

    wfTokenRingRxProcessings OBJECT-TYPE
        SYNTAX	Counter
        ACCESS	read-only
        STATUS	mandatory
        DESCRIPTION
                "Number of processings of received frames (similar to RINT)."
        ::= { wfTokenRingEntry 50 }

    wfTokenRingTxProcessings OBJECT-TYPE
        SYNTAX	Counter
        ACCESS	read-only
        STATUS	mandatory
        DESCRIPTION
                "Number of processings of frames for transmit."
        ::= { wfTokenRingEntry 51 }

    wfTokenRingTxCmplProcessings OBJECT-TYPE
        SYNTAX	Counter
        ACCESS	read-only
        STATUS	mandatory
        DESCRIPTION
                "Number of processings of transmitted frames (similar to TINT)."
        ::= { wfTokenRingEntry 52 }

    wfTokenRingRxTimeouts OBJECT-TYPE
        SYNTAX	Counter
        ACCESS	read-only
        STATUS	mandatory
        DESCRIPTION
                "Number of re-initializations due to receiver time-outs."
        ::= { wfTokenRingEntry 53 }

    wfTokenRingCmdTimeouts OBJECT-TYPE
        SYNTAX	Counter
        ACCESS	read-only
        STATUS	mandatory
        DESCRIPTION
                "Number of re-initializations due to command time-outs."
        ::= { wfTokenRingEntry 54 }

    wfTokenRingRxHostIntErrors OBJECT-TYPE
        SYNTAX	Counter
        ACCESS	read-only
        STATUS	mandatory
        DESCRIPTION
                "Number of re-initializations due to receive host interface errors."
        ::= { wfTokenRingEntry 55 }

    wfTokenRingRxTxBufferSize OBJECT-TYPE
        SYNTAX	INTEGER
        ACCESS	read-only
        STATUS	mandatory
        DESCRIPTION
                "Internal Adapter RAM buffer size."
        ::= { wfTokenRingEntry 56 }

    wfTokenRingCfgTxQueueLength OBJECT-TYPE
        SYNTAX	INTEGER(0..255)
        ACCESS	read-write
        STATUS	mandatory
        DESCRIPTION
                "Configured Transmit Queue Length. Values other than zero over-ride the
                router selected values.  A value of zero has a special meaning.  Zero
                causes router based default values to be used.  Values larger than the
                compiled ring size are truncated to the compiled ring size. "
        ::= { wfTokenRingEntry 57 }

    wfTokenRingCfgRxQueueLength OBJECT-TYPE
        SYNTAX	INTEGER(0..255)
        ACCESS	read-write
        STATUS	mandatory
        DESCRIPTION
                "Configured Receive Queue Length. Values other than zero over-ride the
                router selected values.  A value of zero has a special meaning.  Zero
                causes router based default values to be used.  Values larger than the
                compiled ring size are truncated to the compiled ring size. "
        ::= { wfTokenRingEntry 58 }

    wfTokenRingTxQueueLength OBJECT-TYPE
        SYNTAX	INTEGER
        ACCESS	read-only
        STATUS	mandatory
        DESCRIPTION
                "Current Transmit Queue Length."
        ::= { wfTokenRingEntry 59 }

    wfTokenRingRxQueueLength OBJECT-TYPE
        SYNTAX	INTEGER
        ACCESS	read-only
        STATUS	mandatory
        DESCRIPTION
                "Current Receive Queue Length."
        ::= { wfTokenRingEntry 60 }

    wfTokenRingMacRxOctets OBJECT-TYPE
        SYNTAX	Counter
        ACCESS	read-only
        STATUS	mandatory
        DESCRIPTION
                "Number of Mac frame octets received without error."
        ::= { wfTokenRingEntry 61 }

    wfTokenRingMacRxFrames OBJECT-TYPE
        SYNTAX	Counter
        ACCESS	read-only
        STATUS	mandatory
        DESCRIPTION
                "Number of Mac frames received without error."
        ::= { wfTokenRingEntry 62 }

    wfTokenRingCfgFunctionalAddress OBJECT-TYPE
        SYNTAX	INTEGER {
    		    mask(2147467520)
    		}
        ACCESS	read-write
        STATUS	mandatory
        DESCRIPTION
                "The configurable bit mask of all Token Ring Functional addresses for which
                this interface will accept frames. This value is loaded into the func addr
                defined in the attribute 'wfTokenRingFunctionalAddress.'
                note: 2147467520 = 0x7fffc100"
        DEFVAL	{ mask }
        ::= { wfTokenRingEntry 63 }

    wfTokenRingFunctionalAddress OBJECT-TYPE
        SYNTAX	INTEGER
        ACCESS	read-only
        STATUS	mandatory
        DESCRIPTION
                "The bit mask of all Token Ring Functional addresses for which this
                interface will accept frames."
        ::= { wfTokenRingEntry 64 }

    wfTokenRingGroupAddress OBJECT-TYPE
        SYNTAX	INTEGER
        ACCESS	read-only
        STATUS	mandatory
        DESCRIPTION
                "The single Token Ring Group address for which this interface will
                accept frames."
        ::= { wfTokenRingEntry 65 }

    wfTokenRingLineNumber OBJECT-TYPE
        SYNTAX	INTEGER
        ACCESS	read-write
        STATUS	mandatory
        DESCRIPTION
                "Logical line number associated with this driver entity."
        ::= { wfTokenRingEntry 66 }

    wfTokenRingMacCode OBJECT-TYPE
        SYNTAX	DisplayString
        ACCESS	read-only
        STATUS	mandatory
        DESCRIPTION
                "Type and version of microcode running on the TMS380."
        ::= { wfTokenRingEntry 67 }

    wfTokenRingModule OBJECT-TYPE
        SYNTAX	INTEGER {
    		    one(1),
    		    two(2),
    		    three(3),
    		    four(4)
    		}
        ACCESS	read-only
        STATUS	mandatory
        DESCRIPTION
                "Module number for ASN platform, filled in by driver. For non-ASN
                platforms this attribute will not be used."
        ::= { wfTokenRingEntry 68 }

    wfTokenRingActualConnector OBJECT-TYPE
        SYNTAX	INTEGER {
    		    one(1),
    		    two(2),
    		    three(3),
    		    four(4)
    		}
        ACCESS	read-only
        STATUS	mandatory
        DESCRIPTION
                "Actual connector number for ASN platform, filled in by
                driver. For non-ASN platforms this attribute will not be used."
        ::= { wfTokenRingEntry 69 }

    wfTokenRingLastChange OBJECT-TYPE
        SYNTAX	TimeTicks
        ACCESS	read-only
        STATUS	mandatory
        DESCRIPTION
                "The value of SysUpTime at the time the interface entered it's current
                operational state (UP state).  SysUpTime is defined as the time (in
                hundredths of a second) since the network management portion of the
                system was last re-initialized.  Usually the time since boot."
        ::= { wfTokenRingEntry 70 }

    wfTokenRingOutQLen OBJECT-TYPE
        SYNTAX	Gauge
        ACCESS	read-only
        STATUS	mandatory
        DESCRIPTION
                "The instantaneous current length of the output packet queue (in packets)."
        ::= { wfTokenRingEntry 71 }

    wfTokenRingForceMacCode OBJECT-TYPE
        SYNTAX	INTEGER {
    		    timac(1),
    		    fastmac(2),
    		    fastmacplus(3),
    		    fastmacplusb(4)
    		}
        ACCESS	read-write
        STATUS	mandatory
        DESCRIPTION
                "Selector determines which microcode will be downloaded for the TMS380."
        ::= { wfTokenRingEntry 72 }

    wfTokenRingMSBMadr OBJECT-TYPE
        SYNTAX	OCTET STRING
        ACCESS	read-only
        STATUS	mandatory
        DESCRIPTION
                "Provides this interface's MAC address in Most Significant Bit (MSB)
                format.  This format is also referred to as Token Ring or IBM format.
                This MAC address is the same MAC address as given in the wfTokenRingMadr
                attribute except that wfTokenRingMadr is displayed in ethernet format."
        ::= { wfTokenRingEntry 73 }

    wfTokenRingTurboBoflDebug OBJECT-TYPE
        SYNTAX	INTEGER
        ACCESS	read-write
        STATUS	mandatory
        DESCRIPTION
                "Special Turbo-BOFL debug mechanism to be used by Engineering
		 and Manufacturing only.
		 31-24 : TMO - period of breath (amount of time between
						 successive breaths of life)
		 23-16 : Number of packets per breath.
		 15-0  : Packet length in bytes - 22 bytes minimum.
		 All bits set to zero will disable this attribute."
		
        DEFVAL	{ 0 }
        ::= { wfTokenRingEntry 74 }

    wfTokenRingSingleStatDis OBJECT-TYPE
        SYNTAX  INTEGER {
                    enabled(1),
                    disabled(2)
                }
        ACCESS  read-write
        STATUS  mandatory
        DESCRIPTION
                "Enable/Disable the single station mode"
        DEFVAL  { enabled }
        ::= { wfTokenRingEntry 75 }

    END  -- Wellfleet-TOKEN-RING-MIB
