AirDefense-airCommand-MIB DEFINITIONS::=BEGIN

IMPORTS

	NOTIFICATION-TYPE, enterprises
		
		FROM SNMPv2-SMI

	OBJECT-TYPE
		
		FROM RFC-1212;





airDefense OBJECT IDENTIFIER::={enterprises 13416 }

airDefenseProducts OBJECT IDENTIFIER::={airDefense 1}

airCommand OBJECT IDENTIFIER::={airDefenseProducts 1}

airCommandEventTable OBJECT-TYPE

	SYNTAX SEQUENCE OF AirCommandEventEntry

	MAX-ACCESS	read-only

	STATUS		current

	DESCRIPTION

		"Table of airCommand Events"

	::={airCommand 1}

	airCommandEventEntry	OBJECT-TYPE

		SYNTAX		AirCommandEventEntry

		MAX-ACCESS	not-accessible

		STATUS		current
		
		DESCRIPTION	""

		INDEX		{airCommandEventId }

		::={airCommandEventTable 1}


	AirCommandEventEntry::=

		SEQUENCE {

			airCommandEventId		INTEGER,
			airCommandEventPriority		INTEGER, 
			airCommandEventDescriptor	OCTET STRING,
			airCommandEventCount		INTEGER

			}


	airCommandEventId	OBJECT-TYPE
		
		SYNTAX		INTEGER

		MAX-ACCESS	read-only

		STATUS		current

		DESCRIPTION	"Unique Identifier for the Event"

		::={airCommandEventEntry 1}



	airCommandEventPriority	OBJECT-TYPE

		SYNTAX		INTEGER{critical(1),major(2),minor(3),low(4)}

		MAX-ACCESS	read-only

		STATUS		current	

		DESCRIPTION	"The priority of Event that Occurred"

		::={airCommandEventEntry 2}


	airCommandEventDescriptor	OBJECT-TYPE

		SYNTAX		OCTET STRING (SIZE(0..1024))

		MAX-ACCESS	read-only

		STATUS		current	

		DESCRIPTION	"Information to Provide Detail Regarding the Event"

		::={airCommandEventEntry 3}

	airCommandEventCount	OBJECT-TYPE

		SYNTAX		INTEGER	

		MAX-ACCESS	read-only

		STATUS		current	

		DESCRIPTION	"Count of the Number of Events of this Priority since the Last Update"

		::={airCommandEventEntry 4}

airCommandAlarm NOTIFICATION-TYPE

	OBJECTS		{airCommandEventPriority,airCommandEventDescriptor,airCommandEventCount}

	STATUS		current

	DESCRIPTION	"AirCommand Alarms with ID,Priority and Description"

	::={airCommand 2}


END
