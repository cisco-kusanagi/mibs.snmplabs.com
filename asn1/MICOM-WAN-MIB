--
-- Based on Jan Medved mail Dated July 09, 1996
-- MIB Revision Dated: 08-20-96 
-- 
-- MIB Revision : 1.0 dated 1-17-97
-- Change Desc. : None. 
-- 
-- MIB Revision : 1.1 dated 3-13-97
-- Change Desc. : Added control group to allow WAN stats reset. 
-- Change Desc. : Specified ranges for different objects. 
-- 
-- 
-- MIB Revision : 1.2 dated 4-04-97
-- Change Desc. : Changed wanIfType (std and nvm) to an enumeration . -A.Llanes
-- 
-- 
--   *** 4400 RELEASE 1.1 ***
-- MIB Revision : 1.5 dated 4-30-97
-- Change Desc. : Added access privileges to capabilities field - S.Gaur. 
-- Added FR DCE related changes as per FR DCE/HTDS MIB Req't Document
-- (dated 4/20/97) - R. Carmona.
-- 
-- 
-- MIB Revision : 1.6 dated 5-8-97
-- Change Desc. : Rearranged FR DCE related objects for SNMP compliance
--		for modifications from 4400 1.0 to 4400 1.1. - R. Carmona
-- 
-- MIB Revision : 1.7 dated 5-17-97
-- Change Desc. : Updated Description entry DESC -BP
--
-- *** 4400 RELEASE 2.0 ***
-- MIB Revision : 2.0 dated 7-24-97
-- Change Desc. : Added enumerations for WanifProtocolSupType objects
--		  to add HTDS functionality as per 7/22/97 meeting
--		  with RC, Bhushan, Amparo, Dave S., Tom M., Melanie G.,
--		  BS, and KS.  
--		  Also, changed Integer range of WanifChannel objects 
--		  from 1..2 to 1..8. -R. Carmona 
--
-- MIB Revision : 2.1 dated 8-28-97
-- Change Desc. : Changed nvmWanifTDSCutThru ACCESS from read-only to
--		  read-write as per 8/28/97 conversation with Dave S.
--		  (made it a configurable object for HTDS fragmentation).
--		  -R. Carmona 
--
-- MIB Revision : 2.2 dated 10-14-97
-- Change Desc. : Replaced MPA with 4400, and other minor changes - B. Jafari. 
--
-- MIB Revision : 2.3 dated 10-17-97
-- Change Desc. : Replaced all MIPs with FRAGs.
--		  Added a VoFR statistic group. - K. Yeh
--
-- MIB Revision : 2.4 dated 10-23-97
-- Change Desc. : Changed VoFr statistics from group to table. - K. Yeh
--
-- MIB Revision : 2.5 dated 11-3-97
-- Change Desc. : Added a Vofr Counter group. - K. Yeh
--
--
-- MIB Revision : 2.6 dated 11-10-97
-- Change Desc. : Added tables to provide user capability to provision
--                DCLIs for the tunneling PVC superframes.
--                (nvm)wanDtePortTunnelPvcTables. - S. Gaur
--
-- MIB Revision : 2.7 dated 12-4-97
-- Change Desc. : Changed baudrate to an enumeration.
--
-- MIB Revision : 2.8 dated 12-18-97
-- Change Desc. : Added two enumerations to wanifType.
--
-- MIB Revision : 2.9 dated 2-12-98
-- Change Desc. : Renamed (nvm)wanifSlot to (nvm)wanifLim
--                (lim = logical interface module), and changed syntax
--                field enumeration for (nvm)wanifLim objects. - B. Jafari
--
-- *** RELEASE 3.0 ***
-- MIB Revision : 3.0 dated 5-28-98
-- Change Desc. : Added the nvmwanifTDSIdleChar and 
--                 wanifTDSIdleChar objects.
--                Added the nvmwanifTDSSyncChar and 
--                 wanifTDSSyncChar objects.
--                Modified the enumeration parameters for 
--                  nvmWanifProtocolSupType and wanifProtocolSupType.
--                Deprecated the nvmWanDTEPortTunnelPvcTable
--                 and the wanDTEPortTunnelPvcTable, replacing 
--                them with the (mcm/nvm)NetlinkTable's in the 
--                Frame Relay MIB.
--                Changed the range for nvmWanifTxFragQueueSize from 10 
--                 to 5.          
--                Added the e1csu enumeration to wanifType and 
--                 nvmWanifType. 
--                Obsoleted the wanifFragStatisticsTable as per e-mail 
--                 from T. Messick/P. Bailey. 
--                Obsoleted wanifControlLineOn and nvmWanifControlLineOn
--                Obsoleted wanifFragFragmentSize and nvmWanifFragFragmentSize
--                Obsoleted wanifRowStatus and nvmWanifRowStatus 
--                The above six obsoletions were  per K. Seggelke/T. Messick
--                Added DEFVALs to certain nvm objects.
--                Replaced all instances of the string "4400" with the 
--                generic string "access device".
--                                                 -   S. Gaur, A. Llanes
--
-- MIB Revision : 3.1 dated 7-2-98
-- Change Desc. : Added the wanifEncodeMethod and nvmwanifEncodeMethod
--                objects.
--                Obsoleted the following tables: wanifCounterGlobalTable,
--                wanifCounterFragTable and wanifVofrCounterTable.
--
-- MIB Revision : 3.2 dated 9-2-98
-- Change Desc. : Modified the minimum range for wanifBaudRate and 
--                nvmWanifBaudRate to 300 as per K. Seggeleke.
--                                                       -S. Gaur
--

MICOM-WAN-MIB DEFINITIONS ::= BEGIN
	IMPORTS
		Counter
                   		 	FROM RFC1155-SMI
		OBJECT-TYPE
                    			FROM RFC-1212
	    	micom-oscar 
		    			FROM MICOM-OSCAR-MIB;

-- group OBJECT IDENTIFIERs

	micom-wan			OBJECT IDENTIFIER ::= {micom-oscar 2}
	wan-configuration	 	OBJECT IDENTIFIER ::= {micom-wan 1}
	wan-statistics 			OBJECT IDENTIFIER ::= {micom-wan 2}
	wan-control 			OBJECT IDENTIFIER ::= {micom-wan 3}

--
--	Port Configuration 
--

wanifTable OBJECT-TYPE
	SYNTAX	SEQUENCE OF WanifEntry
	ACCESS	not-accessible
	STATUS	mandatory
	DESCRIPTION
	  "NAME = ;
	   DESC = The WAN interface Table;
	   HELP = ;
	   CAPABILITIES = NET_CFG, VPN_DISP;"
	::= {wan-configuration 1}

wanifEntry OBJECT-TYPE
	SYNTAX	WanifEntry
	ACCESS	not-accessible
	STATUS	mandatory
	DESCRIPTION
	  "NAME = ;
	   DESC = WAN inteface entry object;
	   HELP = ;
	   CAPABILITIES = ;"
	INDEX { wanifIndex }
	::= { wanifTable 1}

WanifEntry ::= SEQUENCE {
	wanifIndex			INTEGER,
	wanifType			INTEGER,
	wanifMode			INTEGER,
	wanifBaudRate			INTEGER,
	wanifMaxFrameSize		INTEGER,
	wanifProtocolType		INTEGER,
	wanifControlLineOn		INTEGER,
	wanifNumRxBuffers		INTEGER,
	wanifRxFragQueueSize		INTEGER,
	wanifTxFragQueueSize		INTEGER,
	wanifFragFragmentSize		INTEGER,
	wanifRowStatus			INTEGER,
	wanifLim			INTEGER,
	wanifChannel			INTEGER,
	wanifProtocolSupType		INTEGER,
	wanifTDSCutThru			INTEGER,
	wanifTDSFragSize		INTEGER,
        wanifTDSIdleChar                INTEGER,
        wanifTDSSyncChar                INTEGER,
        wanifEncodeMethod               INTEGER
	}

wanifIndex OBJECT-TYPE
	SYNTAX	INTEGER (1..255)
	ACCESS	read-only
	STATUS	mandatory
	DESCRIPTION
	  "NAME = ;
	   DESC = IfIndex value for WAN port;
	   HELP = Same as corresponding ifIndex value in \
		  ifTable;
	   CAPABILITIES = ;"
	::= {wanifEntry 1}

wanifType OBJECT-TYPE
	SYNTAX	INTEGER {
		none (1),
		rs232 (2),
		v35 (5),
		x21 (6),
		v36 (7),
		csu-dsu (8),
                isdn-BRI (9),
                t1csu (10),
                e1csu (11)
		}
	ACCESS	read-only
	STATUS	mandatory
	DESCRIPTION
	  "NAME = ;
	   DESC = Signalling characteristics for WAN interface;
	   HELP = ;
	   CAPABILITIES = ;"
	::= {wanifEntry 2}

wanifMode OBJECT-TYPE
	SYNTAX	INTEGER {
		dce (1),
		dte (2)
		}
	ACCESS	read-only
	STATUS	mandatory
	DESCRIPTION
	  "NAME = ;
	   DESC = Determines whether the access device \
                  receives or transmits clocking signals;
	   HELP = ;
	   CAPABILITIES = ;"
	::= {wanifEntry 3}

wanifBaudRate OBJECT-TYPE
	SYNTAX	INTEGER (300..1920000)
	ACCESS	read-only
	STATUS	mandatory
	DESCRIPTION
	  "NAME = ;
	   DESC = WAN port clocking speed in bits per second \
		  R'qd for DCE, optn'l for DTE.;
	   HELP = Wan link speed. This parameter is not\
		  valid if DTE option is selected for \
		  wanifMode object;
	   CAPABILITIES = ;"
	::= {wanifEntry 4}

wanifMaxFrameSize OBJECT-TYPE
	SYNTAX	INTEGER (1..8192)
	ACCESS	read-only
	STATUS	mandatory
	DESCRIPTION
	  "NAME = ;
	   DESC = Max rcvd frame size allowed at interface;
	   HELP = ;
	   CAPABILITIES = ;"
	::= {wanifEntry 5}

wanifProtocolType OBJECT-TYPE
	SYNTAX	INTEGER {
		hdlc (1)
		}
	ACCESS	read-only
	STATUS	mandatory
	DESCRIPTION
	  "NAME = ;
	   DESC = Link protocol type;
	   HELP = ;
	   CAPABILITIES = ;"
	::= {wanifEntry 6}

wanifControlLineOn OBJECT-TYPE
	SYNTAX	INTEGER {
		yes (1),
		no (2)
		}
	ACCESS	read-only 
	STATUS	obsolete
	DESCRIPTION
	  "NAME = ;
	   DESC = *** NOTE THIS OBJECT IS OBSOLETE *** \
                  Determines whether the control lines are \
		  driven/monitored;
	   HELP = ;
	   CAPABILITIES = ;"
	::= {wanifEntry 7}

wanifNumRxBuffers OBJECT-TYPE
	SYNTAX	INTEGER (20..255)
	ACCESS	read-only
	STATUS	mandatory
	DESCRIPTION
	  "NAME = ;
	   DESC = Number of configured receive buffers;
	   HELP = ;
	   CAPABILITIES = ;"
	::= {wanifEntry 8}

wanifRxFragQueueSize OBJECT-TYPE
	SYNTAX	INTEGER (10..255)
	ACCESS	read-only
	STATUS	mandatory
	DESCRIPTION
	  "NAME = ;
	   DESC = The size (in frames) of Frag receive \
		  queue (one queue per priority);
	   HELP = ;
	   CAPABILITIES = ;"
	::= {wanifEntry 9}

wanifTxFragQueueSize OBJECT-TYPE
	SYNTAX	INTEGER (5..255)
	ACCESS	read-only
	STATUS	mandatory
	DESCRIPTION
	  "NAME = ;
	   DESC = The size (in frames) of Frag transmit \
		  (one queue per priority);
	   HELP = ;
	   CAPABILITIES = ;"
	::= {wanifEntry 10}

wanifFragFragmentSize OBJECT-TYPE
	SYNTAX	INTEGER (80..8192)
	ACCESS	read-only
	STATUS	obsolete
	DESCRIPTION
	  "NAME = ;
	   DESC = *** NOTE THIS OBJECT IS OBSOLETE ***\
                  Size of MFP fragments in bytes;
	   HELP = ;
	   CAPABILITIES = ;"
	::= {wanifEntry 11}

wanifRowStatus OBJECT-TYPE
	SYNTAX	INTEGER
	ACCESS	read-only
	STATUS	obsolete
	DESCRIPTION
	  "NAME = ;
	   DESC = *** NOTE THIS OBJECT IS OBSOLETE ***\
                  Row status for WAN interface;
	   HELP = ;
	   CAPABILITIES = ;"
	::= {wanifEntry 12}

wanifLim OBJECT-TYPE
	SYNTAX	INTEGER {
		limA (1),
		lim1 (2),
		lim2 (3),
		lim3 (4),
		lim4 (5)
		}
	ACCESS	read-only
	STATUS	mandatory
	DESCRIPTION
	  "NAME = ;
	   DESC = The lim (logical interface module) number \
  		  of this WAN port (operational);
	   HELP = ;
	   CAPABILITIES = ;"
	::= {wanifEntry 13}

wanifChannel OBJECT-TYPE
	SYNTAX	INTEGER (1..8)
	ACCESS	read-only
	STATUS	mandatory
	DESCRIPTION
	  "NAME = ;
	   DESC = The channel number of this WAN port. \
  		  (SCC number);
	   HELP = ;
	   CAPABILITIES = ;"
	::= {wanifEntry 14}

wanifProtocolSupType OBJECT-TYPE
	SYNTAX	INTEGER {
		none (1),
		standardFr (2),
		switchingFr (3),
		htds (4),
                cbr (5)
		}
	ACCESS	read-only
	STATUS	mandatory
	DESCRIPTION
	  "NAME = ;
	   DESC = The protocol supported on this interface. ;
	   HELP = ;
	   CAPABILITIES = ;"
	::= {wanifEntry 15}

wanifTDSCutThru OBJECT-TYPE
	SYNTAX	INTEGER {
		yes (1),
		no (2)
		}
	ACCESS	read-only
	STATUS	mandatory
	DESCRIPTION
	  "NAME = ;
	   DESC = Fragmenting enabled/disabled.  This parameter \
		  only valid for HTDS protocol.;
	   HELP = ;
	   CAPABILITIES = ;"
	::= {wanifEntry 16}

wanifTDSFragSize OBJECT-TYPE
	SYNTAX	INTEGER 
	ACCESS	read-only
	STATUS	mandatory
	DESCRIPTION
	  "NAME = ;
	   DESC = TDS cutThru computed fragment/buffer size. \
		  This parameter only valid for HTDS protocol.;
	   HELP = ;
	   CAPABILITIES = ;"
	::= {wanifEntry 17}

wanifTDSIdleChar OBJECT-TYPE
	SYNTAX	INTEGER (1..255) 
	ACCESS	read-only
	STATUS	mandatory
	DESCRIPTION
	  "NAME = ;
	   DESC = The idle character required for  \
                  Constant Bit Rate transfer.;
	   HELP = ;
	   CAPABILITIES = ;"
	::= {wanifEntry 18}

wanifTDSSyncChar OBJECT-TYPE
	SYNTAX	INTEGER (1..255) 
	ACCESS	read-only
	STATUS	mandatory
	DESCRIPTION
	  "NAME = ;
	   DESC = The 8 bit Syncronization character \
                  required by the Constant Bit Rate (CBR) \
                  transfer method.;
	   HELP = ;
	   CAPABILITIES = ;"
	::= {wanifEntry 19}

wanifEncodeMethod OBJECT-TYPE
	SYNTAX	INTEGER {
                nrz        (1),
                nrzi-mark  (2),
                nrzi-space (3)
                } 
	ACCESS	read-only
	STATUS	mandatory
	DESCRIPTION
	  "NAME = ;
	   DESC = The value of this object indicates the  \
                  port transmit/receive data encoding     \
                  method.;
	   HELP = ;
	   CAPABILITIES = ;"
	::= {wanifEntry 20}

--
-- 	Parallel Port Configuration
--

nvmWanifTable OBJECT-TYPE
	SYNTAX	SEQUENCE OF NvmWanifEntry
	ACCESS	not-accessible
	STATUS	mandatory
	DESCRIPTION
	  "NAME = ;
	   DESC = The WAN interface Table;
	   HELP = ;
	   CAPABILITIES = NET_CFG, VPN_DISP;"
	::= {wan-configuration 2}

nvmWanifEntry OBJECT-TYPE
	SYNTAX	NvmWanifEntry
	ACCESS	not-accessible
	STATUS	mandatory
	DESCRIPTION
	  "NAME = ;
	   DESC = WAN inteface entry object;
	   HELP = ;
	   CAPABILITIES = ;"
	INDEX		{nvmWanifIndex }
	::= { nvmWanifTable 1}

NvmWanifEntry ::= SEQUENCE {
	nvmWanifIndex			INTEGER,
	nvmWanifType			INTEGER,
	nvmWanifMode			INTEGER,
	nvmWanifBaudRate		INTEGER,
	nvmWanifMaxFrameSize		INTEGER,
	nvmWanifProtocolType		INTEGER,
	nvmWanifControlLineOn		INTEGER,
	nvmWanifNumRxBuffers		INTEGER,
	nvmWanifRxFragQueueSize		INTEGER,
	nvmWanifTxFragQueueSize		INTEGER,
	nvmWanifFragFragmentSize	INTEGER,
	nvmWanifRowStatus		INTEGER,
	nvmWanifLim			INTEGER,
	nvmWanifChannel			INTEGER,
	nvmWanifProtocolSupType		INTEGER,
	nvmWanifTDSCutThru		INTEGER,
	nvmWanifTDSFragSize		INTEGER,
        nvmWanifTDSIdleChar             INTEGER,
        nvmWanifTDSSyncChar             INTEGER,
        nvmWanifEncodeMethod            INTEGER
        
	}

nvmWanifIndex OBJECT-TYPE
	SYNTAX	INTEGER (1..255)
	ACCESS	read-only
	STATUS	mandatory
	DESCRIPTION
	  "NAME = ;
	   DESC = IfIndex value for WAN port;
	   HELP = Same as corresponding ifIndex value in \
		  ifTable;
	   CAPABILITIES = ;"
	::= {nvmWanifEntry 1}

nvmWanifType OBJECT-TYPE
	SYNTAX	INTEGER {
		none (1),
		rs232 (2),
		v35 (5),
		x21 (6),
		v36 (7),
		csu-dsu (8),
                isdn-BRI (9),
                t1csu (10),
                e1csu (11)
		}
	ACCESS	read-write
	STATUS	mandatory
	DESCRIPTION
	  "NAME = ;
	   DESC = Signalling characteristics for WAN interface;
	   HELP = ;
	   CAPABILITIES = ;"
	DEFVAL { v35 }
	::= {nvmWanifEntry 2}

nvmWanifMode OBJECT-TYPE
	SYNTAX	INTEGER {
		dce (1),
		dte (2)
		}
	ACCESS	read-write
	STATUS	mandatory
	DESCRIPTION
	  "NAME = ;
	   DESC = Determines whether the access device \
                  receives or transmits clocking signals;
	   HELP = ;
	   CAPABILITIES = ;"
        DEFVAL { dce }
	::= {nvmWanifEntry 3}

nvmWanifBaudRate OBJECT-TYPE
	SYNTAX	INTEGER (300..1920000)
	ACCESS	read-write
	STATUS	mandatory
	DESCRIPTION
	  "NAME = ;
	   DESC = WAN port clocking speed in bits per second \
		  R'qd for DCE, optn'l for DTE.;
	   HELP = Wan link speed. This parameter is not \
		  valid if DTE option is selected for \
		  nvmWanifMode object;
	   CAPABILITIES = ;"
        DEFVAL { 65536 }
	::= {nvmWanifEntry 4}

nvmWanifMaxFrameSize OBJECT-TYPE
	SYNTAX	INTEGER (1..8192)
	ACCESS	read-write
	STATUS	mandatory
	DESCRIPTION
	  "NAME = ;
	   DESC = Max rcvd frame size allowed at interface;
	   HELP = ;
	   CAPABILITIES = ;"
        DEFVAL { 4000 }
	::= {nvmWanifEntry 5}

nvmWanifProtocolType OBJECT-TYPE
	SYNTAX	INTEGER {
		hdlc (1)
		}
	ACCESS	read-only 
	STATUS	mandatory
	DESCRIPTION
	  "NAME = ;
	   DESC = Link protocol type;
	   HELP = ;
	   CAPABILITIES = ;"
        DEFVAL { hdlc }
	::= {nvmWanifEntry 6}

nvmWanifControlLineOn OBJECT-TYPE
	SYNTAX	INTEGER {
		yes (1),
		no (2)
		}
	ACCESS	read-write 
	STATUS	obsolete
	DESCRIPTION
	  "NAME = ;
	   DESC = *** NOTE THIS OBJECT IS OBSOLETE ***\
                  Determines whether the control lines are \
		  driven/monitored;
	   HELP = ;
	   CAPABILITIES = ;"
	::= {nvmWanifEntry 7}

nvmWanifNumRxBuffers OBJECT-TYPE
	SYNTAX	INTEGER (20..255)
	ACCESS	read-write
	STATUS	mandatory
	DESCRIPTION
	  "NAME = ;
	   DESC = Number of configured receive buffers;
	   HELP = ;
	   CAPABILITIES = ;"
	DEFVAL	{ 100 }
	::= {nvmWanifEntry 8}

nvmWanifRxFragQueueSize OBJECT-TYPE
	SYNTAX	INTEGER (10..255)
	ACCESS	read-write
	STATUS	mandatory
	DESCRIPTION
	  "NAME = ;
	   DESC = The size (in frames) of Frag receive \
		  queue (one queue per priority);
	   HELP = ;
	   CAPABILITIES = ;"
	DEFVAL	{ 10 }
	::= {nvmWanifEntry 9}

nvmWanifTxFragQueueSize OBJECT-TYPE
	SYNTAX	INTEGER (5..255)
	ACCESS	read-write
	STATUS	mandatory
	DESCRIPTION
	  "NAME = ;
	   DESC = The size (in frames) of Frag transmit \
		  (one queue per priority). \
                  Note that the minumum range value \
                  is 10 when managing the 2.0 Release \
                  of the access device. ;
	   HELP = ;
	   CAPABILITIES = ;"
	DEFVAL	{ 10 }
	::= {nvmWanifEntry 10}

nvmWanifFragFragmentSize OBJECT-TYPE
	SYNTAX	INTEGER (80..8192)
	ACCESS	read-write
	STATUS	obsolete
	DESCRIPTION
	  "NAME = ;
	   DESC = *** NOTE THIS OBJECT IS OBSOLETE ***\
                  Size of MFP fragments in bytes;
	   HELP = ;
	   CAPABILITIES = ;"
	::= {nvmWanifEntry 11}

nvmWanifRowStatus OBJECT-TYPE
	SYNTAX	INTEGER
	ACCESS	read-write
	STATUS	obsolete
	DESCRIPTION
	  "NAME = ;
	   DESC = *** NOTE THIS OBJECT IS OBSOLETE ***\
                  Row status for WAN interface;
	   HELP = ;
	   CAPABILITIES = ;"
	::= {nvmWanifEntry 12}

nvmWanifLim OBJECT-TYPE
	SYNTAX	INTEGER {
		limA (1),
		lim1 (2),
		lim2 (3),
		lim3 (4),
		lim4 (5)
		}
	ACCESS	read-only
	STATUS	mandatory
	DESCRIPTION
	  "NAME = ;
	   DESC = The lim (logical interface module) number \
  		  of this WAN port (configuration);
	   HELP = ;
	   CAPABILITIES = ;"
	::= {nvmWanifEntry 13}

nvmWanifChannel OBJECT-TYPE
	SYNTAX	INTEGER (1..8)
	ACCESS	read-only
	STATUS	mandatory
	DESCRIPTION
	  "NAME = ;
	   DESC = The channel number of this WAN port. \
  		  (SCC number);
	   HELP = ;
	   CAPABILITIES = ;"
	::= {nvmWanifEntry 14}

nvmWanifProtocolSupType OBJECT-TYPE
	SYNTAX	INTEGER {
		none (1),
		standardFr (2),
		switchingFr (3),
		htds (4),
                cbr (5)
		}
	ACCESS	read-write
	STATUS	mandatory
	DESCRIPTION
	  "NAME = ;
	   DESC = The protocol supported on this interface. ;
	   HELP = ;
	   CAPABILITIES = ;"
	DEFVAL { 1 }
	::= {nvmWanifEntry 15}

nvmWanifTDSCutThru OBJECT-TYPE
	SYNTAX	INTEGER {
		yes (1),
		no (2)
		}
	ACCESS	read-write
	STATUS	mandatory
	DESCRIPTION
	  "NAME = ;
	   DESC = Fragmenting enabled/disabled.  This parameter \
		  only valid for HTDS protocol.;
	   HELP = ;
	   CAPABILITIES = ;"
        DEFVAL { no }
	::= {nvmWanifEntry 16}

nvmWanifTDSFragSize OBJECT-TYPE
	SYNTAX	INTEGER 
	ACCESS	read-only
	STATUS	mandatory
	DESCRIPTION
	  "NAME = ;
	   DESC = TDS cutThru computed fragment/buffer size. \
		  This parameter only valid for HTDS protocol.;
	   HELP = ;
	   CAPABILITIES = ;"
	::= {nvmWanifEntry 17}

nvmWanifTDSIdleChar OBJECT-TYPE
	SYNTAX	INTEGER (1..255) 
	ACCESS	read-write
	STATUS	mandatory
	DESCRIPTION
	  "NAME = ;
	   DESC = The idle character required by  \
                  the Constant Bit Rate (CBR) \
                  transfer method.;
	   HELP = ;
	   CAPABILITIES = ;"
	DEFVAL	{ 255 }
	::= {nvmWanifEntry 18}

nvmWanifTDSSyncChar OBJECT-TYPE
	SYNTAX	INTEGER (1..255) 
	ACCESS	read-write
	STATUS	mandatory
	DESCRIPTION
	  "NAME = ;
	   DESC = The 8 bit Syncronization character \
                  required by the Constant Bit Rate (CBR) \
                  transfer method.;
	   HELP = ;
	   CAPABILITIES = ;"
	DEFVAL	{ 126 }
	::= {nvmWanifEntry 19}

nvmWanifEncodeMethod OBJECT-TYPE
	SYNTAX	INTEGER {
                nrz        (1),
                nrzi-mark  (2),
                nrzi-space (3)
                } 
	ACCESS	read-write
	STATUS	mandatory
	DESCRIPTION
	  "NAME = ;
	   DESC = The value of this object indicates the  \
                  port transmit/receive data encoding     \
                  method.;
	   HELP = ;
	   CAPABILITIES = ;"
        DEFVAL { nrz }
	::= {nvmWanifEntry 20}


-- This table allows the user to monitor DLCIs for the Tunneling
-- PVC Superframes. DLCIs are configured for each DTE port residing
-- on the access device.(Operational)
--
-- NOTE That the table below has been deprecated 
-- and its functionality has been replaced by 
-- the mcmNetLinkTable located in the Frame Relay MIB.

wanDTEPortTunnelPvcTable OBJECT-TYPE
	SYNTAX	SEQUENCE OF WanDTEPortTunnelPvcEntry
	ACCESS	not-accessible
	STATUS	deprecated
	DESCRIPTION
	  "NAME = ;
	   DESC = Tunneling PVC DLCI Configuration table;
	   HELP = ;
	   CAPABILITIES = NET_CFG, VPN_CFG;"
	::= {wan-configuration 3}

wanDTEPortTunnelPvcEntry OBJECT-TYPE
	SYNTAX	WanDTEPortTunnelPvcEntry
	ACCESS	not-accessible
	STATUS	deprecated
	DESCRIPTION
	  "NAME = ;
	   DESC = WAN DTE port tunneling PVC DLCI Entry;
	   HELP = ;
	   CAPABILITIES = ;"
	INDEX	{wanDTEPortTunnelPvcIfIndex}
	::= {wanDTEPortTunnelPvcTable 1}

WanDTEPortTunnelPvcEntry ::= SEQUENCE {
	wanDTEPortTunnelPvcIfIndex			INTEGER,
	wanDTEPortTunnelPvcDlci		        	INTEGER
	}

wanDTEPortTunnelPvcIfIndex OBJECT-TYPE
	SYNTAX	INTEGER (1..255)
	ACCESS	read-only
	STATUS	deprecated
	DESCRIPTION
	  "NAME = ;
	   DESC = Index for the DTE port;
	   HELP = ;
	   CAPABILITIES = ;"
	::= {wanDTEPortTunnelPvcEntry 1}

wanDTEPortTunnelPvcDlci OBJECT-TYPE
	SYNTAX	INTEGER (16..1007)
	ACCESS	read-only
	STATUS	deprecated
	DESCRIPTION
	  "NAME = ;
	   DESC = The value of this object holds\
                  the tunneling PVC DLCI number;
	   HELP = ;
	   CAPABILITIES = ;"
	::= {wanDTEPortTunnelPvcEntry 2}


-- This is the parallel configuration table of wanDTEPortTunnelPvcTable
-- This table allows the user to monitor DLCIs for the Tunneling
-- PVC Superframes. DLCIs are configured for each DTE port residing
-- on the access device.(Configuration)
--

-- NOTE That the table below has been deprecated and
-- its functionality has been replaced by 
-- the nvmNetLinkTable located in the Frame Relay MIB.

nvmWanDTEPortTunnelPvcTable OBJECT-TYPE
	SYNTAX	SEQUENCE OF NvmWanDTEPortTunnelPvcEntry
	ACCESS	not-accessible
	STATUS	deprecated
	DESCRIPTION
	  "NAME = ;
	   DESC = Tunneling PVC DLCI Configuration table.\
                  (configuration);
	   HELP = ;
	   CAPABILITIES = NET_CFG, VPN_CFG;"
	::= {wan-configuration 4}

nvmWanDTEPortTunnelPvcEntry OBJECT-TYPE
	SYNTAX	NvmWanDTEPortTunnelPvcEntry
	ACCESS	not-accessible
	STATUS	deprecated
	DESCRIPTION
	  "NAME = ;
	   DESC = WAN DTE port tunneling PVC DLCI Entry;
	   HELP = ;
	   CAPABILITIES = ;"
	INDEX	{nvmWanDTEPortTunnelPvcIfIndex}
	::= {nvmWanDTEPortTunnelPvcTable 1}

NvmWanDTEPortTunnelPvcEntry ::= SEQUENCE {
	nvmWanDTEPortTunnelPvcIfIndex			INTEGER,
	nvmWanDTEPortTunnelPvcDlci		        INTEGER
	}

nvmWanDTEPortTunnelPvcIfIndex OBJECT-TYPE
	SYNTAX	INTEGER (1..255)
	ACCESS	read-only
	STATUS	deprecated
	DESCRIPTION
	  "NAME = ;
	   DESC = Index for the DTE port;
	   HELP = ;
	   CAPABILITIES = ;"
	::= {nvmWanDTEPortTunnelPvcEntry 1}

nvmWanDTEPortTunnelPvcDlci OBJECT-TYPE
	SYNTAX	INTEGER (16..1007)
	ACCESS	read-write
	STATUS	deprecated
	DESCRIPTION
	  "NAME = ;
	   DESC = The value of this object is used \
                  to configure the tunneling PVC DLCI \
                  number.;
	   HELP = ;
	   CAPABILITIES = ;"
        DEFVAL {16}
	::= {nvmWanDTEPortTunnelPvcEntry 2}

--
--	Global Operational Parameters
--

wanifGlobalStatisticsTable OBJECT-TYPE
	SYNTAX	SEQUENCE OF WanifGlobalStatisticsEntry
	ACCESS	not-accessible
	STATUS	mandatory
	DESCRIPTION
	  "NAME = ;
	   DESC = WAN Global Statistics Table;
	   HELP = ;
	   CAPABILITIES = NET_CFG, VPN_DISP;"
	::= {wan-statistics 1}

wanifGlobalStatisticsEntry OBJECT-TYPE
	SYNTAX	WanifGlobalStatisticsEntry
	ACCESS	not-accessible
	STATUS	mandatory
	DESCRIPTION
	  "NAME = ;
	   DESC = WAN Global Statistics Entry;
	   HELP = ;
	   CAPABILITIES = ;"
	INDEX		{wanifGlobalStatisticsIndex }
	::= {wanifGlobalStatisticsTable 1}

WanifGlobalStatisticsEntry ::= SEQUENCE {
	wanifGlobalStatisticsIndex			INTEGER,
	wanifGlobalStatisticsRxBlockCount		Counter,
	wanifGlobalStatisticsTxBlockCount		Counter,
	wanifGlobalStatisticsTxLinkUnderruns		Counter,
	wanifGlobalStatisticsTxLinkOverflows		Counter,
	wanifGlobalStatisticsRxDiscards			Counter,
	wanifGlobalStatisticsTxErrors			Counter
	}

wanifGlobalStatisticsIndex OBJECT-TYPE
	SYNTAX	INTEGER (1..255)
	ACCESS	read-only
	STATUS	mandatory
	DESCRIPTION
	  "NAME = ;
	   DESC = Same as corresponding ifIndex value \
		  in ifTable;
	   HELP = ;
	   CAPABILITIES = ;"
	::= {wanifGlobalStatisticsEntry 1}

wanifGlobalStatisticsRxBlockCount OBJECT-TYPE
	SYNTAX	Counter
	ACCESS	read-only
	STATUS	mandatory
	DESCRIPTION
	  "NAME = ;
	   DESC = Number of frames rcvd from WAN;
	   HELP = ;
	   CAPABILITIES = ;"
	::= {wanifGlobalStatisticsEntry 2}

wanifGlobalStatisticsTxBlockCount OBJECT-TYPE
	SYNTAX	Counter
	ACCESS	read-only
	STATUS	mandatory
	DESCRIPTION
	  "NAME = ;
	   DESC = Number of frames txd to WAN;
	   HELP = ;
	   CAPABILITIES = ;"
	::= {wanifGlobalStatisticsEntry 3}

wanifGlobalStatisticsTxLinkUnderruns OBJECT-TYPE
	SYNTAX	Counter
	ACCESS	read-only
	STATUS	mandatory
	DESCRIPTION
	  "NAME = ;
	   DESC = Number of SCC reported link underruns;
	   HELP = ;
	   CAPABILITIES = ;"
	::= {wanifGlobalStatisticsEntry 4}

wanifGlobalStatisticsTxLinkOverflows OBJECT-TYPE
	SYNTAX	Counter
	ACCESS	read-only
	STATUS	mandatory
	DESCRIPTION
	  "NAME = ;
	   DESC = Number of SCC reported link overflows;
	   HELP = ;
	   CAPABILITIES = ;"
	::= {wanifGlobalStatisticsEntry 5}

wanifGlobalStatisticsRxDiscards OBJECT-TYPE
	SYNTAX	Counter
	ACCESS	read-only
	STATUS	mandatory
	DESCRIPTION
	  "NAME = ;
	   DESC = Number of HDLC packets discarded by SCC;
	   HELP = ;
	   CAPABILITIES = ;"
	::= {wanifGlobalStatisticsEntry 6}

wanifGlobalStatisticsTxErrors OBJECT-TYPE
	SYNTAX	Counter
	ACCESS	read-only
	STATUS	mandatory
	DESCRIPTION
	  "NAME = ;
	   DESC = Number of times CTS went down while pkt \
		  was being txd OR a link underrun occured;
	   HELP = ;
	   CAPABILITIES = ;"
	::= {wanifGlobalStatisticsEntry 7}


--	
-- NOTE THAT THE TABLE BELOW HAS BEEN OBSOLETED.
--

wanifFragStatisticsTable OBJECT-TYPE
	SYNTAX	SEQUENCE OF WanifFragStatisticsEntry
	ACCESS	not-accessible
	STATUS	obsolete
	DESCRIPTION
	  "NAME = ;
	   DESC = WAN Frag Statistics Table;
	   HELP = ;
	   CAPABILITIES = NET_CFG, VPN_DISP;"
	::= {wan-statistics 2}

wanifFragStatisticsEntry OBJECT-TYPE
	SYNTAX	WanifFragStatisticsEntry
	ACCESS	not-accessible
	STATUS	obsolete
	DESCRIPTION
	  "NAME = ;
	   DESC = WAN Frag Statistics Entry;
	   HELP = ;
	   CAPABILITIES = ;"
	INDEX		{wanifFragStatisticsIndex, wanifFragStatisticsFragPriority}
	::= {wanifFragStatisticsTable 1}

WanifFragStatisticsEntry ::= SEQUENCE {
	wanifFragStatisticsIndex			INTEGER,
	wanifFragStatisticsFragPriority			INTEGER,
	wanifFragStatisticsRxFrameCount			Counter,
	wanifFragStatisticsTxFrameCount			Counter,
	wanifFragStatisticsRxFragmentCount		Counter,
	wanifFragStatisticsTxFragmentCount		Counter,
	wanifFragStatisticsTxFragQueueSize		INTEGER
	}

wanifFragStatisticsIndex OBJECT-TYPE
	SYNTAX	INTEGER (1..255)
	ACCESS	read-only
	STATUS	obsolete
	DESCRIPTION
	  "NAME = ;
	   DESC = WAN Frag Ifindex;
	   HELP = ;
	   CAPABILITIES = ;"
	::= {wanifFragStatisticsEntry 1}

wanifFragStatisticsFragPriority OBJECT-TYPE
	SYNTAX	INTEGER (0..3)
	ACCESS	read-only
	STATUS	obsolete
	DESCRIPTION
	  "NAME = ;
	   DESC = Traffic class emission priority \
		  1 voice, 2 NMS and NAS, 3 signalling \
		  4 LAN data;
	   HELP = ;
	   CAPABILITIES = ;"
	::= {wanifFragStatisticsEntry 2}

wanifFragStatisticsRxFrameCount OBJECT-TYPE
	SYNTAX	Counter
	ACCESS	read-only
	STATUS	obsolete
	DESCRIPTION
	  "NAME = ;
	   DESC = Number of frames rcvd from WAN for \
		  individual traffic class;
	   HELP = ;
	   CAPABILITIES = ;"
	::= {wanifFragStatisticsEntry 3}

wanifFragStatisticsTxFrameCount OBJECT-TYPE
	SYNTAX	Counter
	ACCESS	read-only
	STATUS	obsolete
	DESCRIPTION
	  "NAME = ;
	   DESC = Number of frames txd to WAN for \
		  individual traffic class;
	   HELP = ;
	   CAPABILITIES = ;"
	::= {wanifFragStatisticsEntry 4}

wanifFragStatisticsRxFragmentCount OBJECT-TYPE
	SYNTAX	Counter
	ACCESS	read-only
	STATUS	obsolete
	DESCRIPTION
	  "NAME = ;
	   DESC = Number of pkts rcvd from WAN including \
		  all fragments for one traffic class;
	   HELP = ;
	   CAPABILITIES = ;"
	::= {wanifFragStatisticsEntry 5}

wanifFragStatisticsTxFragmentCount OBJECT-TYPE
	SYNTAX	Counter
	ACCESS	read-only
	STATUS	obsolete
	DESCRIPTION
	  "NAME = ;
	   DESC = Number of pkts txd to WAN including \
		  all fragments for one traffic class;
	   HELP = ;
	   CAPABILITIES = ;"
	::= {wanifFragStatisticsEntry 6}

wanifFragStatisticsTxFragQueueSize OBJECT-TYPE
	SYNTAX	INTEGER
	ACCESS	read-only
	STATUS	obsolete
	DESCRIPTION
	  "NAME = ;
	   DESC = Dynamic counter which indicates whether \
		  the Frag queue has any pkts backlogged;
	   HELP = ;
	   CAPABILITIES = ;"
	::= {wanifFragStatisticsEntry 7}

--
-- VoFr Statistics
--


wanifVofrStatsTable OBJECT-TYPE
	SYNTAX	SEQUENCE OF WanifVofrStatsEntry
	ACCESS	not-accessible
	STATUS	mandatory
	DESCRIPTION
	  "NAME = ;
	   DESC = WAN Vofr Statistics Table;
	   HELP = ;
	   CAPABILITIES = NET_DISP, VPN_DISP;"
	::= {wan-statistics 3}

wanifVofrStatsEntry OBJECT-TYPE
	SYNTAX	WanifVofrStatsEntry
	ACCESS	not-accessible
	STATUS	mandatory
	DESCRIPTION
	  "NAME = ;
	   DESC = WAN Vofr Statistics Entry;
	   HELP = ;
	   CAPABILITIES = ;"
	INDEX	{wanifVofrStatsIndex}
	::= {wanifVofrStatsTable 1}

WanifVofrStatsEntry ::= SEQUENCE {
	wanifVofrStatsIndex				INTEGER,
	wanifVofrStatsFragHighPriFramesCount		Counter,
	wanifVofrStatsFragToIfCount			Counter,
	wanifVofrStatsPackingToIfCount			Counter,
	wanifVofrStatsFragsFromIfCount			Counter,
	wanifVofrStatsLostFragsFromIfCount		Counter,
	wanifVofrStatsProtViolationsFromIfCount		Counter
	}

wanifVofrStatsIndex OBJECT-TYPE
	SYNTAX	INTEGER (1..255)
	ACCESS	read-only
	STATUS	mandatory
	DESCRIPTION
	  "NAME = ;
	   DESC = WAN Vofr Ifindex;
	   HELP = ;
	   CAPABILITIES = ;"
	::= {wanifVofrStatsEntry 1}

wanifVofrStatsFragHighPriFramesCount OBJECT-TYPE
	SYNTAX	Counter
	ACCESS	read-only
	STATUS	mandatory
	DESCRIPTION
	  "NAME = ;
	   DESC = This attribute counts egress frames with the \
		  highest priority, which had to be fragmented \
		  because they were larger than maximumFrameSize. \
		  This could happen when a data call is setup to \
		  use the highest emission priority, or the access \
		  device is provisioned with too low maximum \
                  frame size.;
	   HELP = ;
	   CAPABILITIES = ;"
	::= {wanifVofrStatsEntry 2}

wanifVofrStatsFragToIfCount OBJECT-TYPE
	SYNTAX	Counter
	ACCESS	read-only
	STATUS	mandatory
	DESCRIPTION
	  "NAME = ;
	   DESC = This attribute counts VoFr fragmentation actions \
		  applied to egress frames which were too long \
	 	  to fit in the next link frame.;
	   HELP = ;
	   CAPABILITIES = ;"
	::= {wanifVofrStatsEntry 3}

wanifVofrStatsPackingToIfCount OBJECT-TYPE
	SYNTAX	Counter
	ACCESS	read-only
	STATUS	mandatory
	DESCRIPTION
	  "NAME = ;
	   DESC = This attribute counts number of fragments \
		  which were packaged with other frames or \
		  fragments into a VoFr frame in the egress \
		  direction.;
	   HELP = ;
	   CAPABILITIES = ;"
	::= {wanifVofrStatsEntry 4}

wanifVofrStatsFragsFromIfCount OBJECT-TYPE
	SYNTAX	Counter
	ACCESS	read-only
	STATUS	mandatory
	DESCRIPTION
	  "NAME = ;
	   DESC = This attribute counts VoFr fragments received \
		  from the interface which were assembled into \
		  larger frames.'
	   HELP = ;
	   CAPABILITIES = ;"
	::= {wanifVofrStatsEntry 5}

wanifVofrStatsLostFragsFromIfCount OBJECT-TYPE
	SYNTAX	Counter
	ACCESS	read-only
	STATUS	mandatory
	DESCRIPTION
	  "NAME = ;
	   DESC = This attribute counts lost VoFr fragments from \
		  the interface.  Presence of lost fragments indicated \
		  a link problem.  Note that lost whole frames cannot \
		  detected.;
	   HELP = ;
	   CAPABILITIES = ;"
	::= {wanifVofrStatsEntry 6}

wanifVofrStatsProtViolationsFromIfCount OBJECT-TYPE
	SYNTAX	Counter
	ACCESS	read-only
	STATUS	mandatory
	DESCRIPTION
	  "NAME = ;
	   DESC = This attribute counts VoFr protocol violations \
		  detected in the data from the interface.;
	   HELP = ;
	   CAPABILITIES = ;"
	::= {wanifVofrStatsEntry 7}

--	
--  NOTE THAT THE TABLE BELOW(wanifCounterGlobalTable)
--  HAS BEEN OBSOLETED IN RELEASE 3.0 AND BEYOND.
--

wanifCounterGlobalTable OBJECT-TYPE
	SYNTAX  SEQUENCE OF WanifCounterGlobalEntry
	ACCESS  not-accessible
	STATUS  obsolete
	DESCRIPTION
	  "NAME = ;
	   DESC = This table is used to reset counters \
		  in the WAN Statistics Global Tables;
	   HELP = ;
	   CAPABILITIES = NET_CFG, VPN_DISP;"
	::= { wan-control 1 }

wanifCounterGlobalEntry OBJECT-TYPE
	SYNTAX  WanifCounterGlobalEntry
	ACCESS  not-accessible
	STATUS  obsolete
	DESCRIPTION
	  "NAME = ;
	   DESC = This specifies an entry indexed \
		  by portId;
	   HELP = ;
	   CAPABILITIES = ;"
	INDEX	{wanifCounterGlobalPortId}
	::= { wanifCounterGlobalTable 1 }

WanifCounterGlobalEntry ::= SEQUENCE {
		wanifCounterGlobalPortId	INTEGER,
		wanifCounterGlobalStatistics	INTEGER
		}

wanifCounterGlobalPortId OBJECT-TYPE
	SYNTAX	INTEGER
	ACCESS	read-only
	STATUS	obsolete
	DESCRIPTION
	  "NAME = ;
	   DESC = WAN Port ID for global counter reset;
	   HELP = ;
	   CAPABILITIES = ;"
	::= { wanifCounterGlobalEntry 1}

wanifCounterGlobalStatistics OBJECT-TYPE
        SYNTAX  INTEGER { reset(1), other(2) }
	ACCESS	write-only
        STATUS  obsolete
	DESCRIPTION
	  "NAME = ;
	   DESC = When set to reset, GlobalStatistics \
		  counters should be zeroed out;
	   HELP = ;
	   CAPABILITIES = ;"
        ::= { wanifCounterGlobalEntry 2 }
--
--  Frag Counter Table
--
--	
--  NOTE THAT THE TABLE BELOW(wanifCounterFragTable)
--  HAS BEEN OBSOLETED IN RELEASE 3.0 AND BEYOND.
--

wanifCounterFragTable OBJECT-TYPE
	SYNTAX  SEQUENCE OF WanifCounterFragEntry
	ACCESS  not-accessible
	STATUS  obsolete
	DESCRIPTION
	  "NAME = ;
	   DESC = This table is used to reset counters \
		  in the WAN Statistics Frag Tables;
	   HELP = ;
	   CAPABILITIES = NET_CFG, VPN_DISP;"
	::= { wan-control 2 }

wanifCounterFragEntry OBJECT-TYPE
	SYNTAX  WanifCounterFragEntry
	ACCESS  not-accessible
	STATUS  obsolete
	DESCRIPTION
	  "NAME = ;
	   DESC = This specifies an entry indexed \
		  by portId;
	   HELP = ;
	   CAPABILITIES = ;"
	INDEX	{wanifCounterFragPortId, wanifCounterFragProtocol}
	::= { wanifCounterFragTable 1 }

WanifCounterFragEntry ::= SEQUENCE {
		wanifCounterFragPortId		INTEGER,
		wanifCounterFragProtocol	INTEGER,
		wanifCounterFragStatistics	INTEGER
		}

wanifCounterFragPortId OBJECT-TYPE
	SYNTAX	INTEGER
	ACCESS	read-only
	STATUS	obsolete
	DESCRIPTION
	  "NAME = ;
	   DESC = WAN port id for counter reset;
	   HELP = ;
	   CAPABILITIES = ;"
	::= { wanifCounterFragEntry 1 }

wanifCounterFragProtocol OBJECT-TYPE
	SYNTAX	INTEGER (0..3)
	ACCESS	read-only
	STATUS	obsolete
	DESCRIPTION
	  "NAME = ;
	   DESC = Traffic class emission priority \
		  1 voice, 2 NMS and NAS, 3 signalling \
		  4 LAN data;
	   HELP = ;
	   CAPABILITIES = ;"
	::= { wanifCounterFragEntry 2 }

wanifCounterFragStatistics OBJECT-TYPE
        SYNTAX  INTEGER { reset(1), other(2) }
	ACCESS	write-only
        STATUS  obsolete
	DESCRIPTION
	  "NAME = ;
	   DESC = When set to reset, GlobalStatistics \
		  counters should be zeroed out;
	   HELP = ;
	   CAPABILITIES = ;"
        ::= { wanifCounterFragEntry 3 }

--
-- Vofr Counter Table
--
--	
--  NOTE THAT THE TABLE BELOW(wanifVofrCounterTable)
--  HAS BEEN OBSOLETED IN RELEASE 3.0 AND BEYOND.
--

wanifVofrCounterTable OBJECT-TYPE
	SYNTAX  SEQUENCE OF WanifVofrCounterEntry
	ACCESS  not-accessible
	STATUS  obsolete
	DESCRIPTION
	  "NAME = ;
	   DESC = This table is used to reset counters \
		  in the WAN Statistics Vofr Tables;
	   HELP = ;
	   CAPABILITIES = NET_CFG, VPN_DISP;"
	::= { wan-control 3 }

wanifVofrCounterEntry OBJECT-TYPE
	SYNTAX  WanifVofrCounterEntry
	ACCESS  not-accessible
	STATUS  obsolete
	DESCRIPTION
	  "NAME = ;
	   DESC = This specifies an entry indexed \
		  by portId;
	   HELP = ;
	   CAPABILITIES = ;"
	INDEX	{wanifVofrCounterPortId}
	::= { wanifVofrCounterTable 1 }

WanifVofrCounterEntry ::= SEQUENCE {
		wanifVofrCounterPortId		INTEGER,
		wanifVofrCounterStatistics	INTEGER
		}

wanifVofrCounterPortId OBJECT-TYPE
	SYNTAX	INTEGER
	ACCESS	read-only
	STATUS	obsolete
	DESCRIPTION
	  "NAME = ;
	   DESC = WAN Port ID for Vofr counter reset;
	   HELP = ;
	   CAPABILITIES = ;"
	::= { wanifVofrCounterEntry 1}

wanifVofrCounterStatistics OBJECT-TYPE
        SYNTAX  INTEGER { reset(1), other(2) }
	ACCESS	write-only
        STATUS  obsolete
	DESCRIPTION
	  "NAME = ;
	   DESC = When set to reset, Vofr Statistics \
		  counters should be zeroed out;
	   HELP = ;
	   CAPABILITIES = ;"
        ::= { wanifVofrCounterEntry 2 }

END
