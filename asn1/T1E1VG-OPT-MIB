-- Version 2.15.1.1, modified 2001-05-31 17:28:45-04 

        T1E1VG-OPT-MIB DEFINITIONS ::= BEGIN

        IMPORTS
            Counter, Gauge, enterprises
                FROM RFC1155-SMI

            OBJECT-TYPE
                FROM RFC-1212;

        -- Codex MIB Group definitions

                      codex OBJECT IDENTIFIER ::= { enterprises 449 }
         cdxProductSpecific OBJECT IDENTIFIER ::= { codex 2 }
                    cdx6500 OBJECT IDENTIFIER ::= { cdxProductSpecific 1 }

      cdx6500Configuration  OBJECT IDENTIFIER ::= { cdx6500 2 }
     cdx6500CfgGeneralGroup OBJECT IDENTIFIER ::= { cdx6500Configuration 2 }

          cdx6500Statistics OBJECT IDENTIFIER ::= { cdx6500 3 }
 cdx6500StatOtherStatsGroup OBJECT IDENTIFIER ::= { cdx6500Statistics 2 }
       cdx6500STT1E1VGGroup OBJECT IDENTIFIER ::= { cdx6500StatOtherStatsGroup 15 }

            cdx6500Controls OBJECT IDENTIFIER ::= { cdx6500 4 }

        -- Textual Conventions

        DisplayString ::= OCTET STRING


        -- T1E1VG Configuration Table

        cdx6500T1E1VGTable OBJECT-TYPE
            SYNTAX SEQUENCE OF Cdx6500T1E1VGEntry
            ACCESS not-accessible
            STATUS mandatory
            DESCRIPTION
                "This table contains the T1E1VG Configuration
                 parameters."
        ::= { cdx6500CfgGeneralGroup 25 }

        cdx6500T1E1VGEntry OBJECT-TYPE
            SYNTAX Cdx6500T1E1VGEntry 
            ACCESS not-accessible
            STATUS mandatory
            DESCRIPTION
                "A T1E1VG Table Entry. Each entry
                 contains the configuration parameters for a single
                 T1E1VG  Table."
            INDEX { cdx6500T1E1VGCfgEntryNumber }
        ::= { cdx6500T1E1VGTable 1 }

        Cdx6500T1E1VGEntry ::=
            SEQUENCE {
                cdx6500T1E1VGCfgEntryNumber 
                    INTEGER,
                cdx6500T1E1VGCfgInterfaceType
                    DisplayString,
                cdx6500T1E1VGCfgFormat
                    INTEGER,
                cdx6500T1E1VGCfgSwitchType
                    INTEGER,
                cdx6500T1E1VGCfgUserNetworkSide
                    INTEGER,
                cdx6500T1E1VGCfgDirectBchannel
                    INTEGER,
                cdx6500T1E1VGCfgBchRange
                    DisplayString,
                cdx6500T1E1VGCfgCallAddrReplace
                    INTEGER,
                cdx6500T1E1VGCfgIsdnQsigOpt
                    DisplayString,
                cdx6500T1E1VGCfgFilteredIE
                    DisplayString,
                cdx6500T1E1VGCfgReplIsdnQsig
                    DisplayString,
                cdx6500T1E1VGCfgCallPartyNumType
                    INTEGER,
                cdx6500T1E1VGCfgCallPartyNumPlan
                    INTEGER,
                cdx6500T1E1VGCfg1stChanPort
                    INTEGER,
                cdx6500T1E1VGCfg1stChanSlot
                    DisplayString,
                cdx6500T1E1VGCfg1stChanDS0Rate
                    INTEGER,
                cdx6500T1E1VGCfg2ndChanPort
                    INTEGER,
                cdx6500T1E1VGCfg2ndChanSlot
                    DisplayString,
                cdx6500T1E1VGCfg2ndChanDS0Rate
                    INTEGER,
                cdx6500T1E1VGCfg3rdChanPort
                    INTEGER,
                cdx6500T1E1VGCfg3rdChanSlot
                    DisplayString,
                cdx6500T1E1VGCfg3rdChanDS0Rate
                    INTEGER,
                cdx6500T1E1VGCfgLineFramingType
                    INTEGER,
                cdx6500T1E1VGCfgLineCoding
                    INTEGER,
                cdx6500T1E1VGCfgTransmitClock
                    INTEGER,
                cdx6500T1E1VGCfgLineImpedance
                    INTEGER,
                cdx6500T1E1VGCfgLineBuildOut
                    INTEGER,
                cdx6500T1E1VGCfgRecvSense
                    INTEGER,
                cdx6500T1E1VGCfgFacilityDataLink
                    INTEGER,
                cdx6500T1E1VGCfgV54RecvRLBK
                    INTEGER,
                cdx6500T1E1VGCfgThresholdValueLES
                    INTEGER,
                cdx6500T1E1VGCfgThresholdValueLCV
                    INTEGER,
                cdx6500T1E1VGCfgThresholdValuePCV
                    INTEGER,
                cdx6500T1E1VGCfgThresholdValueCSS
                    INTEGER,
                cdx6500T1E1VGCfgThresholdValueES
                    INTEGER,
                cdx6500T1E1VGCfgThresholdValueBES
                    INTEGER,
                cdx6500T1E1VGCfgThresholdValueSES
                    INTEGER,
                cdx6500T1E1VGCfgThresholdValueSEFS
                    INTEGER,
                cdx6500T1E1VGCfgThresholdValueUAS
                    INTEGER,
                cdx6500T1E1VGCfgBchNumScheme
                    INTEGER
                }

        cdx6500T1E1VGCfgEntryNumber OBJECT-TYPE
            SYNTAX INTEGER 
            ACCESS read-only
            STATUS mandatory
            DESCRIPTION
                "Entry number of the T1E1VG Table."
        ::= { cdx6500T1E1VGEntry 1 }

        cdx6500T1E1VGCfgInterfaceType OBJECT-TYPE
            SYNTAX DisplayString
            ACCESS read-only
            STATUS mandatory
            DESCRIPTION
                "This is a T1E1VG  having interface type."
        ::= { cdx6500T1E1VGEntry 2 }

        cdx6500T1E1VGCfgFormat OBJECT-TYPE
            SYNTAX INTEGER {
                    vg-format-frational (1),
                    vg-format-channelize (2),
                    vg-format-isdn (3),
                    vg-format-ccs (4)
                    } 
            ACCESS read-only
            STATUS mandatory
            DESCRIPTION
                "This parameter is used to select the format 
                 of the T1E1VG interface.
		 vg-format-frational :DS0's are predefined by the TELCO or the User
                 vg-format-channelize :DS0 is predefined by the TELCO or the User
                 vg-format-isdn  :DS0 is defined by the ISDN (Q.931) D-Channel
                 vg-format-ccs  :DS0 is defined by the signalling channel (Voice)."
        ::= { cdx6500T1E1VGEntry 3 }

        cdx6500T1E1VGCfgSwitchType OBJECT-TYPE
            SYNTAX INTEGER {
                    unspecified  (1),
                    ni2 	(2),
                    ess5        (3),
                    dms100      (4),
                    ntt         (5),
                    tso14      (6),
                    etsi       (7),
                    qsig       (8)
                    }
            ACCESS read-only
            STATUS mandatory
            DESCRIPTION
                "The ISDN switch type. This specifies the type of
                 equipment to which this span is connected.
                 The possible choices are:
                 ni2	  : National ISDN version 2
                 5ess     : AT&T 5ESS Switch
                 dms100   : Northern Telecom DMS-100 Switch
                 ntt      : Nippon Telephone and Telegraph switch (Japan)
                 tso14    : AUSTEL Technical Standard 014 for Australia
                 etsi     : Euro ISDN PRI (NET5)
		 qsig     : ISDN QSIG PRI."
        ::= { cdx6500T1E1VGEntry 4 }

        cdx6500T1E1VGCfgUserNetworkSide OBJECT-TYPE
            SYNTAX INTEGER {
                    user    (1),
                    network (2)
                    }
                ACCESS read-only
                STATUS mandatory
                DESCRIPTION
                    "This parameter specifies whether the T1E1VG 
                     is emulating the network or user side of the
                     ISDN network.
                     user    : The T1 or E1 port is emulating the user,
                               ex.  the T1 or E1 port is to be connected
                               to an ISDN network.
                     network : The T1 or E1 port is emulating the network,
                               ex. the T1 or E1 port is to be connected
                               to an ISDN PBX."
        ::= { cdx6500T1E1VGEntry 5 }

        cdx6500T1E1VGCfgDirectBchannel OBJECT-TYPE
            SYNTAX INTEGER {
                    high-to-low    (1),
                    low-to-high (2)
                    }
                ACCESS read-only
                STATUS mandatory
                DESCRIPTION
                    "This parameter specifies the direction of B-Channel
		      assignment on outbound calls made from this port.
			high-to-low : B-Channels are selected starting with the highest
                			 numbered available channel.
   			high-to-low : B-Channels are selected starting with the lowest
                		       numbered available channel."
        ::= { cdx6500T1E1VGEntry 6 }

        cdx6500T1E1VGCfgBchRange OBJECT-TYPE
            SYNTAX DisplayString 
            ACCESS read-only
            STATUS mandatory
            DESCRIPTION
                "Specify the B-Channel assignments that will be used
		 for the ISDN/QSIG calls.
		  Select Individual or Time Slot ranges, e.g. 1-3,10,13-15
		  will include Time Slots 1,2,3,10,13,14,15."
        ::= { cdx6500T1E1VGEntry 7 }

        cdx6500T1E1VGCfgCallAddrReplace OBJECT-TYPE
            SYNTAX INTEGER {
                    none    (1)
                    }
                ACCESS read-only
                STATUS mandatory
                DESCRIPTION
		 "This parameter is a PLACE HOLDER item."
        ::= { cdx6500T1E1VGEntry 8 }

        cdx6500T1E1VGCfgIsdnQsigOpt OBJECT-TYPE
            SYNTAX DisplayString
            ACCESS read-only
            STATUS mandatory
            DESCRIPTION
                "This parameter is a PLACE HOLDER item."
        ::= { cdx6500T1E1VGEntry 9 }

        cdx6500T1E1VGCfgFilteredIE OBJECT-TYPE
            SYNTAX DisplayString
            ACCESS read-only
            STATUS mandatory
            DESCRIPTION
                "This parameter is a PLACE HOLDER item."
        ::= { cdx6500T1E1VGEntry 10 }

        cdx6500T1E1VGCfgReplIsdnQsig OBJECT-TYPE
            SYNTAX DisplayString
            ACCESS read-only
            STATUS mandatory
            DESCRIPTION
                "This parameter is a PLACE HOLDER item."
        ::= { cdx6500T1E1VGEntry 11 }

        cdx6500T1E1VGCfgCallPartyNumType OBJECT-TYPE
            SYNTAX INTEGER {
                    unknown (1),
                    international (2),
                    national  (3),
                    subscriber  (5)
                    }
            ACCESS read-only
            STATUS mandatory
            DESCRIPTION
                 "This is the Calling/Called Party Number Type as defined by ITU-T
		   unknown       - Unknown
   		   international - International number
   		   national      - National number
   		   subscriber    - Subscriber number."
        ::= { cdx6500T1E1VGEntry 12 }

        cdx6500T1E1VGCfgCallPartyNumPlan OBJECT-TYPE
            SYNTAX INTEGER {
                    unknown (1),
                    isdn (2),
                    telephony  (3),
                    private  (10)
                    }
            ACCESS read-only
            STATUS mandatory
            DESCRIPTION
	         "This is the Calling/Called Party Number Plan as defined by ITU-T
   			unknown   - Unknown
   			iSDN      - ISDN numbering plan (E.164)
   			telephony - Standard Telephone numbering plan
   			private   - Private numbering plan."
        ::= { cdx6500T1E1VGEntry 13 }

        cdx6500T1E1VGCfg1stChanPort OBJECT-TYPE
            SYNTAX INTEGER 
            ACCESS read-only
            STATUS mandatory
            DESCRIPTION
                 "*Note that: This port must be configured as default."
        ::= { cdx6500T1E1VGEntry 14 }

        cdx6500T1E1VGCfg1stChanSlot OBJECT-TYPE
            SYNTAX DisplayString
            ACCESS read-only
            STATUS mandatory
            DESCRIPTION
                 "Specify the Time Slot assignments, 1 to 24 for T1 or 1 to 31 for E1.
	           Select Individual or Time Slot ranges, e.g. 1-3,10,13-15
		   will include Time Slots 1,2,3,10,13,14,15."
        ::= { cdx6500T1E1VGEntry 15 }

        cdx6500T1E1VGCfg1stChanDS0Rate OBJECT-TYPE
            SYNTAX INTEGER {
		rate-56k	(1),
		rate-64k	(2)
		} 
            ACCESS read-only
            STATUS mandatory
            DESCRIPTION
	      "Specify the DS0 Rate for T1."
        ::= { cdx6500T1E1VGEntry 16 }

        cdx6500T1E1VGCfg2ndChanPort OBJECT-TYPE
            SYNTAX INTEGER
            ACCESS read-only
            STATUS mandatory
            DESCRIPTION
                 "0       : No Data activity on the Second FT1/FE1 Channel.
		  Port No.: Associated to the Second FT1/FE1 Channel."
        ::= { cdx6500T1E1VGEntry 17 }

        cdx6500T1E1VGCfg2ndChanSlot OBJECT-TYPE
            SYNTAX DisplayString 
            ACCESS read-only
            STATUS mandatory
            DESCRIPTION
                 "Specify the Time Slot assignments, 1 to 24 for T1 or 1 to 31 for E1.
                   Select Individual or Time Slot ranges, e.g. 1-3,10,13-15
                   will include Time Slots 1,2,3,10,13,14,15."
        ::= { cdx6500T1E1VGEntry 18 }

        cdx6500T1E1VGCfg2ndChanDS0Rate OBJECT-TYPE
            SYNTAX INTEGER {
                rate-56k     (1),
                rate-64k     (2)
                }
            ACCESS read-only
            STATUS mandatory
            DESCRIPTION
              "Specify the DS0 Rate for T1."
        ::= { cdx6500T1E1VGEntry 19 }

        cdx6500T1E1VGCfg3rdChanPort OBJECT-TYPE
            SYNTAX INTEGER
            ACCESS read-only
            STATUS mandatory
            DESCRIPTION
                 "0       : No Data activity on the Third FT1/FE1 Channel.
                  Port No.: Associated to the Third FT1/FE1 Channel."
        ::= { cdx6500T1E1VGEntry 20 }

        cdx6500T1E1VGCfg3rdChanSlot OBJECT-TYPE
            SYNTAX DisplayString 
            ACCESS read-only
            STATUS mandatory
            DESCRIPTION
                 "Specify the Time Slot assignments, 1 to 24 for T1 or 1 to 31 for E1.
                   Select Individual or Time Slot ranges, e.g. 1-3,10,13-15
                   will include Time Slots 1,2,3,10,13,14,15."
        ::= { cdx6500T1E1VGEntry 21 }

        cdx6500T1E1VGCfg3rdChanDS0Rate OBJECT-TYPE
            SYNTAX INTEGER {
                rate-56k     (1),
                rate-64k     (2)
                }
            ACCESS read-only
            STATUS mandatory
            DESCRIPTION
              "Specify the DS0 Rate for T1."
        ::= { cdx6500T1E1VGEntry 22 }

        cdx6500T1E1VGCfgLineFramingType OBJECT-TYPE
            SYNTAX INTEGER {
                    sf (1),
                    esf  (2),
                    e1 (3),
                    e1crc  (4),
                    e1crc-febe  (5)
                    }
            ACCESS read-only
            STATUS mandatory
            DESCRIPTION
               "Indicate type of framing used by the DS1 circuit.
		    esf : Extended Super Frame
   		    sf  : Super Frame (Also known as D4 framing type)
		    e1  : D2048S or D2048U
                    e1-crc  : D2048S with CRC
                    e1-crc-febe: D2048S with CRC and Si=FEBE."
        ::= { cdx6500T1E1VGEntry 23 }

        cdx6500T1E1VGCfgLineCoding OBJECT-TYPE
            SYNTAX INTEGER {
                    ami  (1),
                    b8zs   (2),
		    hdb3   (3) 
                    }
            ACCESS read-only
            STATUS mandatory
            DESCRIPTION
	        "Selects variety of zero suppression used on the T1 link.
		   ami : Alternate Mark Inversion.
		   b8zs : Bipolar 8 Zero Substitution.
		   hdb3 : High Density Bipolar 3"
        ::= { cdx6500T1E1VGEntry 24 }

        cdx6500T1E1VGCfgTransmitClock OBJECT-TYPE
            SYNTAX INTEGER {
                    rec  (1),
                    int (2)
                    }
            ACCESS read-only
            STATUS mandatory
            DESCRIPTION
                "Selects the source of the transmit clock.
                 int  : Internal Oscillator.
                 rec  : Received Timing."
        ::= { cdx6500T1E1VGEntry 25 }

        cdx6500T1E1VGCfgLineImpedance OBJECT-TYPE
            SYNTAX INTEGER {
                    ohms-120 (1),
                    ohms-75 (2)
                    }
            ACCESS read-only
            STATUS mandatory
            DESCRIPTION
                "Selects the line impedance as 75 ohms or 120 ohms."
        ::= { cdx6500T1E1VGEntry 26 }

        cdx6500T1E1VGCfgLineBuildOut OBJECT-TYPE
            SYNTAX INTEGER
            ACCESS read-only
            STATUS mandatory
            DESCRIPTION
                 "Select the Line Build Out to match the physical interface.
                  For DSX interfaces, this value is based on cable
			0 - 0ft to 133ft
     			1 - 134ft to 266ft
     			2 - 267ft to 399ft
     			3 - 400ft to 533ft
     			4 - 534ft to 655ft

                  For DS1 interfaces, this value is based on the
			0 - 0db
     			5 - -7.5db
     			6 - -15db
     			7 - -22.5db
     			4 - Not valid for DS1 interfaces"
        ::= { cdx6500T1E1VGEntry 27 }   

        cdx6500T1E1VGCfgRecvSense OBJECT-TYPE
            SYNTAX INTEGER {
                    low (1),
                    high (2)
                    }
            ACCESS read-only
            STATUS mandatory
            DESCRIPTION
	       "Select HIGH (-36DB) if line is marginal."
        ::= { cdx6500T1E1VGEntry 28 }

        cdx6500T1E1VGCfgFacilityDataLink OBJECT-TYPE
            SYNTAX INTEGER {
                    none (1),
                    ansi (3),
                    att  (2)
                    }
            ACCESS read-only
            STATUS mandatory
            DESCRIPTION
                "This describes the use of the facilities data link,
                 and may have the following capabilities:
                 none : indicates that the device does  not use
                        the FDL.
                 ansi : refers to the  FDL  exchange recommended 
                        by ANSI (Ansi-T1-403).
                 att  : refers to ESF FDL exchanges (Att-54016)."
        ::= { cdx6500T1E1VGEntry 29 }

        cdx6500T1E1VGCfgV54RecvRLBK OBJECT-TYPE
            SYNTAX INTEGER {
                    disable (1),
                    enable (2)
                    }
            ACCESS read-only
            STATUS mandatory
            DESCRIPTION
	       "enable : Respond to incoming V.54 loopback requests.
                disable: Do not respond to incoming V.54 loopback requests."
        ::= { cdx6500T1E1VGEntry 30 }

        cdx6500T1E1VGCfgThresholdValueLES OBJECT-TYPE
            SYNTAX INTEGER (1..255)
            ACCESS read-only
            STATUS mandatory
            DESCRIPTION
                "Threshold value of Line Errored Seconds (LESs)
                 to report alarms on CTP when exceeded."
        ::= { cdx6500T1E1VGEntry 31  }

        cdx6500T1E1VGCfgThresholdValueLCV OBJECT-TYPE
            SYNTAX INTEGER (1..255)
            ACCESS read-only
            STATUS mandatory
            DESCRIPTION
                "Threshold value of Line Code Violations (LCVs)
                 to report alarms on CTP when exceeded."
        ::= { cdx6500T1E1VGEntry 32 }

        cdx6500T1E1VGCfgThresholdValuePCV OBJECT-TYPE
            SYNTAX INTEGER (1..255)
            ACCESS read-only
            STATUS mandatory
            DESCRIPTION
                "Threshold value of Path Code Violations (PCVs)
                 to report alarms on CTP when exceeded."
        ::= { cdx6500T1E1VGEntry 33  }


        cdx6500T1E1VGCfgThresholdValueCSS OBJECT-TYPE
            SYNTAX INTEGER (1..255)
            ACCESS read-only
            STATUS mandatory
            DESCRIPTION
                "Threshold value of Controlled Slip Seconds (CSSs)
                 to report alarms on CTP when exceeded."
        ::= { cdx6500T1E1VGEntry 34 }

        cdx6500T1E1VGCfgThresholdValueES OBJECT-TYPE
            SYNTAX INTEGER (1..255)
            ACCESS read-only
            STATUS mandatory
            DESCRIPTION
                "Threshold value of Errored Seconds (ESs)
                 to report alarms on CTP when exceeded."
        ::= { cdx6500T1E1VGEntry 35 }

        cdx6500T1E1VGCfgThresholdValueBES OBJECT-TYPE
            SYNTAX INTEGER (1..255)
            ACCESS read-only
            STATUS mandatory
            DESCRIPTION
                "Threshold value of Bursty Errored Seconds (BESs)
                 to report alarms on CTP when exceeded."
        ::= { cdx6500T1E1VGEntry 36 }

        cdx6500T1E1VGCfgThresholdValueSES OBJECT-TYPE
            SYNTAX INTEGER (1..255)
            ACCESS read-only
            STATUS mandatory
            DESCRIPTION
                "Threshold value of Severely Errored Seconds (SESs)
                 to report alarms on CTP when exceeded."
        ::= { cdx6500T1E1VGEntry 37 }

        cdx6500T1E1VGCfgThresholdValueSEFS OBJECT-TYPE
            SYNTAX INTEGER (1..255)
            ACCESS read-only
            STATUS mandatory
            DESCRIPTION
                "Threshold value of Severely Errored Framing Seconds (SEFSs)
                 to report alarms on CTP when exceeded."
        ::= { cdx6500T1E1VGEntry 38 }

        cdx6500T1E1VGCfgThresholdValueUAS OBJECT-TYPE
            SYNTAX INTEGER (1..255)
            ACCESS read-only
            STATUS mandatory
            DESCRIPTION
                "Threshold value of Unavailable Seconds (UASs)
                 to report alarms on CTP when exceeded."
        ::= { cdx6500T1E1VGEntry 39 }

        cdx6500T1E1VGCfgBchNumScheme OBJECT-TYPE
            SYNTAX INTEGER {
                    nb-1-30 (1),
                    nb-1-31 (2)
                    }
            ACCESS read-only
            STATUS mandatory
            DESCRIPTION
               "This parameter specifies the B-Channel numbering scheme 
		used by the ISDN service provider.
		  1-31  : B-Channels are numbered 1 to 31.
		  1-30  : B-Channels are numbered 1 to 30."
        ::= { cdx6500T1E1VGEntry 40 }


        -- The T1E1VG Statistics Table
        
        cdx6500STT1E1VGTable OBJECT-TYPE
            SYNTAX SEQUENCE OF Cdx6500STT1E1VGEntry
            ACCESS not-accessible
            STATUS mandatory
            DESCRIPTION
                "This table holds statistics information for T1E1VG."
        ::= { cdx6500STT1E1VGGroup 1 }
        
        cdx6500STT1E1VGEntry OBJECT-TYPE
            SYNTAX Cdx6500STT1E1VGEntry 
            ACCESS not-accessible
            STATUS mandatory
            DESCRIPTION
                "Each entry contains statistics information for one T1E1VG interface."
            INDEX { cdx6500T1E1VGStatIfNumber }            
        ::= { cdx6500STT1E1VGTable 1 }
        
        Cdx6500STT1E1VGEntry ::=
            SEQUENCE {
                cdx6500T1E1VGStatIfNumber 
                    INTEGER,
                cdx6500T1E1VGStatInterfaceType 
                    DisplayString,
                cdx6500T1E1VGStatTimeSinceLastReset 
                    DisplayString,
                cdx6500T1E1VGStatAlarmState
                    DisplayString,
                cdx6500T1E1VGStatChannelState
                    DisplayString 
                }

         cdx6500T1E1VGStatIfNumber OBJECT-TYPE
            SYNTAX INTEGER 
            ACCESS read-only
            STATUS mandatory
            DESCRIPTION
               "A T1E1VG Stat Table Interface Number. Each interface 
                 contains the configuration parameters for a single
                 T1E1VG  Table."
        ::= { cdx6500STT1E1VGEntry 1 }

        cdx6500T1E1VGStatInterfaceType OBJECT-TYPE
            SYNTAX DisplayString
            ACCESS read-only
            STATUS mandatory
            DESCRIPTION
                "This parameter indicates the type of interface."
        ::= { cdx6500STT1E1VGEntry 2 }

        cdx6500T1E1VGStatTimeSinceLastReset OBJECT-TYPE
            SYNTAX DisplayString
            ACCESS read-only
            STATUS mandatory
            DESCRIPTION
                "Time since last reset has happened for the interface."
        ::= { cdx6500STT1E1VGEntry 3 }

        cdx6500T1E1VGStatAlarmState OBJECT-TYPE
            SYNTAX DisplayString
            ACCESS read-only
            STATUS mandatory
            DESCRIPTION
                "Time since last reset has happened for the interface."
        ::= { cdx6500STT1E1VGEntry 4 }

        cdx6500T1E1VGStatChannelState OBJECT-TYPE
            SYNTAX DisplayString
            ACCESS read-only
            STATUS mandatory
            DESCRIPTION
                "The status of or the interface."
        ::= { cdx6500STT1E1VGEntry 5 }

                    
                    
        -- The last 24 hour Error Statistics Table

        cdx6500T1E1VGStatTotal24HoursReportTable OBJECT-TYPE
            SYNTAX SEQUENCE OF Cdx6500T1E1VGStatTotal24HoursReportEntry
            ACCESS not-accessible
            STATUS mandatory
            DESCRIPTION
                "This table holds a report of the cumulative sum
                 of the statistics for the previous 24 hour interval."
        ::= { cdx6500STT1E1VGGroup 2 }

        cdx6500T1E1VGStatTotal24HoursReportEntry OBJECT-TYPE
            SYNTAX Cdx6500T1E1VGStatTotal24HoursReportEntry
            ACCESS not-accessible
            STATUS mandatory
            DESCRIPTION
                "Each entry contains statistics information for one T1 port."
            INDEX  { cdx6500T1E1VGStatTotal24HoursReportIfNumber }
        ::= { cdx6500T1E1VGStatTotal24HoursReportTable 1 }

        Cdx6500T1E1VGStatTotal24HoursReportEntry ::=
            SEQUENCE {
                cdx6500T1E1VGStatTotal24HoursReportIfNumber
                    INTEGER,
                cdx6500T1E1VGStatTotal24HoursReportLES
                    Gauge,
                cdx6500T1E1VGStatTotal24HoursReportLCV
                    Gauge,
                cdx6500T1E1VGStatTotal24HoursReportPCV
                    Gauge,
                cdx6500T1E1VGStatTotal24HoursReportCSS
                    Gauge,
                cdx6500T1E1VGStatTotal24HoursReportES
                    Gauge,
                cdx6500T1E1VGStatTotal24HoursReportBES
                    Gauge,
                cdx6500T1E1VGStatTotal24HoursReportSES
                    Gauge,
                cdx6500T1E1VGStatTotal24HoursReportSEFS
                    Gauge,
                cdx6500T1E1VGStatTotal24HoursReportUAS
                    Gauge
                }

        cdx6500T1E1VGStatTotal24HoursReportIfNumber OBJECT-TYPE
            SYNTAX INTEGER 
            ACCESS read-only
            STATUS mandatory
            DESCRIPTION
                "Interface number of the T1E1VG."
        ::= { cdx6500T1E1VGStatTotal24HoursReportEntry 1 }
     
        cdx6500T1E1VGStatTotal24HoursReportLES OBJECT-TYPE
            SYNTAX Gauge
            ACCESS read-only
            STATUS mandatory
            DESCRIPTION
                "The number of Line Errored Seconds (LESs)
                 encountered by the T1E1VG interface in the 
                 previous 24 hour interval. "
        ::= { cdx6500T1E1VGStatTotal24HoursReportEntry 2 }

        cdx6500T1E1VGStatTotal24HoursReportLCV OBJECT-TYPE
            SYNTAX Gauge
            ACCESS read-only
            STATUS mandatory
            DESCRIPTION
                "The number of Line Code Violations (LCVs)
                 encountered by the T1E1VG interface in the 
                 previous 24 hour interval."
        ::= { cdx6500T1E1VGStatTotal24HoursReportEntry 3 }

        cdx6500T1E1VGStatTotal24HoursReportPCV OBJECT-TYPE
            SYNTAX Gauge
            ACCESS read-only
            STATUS mandatory
            DESCRIPTION
                "The number of Path Coding  Violations (PCVs)
                 encountered by the T1E1VG interface in the 
                 previous 24 hour interval."
        ::= { cdx6500T1E1VGStatTotal24HoursReportEntry 4 }

        cdx6500T1E1VGStatTotal24HoursReportCSS OBJECT-TYPE
            SYNTAX Gauge
            ACCESS read-only
            STATUS mandatory
            DESCRIPTION
                "The number of Controlled Slip Seconds (CSSs)
                 encountered by the T1E1VG interface in the 
                 previous 24 hour interval."
        ::= { cdx6500T1E1VGStatTotal24HoursReportEntry 5 }

        cdx6500T1E1VGStatTotal24HoursReportES OBJECT-TYPE
            SYNTAX Gauge
            ACCESS read-only
            STATUS mandatory
            DESCRIPTION
                "The number of Errored Seconds (ESs) 
                 encountered by the T1E1VG interface in the 
                 previous 24 hour interval."
        ::= { cdx6500T1E1VGStatTotal24HoursReportEntry 6 }

        cdx6500T1E1VGStatTotal24HoursReportBES OBJECT-TYPE
            SYNTAX Gauge
            ACCESS read-only
            STATUS mandatory
            DESCRIPTION
                "The number of Bursty Errored Seconds (BESs)
                 encountered by the T1E1VG interface in the 
                 previous 24 hour interval."
        ::= { cdx6500T1E1VGStatTotal24HoursReportEntry 7 }

        cdx6500T1E1VGStatTotal24HoursReportSES OBJECT-TYPE
            SYNTAX Gauge
            ACCESS read-only
            STATUS mandatory
            DESCRIPTION
                "The number of Severely Errored Seconds (SESs)
                 encountered by the T1E1VG interface in the
                 previous 24 hour interval."
        ::= { cdx6500T1E1VGStatTotal24HoursReportEntry 8 }

        cdx6500T1E1VGStatTotal24HoursReportSEFS OBJECT-TYPE
            SYNTAX Gauge
            ACCESS read-only
            STATUS mandatory
            DESCRIPTION
                "The number of Severely Errored Framing Seconds (SEFSs)
                 encountered by the T1E1VG interface in the previous
                 24 hour interval."
        ::= { cdx6500T1E1VGStatTotal24HoursReportEntry 9 }

        cdx6500T1E1VGStatTotal24HoursReportUAS OBJECT-TYPE
            SYNTAX Gauge
            ACCESS read-only
            STATUS mandatory
            DESCRIPTION
                "The number of Unavailable Seconds (UASs)
                 encountered by the T1E1VG interface in the 
                 previous 24 hour interval."
        ::= { cdx6500T1E1VGStatTotal24HoursReportEntry 10 }

        -- The current 15 minute interval Error Statistics Table

        cdx6500T1E1VGStatCurrent15MinutesReportTable OBJECT-TYPE
            SYNTAX SEQUENCE OF Cdx6500T1E1VGStatCurrent15MinutesReportEntry
            ACCESS not-accessible
            STATUS mandatory
            DESCRIPTION
                "This table holds a report of the statistics for the 
                 current 15 minutes interval."
        ::= { cdx6500STT1E1VGGroup 3 }

        cdx6500T1E1VGStatCurrent15MinutesReportEntry OBJECT-TYPE
            SYNTAX Cdx6500T1E1VGStatCurrent15MinutesReportEntry
            ACCESS not-accessible
            STATUS mandatory
            DESCRIPTION
                "Each entry contains statistics information for one T1E1VG Interface."
            INDEX  { cdx6500T1E1VGStatCurrent15MinutesReportIfNumber }
        ::= { cdx6500T1E1VGStatCurrent15MinutesReportTable 1 }

        Cdx6500T1E1VGStatCurrent15MinutesReportEntry ::=
            SEQUENCE {
                cdx6500T1E1VGStatCurrent15MinutesReportIfNumber
                    INTEGER,
                cdx6500T1E1VGStatCurrent15MinutesReportTimeElapsed
                    INTEGER,
                cdx6500T1E1VGStatCurrent15MinutesReportLES
                    Gauge,
                cdx6500T1E1VGStatCurrent15MinutesReportLCV
                    Gauge,
                cdx6500T1E1VGStatCurrent15MinutesReportPCV
                    Gauge,
                cdx6500T1E1VGStatCurrent15MinutesReportCSS
                    Gauge,
                cdx6500T1E1VGStatCurrent15MinutesReportES
                    Gauge,
                cdx6500T1E1VGStatCurrent15MinutesReportBES
                    Gauge,
                cdx6500T1E1VGStatCurrent15MinutesReportSES
                    Gauge,
                cdx6500T1E1VGStatCurrent15MinutesReportSEFS
                    Gauge,
                cdx6500T1E1VgStatCurrent15MinutesReportUAS
                    Gauge
                }                                               

        cdx6500T1E1VGStatCurrent15MinutesReportIfNumber OBJECT-TYPE
            SYNTAX INTEGER 
            ACCESS read-only
            STATUS mandatory
            DESCRIPTION
                "Interface number of the T1E1VG."
        ::= { cdx6500T1E1VGStatCurrent15MinutesReportEntry 1 }

        cdx6500T1E1VGStatCurrent15MinutesReportTimeElapsed OBJECT-TYPE
            SYNTAX INTEGER 
            ACCESS read-only
            STATUS mandatory
            DESCRIPTION
                "The time that has elapsed since the beginning 
                 of the current 15 minutes interval."
        ::= { cdx6500T1E1VGStatCurrent15MinutesReportEntry 2 }
                    
        cdx6500T1E1VGStatCurrent15MinutesReportLES OBJECT-TYPE
            SYNTAX Gauge
            ACCESS read-only
            STATUS mandatory
            DESCRIPTION
                "The number of Line Errored Seconds (LESs)
                 encountered by the T1E1VG interface in the 
                 current 15 minute interval."
        ::= { cdx6500T1E1VGStatCurrent15MinutesReportEntry 3 }

        cdx6500T1E1VGStatCurrent15MinutesReportLCV OBJECT-TYPE
            SYNTAX Gauge
            ACCESS read-only
            STATUS mandatory
            DESCRIPTION
                "The number of Line Code Violations (LCVs)
                 encountered by the T1E1VG interface in the 
                 current 15 minute interval."
        ::= { cdx6500T1E1VGStatCurrent15MinutesReportEntry 4 }

        cdx6500T1E1VGStatCurrent15MinutesReportPCV OBJECT-TYPE
            SYNTAX Gauge
            ACCESS read-only
            STATUS mandatory
            DESCRIPTION
                "The number of Path Coding  Violations (PCVs)
                 encountered by the T1E1VG interface in the 
                 current 15 minute interval."
        ::= { cdx6500T1E1VGStatCurrent15MinutesReportEntry 5 }

        cdx6500T1E1VGStatCurrent15MinutesReportCSS OBJECT-TYPE
            SYNTAX Gauge
            ACCESS read-only
            STATUS mandatory
            DESCRIPTION
                "The number of Controlled Slip Seconds (CSSs)
                 encountered by the T1E1VG interface in the 
                 current 15 minute interval."
        ::= { cdx6500T1E1VGStatCurrent15MinutesReportEntry 6 }

        cdx6500T1E1VGStatCurrent15MinutesReportES OBJECT-TYPE
            SYNTAX Gauge
            ACCESS read-only
            STATUS mandatory
            DESCRIPTION
                "The number of Errored Seconds (ESs) 
                 encountered by the T1E1VG interface in the 
                 current 15 minute interval."
        ::= { cdx6500T1E1VGStatCurrent15MinutesReportEntry 7 }

        cdx6500T1E1VGStatCurrent15MinutesReportBES OBJECT-TYPE
            SYNTAX Gauge
            ACCESS read-only
            STATUS mandatory
            DESCRIPTION
                "The number of Bursty Errored Seconds (BESs)
                 encountered by the T1E1VG interface in the 
                 current 15 minute interval."
        ::= { cdx6500T1E1VGStatCurrent15MinutesReportEntry 8 }

        cdx6500T1E1VGStatCurrent15MinutesReportSES OBJECT-TYPE
            SYNTAX Gauge
            ACCESS read-only
            STATUS mandatory
            DESCRIPTION
                "The number of Severely Errored Seconds (SESs)
                 encountered by the T1E1VG interface in the
                 current 15 minute interval."
        ::= { cdx6500T1E1VGStatCurrent15MinutesReportEntry 9 }

        cdx6500T1E1VGStatCurrent15MinutesReportSEFS OBJECT-TYPE
            SYNTAX Gauge
            ACCESS read-only
            STATUS mandatory
            DESCRIPTION
                "The number of Severely Errored Framing Seconds (SEFSs)
                 encountered by the T1E1VG interface in the current
                 15 minute interval."
        ::= { cdx6500T1E1VGStatCurrent15MinutesReportEntry 10 }

        cdx6500T1E1VGStatCurrent15MinutesReportUAS OBJECT-TYPE
            SYNTAX Gauge
            ACCESS read-only
            STATUS mandatory
            DESCRIPTION
                "The number of Unavailable Seconds (UASs)
                 encountered by the T1E1VG interface in the 
                 current 15 minute interval."
        ::= { cdx6500T1E1VGStatCurrent15MinutesReportEntry 11 }

        -- T1 Channel State Table

        cdx6500T1E1VGStatT1ChannelStateTable OBJECT-TYPE
            SYNTAX SEQUENCE OF Cdx6500T1StatT1ChannelStateEntry
            ACCESS not-accessible
            STATUS mandatory
            DESCRIPTION
                "The Channel State Table contains the current
                 RX Channel state of the Configured DS0 Channels."
        ::= { cdx6500STT1E1VGGroup 4 }

        cdx6500T1E1VGStatT1ChannelStateEntry OBJECT-TYPE
            SYNTAX Cdx6500T1StatT1ChannelStateEntry 
            ACCESS not-accessible
            STATUS mandatory
            DESCRIPTION
                "An Entry in the ABCD State Table."
            INDEX { cdx6500T1E1VGStatT1ChannelStateIfNumber,
                    cdx6500T1E1VGStatT1ChannelStateABCDNumber }
        ::= { cdx6500T1E1VGStatT1ChannelStateTable 1 }

        Cdx6500T1StatT1ChannelStateEntry ::=
            SEQUENCE {
                cdx6500T1E1VGStatT1ChannelStateIfNumber 
                    INTEGER,
                cdx6500T1E1VGStatT1ChannelStateABCDNumber 
                    INTEGER,
                cdx6500T1E1VGStatT1ChannelStateCurrentRxState
                    DisplayString
                }

        cdx6500T1E1VGStatT1ChannelStateIfNumber OBJECT-TYPE
            SYNTAX INTEGER 
            ACCESS read-only
            STATUS mandatory
            DESCRIPTION
                "Interface number of the configured T1 channel."
        ::= {cdx6500T1E1VGStatT1ChannelStateEntry 1 }

        cdx6500T1E1VGStatT1ChannelStateABCDNumber OBJECT-TYPE
            SYNTAX INTEGER (1..24)
            ACCESS read-only
            STATUS mandatory
            DESCRIPTION
                "ABCD number of the configured T1 channel."
        ::= {cdx6500T1E1VGStatT1ChannelStateEntry 2 }

        cdx6500T1E1VGStatT1ChannelStateCurrentRxState OBJECT-TYPE
            SYNTAX DisplayString
            ACCESS read-only
            STATUS mandatory
            DESCRIPTION
                "Current RX Channel state of the configured T1 channels."
        ::= { cdx6500T1E1VGStatT1ChannelStateEntry 3 }

        -- E1ABCD State Table

        cdx6500T1E1VGStatE1ABCDStateTable OBJECT-TYPE
            SYNTAX SEQUENCE OF Cdx6500T1E1VGStatE1ABCDStateEntry
            ACCESS not-accessible
            STATUS mandatory
            DESCRIPTION
                "The ABCD State Table contains the current
                 RX ABCD state of the Configured DS0 Channels."
        ::= { cdx6500STT1E1VGGroup 5 }

        cdx6500T1E1VGStatE1ABCDStateEntry OBJECT-TYPE
            SYNTAX Cdx6500T1E1VGStatE1ABCDStateEntry
            ACCESS not-accessible
            STATUS mandatory
            DESCRIPTION
                "An Entry in the ABCD State Table."
            INDEX { cdx6500T1E1VGStatE1ABCDStateIfNumber,
                    cdx6500T1E1VGStatE1ABCDStateChannelNumber }
        ::= { cdx6500T1E1VGStatE1ABCDStateTable 1 }

        Cdx6500T1E1VGStatE1ABCDStateEntry ::=
            SEQUENCE {
                cdx6500T1E1VGStatE1ABCDStateIfNumber
                    INTEGER,
                cdx6500T1E1VGStatE1ABCDStateChannelNumber
                    INTEGER,
                cdx6500T1E1VGStatE1ABCDStateCurrentRxState
                    DisplayString
                }

        cdx6500T1E1VGStatE1ABCDStateIfNumber OBJECT-TYPE
            SYNTAX INTEGER
            ACCESS read-only
            STATUS mandatory
            DESCRIPTION
                "Interface number of the configured E1 channel."
        ::= {cdx6500T1E1VGStatE1ABCDStateEntry 1 }

        cdx6500T1E1VGStatE1ABCDStateChannelNumber OBJECT-TYPE
            SYNTAX INTEGER (1..30)
            ACCESS read-only
            STATUS mandatory
            DESCRIPTION
                "Channel number of the configured E1 channel."
        ::= {cdx6500T1E1VGStatE1ABCDStateEntry 2 }

        cdx6500T1E1VGStatE1ABCDStateCurrentRxState OBJECT-TYPE
            SYNTAX DisplayString
            ACCESS read-only
            STATUS mandatory
            DESCRIPTION
                "Current RX ABCD state of the configured E1 channels."
        ::= { cdx6500T1E1VGStatE1ABCDStateEntry 3 }

        -- The T1E1VG Control Table
        cdx6500ContT1E1VGTable OBJECT IDENTIFIER
        ::= { cdx6500Controls 19 }

        cdx6500T1E1VGContEntry OBJECT-TYPE
            SYNTAX Cdx6500T1E1VGContEntry 
            ACCESS not-accessible
            STATUS mandatory
            DESCRIPTION
                "Each control applies to a single T1E1VG Interface."
            INDEX { t1e1vgContIfNumber }
        ::= { cdx6500ContT1E1VGTable 1 }

        Cdx6500T1E1VGContEntry ::=
            SEQUENCE {
                t1e1vgContIfNumber 
                    INTEGER,
                t1e1vgContIfBoot 
                    INTEGER
                }

        t1e1vgContIfNumber OBJECT-TYPE
            SYNTAX INTEGER 
            ACCESS not-accessible
            STATUS mandatory
            DESCRIPTION
                "Interface number of the T1E1VG."
        ::= { cdx6500T1E1VGContEntry 1 }

        t1e1vgContIfBoot OBJECT-TYPE
            SYNTAX INTEGER {
                   boot       (1),
                   noboot     (2)
                   }
            ACCESS write-only
            STATUS mandatory
            DESCRIPTION
                "Boot operations for the specified T1E1VG.
                 boot   : Boots the T1E1VG Interface 
                 noboot : Do not Boots the T1E1VG Interface."
        ::= { cdx6500T1E1VGContEntry 2 }

        END
