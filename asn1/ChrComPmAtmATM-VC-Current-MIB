ChrComPmAtmATM-VC-Current-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComPmAtm				FROM  Chromatis-MIB
	chrComIfifIndex					FROM  ChrComIfifTable-MIB
	atmVclVpi					FROM  ATM-MIB
	atmVclVci					FROM  ATM-MIB
	TruthValue				FROM  ChrTyp-MIB
	Gauge32				FROM  SNMPv2-SMI;

-- chrComPmAtmATM-VC-Current Table

chrComPmAtmATM-VC-CurrentTable		OBJECT-TYPE
	SYNTAX		SEQUENCE OF ChrComPmAtmATM-VC-CurrentEntry
	MAX-ACCESS	not-accessible
	STATUS		current
	DESCRIPTION
	""
	::= { chrComPmAtm 7}

chrComPmAtmATM-VC-CurrentEntry		OBJECT-TYPE
	SYNTAX		ChrComPmAtmATM-VC-CurrentEntry
	MAX-ACCESS	not-accessible
	STATUS		current
	DESCRIPTION
	""
	INDEX  {  chrComIfifIndex, atmVclVpi, atmVclVci }

--DEFAULT  get-function-async  MNIL_GetRoutine
--DEFAULT  set-function-async  MNIL_SetRoutine
--DEFAULT  next-function-async MNIL_NextRoutine
--DEFAULT  test-function-async MNIL_TestRoutine
--DEFAULT  cookie "ATM-VC-Current"
	::= { chrComPmAtmATM-VC-CurrentTable  1 }

ChrComPmAtmATM-VC-CurrentEntry  ::=
	SEQUENCE  {
	chrComPmAtmSuspectedInterval	TruthValue,
	chrComPmAtmElapsedTime		Unsigned32	(0..4294967295),
	chrComPmAtmSuppressedIntrvls	Gauge32			(0..4294967295),
	chrComPmAtmReceivedCells		Gauge32			(0..4294967295),
	chrComPmAtmTransmittedCells	Gauge32			(0..4294967295),
	chrComPmAtmThresholdProfIndex	Unsigned32	(0..4294967295),
	chrComPmAtmResetPmCountersAction	TruthValue
}

chrComPmAtmSuspectedInterval 	OBJECT-TYPE
	SYNTAX		TruthValue
	MAX-ACCESS 	read-only
	STATUS 		current
	DESCRIPTION
	""
	::= { chrComPmAtmATM-VC-CurrentEntry  1 }

chrComPmAtmElapsedTime 	OBJECT-TYPE
	SYNTAX		Unsigned32	(0..4294967295)
	MAX-ACCESS 	read-only
	STATUS 		current
	DESCRIPTION
	""
	::= { chrComPmAtmATM-VC-CurrentEntry  2 }

chrComPmAtmSuppressedIntrvls 	OBJECT-TYPE
	SYNTAX		Gauge32			(0..4294967295)
	MAX-ACCESS 	read-only
	STATUS 		current
	DESCRIPTION
	""
	::= { chrComPmAtmATM-VC-CurrentEntry  3 }

chrComPmAtmReceivedCells 	OBJECT-TYPE
	SYNTAX		Gauge32			(0..4294967295)
	MAX-ACCESS 	read-only
	STATUS 		current
	DESCRIPTION
	""
	::= { chrComPmAtmATM-VC-CurrentEntry  4 }

chrComPmAtmTransmittedCells 	OBJECT-TYPE
	SYNTAX		Gauge32			(0..4294967295)
	MAX-ACCESS 	read-only
	STATUS 		current
	DESCRIPTION
	""
	::= { chrComPmAtmATM-VC-CurrentEntry  5 }

chrComPmAtmThresholdProfIndex 	OBJECT-TYPE
	SYNTAX		Unsigned32	(0..4294967295)
	MAX-ACCESS 	read-write
	STATUS 		current
	DESCRIPTION
	""
	::= { chrComPmAtmATM-VC-CurrentEntry  6 }

chrComPmAtmResetPmCountersAction 	OBJECT-TYPE
	SYNTAX		TruthValue
	MAX-ACCESS 	read-write
	STATUS 		current
	DESCRIPTION
	""
	::= { chrComPmAtmATM-VC-CurrentEntry  7 }


END
