--			Ascend mibprroute MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBPRROUTE-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibprivateRouteTableProfile  OBJECT IDENTIFIER ::= { configuration 103}

	-- The mibprivateRouteTableProfile table
	--
	-- This table contains parameters for the mibprivateRouteTableProfile profile
	--

    mibprivateRouteTableProfileTable	OBJECT-TYPE
	SYNTAX		SEQUENCE OF MibprivateRouteTableProfileEntry
	ACCESS		not-accessible
	STATUS		mandatory
	DESCRIPTION	"A list of mibprivateRouteTableProfile profile entries."
	::= { mibprivateRouteTableProfile 1 }

    mibprivateRouteTableProfileEntry	OBJECT-TYPE
	SYNTAX		MibprivateRouteTableProfileEntry
	ACCESS		not-accessible
	STATUS		mandatory
	DESCRIPTION	"A mibprivateRouteTableProfile entry containing objects that
			 maps to the parameters of mibprivateRouteTableProfile profile."
	INDEX		{ privateRouteTableProfile-Name }
	::= { mibprivateRouteTableProfileTable 1 }

    MibprivateRouteTableProfileEntry ::=
	SEQUENCE {
	    privateRouteTableProfile-Name
		DisplayString,
	    privateRouteTableProfile-Action-o
		INTEGER
	}

    privateRouteTableProfile-Name	OBJECT-TYPE
	SYNTAX	DisplayString
	ACCESS	read-only
	STATUS	mandatory
	DESCRIPTION	"The name of this route table profile."
	::= { mibprivateRouteTableProfileEntry 1 }

    privateRouteTableProfile-Action-o	OBJECT-TYPE
	SYNTAX	INTEGER {
		    noAction (1),
		    createProfile (2),
		    deleteProfile (3)
		}
	ACCESS	read-write
	STATUS	mandatory
	DESCRIPTION	""
	::= { mibprivateRouteTableProfileEntry 2 }


	-- The mibprivateRouteTableProfile__route_description_list table
	--
	-- This table contains parameters for the mibprivateRouteTableProfile__route_description_list profile
	--

    mibprivateRouteTableProfile-RouteDescriptionListTable	OBJECT-TYPE
	SYNTAX		SEQUENCE OF MibprivateRouteTableProfile-RouteDescriptionListEntry
	ACCESS		not-accessible
	STATUS		mandatory
	DESCRIPTION	"A list of mibprivateRouteTableProfile__route_description_list profile entries."
	::= { mibprivateRouteTableProfile 2 }

    mibprivateRouteTableProfile-RouteDescriptionListEntry	OBJECT-TYPE
	SYNTAX		MibprivateRouteTableProfile-RouteDescriptionListEntry
	ACCESS		not-accessible
	STATUS		mandatory
	DESCRIPTION	"A mibprivateRouteTableProfile__route_description_list entry containing objects that
			 maps to the parameters of mibprivateRouteTableProfile__route_description_list profile."
	INDEX		{ privateRouteTableProfile-RouteDescriptionList-Name, privateRouteTableProfile-RouteDescriptionList-Index-o }
	::= { mibprivateRouteTableProfile-RouteDescriptionListTable 1 }

    MibprivateRouteTableProfile-RouteDescriptionListEntry ::=
	SEQUENCE {
	    privateRouteTableProfile-RouteDescriptionList-Name
		DisplayString,
	    privateRouteTableProfile-RouteDescriptionList-Index-o
		INTEGER,
	    privateRouteTableProfile-RouteDescriptionList-Enabled
		INTEGER,
	    privateRouteTableProfile-RouteDescriptionList-DestAddress
		IpAddress,
	    privateRouteTableProfile-RouteDescriptionList-Netmask
		IpAddress,
	    privateRouteTableProfile-RouteDescriptionList-GatewayAddress
		IpAddress,
	    privateRouteTableProfile-RouteDescriptionList-Metric
		INTEGER
	}

    privateRouteTableProfile-RouteDescriptionList-Name	OBJECT-TYPE
	SYNTAX	DisplayString
	ACCESS	read-only
	STATUS	mandatory
	DESCRIPTION	""
	::= { mibprivateRouteTableProfile-RouteDescriptionListEntry 1 }

    privateRouteTableProfile-RouteDescriptionList-Index-o	OBJECT-TYPE
	SYNTAX	INTEGER
	ACCESS	read-only
	STATUS	mandatory
	DESCRIPTION	""
	::= { mibprivateRouteTableProfile-RouteDescriptionListEntry 2 }

    privateRouteTableProfile-RouteDescriptionList-Enabled	OBJECT-TYPE
	SYNTAX	INTEGER {
		    no (1),
		    yes (2)
		}
	ACCESS	read-write
	STATUS	mandatory
	DESCRIPTION	"Set yes to enable this route in the routing table."
	::= { mibprivateRouteTableProfile-RouteDescriptionListEntry 3 }

    privateRouteTableProfile-RouteDescriptionList-DestAddress	OBJECT-TYPE
	SYNTAX	IpAddress
	ACCESS	read-write
	STATUS	mandatory
	DESCRIPTION	"The IP address of the destination network or subnet."
	::= { mibprivateRouteTableProfile-RouteDescriptionListEntry 4 }

    privateRouteTableProfile-RouteDescriptionList-Netmask	OBJECT-TYPE
	SYNTAX	IpAddress
	ACCESS	read-write
	STATUS	mandatory
	DESCRIPTION	"The netmask to be used for the destination."
	::= { mibprivateRouteTableProfile-RouteDescriptionListEntry 5 }

    privateRouteTableProfile-RouteDescriptionList-GatewayAddress	OBJECT-TYPE
	SYNTAX	IpAddress
	ACCESS	read-write
	STATUS	mandatory
	DESCRIPTION	"The address of the gateway/router for this private route. An address of 0.0.0.0 means use the global routing table for this route."
	::= { mibprivateRouteTableProfile-RouteDescriptionListEntry 6 }

    privateRouteTableProfile-RouteDescriptionList-Metric	OBJECT-TYPE
	SYNTAX	INTEGER
	ACCESS	read-write
	STATUS	mandatory
	DESCRIPTION	"The number of hops to the named host."
	::= { mibprivateRouteTableProfile-RouteDescriptionListEntry 7 }

END
