--
-- Cayman GatorBox "R6" AppleTalk MIB
--
--
-- 1.	This version of the Cayman private AppleTalk MIB is a duplicate of
--	the AppleTalk MIB in the Kinetics FastPath KStar V8.0 software.
--	This duplication of private MIB variable definitions is done as a
--	courtesy to our customers.
--
--	FASTPATH-MIB { private(4) enterprises(1) excelan(23)
--			 mibDoc(2) fastpath(11) }
--
-- 2.	This is the first release of an RFC1066 MIB with RFC1067 SNMP. It is
--	not yet fully compliant.  It is, however, functional and useful as a
--	monitoring tool.  We plan to release a fully compliant RFC1066 as a
--	point release to the v2.0 GatorBox software.
--
--	The RFC1066 MIB for TCP/IP is also supported with the following
--	exceptions:
--
-- History:
--	Originally created by Steve Waldbusser at Carnegie Mellon
--
--	v1.0	11/89	initially formed from  Kinetics KStar V8.0 MIB
--
--		02/89	cleaned up some syntax errors; changed to be
--			parsable by CMU ASN.1 parser.
--
--		05/89	commented out bogus DEFINITION lines.
--
-- Notes:
--
-- The tcp variables are present but are unsupported; While TCP is present, the
--  SNMP MIB variables are not yet supported.
-- The egp variables are present but are unsupported; There is no protocol
--  support for EGP in the GatorBox.
-- The may be slight inconsistencies about reporting of some variables as
--  we have not yet completed a full review of the implementation to determine
--  compliance.
--
-- scc, alap and ethernet are prefixed by 2 byte interface # ?
--
-- atifTable is indexed by trailing 1 byte entry number
-- rtmpTable is indexed by trailing 2 byte network number
-- zipTable is indexed by trailing 1 byte entry number

CAYMAN-MIB  -- { private(4) enterprises(1) cayman(7) gatorbox(1) }

DEFINITIONS ::= BEGIN

IMPORTS
	OBJECT-TYPE, NetworkAddress, IpAddress,
		Counter, Gauge, TimeTicks
	FROM RFC1155-SMI;

cayman		OBJECT IDENTIFIER ::= { enterprises 7 }
gatorbox	OBJECT IDENTIFIER ::= { cayman 1 }
gatorbox-id	OBJECT IDENTIFIER ::= { cayman 2 }
cayscc		OBJECT IDENTIFIER ::= { gatorbox 1 }
alap		OBJECT IDENTIFIER ::= { gatorbox 2 }
ethernet	OBJECT IDENTIFIER ::= { gatorbox 3 }
aarp		OBJECT IDENTIFIER ::= { gatorbox 4 }
atif		OBJECT IDENTIFIER ::= { gatorbox 5 }
ddp		OBJECT IDENTIFIER ::= { gatorbox 6 }
rtmp		OBJECT IDENTIFIER ::= { gatorbox 7 }
kip		OBJECT IDENTIFIER ::= { gatorbox 8 }
zip		OBJECT IDENTIFIER ::= { gatorbox 9 }
nbp		OBJECT IDENTIFIER ::= { gatorbox 10 }
caymanEcho	OBJECT IDENTIFIER ::= { gatorbox 11 }
buffer		OBJECT IDENTIFIER ::= { gatorbox 12 }

-- Product id

name 		OBJECT-TYPE
SYNTAX		OCTET STRING
ACCESS		read-only
STATUS		mandatory
DESCRIPTION	"The name of the product in human-readable form."
::= { gatorbox-id 1 }

-- The SCC Group

sccInterruptCount OBJECT-TYPE
SYNTAX		Counter
ACCESS		read-only
STATUS		mandatory
DESCRIPTION	"The total number of receive interrupts on this
		interface."
::=  { cayscc 1 }

sccAbortCount	OBJECT-TYPE
SYNTAX		Counter
ACCESS		read-only
STATUS		mandatory
DESCRIPTION	"The total number of abort interrupts on this
		interface."
::=  { cayscc 2 }

sccSpuriousCount OBJECT-TYPE
SYNTAX		Counter
ACCESS		read-only
STATUS		mandatory
DESCRIPTION	"The total number of spurious interrupts on this
		interface."
::=  { cayscc 3 }

sccCRCCount OBJECT-TYPE
SYNTAX		Counter
ACCESS		read-only
STATUS		mandatory
DESCRIPTION	"The total number of CRC errors on this interface."
::=  { cayscc 4 }

sccOverrunCount OBJECT-TYPE
SYNTAX		Counter
ACCESS		read-only
STATUS		mandatory
DESCRIPTION	"The total number of receive overrun errors on this
		interface."
::=  { cayscc 5 }

sccUnderrunCount OBJECT-TYPE
SYNTAX		Counter
ACCESS		read-only
STATUS		mandatory
DESCRIPTION	"The total number of receive underrun errors on this
		interface."
::=  { cayscc 6 }

-- The ALAP Group

alapReceiveCount OBJECT-TYPE
SYNTAX		Counter
ACCESS		read-only
STATUS		mandatory
DESCRIPTION	"The total number of good packets received on this
		LocalTalk interface."
::= { alap 1 }

alapTransmitCount OBJECT-TYPE
SYNTAX		Counter
ACCESS		read-only
STATUS		mandatory
DESCRIPTION	"The total number of packets transmitted on this
		LocalTalk interface."
::= { alap 2 }

alapNoHandlerCount OBJECT-TYPE
SYNTAX		Counter
ACCESS		read-only
STATUS		mandatory
DESCRIPTION	"The total number of packets received on this
		LocalTalk interface for which there was no protocol
		handler."
::= { alap 3 }

alapLengthErrorCount OBJECT-TYPE
SYNTAX		Counter
ACCESS		read-only
STATUS		mandatory
DESCRIPTION	"The total number of packets received on this
		LocalTalk interface whose actual length did not match
		the length in its header."
::= { alap 4 }

alapBadCount OBJECT-TYPE
SYNTAX		Counter
ACCESS		read-only
STATUS		mandatory
DESCRIPTION	"The total number of bad packets received on this
		LocalTalk interface."
::= { alap 5 }

alapCollisionCount OBJECT-TYPE
SYNTAX		Counter
ACCESS		read-only
STATUS		mandatory
DESCRIPTION	"The total number of collisions assumed on this
		LocalTalk interface."
::= { alap 6 }

alapDeferCount OBJECT-TYPE
SYNTAX		Counter
ACCESS		read-only
STATUS		mandatory
DESCRIPTION	"The total number of times this LocalTalk interface
		deferred to other packets."
::= { alap 7 }

alapNoDataCount OBJECT-TYPE
SYNTAX		Counter
ACCESS		read-only
STATUS		mandatory
DESCRIPTION	"The total number of times this LocalTalk interface
		received an RTS packet and expected a data packet,
		but did not receive any data packet."
::= { alap 8 }

alapRandomCTS OBJECT-TYPE
SYNTAX		Counter
ACCESS		read-only
STATUS		mandatory
DESCRIPTION	"The total number of times this LocalTalk interface
		received a CTS packet that was not solicited by an
		RTS packet."
::= { alap 9 }


-- The Ethernet Group

cayetherCRCErrors OBJECT-TYPE
SYNTAX		Counter
ACCESS		read-only
STATUS		mandatory
DESCRIPTION	"The total number of CRC errors on this ethernet
		interface."
::= { ethernet 1 }

cayetherAlignErrors OBJECT-TYPE
SYNTAX		Counter
ACCESS		read-only
STATUS		mandatory
DESCRIPTION	"The total number of alignment errors on this ethernet
		interface."
::= { ethernet 2 }

cayetherResourceError OBJECT-TYPE
SYNTAX		Counter
ACCESS		read-only
STATUS		mandatory
DESCRIPTION	"The total number of errors due to lack of resources
		on thick ethernet interface."
::= { ethernet 3 }

cayetherOverrunErrors OBJECT-TYPE
SYNTAX		Counter
ACCESS		read-only
STATUS		mandatory
DESCRIPTION	"The total number of overrun errors on this ethernet
		interface."
::= { ethernet 4 }

cayetherInPackets OBJECT-TYPE
SYNTAX		Counter
ACCESS		read-only
STATUS		mandatory
DESCRIPTION	"The total number of input packets on this ethernet
		interface."
::= { ethernet 5 }

cayetherOutPackets OBJECT-TYPE
SYNTAX		Counter
ACCESS		read-only
STATUS		mandatory
DESCRIPTION	"The total number of output packets on this ethernet
		interface."
::= { ethernet 6 }

cayetherBadTransmits OBJECT-TYPE
SYNTAX		Counter
ACCESS		read-only
STATUS		mandatory
DESCRIPTION	"The total number of transmission errors on this
		ethernet interface."
::= { ethernet 7 }

cayetherOversizeFrames OBJECT-TYPE
SYNTAX		Counter
ACCESS		read-only
STATUS		mandatory
DESCRIPTION	"The total number of oversize frame errors on this
		ethernet interface."
::= { ethernet 8 }

cayetherSpurRUReadys OBJECT-TYPE
SYNTAX		Counter
ACCESS		read-only
STATUS		mandatory
DESCRIPTION	"The total number of spurious RU Ready interrupts on
		this ethernet interface."
::= { ethernet 9 }

cayetherSpurCUActives OBJECT-TYPE
SYNTAX		Counter
ACCESS		read-only
STATUS		mandatory
DESCRIPTION	"The total number of spurious CU Active interrupts on
		this ethernet interface."
::= { ethernet 10 }

cayetherSpurUnknown OBJECT-TYPE
SYNTAX		Counter
ACCESS		read-only
STATUS		mandatory
DESCRIPTION	"The total number of unknown spurious interrupts on
		this ethernet interface."
::= { ethernet 11 }

cayetherBcastDrops OBJECT-TYPE
SYNTAX		Counter
ACCESS		read-only
STATUS		mandatory
DESCRIPTION	"The total number of broadcast packets dropped to free
		resources on this ethernet interface."
::= { ethernet 12 }

cayetherReceiverRestarts OBJECT-TYPE
SYNTAX		Counter
ACCESS		read-only
STATUS		mandatory
DESCRIPTION	"The total number of receiver restarts on this
		ethernet interface."
::= { ethernet 13 }

cayetherReinterrupts OBJECT-TYPE
SYNTAX		Counter
ACCESS		read-only
STATUS		mandatory
DESCRIPTION	"The total number of reinterrupts on this ethernet
		interface."
::= { ethernet 14 }

cayetherBufferReroutes OBJECT-TYPE
SYNTAX		Counter
ACCESS		read-only
STATUS		mandatory
DESCRIPTION	"The total number of buffers taken off of queues to
		service incoming packets on this ethernet interface."
::= { ethernet 15 }

cayetherBufferDrops OBJECT-TYPE
SYNTAX		Counter
ACCESS		read-only
STATUS		mandatory
DESCRIPTION	"The total number of buffers dropped on this ethernet
		interface."
::= { ethernet 16 }

cayetherCollisions OBJECT-TYPE
SYNTAX		Counter
ACCESS		read-only
STATUS		mandatory
DESCRIPTION	"The total number of collisions encountered on this
		ethernet interface."
::= { ethernet 17 }

cayetherDefers OBJECT-TYPE
SYNTAX		Counter
ACCESS		read-only
STATUS		mandatory
DESCRIPTION	"The total number of deferrals encountered on this
		ethernet interface."
::= { ethernet 18 }

cayetherDMAUnderruns OBJECT-TYPE
SYNTAX		Counter
ACCESS		read-only
STATUS		mandatory
DESCRIPTION	"The total number of DMA Underruns on this ethernet
		interface."
::= { ethernet 19 }

cayetherMaxCollisions OBJECT-TYPE
SYNTAX		Counter
ACCESS		read-only
STATUS		mandatory
DESCRIPTION	"The total number of packets dropped on this ethernet
		interface because they encountered more than 16
		collisions."
::= { ethernet 20 }

cayetherNoCarriers OBJECT-TYPE
SYNTAX		Counter
ACCESS		read-only
STATUS		mandatory
DESCRIPTION	"The total number of no carrier errors experienced on
		this ethernet interface."
::= { ethernet 21 }

cayetherNoCTS OBJECT-TYPE
SYNTAX		Counter
ACCESS		read-only
STATUS		mandatory
DESCRIPTION	"The total number of no CTS errors experienced on this
		ethernet interface."
::= { ethernet 22 }

cayetherNoSQEs OBJECT-TYPE
SYNTAX		Counter
ACCESS		read-only
STATUS		mandatory
DESCRIPTION	"The total number of no SQE errors experienced on this
		ethernet interface."
::= { ethernet 23 }


-- The AARP Group

aarpTable OBJECT-TYPE
SYNTAX		SEQUENCE OF AarpEntry
ACCESS		read-write
STATUS		mandatory
DESCRIPTION	"The AppleTalk Address Resolution Table contains an
		equivalence of AppleTalk Network Addresses to the
		link layer physical address."
::= { aarp 1 }

aarpEntry OBJECT-TYPE
SYNTAX		SEQUENCE OF AarpEntry
ACCESS		read-write
STATUS		mandatory
DESCRIPTION	"Each entry contains one AppleTalk Network Address to
		'physical' address equivalence."
::= { aarpTable 1 }

    AarpEntry ::= SEQUENCE {
	aarpIfIndex	INTEGER,
	aarpPhysAddress	OCTET STRING,
	aarpNetAddress	OCTET STRING
}

aarpIfIndex OBJECT-TYPE
SYNTAX		INTEGER
ACCESS		read-only
STATUS		mandatory
DESCRIPTION	"The interface on which this entry's equivalence is
		effective; The interface identified by a particular
		value of this index is the same interface as
		identified by the same value of ifIndex."
::= { aarpEntry 1 }

aarpPhysAddress OBJECT-TYPE
SYNTAX		OCTET STRING
ACCESS		read-only
STATUS		mandatory
DESCRIPTION	"The media-dependent physical address."
::= { aarpEntry 2 }

aarpNetAddress OBJECT-TYPE
SYNTAX		OCTET STRING
ACCESS		read-only
STATUS		mandatory
DESCRIPTION	"The AppleTalk Network Address corresponding to the
		media-dependent physical address."
::= { aarpEntry 3 }

atifTable OBJECT-TYPE
SYNTAX		SEQUENCE OF AtifEntry
ACCESS		read-write
STATUS		mandatory
DESCRIPTION	"The description of one of the logical interfaces on
		this entity."
::= { atif 1 }

atifEntry OBJECT-TYPE
SYNTAX		AtifEntry
ACCESS		read-write
STATUS		mandatory
DESCRIPTION	"The description of one of the logical appletalk
		interfaces on this entity."
::= { atifTable 1 }

    AtifEntry ::= SEQUENCE {
	atifIndex	INTEGER,
	atifDescr	OCTET STRING,
	atifType	INTEGER,
	atifNetStart	OCTET STRING,
	atifNetEnd	OCTET STRING,
	atifNetAddress	OCTET STRING,
	atifStatus	INTEGER,
	atifNetConfig	INTEGER,
	atifZoneConfig	INTEGER,
	atifZone	OCTET STRING,
	atifIfIndex	INTEGER
}

atifIndex OBJECT-TYPE
SYNTAX		INTEGER
ACCESS		read-only
STATUS		mandatory
DESCRIPTION	"A unique value for each logical AppleTalk interface;
		Its value is between 1 and the total number of
		logical AppleTalk interfaces."
::= { atifEntry 1 }

atifDescr OBJECT-TYPE
SYNTAX		OCTET STRING
ACCESS		read-only
STATUS		mandatory
DESCRIPTION	"A text string containing information about the
		interface; This string is intended for presentation
		to a human; it must not contain anything but
		printable ASCII characters."
::= { atifEntry 2 }

atifType OBJECT-TYPE
SYNTAX		INTEGER {
			other(1),	-- none of the following
			localtalk(2),
			ethertalk1(3),
			ethertalk2(4),
			tokentalk(5),
			iptalk(6)
		}
ACCESS		read-only
STATUS		mandatory
DESCRIPTION	"The type of interface, distinguished by the protocol
		immediately below DDP in the protocol stack."
::= { atifEntry 3 }

atifNetStart OBJECT-TYPE
SYNTAX		OCTET STRING
ACCESS		read-write
STATUS		mandatory
DESCRIPTION	"The first Appletalk network address in the range
		configured for this interface, or the single network
		number configured for this interface."
::= { atifEntry 4 }

atifNetEnd OBJECT-TYPE
SYNTAX		OCTET STRING
ACCESS		read-write
STATUS		mandatory
DESCRIPTION	"The last Appletalk network address in the range
		configured for this interface, or zero if a single
		network number is configured."
::= { atifEntry 5 }

atifNetAddress OBJECT-TYPE
SYNTAX		OCTET STRING
ACCESS		read-write
STATUS		mandatory
DESCRIPTION	"The Appletalk network address configured for this interface."
::= { atifEntry 6 }

atifStatus OBJECT-TYPE
SYNTAX		INTEGER {
			operational(1),
			unconfigured(2),
			off(3)
		}
ACCESS		read-only
STATUS		mandatory
DESCRIPTION	"The configuration status of this interface."
::= { atifEntry 7 }

atifNetConfig OBJECT-TYPE
SYNTAX		INTEGER {
			configured(1),
			garnered(2),
			guessed(3),
			unconfigured(4)
		}
ACCESS		read-only
STATUS		mandatory
DESCRIPTION	"The configuration status of the DDP network number(s)
		for this interface."
::= { atifEntry 8 }

atifZoneConfig OBJECT-TYPE
SYNTAX		INTEGER {
			configured(1),
			garnered(2),
			guessed(3),
			unconfigured(4)
		}
ACCESS		read-only
STATUS		mandatory
DESCRIPTION	"The configuration status of AppleTalk zone name(s)
		for this interface."
::= { atifEntry 9 }

atifZone OBJECT-TYPE
SYNTAX		OCTET STRING
ACCESS		read-write
STATUS		mandatory
DESCRIPTION	"The zone name configured for this logical interface;
		In Phase 2 networks, this is the default zone for
		this interface."
::= { atifEntry 10 }

atifIfIndex OBJECT-TYPE
SYNTAX		INTEGER
ACCESS		read-write
STATUS		mandatory
DESCRIPTION	"The physical interface associated with this logical
		interface; A particular value of this index
		identifies the same interface as is identified by the
		same value of ifIndex."
::= { atifEntry 11 }


-- The DDP Group

ddpOutRequests OBJECT-TYPE
SYNTAX		Counter
ACCESS		read-only
STATUS		mandatory
DESCRIPTION	"The total number of DDP datagrams which were supplied
		to DDP in requests for transmission."
::= { ddp 1 }

ddpOutShort OBJECT-TYPE
SYNTAX		Counter
ACCESS		read-only
STATUS		mandatory
DESCRIPTION	"The total number of short DDP datagrams which were
		transmitted from this entity."
::= { ddp 2 }

ddpOutLong OBJECT-TYPE
SYNTAX		Counter
ACCESS		read-only
STATUS		mandatory
DESCRIPTION	"The total number of long DDP datagrams which were
		transmitted from this entity."
::= { ddp 3 }

ddpReceived OBJECT-TYPE
SYNTAX		Counter
ACCESS		read-only
STATUS		mandatory
DESCRIPTION	"The total number of input datagrams received by DDP."
::= { ddp 4 }

ddpToForward OBJECT-TYPE
SYNTAX		Counter
ACCESS		read-only
STATUS		mandatory
DESCRIPTION	"The number of input datagrams for which this entity
		was not their final DDP destination, as a result of
		which an attempt was made to find a route to forward
		them to that final destination."
::= { ddp 5 }

ddpForwards OBJECT-TYPE
SYNTAX		Counter
ACCESS		read-only
STATUS		mandatory
DESCRIPTION	"The number of input datagrams for which this entity
		was not their final DDP destination, as a result of
		which they were forwarded to their final destination."
::= { ddp 6 }

ddpForMe OBJECT-TYPE
SYNTAX		Counter
ACCESS		read-only
STATUS		mandatory
DESCRIPTION	"The total number of input DDP datagrams for which
		this entity was their final DDP destination."
::= { ddp 7 }

ddpNoProtocolHandler OBJECT-TYPE
SYNTAX		Counter
ACCESS		read-only
STATUS		mandatory
DESCRIPTION	"The total number of DDP datagrams addressed to this
		entity that were addressed to an upper layer protocol
		for which no protocol handler existed."
::= { ddp 8 }

ddpOutNoRoutes OBJECT-TYPE
SYNTAX		Counter
ACCESS		read-only
STATUS		mandatory
DESCRIPTION	"The total number of DDP datagrams dropped because a
		route could not be found to their final destination."
::= { ddp 9 }

ddpTooShortDrops OBJECT-TYPE
SYNTAX		Counter
ACCESS		read-only
STATUS		mandatory
DESCRIPTION	"The total number of input DDP datagrams dropped
		because the received data length was less than the
		data length in the DDP header."
::= { ddp 10 }

ddpTooLongDrops OBJECT-TYPE
SYNTAX		Counter
ACCESS		read-only
STATUS		mandatory
DESCRIPTION	"The total number of input DDP datagrams dropped
		because they exceeded the maximum DDP datagram size
		or because their header size was greater than their
		length."
::= { ddp 11 }

ddpBroadcastDrops OBJECT-TYPE
SYNTAX		Counter
ACCESS		read-only
STATUS		mandatory
DESCRIPTION	"The total number of input DDP datagrams dropped
		because this entity was not their final destination
		and they were addressed to the link level broadcast."
::= { ddp 12 }

ddpShortDDPDrops OBJECT-TYPE
SYNTAX		Counter
ACCESS		read-only
STATUS		mandatory
DESCRIPTION	"The total number of input DDP datagrams dropped
		because this entity was not their final destination
		and their type was short DDP."
::= { ddp 13 }

ddpHopCountDrops OBJECT-TYPE
SYNTAX		Counter
ACCESS		read-only
STATUS		mandatory
DESCRIPTION	"The total number of input DDP datagrams dropped
		because this entity was not their final destination
		and their hop count would exceed 16."
::= { ddp 14 }


-- The RTMP Group

rtmpTable OBJECT-TYPE
SYNTAX		SEQUENCE OF RtmpEntry
ACCESS		read-write
STATUS		mandatory
DESCRIPTION	"This entity's RTMP table."
::= { rtmp 1 }

rtmpEntry OBJECT-TYPE
SYNTAX		RtmpEntry
ACCESS		read-write
STATUS		mandatory
DESCRIPTION	"The route entry to a particular range of networks."
::= { rtmpTable 1 }

RtmpEntry ::= SEQUENCE {
	rtmpRangeStart	OCTET STRING,
	rtmpRangeEnd	OCTET STRING,
	rtmpNextHop	OCTET STRING,
	rtmpInterface	INTEGER,
	rtmpHops	INTEGER,
	rtmpState	INTEGER
}

rtmpRangeStart OBJECT-TYPE
SYNTAX		OCTET STRING
ACCESS		read-write
STATUS		mandatory
DESCRIPTION	"The first DDP network address in the range of
		networks that this routing entry pertains to, or the
		single network number that this routing entry
		pertains to; This is a two octet DDP network
		address."
::= { rtmpEntry 1 }

rtmpRangeEnd OBJECT-TYPE
SYNTAX		OCTET STRING
ACCESS		read-write
STATUS		mandatory
DESCRIPTION	"The last DDP network address in the range of networks
		that this routing entry pertains to, or zero if this
		routing entry pertains to a single network number;
		This is a two octet DDP network address."
::= { rtmpEntry 2 }

rtmpNextHop OBJECT-TYPE
SYNTAX		OCTET STRING
ACCESS		read-write
STATUS		mandatory
DESCRIPTION	"The next hop in the route to this entry's destination
		network."
::= { rtmpEntry 3 }

rtmpInterface OBJECT-TYPE
SYNTAX		INTEGER
ACCESS		read-write
STATUS		mandatory
DESCRIPTION	"The index of the logical appletalk interface over
		which this route points."
::= { rtmpEntry 4 }

rtmpHops OBJECT-TYPE
SYNTAX		INTEGER
ACCESS		read-write
STATUS		mandatory
DESCRIPTION	"The number of hops required to reach the destination
		network that this entry pertains to."
::= { rtmpEntry 5 }

rtmpState OBJECT-TYPE
SYNTAX		INTEGER {
			good(1),
			suspect(2),
			bad(3)
		}
ACCESS		read-write
STATUS		mandatory
DESCRIPTION	"The status of the information contained in this route entry."
::= { rtmpEntry 6 }


-- The KIP Group

kipTable OBJECT-TYPE
SYNTAX		SEQUENCE OF KipEntry
ACCESS		read-write
STATUS		mandatory
DESCRIPTION	"The table of routing information for KIP networks."
::= { kip 1 }

kipEntry OBJECT-TYPE
SYNTAX		KipEntry
ACCESS		read-write
STATUS		mandatory
DESCRIPTION	"An entry in the routing table for RIP networks."
::= { kipTable 1 }

KipEntry ::= SEQUENCE {
   	kipNet		OCTET STRING,
   	kipNextHop	IpAddress,
   	kipHopCount	INTEGER,
   	kipBCastAddr	IpAddress,
	kipCore		INTEGER,
	kipKfps		INTEGER
}

kipNet OBJECT-TYPE
SYNTAX		OCTET STRING
ACCESS		read-write
STATUS		mandatory
DESCRIPTION	"The appletalk network address for this routing entry."
::= { kipEntry 1 }

kipNextHop OBJECT-TYPE
SYNTAX		IpAddress
ACCESS		read-write
STATUS		mandatory
DESCRIPTION	"The IP address of the next hop for this routing entry."
::= { kipEntry 2 }

kipHopCount OBJECT-TYPE
SYNTAX		INTEGER
ACCESS		read-write
STATUS		mandatory
DESCRIPTION	"The distance in hops to the destination of this route."
::= { kipEntry 3 }

kipBCastAddr OBJECT-TYPE
SYNTAX		IpAddress
ACCESS		read-write
STATUS		mandatory
DESCRIPTION	"The form of the IP address used to broadcast on this network."
::= { kipEntry 4 }

kipCore OBJECT-TYPE
SYNTAX		INTEGER {
			core(1),
			notcore(2)
		}
ACCESS		read-write
STATUS		mandatory
DESCRIPTION	"The status of this network as a Core network."
::= { kipEntry 5 }

kipKfps OBJECT-TYPE
SYNTAX		INTEGER {
			kfps(1),
			notkfps(2)
		}
ACCESS		read-write
STATUS		mandatory
DESCRIPTION	"The type of the device that this network resides on."
::= { kipEntry 6 }


-- The ZIP Group

zipTable OBJECT-TYPE
SYNTAX		SEQUENCE OF ZipEntry
ACCESS		read-write
STATUS		mandatory
DESCRIPTION	"The table of zone information for reachable AppleTalk
		networks."
::= { zip 1 }

zipEntry OBJECT-TYPE
SYNTAX		ZipEntry
ACCESS		read-write
STATUS		mandatory
DESCRIPTION	"An entry of zone information for a particular zone
		and network combination."
::= { zipTable 1 }

ZipEntry ::= SEQUENCE {
	zipZoneName	OCTET STRING,
	zipZoneIndex	INTEGER,
	zipNetStart	OCTET STRING,
	zipNetEnd	OCTET STRING
}

zipZoneName OBJECT-TYPE
SYNTAX		OCTET STRING
ACCESS		read-write
STATUS		mandatory
DESCRIPTION	"The ASCII zone name of this entry."
::= { zipEntry 1 }

zipZoneIndex OBJECT-TYPE
SYNTAX		INTEGER
ACCESS		read-only
STATUS		mandatory
DESCRIPTION	"An integer that is unique to the zipZoneName that is
		present in this entry; For any given zone name,
		every zipEntry that has that zone name will have the
		same zipZoneIndex (in a given GatorBox, as long as it
		has not been rebooted)."
::= { zipEntry 2 }

zipZoneNetStart OBJECT-TYPE
SYNTAX		OCTET STRING
ACCESS		read-write
STATUS		mandatory
DESCRIPTION	"The network that starts the range for this entry, or
		the single network number for this entry."
::= { zipEntry 3 }

zipZoneNetEnd OBJECT-TYPE
SYNTAX		OCTET STRING
ACCESS		read-write
STATUS		mandatory
DESCRIPTION	"The network that ends the range for this entry, or
		zero if this entry refers to a single network number."
::= { zipEntry 4 }


-- The NBP Group

nbpTable OBJECT-TYPE
SYNTAX		SEQUENCE OF NbpEntry
ACCESS		read-write
STATUS		mandatory
DESCRIPTION	"The table of NBP services registered on this entity."
::= { nbp 1 }

nbpEntry OBJECT-TYPE
SYNTAX		NbpEntry
ACCESS		read-write
STATUS		mandatory
DESCRIPTION	"The description of an NBP service registered on this
		entity."
::= { nbpTable 1 }

    NbpEntry ::= SEQUENCE {
	nbpIndex	INTEGER,
	nbpObject	OCTET STRING,
	nbpType		OCTET STRING,
	nbpZone		OCTET STRING
}

nbpIndex OBJECT-TYPE
SYNTAX		INTEGER
ACCESS		read-only
STATUS		mandatory
DESCRIPTION	"The index of this NBP entry; this value ranges from
		1 to the number of NBP entries registered on this
		entity."
::= { nbpEntry 1 }

nbpObject OBJECT-TYPE
SYNTAX		OCTET STRING
ACCESS		read-write
STATUS		mandatory
DESCRIPTION	"The name of the service described by this entity."
::= { nbpEntry 2 }

nbpType OBJECT-TYPE
SYNTAX		OCTET STRING
ACCESS		read-write
STATUS		mandatory
DESCRIPTION	"The type of the service described by this entity."
::= { nbpEntry 3 }

nbpZone OBJECT-TYPE
SYNTAX		OCTET STRING
ACCESS		read-write
STATUS		mandatory
DESCRIPTION	"The zone the service described by this entity is
		registered in."
::= { nbpEntry 4 }


-- The Echo Group

echoRequests OBJECT-TYPE
SYNTAX		Counter
ACCESS		read-only
STATUS		mandatory
DESCRIPTION	"The number of echo requests received."
::= { caymanEcho 1 }

echoReplies OBJECT-TYPE
SYNTAX		Counter
ACCESS		read-only
STATUS		mandatory
DESCRIPTION	"The number of echo replies sent."
::= { caymanEcho 2 }


-- The Buffer Group

caybufferSize OBJECT-TYPE
SYNTAX		INTEGER
ACCESS		read-only
STATUS		mandatory
DESCRIPTION	"The size of a buffer including the header."
::= { buffer 1 }

caybufferAvail OBJECT-TYPE
SYNTAX		INTEGER
ACCESS		read-only
STATUS		mandatory
DESCRIPTION	"The total number of buffers initialized."
::= { buffer 2 }

caybufferDrops OBJECT-TYPE
SYNTAX		Counter
ACCESS		read-only
STATUS		mandatory
DESCRIPTION	"The total number of requests for a buffer that were
		denied."
::= { buffer 3 }

caybufferTypeTable OBJECT-TYPE
SYNTAX		SEQUENCE OF CaybufferTypeEntry
ACCESS		read-only
STATUS		mandatory
DESCRIPTION	"The information about each buffer type."
::= { buffer 4 }

caybufferTypeEntry OBJECT-TYPE
SYNTAX		CaybufferTypeEntry
ACCESS		read-only
STATUS		mandatory
DESCRIPTION	"The information about a buffer of this type."
::= { caybufferTypeTable 1 }

 CaybufferTypeEntry ::=
	 SEQUENCE {
	caybufferTypeIndex	INTEGER,
	caybufferType	INTEGER,
	caybufferTypeDescr	OCTET STRING,
	caybufferTypeCount	INTEGER
}

caybufferTypeIndex OBJECT-TYPE
SYNTAX		INTEGER
ACCESS		read-only
STATUS		mandatory
DESCRIPTION	"The internal index of this type of buffer; This
		value ranges from 1 to the total number of buffer
		types defined on this entity."
::= { caybufferTypeEntry 1 }

caybufferType OBJECT-TYPE
SYNTAX		INTEGER {
			other(1),
			free(2),
			localtalk(3),
			ethernet(4),
			arp(5),
			data(6),		  -- general data
			erbf(7),		  -- ethernet receive
			etbf(8),		  -- ethernet transmit complete
			malloc(9),
			tkbf(10),		  -- token ring receive packet
			token(11)		  -- token ring packet
		}
ACCESS		read-only
STATUS		mandatory
DESCRIPTION	"The type of this type of buffer."
::= { caybufferTypeEntry 2 }

caybufferTypeDescr OBJECT-TYPE
SYNTAX		OCTET STRING
ACCESS		read-only
STATUS		mandatory
DESCRIPTION	"A printable ASCII text description of this type of buffer."
::= { caybufferTypeEntry 3 }

caybufferTypeCount OBJECT-TYPE
SYNTAX		INTEGER
ACCESS		read-only
STATUS		mandatory
DESCRIPTION	"The number of buffers of this type currently allocated."
::= { caybufferTypeEntry 4 }

END
