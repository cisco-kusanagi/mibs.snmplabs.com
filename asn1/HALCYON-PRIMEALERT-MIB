HALCYON-PRIMEALERT-MIB DEFINITIONS ::= BEGIN

--
--   File:    HALEventTrap.mib
--   Author:  Halcyon Monitoring Solutions, Inc.
--   Version: $Revision: 1.2 $ $Date: 2002/11/19 20:25:35 $ 
--
--   Copyright (c) 1993-2001 Halcyon Inc.
--

--  This MIB text file contains the information sent by
--  the event trap scripts.

IMPORTS
    OBJECT-TYPE, NOTIFICATION-TYPE, MODULE-IDENTITY,
    Integer32, enterprises
        FROM SNMPv2-SMI
    TAddress,
    DisplayString
        FROM SNMPv2-TC;

primealert MODULE-IDENTITY
    LAST-UPDATED "0211191502Z"
    ORGANIZATION "Halcyon Monitoring Solutions Inc."
    CONTACT-INFO
        "        Halcyon Customer Support
         Postal: 2300 Yonge Street
                 Suite 1900, Box 2419
                 Toronto, ON
                 M4P 1E4
                 CANADA
          Phone: (416) 932-4647
            Fax: (416) 932-4711
          Email: info@HalcyonInc.com"
    DESCRIPTION
        "The core Halcyon PrimeAlert v6 MIB"
  ::= { enterprises halcyon(1242) 1 }


traps OBJECT IDENTIFIER ::= { primealert 0 }
base OBJECT IDENTIFIER ::= { primealert 1 }
trapInfo OBJECT IDENTIFIER ::= { base 3 }

eventOpenTrap NOTIFICATION-TYPE
    OBJECTS { eventHost, eventPort, eventModule, eventContext, eventSeverity, eventMessage, eventUrl, eventOpenTime, eventCloseTime }
    STATUS  current
    DESCRIPTION
        "An open event is sent whenever an alarm condition opens on an agent."
    ::= { traps 9 }

eventCloseTrap NOTIFICATION-TYPE
    OBJECTS { eventHost, eventPort, eventModule, eventContext, eventSeverity, eventMessage, eventUrl, eventOpenTime, eventCloseTime }
    STATUS  current
    DESCRIPTION
        "A close event is sent whenever an alarm condition closes on an agent."
    ::= { traps 10 }

eventLogTrap NOTIFICATION-TYPE
    OBJECTS { eventHost, eventPort, eventModule, eventContext, eventSeverity, eventMessage, eventUrl, eventOpenTime, eventCloseTime }
    STATUS  current
    DESCRIPTION
        "A log event is sent whenever an alarm condition is detected on an agent
         and it is considered closed instantaneously (e.g. when fault conditions
         are reported through logging of a message, but the application logs no
         corresponding return-to-normal message, such faults are flagged by a
         log event)"

    ::= { traps 11 }

eventColdstartTrap NOTIFICATION-TYPE
    OBJECTS { eventHost, eventPort, eventModule, eventContext, eventSeverity, eventMessage, eventUrl, eventOpenTime, eventCloseTime }
    STATUS  current
    DESCRIPTION
        "A coldstart trap is sent whenever an agent starts up."
    ::= { traps 12 }

eventAcknowledgeTrap NOTIFICATION-TYPE
    OBJECTS { eventHost, eventPort, eventModule, eventContext, eventSeverity, eventMessage, eventUrl, eventOpenTime, eventCloseTime }
    STATUS  current
    DESCRIPTION
        "An acknowledge trap is sent whenever an event is acknowledged at the agent."
    ::= { traps 13 }

eventUnAcknowledgeTrap NOTIFICATION-TYPE
    OBJECTS { eventHost, eventPort, eventModule, eventContext, eventSeverity, eventMessage, eventUrl, eventOpenTime, eventCloseTime }
    STATUS  current
    DESCRIPTION
        "An unacknowledge trap is sent whenever an event is unacknowledged at the agent."
    ::= { traps 14 }

eventModuleUnavailableTrap NOTIFICATION-TYPE
    OBJECTS { eventHost, eventPort, eventModule, eventContext, eventSeverity, eventMessage, eventUrl, eventOpenTime, eventCloseTime }
    STATUS  current
    DESCRIPTION
        "A module unavailable trap is sent whenever a module becomes unavailable (for example, if it is unloaded) and all open events for that module should be considered closed."
    ::= { traps 15 }


eventHost OBJECT-TYPE
    SYNTAX      DisplayString (SIZE (1..255))
    MAX-ACCESS  accessible-for-notify
    STATUS      current
    DESCRIPTION
        "The hostname of the agent on which the event occurred. This occurs as the first
         trap-specific varbind of an event trap."
    ::= { trapInfo 6 }

eventPort OBJECT-TYPE
    SYNTAX      Integer32
    MAX-ACCESS  accessible-for-notify
    STATUS      current
    DESCRIPTION
        "The SNMP port of the agent on which the event occurred. This occurs as the second
         trap-specific varbind of an event trap."
    ::= { trapInfo 7 } 

eventModule OBJECT-TYPE
    SYNTAX      DisplayString (SIZE (1..64))
    MAX-ACCESS  accessible-for-notify
    STATUS      current
    DESCRIPTION
        "The identifier of the Primealert module in which the event occurred. This occurs as the
         third trap-specific varbind of an event trap."
    ::= { trapInfo 8 }

eventContext OBJECT-TYPE
    SYNTAX      DisplayString (SIZE (0..64))
    MAX-ACCESS  accessible-for-notify
    STATUS      current
    DESCRIPTION
        "The SNMP context of the Primealert module in which the event occurred, for modules which can
         be loaded multiple times in one agent. For modules which can only be loaded once, this
         is empty. This occurs as the fourth trap-specific varbind of an event trap."
    ::= { trapInfo 9 }

eventSeverity OBJECT-TYPE
    SYNTAX      DisplayString (SIZE (1..16))
    MAX-ACCESS  accessible-for-notify
    STATUS      current
    DESCRIPTION
        "A human-readable string representing the severity of the event in question, such as
         'Critical'. This occurs as the fifth trap-specific varbind of an event trap."
    ::= { trapInfo 10 }

eventMessage OBJECT-TYPE
    SYNTAX      DisplayString (SIZE (1..255))
    MAX-ACCESS  accessible-for-notify
    STATUS      current
    DESCRIPTION
        "A human-readable string describing the event. This occurs as the sixth trap-specific
         varbind of an event trap."
    ::= { trapInfo 11 }

eventUrl OBJECT-TYPE
    SYNTAX      DisplayString (SIZE (1..255))
    MAX-ACCESS  accessible-for-notify
    STATUS      current
    DESCRIPTION
        "A url-formatted string representing the MIB location at which the event occurred. It
         can be used to associate a close event with its corresponding open event. This
         occurs as the seventh trap-specific varbind of an event trap."
    ::= { trapInfo 12 }

eventOpenTime OBJECT-TYPE
    SYNTAX      DisplayString (SIZE (1..255))
    MAX-ACCESS  accessible-for-notify
    STATUS      current
    DESCRIPTION
        "A human-readable string containing the time that the event was opened.  Example: Aug 08, 2002 15:34:27.000 GMT.  This occurs as the eighth trap-specific varbind of an event trap"
    ::= { trapInfo 13 }

eventCloseTime OBJECT-TYPE
    SYNTAX      DisplayString (SIZE (1..255))
    MAX-ACCESS  accessible-for-notify
    STATUS      current
    DESCRIPTION
        "A human-readable string containing the time that the event was closed (if applicable).  Example: Aug 08, 2002 15:34:27 .000 GMT.  This occurs as the ninth trap-specific varbind of an event trap"
    ::= { trapInfo 14 }


END
