NETWORK-ALCHEMY-VPN-MIB DEFINITIONS ::= BEGIN

-- Title:		    Network Alchemy VPN MIB
-- Date:		    January 22, 2000
-- Author:		    Jonny Larson (jlarson@network-alchemy.com)
-- Location:		    Santa Cruz, CA

IMPORTS  netalModules, vpn FROM NETAL-SMI
         MODULE-IDENTITY, OBJECT-TYPE, Integer32, IpAddress FROM SNMPv2-SMI
         DisplayString FROM SNMPv2-TC;

-- Information global to all tunnels

networkAlchemyVPNMIB MODULE-IDENTITY
    LAST-UPDATED "200010250000Z"
    ORGANIZATION "Network Alchemy, Inc."
    CONTACT-INFO 
		 "	Network Alchemy
			Customer Support

		  Postal: 1538 Pacific Av.
			Santa Cruz, CA 95060
			USA
	          E-Mail: snmp-contact@network-alchemy.com"

    DESCRIPTION "Virtual Private Network (L2TP and PPTP) MIB module."
    REVISION "200010250000Z"
    DESCRIPTION "Cleanup."
    ::= { netalModules 5 }


vpnL2TPTunnels OBJECT-TYPE
    SYNTAX      Integer32
    MAX-ACCESS  read-only
    STATUS      current
    DESCRIPTION "Number of L2TP tunnels"
    ::= { vpn 1 }

vpnActiveL2TPTunnels OBJECT-TYPE
    SYNTAX      Integer32
    MAX-ACCESS  read-only
    STATUS      current
    DESCRIPTION "Number of Active L2TP Tunnels"
    ::= { vpn 2 }

vpnL2TPSessions OBJECT-TYPE
    SYNTAX      Integer32
    MAX-ACCESS  read-only
    STATUS      current
    DESCRIPTION "Number of L2TP Sessions"
    ::= { vpn 3 }

vpnActiveL2TPSessions OBJECT-TYPE
    SYNTAX      Integer32
    MAX-ACCESS  read-only
    STATUS      current
    DESCRIPTION "Number of Active L2TP Sessions"
    ::= { vpn 4 }

vpnPPTPTS OBJECT-TYPE
    SYNTAX      Integer32
    MAX-ACCESS  read-only
    STATUS      current
    DESCRIPTION "Number of PPTP Tunnel&Sessions.  Number of PPTP tunnels are equal to 
		 the number of PPTP Sessions"
    ::= { vpn 5 }

vpnActivePPTPTS OBJECT-TYPE
    SYNTAX      Integer32
    MAX-ACCESS  read-only
    STATUS      current
    DESCRIPTION "# of Active PPTP Tunnels&Sessions"
    ::= { vpn 6 }

-- The following is the tunnel table.  There can be multiple tunnels.  Each tunnel
-- can have multiple sessions.

vpnTunnelTable OBJECT-TYPE
    SYNTAX	SEQUENCE OF VpnTunnelEntry
    MAX-ACCESS  not-accessible
    STATUS      current
    DESCRIPTION	"A list of tunnels."

    ::= { vpn 7 }

vpnTunnelEntry OBJECT-TYPE
        SYNTAX        VpnTunnelEntry
        MAX-ACCESS    not-accessible
        STATUS        current
        DESCRIPTION   "A table entry containing information about a tunnel."
        INDEX         { vpnTunnelLocalID, vpnTunnelIPAddress }
        ::= { vpnTunnelTable 1 }

VpnTunnelEntry ::= SEQUENCE {
                vpnTunnelLocalID        Integer32,
		vpnTunnelIPAddress	IpAddress,
                vpnTunnelRemoteID       Integer32,
                vpnTunnelType           INTEGER,
                vpnTunnelActive         INTEGER,
		vpnTunnelState		INTEGER
		}

vpnTunnelLocalID OBJECT-TYPE
        SYNTAX        Integer32
        MAX-ACCESS    read-only
        STATUS        current
        DESCRIPTION   "Tunnel local ID."
        ::= { vpnTunnelEntry 1 }

vpnTunnelIPAddress OBJECT-TYPE
        SYNTAX        IpAddress
        MAX-ACCESS    read-only
        STATUS        current
        DESCRIPTION   "Tunnel IP Address."
        ::= { vpnTunnelEntry 2 }

vpnTunnelRemoteID OBJECT-TYPE
        SYNTAX        Integer32
        MAX-ACCESS    read-only
        STATUS        current
        DESCRIPTION   "Tunnel remote ID."
        ::= { vpnTunnelEntry 3 }

vpnTunnelType OBJECT-TYPE
        SYNTAX        INTEGER { any(0), l2tp(1), pptp(2) }
        MAX-ACCESS    read-only
        STATUS        current
        DESCRIPTION   "Tunnel type: ANY=0, L2TP=1, PPTP=2."
        ::= { vpnTunnelEntry 4 }

vpnTunnelActive OBJECT-TYPE
        SYNTAX        INTEGER { inactive(0), active(1) }
        MAX-ACCESS    read-only
        STATUS        current
        DESCRIPTION   "INACTIVE=0, ACTIVE!=0"
        ::= { vpnTunnelEntry 5 }

vpnTunnelState OBJECT-TYPE
        SYNTAX        INTEGER (0..4)
        MAX-ACCESS    read-only
        STATUS        current
        DESCRIPTION   "Tunnel states      
                       For PPTP tunnel type:
                         PPP_STATE_INACTIVE        0  
                         PPP_STATE_SUSPENDED       1 
                         PPP_STATE_ACTIVE          2  
                         
		       For L2TP tunnel type:
                         L2TP_IDLE           0
			 L2TP_WAIT_REPLY     1
			 L2TP_WAIT_CONN      2
			 L2TP_ESTABLISHED    3
			 L2TP_WAIT_FINAL_ACK 4"
        ::= { vpnTunnelEntry 6 }


-- Now, since we can't define a table within a table in SNMP SMI, I'll merely
-- define a second table.  The second table will be the session table, and will
-- be indexed by both the index into the tunnel table, along with the index into
-- the session table for that tunnel.

vpnSessionTable OBJECT-TYPE
    SYNTAX	SEQUENCE OF VpnSessionEntry
    MAX-ACCESS  not-accessible
    STATUS      current
    DESCRIPTION	"A list of sessions for the given tunnel."
    ::= { vpn 8 }

vpnSessionEntry OBJECT-TYPE
        SYNTAX        VpnSessionEntry
        MAX-ACCESS    not-accessible
        STATUS        current
        DESCRIPTION   "A table entry containing information about a session on the given tunnel."
        INDEX         { vpnTunnelLocalID,
			vpnTunnelIPAddress,
			vpnSessionLocalID,
			vpnSessionIPAddress
		      }
        ::= { vpnSessionTable 1 }

VpnSessionEntry ::= SEQUENCE {
                vpnSessionLocalID           Integer32,
                vpnSessionIPAddress         IpAddress,
                vpnSessionRemoteID          Integer32,
                vpnSessionPacketsIn         Integer32,
                vpnSessionPacketsOut        Integer32,
                vpnSessionActive            INTEGER,
                vpnSessionState             INTEGER,
                vpnSessionAuthType          INTEGER,
                vpnSessionSendFlags         Integer32,
                vpnSessionRecvFlags         Integer32,
                vpnSessionUsername          DisplayString,
                vpnSessionLifetimeSeconds   Integer32
		}

vpnSessionLocalID OBJECT-TYPE
        SYNTAX        Integer32
        MAX-ACCESS    read-only
        STATUS        current
        DESCRIPTION   "Session local ID."
        ::= { vpnSessionEntry 1 }

vpnSessionIPAddress OBJECT-TYPE
        SYNTAX        IpAddress
        MAX-ACCESS    read-only
        STATUS        current
        DESCRIPTION   "Session IP Address."
        ::= { vpnSessionEntry 2 }

vpnSessionRemoteID OBJECT-TYPE
        SYNTAX        Integer32
        MAX-ACCESS    read-only
        STATUS        current
        DESCRIPTION   "Session remote ID."
        ::= { vpnSessionEntry 3 }

vpnSessionPacketsIn OBJECT-TYPE
        SYNTAX        Integer32
        MAX-ACCESS    read-only
        STATUS        current
        DESCRIPTION   "Number of input packets."
        ::= { vpnSessionEntry 4 }

vpnSessionPacketsOut OBJECT-TYPE
        SYNTAX        Integer32
        MAX-ACCESS    read-only
        STATUS        current
        DESCRIPTION   "Number of output packets."
        ::= { vpnSessionEntry 5 }

vpnSessionActive OBJECT-TYPE
        SYNTAX        INTEGER { inactive(0), active(1) }
        MAX-ACCESS    read-only
        STATUS        current
        DESCRIPTION   "INACTIVE=0, ACTIVE!=0"
        ::= { vpnSessionEntry 6 }

vpnSessionState OBJECT-TYPE
        SYNTAX        INTEGER { inactive(0), suspended(1), active(2) }
        MAX-ACCESS    read-only
        STATUS        current
        DESCRIPTION   "Session States:
		         PPP_STATE_INACTIVE    0
		         PPP_STATE_SUSPENDED   1
		         PPP_STATE_ACTIVE      2"
        ::= { vpnSessionEntry 7 }

vpnSessionAuthType OBJECT-TYPE
        SYNTAX        INTEGER { none(0), chap(1), mschap(2), pap(3) }
        MAX-ACCESS    read-only
        STATUS        current
        DESCRIPTION   "Authenication type 
			 VPN_AUTHENTICATION_NONE   0
			 VPN_AUTHENTICATION_CHAP   1
			 VPN_AUTHENTICATION_MSCHAP 2
 			 VPN_AUTHENTICATION_PAP    3"
        ::= { vpnSessionEntry 8 }

vpnSessionSendFlags OBJECT-TYPE
        SYNTAX        Integer32
        MAX-ACCESS    read-only
        STATUS        current
        DESCRIPTION   "Send flags

		       MS_MPPC           0x00000001
                       MS_MPPE_LM_40     0x00000020
                       MS_MPPE_128       0x00000040    
                       MS_MPPX_STATELESS 0x01000000
                       
                       MSCCP_ENCRYPTION  (MS_MPPE_LM_40 | MS_MPPE_128)
                       MSCCP_COMPRESSION (MS_MPPC)
                       MSCCP_STATELESS   (MS_MPPX_STATELESS)
                       MSCCP_ALL         (MSCCP_COMPRESSION | 
		       MSCCP_ENCRYPTION | 
		       MSCCP_STATELESS)"

        ::= { vpnSessionEntry 9 }

vpnSessionRecvFlags OBJECT-TYPE
        SYNTAX        Integer32
        MAX-ACCESS    read-only
        STATUS        current
        DESCRIPTION   "Received flags.

		       MS_MPPC           0x00000001
                       MS_MPPE_LM_40     0x00000020
                       MS_MPPE_128       0x00000040    
                       MS_MPPX_STATELESS 0x01000000
                       
                       MSCCP_ENCRYPTION  (MS_MPPE_LM_40 | MS_MPPE_128)
                       MSCCP_COMPRESSION (MS_MPPC)
                       MSCCP_STATELESS   (MS_MPPX_STATELESS)
                       MSCCP_ALL         (MSCCP_COMPRESSION | 
		       MSCCP_ENCRYPTION | 
		       MSCCP_STATELESS)"
        ::= { vpnSessionEntry 10 }

vpnSessionUsername OBJECT-TYPE
        SYNTAX        DisplayString
        MAX-ACCESS    read-only
        STATUS        current
        DESCRIPTION   "Session Username."
        ::= { vpnSessionEntry 11 }

vpnSessionLifetimeSeconds OBJECT-TYPE
        SYNTAX        Integer32
        MAX-ACCESS    read-only
        STATUS        current
        DESCRIPTION   "Number of seconds the session has been active."
        ::= { vpnSessionEntry 12 }


END
