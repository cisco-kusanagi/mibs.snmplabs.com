ExpandAccelerator-MIB DEFINITIONS ::= BEGIN
          
	IMPORTS
               OBJECT-TYPE FROM RFC-1212
					Gauge,
               Counter,
               enterprises
			FROM RFC1155-SMI
			Unsigned32 FROM SNMPv2-SMI;

		   --IfIndex
			--FROM IF-MIB;


		--InterfaceIndex ::= IfIndex

          Enumerator00 ::= INTEGER { down(0), up(1) }
          Enumerator01 ::= INTEGER { ppp(0), hdlc(1), auto(2) }
          Enumerator02 ::= INTEGER { on(0), off(1) }
          Enumerator03 ::= INTEGER { down(0), up(1) }
          Enumerator04 ::= INTEGER { ppp(0), hdlc(1), auto(2) }
          Enumerator05 ::= INTEGER { on(0), off(1), auto(2) }
          Enumerator06 ::= INTEGER { bit-16(0), bit-32(1) }


          -- Expand

          expand              OBJECT IDENTIFIER ::= { enterprises 3405 }

          -- Expand.accelerator

          accelerator         OBJECT IDENTIFIER ::= { expand 1 }

          -- Expand.accelerator.acc4000

          acc4000             OBJECT IDENTIFIER ::= { accelerator 1 }

          -- Expand.accelerator.acc4000.[accelerator-4000-series]

          accelerator-4000-series OBJECT-TYPE
               SYNTAX  Unsigned32
               ACCESS  read-only
               STATUS  mandatory
               DESCRIPTION
                         "Expand Accelerator 4000 series base OID"
               ::= { acc4000 1 }

          -- Expand.accelerator.acc4000.details

          details             OBJECT IDENTIFIER ::= { acc4000 2 }

          detailsInterfaceTable OBJECT-TYPE
               SYNTAX  SEQUENCE OF DetailsInterfaceEntry
               ACCESS  not-accessible
               STATUS  mandatory
               ::= { details 1 }

          detailsInterfaceEntry OBJECT-TYPE
               SYNTAX  DetailsInterfaceEntry
               ACCESS  not-accessible
               STATUS  mandatory
               DESCRIPTION
                         "interface details table"
               INDEX   { interfaceName }
               ::= { detailsInterfaceTable 1 }

          DetailsInterfaceEntry ::=
               SEQUENCE {
                 interfaceName
                    OCTET STRING,
                 interfaceStatus
                    Enumerator00,
                 interfaceCloackRate
                    INTEGER,
                 interfaceQueueMode
                    Enumerator01,
                 interfaceFifoSystemLimits
                    Unsigned32,
                 interfaceFairQueueSystemLimits
                    Unsigned32,
                 interfaceFairQueueSessionLimits
                    Unsigned32,
                 interfaceIgnoreDCD
                    Enumerator02,
                 interfaceBandwidth
                    Unsigned32,
                 interfaceCountersPeriod
                    Unsigned32,
                 interfaceProtocolType
                    Enumerator04,
                 interfaceDCDMode
                    Enumerator05,
                 interfaceCRCMode
                    Enumerator06
               }

          -- Expand.accelerator.acc4000.details.detailsInterface.detailsInterfaceEntry.[interfaceName]

          interfaceName OBJECT-TYPE
               SYNTAX  OCTET STRING
               ACCESS  read-only
               STATUS  mandatory
               DESCRIPTION
                         "interface name"
               ::= { detailsInterfaceEntry 1 }

          -- Expand.accelerator.acc4000.details.detailsInterface.detailsInterfaceEntry.[interfaceStatus]

          interfaceStatus OBJECT-TYPE
               SYNTAX  Enumerator00
               ACCESS  read-only
               STATUS  mandatory
               DESCRIPTION
                         "interface status"
               ::= { detailsInterfaceEntry 2 }

          -- Expand.accelerator.acc4000.details.detailsInterface.detailsInterfaceEntry.[interfaceCloackRate]

          interfaceCloackRate OBJECT-TYPE
               SYNTAX  INTEGER
               ACCESS  read-only
               STATUS  mandatory
               DESCRIPTION
                         "interface clock rate"
               ::= { detailsInterfaceEntry 3 }

          -- Expand.accelerator.acc4000.details.detailsInterface.detailsInterfaceEntry.[interfaceQueueMode]

          interfaceQueueMode OBJECT-TYPE
               SYNTAX  Enumerator01
               ACCESS  read-only
               STATUS  mandatory
               DESCRIPTION
                         "interface queuing mode"
               ::= { detailsInterfaceEntry 4 }

          -- Expand.accelerator.acc4000.details.detailsInterface.detailsInterfaceEntry.[interfaceFifoSystemLimits]

          interfaceFifoSystemLimits OBJECT-TYPE
               SYNTAX  Unsigned32
               ACCESS  read-only
               STATUS  mandatory
               DESCRIPTION
                         "fifo system limits"
               ::= { detailsInterfaceEntry 5 }

          -- Expand.accelerator.acc4000.details.detailsInterface.detailsInterfaceEntry.[interfaceFairQueueSystemLimits]

          interfaceFairQueueSystemLimits OBJECT-TYPE
               SYNTAX  Unsigned32
               ACCESS  read-only
               STATUS  mandatory
               DESCRIPTION
                         "fair queuing system limits"
               ::= { detailsInterfaceEntry 6 }

          -- Expand.accelerator.acc4000.details.detailsInterface.detailsInterfaceEntry.[interfaceFairQueueSessionLimits]

          interfaceFairQueueSessionLimits OBJECT-TYPE
               SYNTAX  Unsigned32
               ACCESS  read-only
               STATUS  mandatory
               DESCRIPTION
                         "fair queuing session limits"
               ::= { detailsInterfaceEntry 7 }

          -- Expand.accelerator.acc4000.details.detailsInterface.detailsInterfaceEntry.[interfaceIgnoreDCD]

          interfaceIgnoreDCD OBJECT-TYPE
               SYNTAX  Enumerator02
               ACCESS  read-only
               STATUS  mandatory
               DESCRIPTION
                         "ignore dcd"
               ::= { detailsInterfaceEntry 8 }

          -- Expand.accelerator.acc4000.details.detailsInterface.detailsInterfaceEntry.[interfaceBandwidth]

          interfaceBandwidth OBJECT-TYPE
               SYNTAX  Unsigned32
               ACCESS  read-only
               STATUS  mandatory
               DESCRIPTION
                         "bandwidth"
               ::= { detailsInterfaceEntry 9 }

          -- Expand.accelerator.acc4000.details.detailsInterface.detailsInterfaceEntry.[interfaceCountersPeriod]

          interfaceCountersPeriod OBJECT-TYPE
               SYNTAX  Unsigned32
               ACCESS  read-only
               STATUS  mandatory
               DESCRIPTION
                         "period over which data is avaraged"
               ::= { detailsInterfaceEntry 10 }

          -- Expand.accelerator.acc4000.details.detailsInterface.detailsInterfaceEntry.[interfaceProtocolType]

          interfaceProtocolType OBJECT-TYPE
               SYNTAX  Enumerator04
               ACCESS  read-only
               STATUS  mandatory
               DESCRIPTION
                         "interface encapsulation protocol type"
               ::= { detailsInterfaceEntry 11 }

          -- Expand.accelerator.acc4000.details.detailsInterface.detailsInterfaceEntry.[interfaceDCDMode]

          interfaceDCDMode OBJECT-TYPE
               SYNTAX  Enumerator05
               ACCESS  read-only
               STATUS  mandatory
               DESCRIPTION
                         "dcd mode"
               ::= { detailsInterfaceEntry 12 }

          -- Expand.accelerator.acc4000.details.detailsInterface.detailsInterfaceEntry.[interfaceCRCMode]

          interfaceCRCMode OBJECT-TYPE
               SYNTAX  Enumerator06
               ACCESS  read-only
               STATUS  mandatory
               DESCRIPTION
                         "crc mode"
               ::= { detailsInterfaceEntry 13 }

          -- Expand.accelerator.acc4000.statistics

          statistics          OBJECT IDENTIFIER ::= { acc4000 3 }

          statInterfaceTable OBJECT-TYPE
               SYNTAX  SEQUENCE OF StatInterfaceEntry
               ACCESS  not-accessible
               STATUS  mandatory
               ::= { statistics 1 }

          statInterfaceEntry OBJECT-TYPE
               SYNTAX  StatInterfaceEntry
               ACCESS  not-accessible
               STATUS  mandatory
               DESCRIPTION
                         "interface statistics table"
               INDEX   { interfaceName }
               ::= { statInterfaceTable 1 }

          StatInterfaceEntry ::=
               SEQUENCE {
                 interfaceName
                    OCTET STRING,
                 systemUpInBytes-Low
                    INTEGER,
                 systemUpInBytes-High
                    INTEGER,
                 systemUpInBytes-String
                    OCTET STRING,
                 systemUpInPackets-Low
                    INTEGER,
                 systemUpInPackets-High
                    INTEGER,
                 systemUpInPackets-String
                    OCTET STRING,
                 systemUpOutBytes-Low
                    INTEGER,
                 systemUpOutBytes-High
                    INTEGER,
                 systemUpOutBytes-String
                    OCTET STRING,
                 systemUpOutPackets-Low
                    INTEGER,
                 systemUpOutPackets-High
                    INTEGER,
                 systemUpOutPackets-String
                    OCTET STRING,
                 systemUpDroppedBytes-Low
                    INTEGER,
                 systemUpDroppedBytes-High
                    INTEGER,
                 systemUpDroppedBytes-String
                    OCTET STRING,
                 systemUpDroppedPackets-Low
                    INTEGER,
                 systemUpDroppedPackets-High
                    INTEGER,
                 systemUpDroppedPackets-String
                    OCTET STRING,
                 systemUpOverrunPackets-Low
                    INTEGER,
                 systemUpOverrunPackets-High
                    INTEGER,
                 systemUpOverrunPackets-String
                    OCTET STRING,
                 systemUpCrcErrors-Low
                    INTEGER,
                 systemUpCrcErrors-High
                    INTEGER,
                 systemUpCrcErrors-String
                    OCTET STRING,
                 clearCountersInBytes-Low
                    INTEGER,
                 clearCountersInBytes-High
                    INTEGER,
                 clearCountersInBytes-String
                    OCTET STRING,
                 clearCountersInPackets-Low
                    INTEGER,
                 clearCountersInPackets-High
                    INTEGER,
                 clearCountersInPackets-String
                    OCTET STRING,
                 clearCountersOutBytes-Low
                    INTEGER,
                 clearCountersOutBytes-High
                    INTEGER,
                 clearCountersOutBytes-String
                    OCTET STRING,
                 clearCountersOutPackets-Low
                    INTEGER,
                 clearCountersOutPackets-High
                    INTEGER,
                 clearCountersOutPackets-String
                    OCTET STRING,
                 clearCountersDroppedBytes-Low
                    INTEGER,
                 clearCountersDroppedBytes-High
                    INTEGER,
                 clearCountersDroppedBytes-String
                    OCTET STRING,
                 clearCountersDroppedPackets-Low
                    INTEGER,
                 clearCountersDroppedPackets-High
                    INTEGER,
                 clearCountersDroppedPackets-String
                    OCTET STRING,
                 clearCountersOverrunPackets-Low
                    INTEGER,
                 clearCountersOverrunPackets-High
                    INTEGER,
                 clearCountersOverrunPackets-String
                    OCTET STRING,
                 clearCountersCrcErrors-Low
                    INTEGER,
                 clearCountersCrcErrors-High
                    INTEGER,
                 clearCountersCrcErrors-String
                    OCTET STRING,
                 countersPeriodBytesInPerSec
                    Unsigned32,
                 countersPeriodPacketsInPerSec
                    Unsigned32,
                 countersPeriodBytesOutPerSec
                    Unsigned32,
                 countersPeriodPacketsOutPerSec
                    Unsigned32,
                 countersPeriodDroppedBytes
                    Unsigned32,
                 countersPeriodDroppedPackets
                    Unsigned32,
                 countersPeriodOverrunPackets
                    Unsigned32,
                 countersPeriodCrcErrors
                    Unsigned32
               }

          -- Expand.accelerator.acc4000.statistics.statInterface.statInterfaceEntry.[interfaceName]

          interfaceName2 OBJECT-TYPE
               SYNTAX  OCTET STRING
               ACCESS  read-only
               STATUS  mandatory
               DESCRIPTION
                         "interface name"
               ::= { statInterfaceEntry 1 }

          -- Expand.accelerator.acc4000.statistics.statInterface.statInterfaceEntry.[systemUpInBytes-Low]

          systemUpInBytes-Low OBJECT-TYPE
               SYNTAX  Unsigned32
               ACCESS  read-only
               STATUS  mandatory
               DESCRIPTION
                         "bytes in since system up low 32-bit"
               ::= { statInterfaceEntry 2 }

          -- Expand.accelerator.acc4000.statistics.statInterface.statInterfaceEntry.[systemUpInBytes-High]

          systemUpInBytes-High OBJECT-TYPE
               SYNTAX  Unsigned32
               ACCESS  read-only
               STATUS  mandatory
               DESCRIPTION
                         "bytes in since system up high 32-bit"
               ::= { statInterfaceEntry 3 }

          -- Expand.accelerator.acc4000.statistics.statInterface.statInterfaceEntry.[systemUpInBytes-String]

          systemUpInBytes-String OBJECT-TYPE
               SYNTAX  OCTET STRING
               ACCESS  read-write
               STATUS  mandatory
               DESCRIPTION
                         "bytes in since system up string representation"
               ::= { statInterfaceEntry 4 }

          -- Expand.accelerator.acc4000.statistics.statInterface.statInterfaceEntry.[systemUpInPackets-Low]

          systemUpInPackets-Low OBJECT-TYPE
               SYNTAX  Unsigned32
               ACCESS  read-only
               STATUS  mandatory
               DESCRIPTION
                         "packets in since system up low 32-bit"
               ::= { statInterfaceEntry 5 }

          -- Expand.accelerator.acc4000.statistics.statInterface.statInterfaceEntry.[systemUpInPackets-High]

          systemUpInPackets-High OBJECT-TYPE
               SYNTAX  Unsigned32
               ACCESS  read-only
               STATUS  mandatory
               DESCRIPTION
                         "packets in since system up high 32-bit"
               ::= { statInterfaceEntry 6 }

          -- Expand.accelerator.acc4000.statistics.statInterface.statInterfaceEntry.[systemUpInPackets-String]

          systemUpInPackets-String OBJECT-TYPE
               SYNTAX  OCTET STRING
               ACCESS  read-write
               STATUS  mandatory
               DESCRIPTION
                         "packets in since system up string representation"
               ::= { statInterfaceEntry 7 }

          -- Expand.accelerator.acc4000.statistics.statInterface.statInterfaceEntry.[systemUpOutBytes-Low]

          systemUpOutBytes-Low OBJECT-TYPE
               SYNTAX  Unsigned32
               ACCESS  read-only
               STATUS  mandatory
               DESCRIPTION
                         "bytes out since system up low 32-bit"
               ::= { statInterfaceEntry 8 }

          -- Expand.accelerator.acc4000.statistics.statInterface.statInterfaceEntry.[systemUpOutBytes-High]

          systemUpOutBytes-High OBJECT-TYPE
               SYNTAX  Unsigned32
               ACCESS  read-only
               STATUS  mandatory
               DESCRIPTION
                         "bytes out since system up high 32-bit"
               ::= { statInterfaceEntry 9 }

          -- Expand.accelerator.acc4000.statistics.statInterface.statInterfaceEntry.[systemUpOutBytes-String]

          systemUpOutBytes-String OBJECT-TYPE
               SYNTAX  OCTET STRING
               ACCESS  read-write
               STATUS  mandatory
               DESCRIPTION
                         "bytes out since system up string representation"
               ::= { statInterfaceEntry 10 }

          -- Expand.accelerator.acc4000.statistics.statInterface.statInterfaceEntry.[systemUpOutPackets-Low]

          systemUpOutPackets-Low OBJECT-TYPE
               SYNTAX  Unsigned32
               ACCESS  read-only
               STATUS  mandatory
               DESCRIPTION
                         "packets out since system up low 32-bit"
               ::= { statInterfaceEntry 11 }

          -- Expand.accelerator.acc4000.statistics.statInterface.statInterfaceEntry.[systemUpOutPackets-High]

          systemUpOutPackets-High OBJECT-TYPE
               SYNTAX  Unsigned32
               ACCESS  read-only
               STATUS  mandatory
               DESCRIPTION
                         "packets out since system up high 32-bit"
               ::= { statInterfaceEntry 12 }

          -- Expand.accelerator.acc4000.statistics.statInterface.statInterfaceEntry.[systemUpOutPackets-String]

          systemUpOutPackets-String OBJECT-TYPE
               SYNTAX  OCTET STRING
               ACCESS  read-write
               STATUS  mandatory
               DESCRIPTION
                         "packets out since system up string representation"
               ::= { statInterfaceEntry 13 }

          -- Expand.accelerator.acc4000.statistics.statInterface.statInterfaceEntry.[systemUpDroppedBytes-Low]

          systemUpDroppedBytes-Low OBJECT-TYPE
               SYNTAX  Unsigned32
               ACCESS  read-only
               STATUS  mandatory
               DESCRIPTION
                         "bytes overrun since system up low 32-bit"
               ::= { statInterfaceEntry 14 }

          -- Expand.accelerator.acc4000.statistics.statInterface.statInterfaceEntry.[systemUpDroppedBytes-High]

          systemUpDroppedBytes-High OBJECT-TYPE
               SYNTAX  Unsigned32
               ACCESS  read-only
               STATUS  mandatory
               DESCRIPTION
                         "bytes overrun since system up high 32-bit"
               ::= { statInterfaceEntry 15 }

          -- Expand.accelerator.acc4000.statistics.statInterface.statInterfaceEntry.[systemUpDroppedBytes-String]

          systemUpDroppedBytes-String OBJECT-TYPE
               SYNTAX  OCTET STRING
               ACCESS  read-write
               STATUS  mandatory
               DESCRIPTION
                         "bytes overrun since system up string representation"
               ::= { statInterfaceEntry 16 }

          -- Expand.accelerator.acc4000.statistics.statInterface.statInterfaceEntry.[systemUpDroppedPackets-Low]

          systemUpDroppedPackets-Low OBJECT-TYPE
               SYNTAX  Unsigned32
               ACCESS  read-only
               STATUS  mandatory
               DESCRIPTION
                         "packets dropped since system up low 32-bit"
               ::= { statInterfaceEntry 17 }

          -- Expand.accelerator.acc4000.statistics.statInterface.statInterfaceEntry.[systemUpDroppedPackets-High]

          systemUpDroppedPackets-High OBJECT-TYPE
               SYNTAX  Unsigned32
               ACCESS  read-only
               STATUS  mandatory
               DESCRIPTION
                         "packets dropped since system up high 32-bit"
               ::= { statInterfaceEntry 18 }

          -- Expand.accelerator.acc4000.statistics.statInterface.statInterfaceEntry.[systemUpDroppedPackets-String]

          systemUpDroppedPackets-String OBJECT-TYPE
               SYNTAX  OCTET STRING
               ACCESS  read-write
               STATUS  mandatory
               DESCRIPTION
                         "packets dropped since system up string representation"
               ::= { statInterfaceEntry 19 }

          -- Expand.accelerator.acc4000.statistics.statInterface.statInterfaceEntry.[systemUpOverrunPackets-Low]

          systemUpOverrunPackets-Low OBJECT-TYPE
               SYNTAX  Unsigned32
               ACCESS  read-only
               STATUS  mandatory
               DESCRIPTION
                         "packets overrun since system up low 32-bit"
               ::= { statInterfaceEntry 20 }

          -- Expand.accelerator.acc4000.statistics.statInterface.statInterfaceEntry.[systemUpOverrunPackets-High]

          systemUpOverrunPackets-High OBJECT-TYPE
               SYNTAX  Unsigned32
               ACCESS  read-only
               STATUS  mandatory
               DESCRIPTION
                         "packets overrun since system up high 32-bit"
               ::= { statInterfaceEntry 21 }

          -- Expand.accelerator.acc4000.statistics.statInterface.statInterfaceEntry.[systemUpOverrunPackets-String]

          systemUpOverrunPackets-String OBJECT-TYPE
               SYNTAX  OCTET STRING
               ACCESS  read-write
               STATUS  mandatory
               DESCRIPTION
                         "packets overrun since system up string representation"
               ::= { statInterfaceEntry 22 }

          -- Expand.accelerator.acc4000.statistics.statInterface.statInterfaceEntry.[systemUpCrcErrors-Low]

          systemUpCrcErrors-Low OBJECT-TYPE
               SYNTAX  Unsigned32
               ACCESS  read-only
               STATUS  mandatory
               DESCRIPTION
                         "crc errors since system up low 32-bit"
               ::= { statInterfaceEntry 23 }

          -- Expand.accelerator.acc4000.statistics.statInterface.statInterfaceEntry.[systemUpCrcErrors-High]

          systemUpCrcErrors-High OBJECT-TYPE
               SYNTAX  Unsigned32
               ACCESS  read-only
               STATUS  mandatory
               DESCRIPTION
                         "crc errors since system up high 32-bit"
               ::= { statInterfaceEntry 24 }

          -- Expand.accelerator.acc4000.statistics.statInterface.statInterfaceEntry.[systemUpCrcErrors-String]

          systemUpCrcErrors-String OBJECT-TYPE
               SYNTAX  OCTET STRING
               ACCESS  read-write
               STATUS  mandatory
               DESCRIPTION
                         "crc errors since system up string representation"
               ::= { statInterfaceEntry 25 }

          -- Expand.accelerator.acc4000.statistics.statInterface.statInterfaceEntry.[clearCountersInBytes-Low]

          clearCountersInBytes-Low OBJECT-TYPE
               SYNTAX  Unsigned32
               ACCESS  read-only
               STATUS  mandatory
               DESCRIPTION
                         "bytes in since clear counters low 32-bit"
               ::= { statInterfaceEntry 26 }

          -- Expand.accelerator.acc4000.statistics.statInterface.statInterfaceEntry.[clearCountersInBytes-High]

          clearCountersInBytes-High OBJECT-TYPE
               SYNTAX  Unsigned32
               ACCESS  read-only
               STATUS  mandatory
               DESCRIPTION
                         "bytes in since clear counters high 32-bit"
               ::= { statInterfaceEntry 27 }

          -- Expand.accelerator.acc4000.statistics.statInterface.statInterfaceEntry.[clearCountersInBytes-String]

          clearCountersInBytes-String OBJECT-TYPE
               SYNTAX  OCTET STRING
               ACCESS  read-write
               STATUS  mandatory
               DESCRIPTION
                         "bytes in since clear counters string representation"
               ::= { statInterfaceEntry 28 }

          -- Expand.accelerator.acc4000.statistics.statInterface.statInterfaceEntry.[clearCountersInPackets-Low]

          clearCountersInPackets-Low OBJECT-TYPE
               SYNTAX  Unsigned32
               ACCESS  read-only
               STATUS  mandatory
               DESCRIPTION
                         "packets in since clear counters low 32-bit"
               ::= { statInterfaceEntry 29 }

          -- Expand.accelerator.acc4000.statistics.statInterface.statInterfaceEntry.[clearCountersInPackets-High]

          clearCountersInPackets-High OBJECT-TYPE
               SYNTAX  Unsigned32
               ACCESS  read-only
               STATUS  mandatory
               DESCRIPTION
                         "packets in since clear counters high 32-bit"
               ::= { statInterfaceEntry 30 }

          -- Expand.accelerator.acc4000.statistics.statInterface.statInterfaceEntry.[clearCountersInPackets-String]

          clearCountersInPackets-String OBJECT-TYPE
               SYNTAX  OCTET STRING
               ACCESS  read-write
               STATUS  mandatory
               DESCRIPTION
                         "packets in since clear counters string representation"
               ::= { statInterfaceEntry 31 }

          -- Expand.accelerator.acc4000.statistics.statInterface.statInterfaceEntry.[clearCountersOutBytes-Low]

          clearCountersOutBytes-Low OBJECT-TYPE
               SYNTAX  Unsigned32
               ACCESS  read-only
               STATUS  mandatory
               DESCRIPTION
                         "bytes out since clear counters low 32-bit"
               ::= { statInterfaceEntry 32 }

          -- Expand.accelerator.acc4000.statistics.statInterface.statInterfaceEntry.[clearCountersOutBytes-High]

          clearCountersOutBytes-High OBJECT-TYPE
               SYNTAX  Unsigned32
               ACCESS  read-only
               STATUS  mandatory
               DESCRIPTION
                         "bytes out since clear counters high 32-bit"
               ::= { statInterfaceEntry 33 }

          -- Expand.accelerator.acc4000.statistics.statInterface.statInterfaceEntry.[clearCountersOutBytes-String]

          clearCountersOutBytes-String OBJECT-TYPE
               SYNTAX  OCTET STRING
               ACCESS  read-write
               STATUS  mandatory
               DESCRIPTION
                         "bytes out since clear counters string representation"
               ::= { statInterfaceEntry 34 }

          -- Expand.accelerator.acc4000.statistics.statInterface.statInterfaceEntry.[clearCountersOutPackets-Low]

          clearCountersOutPackets-Low OBJECT-TYPE
               SYNTAX  Unsigned32
               ACCESS  read-only
               STATUS  mandatory
               DESCRIPTION
                         "packets out since clear counters low 32-bit"
               ::= { statInterfaceEntry 35 }

          -- Expand.accelerator.acc4000.statistics.statInterface.statInterfaceEntry.[clearCountersOutPackets-High]

          clearCountersOutPackets-High OBJECT-TYPE
               SYNTAX  Unsigned32
               ACCESS  read-only
               STATUS  mandatory
               DESCRIPTION
                         "packets out since clear counters high 32-bit"
               ::= { statInterfaceEntry 36 }

          -- Expand.accelerator.acc4000.statistics.statInterface.statInterfaceEntry.[clearCountersOutPackets-String]

          clearCountersOutPackets-String OBJECT-TYPE
               SYNTAX  OCTET STRING
               ACCESS  read-write
               STATUS  mandatory
               DESCRIPTION
                         "packets out since clear counters string representation"
               ::= { statInterfaceEntry 37 }

          -- Expand.accelerator.acc4000.statistics.statInterface.statInterfaceEntry.[clearCountersDroppedBytes-Low]

          clearCountersDroppedBytes-Low OBJECT-TYPE
               SYNTAX  Unsigned32
               ACCESS  read-only
               STATUS  mandatory
               DESCRIPTION
                         "bytes dropped since clear counters low 32-bit"
               ::= { statInterfaceEntry 38 }

          -- Expand.accelerator.acc4000.statistics.statInterface.statInterfaceEntry.[clearCountersDroppedBytes-High]

          clearCountersDroppedBytes-High OBJECT-TYPE
               SYNTAX  Unsigned32
               ACCESS  read-only
               STATUS  mandatory
               DESCRIPTION
                         "bytes dropped since clear counters high 32-bit"
               ::= { statInterfaceEntry 39 }

          -- Expand.accelerator.acc4000.statistics.statInterface.statInterfaceEntry.[clearCountersDroppedBytes-String]

          clearCountersDroppedBytes-String OBJECT-TYPE
               SYNTAX  OCTET STRING
               ACCESS  read-write
               STATUS  mandatory
               DESCRIPTION
                         "bytes dropped since clear counters string representation"
               ::= { statInterfaceEntry 40 }

          -- Expand.accelerator.acc4000.statistics.statInterface.statInterfaceEntry.[clearCountersDroppedPackets-Low]

          clearCountersDroppedPackets-Low OBJECT-TYPE
               SYNTAX  Unsigned32
               ACCESS  read-only
               STATUS  mandatory
               DESCRIPTION
                         "packets dropped since clear counters low 32-bit"
               ::= { statInterfaceEntry 41 }

          -- Expand.accelerator.acc4000.statistics.statInterface.statInterfaceEntry.[clearCountersDroppedPackets-High]

          clearCountersDroppedPackets-High OBJECT-TYPE
               SYNTAX  Unsigned32
               ACCESS  read-only
               STATUS  mandatory
               DESCRIPTION
                         "packets dropped since clear counters high 32-bit"
               ::= { statInterfaceEntry 42 }

          -- Expand.accelerator.acc4000.statistics.statInterface.statInterfaceEntry.[clearCountersDroppedPackets-String]

          clearCountersDroppedPackets-String OBJECT-TYPE
               SYNTAX  OCTET STRING
               ACCESS  read-write
               STATUS  mandatory
               DESCRIPTION
                         "packets dropped since clear counters string representation"
               ::= { statInterfaceEntry 43 }

          -- Expand.accelerator.acc4000.statistics.statInterface.statInterfaceEntry.[clearCountersOverrunPackets-Low]

          clearCountersOverrunPackets-Low OBJECT-TYPE
               SYNTAX  Unsigned32
               ACCESS  read-only
               STATUS  mandatory
               DESCRIPTION
                         "packets overrun  since clear counters low 32-bit"
               ::= { statInterfaceEntry 44 }

          -- Expand.accelerator.acc4000.statistics.statInterface.statInterfaceEntry.[clearCountersOverrunPackets-High]

          clearCountersOverrunPackets-High OBJECT-TYPE
               SYNTAX  Unsigned32
               ACCESS  read-only
               STATUS  mandatory
               DESCRIPTION
                         "packets overrun  since clear counters high 32-bit"
               ::= { statInterfaceEntry 45 }

          -- Expand.accelerator.acc4000.statistics.statInterface.statInterfaceEntry.[clearCountersOverrunPackets-String]

          clearCountersOverrunPackets-String OBJECT-TYPE
               SYNTAX  OCTET STRING
               ACCESS  read-write
               STATUS  mandatory
               DESCRIPTION
                         "packets overrun  since clear counters string representation"
               ::= { statInterfaceEntry 46 }

          -- Expand.accelerator.acc4000.statistics.statInterface.statInterfaceEntry.[clearCountersCrcErrors-Low]

          clearCountersCrcErrors-Low OBJECT-TYPE
               SYNTAX  Unsigned32
               ACCESS  read-only
               STATUS  mandatory
               DESCRIPTION
                         "crc error since clear counters low 32-bit"
               ::= { statInterfaceEntry 47 }

          -- Expand.accelerator.acc4000.statistics.statInterface.statInterfaceEntry.[clearCountersCrcErrors-High]

          clearCountersCrcErrors-High OBJECT-TYPE
               SYNTAX  Unsigned32
               ACCESS  read-only
               STATUS  mandatory
               DESCRIPTION
                         "crc error since clear counters high 32-bit"
               ::= { statInterfaceEntry 48 }

          -- Expand.accelerator.acc4000.statistics.statInterface.statInterfaceEntry.[clearCountersCrcErrors-String]

          clearCountersCrcErrors-String OBJECT-TYPE
               SYNTAX  OCTET STRING
               ACCESS  read-write
               STATUS  mandatory
               DESCRIPTION
                         "crc error since clear counters string representation"
               ::= { statInterfaceEntry 49 }

          -- Expand.accelerator.acc4000.statistics.statInterface.statInterfaceEntry.[countersPeriodBytesInPerSec]

          countersPeriodBytesInPerSec OBJECT-TYPE
               SYNTAX  Unsigned32
               ACCESS  read-only
               STATUS  mandatory
               DESCRIPTION
                         "bytes in during countersPeriod"
               ::= { statInterfaceEntry 50 }

          -- Expand.accelerator.acc4000.statistics.statInterface.statInterfaceEntry.[countersPeriodPacketsInPerSec]

          countersPeriodPacketsInPerSec OBJECT-TYPE
               SYNTAX  Unsigned32
               ACCESS  read-only
               STATUS  mandatory
               DESCRIPTION
                         "packets in last countersPeriod"
               ::= { statInterfaceEntry 51 }

          -- Expand.accelerator.acc4000.statistics.statInterface.statInterfaceEntry.[countersPeriodBytesOutPerSec]

          countersPeriodBytesOutPerSec OBJECT-TYPE
               SYNTAX  Unsigned32
               ACCESS  read-only
               STATUS  mandatory
               DESCRIPTION
                         "bytes out last countersPeriod"
               ::= { statInterfaceEntry 52 }

          -- Expand.accelerator.acc4000.statistics.statInterface.statInterfaceEntry.[countersPeriodPacketsOutPerSec]

          countersPeriodPacketsOutPerSec OBJECT-TYPE
               SYNTAX  Unsigned32
               ACCESS  read-only
               STATUS  mandatory
               DESCRIPTION
                         "packets out last countersPeriod"
               ::= { statInterfaceEntry 53 }

          -- Expand.accelerator.acc4000.statistics.statInterface.statInterfaceEntry.[countersPeriodDroppedBytes]

          countersPeriodDroppedBytes OBJECT-TYPE
               SYNTAX  Unsigned32
               ACCESS  read-only
               STATUS  mandatory
               DESCRIPTION
                         "drop bytes last countersPeriod"
               ::= { statInterfaceEntry 54 }

          -- Expand.accelerator.acc4000.statistics.statInterface.statInterfaceEntry.[countersPeriodDroppedPackets]

          countersPeriodDroppedPackets OBJECT-TYPE
               SYNTAX  Unsigned32
               ACCESS  read-only
               STATUS  mandatory
               DESCRIPTION
                         "drop packets last countersPeriod"
               ::= { statInterfaceEntry 55 }

          -- Expand.accelerator.acc4000.statistics.statInterface.statInterfaceEntry.[countersPeriodOverrunPackets]

          countersPeriodOverrunPackets OBJECT-TYPE
               SYNTAX  Unsigned32
               ACCESS  read-only
               STATUS  mandatory
               DESCRIPTION
                         "packets overrun  sine last countersPeriod"
               ::= { statInterfaceEntry 56 }

          -- Expand.accelerator.acc4000.statistics.statInterface.statInterfaceEntry.[countersPeriodCrcErrors]

          countersPeriodCrcErrors OBJECT-TYPE
               SYNTAX  Unsigned32
               ACCESS  read-only
               STATUS  mandatory
               DESCRIPTION
                         "crc error sine last countersPeriod"
               ::= { statInterfaceEntry 57 }

          -- Expand.accelerator.acc4000.acceleration

          acceleration        OBJECT IDENTIFIER ::= { acc4000 4 }

          -- Expand.accelerator.acc4000.acceleration.[accPeriod]

          accPeriod OBJECT-TYPE
               SYNTAX  Unsigned32
               ACCESS  read-only
               STATUS  mandatory
               DESCRIPTION
                         "timed period for acceleration"
               ::= { acceleration 3 }

          -- Expand.accelerator.acc4000.acceleration.local

          local               OBJECT IDENTIFIER ::= { acceleration 1 }

          -- Expand.accelerator.acc4000.acceleration.local.[aclSystemUp]

          aclSystemUp OBJECT-TYPE
               SYNTAX  Unsigned32
               ACCESS  read-only
               STATUS  mandatory
               DESCRIPTION
                         "acceleration since system up"
               ::= { local 1 }

          -- Expand.accelerator.acc4000.acceleration.local.[aclSinceClear]

          aclSinceClear OBJECT-TYPE
               SYNTAX  Unsigned32
               ACCESS  read-only
               STATUS  mandatory
               DESCRIPTION
                         "acceleration since cleared"
               ::= { local 2 }

          -- Expand.accelerator.acc4000.acceleration.local.[aclLastPeriod]

          aclLastPeriod OBJECT-TYPE
               SYNTAX  Unsigned32
               ACCESS  read-only
               STATUS  mandatory
               DESCRIPTION
                         "acceleration for last period of seconds"
               ::= { local 3 }

          -- Expand.accelerator.acc4000.acceleration.remote

          remote              OBJECT IDENTIFIER ::= { acceleration 2 }

          -- Expand.accelerator.acc4000.acceleration.remote.[acrSystemUp]

          acrSystemUp OBJECT-TYPE
               SYNTAX  Unsigned32
               ACCESS  read-only
               STATUS  mandatory
               DESCRIPTION
                         "acceleration since system up"
               ::= { remote 1 }

          -- Expand.accelerator.acc4000.acceleration.remote.[acrSinceClear]

          acrSinceClear OBJECT-TYPE
               SYNTAX  Unsigned32
               ACCESS  read-only
               STATUS  mandatory
               DESCRIPTION
                         "acceleration since cleared"
               ::= { remote 2 }

          -- Expand.accelerator.acc4000.acceleration.remote.[acrLastPeriod]

          acrLastPeriod OBJECT-TYPE
               SYNTAX  Unsigned32
               ACCESS  read-only
               STATUS  mandatory
               DESCRIPTION
                         "acceleration for last period of seconds"
               ::= { remote 3 }



END
