XYLANTRAP-9-MIB DEFINITIONS ::= BEGIN

	--  RCSID information

	--  $RCSfile: xylan-traps.mib,v $
	--  $Revision: 1.22 $            $State: Exp $
	--  $Date: 1998/09/24 18:38:00 $
	--  $Author: burt $


	--  xylan-9slot-trap.mib 
	--  Revision: 1.00
	--  Date: October 21, 1995

	--  Xylan Corporation, Inc.
	--  26679 W. Agoura Road
	--  Calabasas, CA 91302
	--  (818) 880-3500
	--  support@xylan.com

	--  This module provides authoritative definitions for Xylan's
	--  enterprise specific traps.

	--  This module will be extended, as needed.

	--  Xylan Corporation reserves the right to make changes in
	--  specification and oher information contained in this document
	--  without prior notice.  The reader should consult Xylan Corporation
	--  to determine whether any such changes have been made.
	--  Current MIBs are availible from the following URLs:
	--		ftp://ftp.xylan.com/pub/products/mibs
	--		http://www.xylan.com

	--  In no event shall Xylan Corporation be liable for any incidental,
	--  indirect, special, or consequential damages whatsoever (including
	--  but not limited to lost profits) arising out of or related to this
	--  document or the information contained in it, even if Xylan
	--  Corporation has been advised of, known, or should have known, the
	--  possibility of such damages.
 
	--  Xylan grants vendors, end-users, and other interested parties
	--  a non-exclusive license to use this Specification in connection
	--  with the management of Xylan products.
 
	--  Copyright (C) 1995, Xylan Corporation. All Rights Reserved.
 

	IMPORTS
	    xylan, xylanSwitchDevice,
	    omniswitch5, omniswitch9, pizzaSwitch, microSwitch
		FROM XYLAN-BASE-MIB

	    chasControlSlot, chasControlState, chasModuleSlot,
	    chasModuleSubUnit, chasModuleType, chasPowerSupply1State,
	    chasPowerSupply2State, chasModuleOperStatus
		FROM CHASSIS-MIB

	    vBrdgTpFdbAddress, vLanNumber, vLanAdmStatus, 
	    atVLANGroupId, atVLANId, atVLANAdminStatus,
            vDupMacMac, vDupMacSlot, vDupMacIntf, vDupMacTime
		FROM XYLAN-VLAN-MIB

	    vportSlot, vportIF, vportFuncType, vportFuncTypeInstance,
	    vportAdmStatus
		FROM XYLAN-PORT-MIB

	    atmxServiceSlotIndex, atmxServicePortIndex, atmxServiceNumber,
	    atmxServiceAdmStatus, atmxPortSlotIndex, atmxPortPortIndex,
	    atmxVccSlotIndex, atmxVccPortIndex, atmxVccVpi,
	    atmxVccVci, atmxVccAdmStatus, atmxPortEnableILMI
		FROM XYLAN-ATM-MIB

		fddimibSMTIndex, fddimibSMTCFState
		FROM FDDI-SMT73-MIB

            frxVcControlSlotIndex, frxVcControlPortIndex, frxVcControlDlci
                FROM XYLAN-FRAME-RELAY-MIB
            
	    systemEventTrapNumber
		FROM XYLAN-MGMTSTN-MIB

            xylanIpAssocAddr, xylanIpAssocMac,
            xylanIpAssocSlot, xylanIpAssocIntf,
            xylanIpAssocDupMac,  xylanIpAssocDupSlot, xylanIpAssocDupIntf 
                FROM XYLAN-IP-MIB

	    healthThreshDevTrapData,
            healthThreshModTrapCount, 
            healthThreshModTrapData 
                FROM XYLAN-HEALTH-MIB

	    TRAP-TYPE
                FROM RFC-1215;

        --  These definitions use the TRAP-TYPE macro as
        --  defined in RFC 1215 [10]
 
	-- traps for the chassis mgr

	tempAlarm9 TRAP-TYPE
	    ENTERPRISE  omniswitch9
	    DESCRIPTION
		"A tempAlarm indicates a temperature sensor has changed
		its state from underThreshold(4) to overThreshold(3)."
	    ::= 1
	
	moduleChange9 TRAP-TYPE
	    ENTERPRISE  omniswitch9
	    VARIABLES   { chasModuleSlot, chasModuleSubUnit, chasModuleType }
	    DESCRIPTION
		"A moduleChange trap occurs when a module is inserted or
		removed from the chassis."
	    ::= 2

	powerEvent9 TRAP-TYPE
	    ENTERPRISE  omniswitch9
	    VARIABLES   { chasPowerSupply1State, chasPowerSupply2State }
	    DESCRIPTION
		"A powerEvent trap occurs when a power supply is inserted or
		removed from the chassis, or a problem condition is
		recognized on a power supply."
	    ::= 3

	controllerEvent9 TRAP-TYPE
	    ENTERPRISE  omniswitch9
	    VARIABLES   { chasControlSlot, chasControlState }
	    DESCRIPTION
		"A controlEvent trap occurs when a chassis controller (MPM)
		loses or gains the state of master(3).  If this is due to
		chassis controller being inserted or removed from the slot,
		a moduleChange trap will also be sent."
	    ::= 4

	loginViolation9 TRAP-TYPE
	    ENTERPRISE  omniswitch9
	    DESCRIPTION
		"A loginViolation trap occurs when a login attempt fails
		due to an incorrect login-id or password."
	    ::= 5

	macVlanViolation9 TRAP-TYPE
	    ENTERPRISE  omniswitch9
	    VARIABLES   { vBrdgTpFdbAddress }
	    DESCRIPTION
		"A macVlanViolation trap occurs when a frame is received from
		a port with a VLAN ID different from the VLAN where the
		frame previously has received."
	    ::= 6

	macDuplicatePort9 TRAP-TYPE
	    ENTERPRISE  omniswitch9
	    VARIABLES   { vBrdgTpFdbAddress }
	    DESCRIPTION
		"A macDuplicatePort trap occurs when a frame is received from
		a source port different from the port where the frame previously
		has received although they both ports belong to the same VLAN."
	    ::= 7

	portLinkUpEvent9 TRAP-TYPE
	    ENTERPRISE  omniswitch9
	    VARIABLES  { vportSlot, vportIF, vportFuncType,
			 vportFuncTypeInstance }
	    DESCRIPTION
		"A portLinkTrap occurs whenever a phy, log, or virt port
		is enabled."
	    ::= 8

	portLinkDownEvent9 TRAP-TYPE
	    ENTERPRISE  omniswitch9
	    VARIABLES  { vportSlot, vportIF, vportFuncType,
			 vportFuncTypeInstance }
	    DESCRIPTION
		"A portLinkTrap occurs whenever a phy, log, or virt port
		is disabled."
	    ::= 9

	portPartitioned9 TRAP-TYPE
	    ENTERPRISE  omniswitch9
	    VARIABLES  { vportSlot, vportIF, vportFuncType,
			 vportFuncTypeInstance }
	    DESCRIPTION
		"A portPartioned trap occurs when the physical port
		 has transitioned thru enable/disable states faster
		 than 10 times in the past second...indicative of a
		 flakey cable."
	    ::= 10

	portRecordMismatch9 TRAP-TYPE
	    ENTERPRISE  omniswitch9
	    VARIABLES { vportSlot, vportIF, vportFuncType,
			vportFuncTypeInstance }
	    DESCRIPTION
		"A portRecordMismatch trap occurs when the specified
		 port data is found to be diferent than the privious
		 configuration. Typically this will be generated when
		 a NIC of one type is swapped out for a DIFFERENT type.
		 IE ethernet for fddi, atm for token-ring, etc..."
	    ::= 11


	-- group/vlan state changes

	groupChange9 TRAP-TYPE
	    ENTERPRISE  omniswitch9
	    VARIABLES { vLanNumber, vLanAdmStatus }
	    DESCRIPTION
		"A groupChange trap occurs whenever a group is
		 created or deleted from the system via the UI
		 or SNMP. The group and status code are sent as
		 part of the variable binding.

		 The status codes are:
			1 - disable
			2 - enable
			3 - delete
			4 - create
			5 - modify	(see xylan-vport MIB)"
	    ::= 14

	vlanChange9 TRAP-TYPE
	    ENTERPRISE  omniswitch9
	    VARIABLES { atVLANGroupId, atVLANId, atVLANAdminStatus }
	    DESCRIPTION
		"A vlanChange trap occurs whenever a VLAN is
		 created or deleted from the system via the UI
		 or SNMP. The group, vlan and status code are sent as
		 part of the variable binding. See groupChange for
		 the status codes."
	    ::= 15

	portMove9 TRAP-TYPE
	    ENTERPRISE  omniswitch9
	    VARIABLES { vportSlot, vportIF, vportFuncType,
			vportFuncTypeInstance, vportAdmStatus }
	    DESCRIPTION
		"A portMove trap occurs when the specified
		 port is moved from a group/vlan or has had
		 its configuration changed."
	    ::= 16

	moduleResetReload9 TRAP-TYPE
	    ENTERPRISE  omniswitch9
	    VARIABLES { chasModuleSlot, chasModuleSubUnit, chasModuleType,
			chasModuleOperStatus }
	    DESCRIPTION
		"A moduleResetReload trap occurs when the specified
		 module has been reset or reloaded by the chassis mgr."
	    ::= 17

	systemEvent9 TRAP-TYPE
	    ENTERPRISE  omniswitch9
	    VARIABLES { systemEventTrapNumber }
	    DESCRIPTION
		"A systemEvent trap occurs when a potentially
		 fatal system error occurrs. Such as: out of FLASH/
		 memory space. The event type is in the var bind.
		 A Descriptive string MAY be present. The following
		 trap numbers are defined (see xylan-trapc.mib):

			10	Unspecified log event
			11	Log file full
			12	Log file erased

			20	Unspecified memory event
			21	Memory shortage

			30	Unsepcified CPU event
			31	Long term CPU overload
			32	Short term CPU overload

			40	Unspecified ffs event
			41	Attempt to write to full ffs
			42	System/user directed purge
			43	Removed imgs/cfgs
			44	Exec file removed
			45	Config file removed
			46	Exec file updated
			47	Config file updated

			50	Unspecified chassis event
			51	Module failed to init
			52	Module failed to load
			53	Module startup failed
			54	Module failed
			55	Driver failed "
	    ::= 18

	vlanRouteTableFull9 TRAP-TYPE
	    ENTERPRISE  omniswitch9
	    DESCRIPTION
		"A vlanRouteTableFull trap occurs when either the
		 IP or IPX route table is full. (discovered on
		 insertion attempt)"
	    ::= 19

	sapTableFull9 TRAP-TYPE
	    ENTERPRISE  omniswitch9
	    DESCRIPTION
		"A sapTableFull trap occurs when the IPX SAP
		 table is found to be full on insertion."
	    ::= 20

	atmSSCOPstate9 TRAP-TYPE
	    ENTERPRISE  omniswitch9
	    VARIABLES { atmxPortSlotIndex, atmxPortPortIndex }
	    DESCRIPTION
		"A atmSSCOPstate trap occurs when the signalling
		 state for the specified physical port changes."
	    ::= 21

	ilmiState9 TRAP-TYPE
	    ENTERPRISE  omniswitch9
	    VARIABLES { atmxPortSlotIndex, atmxPortPortIndex,
			atmxPortEnableILMI }
	    DESCRIPTION
		"A ilmiState trap occurs when the ILMI state for
		 the specified physical port changes."
	    ::= 22

	atmConnection9 TRAP-TYPE
	    ENTERPRISE  omniswitch9
	    VARIABLES { atmxVccSlotIndex, atmxVccPortIndex, atmxVccVpi,
			atmxVccVci, atmxVccAdmStatus }
	    DESCRIPTION
		"A atmConnection trap occurs when the specified
		 ATM Vcc is created or deleted."
	    ::= 23

	atmService9 TRAP-TYPE
	    ENTERPRISE  omniswitch9
	    VARIABLES { atmxServiceSlotIndex, atmxServicePortIndex,
			atmxServiceNumber, atmxServiceAdmStatus }
	    DESCRIPTION
		"A atmService trap occurs when the specified
		 ATM service is created or deleted>"
	    ::= 24

	dlciNew9 TRAP-TYPE
	    ENTERPRISE  omniswitch9
	    VARIABLES { frxVcControlSlotIndex, frxVcControlPortIndex, frxVcControlDlci}
	    DESCRIPTION
		"Frame-Relay Dlci Just Created"
	    ::= 27

	dlciDel9 TRAP-TYPE
	    ENTERPRISE  omniswitch9
	    VARIABLES { frxVcControlSlotIndex, frxVcControlPortIndex, frxVcControlDlci}
	    DESCRIPTION
		"Frame-Relay Dlci Just Deleted"
	    ::= 28

	dlciUp9 TRAP-TYPE
	    ENTERPRISE  omniswitch9
	    VARIABLES { frxVcControlSlotIndex, frxVcControlPortIndex, frxVcControlDlci}
	    DESCRIPTION
		"Frame-Relay Dlci Just Changed to Active"
	    ::= 29

	dlciDn9 TRAP-TYPE
	    ENTERPRISE  omniswitch9
	    VARIABLES { frxVcControlSlotIndex, frxVcControlPortIndex, frxVcControlDlci}
	    DESCRIPTION
		"Frame-Relay Dlci Just Changed to InActive"
	    ::= 30

	portManualForwardingMode9 TRAP-TYPE
	    ENTERPRISE  omniswitch9
            VARIABLES { vportSlot, vportIF, vportFuncType,
                        vportFuncTypeInstance }
            DESCRIPTION
                "A portManualForwardingMode trap occurs when the specified
                 port is placed into manual mode forwarding as its default
                 setting whenever the port is assigned to a Group that is
                 participating in the IBM spanning tree algorithm."
            ::= 31

	fddiCFStateChange9 TRAP-TYPE
	    ENTERPRISE  omniswitch9
            VARIABLES { fddimibSMTIndex, fddimibSMTCFState }
            DESCRIPTION
                "A fddiCFStateChange trap occurs when the specified
                 fddi physical port changes from wrap configuration state."
            ::= 32

	duplicateIPaddress9 TRAP-TYPE
	    ENTERPRISE  omniswitch9
            VARIABLES { xylanIpAssocAddr, xylanIpAssocMac,
                        xylanIpAssocSlot, xylanIpAssocIntf,
                        xylanIpAssocDupMac,  xylanIpAssocDupSlot, 
                        xylanIpAssocDupIntf }
            DESCRIPTION
                "A duplicateIPaddress trap occurs whenever the switch 
                 detects a duplicate IP address."
            ::= 35

	duplicateMACaddress9 TRAP-TYPE
	    ENTERPRISE  omniswitch9
            VARIABLES { vDupMacMac, vDupMacSlot,
                        vDupMacIntf, vDupMacTime }
            DESCRIPTION
                "A duplicateMACaddress trap occurs whenever the switch
                 detects a duplicate MAC address of one of its own
                 router ports."
            ::= 36

	healthThresholdRising9 TRAP-TYPE
	    ENTERPRISE  omniswitch9
	    DESCRIPTION
		"A healthThresholdRising trap occurs when at least
		 one of the user-specified thresholds is exceeded
		 for the first time."
	    ::= 37

	healthThresholdFalling9 TRAP-TYPE
	    ENTERPRISE  omniswitch9
	    DESCRIPTION
		"A healthThresholdFalling trap occurs when at least
		 one of the user-specified thresholds was exceeded
		 during the previous cycle and none of them are exceeded 
		 this cycle."
	    ::= 38

	healthThresholdDevice9 TRAP-TYPE
	    ENTERPRISE  omniswitch9
            VARIABLES { healthThreshDevTrapData } 
	    DESCRIPTION
		"A healthThresholdDevice trap occurs when at least
		 one device-level threshold crossing is detected."
	    ::= 39

	healthThresholdModule9 TRAP-TYPE
	    ENTERPRISE  omniswitch9
            VARIABLES { healthThreshModTrapCount, 
                        healthThreshModTrapData } 
	    DESCRIPTION
		"A healthThresholdModule trap occurs when at least
		 one module-level threshold crossing is detected."
	    ::= 40

-- Traps 50-59 are reserved for PNNI...

	pnniRouteConflictPort9 TRAP-TYPE
	    ENTERPRISE  omniswitch9
            DESCRIPTION
                "This trap occurs when PNNI detects that a static
                 route on the pnnixIfPortId port has been created
                 and this port has been configured as a PNNI port.

                 This is something that may cause misrouting in a
                 PNNI network if the port turns out to be an Inside
                 port."
            ::= 50


	pnniRouteConflictSamePG9 TRAP-TYPE
	    ENTERPRISE  omniswitch9
            DESCRIPTION
                "This trap occurs when PNNI detects that a static
                 route on the pnnixIfPortId port has been created
                 and this route matches (a prefix of) the Peer
                 Group ID. This is something that may cause
                 misrouting in a PNNI network."
            ::= 51



	END
