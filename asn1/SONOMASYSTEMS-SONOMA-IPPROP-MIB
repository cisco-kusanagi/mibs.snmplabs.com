-- |**********************************************************************|
 -- | Copyright 1998 - Sonoma Systems, Inc. Marina del Rey, CA 90292       |
 -- |    Unpublished software - All rights reserved.                       |
 -- |                                                                      |
 -- | The information in this software is subject to change without notice |
 -- | and should not be construed as a commitment by Sonoma Systems, Inc.  |
 -- |                                                                      |
 -- | Sonoma Systems, Inc. assumes no responsibility for the use or        |
 -- | reliability of its software on equipment which is not supplied by    |
 -- | Sonoma Systems, Inc.                                                 |
 -- |                                                                      |
 -- | This software is furnished under a license and may be copied only    |
 -- | under the terms of that license and with the inclusion of this       |
 -- | notice. This software, or any other copies thereof, may not be       |
 -- | provided or otherwise made available to any other person except to   |
 -- | one who agrees to these license terms. Title to and ownership of the |
 -- | software shall at all times remain with Sonoma Systems, Inc.         |
 -- |**********************************************************************|
 --
 -- Sonoma Systems Inc.,
 -- 4640 Admiralty Way, Suite #600,
 -- Marina Del Rey,
 -- California 90292-6695.
 --
 -- Web : www.sonoma-systems.com
 -- Phone:  310.827.8000
 --
 -- NAME        :  ipmib.def
 -- 
 -- DESCRIPTION :
 --
 -- This is the MIB for the Sonoma Systems proprietary IP objects for the
 -- Sonoma product line.
 --
 -- ARCHIVE : $Archive:   M:\pvcs\pvcsproj\sonoma3\src\mib\ipmib.dev  $
 -- REVISION: $Revision:   1.13  $
 -- AUTHOR  : $Author:   PCaswell  $
 -- DATE    : $Date:   Mar 11 1999 11:41:46  $
 --
     SONOMASYSTEMS-SONOMA-IPPROP-MIB DEFINITIONS ::= BEGIN
 
     IMPORTS
        IpAddress, Counter
        FROM RFC1155-SMI
        OBJECT-TYPE
        FROM RFC-1212
        sonomaRouting
        FROM SONOMASYSTEMS-SONOMA-MIB;

    --
    -- The ipRouting Group
    --
    -- This group augments the MIB-II ip group.
    -- Hierarchy for these groups
    -- enterprises OBJECT IDENTIFIER ::= { private 4 }
    -- sonomaSystems OBJECT IDENTIFIER ::= {  enterprises 2926 }
    -- sonomaSeries OBJECT IDENTIFIER ::= { sonomaSystems 25 }
    -- sonomaRouting OBJECT IDENTIFIER ::= { sonomaSeries 4 }
    ipRouting OBJECT IDENTIFIER ::= { sonomaRouting 1 }
    --

        ipRIPState  OBJECT-TYPE
            SYNTAX  INTEGER {
                        enabled (1),
                        disabled (2)
                    }
            ACCESS  read-write
            STATUS  mandatory
            DESCRIPTION
              "This parameter determines if the RIP routing protocol
            is enabled globally. This parameter is set to DISABLED
            if IP routing is disabled globally."
            ::= { ipRouting 1 }

        ipSecurity  OBJECT-TYPE
            SYNTAX  INTEGER {
                   enabled (1),
                   disabled (2)
                   }
            ACCESS  read-write
            STATUS  mandatory
            DESCRIPTION
                  "This parameter enables or disables the security mechanism."
            ::= { ipRouting 2 }


    --
    -- The ipPortConfigTable
    --

        ipPortConfigTable  OBJECT-TYPE
            SYNTAX  SEQUENCE OF IpPortConfigEntry
            ACCESS  not-accessible
            STATUS  mandatory
            DESCRIPTION
               "This is a table of configurable IP parameters."
            ::= { ipRouting 3 }

        ipPortConfigEntry  OBJECT-TYPE
            SYNTAX  IpPortConfigEntry
            ACCESS  not-accessible
            STATUS  mandatory
            DESCRIPTION
               "This is an entry of the ipPortConfigTable."
            INDEX   { ipPortConfigIndex }
            ::= { ipPortConfigTable 1 }

          IpPortConfigEntry ::= SEQUENCE {
            ipPortConfigIndex
                 INTEGER,
            ipPortForwarding
                 INTEGER,
            ipPortMACEncapsulation
                 INTEGER,
            ipPortDisposition
                 INTEGER,
            ipPortMTU
                 INTEGER,
            ipPortDefaultGateway
		 IpAddress,
            ipPortDefaultGatewayLP
                 INTEGER
            }
  
        ipPortConfigIndex  OBJECT-TYPE
            SYNTAX  INTEGER
            ACCESS  read-only
            STATUS  mandatory
            DESCRIPTION
                    "This is the Logical Port No. to which this Table entry
            pertains."
            ::= { ipPortConfigEntry 1 }

        ipPortForwarding  OBJECT-TYPE
            SYNTAX  INTEGER {
                    enabled (1),
                    disabled (2)
                    }
            ACCESS  read-write
            STATUS  mandatory
            DESCRIPTION
                  "The indication of whether this entity is acting as
            a gateway in respect to the forwarding of datagrams
            received by, but not addressed to, this entity. IP
            gateways forward datagrams. IP hosts do not ( except
            those source-routed via the host.) Even if enabled, this
            port will not forward unless the global ipForwarding flag is
            enabled and at least one IP Address has been configured on 
            the unit."
            ::= { ipPortConfigEntry 2 }

  
        ipPortMACEncapsulation  OBJECT-TYPE
            SYNTAX  INTEGER {
                    noencap       (1),
                    ethernet      (2),
                    ieee8023      (3),
                    tokenRing     (4),
                    tokenRingSnap (5),
                    fddiSnap      (6)
                    }
            ACCESS  read-write
            STATUS  mandatory
            DESCRIPTION
              "This parameter determines the LAN encapsulation used
            when transmitting a datagram on this logical port.
            This parameter is only applicable for logical ports which
            are attached to LAN physical ports. Slip ports have noencap"
            ::= { ipPortConfigEntry 3 }

        ipPortDisposition  OBJECT-TYPE
            SYNTAX  INTEGER {
                    bridge (1),
                    discard (2)
                    }
            ACCESS  read-write
            STATUS  mandatory
            DESCRIPTION
              " This parameter determines the action taken on a received IP
            datagram if routing is disabled for this port, and the
            global routing flag is set to enabled (2). If routing is
            disabled for this port and this object has a value of
            discard (2), than all IP datagrams received on this port
            which are not addressed to the unit, will be discarded."
            ::= { ipPortConfigEntry 4 }

        ipPortMTU  OBJECT-TYPE
            SYNTAX  INTEGER
            ACCESS  read-write
            STATUS  mandatory
            DESCRIPTION
              " Maximum size of an IP packet that can be transferred through
                this interface. It is the ifMtu for the port minus the 
                mac header. The minimum value is 64 bytes"
            ::= { ipPortConfigEntry 5 }

        ipPortDefaultGateway  OBJECT-TYPE
            SYNTAX  IpAddress
            ACCESS  read-write
            STATUS  mandatory
            DESCRIPTION
              " This parameter determines the default gateway for this specific
                IP port. If the destination for packets received on this
                port is not in the forwarding table, they will be routed 
                to this address "
            ::= { ipPortConfigEntry 6 }

        ipPortDefaultGatewayLP  OBJECT-TYPE
            SYNTAX  INTEGER
            ACCESS  read-write
            STATUS  mandatory
            DESCRIPTION
              " This parameter determines the logical port that the default
                gateway could be reached."
            ::= { ipPortConfigEntry 7 }

    --
    -- The ipPortAddrTable
    --

        ipPortAddrTable  OBJECT-TYPE
            SYNTAX  SEQUENCE OF IpPortAddrEntry
            ACCESS  not-accessible
            STATUS  mandatory
            DESCRIPTION
              "This table is a table of IP addresses and masks associated
            with each logical port."
            ::= { ipRouting 4 }

        ipPortAddrEntry  OBJECT-TYPE
            SYNTAX  IpPortAddrEntry
            ACCESS  not-accessible
            STATUS  mandatory
            DESCRIPTION
              "An entry of the IP port address table. All the objects in an 
            entry must be supplied in a single SET PDU."
            INDEX   { ipPortAddrIndex, ipPortIpAddress }
            ::= { ipPortAddrTable 1 }

        IpPortAddrEntry ::= SEQUENCE {
            ipPortAddrIndex
                 INTEGER,
            ipPortIpAddress
                 IpAddress,
            ipPortIpAddressMask
                 IpAddress,
            ipPortAddrType
                INTEGER    
            }

        ipPortAddrIndex  OBJECT-TYPE
            SYNTAX  INTEGER
            ACCESS  read-write
            STATUS  mandatory
            DESCRIPTION
              "An index into the ipPortAddr Table which identifies the 
            Logical Port No, for which the address is valid."
            ::= { ipPortAddrEntry 1 }

        ipPortIpAddress  OBJECT-TYPE
            SYNTAX  IpAddress
            ACCESS  read-write
            STATUS  mandatory
            DESCRIPTION
              "The IP Address of the logical port.This object combined
            with the ipPortAddrIndex object constitutes the instance value
            used to uniquely identify and entry in this table."
            ::= { ipPortAddrEntry 2 }

        ipPortIpAddressMask  OBJECT-TYPE
            SYNTAX  IpAddress
            ACCESS  read-write
            STATUS  mandatory
            DESCRIPTION
              "The IP address mask associated with the IP address. "
            ::= { ipPortAddrEntry 3 }

          ipPortAddrType  OBJECT-TYPE
            SYNTAX  INTEGER {
                    valid(1),        -- none of the following
                    invalid(2)      -- an invalidated mapping
                    }
            ACCESS  read-write
            STATUS  mandatory
            DESCRIPTION
                "If the value of this object is valid(1) and we are performing
            a SetRequest then this is a request to add an entry to the
            table. If a value of invalid(2) is passed in the SetRequest,
            along with the other objects in an entry then this is a
            request to  delete the entry from the table."
              ::= { ipPortAddrEntry 4 }

        ipAccessViolations  OBJECT-TYPE
            SYNTAX  Counter
            ACCESS  read-only
            STATUS  mandatory
            DESCRIPTION
               " This is a count of the number of access violations which have
            occurred for the entire unit."
            ::= { ipRouting 5 }

        ipOtherDiscards  OBJECT-TYPE
            SYNTAX  Counter
            ACCESS  read-only
            STATUS  mandatory
            DESCRIPTION
              "This is the total number of IP datagrams discarded for the 
            entire unit, for other reasons, eg the incorrect configuration 
            of a WAN port, etc"
            ::= { ipRouting 6 }

        ipOutTransmits  OBJECT-TYPE
            SYNTAX  Counter
            ACCESS  read-only
            STATUS  mandatory
            DESCRIPTION
              "This is the total number of IP datagrams which have been
            transmitted by this unit."
            ::= { ipRouting 7 }

        ipRelay  OBJECT-TYPE
            SYNTAX  INTEGER {
                   enabled (1),
                   disabled (2)
                   }
            ACCESS  read-write
            STATUS  mandatory
            DESCRIPTION
                  "This parameter enables or disables the BOOTP/DHCP Relay
                   Agent mechanism."
            ::= { ipRouting 8 }

    --
    -- BOOTP/DHCP Relay Agent Destination Table
    --

        ipRelayServerTable OBJECT-TYPE
            SYNTAX SEQUENCE OF IpRelayServerEntry
            ACCESS not-accessible
            STATUS mandatory
            DESCRIPTION
                  "Table of servers to whom BOOTP/DHCP broadcast messages
                   will be forwarded."
            ::= { ipRouting 9 }

        ipRelayServerEntry OBJECT-TYPE
            SYNTAX IpRelayServerEntry
            ACCESS not-accessible
            STATUS mandatory
            DESCRIPTION
                  "A particular entry."
            INDEX { ipRelayServerAddress }
            ::= { ipRelayServerTable 1 }

        IpRelayServerEntry ::= SEQUENCE {
                ipRelayServerAddress
                        IpAddress,
                ipRelayServerStatus
                        INTEGER
            }

        ipRelayServerAddress OBJECT-TYPE
            SYNTAX IpAddress
            ACCESS read-only
            STATUS mandatory
            DESCRIPTION
                  "The IP Address of the BOOTP/DHCP destination server."
            ::= { ipRelayServerEntry 1 }

        ipRelayServerStatus OBJECT-TYPE
            SYNTAX  INTEGER {
                    valid(1),       -- none of the following
                    invalid(2)      -- an invalidated mapping
                    }
            ACCESS read-write
            STATUS mandatory
            DESCRIPTION
                  "If the value of this object is valid(1) and we are performing
                   a SetRequest then this is a request to add an entry to the
                   table. If a value of invalid(2) is passed in the SetRequest,
                   along with the other objects in an entry then this is a
                   request to  delete the entry from the table."
            DEFVAL { valid }
            ::= { ipRelayServerEntry 2 }

        ipDhcpClient  OBJECT-TYPE
            SYNTAX  INTEGER {
                   enabled (1),
                   disabled (2)
                   }
            ACCESS  read-write
            STATUS  mandatory
            DESCRIPTION
                  "This parameter enables or disables the DHCP Client 
                   capabilities for this entity."
            ::= { ipRouting 10 }



    -- The ip Counter Group - Counters associated with the IP
    -- forwarder.

    ipCounters    OBJECT IDENTIFIER ::= { ipRouting 11 }

    --IP Counter group

          ipInternalReceived OBJECT-TYPE
              SYNTAX  Counter
              ACCESS  read-only
              STATUS  mandatory
              DESCRIPTION
                      "The number of datagrams received that were
                      addressed to the router's IP address."
              ::= { ipCounters 1 }

          ipLoopback OBJECT-TYPE
              SYNTAX  Counter
              ACCESS  read-only
              STATUS  mandatory
              DESCRIPTION
                      "The number of datagrams looped back to ourselves."
              ::= { ipCounters 2 }

          ipNonFastPath OBJECT-TYPE
              SYNTAX  Counter
              ACCESS  read-only
              STATUS  mandatory
              DESCRIPTION
                      "The number of  datagrams forwarded by software
                      outside the fastpath."
              ::= { ipCounters 3 }

          ipBackgroundPath OBJECT-TYPE
              SYNTAX  Counter
              ACCESS  read-only
              STATUS  mandatory
              DESCRIPTION
                      "The number of datagrams forwarded
                      or received through the background software path."
              ::= { ipCounters 4 }

          ipNotForwarding OBJECT-TYPE
              SYNTAX  Counter
              ACCESS  read-only
              STATUS  mandatory
              DESCRIPTION
                      "The number of datagrams received that would have
                      been forwarded except that forwarding was disabled
				  on the inbound port."
              ::= { ipCounters 5 }

          ipVlanMismatch OBJECT-TYPE
              SYNTAX  Counter
              ACCESS  read-only
              STATUS  mandatory
              DESCRIPTION
                      "The number of datagrams not forwarded because
                      the source VLAN id did not match the destination
                      VLAN id."
              ::= { ipCounters 6 }

          ipShortHeader OBJECT-TYPE
              SYNTAX  Counter
              ACCESS  read-only
              STATUS  mandatory
              DESCRIPTION
                      "The number of datagrams received with a
                      header shorter than is allowed."
              ::= { ipCounters 7 }

          ipHeaderLengthError OBJECT-TYPE
              SYNTAX  Counter
              ACCESS  read-only
              STATUS  mandatory
              DESCRIPTION
                      "The number of datagrams received with a header
				   specifying a length longer than the enclosing frame."
              ::= { ipCounters 8 }

          ipVersionError OBJECT-TYPE
              SYNTAX  Counter
              ACCESS  read-only
              STATUS  mandatory
              DESCRIPTION
                      "The number of datagrams received with an
                      incorrect header version number."
              ::= { ipCounters 9 }

          ipCsumError OBJECT-TYPE
              SYNTAX  Counter
              ACCESS  read-only
              STATUS  mandatory
              DESCRIPTION
                      "The number of datagrams received with an
                      incorrect header checksum."
              ::= { ipCounters 10 }

          ipFwdFormatError OBJECT-TYPE
              SYNTAX  Counter
              ACCESS  read-only
              STATUS  mandatory
              DESCRIPTION
                      "The number of datagrams not forwarded because
                      an error was encountered formating the datagram
                      for its next hop.
				  This is an internal software error."
              ::= { ipCounters 11 }

          ipConvFailedInbound OBJECT-TYPE
              SYNTAX  Counter
              ACCESS  read-only
              STATUS  mandatory
              DESCRIPTION
                      "The number of datagrams not forwarded because
                      an internal buffer translation failed (inbound).
				  This is an internal software error."
              ::= { ipCounters 12 }

          ipConvFailedOutbound OBJECT-TYPE
              SYNTAX  Counter
              ACCESS  read-only
              STATUS  mandatory
              DESCRIPTION
                      "The number of datagrams not forwarded because
                      an internal buffer translation failed (outbound).
				  This is an internal software error."
              ::= { ipCounters 13 }

          ipArpRequestsSent OBJECT-TYPE
              SYNTAX  Counter
              ACCESS  read-only
              STATUS  mandatory
              DESCRIPTION
                      "The number of ARP requests sent."
              ::= { ipCounters 14 }

          ipArpRepliesSent OBJECT-TYPE
              SYNTAX  Counter
              ACCESS  read-only
              STATUS  mandatory
              DESCRIPTION
                      "The number of ARP Replies sent."
              ::= { ipCounters 15 }

          ipArpRequestsRecv OBJECT-TYPE
              SYNTAX  Counter
              ACCESS  read-only
              STATUS  mandatory
              DESCRIPTION
                      "The number of ARP requests received."
              ::= { ipCounters 16 }

          ipArpRepliesRecv OBJECT-TYPE
              SYNTAX  Counter
              ACCESS  read-only
              STATUS  mandatory
              DESCRIPTION
                      "The number of ARP replies received."
              ::= { ipCounters 17 }

          ipArpQueueSatisfied OBJECT-TYPE
              SYNTAX  Counter
              ACCESS  read-only
              STATUS  mandatory
              DESCRIPTION
                      "The number of datagrams queued to an ARP queue
				   that we later transmitted."
              ::= { ipCounters 18 }

          ipArpQueueDropped OBJECT-TYPE
              SYNTAX  Counter
              ACCESS  read-only
              STATUS  mandatory
              DESCRIPTION
                      "The number of datagrams queued to an ARP queue
				   that we later dropped."
              ::= { ipCounters 19 }

          ipArpNotQueuedLimit OBJECT-TYPE
              SYNTAX  Counter
              ACCESS  read-only
              STATUS  mandatory
              DESCRIPTION
                      "The number of datagrams not queued to an ARP queue
				   because the limit was reached."
              ::= { ipCounters 20 }

          ipRequestsThrottled OBJECT-TYPE
              SYNTAX  Counter
              ACCESS  read-only
              STATUS  mandatory
              DESCRIPTION
                      "The number of requests dropped because they exceeded
				   the IP request throttle."
              ::= { ipCounters 21 }

          ipRequestsThrottledLastSecond OBJECT-TYPE
              SYNTAX  Counter
              ACCESS  read-only
              STATUS  mandatory
              DESCRIPTION
                      "The number of requests dropped in the last second because
                       they exceeded the IP request throttle."
              ::= { ipCounters 22 }

    -- The ip Parameter Group - Parameters associated with the IP
    -- forwarder, on a global basis

    ipParameters    OBJECT IDENTIFIER ::= { ipRouting 12 }

    --IP Paramter group
          ipparamBackwardingThrottle OBJECT-TYPE
              SYNTAX  INTEGER (300..64000)
              ACCESS  read-write
              STATUS  mandatory
              DESCRIPTION
                      "In order to avoid denial-of-service attacks, the
                      IP forwarder throttles the number of requests directed
                      to this system which are processed."
              ::= { ipParameters 1 }




END
