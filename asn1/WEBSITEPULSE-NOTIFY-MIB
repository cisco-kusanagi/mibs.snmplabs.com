WEBSITEPULSE-NOTIFY-MIB DEFINITIONS ::= BEGIN

IMPORTS
  enterprises FROM SNMPv2-SMI;

WEBSITEPULSE-NOTIFY-MIB MODULE-IDENTITY
    LAST-UPDATED "200912140000Z"
    ORGANIZATION "WebSitePulse.com"
    CONTACT-INFO
         "Postal: 674 Saxon Boulevard,
          Deltona, Florida 32725
          USA

          EMail:    support@websitepulse.com
                    Phone:    +1-407-380-1600
         "

DESCRIPTION  "WebSitePulse NOTIFICATION MIB"
  ::= { enterprises 22096 }

WebSitePulseMIBObjects     OBJECT IDENTIFIER ::= { WEBSITEPULSE-NOTIFY-MIB 1 }
WebSitePulsePublic     OBJECT IDENTIFIER ::= { WebSitePulseMIBObjects 1 }
WebSitePulseTraps     OBJECT IDENTIFIER ::= { WebSitePulseMIBObjects 2 }


WebSitePulseAlertType OBJECT-TYPE
    SYNTAX  DisplayString
    MAX-ACCESS  read-write
    STATUS  current
    DESCRIPTION
  "Alert type"
    ::= { WebSitePulsePublic 1 }


WebSitePulseSubscriberNames OBJECT-TYPE
    SYNTAX  DisplayString
    MAX-ACCESS  read-write
    STATUS  current
    DESCRIPTION
  "Subscriber Names"
    ::= { WebSitePulsePublic 2 }

WebSitePulseStatus OBJECT-TYPE
    SYNTAX  DisplayString
    MAX-ACCESS  read-write
    STATUS  current
    DESCRIPTION
  "This is the status message of the monitored resource."
    ::= { WebSitePulsePublic 3 }

WebSitePulseDomain OBJECT-TYPE
    SYNTAX  DisplayString
    MAX-ACCESS  read-write
    STATUS  current
    DESCRIPTION
  "Domain hostname or IP address."
    ::= { WebSitePulsePublic 4 }

WebSitePulseTargetLabel OBJECT-TYPE
    SYNTAX  DisplayString
    MAX-ACCESS  read-write
    STATUS  current
    DESCRIPTION
  "The label of the target."
    ::= { WebSitePulsePublic 5 }

WebSitePulseServerType OBJECT-TYPE
    SYNTAX  DisplayString
    MAX-ACCESS  read-write
    STATUS  current
    DESCRIPTION
  "The server type (HTTP, FTP and etc.)."
    ::= { WebSitePulsePublic 6 }

WebSitePulsePort OBJECT-TYPE
    SYNTAX  DisplayString
    MAX-ACCESS  read-write
    STATUS  current
    DESCRIPTION
  "The server port that is monitored."
    ::= { WebSitePulsePublic 7 }

WebSitePulseDate OBJECT-TYPE
    SYNTAX  DisplayString
    MAX-ACCESS  read-write
    STATUS  current
    DESCRIPTION
  "The local time of the monitored server."
    ::= { WebSitePulsePublic 8 }

WebSitePulseResponseTime OBJECT-TYPE
    SYNTAX  Float
    MAX-ACCESS  read-write
    STATUS  current
    DESCRIPTION
  "Response Time."
    ::= { WebSitePulsePublic 9 }

WebSitePulseDowntime OBJECT-TYPE
    SYNTAX  DisplayString
    MAX-ACCESS  read-write
    STATUS  current
    DESCRIPTION
  "The estimated downtime is the multiplication of the number of consecutive failures and the monitoring frequency (in minutes) for the selected target."
    ::= { WebSitePulsePublic 10 }

WebSitePulseRuleName OBJECT-TYPE
    SYNTAX  DisplayString
    MAX-ACCESS  read-write
    STATUS  current
    DESCRIPTION
  "The label of the dependency rule that was satisfied prior to sending a dependency alert."
    ::= { WebSitePulsePublic 11 }

WebSitePulseUrl OBJECT-TYPE
    SYNTAX  DisplayString
    MAX-ACCESS  read-write
    STATUS  current
    DESCRIPTION
  "The URL address for URL monitoring."
    ::= { WebSitePulsePublic 12 }

WebSitePulseStepNumber OBJECT-TYPE
    SYNTAX  DisplayString
    MAX-ACCESS  read-write
    STATUS  current
    DESCRIPTION
  "Transaction step number."
    ::= { WebSitePulsePublic 13 }

WebSitePulseStepLabel OBJECT-TYPE
    SYNTAX  DisplayString
    MAX-ACCESS  read-write
    STATUS  current
    DESCRIPTION
  "Transaction step label."
    ::= { WebSitePulsePublic 14 }

WebSitePulseConnectionFailure NOTIFICATION-TYPE
    STATUS  current
    OBJECTS { WebSitePulseAlertType,
              WebSitePulseSubscriberNames,
              WebSitePulseStatus,
              WebSitePulseDomain,
              WebSitePulseTargetLabel,
              WebSitePulseServerType,
              WebSitePulsePort,
              WebSitePulseDate,
              WebSitePulseResponseTime,
              WebSitePulseDowntime,
              WebSitePulseRuleName,
              WebSitePulseUrl,
              WebSitePulseStepNumber,
              WebSitePulseStepLabel
            }
    DESCRIPTION
  "Connection problem - sent when the problem is detected for the first time"
    ::= { WebSitePulseTraps 1 }

WebSitePulseContentFailure NOTIFICATION-TYPE
    STATUS  current
    OBJECTS { WebSitePulseAlertType,
              WebSitePulseSubscriberNames,
              WebSitePulseStatus,
              WebSitePulseDomain,
              WebSitePulseTargetLabel,
              WebSitePulseServerType,
              WebSitePulsePort,
              WebSitePulseDate,
              WebSitePulseResponseTime,
              WebSitePulseDowntime,
              WebSitePulseRuleName,
              WebSitePulseUrl,
              WebSitePulseStepNumber,
              WebSitePulseStepLabel
            }
    DESCRIPTION
  "Content problem - sent when the problem is detected for the first time"
    ::= { WebSitePulseTraps 2 }

WebSitePulseTimeoutFailure NOTIFICATION-TYPE
    STATUS  current
    OBJECTS { WebSitePulseAlertType,
              WebSitePulseSubscriberNames,
              WebSitePulseStatus,
              WebSitePulseDomain,
              WebSitePulseTargetLabel,
              WebSitePulseServerType,
              WebSitePulsePort,
              WebSitePulseDate,
              WebSitePulseResponseTime,
              WebSitePulseDowntime,
              WebSitePulseRuleName,
              WebSitePulseUrl,
              WebSitePulseStepNumber,
              WebSitePulseStepLabel
            }
    DESCRIPTION
  "Timeout warning - sent when the problem is detected for the first time"
    ::= { WebSitePulseTraps 3 }

WebSitePulseFailureRepeated NOTIFICATION-TYPE
    STATUS  current
    OBJECTS { WebSitePulseAlertType,
              WebSitePulseSubscriberNames,
              WebSitePulseStatus,
              WebSitePulseDomain,
              WebSitePulseTargetLabel,
              WebSitePulseServerType,
              WebSitePulsePort,
              WebSitePulseDate,
              WebSitePulseResponseTime,
              WebSitePulseDowntime,
              WebSitePulseRuleName,
              WebSitePulseUrl,
              WebSitePulseStepNumber,
              WebSitePulseStepLabel
            }
    DESCRIPTION
  "A repeat failure notification - sent if the targets has been detected down more than once"
    ::= { WebSitePulseTraps 4 }


WebSitePulseRecovery NOTIFICATION-TYPE
    STATUS  current
    OBJECTS { WebSitePulseAlertType,
              WebSitePulseSubscriberNames,
              WebSitePulseStatus,
              WebSitePulseDomain,
              WebSitePulseTargetLabel,
              WebSitePulseServerType,
              WebSitePulsePort,
              WebSitePulseDate,
              WebSitePulseResponseTime,
              WebSitePulseDowntime,
              WebSitePulseRuleName,
              WebSitePulseUrl,
              WebSitePulseStepNumber,
              WebSitePulseStepLabel
            }
    DESCRIPTION
  "A recovery notification"
    ::= { WebSitePulseTraps 5 }

WebSitePulseFirstCheckFailure NOTIFICATION-TYPE
    STATUS  current
    OBJECTS { WebSitePulseAlertType,
              WebSitePulseSubscriberNames,
              WebSitePulseStatus,
              WebSitePulseDomain,
              WebSitePulseTargetLabel,
              WebSitePulseServerType,
              WebSitePulsePort,
              WebSitePulseDate,
              WebSitePulseResponseTime,
              WebSitePulseDowntime,
              WebSitePulseRuleName,
              WebSitePulseUrl,
              WebSitePulseStepNumber,
              WebSitePulseStepLabel
            }
    DESCRIPTION
  "A failure has been detected on the first check - could be target misconfiguration"
    ::= { WebSitePulseTraps 6 }

WebSitePulseDependency NOTIFICATION-TYPE
    STATUS  current
    OBJECTS { WebSitePulseAlertType,
              WebSitePulseSubscriberNames,
              WebSitePulseStatus,
              WebSitePulseDomain,
              WebSitePulseTargetLabel,
              WebSitePulseServerType,
              WebSitePulsePort,
              WebSitePulseDate,
              WebSitePulseResponseTime,
              WebSitePulseDowntime,
              WebSitePulseRuleName,
              WebSitePulseUrl,
              WebSitePulseStepNumber,
              WebSitePulseStepLabel
            }
    DESCRIPTION
  "A dependency rule has been satisfied"
    ::= { WebSitePulseTraps 7 }

WebSitePulseSoftTimeout NOTIFICATION-TYPE
    STATUS  current
    OBJECTS { WebSitePulseAlertType,
              WebSitePulseSubscriberNames,
              WebSitePulseStatus,
              WebSitePulseDomain,
              WebSitePulseTargetLabel,
              WebSitePulseServerType,
              WebSitePulsePort,
              WebSitePulseDate,
              WebSitePulseResponseTime,
              WebSitePulseDowntime,
              WebSitePulseRuleName,
              WebSitePulseUrl,
              WebSitePulseStepNumber,
              WebSitePulseStepLabel
            }
    DESCRIPTION
  "Soft timeout warning"
    ::= { WebSitePulseTraps 8 }

WebSitePulseSimulation NOTIFICATION-TYPE
    STATUS  current
    OBJECTS { WebSitePulseAlertType,
              WebSitePulseSubscriberNames,
              WebSitePulseStatus,
              WebSitePulseDomain,
              WebSitePulseTargetLabel,
              WebSitePulseServerType,
              WebSitePulsePort,
              WebSitePulseDate,
              WebSitePulseResponseTime,
              WebSitePulseDowntime,
              WebSitePulseRuleName,
              WebSitePulseUrl,
              WebSitePulseStepNumber,
              WebSitePulseStepLabel
            }
    DESCRIPTION
  "A failure simulation notification"
    ::= { WebSitePulseTraps 9 }

END
