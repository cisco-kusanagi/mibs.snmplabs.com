-- ********************************************************************
-- * Wireless LAN Access Point Management Base
-- ********************************************************************

WG302-MIB DEFINITIONS ::= BEGIN

	IMPORTS
	MODULE-IDENTITY,	OBJECT-TYPE,
	NOTIFICATION-TYPE,	enterprises,
	Integer32,			Counter32,
	IpAddress,			Unsigned32,
	TimeTicks			FROM SNMPv2-SMI
	MODULE-COMPLIANCE,	NOTIFICATION-GROUP,
	OBJECT-GROUP		FROM SNMPv2-CONF

	TEXTUAL-CONVENTION,	DisplayString,
	MacAddress,		TruthValue		FROM SNMPv2-TC
	ifIndex						FROM RFC1213-MIB;

-- ********************************************************************
-- *  MODULE IDENTITY
-- ********************************************************************
accesspoint MODULE-IDENTITY
		LAST-UPDATED	"200411030003Z"
		ORGANIZATION	"NETGEAR Inc."
		CONTACT-INFO
			"4500 Great America Parkway
			Santa Clara, California 95054
			Phone: (408) 907-8000
			Fax: (408) 907-8097
			Web Site: http://www.netgear.com"
		DESCRIPTION
			"The MIB module for 802.11g ProSafe Wireless Access Point entities.
			iso(1).org(3).dod(6).internet(1).private(4).
			enterprises(1).netgear(4526).wireless(4).accesspoint(2)"
	::= { wireless 2 }

-- The Enterprises Number
	netgear	OBJECT IDENTIFIER  ::= { enterprises 4526 }
	wireless OBJECT IDENTIFIER ::= { netgear 4 }

-- Wireless LAN Access Point Identifier

-- **********************************************************************
-- *  MIB attribute OBJECT-TYPE definitions follow
-- **********************************************************************
-- **********************************************************************
-- *  IP Setting  Table
-- **********************************************************************
lanSettings OBJECT IDENTIFIER ::=  { accesspoint 1 }

apName OBJECT-TYPE
		SYNTAX DisplayString ( SIZE(1..32) )
		MAX-ACCESS read-write
		STATUS current
		DESCRIPTION
			 "The field indicates the name of AP."
	::= { lanSettings 1 }

adminName OBJECT-TYPE
		SYNTAX DisplayString (SIZE(0..32))
		MAX-ACCESS not-accessible
		STATUS current
		DESCRIPTION
			"The field indicates the administrator name."
	::= { lanSettings 2 }

adminPasswd OBJECT-TYPE
		SYNTAX DisplayString (SIZE(0..32))
		MAX-ACCESS not-accessible
		STATUS current
		DESCRIPTION
			"The field indicates the administrator password.
			The AP can be managed in such way as utility,telnet
			and so on."
	::= { lanSettings 3 }

dhcpStatus OBJECT-TYPE
		SYNTAX INTEGER { static(0), dhcpclient(1) }
		MAX-ACCESS read-write
		STATUS current
		DESCRIPTION
			"This attribute shall indicate whether dhcp client status."
	::= { lanSettings 4 }

ipAddr OBJECT-TYPE
		SYNTAX IpAddress
		MAX-ACCESS read-write
		STATUS current
		DESCRIPTION
			"The field indicates the IP address of AP on the wireless
			interface,when worked in router or router/bridge mode.
			Ethernet and wireless interface share the same IP address,
			when worked in bridge mode. "
	::= { lanSettings 5 }

netmaskAddr OBJECT-TYPE
		SYNTAX IpAddress
		MAX-ACCESS read-write
		STATUS current
		DESCRIPTION
			"The field indicates the netmask of AP on the wireless
			interface,when worked in router or router/bridge mode.
			Ethernet and wireless interface share the same netmask
			address,when worked in bridge mode. "
	::= { lanSettings 6 }

gatewayAddr OBJECT-TYPE
		SYNTAX IpAddress
		MAX-ACCESS read-write
		STATUS current
		DESCRIPTION
			"The field indicates the gateway of AP on the wireless
			interface,when worked in router or router/bridge mode.
			Ethernet and wireless interface share the same gateway
			address,when worked in bridge mode. "
	::= { lanSettings 7 }

spantree OBJECT-TYPE
		SYNTAX TruthValue
		MAX-ACCESS read-write
		STATUS current
		DESCRIPTION
			"This attribute shall indicate spanning tree."
	::= { lanSettings 8 }


pridnsipAddr OBJECT-TYPE
		SYNTAX IpAddress
		MAX-ACCESS read-write
		STATUS current
		DESCRIPTION
			"This attributes shall indicates the IP address of the primary DNS server.
			***The value can only be set to an IP address in dot format."	    
	::= { lanSettings 9 }

snddnsipAddr OBJECT-TYPE
		SYNTAX IpAddress
		MAX-ACCESS read-write
		STATUS current
		DESCRIPTION
			"This attributes shall indicates the IP address of the secondary DNS server.
			***The value can only be set to an IP address in dot format."	    
	::= { lanSettings 10 }

-- **********************************************************************
-- *  Wireless Settings Table
-- **********************************************************************
wlanSettingTable OBJECT-TYPE
		SYNTAX SEQUENCE OF WlanSettingEntry
		MAX-ACCESS not-accessible
		STATUS current
		DESCRIPTION
			"wlanSettingsallow for multiple instances on an agent."
	::= { accesspoint 2 }

wlanSettingEntry OBJECT-TYPE
		SYNTAX WlanSettingEntry
		MAX-ACCESS not-accessible
		STATUS current
		DESCRIPTION
			"An entry in the wlanSettingTable.  It is possible for
			there to be multiple AP interfaces on one agent,
			each with its unique MAC address. The relationship
			between an AP interface and an interface in the context
			of the Internet-standard MIB is one-to-one.
			As such, the value of an ifIndex object instance can be
			directly used to identify corresponding instances of the
			objects defined herein. "
		INDEX {ifIndex}
	::= { wlanSettingTable 1 }

WlanSettingEntry ::=
		SEQUENCE 
		{
			operatemode				INTEGER,
			countrycode				INTEGER,
			ssid					DisplayString,
			channel					INTEGER,
			datarate				DisplayString,
			beaconinterval			INTEGER,
			rtsthreshold			INTEGER,
			fraglength				INTEGER,
			dtiminterval			INTEGER,
			preambletype			INTEGER,
			hidenetworkname			TruthValue,
			txpower					INTEGER,
			superG					TruthValue,
			antenna					INTEGER
		}

operatemode OBJECT-TYPE
		SYNTAX INTEGER { auto(0), dot11b(2), dot11g(3) }
		MAX-ACCESS read-write
		STATUS current
		DESCRIPTION
			"This attribute shall indicate the desired wireless operating mode.
			The option are:
			auto -  Both 802.11g and 802.11b wireless stations can be used.
			dot11b - All 802.11b wireless stations can be used.
				 802.11g wireless stations can still be used
				 if they can operate in 802.11b mode.
			dot11g - Only 802.11g wireless stations can be used."
	::= { wlanSettingEntry 1 }

ssid OBJECT-TYPE
		SYNTAX DisplayString (SIZE(0..32))
		MAX-ACCESS read-write
		STATUS current
		DESCRIPTION
			"This attribute shall indicate SSID.Its length can't be large than 33 ."
	::= { wlanSettingEntry 2 }

countrycode OBJECT-TYPE
		SYNTAX INTEGER  
		{
			asia(410), australia(36), canada(124), denmark(208),europe(40), finland(246), 
			france(250), germany(276), ireland(372),italy(380),japan(392), mexico(484),
			netherlands(528), newzealand(554),norway(578),puertorico(630), southamerica(340), 
			spain(724), sweden(752),switzerland(756), unitedkingdom(826), unitedstates(840) 
		}
		MAX-ACCESS read-write
		STATUS current
		DESCRIPTION
			"This attribute shall indicate the region of operation
			for which which the wireless interface is inted.
				  =410: asia
				  =36:  australia
				  =124: canada
				  =208: denmark
				  =40:  europe
				  =246: finland
				  =250: france
				  =276: germany
				  =372: ireland
				  =380: italy
				  =392: japan
				  =484: mexico
				  =528: netherlands
				  =554:	new zealand
				  =578: norway
				  =630: puerto rico
				  =756: switzerland
				  =340:  south america
				  =724: spain
				  =752: sweden
				  =826: unitedKingdom
				  =840: usa"
	::= { wlanSettingEntry 3 }

channel OBJECT-TYPE
		SYNTAX INTEGER (1..14)
		MAX-ACCESS read-write
		STATUS current
		DESCRIPTION
			"This attribute shall indicate the channel number to use on your Wireless LAN.
			1:	CH01 2412MHz
			2:	CH02 2417MHz
			3:	CH03 2422MHz
			4:	CH04 2427MHz
			5:	CH05 2432MHz
			6:	CH06 2437MHz
			7:	CH07 2442MHz
			8:	CH08 2447MHz
			9:	CH09 2452MHz
			10:	CH10 2457MHz
			11:	CH11 2462MHz
			12:	CH12 2467MHz
			13:	CH13 2472MHz
			14:	CH14 2484MHz
		The default value is 11."
	::= { wlanSettingEntry 4 }

datarate OBJECT-TYPE
		SYNTAX DisplayString (SIZE(0..3))
		MAX-ACCESS read-write
		STATUS current
		DESCRIPTION
			"This attribute shall indicate the transmite rate.
			When operatemode is auto(0) can set to
			0:best,1:1Mb/s,2:2Mb/s, 5.5:5.5Mb/s,11:11 Mb/s,
			6:6Mb/s,9:   9Mb/s,12:12Mb/s,18:8Mb/s,24:24Mb/s
			36:36Mb/s,48:48Mb/s,54:54Mb/s .
			When operatemode is dot11b(2) can set to
			0:best,1:1Mb/s,2:2Mb/s,5.5:5.5Mb/s,11:11 Mb/s.
			When operatemode is dot11g(3) can set to
			0:best,6:6Mb/s,9:9Mb/s,12:12Mb/s,18:18Mb/s,24:24Mb/s
			36:36Mb/s,48:48Mb/s,54:54Mb/s,108:108Mb/s. "
	::= { wlanSettingEntry 5 }

beaconinterval OBJECT-TYPE
		SYNTAX INTEGER (20..1000)
		MAX-ACCESS read-write
		STATUS current
		DESCRIPTION
			"This attribute shall indicate the Beacon Interval."
	::= { wlanSettingEntry 6 }

rtsthreshold OBJECT-TYPE
		SYNTAX INTEGER (0..2346)
		MAX-ACCESS read-write
		STATUS current
		DESCRIPTION
			"This attribute shall indicate the RTS threshold."
	::= { wlanSettingEntry 7 }

fraglength OBJECT-TYPE
		SYNTAX INTEGER (256..2346)
		MAX-ACCESS read-write
		STATUS current
		DESCRIPTION
			"This attribute shall indicate the fragmentation threshold."
	::= { wlanSettingEntry 8 }

dtiminterval OBJECT-TYPE
		SYNTAX INTEGER (1..255)
		MAX-ACCESS read-write
		STATUS current
		DESCRIPTION
			"This attribute shall indicate the DTIM period."
	::= { wlanSettingEntry 9 }

preambletype OBJECT-TYPE
		SYNTAX INTEGER { long(0), auto(1) }
		MAX-ACCESS read-write
		STATUS current
		DESCRIPTION
			"This attribute shall indicate the preamble setting."
	::= { wlanSettingEntry 10 }

hidenetworkname OBJECT-TYPE
		SYNTAX TruthValue
		MAX-ACCESS read-write
		STATUS current
		DESCRIPTION
			"This attribute shall indicate whether broadcast wireless network Name (SSID)."
	::= { wlanSettingEntry 11 }

txpower OBJECT-TYPE
		SYNTAX INTEGER { full(0), half(1), quarter(2), eighth(3), min(4) }
		MAX-ACCESS read-write
		STATUS current
		DESCRIPTION
			"This attribute shall indicate the tranmiste power."
	::= { wlanSettingEntry 12 }

superG OBJECT-TYPE
		SYNTAX TruthValue
		MAX-ACCESS read-write
		STATUS current
		DESCRIPTION
			"This attribute shall indicate whether super-G."
	::= { wlanSettingEntry 13 }

antenna OBJECT-TYPE
		SYNTAX INTEGER { auto(0), primary(1), secondary(2) }
		MAX-ACCESS read-write
		STATUS current
		DESCRIPTION
			"This attribute shall indicate the tranmiste power."
	::= { wlanSettingEntry 14 }

-- **********************************************************************
-- *  Security  SettingsTable
-- **********************************************************************
securityTable OBJECT-TYPE
		SYNTAX SEQUENCE OF SecurityEntry
		MAX-ACCESS not-accessible
		STATUS current
		DESCRIPTION
			"Security attributes.  In tablular form to
			allow for multiple instances on an agent."
	::= { accesspoint 3 }

securityEntry OBJECT-TYPE
		SYNTAX SecurityEntry
		MAX-ACCESS not-accessible
		STATUS current
		DESCRIPTION
			"An entry in the securityTable.  It is possible for
			there to be multiple AP interfaces on one agent,
			each with its unique MAC address. The relationship
			between an AP interface and an interface in the context
			of the Internet-standard MIB is one-to-one.
			As such, the value of an ifIndex object instance can be
			directly used to identify corresponding instances of the
			objects defined herein. "
		INDEX {ifIndex}
	::= { securityTable 1 }

SecurityEntry ::=
		SEQUENCE
		{
			authenticationtype		INTEGER,
			encryption				INTEGER,
			encryptionstrength		INTEGER,
			keyno					INTEGER,
			key1					DisplayString,
			key2					DisplayString,
			key3					DisplayString,
			key4					DisplayString,
			wlanseparator			TruthValue,
			presharekey				DisplayString
		}

authenticationtype OBJECT-TYPE
		SYNTAX INTEGER { open(0), shared(1),legacy802dot1x(2),wpa(3),wpapsk(4) }
		MAX-ACCESS read-write
		STATUS current
		DESCRIPTION
			"The field indicates how to authenticate the station."
	::= { securityEntry 1 }

encryption OBJECT-TYPE
		SYNTAX INTEGER {none(0),wep(1), tkip(2) }
		MAX-ACCESS read-write
		STATUS current
		DESCRIPTION
			"The field indicates how to encryption the station."
	::= { securityEntry 2 }

encryptionstrength OBJECT-TYPE
		SYNTAX INTEGER {none(0),wep64(40), wep128(104), wep152(128)}
		MAX-ACCESS read-write
		STATUS current
		DESCRIPTION
			"The field indicates the key length of default keys."
	::= { securityEntry 3 }

keyno OBJECT-TYPE
		 SYNTAX INTEGER (1..4)
		 MAX-ACCESS read-write
		 STATUS current
		 DESCRIPTION
			 "The field indicates the number of default wep key."
	::= { securityEntry 4 }

key1 OBJECT-TYPE
		 SYNTAX DisplayString (SIZE(0..40))
		 MAX-ACCESS read-write
		 STATUS current
		 DESCRIPTION
			 "The field indicates the key value of the first default wep key."
	::= { securityEntry 5 }

key2 OBJECT-TYPE
		 SYNTAX DisplayString (SIZE(0..40))
		 MAX-ACCESS read-write
		 STATUS current
		 DESCRIPTION
			 "The field indicates the key value of the second default wep key."
	::= { securityEntry 6 }

key3 OBJECT-TYPE
		 SYNTAX DisplayString (SIZE(0..40))
		 MAX-ACCESS read-write
		 STATUS current
		 DESCRIPTION
			 "The field indicates the key value of the third default wep key."
	::= { securityEntry 7 }

key4 OBJECT-TYPE
		 SYNTAX DisplayString (SIZE(0..40))
		 MAX-ACCESS read-write
		 STATUS current
		 DESCRIPTION
			 "The field indicates the key value of the fourth default wep key."
	::= { securityEntry 8 }

wlanseparator OBJECT-TYPE
		SYNTAX TruthValue
		MAX-ACCESS read-write
		STATUS current
		DESCRIPTION
			"This attribute shall indicate whether enable No see."
	::= { securityEntry 9 }

presharekey OBJECT-TYPE
		SYNTAX DisplayString (SIZE(0..63))
		MAX-ACCESS read-write
		STATUS current
		DESCRIPTION
			"This attribute shall indicate preshare key."
	::= { securityEntry 10 }


--*********************************************************
-- Remote Settings Information
--*********************************************************
remoteSettings OBJECT IDENTIFIER ::=  { accesspoint 4}

sshd	OBJECT-TYPE
		SYNTAX TruthValue
		MAX-ACCESS read-write
		STATUS current
		DESCRIPTION
			"This attribute shall indicate whether enable sshd."
	::= { remoteSettings 1 }

snmpenable 	OBJECT-TYPE
		SYNTAX TruthValue
		MAX-ACCESS read-write
		STATUS current
		DESCRIPTION
			"This attribute shall indicate whether enable snmp."
	::= { remoteSettings 2 }

trapServerIP  OBJECT-TYPE
		SYNTAX IpAddress
		MAX-ACCESS read-write
		STATUS current
		DESCRIPTION
			"The field indicates the trap server IP address.
			***The value can only be set to a IP address in dot format."
	::= { remoteSettings 3 }

readOnlyCommunity  OBJECT-TYPE
		SYNTAX DisplayString (SIZE(1..31))
		MAX-ACCESS read-write
		STATUS current
		DESCRIPTION
			"The field indicates the read only community name.
			***The value can only be set to 1 to 32 readable string."
	::= { remoteSettings 4 }

readWriteCommunity  OBJECT-TYPE
		SYNTAX DisplayString (SIZE(1..31))
		MAX-ACCESS read-write
		STATUS current
		DESCRIPTION
			"The field indicates the read write community name.
			***The value can only be set to 1 to 32 readable string."
	::= { remoteSettings 5 }

--***********************************************************************
--*Statistic
--***********************************************************************
statistic OBJECT IDENTIFIER ::=  { accesspoint 5 }
wiredethernetstat OBJECT IDENTIFIER ::= { statistic 1 }

lanrecvpacket  OBJECT-TYPE
		SYNTAX Unsigned32
		MAX-ACCESS read-only
		STATUS current
		DESCRIPTION
			"the field indicates the sum of received packets."
	::= { wiredethernetstat 1 }

lantranspacket  OBJECT-TYPE
		SYNTAX Unsigned32
		MAX-ACCESS read-only
		STATUS current
		DESCRIPTION
			"the field indicates the sum of transmitted packets."
	::= { wiredethernetstat 2 }

lanrecvbytes  OBJECT-TYPE
		SYNTAX Unsigned32
		MAX-ACCESS read-only
		STATUS current
		DESCRIPTION
			"the field indicates the sum of received bytes."
	::= { wiredethernetstat 3 }

lantransbytes  OBJECT-TYPE
		SYNTAX Unsigned32
		MAX-ACCESS read-only
		STATUS current
		DESCRIPTION
			"the field indicates the sum of transmitted bytes."
	::= { wiredethernetstat 4 }

wirelessstat OBJECT IDENTIFIER ::= { statistic 2 }

wlanrecvunicastpacket  OBJECT-TYPE
		SYNTAX Unsigned32
		MAX-ACCESS read-only
		STATUS current
		DESCRIPTION
			"the field indicates the sum of received unicast packets."
	::= { wirelessstat 1 }

wlantransunicastpacket  OBJECT-TYPE
		SYNTAX Unsigned32
		MAX-ACCESS read-only
		STATUS current
		DESCRIPTION
			"the field indicates the sum of transmitted unicast packets."
	::= { wirelessstat 2 }

wlanrecvbroadcastpacket  OBJECT-TYPE
		SYNTAX Unsigned32
		MAX-ACCESS read-only
		STATUS current
		DESCRIPTION
			"the field indicates the sum of received broadcast packets."
	::= { wirelessstat 3 }

wlantransbroadcastpacket  OBJECT-TYPE
		SYNTAX Unsigned32
		MAX-ACCESS read-only
		STATUS current
		DESCRIPTION
			"the field indicates the sum of transmitted broadcast packets."
	::= { wirelessstat 4 }

wlanrecvmulticastpacket  OBJECT-TYPE
		SYNTAX Unsigned32
		MAX-ACCESS read-only
		STATUS current
		DESCRIPTION
			"the field indicates the sum of received multicast packets."
	::= { wirelessstat 5 }

wlantransmulticastpacket  OBJECT-TYPE
		SYNTAX Unsigned32
		MAX-ACCESS read-only
		STATUS current
		DESCRIPTION
			"the field indicates the sum of transmitted multicast packets."
	::= { wirelessstat 6 }

wlanrecvpacket  OBJECT-TYPE
		SYNTAX Unsigned32
		MAX-ACCESS read-only
		STATUS current
		DESCRIPTION
			"the field indicates the sum of received packets."
	::= { wirelessstat 7 }

wlantranspacket  OBJECT-TYPE
		SYNTAX Unsigned32
		MAX-ACCESS read-only
		STATUS current
		DESCRIPTION
			"the field indicates the sum of transmitted packets."
	::= { wirelessstat 8 }

wlanrecvbytes  OBJECT-TYPE
		SYNTAX Unsigned32
		MAX-ACCESS read-only
		STATUS current
		DESCRIPTION
			"the field indicates the sum of received bytes."
	::= { wirelessstat 9 }

wlantransbytes  OBJECT-TYPE
		SYNTAX Unsigned32
		MAX-ACCESS read-only
		STATUS current
		DESCRIPTION
			"the field indicates the sum of transmitted bytes."
	::= { wirelessstat 10 }

stationnumber OBJECT-TYPE
		SYNTAX Unsigned32
		MAX-ACCESS read-only
		STATUS current
		DESCRIPTION
			"This attribute shall indicate the stations count."
	::= { wirelessstat 11 }

-- **********************************************************************
-- *  Station List Table
-- **********************************************************************
stationListTable OBJECT-TYPE
		SYNTAX SEQUENCE OF StationListEntry
		MAX-ACCESS not-accessible
		STATUS current
		DESCRIPTION
			"stationList Table show multiple instances on an agent."
	::= { accesspoint 6 }

stationListEntry OBJECT-TYPE
		SYNTAX StationListEntry
		MAX-ACCESS not-accessible
		STATUS current
		DESCRIPTION
			"stationlist Entry show the connected station status "
		INDEX {ifIndex}
	::= { stationListTable 1 }

StationListEntry ::=
		SEQUENCE 
		{
			macaddress				MacAddress,
			ipaddr					IpAddress,
			stationstatus			INTEGER 
		}

macaddress OBJECT-TYPE
		SYNTAX MacAddress
		MAX-ACCESS read-only
		STATUS current
		DESCRIPTION
			"This attribute shall indicate MAC address of the associated stationID."
	::= { stationListEntry 1 }

ipaddr OBJECT-TYPE
		SYNTAX IpAddress
		MAX-ACCESS read-only
		STATUS current
		DESCRIPTION
			"This attribute shall indicate Ip address of the associated stationID."
	::= { stationListEntry 2 }

stationstatus OBJECT-TYPE
		SYNTAX INTEGER { none(0), authenticating(1), authenticated(2), associating(3), associated(4) }
		MAX-ACCESS read-only
		STATUS current
		DESCRIPTION
			"This attribute shall indicate the status of station."
	::= { stationListEntry 3 }

--*********************************************************
-- AP Operation Mode
--*********************************************************
--ap mode
operationapmode OBJECT IDENTIFIER ::=  {accesspoint 7}

apmode  OBJECT-TYPE
		SYNTAX INTEGER { ap(0), ptp(2),ptp-ap(3),pxp(4), pxp-ap(5),repeater(6) }
		MAX-ACCESS read-write
		STATUS current
		DESCRIPTION
			"This a command field for conntrol AP operation mode. "
	::= { operationapmode 1  }

ptpremotemacaddress OBJECT-TYPE
		SYNTAX MacAddress
		MAX-ACCESS read-write
		STATUS current
		DESCRIPTION
			"This attribute shall indicate the stationID."
	::= { operationapmode 2 }

pxpremotemacaddress1 OBJECT-TYPE
		SYNTAX MacAddress
		MAX-ACCESS read-write
		STATUS current
		DESCRIPTION
			"This attribute shall indicate the stationID."
	::= { operationapmode 3 }

pxpremotemacaddress2 OBJECT-TYPE
		SYNTAX MacAddress
		MAX-ACCESS read-write
		STATUS current
		DESCRIPTION
			"This attribute shall indicate the stationID."
	::= { operationapmode 4 }

pxpremotemacaddress3 OBJECT-TYPE
		SYNTAX MacAddress
		MAX-ACCESS read-write
		STATUS current
		DESCRIPTION
			"This attribute shall indicate the stationID."
	::= { operationapmode 5 }

pxpremotemacaddress4 OBJECT-TYPE
		SYNTAX MacAddress
		MAX-ACCESS read-write
		STATUS current
		DESCRIPTION
			"This attribute shall indicate the stationID."
	::= { operationapmode 6 }

repremotemacaddress1 OBJECT-TYPE
		SYNTAX MacAddress
		MAX-ACCESS read-write
		STATUS current
		DESCRIPTION
			"This attribute shall indicate the stationID."
	::= { operationapmode 7 }
				
repremotemacaddress2 OBJECT-TYPE
		SYNTAX MacAddress
		MAX-ACCESS read-write
		STATUS current
		DESCRIPTION
			"This attribute shall indicate the stationID."
	::= { operationapmode 8 }

repremotemacaddress3 OBJECT-TYPE
		SYNTAX MacAddress
		MAX-ACCESS read-write
		STATUS current
		DESCRIPTION
			"This attribute shall indicate the stationID."
	::= { operationapmode 9 }

repremotemacaddress4 OBJECT-TYPE
		SYNTAX MacAddress
		MAX-ACCESS read-write
		STATUS current
		DESCRIPTION
			"This attribute shall indicate the stationID."
	::= { operationapmode 10 }

--*********************************************************
-- 802.1x Information
--*********************************************************
	info802dot1x OBJECT IDENTIFIER ::=  {accesspoint 8}
	authinfo OBJECT IDENTIFIER ::=  {info802dot1x 1}

priradipaddr OBJECT-TYPE
		SYNTAX IpAddress
		MAX-ACCESS read-write
		STATUS current
		DESCRIPTION
			"Internet address of the Primary Radius Server."
	::= { authinfo 1 }

priradport	OBJECT-TYPE
		SYNTAX INTEGER
		MAX-ACCESS read-write
		STATUS current
		DESCRIPTION
			"Port number used for authentication at the
			Primary Radius Server."
	::= { authinfo 2  }

priradsharedsecret	OBJECT-TYPE
		SYNTAX DisplayString (SIZE(0..32))
		MAX-ACCESS read-write
		STATUS current
		DESCRIPTION
			"Secret shared between NAS and the Primary Radius Server."
	::= { authinfo 3 }

sndradipaddr OBJECT-TYPE
		SYNTAX IpAddress
		MAX-ACCESS read-write
		STATUS current
		DESCRIPTION
			"Internet address of the Second Radius Server."
	::= { authinfo 4 }

sndradport	OBJECT-TYPE
		SYNTAX INTEGER
		MAX-ACCESS read-write
		STATUS current
		DESCRIPTION
			"Port number used for authentication at
			the Second Radius Server."
	::= { authinfo 5  }

sndradsharedsecret	OBJECT-TYPE
		SYNTAX DisplayString (SIZE(0..32))
		MAX-ACCESS read-write
		STATUS current
		DESCRIPTION
			"Secret shared between NAS and the Second Radius Server."
	::= { authinfo 6 }

reauthtime 	OBJECT-TYPE
		SYNTAX INTEGER
		MAX-ACCESS read-write
		STATUS current
		DESCRIPTION
			"Current Login Status."
	::= { authinfo 7 }
	
accntinfo OBJECT IDENTIFIER ::=  {info802dot1x 2}

priacntipaddr OBJECT-TYPE
		SYNTAX IpAddress
		MAX-ACCESS read-write
		STATUS current
		DESCRIPTION
			"IP address of the Primary radius account server."
	::= { accntinfo 1 }

priacntport	OBJECT-TYPE
		SYNTAX INTEGER
		MAX-ACCESS read-write
		STATUS current
		DESCRIPTION
			"port number of the Primary radius account server."
	::= { accntinfo 2  }

priacntsharedsecret	OBJECT-TYPE
		SYNTAX DisplayString (SIZE(0..32))
		MAX-ACCESS read-write
		STATUS current
		DESCRIPTION
			"password used by the ap to connect to the Primary radius account serve."
	::= { accntinfo 3 }

sndacntipaddr OBJECT-TYPE
		SYNTAX IpAddress
		MAX-ACCESS read-write
		STATUS current
		DESCRIPTION
			"IP address of the Second radius account server."
	::= { accntinfo 4 }

sndacntport	OBJECT-TYPE
		SYNTAX INTEGER
		MAX-ACCESS read-write
		STATUS current
		DESCRIPTION
			"port number of the Second radius account server."
	::= { accntinfo 5  }

sndacntsharedsecret	OBJECT-TYPE
		SYNTAX DisplayString (SIZE(0..32))
		MAX-ACCESS read-write
		STATUS current
		DESCRIPTION
			"password used by the ap to connect to the Second radius account server."
	::= { accntinfo 6 }

--acntcurloginstat 	OBJECT-TYPE
--			SYNTAX TruthValue
--			MAX-ACCESS read-write
--			STATUS current
--			DESCRIPTION
--				"Current Login Status."
--		::= { accntinfo 7 }

--*********************************************************
-- Command Information
--*********************************************************
--  Command information
userCommand OBJECT IDENTIFIER ::=  {accesspoint 9}

resetAP	OBJECT-TYPE
		SYNTAX INTEGER
		MAX-ACCESS read-write
		STATUS current
		DESCRIPTION
			"This a command field for conntrol AP action.
			Write any value to reset the AP."
	::= { userCommand 1 }

setWirelessstatus OBJECT-TYPE
		SYNTAX TruthValue
		MAX-ACCESS read-write
		STATUS current
		DESCRIPTION
			"This a command field for conntrol AP's wireless card action.
			0: enable wireless card
			1: disable wireless card"
	::= { userCommand 2  }


-- **********************************************************************
-- *  System Basic Setting  Table 2004/6/17
-- **********************************************************************
timeSettings OBJECT IDENTIFIER ::=  { accesspoint 10 }

currenttime OBJECT-TYPE
		SYNTAX DisplayString ( SIZE(1..20) )
		MAX-ACCESS read-only
		STATUS current
		DESCRIPTION
			"This attributes shall indicates the current system time in a format:
			YYYY/MM/DD hh:mm:ss."
	::= { timeSettings 1 }

timezone OBJECT-TYPE
		SYNTAX INTEGER 
		{
			gmtwest12-international-date-line-west(0), gmtwest11-midway-island-samoa(1),
			gmtwest10-hawaii(2), gmtwest09-alaska(3),
			gmtwest08-pacific-time-us-canada-tijuana(4),gmtwest07-arizona(5),
			gmtwest07-chihuahua-la-paz-mazatlan(6),gmtwest07-mountain-time-us-canada(7),
			gmtwest06-central-america(8), gmtwest06-central-time-us-canada(9),
			gmtwest06-guadalajara-mexico-city-monterrey(10), gmtwest06-saskatchewan(11),
			gmtwest05-bogota-lima-quito(12),gmtwest05-eastern-time-us-canada(13),
			gmtwest05-indiana-east(14), gmtwest04-atlantic-Time-canada(15),
			gmtwest04-caracas-la-paz(16), gmtwest04-santiago(17),gmtwest03-30-newfoundland(18),
			gmtwest03-brasilia(19),gmtwest03-buenos-aires-georgetown(20),gmtwest03-greenland(21),
			gmtwest02-mid-atlantic(22),gmtwest01-azores(23),
			gmtwest01-cape-verde-is(24), gmt00-casablanca-monrovia(25),
			gmt00-greenwich-mean-time-dublin-edinburgh-lisbon-London(26),
			gmteast01-amsterdam-berlin-bern-rome-stockholm-vienna(27),
			gmteast01-belgrade-bratislava-budapest-ljubljana-prague(28),
			gmteast01-brussels-copenhagen-madrid-paris(29),gmteast01-sarajevo-skopje-warsaw-zagreb(30),
			gmteast01-west-central-africa(31),gmteast02-athens-istanbul-minsk(32),
			gmteast02-bucharest(33), gmteast02-cairo(34), gmteast02-harare-pretoria(35),
			gmteast02-helsinki-kyiv-riga-sofia-tallinn-vilnius(36),gmteast02-jerusalem(37),
			gmteast03-baghdad(38), gmteast03-kuwait-riyadh(39),
			gmteast03-moscow-st-petersburg-volgograd(40),gmteast03-nairobi(41),gmteast03-tehran(42),
			gmteast04-abu-dhabi-muscat(43),gmteast04-baku-tbilisi-yerevan(44), gmteast04-kabul(45),
			gmteast05-ekaterinburg(46),gmteast05-islamabad-karachi-kashkent(47),
			gmteast05-chennai-kolkata-mumbai-new-delhi(48), gmteast05-kathmandu(49),
			gmteast06-almaty-novosibirsk(50),gmteast06-astana-dhaka(51), gmteast06-sri-jayawardenepura(52),
			gmteast06-rangoon(53),gmteast07-bangkok-hanoi-jakarta(54),gmteast07-krasnoyarsk(55),
			gmteast08-beijing-chongqing-hong-kong-urumqi(56),gmteast08-irkutsk-ulaan-bataar(57),
			gmteast08-kuala-lumpur-singapore(58),gmteast08-perth(59), gmteast08-taipei(60),
			gmteast09-osaka-sapporo-tokyo(61),gmteast09-seoul(62),gmteast09-yakutsk(63),
			gmteast09-adelaide(64),gmteast09-darwin(65), gmteast10-brisbane(66),
			gmteast10-canberra-melbourne-sydney(67),gmteast10-guam-port-moresby(68),
			gmteast10-hobart(69), gmteast10-vladivostok(70),
			gmteast11-magadan-solomon-is-new-caledonia(71),gmteast12-auckland-wellington(72),
			gmteast12-fiji-kamchatka-marshall-is(73),gmteast13-nuku-alofa(74)
		}
		MAX-ACCESS read-write
		STATUS current
		DESCRIPTION
			"This attribute shall indicate the timezone of the system."
	::= { timeSettings 2 }

daylightsaving OBJECT-TYPE
		SYNTAX TruthValue
		MAX-ACCESS read-write
		STATUS current
		DESCRIPTION
			"This attribute shall indicate the Daylight Saving time."
	::= { timeSettings 3 }

-- **********************************************************************
-- *  DHCP Server Setting  Table 2004/6/17
-- **********************************************************************
dhcpsSettings OBJECT IDENTIFIER ::=  { accesspoint 11 }

dhcpserver 	OBJECT-TYPE
		SYNTAX TruthValue
		MAX-ACCESS read-write
		STATUS current
		DESCRIPTION
			"This attribute shall indicate whether DHCP server is enable
			or disable."
	::= { dhcpsSettings 1 }

dhcpsipstart  OBJECT-TYPE
		SYNTAX IpAddress
		MAX-ACCESS read-write
		STATUS current
		DESCRIPTION
			"This attribute indicates the starting IP address of DHCP server will give.
			***The value can only be set to a IP address in dot format."
	::= { dhcpsSettings 2 }

dhcpsipend  OBJECT-TYPE
		SYNTAX IpAddress
		MAX-ACCESS read-write
		STATUS current
		DESCRIPTION
			"This attribute indicates the ending IP address of DHCP server will give.
			***The value can only be set to a IP address in dot format."
	::= { dhcpsSettings 3 }

dhcpnetmask  OBJECT-TYPE
		SYNTAX IpAddress
		MAX-ACCESS read-write
		STATUS current
		DESCRIPTION
			"This attribute indicates the net mask of DHCP server will give.
			***The value can only be set to the net mask address in dot format."
	::= { dhcpsSettings 4 }


dhcpsgateway  OBJECT-TYPE
		SYNTAX IpAddress
		MAX-ACCESS read-write
		STATUS current
		DESCRIPTION
			"This attribute indicates the gateway IP address of DHCP server will give.
			***The value can only be set to a IP address in dot format."
	::= { dhcpsSettings 5 }

dhcpspridns OBJECT-TYPE
		SYNTAX IpAddress
		MAX-ACCESS read-write
		STATUS current
		DESCRIPTION
			"This attribute indicates the primary DNS IP address of DHCP server will give.
			***The value can only be set to a IP address in dot format."
	::= { dhcpsSettings 6 }

dhcpspsnddns OBJECT-TYPE
		SYNTAX IpAddress
		MAX-ACCESS read-write
		STATUS current
		DESCRIPTION
			"This attribute indicates the secondary DNS IP address of DHCP server will give.
			***The value can only be set to a IP address in dot format."
	::= { dhcpsSettings 7 }

dhcpspriwins OBJECT-TYPE
		SYNTAX IpAddress
		MAX-ACCESS read-write
		STATUS current
		DESCRIPTION
			"This attribute indicates the primary WINS IP address of DHCP server will give.
			***The value can only be set to a IP address in dot format."
	::= { dhcpsSettings 8 }

dhcpspsndwins OBJECT-TYPE
		SYNTAX IpAddress
		MAX-ACCESS read-write
		STATUS current
		DESCRIPTION
			"This attribute indicates the secondary WINS IP address of DHCP server will give.
			***The value can only be set to a IP address in dot format."
	::= { dhcpsSettings 9 }

dhcpsleasetime OBJECT-TYPE
		SYNTAX INTEGER (15..44640)
		MAX-ACCESS read-write
		STATUS current
		DESCRIPTION
			"This attribute shall indicate the IP lease time of DHCP server will give
			to DHCP clients in minutes"
	::= { dhcpsSettings 10 }

anyip 	OBJECT-TYPE
		SYNTAX TruthValue
		MAX-ACCESS read-write
		STATUS current
		DESCRIPTION
			"This attribute shall indicate whether AnyIP function is enable
			or disable."
	::= { dhcpsSettings 11 }

-- **********************************************************************
-- *  SYSLOG Server Setting  Table 2004/8/2
-- **********************************************************************
logSettings OBJECT IDENTIFIER ::=  { accesspoint 12 }

syslog OBJECT-TYPE
		SYNTAX TruthValue
		MAX-ACCESS read-write
		STATUS current
		DESCRIPTION
			"This attribute shall indicate whether syslog is enable 
			or disable."
	::= { logSettings 1 }

syslogsrvip OBJECT-TYPE
		SYNTAX IpAddress
		MAX-ACCESS read-write
		STATUS current
		DESCRIPTION
			"This attributes shall indicates the IP address of the syslog server.
			***The value can only be set to a IP address in dot format."	    
	::= { logSettings 2 }

syslogsrvport OBJECT-TYPE
		SYNTAX INTEGER
		MAX-ACCESS read-write
		STATUS current
		DESCRIPTION
			"This attributes shall indicates the Port of the Syslog server.
			*** The value can only be set to a port in dot format."
	::= { logSettings 3 }	

END
