Wellfleet-STA-MIB DEFINITIONS ::= BEGIN

-- Created by mdl2asn version 3.1
-- Creation date: Wed Aug 30 16:48:19 EDT 1995


    IMPORTS

      IpAddress, Counter, Gauge, TimeTicks, Opaque, enterprises, mgmt
        FROM RFC1155-SMI
      OBJECT-TYPE
        FROM RFC-1212
      TRAP-TYPE
        FROM RFC-1215
      DisplayString, mib-2
        FROM RFC1213-MIB
      wfStaGroup
        FROM Wellfleet-COMMON-MIB;


    wfSta		OBJECT IDENTIFIER ::= { wfStaGroup 1 }

    wfStaDisable OBJECT-TYPE
        SYNTAX	INTEGER {
    		    enabled(1),
    		    disabled(2)
    		}
        ACCESS	read-write
        STATUS	mandatory
        DESCRIPTION
                "Enables or disables statistical thresholds and alarms"
        DEFVAL	{ enabled }
        ::= { wfSta 1 }

    wfStaPollInterval OBJECT-TYPE
        SYNTAX	INTEGER(5..2147483647)
        ACCESS	read-write
        STATUS	mandatory
        DESCRIPTION
                "The polling interval (in seconds) in which to examine objects
                in the threshold table for threshold exceptions."
        DEFVAL	{ 60 }
        ::= { wfSta 2 }

    wfStaThresholdTable OBJECT-TYPE
        SYNTAX	SEQUENCE OF WfStaThresholdEntry
        ACCESS	not-accessible
        STATUS	mandatory
        DESCRIPTION
                "A table containing threshold targets"
        ::= { wfStaGroup 2 }

    wfStaThresholdEntry OBJECT-TYPE
        SYNTAX	WfStaThresholdEntry
        ACCESS	not-accessible
        STATUS	mandatory
        DESCRIPTION
                "Information about a particular threshold object"
        INDEX	{ wfStaThresholdObject }
        ::= { wfStaThresholdTable 1 }

    WfStaThresholdEntry ::= SEQUENCE {
    	    wfStaThresholdDelete
    		INTEGER,
    	    wfStaThresholdDisable
    		INTEGER,
    	    wfStaThresholdState
    		INTEGER,
    	    wfStaThresholdObject
    		OBJECT IDENTIFIER,
    	    wfStaThresholdLowValue
    		Gauge,
    	    wfStaThresholdLowEventLevel
    		INTEGER,
    	    wfStaThresholdMediumValue
    		Gauge,
    	    wfStaThresholdMediumEventLevel
    		INTEGER,
    	    wfStaThresholdHighValue
    		Gauge,
    	    wfStaThresholdHighEventLevel
    		INTEGER,
    	    wfStaThresholdCurrentValue
    		Gauge,
    	    wfStaThresholdUnits
    		INTEGER,
    	    wfStaThresholdAction
    		INTEGER,
    	    wfStaThresholdMaxSuccessiveAlarms
    		INTEGER,
    	    wfStaThresholdHoldDownIntervals
    		INTEGER,
    	    wfStaThresholdLowExceptions
    		Counter,
    	    wfStaThresholdLowAlarms
    		Counter,
    	    wfStaThresholdMediumExceptions
    		Counter,
    	    wfStaThresholdMediumAlarms
    		Counter,
    	    wfStaThresholdHighExceptions
    		Counter,
    	    wfStaThresholdHighAlarms
    		Counter,
    	    wfStaThresholdLabel
    		DisplayString
        }

    wfStaThresholdDelete OBJECT-TYPE
        SYNTAX	INTEGER {
    		    created(1),
    		    deleted(2)
    		}
        ACCESS	read-write
        STATUS	mandatory
        DESCRIPTION
                "The row (object) deletion attribute for this threshold"
        DEFVAL	{ created }
        ::= { wfStaThresholdEntry 1 }

    wfStaThresholdDisable OBJECT-TYPE
        SYNTAX	INTEGER {
    		    enabled(1),
    		    disabled(2)
    		}
        ACCESS	read-write
        STATUS	mandatory
        DESCRIPTION
                "The enable/disable attribute for this threshold. Setting
                this attribute to disabled, causes the threshold to be ignored
                in subsequent polling periods."
        DEFVAL	{ enabled }
        ::= { wfStaThresholdEntry 2 }

    wfStaThresholdState OBJECT-TYPE
        SYNTAX	INTEGER {
    		    valid(1),
    		    ignored(2),
    		    held(3),
    		    suspended(4),
    		    invalid(5)
    		}
        ACCESS	read-only
        STATUS	mandatory
        DESCRIPTION
                "The state of this threshold. An invalid state means that the
                object could not be retrieved from the mib.  A held state
                indicates that the maximum successive exceptions for this
                threshold has been reached and that alarms will not be
                generated until an exception occurrs at a new level or no
                exception occurs for the specified number of hold down
                intervals at which point it becomes valid again.  An ignored
                state, indicates that this threshold is disabled and is not
                being polled.  A valid state indicates that this threshold is
                under examination each polling period and no errors have been
                encountered evaluating this object for exceptions.  A
                suspended state indicates that the object was not an integer
                type; user should manually delete the suspended object."
        DEFVAL	{ valid }
        ::= { wfStaThresholdEntry 3 }

    wfStaThresholdObject OBJECT-TYPE
        SYNTAX	OBJECT IDENTIFIER
        ACCESS	read-only
        STATUS	mandatory
        DESCRIPTION
                "The identifier of the mib object to examine for threshold
                exceptions."
        ::= { wfStaThresholdEntry 4 }

    wfStaThresholdLowValue OBJECT-TYPE
        SYNTAX	Gauge
        ACCESS	read-write
        STATUS	mandatory
        DESCRIPTION
                "The mark for low threshold exceptions"
        ::= { wfStaThresholdEntry 5 }

    wfStaThresholdLowEventLevel OBJECT-TYPE
        SYNTAX	INTEGER {
    		    warning(1),
    		    info(2),
    		    debug(3)
    		}
        ACCESS	read-write
        STATUS	mandatory
        DESCRIPTION
                "The severity level of the event log message (alarm) to be
                generated on low exception"
        DEFVAL	{ info }
        ::= { wfStaThresholdEntry 6 }

    wfStaThresholdMediumValue OBJECT-TYPE
        SYNTAX	Gauge
        ACCESS	read-write
        STATUS	mandatory
        DESCRIPTION
                "The mark for medium threshold exceptions"
        ::= { wfStaThresholdEntry 7 }

    wfStaThresholdMediumEventLevel OBJECT-TYPE
        SYNTAX	INTEGER {
    		    warning(1),
    		    info(2),
    		    debug(3)
    		}
        ACCESS	read-write
        STATUS	mandatory
        DESCRIPTION
                "The severity level of the event log message (alarm) to be
                generated on medium exception"
        DEFVAL	{ info }
        ::= { wfStaThresholdEntry 8 }

    wfStaThresholdHighValue OBJECT-TYPE
        SYNTAX	Gauge
        ACCESS	read-write
        STATUS	mandatory
        DESCRIPTION
                "The mark for high threshold exceptions"
        ::= { wfStaThresholdEntry 9 }

    wfStaThresholdHighEventLevel OBJECT-TYPE
        SYNTAX	INTEGER {
    		    warning(1),
    		    info(2),
    		    debug(3)
    		}
        ACCESS	read-write
        STATUS	mandatory
        DESCRIPTION
                "The severity level of the event log message (alarm) to be
                generated on high exception"
        DEFVAL	{ info }
        ::= { wfStaThresholdEntry 10 }

    wfStaThresholdCurrentValue OBJECT-TYPE
        SYNTAX	Gauge
        ACCESS	read-only
        STATUS	mandatory
        DESCRIPTION
                "The most recently computed threshold value for the polled
                object."
        ::= { wfStaThresholdEntry 11 }

    wfStaThresholdUnits OBJECT-TYPE
        SYNTAX	INTEGER {
    		    absolute(1),
    		    persecond(2)
    		}
        ACCESS	read-write
        STATUS	mandatory
        DESCRIPTION
                "The units to be used in the determination of threshold
                exceptions.  Absolute means that when the value object reaches
                one of the three thresholds, an exception is generated.
                PerSecond means that when the value/second reaches one of the
                three threshold values, an exception is generated."
        DEFVAL	{ persecond }
        ::= { wfStaThresholdEntry 12 }

    wfStaThresholdAction OBJECT-TYPE
        SYNTAX	INTEGER {
    		    greaterthan(1),
    		    lessthan(2)
    		}
        ACCESS	read-write
        STATUS	mandatory
        DESCRIPTION
                "How the threshold should be evaluated with respect to the
                threshold marks"
        DEFVAL	{ greaterthan }
        ::= { wfStaThresholdEntry 13 }

    wfStaThresholdMaxSuccessiveAlarms OBJECT-TYPE
        SYNTAX	INTEGER
        ACCESS	read-write
        STATUS	mandatory
        DESCRIPTION
                "The maximum number of successive alarms that can be generated
                for this object before it enters a HELD state.  A successive
                alarms is defined as two or more successive polling periods
                where an alarm is generated at the same level."
        DEFVAL	{ 5 }
        ::= { wfStaThresholdEntry 14 }

    wfStaThresholdHoldDownIntervals OBJECT-TYPE
        SYNTAX	INTEGER
        ACCESS	read-write
        STATUS	mandatory
        DESCRIPTION
                "The number of exception free polling intervals which an
                object in a held state must pass before transitioning to a
                valid state."
        DEFVAL	{ 1 }
        ::= { wfStaThresholdEntry 15 }

    wfStaThresholdLowExceptions OBJECT-TYPE
        SYNTAX	Counter
        ACCESS	read-only
        STATUS	mandatory
        DESCRIPTION
                "The number of low threshold exceptions."
        ::= { wfStaThresholdEntry 16 }

    wfStaThresholdLowAlarms OBJECT-TYPE
        SYNTAX	Counter
        ACCESS	read-only
        STATUS	mandatory
        DESCRIPTION
                "The number of low threshold alarms."
        ::= { wfStaThresholdEntry 17 }

    wfStaThresholdMediumExceptions OBJECT-TYPE
        SYNTAX	Counter
        ACCESS	read-only
        STATUS	mandatory
        DESCRIPTION
                "The number of medium threshold exceptions."
        ::= { wfStaThresholdEntry 18 }

    wfStaThresholdMediumAlarms OBJECT-TYPE
        SYNTAX	Counter
        ACCESS	read-only
        STATUS	mandatory
        DESCRIPTION
                "The number of medium threshold alarms."
        ::= { wfStaThresholdEntry 19 }

    wfStaThresholdHighExceptions OBJECT-TYPE
        SYNTAX	Counter
        ACCESS	read-only
        STATUS	mandatory
        DESCRIPTION
                "The number of high threshold exceptions."
        ::= { wfStaThresholdEntry 20 }

    wfStaThresholdHighAlarms OBJECT-TYPE
        SYNTAX	Counter
        ACCESS	read-only
        STATUS	mandatory
        DESCRIPTION
                "The number of high threshold alarms."
        ::= { wfStaThresholdEntry 21 }

    wfStaThresholdLabel OBJECT-TYPE
        SYNTAX	DisplayString
        ACCESS	read-write
        STATUS	mandatory
        DESCRIPTION
                "The threshold lable string configurable by user.
                The string would be returned in the trap and will
                show in the log as string wfSyncRxOctets.2.1 instead
                of the ASN.1 form."
        ::= { wfStaThresholdEntry 22 }

    END  -- Wellfleet-STA-MIB
