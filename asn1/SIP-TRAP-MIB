SIP-TRAP-MIB DEFINITIONS ::= BEGIN
IMPORTS
    enterprises, Counter
        FROM RFC1155-SMI
    OBJECT-TYPE
        FROM RFC-1212
    DisplayString
        FROM RFC1213-MIB
    NOTIFICATION-TYPE, MODULE-IDENTITY, ObjectName, Integer32, Counter32, snmpModules
        FROM SNMPv2-SMI
    reason, timeOccurred, code, csID, csType, registrationStatus, gwID, comment, percent, moduleID, port, gwIP, gwType
        FROM AGGREGATED-EXT-MIB
    TruthValue, DisplayString, TestAndIncr, TimeStamp, RowStatus
        FROM SNMPv2-TC;


	lucent		    OBJECT IDENTIFIER  ::=  {  enterprises  1751  }
	products	    OBJECT IDENTIFIER  ::=  {  lucent  1  }
	softSwitch	    OBJECT IDENTIFIER  ::=  {  products 1198  }
	sipDeviceServer OBJECT IDENTIFIER  ::=  {  softSwitch 5 }


	-- The traps group. Listed below are the traps currently
	-- supported by this device server  

sipTraps  MODULE-IDENTITY    
        LAST-UPDATED "240701"
        ORGANIZATION "Lucent Technologies"    
        CONTACT-INFO 
                ""    
        DESCRIPTION
                "The MIB module for entities implementing the xxxx
                protocol."  

::=  {  sipDeviceServer 0 }


	sipCSConnectionStatus NOTIFICATION-TYPE
		OBJECTS { timeOccurred, code, csID, csType, registrationStatus, reason, comment }
        STATUS current
		DESCRIPTION
             		"Indicates the registration status of the device 
			server(registered, unregistered or registration 
			failed).
       			VARIABLE DEFINITIONS:
			1) timeStamp - time when the alarm occured, in 
			<sec>.<usec> format
			2) code - bitwise OR of severity, facility, errorCode,
			instanceID, severity<<28 | facility<<24 | 
			errorCode<<16 | instanceid
			3) csID - call server identifier which will be 
			returned by the call server when any device server 
			registers to it.
			4) csType - call server type, 'primary' or 'secondary'.
			(Right now this information does not come from the 
			call server. It is set to 'primary'.) value = 0 for
			primary, value = 1 for secondary
			5) registrationStatus - registered | unregistred |
			registrationFailed depending on whether the device 
			server is registered, unregistered or could not 
			register to the call server respectively.
			6) reason - {unreachable | unknown | 
			invalidParam}, indicates the cause for the 
			registration failure. 
			7) comment - Any comment sent along with this trap.
 			Severity: INFO for registration/unregistration.
                       	CRITICAL for failed registration."
      		 ::= { sipTraps 0 }

	sipDSError NOTIFICATION-TYPE
       		OBJECTS { timeOccurred, code, reason, comment }
            STATUS current
       		DESCRIPTION
              		"When any error occurs in the device server. 
       			VARIABLE DEFINITIONS:
			1) timeStamp - time when the alarm occured, in 
			<sec>.<usec> format
			2) code - bitwise OR of severity, facility, errorCode,
			instanceID, severity<<28 | facility<<24 | 
			errorCode<<16 | instanceid
			3) reason - the reason for the error that occurs 
			in the device server. Takes one of these values:
			internalError | systemResourceUnavailable |
			unknown 
			4) comment - Any comment sent along with this trap.
			Severity: INFO (internalError), 
			MAJOR (systemResourceUnavailable),
                       	INFO (unknownError - any other errors)."
	       ::= { sipTraps 1 }

	sipCommandFailed NOTIFICATION-TYPE 
       		OBJECTS { timeOccurred, code, reason, comment }
            STATUS current
       		DESCRIPTION 
             		"Triggered when any request is failed by the 
			device server. 		
			VARIABLE DEFINITIONS:
			1) timeStamp - time when the alarm occured, in 
			<sec>.<usec> format
			2) code - bitwise OR of severity, facility, errorCode,
			instanceID, severity<<28 | facility<<24 | 
			errorCode<<16 | instanceid
			3) reason -  reason for the failure of the command. 
			{internalError | systemResourceUnavailable 
			| notSupported | unknown }
     			4) comment - Any comment sent along with this trap.
			Severity: MINOR (or may be command sensitive)."

       		::= { sipTraps 2 }


	
END
