PICTURETEL-VCS-SYSSTAT-MIB DEFINITIONS ::= BEGIN

IMPORTS
	MODULE-IDENTITY, OBJECT-TYPE, OBJECT-IDENTITY, Gauge32
FROM SNMPv2-SMI
	TimeStamp, DisplayString, TEXTUAL-CONVENTION
FROM SNMPv2-TC
	ptSystemStatistics
FROM PICTURETEL-VCS-MIB;

pictureTelVCSSystemStatisticsModule MODULE-IDENTITY
	LAST-UPDATED "0101030000Z"
	ORGANIZATION "PictureTel Corporation"
	CONTACT-INFO
		"
		Postal:	PictureTel Corporation
				100 Minuteman Drive
				Andover, MA 01810-1031
				USA"
	DESCRIPTION
		"Final version"
	REVISION	"0101030000Z"
	DESCRIPTION
		"Rev 0.0.08
		3 Jan 2001 12:00  
		Latest version of MIB module PICTURETEL-VCS-SYSSTAT-MIB"

 ::= { ptSystemStatistics 1 }



--
-- Textual Convention used in this module
--

CallStateType ::= TEXTUAL-CONVENTION
	STATUS	current
	DESCRIPTION
		"Enumerated type representing the current state of the call"
	SYNTAX INTEGER {
		idleinitial(0),
		address(1),
		dialing(2),
		ringing(3),
		connecting(4),
		active(5),
		reconnecting(6),
		incoming(7),
		disconnecting(8),
		gateway(9),
		idlefinal(10)
		}


--
-- System Statistics placeholders
--

ptSysCommonStat             OBJECT-IDENTITY
	STATUS          current
	DESCRIPTION     "Subtree for common statistics"
	::= { pictureTelVCSSystemStatisticsModule 1 }


ptSysH320CallStat           OBJECT-IDENTITY
	STATUS          current
	DESCRIPTION     "Subtree for H.320 video statistics"
	::= { pictureTelVCSSystemStatisticsModule 2 }


ptSysH323CallStat           OBJECT-IDENTITY
	STATUS          current
	DESCRIPTION     "Subtree for H.323 audio statistics"
	::= { pictureTelVCSSystemStatisticsModule 3 }


ptSysVoiceOnlyCallStat      OBJECT-IDENTITY
	STATUS          current
	DESCRIPTION     "Subtree for voice-only statistics"
	::= { pictureTelVCSSystemStatisticsModule 4 }


ptSystemVersions      OBJECT-IDENTITY
	STATUS          current
	DESCRIPTION     "Subtree for system versions"
	::= { pictureTelVCSSystemStatisticsModule 5 }



--
-- Common System Statistics
--

ptTotalCameraCommands  OBJECT-TYPE
	SYNTAX Gauge32
	MAX-ACCESS	read-only
	STATUS          current
	DESCRIPTION     " Number of commands sent to the local camera"
	::= { ptSysCommonStat 1 }

ptTotalIRKeyCommands  OBJECT-TYPE
	SYNTAX Gauge32
	MAX-ACCESS	read-only
	STATUS          current
	DESCRIPTION     " Number of commands sent from the IR Keyboard"
	::= { ptSysCommonStat 2 }


 ptTimeSinceSAPIStartup  OBJECT-TYPE
	SYNTAX TimeStamp
	MAX-ACCESS	read-only
	STATUS          current
	DESCRIPTION     " Total time since SAPI was started"
	::= { ptSysCommonStat 3 }


 ptTimeInCallsSinceSAPIStartup  OBJECT-TYPE
	SYNTAX TimeStamp
	MAX-ACCESS	read-only
	STATUS          current
	DESCRIPTION     " Time system was in the call since SAPI was started"
	::= { ptSysCommonStat 4 }


ptTimeInCallsSinceSysCreation  OBJECT-TYPE
	SYNTAX TimeStamp
	MAX-ACCESS	read-only
	STATUS          current
	DESCRIPTION     " Time system was in the call since system creation"
	::= { ptSysCommonStat 5 }


ptTimeInVoiceOnlyCallsSinceSAPIStartup  OBJECT-TYPE
	SYNTAX TimeStamp
	MAX-ACCESS	read-only
	STATUS          current
	DESCRIPTION     " Time system was in the voice-only call since 
	                  SAPI startup"
	::= { ptSysCommonStat 6 }


ptTimeInVoiceOnlyCallsSinceSysCreation  OBJECT-TYPE
	SYNTAX TimeStamp
	MAX-ACCESS	read-only
	STATUS          current
	DESCRIPTION     " Time system was in the voice-only call since 
	                  system creation"
	::= { ptSysCommonStat 7 }


--
-- H.320 Call System Statistics
--

ptTotalH320CallsPlaced  OBJECT-TYPE
	SYNTAX Gauge32
	MAX-ACCESS read-only
	STATUS          current
	DESCRIPTION     " Total number of H.320 calls placed"
	::= { ptSysH320CallStat 1 }


 ptTotalH320CallsReceived  OBJECT-TYPE
	SYNTAX Gauge32
	MAX-ACCESS read-only
	STATUS          current
	DESCRIPTION     " Total number of H.320 calls received"
	::= { ptSysH320CallStat 2 }



ptH320CallState  OBJECT-TYPE
	SYNTAX CallStateType
	MAX-ACCESS read-only
	STATUS          current
	DESCRIPTION     " Current or most recent H.320 call state"
	::= { ptSysH320CallStat 3 }



ptH320CallDuration  OBJECT-TYPE
	SYNTAX Gauge32
	MAX-ACCESS read-only
	STATUS          current
	DESCRIPTION     " Current or most recent H.320 call duration (sec)"
	::= { ptSysH320CallStat 4 }


--
-- H.323 Call System Statistics
--

ptTotalH323CallsPlaced  OBJECT-TYPE
	SYNTAX Gauge32
	MAX-ACCESS read-only
	STATUS          current
	DESCRIPTION     " Total number of H.323 calls placed"
	::= { ptSysH323CallStat 1 }


ptTotalH323CallsReceived  OBJECT-TYPE
	SYNTAX Gauge32
	MAX-ACCESS	read-only
	STATUS          current
	DESCRIPTION     " Total number of H.323 calls received"
	::= { ptSysH323CallStat 2 }


ptH323CallState  OBJECT-TYPE
	SYNTAX CallStateType
	MAX-ACCESS read-only
	STATUS          current
	DESCRIPTION     " Current or most recent H.323 call state"
	::= { ptSysH323CallStat 3 }


ptH323CallDuration  OBJECT-TYPE
	SYNTAX Gauge32
	MAX-ACCESS read-only
	STATUS          current
	DESCRIPTION     " Current or most recent H.323 call duration (sec)"
	::= { ptSysH323CallStat 4 }


--
-- Voice Only Call System Statistics
--

ptTotalVoiceOnlyCallsPlaced  OBJECT-TYPE
	SYNTAX Gauge32
	MAX-ACCESS read-only
	STATUS          current
	DESCRIPTION     " Total number of voice-only calls placed"
	::= { ptSysVoiceOnlyCallStat 1 }


ptTotalVoiceOnlyCallsReceived  OBJECT-TYPE
	SYNTAX Gauge32
	MAX-ACCESS	read-only
	STATUS          current
	DESCRIPTION     " Total number of voice-only calls received"
	::= { ptSysVoiceOnlyCallStat 2 }


ptVoiceOnlyCallState  OBJECT-TYPE
	SYNTAX CallStateType
	MAX-ACCESS read-only
	STATUS          current
	DESCRIPTION     " Current or most recent voice-only call state"
	::= { ptSysVoiceOnlyCallStat 3 }


ptVoiceOnlyCallDuration  OBJECT-TYPE
	SYNTAX Gauge32
	MAX-ACCESS read-only
	STATUS          current
	DESCRIPTION     " Current or most recent voice-only call duration (sec)"
	::= { ptSysVoiceOnlyCallStat 4 }


--
-- System Versions
--

ptVCSVersion  OBJECT-TYPE
	SYNTAX DisplayString
	MAX-ACCESS read-only
	STATUS          current
	DESCRIPTION     "Current VCS version"
	::= { ptSystemVersions 1 }


ptPlatformVersions      OBJECT-TYPE
	SYNTAX DisplayString
	MAX-ACCESS read-only
	STATUS          current
	DESCRIPTION     "Current version of the aggregate of all 
	                 non-PictureTel software (OS, Video Drivers,
	                 Productivity software,...)"
	::= { ptSystemVersions 2 }


ptVCSRemoteManagementVersion  OBJECT-TYPE
	SYNTAX DisplayString
	MAX-ACCESS read-only
	STATUS          current
	DESCRIPTION     "Current version of Remote Management"
	::= { ptSystemVersions 3 }


ptH323CoreVersion  OBJECT-TYPE
	SYNTAX DisplayString
	MAX-ACCESS read-only
	STATUS          current
	DESCRIPTION     "Current version of H.323 Core"
	::= { ptSystemVersions 4 }



END
