--
--  Title:  Appian-SYSTEM-MIB
--
--  Date:   11/14/99
--
--  Description:
--
--  This file contains the ASN.1 MIB definition for system related 
--  services on the OSAP platform.  Services include, Configuration Manager,
--  Event Logging, Statistics Collection, Alarms and Thresholds and the OSAP 
--  Discovery and Topology protocol.
--
--  The mib also includes a few high density scalars used by AppianVista
--  status poller.
--
APPIAN-SYSTEM-MIB DEFINITIONS ::= BEGIN
    IMPORTS
        acOsap, AcNodeId, AcAdminStatus,
        AcOpStatus, AcNodeArchitecture                  FROM APPIAN-SMI-MIB

        acChassisRingId, acChassisCurrentTime           FROM APPIAN-CHASSIS-MIB

        MODULE-IDENTITY, OBJECT-TYPE, 
        NOTIFICATION-TYPE, IpAddress,
        Gauge32                                         FROM SNMPv2-SMI
        
        TEXTUAL-CONVENTION, DisplayString,
        TruthValue, DateAndTime, MacAddress             FROM SNMPv2-TC;


acSystem  MODULE-IDENTITY
    LAST-UPDATED    "9911140000Z"
    
    ORGANIZATION    "Appian Communications, Inc."

    CONTACT-INFO    "Douglas Theriault"

    DESCRIPTION     "Appian Communications Services MIB definitions file
                     containing configuration and statistics control for
                     system related services.  These services include 
                     Configuration Management, Event Logging, Statistics 
                     Collection, Alarms and Thresholds configuration, OSAP
                     discovery and topology protocol."

    REVISION        "9911140000Z"
    
    DESCRIPTION     "Draft engineering version.  Not for release."

        ::= { acOsap 7 }



--
-- System MIB Hierarchy
--
acCommMgr               OBJECT IDENTIFIER ::= { acSystem 1 }
acStatsMgr              OBJECT IDENTIFIER ::= { acSystem 2 } 
acEventMgr              OBJECT IDENTIFIER ::= { acSystem 3 }
acConfigMgr             OBJECT IDENTIFIER ::= { acSystem 4 }
acSntpMgr               OBJECT IDENTIFIER ::= { acSystem 7 }
acAuthMgr               OBJECT IDENTIFIER ::= { acSystem 8 }
acTrapMgr               OBJECT IDENTIFIER ::= { acSystem 9 }
acFileXferMgr           OBJECT IDENTIFIER ::= { acSystem 10 }
acRdpMgr                OBJECT IDENTIFIER ::= { acSystem 11 }

--
-- Community manager
--

    AcAccessRights ::= TEXTUAL-CONVENTION
    STATUS current
    DESCRIPTION "Community access rights:
                 - readOnly: allows read access to all MIB tables with the
                   exception of acCommMgrCommTable and acCommMgrSourceAddrTable.
                 - readWrite: if there are no configured communities with
                   security access rights, it allows read and write access to all
                   MIB tables. However, if there is a security community configured,
                   a community with readWrite access rights will not have
                   read access to acCommMgrCommTable and acCommMgrSourceAddrTable,
                   and it will not have write access to acCommMgrCommTable,
                   acCommMgrSourceAddrTable, acTrapMgrDestAddrTable and
                   acTrapMgrFilterTable.
                 - security allows read-write access to all MIB tables."
    SYNTAX INTEGER
    {
        readOnly(1),
        readWrite(2),
        security(3)
    }

acCommMgrCommTable OBJECT-TYPE
    SYNTAX SEQUENCE OF AcCommMgrCommEntry
    MAX-ACCESS not-accessible
    STATUS current
    DESCRIPTION "Table for configuring community strings and community
                 access rights."
    ::= { acCommMgr 1 }
    
acCommMgrCommEntry OBJECT-TYPE
    SYNTAX AcCommMgrCommEntry
    MAX-ACCESS not-accessible
    STATUS current
    DESCRIPTION "Entry of community table."
    INDEX
    {
        acCommMgrCommNodeId,
        acCommMgrCommId
    }
    ::= { acCommMgrCommTable 1 }
    
    AcCommMgrCommEntry ::= SEQUENCE
    {
        acCommMgrCommNodeId                    AcNodeId,
        acCommMgrCommId                        INTEGER,
        acCommMgrCommAdminStatus               AcAdminStatus,
        acCommMgrCommString                    DisplayString,
        acCommMgrCommAccessRights              AcAccessRights
    }
        
acCommMgrCommNodeId OBJECT-TYPE
    SYNTAX AcNodeId
    MAX-ACCESS accessible-for-notify
    STATUS current
    DESCRIPTION "Unique identification number of this node within an
                 Appian ring."
    ::= { acCommMgrCommEntry 1 }
    
acCommMgrCommId OBJECT-TYPE
    SYNTAX INTEGER
    MAX-ACCESS accessible-for-notify
    STATUS current
    DESCRIPTION "Number that uniquely identifies a community."
    ::= { acCommMgrCommEntry 2 }
    
acCommMgrCommAdminStatus OBJECT-TYPE
    SYNTAX AcAdminStatus
    MAX-ACCESS read-create
    STATUS current
    DESCRIPTION "The administrative status. See AcAdminStatus for the
                 semantics."
    ::= { acCommMgrCommEntry 3 }
    
acCommMgrCommString OBJECT-TYPE
    SYNTAX DisplayString (SIZE(0..32))
    MAX-ACCESS read-create
    STATUS current
    DESCRIPTION "String that uniquely identifies a community."
    ::= { acCommMgrCommEntry 4 }
    
acCommMgrCommAccessRights OBJECT-TYPE
    SYNTAX AcAccessRights
    MAX-ACCESS read-create
    STATUS current
    DESCRIPTION "Community access rights. See AcAccessRights for the
                 semantics."
    ::= { acCommMgrCommEntry 5 }

acCommMgrSourceAddrTable OBJECT-TYPE
    SYNTAX SEQUENCE OF AcCommMgrSourceAddrEntry
    MAX-ACCESS not-accessible
    STATUS current
    DESCRIPTION "Table that specifies valid SNMP request source IP
                 addresses and/or subnets for the different communities."
    ::= { acCommMgr 2 }
    
acCommMgrSourceAddrEntry OBJECT-TYPE
    SYNTAX AcCommMgrSourceAddrEntry
    MAX-ACCESS not-accessible
    STATUS current
    DESCRIPTION "Entry that specifies a valid SNMP request source IP
                 address or subnet for a given community."
    INDEX
    {
        acCommMgrSourceAddrNodeId,
        acCommMgrSourceAddrCommId,
        acCommMgrSourceAddrIpAddress
    }
    ::= { acCommMgrSourceAddrTable 1 }
    
    AcCommMgrSourceAddrEntry ::= SEQUENCE
    {
        acCommMgrSourceAddrNodeId                    AcNodeId,
        acCommMgrSourceAddrCommId                    INTEGER,
        acCommMgrSourceAddrIpAddress                 IpAddress,
        acCommMgrSourceAddrIpSubnet                  IpAddress,
        acCommMgrSourceAddrAdminStatus               AcAdminStatus
    }
    
acCommMgrSourceAddrNodeId OBJECT-TYPE
    SYNTAX AcNodeId
    MAX-ACCESS accessible-for-notify
    STATUS current
    DESCRIPTION "Unique identification number of this node within an
                 Appian ring."
    ::= { acCommMgrSourceAddrEntry 1 }
    
acCommMgrSourceAddrCommId OBJECT-TYPE
    SYNTAX INTEGER
    MAX-ACCESS accessible-for-notify
    STATUS current
    DESCRIPTION "Number that uniquely identifies a community."
    ::= { acCommMgrSourceAddrEntry 2 }
    
acCommMgrSourceAddrIpAddress OBJECT-TYPE
    SYNTAX IpAddress
    MAX-ACCESS accessible-for-notify
    STATUS current
    DESCRIPTION "Valid source IP address for SNMP requests of this
                 community. All source IP addresses are valid for a given
                 community if there are no entries in acCommMgrSourceAddrTable
                 for this community with acCommMgrSourceAddrAdminStatus
                 equal to activate"
    ::= { acCommMgrSourceAddrEntry 3 }
    
acCommMgrSourceAddrIpSubnet OBJECT-TYPE
    SYNTAX IpAddress
    MAX-ACCESS read-create
    STATUS current
    DESCRIPTION "Subnet mask for valid source IP subnet for SNMP
                 requests of this community."
    ::= { acCommMgrSourceAddrEntry 4 }
    
acCommMgrSourceAddrAdminStatus OBJECT-TYPE
    SYNTAX AcAdminStatus
    MAX-ACCESS read-create
    STATUS current
    DESCRIPTION "The administrative status. See AcAdminStatus for the
                 semantics."
    ::= { acCommMgrSourceAddrEntry 5 }


--
-- Statistics Collection Manager
--
acStatsMgrTable  OBJECT-TYPE
    SYNTAX  SEQUENCE OF AcStatsMgrEntry
    MAX-ACCESS  not-accessible
    STATUS  current
    DESCRIPTION
    "A table of statistics manager configuration parameters which is indexed
    by AcNodeId."
    
    ::= { acStatsMgr 1 }
    
acStatsMgrEntry  OBJECT-TYPE
    SYNTAX  AcStatsMgrEntry
    MAX-ACCESS  not-accessible
    STATUS  current
    DESCRIPTION
    "The configuration and status parameters controlling the Statistics Manager
    service on this specific node."
    
    INDEX { acStatsMgrNodeId }
    
    ::= { acStatsMgrTable 1 }
    
    AcStatsMgrEntry ::=
        SEQUENCE {
            acStatsMgrNodeId                    AcNodeId,
            acStatsMgrAdminStatus               AcAdminStatus
        }

acStatsMgrNodeId  OBJECT-TYPE
    SYNTAX  AcNodeId
    MAX-ACCESS  accessible-for-notify
    STATUS  current
    DESCRIPTION
    "The unique node identification number assigned by the EMS system to uniquely
    identify this node within an Appian ring of OSAP's."
    
    ::= { acStatsMgrEntry 1 }

acStatsMgrAdminStatus  OBJECT-TYPE
    SYNTAX  AcAdminStatus
    MAX-ACCESS  read-write
    STATUS      current
    DESCRIPTION
    "The administrative status. See AcAdminStatus for the semantics."

    DEFVAL { inactivate }

    ::= { acStatsMgrEntry 2 }

--
-- EventLog Manager
--

acEventMgrControlTable  OBJECT-TYPE
    SYNTAX  SEQUENCE OF AcEventMgrControlEntry
    MAX-ACCESS  not-accessible
    STATUS  current
    DESCRIPTION
    "A table of configuration parameters controlling the event manager.  The
    event manager is responsible for logging security and application state
    changes generated on a node.  These events are stored in non-volitile 
    memory and may be sent as traps to the EMS system."
    
    ::= { acEventMgr 1 }

acEventMgrControlEntry  OBJECT-TYPE
    SYNTAX  AcEventMgrControlEntry
    MAX-ACCESS  not-accessible
    STATUS  current
    DESCRIPTION
    "The configuration and status parameters controlling the Event Logging
    Manager service on this specific node."
    
    INDEX { acEventMgrControlNodeId }
    
    ::= { acEventMgrControlTable 1 }

    AcEventMgrControlEntry ::=
        SEQUENCE {
            acEventMgrControlNodeId                        AcNodeId,
            acEventMgrControlAdminStatus                   AcAdminStatus,
            acEventMgrControlLogMode                       INTEGER,
            acEventMgrControlLogMaxFileSize                INTEGER,
            acEventMgrControlLogCurrentSize                INTEGER,
            acEventMgrControlLogFileName                   DisplayString,
            acEventMgrControlLogFileWrapEnable             TruthValue,
            acEventMgrControlSecurityLogMode               INTEGER,
            acEventMgrControlSecurityLogMaxFileSize        INTEGER,
            acEventMgrControlSecurityLogCurrentSize        INTEGER,
            acEventMgrControlSecurityLogFileName           DisplayString,
            acEventMgrControlSecurityLogFileWrapEnable     TruthValue,
            acEventMgrControlRedirectTraceSlot1            TruthValue,
            acEventMgrControlRedirectTraceSlot2            TruthValue
        }
        
acEventMgrControlNodeId  OBJECT-TYPE
    SYNTAX  AcNodeId
    MAX-ACCESS  accessible-for-notify
    STATUS  current
    DESCRIPTION
    "The unique node identification number assigned by the EMS system to uniquely
    identify this node within an Appian ring of OSAP's."
        
    ::= { acEventMgrControlEntry 1 }

acEventMgrControlAdminStatus    OBJECT-TYPE
    SYNTAX  AcAdminStatus
    MAX-ACCESS  read-write
    STATUS  deprecated
    DESCRIPTION
    "The administrative status. See AcAdminStatus for the semantics."
    DEFVAL { activate }

    ::= { acEventMgrControlEntry 2 }

acEventMgrControlLogMode    OBJECT-TYPE
   SYNTAX  INTEGER {
                off(1),
                flash-only(2)
           }
    MAX-ACCESS  read-write
    STATUS  current
    DESCRIPTION
    "There are two kinds of logs in OSAP: regular log, and security log.
    This is the attribute to control the mode of operation of the regular event log.
    The regular event log can be configured to write to flash, or it can be disabled.
    When disabled, the event manager will keep a record of events in memory, 
    which are available to the local CLI/TL1 but are not persistant."
    DEFVAL { flash-only }

    ::= { acEventMgrControlEntry 3 }
        
acEventMgrControlLogMaxFileSize    OBJECT-TYPE
    SYNTAX  INTEGER (10..1024)
    MAX-ACCESS  read-write
    STATUS      current
    DESCRIPTION
    "The size of the regular event log on the file system measured in k-bytes."
    DEFVAL { 512 }

    ::= { acEventMgrControlEntry 4 }

acEventMgrControlLogCurrentSize    OBJECT-TYPE
    SYNTAX      INTEGER
    MAX-ACCESS  read-only
    STATUS      current
    DESCRIPTION
    "The current size of the regular event log measured in k-bytes."

    ::= { acEventMgrControlEntry 5 }

acEventMgrControlLogFileName   OBJECT-TYPE
    SYNTAX      DisplayString (SIZE (0..32))
    MAX-ACCESS  read-only
    STATUS      current
    DESCRIPTION
    "The name of the binary regular log file."

    ::= { acEventMgrControlEntry 6 }

acEventMgrControlLogFileWrapEnable   OBJECT-TYPE
    SYNTAX      TruthValue
    MAX-ACCESS  read-write
    STATUS      deprecated
    DESCRIPTION
    "When set to true, tells the event log manager to wrap the regular event log file
    when it has reached the maximum size.  Oldest log entries are overwritten
    first when a wrap condition is reached."
    DEFVAL { true }

    ::= { acEventMgrControlEntry 7 }

acEventMgrControlSecurityLogMode    OBJECT-TYPE
   SYNTAX  INTEGER {
                off(1),
                flash-only(2)
            }
    MAX-ACCESS  read-write
    STATUS      current
    DESCRIPTION
    "There are two kinds of logs in OSAP: regular log, and security log.
    This is the attribute to control the mode of operation of the security event log.
    The security event log can be configured to write to flash, or it can be disabled.
    When disabled, the event manager will keep a record of events in memory, 
    which are available to the local CLI/TL1 but are not persistant."
    DEFVAL { flash-only }

    ::= { acEventMgrControlEntry 8 }

acEventMgrControlSecurityLogMaxFileSize    OBJECT-TYPE
    SYNTAX  INTEGER (10..1024)
    MAX-ACCESS  read-write
    STATUS      current
    DESCRIPTION
    "The size of the regular security log on the file system measured in k-bytes."
    DEFVAL { 512 }

    ::= { acEventMgrControlEntry 9 }

acEventMgrControlSecurityLogCurrentSize    OBJECT-TYPE
    SYNTAX      INTEGER
    MAX-ACCESS  read-only
    STATUS      current
    DESCRIPTION
    "The current size of the security event log measured in k-bytes."

    ::= { acEventMgrControlEntry 10 }

acEventMgrControlSecurityLogFileName   OBJECT-TYPE
    SYNTAX      DisplayString (SIZE (0..32))
    MAX-ACCESS  read-only
    STATUS      current
    DESCRIPTION
    "The name of the binary security log file."

    ::= { acEventMgrControlEntry 11 }

acEventMgrControlSecurityLogFileWrapEnable   OBJECT-TYPE
    SYNTAX      TruthValue
    MAX-ACCESS  read-write
    STATUS      deprecated
    DESCRIPTION
    "When set to true, tells the event log manager to wrap the security event log file
    when it has reached the maximum size.  Oldest log entries are overwritten
    first when a wrap condition is reached."
    DEFVAL { true }

    ::= { acEventMgrControlEntry 12 }

acEventMgrControlRedirectTraceSlot1   OBJECT-TYPE
    SYNTAX      TruthValue
    MAX-ACCESS  read-write
    STATUS      current
    DESCRIPTION
    "When set to true, events that originate in slot 1 and would otherwise be displayed
    on the global standard output (console or telnet session) of slot 1, will instead be
    displayed on the global standard output of the master switch."
    DEFVAL { false }

    ::= { acEventMgrControlEntry 13 }

acEventMgrControlRedirectTraceSlot2   OBJECT-TYPE
    SYNTAX      TruthValue
    MAX-ACCESS  read-write
    STATUS      current
    DESCRIPTION
    "When set to true, events that originate in slot 2 and would otherwise be displayed
    on the global standard output (console or telnet session) of slot 2, will instead be
    displayed on the global standard output of the master switch."
    DEFVAL { false }

    ::= { acEventMgrControlEntry 14 }

--
-- 
acEventMgrAgentTable OBJECT-TYPE
    SYNTAX  SEQUENCE OF AcEventMgrAgentEntry
    MAX-ACCESS  not-accessible
    STATUS      current
    DESCRIPTION
    "This table provides configuration on a per agent basis for the handling
    of event messages from each agent.  This table is automatically created
    by the system and does not need to be generated by the EMS."

    ::= { acEventMgr 2 }

acEventMgrAgentEntry OBJECT-TYPE
    SYNTAX           AcEventMgrAgentEntry
    MAX-ACCESS       not-accessible
    STATUS           current
    DESCRIPTION
    "A row per entity which allows for configuration settings on how eventlog
    messages generated by this entity are stored and reported for the EMS."
    
    INDEX { acEventMgrAgentNodeId, acEventMgrAgentSlot, acEventMgrAgentId }

    ::= { acEventMgrAgentTable 1 }

    AcEventMgrAgentEntry ::=
        SEQUENCE {
            acEventMgrAgentNodeId                   AcNodeId,
            acEventMgrAgentId                       INTEGER,
            acEventMgrAgentName                     DisplayString,
            acEventMgrAgentAdminStatus              AcAdminStatus,
            acEventMgrAgentLogLevel                 INTEGER,
            acEventMgrAgentNumberEvents             INTEGER,
            acEventMgrAgentLastEventCode            INTEGER,
            acEventMgrAgentLastEventCount           INTEGER,
            acEventMgrAgentSlot                     INTEGER,
            acEventMgrAgentTraceLevel               INTEGER
        }

--
-- Event Mgr Agent Entry Record
--

acEventMgrAgentNodeId  OBJECT-TYPE
    SYNTAX  AcNodeId
    MAX-ACCESS  accessible-for-notify
    STATUS  current
    DESCRIPTION
    "A unique node identification number which uniquely identifies a node
    within an Appian ring of OSAPs."
    
    ::= { acEventMgrAgentEntry 1 }
    
acEventMgrAgentId   OBJECT-TYPE
    SYNTAX  INTEGER {
                kernel(1),
                common(2),
                msgsvc(3),
                fwdmgr(4),
                iasmgr(5),
                tlsmgr(6),
                cfgmgr(7),
                almmgr(8),
                clisvc(9),
                tl1svc(10),
                enetaccess(11),
                system(12),
                enetIME(13),
                ds1Tdm(14),
                ds3Tdm(15),
                ds3Net(16),
                oc3Net(17),
                ppp(18),
                tta(19),
                asrt(20),
                fr(21),
                sntp(22),
                bpm(23),
                snmp(24),
                telnet(25),
                serial(26),
                statsmgr(27),
                appiandcc(28),
                excep(29),
                mgmtapi(30),
                lpta(31),
                scmctrl(32),
                sonet(33),
                temux(34),
                qos(35),
                service(36),
                mlc(37),
                hdlc(38),
                modmgr(39),
                scpplt(40),
                clkdrv(41),
                plc(42),
                mach(43),
                enetagg(44),
                eventmgr(45),
                mgmtrem(46),
                rdp(47),
                loader(48)
            }
    MAX-ACCESS      accessible-for-notify
    STATUS          current
    DESCRIPTION
    "The acEventMgrAgentId identifies the agent which will be logging events
    within the event manager subsystem.  The enumeration list of these well
    known ID's are published and used by the EMS in decoding the event log
    information for which agent has recorded an event."

    ::= { acEventMgrAgentEntry 2 }
        
acEventMgrAgentName OBJECT-TYPE
    SYNTAX      DisplayString (SIZE (1..16))
    MAX-ACCESS  read-only
    STATUS      current
    DESCRIPTION
    "An ASCII name of the well known agent, sutible for display."

    ::= { acEventMgrAgentEntry 3 }

acEventMgrAgentAdminStatus  OBJECT-TYPE
    SYNTAX      AcAdminStatus
    MAX-ACCESS  read-write
    STATUS      deprecated
    DESCRIPTION
    "The administrative status. See AcAdminStatus for the semantics."
    DEFVAL { activate }

    ::= { acEventMgrAgentEntry 4 }

acEventMgrAgentLogLevel  OBJECT-TYPE
    SYNTAX  INTEGER (0..16383)
    MAX-ACCESS  read-write
    STATUS      current
    DESCRIPTION
    "The logging level at which this entity will generate events destined for
    the event log manager.  Currently this value is a bit mask allowing the
    user to select which types of events to store in the log. The bit mask values
    are selected as follows based on the position of the bit:

                critical(1),    -- Critical means needs immediate attn. 
                major(2),       -- The resources may be exhausted soon.
                minor(4),       -- Early indication of resource exhaustion. 
                warning(8),     -- Warnings, non-fatal.
                info(16),       -- Informational event.
                debug(32),      -- Used for debugging only.
                cleared(64),    -- An alarm is being cleared.
                security-critical(128),    -- Security log - Critical means needs immediate attn. 
                security-major(256),       -- Security log - The resources may be exhausted soon.
                security-minor(512),       -- Security log - Early indication of resource exhaustion. 
                security-warning(1024),    -- Security log - Warnings, non-fatal.
                security-info(2048),       -- Security log - Informational event.
                security-debug(4096),      -- Security log - Used for debugging only.
                security-cleared(8192)     -- Security log - An alarm is being cleared.

    The mask is generated as a logical OR of the values defined above."

    ::= { acEventMgrAgentEntry 5 }

acEventMgrAgentNumberEvents OBJECT-TYPE
    SYNTAX  INTEGER
    MAX-ACCESS  read-only
    STATUS      deprecated
    DESCRIPTION
    "The total number of events this entity has generated on this slot."

    ::= { acEventMgrAgentEntry 6 }

acEventMgrAgentLastEventCode  OBJECT-TYPE
    SYNTAX  INTEGER
    MAX-ACCESS  read-only
    STATUS      deprecated
    DESCRIPTION
    "The last event ID which was generated by this entity on this slot."

    ::= { acEventMgrAgentEntry 7 }

acEventMgrAgentLastEventCount OBJECT-TYPE
    SYNTAX  INTEGER
    MAX-ACCESS  read-only
    STATUS      deprecated
    DESCRIPTION
    "The number of times the last event ID has been generated on this slot.
    Helpful in keeping a running count of the last event in the case of
    repeating errors."

    ::= { acEventMgrAgentEntry 8 }

acEventMgrAgentSlot  OBJECT-TYPE
    SYNTAX  INTEGER(1..4)
    MAX-ACCESS  accessible-for-notify
    STATUS      current
    DESCRIPTION
    "The slot number where the configuration of this row will be applied."

    ::= { acEventMgrAgentEntry 9 }

acEventMgrAgentTraceLevel  OBJECT-TYPE
    SYNTAX  INTEGER (0..16383)
    MAX-ACCESS  read-write
    STATUS      current
    DESCRIPTION
    "Specifies what types of events originated by this entity will be displayed on the
    standard global output as traces. Currently this value is a bit mask allowing the
    user to select which types of events to display. The bit mask values are selected
    as follows based on the position of the bit:

                critical(1),    -- Critical means needs immediate attn. 
                major(2),       -- The resources may be exhausted soon.
                minor(4),       -- Early indication of resource exhaustion. 
                warning(8),     -- Warnings, non-fatal.
                info(16),       -- Informational event.
                debug(32),      -- Used for debugging only.
                cleared(64),    -- An alarm is being cleared.
                security-critical(128),    -- Security log - Critical means needs immediate attn. 
                security-major(256),       -- Security log - The resources may be exhausted soon.
                security-minor(512),       -- Security log - Early indication of resource exhaustion. 
                security-warning(1024),    -- Security log - Warnings, non-fatal.
                security-info(2048),       -- Security log - Informational event.
                security-debug(4096),      -- Security log - Used for debugging only.
                security-cleared(8192)     -- Security log - An alarm is being cleared.

    The mask is generated as a logical OR of the values defined above."

    ::= { acEventMgrAgentEntry 10 }

-- 
-- Event Logger Trap Definitions
--
--

acEventMgrTraps   OBJECT IDENTIFIER ::= { acEventMgr 0 }

acEventMgrLogFullTrap  NOTIFICATION-TYPE
    OBJECTS { 
        acChassisCurrentTime, acChassisRingId,
        acEventMgrControlNodeId, 
        acEventMgrControlLogCurrentSize 
    } 
    STATUS  deprecated
    DESCRIPTION
    "The event log is over 90% full and wrapping is not enabled."
    
    ::= { acEventMgrTraps 1 }
    
acEventMgrSecurityLogFullTrap  NOTIFICATION-TYPE
    OBJECTS { 
        acChassisCurrentTime, acChassisRingId,
        acEventMgrControlNodeId, 
        acEventMgrControlSecurityLogCurrentSize 
    } 
    STATUS  deprecated
    DESCRIPTION
    "The security log is over 90% full and wrapping is not enabled."
    
    ::= { acEventMgrTraps 2 }

acEventMgrLogFileCloseFailedTrap  NOTIFICATION-TYPE
    OBJECTS { 
        acChassisCurrentTime, acChassisRingId,
        acEventMgrControlNodeId, 
        acEventMgrControlLogFileName 
    } 
    STATUS  deprecated
    DESCRIPTION
    "The regular log file couldn't be closed."
    
    ::= { acEventMgrTraps 3 }

acEventMgrSecurityLogFileCloseFailedTrap  NOTIFICATION-TYPE
    OBJECTS { 
        acChassisCurrentTime, acChassisRingId,
        acEventMgrControlNodeId, 
        acEventMgrControlSecurityLogFileName 
    } 
    STATUS  deprecated
    DESCRIPTION
    "The security log file couldn't be closed."
    
    ::= { acEventMgrTraps 4 }


--
-- Configuration Manager
--
acConfigMgrTable  OBJECT-TYPE
    SYNTAX  SEQUENCE OF AcConfigMgrEntry
    MAX-ACCESS  not-accessible
    STATUS  current
    DESCRIPTION
    "The configuration manager configuration parameters in a table which is 
    indexed by a unique AcNodeId."
    
    ::= { acConfigMgr 1 }
    
acConfigMgrEntry  OBJECT-TYPE
    SYNTAX  AcConfigMgrEntry
    MAX-ACCESS  not-accessible
    STATUS  current
    DESCRIPTION
    "Single record per node which contains the configuration parameters for
    the configuration manager agent.  This row is automatically created by
    the agent upon system initialization."
    
    INDEX { acConfigMgrNodeId }
    
    ::= { acConfigMgrTable 1 }
    
    AcConfigMgrEntry ::=
        SEQUENCE {
            acConfigMgrNodeId                       AcNodeId,
            acConfigMgrAdminStatus                  AcAdminStatus,
            acConfigMgrCurrentRevision              INTEGER,
            acConfigMgrFileName                     DisplayString,
            acConfigMgrAutoSaveInterval             INTEGER,
            acConfigMgrAutoSaveEnable               TruthValue,
            acConfigMgrLastWritten                  DateAndTime,
            acConfigMgrSaveConfig                   TruthValue,
            acConfigMgrOpStatus                     INTEGER
        }
            
--
-- Config Manager Entry Record
--            

acConfigMgrNodeId  OBJECT-TYPE
    SYNTAX  AcNodeId
    MAX-ACCESS  accessible-for-notify
    STATUS  current
    DESCRIPTION
    "A unique number assigned by the EMS which uniquely identifies a node
    within an Appian ring of OSAP's."
    
    ::= { acConfigMgrEntry 1 }
    
acConfigMgrAdminStatus    OBJECT-TYPE
    SYNTAX  AcAdminStatus
    MAX-ACCESS  read-write
    STATUS      current
    DESCRIPTION
    "The administrative status. See AcAdminStatus for the semantics."
    DEFVAL { inactivate }

    ::= { acConfigMgrEntry 2 }
    
acConfigMgrCurrentRevision    OBJECT-TYPE
    SYNTAX  INTEGER
    MAX-ACCESS  read-only
    STATUS      current
    DESCRIPTION
    "The numeric revision number for the configuration file.  This number is
    Appian specific and not an RCS type revision for the file, but instead an
    internal software revision of the file format."

    ::= { acConfigMgrEntry 3 }

acConfigMgrFileName    OBJECT-TYPE
    SYNTAX  DisplayString   (SIZE (0..32))
    MAX-ACCESS  read-only
    STATUS      current
    DESCRIPTION
    "The name of the configuration file. When the system boots, this config file
    is expected to be on the file system and will be the file that
    the system uses for normal operation."
    DEFVAL { "config.dat" }

    ::= { acConfigMgrEntry 4 }

acConfigMgrAutoSaveInterval   OBJECT-TYPE
    SYNTAX  INTEGER (5..60)
    MAX-ACCESS  read-write
    STATUS      current
    DESCRIPTION
    "The number of seconds after a provisioning change when the config
    file is updated with the current state of configuration for this node.
    The acConfigMgrAutoSaveEnable flag must be set to true(1) for auto-save to take
    place."
    DEFVAL { 20 }

    ::= { acConfigMgrEntry 5 }

acConfigMgrAutoSaveEnable OBJECT-TYPE
    SYNTAX  TruthValue
    MAX-ACCESS  read-write
    STATUS      current
    DESCRIPTION
    "When set to true(1), the configuration manager will perform an update
    operation on the configuration file after 'n' seconds from the
    last provisioning change, specified by acConfigMgrAutoSaveInterval.  Enabling 
    this feature allows the EMS to assume
    the platform is in sync with a recent dynamic provisioning change, vs. 
    sending down a new configuration file."

    DEFVAL { false }

    ::= { acConfigMgrEntry 6 }

acConfigMgrLastWritten    OBJECT-TYPE
    SYNTAX  DateAndTime
    MAX-ACCESS  read-only
    STATUS      current
    DESCRIPTION
    "The last time the configuration file was updated automatically."

    ::= { acConfigMgrEntry 7 }

acConfigMgrSaveConfig OBJECT-TYPE
    SYNTAX  TruthValue
    MAX-ACCESS  read-write
    STATUS      current
    DESCRIPTION
    "When set to true(1), the configuration manager will perform an update
    operation on the configuration file immediately."

    DEFVAL { false }

    ::= { acConfigMgrEntry 8 }

acConfigMgrOpStatus    OBJECT-TYPE
   SYNTAX  INTEGER {
                succeeded(1),
                failed(2),
                writing(3)
            }
    MAX-ACCESS  read-only
    STATUS      current
    DESCRIPTION
    "This attribute indicates the configuration file save status when 
    acConfigMgrSaveConfig is set."
    DEFVAL { succeeded }

    ::= { acConfigMgrEntry 9 }

-- 
-- Configuration Manager Trap Definitions
--
--

acConfigMgrTraps   OBJECT IDENTIFIER ::= { acConfigMgr 0 }

acConfigMgrConfigFileCloseFailedTrap  NOTIFICATION-TYPE
    OBJECTS { 
        acChassisCurrentTime, acChassisRingId,
        acConfigMgrNodeId, 
        acConfigMgrFileName 
    } 
    STATUS  current
    DESCRIPTION
    "The configuration file couldn't be closed."
    
    ::= { acConfigMgrTraps 1 }

--
-- SNTP Client Configuration Record
--
acSntpMgrTable OBJECT-TYPE
    SYNTAX  SEQUENCE OF AcSntpMgrEntry
    MAX-ACCESS  not-accessible
    STATUS  current
    DESCRIPTION
    "The SNTP Manager is responsible for controlling the SNTP client agent
    on the SCP.  The SNTP client will peer with a time server which itself may
    peer with a higher stratum clock or a radio receiver."
    
    ::= { acSntpMgr 1 }
    
acSntpMgrEntry OBJECT-TYPE
    SYNTAX  AcSntpMgrEntry
    MAX-ACCESS  not-accessible
    STATUS  current
    DESCRIPTION
    "A configuration record for the SNTP client agent."
    
    INDEX { acSntpMgrNodeId }
    
    ::= { acSntpMgrTable 1 }
    
    AcSntpMgrEntry ::=
        SEQUENCE {
            acSntpMgrNodeId                     AcNodeId,
            acSntpMgrAdminStatus                AcAdminStatus,
            acSntpMgrOpStatus                   AcOpStatus,
            acSntpMgrErrorCode                  INTEGER,
            acSntpMgrPeerIpAddress              IpAddress,
            acSntpMgrQueryInterval              INTEGER,
            acSntpMgrRetryCount                 INTEGER,
            acSntpMgrMaxVariance                INTEGER,
            acSntpMgrVariance                   INTEGER,
            acSntpMgrVarianceDetectEnable       TruthValue,
            acSntpMgrTimeZone                   INTEGER,
            acSntpMgrDayLightSaving             TruthValue
        }
        
--
-- SNTP Configuration Record
--
acSntpMgrNodeId OBJECT-TYPE
    SYNTAX  AcNodeId
    MAX-ACCESS  accessible-for-notify
    STATUS  current
    DESCRIPTION    
    "A unique identifier assigned by the EMS which uniquely identifies a node
    within an Appian ring of OSAP's."
    
    ::= { acSntpMgrEntry 1 }

acSntpMgrAdminStatus    OBJECT-TYPE
    SYNTAX  AcAdminStatus
    MAX-ACCESS  read-write
    STATUS  current
    DESCRIPTION
    "Attribute allowing enable/disabling control of the SNTP agent for 
    provisioning changes.  Refer to AcAdminStatus definition in appian-smi.mib."
        
    ::= { acSntpMgrEntry 2 }
    
acSntpMgrOpStatus   OBJECT-TYPE
    SYNTAX  AcOpStatus
    MAX-ACCESS  read-only        
    STATUS  current
    DESCRIPTION
    "Attribute which describes the current operational status of the SNTP
    client agent.  Refer to AcOpStatus definition in appian-smi.mib."
    
    ::= { acSntpMgrEntry 3 }
    
acSntpMgrErrorCode  OBJECT-TYPE
    SYNTAX  INTEGER
    MAX-ACCESS  read-only        
    STATUS  current
    DESCRIPTION
    "If an error is reported in acSntpMgrOpStatus, this attribute will contain
    a detailed error code which can be referenced to determine the cause of a
    problem.  The eventlog will also contain the failure reason."
    
    ::= { acSntpMgrEntry 4 }
    
acSntpMgrPeerIpAddress  OBJECT-TYPE
    SYNTAX  IpAddress
    MAX-ACCESS  read-write    
    STATUS  current
    DESCRIPTION
    "The configured IP Address in dotted notation which SNTP uses to perform
    NTP queries against.  The peer should be a Stratum-2 or greater clock."

    ::= { acSntpMgrEntry 5 }
    
acSntpMgrQueryInterval  OBJECT-TYPE
    SYNTAX  INTEGER (5..3600)
    MAX-ACCESS  read-write    
    STATUS  current
    DESCRIPTION
    "The interval expressed in the number of seconds between NTP Query requests."

    DEFVAL { 60 }

    ::= { acSntpMgrEntry 6 }
    
acSntpMgrRetryCount OBJECT-TYPE
    SYNTAX  INTEGER
    MAX-ACCESS  read-write    
    STATUS  current
    DESCRIPTION
    "The number of query attempts the SNTP client should perform before reporting
    that the SNTP client cannot communicate with the peer."

    DEFVAL { 3 }
        
    ::= { acSntpMgrEntry 7 }
    
acSntpMgrMaxVariance  OBJECT-TYPE
    SYNTAX  INTEGER (1..7200000)
    MAX-ACCESS  read-write
    STATUS  current
    DESCRIPTION
    "The variance expressed as the number of milliseconds between client and 
    peer which will trigger an alarm.  This is useful in determining if the 
    historical data recorded in NOVRAM for statistics trending or timestamps 
    used for traps is outside the configured variance parameter."

    DEFVAL { 1000 }
        
    ::= { acSntpMgrEntry 8 }

acSntpMgrVariance  OBJECT-TYPE
    SYNTAX  INTEGER
    MAX-ACCESS  read-only
    STATUS  current
    DESCRIPTION
    "The amount of time expressed as the number of milliseconds delta between 
    client and peer."
    
    ::= { acSntpMgrEntry 9 }
        
acSntpMgrVarianceDetectEnable  OBJECT-TYPE
    SYNTAX  TruthValue
    MAX-ACCESS  read-write
    STATUS  current
    DESCRIPTION
    "Used to enable or disable variance threshold alarms."

    DEFVAL { false }
        
    ::= { acSntpMgrEntry 10 }

acSntpMgrTimeZone   OBJECT-TYPE
    SYNTAX          INTEGER (0..23)
    MAX-ACCESS      read-write
    STATUS          current
    DESCRIPTION
    "The time zone this node is currently located in, expressed as
    an integer ranging from 0 to 23, representing the 24 hr time-
    zones starting at UTC which is equal to 0 and proceeding in
    the positive westerly direction. ie: Boston = 5, California=8.
    Note:  Daylight savings time is not automatically calculated."
    DEFVAL { 0 }

    ::= { acSntpMgrEntry 11 }

acSntpMgrDayLightSaving   OBJECT-TYPE
    SYNTAX      TruthValue
    MAX-ACCESS  read-write
    STATUS      current
    DESCRIPTION
    "It specifies if daylight saving time is applicable."
    DEFVAL { false }

    ::= { acSntpMgrEntry 12 }

--
-- SNTP Trap Definitions
--
acSntpMgrTraps  OBJECT IDENTIFIER ::= { acSntpMgr 0 }

acSntpMgrPeerFailureTrap  NOTIFICATION-TYPE
    OBJECTS { 
        acChassisCurrentTime, acChassisRingId,
        acSntpMgrNodeId, 
        acSntpMgrPeerIpAddress 
    }
    STATUS  current
    DESCRIPTION
    "The SNTP Client is unable to communicate with the NTP Server which 
    has been configured."
    
    ::= { acSntpMgrTraps 1 }
    
acSntpMgrVarianceTrap  NOTIFICATION-TYPE
    OBJECTS { 
        acChassisCurrentTime, acChassisRingId,
        acSntpMgrNodeId, 
        acSntpMgrMaxVariance, 
        acSntpMgrVariance 
    }
    STATUS  current
    DESCRIPTION
    "The difference in time between client and peer exceeds the configured
    variance."
    
    ::= { acSntpMgrTraps 2 }

acSntpMgrHardwareTrap  NOTIFICATION-TYPE
    OBJECTS { 
        acChassisCurrentTime, acChassisRingId,
        acSntpMgrNodeId, 
        acSntpMgrErrorCode 
    }
    STATUS  current
    DESCRIPTION
    "The SNTP Client was unable to read or write the hardware clock."
    
    ::= { acSntpMgrTraps 3 }
    
--
-- Authentication Tracking Table
--
acAuthMgrTable OBJECT-TYPE
    SYNTAX  SEQUENCE OF AcAuthMgrEntry
    MAX-ACCESS  not-accessible
    STATUS  current
    DESCRIPTION
    "The Authentication Manager is responsible for tracking who is logged into
    the system and how many success or failure events have occured for a unique
    user.  As users log off the system they will be removed from the table."

    ::= { acAuthMgr 1 }
    
acAuthMgrEntry OBJECT-TYPE
    SYNTAX  AcAuthMgrEntry
    MAX-ACCESS  not-accessible
    STATUS  current
    DESCRIPTION
    "A single row within the authentication table tracking a single user session
    which can be via telnet, serial, rlogin or ftp."
    
    INDEX { acAuthMgrNodeId, acAuthMgrUserId }
    
    ::= { acAuthMgrTable 1 }

    AcAuthMgrEntry ::=
        SEQUENCE {
            acAuthMgrNodeId                     AcNodeId,
            acAuthMgrUserId                     INTEGER,
            acAuthMgrUserName                   DisplayString,
            acAuthMgrAccessMode                 INTEGER,
            acAuthMgrLogonTime                  DateAndTime,
            acAuthMgrFailures                   INTEGER,
            acAuthMgrLockOut                    TruthValue,
            acAuthMgrDeleteEntry                TruthValue
        }
        
acAuthMgrNodeId OBJECT-TYPE
    SYNTAX  AcNodeId
    MAX-ACCESS  accessible-for-notify
    STATUS  current
    DESCRIPTION
    "A unique number within an Appian Ring identifying the node for which the
    user is logged into."
    
    ::= { acAuthMgrEntry 1 }

acAuthMgrUserId OBJECT-TYPE
    SYNTAX  INTEGER
    MAX-ACCESS  accessible-for-notify
    STATUS  current
    DESCRIPTION
    "A unique identifier within an Appian node which is used to identify
    the user currently attempting to gain access to the system."
    
    ::= { acAuthMgrEntry 2 }

acAuthMgrUserName OBJECT-TYPE
    SYNTAX  DisplayString (SIZE(4..16))
    MAX-ACCESS  read-only
    STATUS  current
    DESCRIPTION
    "A unique identifier within an Appian node which is used to identify
    the user currently attempting to gain access to the system."
    
    ::= { acAuthMgrEntry 3 }
    
acAuthMgrAccessMode  OBJECT-TYPE
    SYNTAX  INTEGER {
                unknown(0),
                serial(1),
                telnet(2),
                rlogin(3),
                ftp(4)
            }
    MAX-ACCESS  read-only
    STATUS  current
    DESCRIPTION
    "The current access method for this user."
    
    ::= { acAuthMgrEntry 4 }
    
acAuthMgrLogonTime  OBJECT-TYPE
    SYNTAX  DateAndTime
    MAX-ACCESS  read-only
    STATUS  current
    DESCRIPTION
    "The logon time this user was given access."
    
    ::= { acAuthMgrEntry 5 }
    
acAuthMgrFailures OBJECT-TYPE
    SYNTAX  INTEGER
    MAX-ACCESS  read-only
    STATUS current
    DESCRIPTION
    "The total number of logon attempts for a user who was given access
    to the system and who is currently still logged in, or the failure
    attempts for a user who attempted to gain access but did not."
    
    ::= { acAuthMgrEntry 6 }
    
acAuthMgrLockOut  OBJECT-TYPE
    SYNTAX  TruthValue
    MAX-ACCESS  read-only
    STATUS  current
    DESCRIPTION
    "This field will read true(1) when the max number of failures has been
    reached for an attempted logon using the user name listed in this row."
    
    ::= { acAuthMgrEntry 7 }
    
acAuthMgrDeleteEntry  OBJECT-TYPE
    SYNTAX  TruthValue
    MAX-ACCESS  read-write
    STATUS  current
    DESCRIPTION
    "Used to delete rows in this table."

    ::= { acAuthMgrEntry 8 }

--
-- Trap manager
--

acTrapMgrDestAddrTable OBJECT-TYPE
    SYNTAX SEQUENCE OF AcTrapMgrDestAddrEntry
    MAX-ACCESS not-accessible
    STATUS current
    DESCRIPTION "Table that specifies trap destination IP addresses for the
                 different communities."
    ::= { acTrapMgr 1 }
    
acTrapMgrDestAddrEntry OBJECT-TYPE
    SYNTAX AcTrapMgrDestAddrEntry
    MAX-ACCESS not-accessible
    STATUS current
    DESCRIPTION "Entry that specifies, for a given community, an IP address
                 to send traps to."
    INDEX
    {
        acTrapMgrDestAddrNodeId,
        acTrapMgrDestAddrCommId,
        acTrapMgrDestAddrIpAddress
    }
    ::= { acTrapMgrDestAddrTable 1 }
    
    AcTrapMgrDestAddrEntry ::= SEQUENCE
    {
        acTrapMgrDestAddrNodeId                    AcNodeId,
        acTrapMgrDestAddrCommId                    INTEGER,
        acTrapMgrDestAddrIpAddress                 IpAddress,
        acTrapMgrDestAddrAdminStatus               AcAdminStatus
    }
    
acTrapMgrDestAddrNodeId OBJECT-TYPE
    SYNTAX AcNodeId
    MAX-ACCESS accessible-for-notify
    STATUS current
    DESCRIPTION "Unique identification number of this node within an
                 Appian ring."
    ::= { acTrapMgrDestAddrEntry 1 }
    
acTrapMgrDestAddrCommId OBJECT-TYPE
    SYNTAX INTEGER
    MAX-ACCESS accessible-for-notify
    STATUS current
    DESCRIPTION "Number that uniquely identifies a community."
    ::= { acTrapMgrDestAddrEntry 2 }
    
acTrapMgrDestAddrIpAddress OBJECT-TYPE
    SYNTAX IpAddress
    MAX-ACCESS accessible-for-notify
    STATUS current
    DESCRIPTION "IP address to send traps to."
    ::= { acTrapMgrDestAddrEntry 3 }
    
acTrapMgrDestAddrAdminStatus OBJECT-TYPE
    SYNTAX AcAdminStatus
    MAX-ACCESS read-create
    STATUS current
    DESCRIPTION "The administrative status. See AcAdminStatus for the
                 semantics."
    ::= { acTrapMgrDestAddrEntry 4 }

acTrapMgrFilterTable OBJECT-TYPE
    SYNTAX SEQUENCE OF AcTrapMgrFilterEntry
    MAX-ACCESS not-accessible
    STATUS current
    DESCRIPTION "Table that lists, for the different communities, the
                 traps that these communities don't want to receive."
    ::= { acTrapMgr 2 }
    
acTrapMgrFilterEntry OBJECT-TYPE
    SYNTAX AcTrapMgrFilterEntry
    MAX-ACCESS not-accessible
    STATUS current
    DESCRIPTION "This entry specifies a trap type (by OID) that the
                 specified community is not interested in receiving."
    INDEX
    {
        acTrapMgrFilterNodeId,
        acTrapMgrFilterCommId,
        acTrapMgrFilterId
    }
    ::= { acTrapMgrFilterTable 1 }
    
    AcTrapMgrFilterEntry ::= SEQUENCE
    {
        acTrapMgrFilterNodeId                    AcNodeId,
        acTrapMgrFilterCommId                    INTEGER,
        acTrapMgrFilterId                        INTEGER,
        acTrapMgrFilterAdminStatus               AcAdminStatus,
        acTrapMgrFilterTrapOid                   OBJECT IDENTIFIER
    }
    
acTrapMgrFilterNodeId OBJECT-TYPE
    SYNTAX AcNodeId
    MAX-ACCESS accessible-for-notify
    STATUS current
    DESCRIPTION "Unique identification number of this node within an
                 Appian ring."
    ::= { acTrapMgrFilterEntry 1 }
    
acTrapMgrFilterCommId OBJECT-TYPE
    SYNTAX INTEGER
    MAX-ACCESS accessible-for-notify
    STATUS current
    DESCRIPTION "Number that uniquely identifies a community."
    ::= { acTrapMgrFilterEntry 2 }
    
acTrapMgrFilterId OBJECT-TYPE
    SYNTAX INTEGER
    MAX-ACCESS accessible-for-notify
    STATUS current
    DESCRIPTION "Number that, for the given node and community, uniquely
                 identifies this filter."
    ::= { acTrapMgrFilterEntry 3 }
    
acTrapMgrFilterAdminStatus OBJECT-TYPE
    SYNTAX AcAdminStatus
    MAX-ACCESS read-create
    STATUS current
    DESCRIPTION "The administrative status. See AcAdminStatus for the
                 semantics."
    ::= { acTrapMgrFilterEntry 4 }
    
acTrapMgrFilterTrapOid OBJECT-TYPE
    SYNTAX OBJECT IDENTIFIER
    MAX-ACCESS read-create
    STATUS current
    DESCRIPTION "Object identifier that identifies the trap type that
                 will not be sent to the given community."
    ::= { acTrapMgrFilterEntry 5 }

acTrapMgrResendTable OBJECT-TYPE
    SYNTAX SEQUENCE OF AcTrapMgrResendEntry
    MAX-ACCESS not-accessible
    STATUS current
    DESCRIPTION "Table that allows a management system to request traps
                 to be resent. Only the last 100 traps generated by the
                 OSAP will be stored."
    ::= { acTrapMgr 3 }
    
acTrapMgrResendEntry OBJECT-TYPE
    SYNTAX AcTrapMgrResendEntry
    MAX-ACCESS not-accessible
    STATUS current
    DESCRIPTION "Setting this entry triggers the specified traps to be
                 resent to the destination IP address specified."
    INDEX
    {
        acTrapMgrResendNodeId
    }
    ::= { acTrapMgrResendTable 1 }
    
    AcTrapMgrResendEntry ::= SEQUENCE
    {
        acTrapMgrResendNodeId                    AcNodeId,
        acTrapMgrResendAdminStatus               AcAdminStatus,
        acTrapMgrResendFromSeqId                 INTEGER,
        acTrapMgrResendToSeqId                   INTEGER
    }
    
acTrapMgrResendNodeId OBJECT-TYPE
    SYNTAX AcNodeId
    MAX-ACCESS accessible-for-notify
    STATUS current
    DESCRIPTION "Unique identification number of this node within an
                 Appian ring."
    ::= { acTrapMgrResendEntry 1 }
    
acTrapMgrResendAdminStatus OBJECT-TYPE
    SYNTAX AcAdminStatus
    MAX-ACCESS read-write
    STATUS current
    DESCRIPTION "The administrative status. See AcAdminStatus for the
                 semantics."
    ::= { acTrapMgrResendEntry 2 }
    
acTrapMgrResendFromSeqId OBJECT-TYPE
    SYNTAX INTEGER
    MAX-ACCESS read-write
    STATUS current
    DESCRIPTION "Beginning of trap sequence number interval of traps
                 to resend."
    ::= { acTrapMgrResendEntry 3 }
    
acTrapMgrResendToSeqId OBJECT-TYPE
    SYNTAX INTEGER
    MAX-ACCESS read-write
    STATUS current
    DESCRIPTION "End of trap sequence number interval of traps
                 to resend. If acTrapMgrResendToSeqId is the same as
                 acTrapMgrResendFromSeqId, then only 1 trap is sent."
    ::= { acTrapMgrResendEntry 4 }

--
-- Appian Enterprise Traps
--
acAuthMgrTraps  OBJECT IDENTIFIER ::= { acAuthMgr 0 }

acAuthenticationFailureTrap NOTIFICATION-TYPE
    OBJECTS {
        acChassisCurrentTime, acChassisRingId,
        acAuthMgrNodeId,
        acAuthMgrUserName,
        acAuthMgrAccessMode,
        acAuthMgrFailures
        }
    STATUS current
    DESCRIPTION
    "Access denied due to a Logon Authentication failure."
    
    ::= { acAuthMgrTraps 1 }

acAuthenticationExceededTrap NOTIFICATION-TYPE
    OBJECTS {
        acChassisCurrentTime, acChassisRingId,
        acAuthMgrNodeId,
        acAuthMgrUserName,
        acAuthMgrAccessMode,
        acAuthMgrFailures
        }
    STATUS current
    DESCRIPTION
    "The maximum number of authentication failure attempts has been 
    exceeded.  Access has been denied."
    
    ::= { acAuthMgrTraps 2 }
    
acAuthenticationSuccessTrap NOTIFICATION-TYPE
    OBJECTS {
        acChassisCurrentTime, acChassisRingId,
        acAuthMgrNodeId,
        acAuthMgrUserName,
        acAuthMgrAccessMode
        }
    STATUS current
    DESCRIPTION
    "Successful logon by user."
    
    ::= { acAuthMgrTraps 3 }

--
-- File Transfer Manager 
--

acFileXferMgrTable OBJECT-TYPE
    SYNTAX  SEQUENCE OF AcFileXferMgrEntry
    MAX-ACCESS  not-accessible
    STATUS      current
    DESCRIPTION
    "This table contains file transfer operation information. This table is created
     during the initialization of the system. The EMS does not create new rows
     in it."

    ::= { acFileXferMgr 1 }

acFileXferMgrEntry OBJECT-TYPE
    SYNTAX           AcFileXferMgrEntry
    MAX-ACCESS       not-accessible
    STATUS           current
    DESCRIPTION
    "Each row in this table indicates a file transfer operation."
    
    INDEX { acFileXferMgrNodeId, acFileXferMgrRowId }

    ::= { acFileXferMgrTable 1 }

    AcFileXferMgrEntry ::=
        SEQUENCE {
            acFileXferMgrNodeId               AcNodeId,
            acFileXferMgrRowId                INTEGER,
            acFileXferMgrAdminStatus          AcAdminStatus,
            acFileXferMgrOperation            INTEGER,
            acFileXferMgrFiletype             INTEGER,
            acFileXferMgrFilesubtype          INTEGER,
            acFileXferMgrFtpServerIpAddress   IpAddress,
            acFileXferMgrUsername             DisplayString,
            acFileXferMgrPassword             DisplayString,
            acFileXferMgrSourceDirectory      DisplayString,
            acFileXferMgrSourceFilename       DisplayString,
            acFileXferMgrDestDirectory        DisplayString,
            acFileXferMgrDestFilename         DisplayString,
            acFileXferMgrXferMode             INTEGER,
            acFileXferMgrOpStatus             INTEGER
        }

--
-- File Transfer Mgr Agent Entry Record
--

acFileXferMgrNodeId  OBJECT-TYPE
    SYNTAX  AcNodeId
    MAX-ACCESS  accessible-for-notify
    STATUS  current
    DESCRIPTION
    "A unique node identification number which uniquely identifies a node
    within an Appian ring of OSAPs."
    
    ::= { acFileXferMgrEntry 1 }
    
acFileXferMgrRowId   OBJECT-TYPE
    SYNTAX  INTEGER (1..5)
    MAX-ACCESS      accessible-for-notify
    STATUS          current
    DESCRIPTION
    "The acFileXferMgrRowId identifies the row index of the table."

    ::= { acFileXferMgrEntry 2 }
        
acFileXferMgrAdminStatus  OBJECT-TYPE
    SYNTAX      AcAdminStatus
    MAX-ACCESS  read-write
    STATUS      current
    DESCRIPTION
    "The administrative status. See AcAdminStatus for the semantics."
    DEFVAL { inactivate }

    ::= { acFileXferMgrEntry 3 }

acFileXferMgrOperation   OBJECT-TYPE
    SYNTAX  INTEGER {
                     upload(1),
                     download(2)
                    }
    MAX-ACCESS      read-write
    STATUS          current
    DESCRIPTION
    "The operation type. The upload and download indicate the direction
    of the file transfer from the perspective of the OSAP. A download is an ftp 
    get from the ftp server, and an upload is an ftp put to the ftp server."
    DEFVAL { download }

    ::= { acFileXferMgrEntry 4 }

acFileXferMgrFiletype   OBJECT-TYPE
    SYNTAX  INTEGER {
                     image(1),
                     eventlog(2),
                     config(3),
                     generic(4)
                    }
    MAX-ACCESS      read-write
    STATUS          current
    DESCRIPTION
    "This attribute indicates whether a binary image, or a binary event log, 
     a textual configuration file or any other file is being transferred."
    DEFVAL { image }

    ::= { acFileXferMgrEntry 5 }

acFileXferMgrFilesubtype   OBJECT-TYPE
    SYNTAX  INTEGER {
                     primaryimage(1),
                     namedbootimage(2),
                     regularlog(3),
                     securitylog(4),
                     none(5)
                    }
    MAX-ACCESS      read-write
    STATUS          current
    DESCRIPTION
    "This attribute indicates what type of file it is."
    DEFVAL { primaryimage }

    ::= { acFileXferMgrEntry 6 }

acFileXferMgrFtpServerIpAddress OBJECT-TYPE
    SYNTAX      IpAddress
    MAX-ACCESS  read-write
    STATUS      current
    DESCRIPTION
    "The IP Address of the ftp server from where the file is being transferred."

    ::= { acFileXferMgrEntry 7 }

acFileXferMgrUsername OBJECT-TYPE
    SYNTAX      DisplayString (SIZE (0..32))
    MAX-ACCESS  read-write
    STATUS      current
    DESCRIPTION
    "The user name to be used for the ftp login authentication. This is optional. If
    not supplied, the default value is used."
    DEFVAL { "anonymous" }

    ::= { acFileXferMgrEntry 8 }

acFileXferMgrPassword OBJECT-TYPE
    SYNTAX      DisplayString (SIZE (0..32))
    MAX-ACCESS  read-write
    STATUS      current
    DESCRIPTION
    "The password to be used for the ftp login authentication. This is optional. If
    not supplied, the default value is used, which is the chassis name of the OSAP. 
    When supplied, the password is in the clear-text form."

    ::= { acFileXferMgrEntry 9 }

acFileXferMgrSourceDirectory OBJECT-TYPE
    SYNTAX      DisplayString (SIZE (0..100))
    MAX-ACCESS  read-write
    STATUS      current
    DESCRIPTION
    "The name of the source directory for the file transfer operation."

    ::= { acFileXferMgrEntry 10 }

acFileXferMgrSourceFilename OBJECT-TYPE
    SYNTAX      DisplayString (SIZE (0..32))
    MAX-ACCESS  read-write
    STATUS      current
    DESCRIPTION
    "The name of the source file for the file transfer operation."

    ::= { acFileXferMgrEntry 11 }

acFileXferMgrDestDirectory OBJECT-TYPE
    SYNTAX      DisplayString (SIZE (0..100))
    MAX-ACCESS  read-write
    STATUS      current
    DESCRIPTION
    "The name of the destination directory for the file transfer operation."

    ::= { acFileXferMgrEntry 12 }

acFileXferMgrDestFilename OBJECT-TYPE
    SYNTAX      DisplayString (SIZE (0..32))
    MAX-ACCESS  read-write
    STATUS      current
    DESCRIPTION
    "The name of the destination file for the file transfer operation."

    ::= { acFileXferMgrEntry 13 }

acFileXferMgrXferMode   OBJECT-TYPE
    SYNTAX  INTEGER {
                     ascii(1),
                     binary(2)
                    }
    MAX-ACCESS      read-write
    STATUS          current
    DESCRIPTION
    "This attribute indicates the mode of the transfer: ascii or binary."
    DEFVAL { binary }

    ::= { acFileXferMgrEntry 14 }


acFileXferMgrOpStatus   OBJECT-TYPE
    SYNTAX  INTEGER {
                     succeeded(1),
                     failed(2),
                     inprogress(3)
                    }
    MAX-ACCESS      read-only
    STATUS          current
    DESCRIPTION
    "This attribute indicates whether the file transfer operation has been successful,
     or failed, or in progress."
    DEFVAL { succeeded }

    ::= { acFileXferMgrEntry 15 }

-- 
-- File Transfer Mgr Trap Definitions
--

acFileXferMgrTraps   OBJECT IDENTIFIER ::= { acFileXferMgr 0 }

acFileXferMgrXferFailedTrap  NOTIFICATION-TYPE
    OBJECTS { 
        acChassisCurrentTime, acChassisRingId,
        acFileXferMgrNodeId,
        acFileXferMgrRowId,
        acFileXferMgrSourceFilename,
        acFileXferMgrDestFilename,
        acFileXferMgrOperation
    } 
    STATUS  current
    DESCRIPTION
    "The file transfer operation failed."
    
    ::= { acFileXferMgrTraps 1 }
    
acFileXferMgrXferCompletedTrap  NOTIFICATION-TYPE
    OBJECTS { 
        acChassisCurrentTime, acChassisRingId,
        acFileXferMgrNodeId,
        acFileXferMgrRowId,
        acFileXferMgrSourceFilename,
        acFileXferMgrDestFilename,
        acFileXferMgrOperation
    } 
    STATUS  current
    DESCRIPTION
    "The file transfer operation completed."
    
    ::= { acFileXferMgrTraps 2 }

--
-- Ring Discovery Protocol (RDP) Manager 
--

acRdpMgrTable OBJECT-TYPE
    SYNTAX     SEQUENCE OF AcRdpMgrEntry
    MAX-ACCESS not-accessible
    STATUS     current
    DESCRIPTION
    "This table contains general Appian ring information discovered
    through the Ring Discovery Protocol (RDP)."
    ::= { acRdpMgr 1 }

acRdpMgrEntry OBJECT-TYPE
    SYNTAX     AcRdpMgrEntry
    MAX-ACCESS not-accessible
    STATUS     current
    DESCRIPTION
    "General Appian ring information discovered through RDP by the
    node specified by the index acRdpMgrNodeId."
    INDEX { acRdpMgrNodeId }
    ::= { acRdpMgrTable 1 }

    AcRdpMgrEntry ::=
        SEQUENCE {
            acRdpMgrNodeId                    AcNodeId,
            acRdpMgrFsmState                  INTEGER,
            acRdpMgrRingMasterNodeMac         MacAddress,
            acRdpMgrRingTopology              INTEGER,
            acRdpMgrRingState                 INTEGER,
            acRdpMgrRingSize                  INTEGER,
            acRdpMgrRdpVersion                INTEGER
        }

acRdpMgrNodeId OBJECT-TYPE
    SYNTAX     AcNodeId
    MAX-ACCESS accessible-for-notify
    STATUS     current
    DESCRIPTION
    "Identifies the node where the Appian ring information was gathered."
    ::= { acRdpMgrEntry 1 }
        
acRdpMgrFsmState OBJECT-TYPE
    SYNTAX     INTEGER {
                isolated(0),
                discovery(1),
                master(2),
                pleb(3)
                }
    MAX-ACCESS read-only
    STATUS     current
    DESCRIPTION
    "State of the RDP Finite State Machine. Possible values:
     - isolated: the node is isolated.
     - discovery: the node is not isolated and is in the process of
       gathering Appian ring information.
     - master: the Appian ring information has been gathered and this
       node plays the role of master in the Ring Discovery Protocol
       (node with lowest Appian DCC MAC in the ring).
     - pleb: the Appian ring information has been gathered and this
       node does not play the role of master in the Ring Discovery
       Protocol (there is a node with a lower Appian DCC MAC in the
       ring)."
    ::= { acRdpMgrEntry 2 }
        
acRdpMgrRingMasterNodeMac OBJECT-TYPE
    SYNTAX     MacAddress
    MAX-ACCESS read-only
    STATUS     current
    DESCRIPTION
    "MAC address of RDP master node in the Appian ring."
    ::= { acRdpMgrEntry 3 }
        
acRdpMgrRingTopology OBJECT-TYPE
    SYNTAX     INTEGER {
                unknown(0),
                open(1),
                closed(2)
                }
    MAX-ACCESS read-only
    STATUS     current
    DESCRIPTION
    "Appian ring topology. Possible values:
     - unknown: there is not enough information available to determine
       whether this node is part of an open or closed ring.
     - open: two of the nodes in the ring are configured as End Systems.
     - closed: all nodes in the ring are configured as Intermediate
       Systems."
    ::= { acRdpMgrEntry 4 }
        
acRdpMgrRingState OBJECT-TYPE
    SYNTAX     INTEGER {
                unknown(0),
                complete(1),
                incomplete(2)
                }
    MAX-ACCESS read-only
    STATUS     current
    DESCRIPTION
    "Appian ring state:
     - unknown: there is not enough information available to determine
       whether the Appian ring is complete or incomplete.
     - complete: the ring map obtained contains all nodes in the ring.
     - incomplete: the ring map obtained does not contain all nodes in the
       ring. This may be due to a broken optical link or to misconfiguration
       of any of the nodes in the ring (wrong acChassisNodeArchitecture)."
    ::= { acRdpMgrEntry 5 }
        
acRdpMgrRingSize OBJECT-TYPE
    SYNTAX     INTEGER
    MAX-ACCESS read-only
    STATUS     current
    DESCRIPTION
    "Number of nodes in the Appian ring. The special value -1 means the
    ring size is unknown."
    ::= { acRdpMgrEntry 6 }
        
acRdpMgrRdpVersion OBJECT-TYPE
    SYNTAX     INTEGER
    MAX-ACCESS read-only
    STATUS     current
    DESCRIPTION
    "Current version of the Ring Discovery Protocol (RDP)"
    ::= { acRdpMgrEntry 7 }

acRdpMgrNodeTable OBJECT-TYPE
    SYNTAX     SEQUENCE OF AcRdpMgrNodeEntry
    MAX-ACCESS not-accessible
    STATUS     current
    DESCRIPTION
    "This table contains information about the different nodes in the Appian DCC
     ring that this node is part of. The first entry in this table corresponds to
     this node. Each entry in the table corresponds to the East neighbor of the
     node referred to by the previous entry."
    ::= { acRdpMgr 2 }

acRdpMgrNodeEntry OBJECT-TYPE
    SYNTAX     AcRdpMgrNodeEntry
    MAX-ACCESS not-accessible
    STATUS     current
    DESCRIPTION
    "Each row in this table contains information about a node in the Appian DCC
     ring."
    INDEX { acRdpMgrNodeNodeId, acRdpMgrNodeRowId }
    ::= { acRdpMgrNodeTable 1 }

    AcRdpMgrNodeEntry ::=
        SEQUENCE {
            acRdpMgrNodeThisNodeId                AcNodeId,
            acRdpMgrNodeRowId                     INTEGER,
            acRdpMgrNodeNodeId                    AcNodeId,
            acRdpMgrNodeADccIpAddress             IpAddress,
            acRdpMgrNodeADccMacAddress            MacAddress,
            acRdpMgrNodeADccConfig                INTEGER,
            acRdpMgrNodeADccEastOk                TruthValue,
            acRdpMgrNodeADccWestOk                TruthValue,
            acRdpMgrNodeNodeArch                  AcNodeArchitecture
        }

acRdpMgrNodeThisNodeId OBJECT-TYPE
    SYNTAX     AcNodeId
    MAX-ACCESS accessible-for-notify
    STATUS     current
    DESCRIPTION
    "A unique node identification number which uniquely identifies this node
    within an Appian ring of OSAPs."
    ::= { acRdpMgrNodeEntry 1 }
    
acRdpMgrNodeRowId OBJECT-TYPE
    SYNTAX     INTEGER
    MAX-ACCESS accessible-for-notify
    STATUS     current
    DESCRIPTION
    "Index that identifies this row in the table."
    ::= { acRdpMgrNodeEntry 2 }
        
acRdpMgrNodeNodeId OBJECT-TYPE
    SYNTAX     AcNodeId
    MAX-ACCESS read-only
    STATUS     current
    DESCRIPTION
    "Node Id of node represented by this entry in the table."
    ::= { acRdpMgrNodeEntry 3 }

acRdpMgrNodeADccIpAddress OBJECT-TYPE
    SYNTAX     IpAddress
    MAX-ACCESS read-only
    STATUS     current
    DESCRIPTION
    "IP address assigned to the Appian DCC management access interface of the
    node represented by this entry in the table."
    ::= { acRdpMgrNodeEntry 4 }

acRdpMgrNodeADccMacAddress   OBJECT-TYPE
    SYNTAX     MacAddress
    MAX-ACCESS read-only
    STATUS     current
    DESCRIPTION
    "Appian DCC MAC address of the node represented by this entry in the table."
    ::= { acRdpMgrNodeEntry 5 }

acRdpMgrNodeADccConfig   OBJECT-TYPE
    SYNTAX     INTEGER {
                unknown(0),
                is(1),
                ese(2),
                esw(3)
                }
    MAX-ACCESS read-only
    STATUS     current
    DESCRIPTION
    "RDP node configuration. Possible values:
     - unknown: the node configuration is unknown.
     - is: Intermediate System. The node is expected to have both an East and
       a West neighbor node in the Appian DCC ring.
     - ese: End System East. The node is expected to only  have a West neighbor
       node in the Appian DCC ring.
     - esw: End System West. The node is expected to only have an East neighbor
       node in the Appian DCC ring."
    ::= { acRdpMgrNodeEntry 6 }

acRdpMgrNodeADccEastOk   OBJECT-TYPE
    SYNTAX     TruthValue
    MAX-ACCESS read-only
    STATUS     current
    DESCRIPTION
    "Specifies whether RDP is active (there is light and we are receiving RDP
    packets) on the East interface."
    ::= { acRdpMgrNodeEntry 7 }

acRdpMgrNodeADccWestOk   OBJECT-TYPE
    SYNTAX     TruthValue
    MAX-ACCESS read-only
    STATUS     current
    DESCRIPTION
    "Specifies whether RDP is active (there is light and we are receiving RDP
    packets) on the West interface."
    ::= { acRdpMgrNodeEntry 8 }

acRdpMgrNodeNodeArch   OBJECT-TYPE
    SYNTAX     AcNodeArchitecture
    MAX-ACCESS read-only
    STATUS     current
    DESCRIPTION
    "Node architecture."
    ::= { acRdpMgrNodeEntry 9 }

-- 
-- RDP Mgr Trap Definitions
--

acRdpMgrTraps OBJECT IDENTIFIER ::= { acRdpMgr 0 }

acRdpMgrRingMapChangedTrap NOTIFICATION-TYPE
    OBJECTS { 
        acChassisCurrentTime,
        acChassisRingId,
        acRdpMgrNodeId
    } 
    STATUS  current
    DESCRIPTION
    "The ring map obtained by RDP has changed."
    ::= { acRdpMgrTraps 1 }

acRdpMgrDuplicateNodeIdTrap NOTIFICATION-TYPE
    OBJECTS { 
        acChassisCurrentTime,
        acChassisRingId,
        acRdpMgrNodeId
    } 
    STATUS  current
    DESCRIPTION
    "There are two nodes in the ring with the same node Id."
    ::= { acRdpMgrTraps 2 }

END
