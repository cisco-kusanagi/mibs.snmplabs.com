PUBLISHEXT-MIB

--	FORCE-INCLUDE <mib.h>
--	FORCE-INCLUDE <snmpdefs.h>
--	FORCE-INCLUDE <snmpstat.h>
--	FORCE-INCLUDE "mibproto.h"

	DEFINITIONS ::= BEGIN

	IMPORTS
	   MODULE-IDENTITY, OBJECT-TYPE, Integer32, IpAddress
	   FROM SNMPv2-SMI
	DisplayString
		FROM SNMPv2-TC
	publishExt
		FROM APENT-MIB;

--PUBLISHEXT MIB

	apPublishExtMib MODULE-IDENTITY
	  LAST-UPDATED "0006082000Z"
	  ORGANIZATION "ArrowPoint Communications Inc."
	  CONTACT-INFO
	  "
	  Postal:               ArrowPoint Communications Inc.
				                 50 Nagog Park
				                 Acton, Massachusetts 01720
	   Tel:                   +1 978-206-3000  option 1
	   E-Mail:                support@arrowpoint.com"
	   DESCRIPTION
	"The MIB module used to describe the ArrowPoint Communications publisher and subscriber"
	::= { publishExt 1}
	
apPubTable OBJECT-TYPE
	SYNTAX		SEQUENCE OF APPubEntry
	MAX-ACCESS	not-accessible
	STATUS		current
	DESCRIPTION
		"A list of Publishers"
	::= { publishExt 2}
	
apPubEntry OBJECT-TYPE
	SYNTAX			APPubEntry
	MAX-ACCESS		not-accessible
	STATUS			current
	DESCRIPTION		
		"A group of information uniqely identifying a publisher. One entry exists
		for every publisher"
	INDEX	{ apPubName }
	::= {apPubTable 1 }
	
APPubEntry ::= SEQUENCE {
	apPubName			DisplayString,
	apPubState			INTEGER,
	apPubAccessError	DisplayString,
	apPubAccessIP		IpAddress,
	apPubAccessUserName	DisplayString,
	apPubPublishedFiles	Integer32,
	apPubManagedDirs	Integer32,
	apPubSubscribers	INTEGER,     
	apPubPublishInterval INTEGER,
	apPubManagedFiles	Integer32,
	apPubLastMethod		DisplayString,
	apPubAccessType		INTEGER,
	apPubAccessPort		INTEGER,
	apPubAccessBaseDir	DisplayString,
	apPubPublishedBytes	Integer32,
	apPubTriggerFile	DisplayString,
	apPubNextInterval	DisplayString,
	apPubSubscrbrsSyncd	INTEGER,
	apPubManagedBytes	Integer32,
	apPubLastTime		DisplayString   
}

apPubName OBJECT-TYPE
	SYNTAX			DisplayString      
	MAX-ACCESS		read-only
	STATUS			current
	DESCRIPTION		"The name of the Publisher service"
	::= {apPubEntry 1}
	
apPubState OBJECT-TYPE
	SYNTAX	INTEGER{
					publisherRegister(0),
					subscriberRegister(1),
					needsConfig(2),
					accessFail(3),
					ready(4),
					busyPublisher(5),
					busyScan(6),
					initializing(7),
					waitsConfig(8),
					online(9),
					suspended(10),
					down(11),
					invalid(12)
					}
	MAX-ACCESS		read-only
	STATUS			current
	DESCRIPTION		         
		"The status of our publisher."
	::= {apPubEntry 2}

apPubAccessError 	OBJECT-TYPE
	SYNTAX			DisplayString
	MAX-ACCESS		read-only        
	STATUS			current
	DESCRIPTION
		"If apPubStatus is accessFail(3) then we will return the error here."    
	::= {apPubEntry 3}
	
apPubAccessIP	OBJECT-TYPE
	SYNTAX		IpAddress   
	MAX-ACCESS	read-only
	STATUS		current
	DESCRIPTION
		"The IP address of the publisher."          
	::= {apPubEntry 4}
	
apPubAccessUserName	OBJECT-TYPE
	SYNTAX		DisplayString
	MAX-ACCESS	read-only
	STATUS		current
	DESCRIPTION
		"Usernmae to use when logging in to a publisher."
	::= {apPubEntry 5}

apPubPublishedFiles	OBJECT-TYPE
	SYNTAX		Integer32
	MAX-ACCESS	read-only
	STATUS		current
	DESCRIPTION
		"The total number of published files."
	::= {apPubEntry 6}

apPubSubscribers	OBJECT-TYPE
	SYNTAX		INTEGER
	MAX-ACCESS	read-only
	STATUS		current
	DESCRIPTION
		"The number of subscribers to this publisher."
	::= {apPubEntry 7}
	
apPubPublishInterval	OBJECT-TYPE
	SYNTAX		INTEGER
	MAX-ACCESS	read-only
	STATUS		current
	DESCRIPTION
		"The interval at which files are published."
	::= {apPubEntry 8}

apPubManagedFiles	OBJECT-TYPE
	SYNTAX		Integer32
	MAX-ACCESS	read-only
	STATUS		current
	DESCRIPTION	
		"The total number of files managed."
	::= {apPubEntry 9}

apPubManagedDirs	OBJECT-TYPE
	SYNTAX		Integer32
	MAX-ACCESS	read-only
	STATUS		current
	DESCRIPTION
		"The total number of directories managed."
	::= {apPubEntry 10}
		
apPubLastMethod	OBJECT-TYPE
	SYNTAX		DisplayString 
	MAX-ACCESS  read-only
	STATUS		current
	DESCRIPTION
		"The last method used to publish."
	::= {apPubEntry 11}
	
apPubAccessType	OBJECT-TYPE
	SYNTAX		INTEGER{
						ftp(0),
						http(1)
						}
	MAX-ACCESS	read-only
	STATUS		current
	DESCRIPTION
		"The type of access to the publisher."
	::= {apPubEntry 12}
	
apPubAccessPort	OBJECT-TYPE
	SYNTAX		INTEGER
	MAX-ACCESS	read-only
	STATUS		current
	DESCRIPTION
		"The port to access content on the publisher."
	::= {apPubEntry 13}

apPubAccessBaseDir	OBJECT-TYPE
	SYNTAX		DisplayString
	MAX-ACCESS	read-only
	STATUS		current
	DESCRIPTION
		"The base directory to access content on the publisher."
	::= {apPubEntry 14}
	
apPubPublishedBytes	OBJECT-TYPE
	SYNTAX			Integer32
	MAX-ACCESS		read-only
	STATUS			current
	DESCRIPTION
		"The total number of bytes published by the publisher."
	::= {apPubEntry 15}
	
apPubTriggerFile	OBJECT-TYPE
	SYNTAX		DisplayString
	MAX-ACCESS	read-only
	STATUS		current
	DESCRIPTION
		"The file used to trigger publishing."
	::= {apPubEntry 16}
	
apPubNextInterval	OBJECT-TYPE
	SYNTAX		DisplayString 
	MAX-ACCESS	read-only
	STATUS		current
	DESCRIPTION
		"The next interval at which the publisher will publish."
	::= {apPubEntry 17}
	
apPubSubscrbrsSyncd	OBJECT-TYPE
	SYNTAX		INTEGER
	MAX-ACCESS	read-only
	STATUS		current
	DESCRIPTION
		"Total number of syncronized subscribers."
	::= {apPubEntry 18}
	                   
apPubManagedBytes	OBJECT-TYPE
	SYNTAX		Integer32	                   
	MAX-ACCESS	read-only
	STATUS		current
	DESCRIPTION
		"Total number of butes we manage."
	::= {apPubEntry 19}
	
apPubLastTime	OBJECT-TYPE
	SYNTAX		DisplayString
	MAX-ACCESS	read-only
	STATUS		current
	DESCRIPTION
		"Last time a publisher action was taken."
	::= {apPubEntry 20}         
END
