SONICWALL-SSL-DEV-MIB DEFINITIONS ::= BEGIN

IMPORTS
    enterprises, IpAddress, Integer32,
	MODULE-IDENTITY 			FROM SNMPv2-SMI
	TRAP-TYPE				FROM RFC-1215
	OBJECT-TYPE				FROM RFC-1212;

-- Our enterprise

sonicWALL	OBJECT IDENTIFIER ::= { enterprises 8714 }

-- security devices such as ssl devices are a type 2 device
sonicSEC	OBJECT IDENTIFIER ::= { sonicWALL 2 }
sonicSSL	OBJECT IDENTIFIER ::= { sonicSEC 1 }

sonicSSLDev MODULE-IDENTITY
    LAST-UPDATED "200203061330Z"
    ORGANIZATION "SonicWALL, Inc."
    CONTACT-INFO
		"	SonicWall Inc.

		Postal: 1160 Bordeaux Dr.
			Sunnyvale, CA 94089
			USA

		   Tel: +1 408 745 9600
		   Fax: +1 408 745 9300

		E-mail: support@sonicwall.com"
    DESCRIPTION
	"The MIB module for SonicWALL enterprise SSL Device objects
	 and traps."
    ::= { sonicSSL 6 }

-- ----------------------------------------------------------------
sslDevInfo     OBJECT IDENTIFIER ::= { sonicSSLDev 0 }
-- 1.3.6.1.4.1.8714.2.1.6.0
-- ----------------------------------------------------------------

lastCfgChgInitiator OBJECT-TYPE
    SYNTAX      IpAddress
    MAX-ACCESS  read-only
    STATUS      mandatory
    DESCRIPTION
	"The IP address of the initiator of the last configuration
	 change on this device."
    ::= { sslDevInfo 1 }

lastCfgChgCmd OBJECT-TYPE
    SYNTAX      Integer32
    MAX-ACCESS  read-only
    STATUS      mandatory
    DESCRIPTION
	"The IOCTL number of the last configuration change on this device."
    ::= { sslDevInfo 2 }

--
-- ----------------------------------------------------------------
sslDevUtil     OBJECT IDENTIFIER ::= { sonicSSLDev 1 }
-- 1.3.6.1.4.1.8714.2.1.6.1
-- ----------------------------------------------------------------

cpuUtilLoThresh OBJECT-TYPE
    SYNTAX      Integer32
    MAX-ACCESS  read-only
    STATUS      mandatory
    DESCRIPTION
	"When a system is in a hi cpu utilization state, this is the
	 threshold value that cpu utilization must fall below to enter
	 the low cpu utlization state.  The value is expressed as the
	 percentage cpu utilization on a scale of 0-100."
    ::= { sslDevUtil 1 }

cpuUtilHiThresh OBJECT-TYPE
    SYNTAX      Integer32
    MAX-ACCESS  read-only
    STATUS      mandatory
    DESCRIPTION
	"When a system is in a low cpu utilization state, this is the
	 threshold value that cpu utilization must rise above to enter
	 the hi cpu utlization state.  The value is expressed as the
	 percentage cpu utilization on a scale of 0-100."
    ::= { sslDevUtil 2 }

-- ----------------------------------------------------------------
sslDevStats     OBJECT IDENTIFIER ::= { sonicSSLDev 2 }
-- 1.3.6.1.4.1.8714.2.1.6.2
-- ----------------------------------------------------------------
cpuUtilStatus OBJECT-TYPE
    SYNTAX      Integer32
    MAX-ACCESS  read-only
    STATUS      mandatory
    DESCRIPTION
	"The cpu utilization at the time the device is SNMP polled. The
         value is expressed as the precentage cpu utilization on a scale
         of 0-100."
    ::= { sslDevStats 1 }
--
-- ----------------------------------------------------------------
sslDevEvents	OBJECT IDENTIFIER ::= { sonicSSLDev 10 }
-- 1.3.6.1.4.1.8714.2.1.6.10
-- -----------------------------------------------------------------
cpuUtilChangeHi TRAP-TYPE
    ENTERPRISE sslDevEvents
    DESCRIPTION
	"The percentage of CPU utilization has transitioned above the upper
	 threshold limit."
    ::= 1

cpuUtilChangeLo TRAP-TYPE
    ENTERPRISE sslDevEvents
    DESCRIPTION
	"The percentage of CPU utilization has transitioned below the lower
	 threshold limit."
    ::= 2 

configChange TRAP-TYPE
    ENTERPRISE sslDevEvents
    VARIABLES { lastCfgChgInitiator, lastCfgChgCmd }
    DESCRIPTION
	"The running configuration of the device has been modified."
    ::= 7

END
