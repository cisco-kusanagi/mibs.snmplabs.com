-------------------------------------------------------------------------------
-- file: PKTStatistics.mib 
--
-- description:
--      This file contains the SNMP definitions for the PKTStatistics area.
--
-- history:
--      34A0505 / 98.01.16 / Jason Paau/ Creation of V1.0
--	34A0505 / 98.03.31 / Jason Paau/ Change NncPktVclCosType value 1
--			from "all" to "controlAndRouting".  Also change
--			CoS objects Max Access types to "not-accessible"
--                                      
--
-- %%history-start%%
-- 98.02.26 jbejjani 34A0538: epe.3.1 trib merge 
-- 98.02.26 jbejjani 34A0538: epe.3.1 trib merge 
-- 98.02.28 jbejjani 34A0538: epe.3.1 trib merge 
-- 98.04.03 jpaau 34A0505: Change access for CoS indices to 
--   'not-accessible'. Change NncPktVclCoSType from 'all' to 
--   'controlAndRouting'. 
-- %%history-end%%
--
-- Copyright 1998 Newbridge Networks Corporation.  All Rights Reserved
-------------------------------------------------------------------------------
NNC-PKT-STATISTICS-MIB DEFINITIONS ::= BEGIN

  IMPORTS
    MODULE-IDENTITY, OBJECT-TYPE
      FROM SNMPv2-SMI
    TEXTUAL-CONVENTION
      FROM SNMPv2-TC
    MODULE-COMPLIANCE, OBJECT-GROUP
      FROM SNMPv2-CONF
    ifIndex
      FROM IF-MIB
    nncExtensions, NncExtCounter64
      FROM NNCGNI0001-SMI
    atmVclVpi, atmVclVci
      FROM ATM-MIB
    NncExtIntvlStateType, NncExtAbsIntvlNumberType, NncExtRelIntvlNumberType
      FROM NNC-INTERVAL-STATISTICS-TC-MIB;
                        
  nncExtPktStatistics MODULE-IDENTITY        
    LAST-UPDATED    "9801160330Z"
    ORGANIZATION    "Newbridge Networks Corporation"
    CONTACT-INFO
		    "Newbridge Networks Corporation
		    Postal: 600 March Road
		    Kanata, Ontario
		    Canada K2K 2E6

		    Phone:  +1 613 591 3600
		    Fax:    +1 613 591 3680"
                
    DESCRIPTION "
      This module contains definitions for performance monitoring of the
      packets routed.

      This MIB module contains the following tables:
	PKT VCL 15 Minute Current Table
	PKT VCL 15 Minute Interval Table

      and the following non-table objects:
	nncDepthOfHistoricalStrata

      These tables are heavily influenced by the definition of VPL/VCL
      described in rfc1695, and by the statistic table definitions described
      in rfc2233. The number of intervals supported is dependent upon
      resource availibility on any given product, but should nominally
      be 32. To avoid building in massive amounts of storage, some products
      may adopt a bulk collection scheme. 

      Note that IP packets are counted because of rfc1483.

      Intervals:
	Statistics on the performance of VPL/VCLs are collected over a
	historical stratum of up to a maximum of M intervals. The value of M
	is a function of a product's storage capability. For example, on the
	36170 product, M = 1. Refer to a product's NEID document for a
	description of these limits.

	The intervals are 15 minutes and are aligned to
	the quarter of one hour of a wall clock. The current
	interval spans back to the last 15 minute tick on the wall
	clock. Continuing along the timeline from that point is the most
	recently completed interval and has an index of 1. The previous
	interval has an index of 2 and so on. Note that the oldest interval
	may be incomplete since the statistic collection may have been
	enabled offset to the quarter or one hour tick.

		   t
		   0          -1i         -2i         -3i
	===========|===========|===========|===========|===========
	  current      N = 1       N = 2       N = 3       N = 4    ... N = M
	  interval

     
    "
      
  ::= { nncExtensions 50 }

  nncPktStatisticsObjects OBJECT IDENTIFIER ::= { nncExtPktStatistics 1 }
  nncPktStatisticsTraps OBJECT IDENTIFIER ::= { nncExtPktStatistics 2 }
  nncPktStatisticsGroups OBJECT IDENTIFIER ::= { nncExtPktStatistics 3 }
  nncPktStatisticsCompliances OBJECT IDENTIFIER ::= { nncExtPktStatistics 4 }


  NncPktVclCoSType ::= TEXTUAL-CONVENTION
    STATUS  current
    DESCRIPTION
      "The type describing the Class of Service provided for a particular
       VC.  Currently, there are three classes of service provided for the
       Amethyst release of CSI:

       a) controlAndRouting - the level of service provided for control
          and routing information being passed
       b) standard - no guarantees for either delay or packet loss
       c) premium - SLA values for delay and packet loss are detailed
          in 34FS0119[9]
      "
    SYNTAX INTEGER {
       controlAndRouting(1),
       standard(2),
       premium(3)
    }

-------------------------------------------------------------------------------
-- Virtual Channel Links 15 Minute Current Statistics Table
-------------------------------------------------------------------------------

  nncPktVcl15MinCurTable        OBJECT-TYPE 
        SYNTAX                  SEQUENCE OF NncPktVcl15MinCurEntry 
        MAX-ACCESS              not-accessible
        STATUS                  current
        DESCRIPTION             "The nncPktVcl15MinCurTable contains
                                objects for monitoring the packet performance
                                of a VCL during the current 15 minute interval."
        ::= { nncPktStatisticsObjects 1 }


  nncPktVcl15MinCurEntry        OBJECT-TYPE 
        SYNTAX                  NncPktVcl15MinCurEntry 
        MAX-ACCESS              not-accessible
        STATUS                  current
        DESCRIPTION             "An entry in the 15 minute current
                                statistics table. Each conceptual row
                                contains current packet statistics for a
                                particular VCL."
        INDEX                   { ifIndex, atmVclVpi, atmVclVci, nncPktVcl15MinCurCoS }
        ::= { nncPktVcl15MinCurTable 1 }

  NncPktVcl15MinCurEntry ::=
    SEQUENCE {
         nncPktVcl15MinCurCoS                     NncPktVclCoSType,
         nncPktVcl15MinCurState                   NncExtIntvlStateType,
         nncPktVcl15MinCurAbsoluteIntervalNumber  NncExtAbsIntvlNumberType,
         nncPktVcl15MinCurInOctets                NncExtCounter64,
         nncPktVcl15MinCurInUcastPkts             NncExtCounter64,
         nncPktVcl15MinCurInMulticastPkts         NncExtCounter64,
         nncPktVcl15MinCurInBroadcastPkts         NncExtCounter64,
         nncPktVcl15MinCurInDiscards              NncExtCounter64,
         nncPktVcl15MinCurInErrors                NncExtCounter64,
         nncPktVcl15MinCurOutOctets               NncExtCounter64,
         nncPktVcl15MinCurOutUcastPkts            NncExtCounter64,
         nncPktVcl15MinCurOutMulticastPkts        NncExtCounter64,
         nncPktVcl15MinCurOutBroadcastPkts        NncExtCounter64,
         nncPktVcl15MinCurOutDiscards             NncExtCounter64,
         nncPktVcl15MinCurOutErrors               NncExtCounter64

     }

   nncPktVcl15MinCurCoS      OBJECT-TYPE
       SYNTAX      NncPktVclCoSType
       MAX-ACCESS  not-accessible
       STATUS      current
       DESCRIPTION
               "The Class of Service provided for the cells in
                the current interval."
   ::= {nncPktVcl15MinCurEntry 1 }

   nncPktVcl15MinCurState OBJECT-TYPE
       SYNTAX      NncExtIntvlStateType
       MAX-ACCESS  read-only
       STATUS      current
       DESCRIPTION
               "The state of the current interval.  The
                object provides a status for those entries
                which have been reset by th user, or have
                been subject to a wall clock time change."
   ::= { nncPktVcl15MinCurEntry 2 }

   nncPktVcl15MinCurAbsoluteIntervalNumber    OBJECT-TYPE
       SYNTAX      NncExtAbsIntvlNumberType
       MAX-ACCESS  read-only
       STATUS      current
       DESCRIPTION
               "The absolute interval number of this interval"
   ::= { nncPktVcl15MinCurEntry 3 }
  
     
   nncPktVcl15MinCurInOctets OBJECT-TYPE
       SYNTAX      NncExtCounter64
       MAX-ACCESS  read-only
       STATUS      current
       DESCRIPTION
               "The total number of octets received on the interface,
               including protocol overhead, but excluding ATMs & AAL
               overhead.  This object is a 64-bit version of ifInOctets.

               Discontinuities in the value of this counter can occur
               at re-initialization of the management system, or if the
               VCL is disconnected"
   ::= { nncPktVcl15MinCurEntry 4 }


   nncPktVcl15MinCurInUcastPkts OBJECT-TYPE
       SYNTAX      NncExtCounter64
       MAX-ACCESS  read-only
       STATUS      current
       DESCRIPTION
               "The number of packets, delivered by this sub-layer to
               a higher (sub-)layer, which were not addressed to a
               multicast or broadcast address at this sub-layer.
               This object is a 64-bit version of ifInUcastPkts.

               Discontinuities in the value of this counter can occur
               at re-initialization of the management system, or if the
               VCL is disconnected"
   ::= { nncPktVcl15MinCurEntry 5 }

   nncPktVcl15MinCurInMulticastPkts OBJECT-TYPE
       SYNTAX      NncExtCounter64
       MAX-ACCESS  read-only
       STATUS      current
       DESCRIPTION
               "The number of packets, delivered by this sub-layer to
               a higher (sub-)layer, which were addressed to a
               multicast address at this sub-layer.  For a MAC layer
               protocol, this includes both Group and Functional
               addresses.  This object is a 64-bit version of
               ifInMulticastPkts.

               Discontinuities in the value of this counter can occur
               at re-initialization of the management system, or if the
               VCL is disconnected"
   ::= { nncPktVcl15MinCurEntry 6 }

   nncPktVcl15MinCurInBroadcastPkts OBJECT-TYPE
       SYNTAX      NncExtCounter64
       MAX-ACCESS  read-only
       STATUS      current
       DESCRIPTION
               "The number of packets, delivered by this sub-layer to
               a higher (sub-)layer, which were addressed to a
               broadcast address at this sub-layer.  This object is a
               64-bit version of ifInBroadcastPkts.

               Discontinuities in the value of this counter can occur
               at re-initialization of the management system, or if the
               VCL is disconnected"
   ::= { nncPktVcl15MinCurEntry 7 }
 
   nncPktVcl15MinCurInDiscards OBJECT-TYPE
       SYNTAX      NncExtCounter64
       MAX-ACCESS  read-only
       STATUS      current
       DESCRIPTION
               "The number of inbound packets which were chosen to be
               discarded even though no errors had been detected to
               prevent their being deliverable to a higher-layer
               protocol.  One possible reason for discarding such a
               packet could be to free up buffer space.

               Discontinuities in the value of this counter can occur
               at re-initialization of the management system, or if the
               VCL is disconnected"
   ::= { nncPktVcl15MinCurEntry 8 }


   nncPktVcl15MinCurInErrors OBJECT-TYPE
       SYNTAX      NncExtCounter64
       MAX-ACCESS  read-only
       STATUS      current
       DESCRIPTION
               "For packet-oriented interfaces, the number of inbound
               packets that contained errors preventing them from
               being deliverable to a higher-layer protocol.  For
               character-oriented or fixed-length interfaces, the
               number of inbound transmission units that contained
               errors preventing them from being deliverable to a
               higher-layer protocol.

               Discontinuities in the value of this counter can occur
               at re-initialization of the management system, or if the
               VCL is disconnected"
     ::= { nncPktVcl15MinCurEntry 9 }


     nncPktVcl15MinCurOutOctets OBJECT-TYPE
       SYNTAX      NncExtCounter64
       MAX-ACCESS  read-only
       STATUS      current
       DESCRIPTION
               "The total number of octets transmitted out of the
               interface, including protocol overhead, but excluding ATMs
               & AAL overhead.  This object is a 64-bit version of 
               ifOutOctets.

               Discontinuities in the value of this counter can occur
               at re-initialization of the management system, or if the
               VCL is disconnected"
     ::= { nncPktVcl15MinCurEntry 10 }
 

     nncPktVcl15MinCurOutUcastPkts OBJECT-TYPE
       SYNTAX      NncExtCounter64
       MAX-ACCESS  read-only
       STATUS      current
       DESCRIPTION
               "The total number of packets that higher-level
               protocols requested be transmitted, and which were not
               addressed to a multicast or broadcast address at this
               sub-layer, including those that were discarded or not
               sent.  This object is a 64-bit version of
               ifOutUcastPkts.

               Discontinuities in the value of this counter can occur
               at re-initialization of the management system, or if the
               VCL is disconnected"
    ::= { nncPktVcl15MinCurEntry 11 }

    nncPktVcl15MinCurOutMulticastPkts OBJECT-TYPE
       SYNTAX      NncExtCounter64
       MAX-ACCESS  read-only
       STATUS      current
       DESCRIPTION
               "The total number of packets that higher-level
               protocols requested be transmitted, and which were
               addressed to a multicast address at this sub-layer,
               including those that were discarded or not sent.  For
               a MAC layer protocol, this includes both Group and
               Functional addresses.  This object is a 64-bit version
               of ifOutMulticastPkts.
               Discontinuities in the value of this counter can occur
               at re-initialization of the management system, or if the
               VCL is disconnected"
    ::= { nncPktVcl15MinCurEntry 12 }

    nncPktVcl15MinCurOutBroadcastPkts OBJECT-TYPE
       SYNTAX      NncExtCounter64
       MAX-ACCESS  read-only
       STATUS      current
       DESCRIPTION
               "The total number of packets that higher-level
               protocols requested be transmitted, and which were
               addressed to a broadcast address at this sub-layer,
               including those that were discarded or not sent.  This
               object is a 64-bit version of ifOutBroadcastPkts.

               Discontinuities in the value of this counter can occur
               at re-initialization of the management system, or if the
               VCL is disconnected"
     ::= { nncPktVcl15MinCurEntry 13 }

     nncPktVcl15MinCurOutDiscards OBJECT-TYPE
       SYNTAX      NncExtCounter64
       MAX-ACCESS  read-only
       STATUS      current
       DESCRIPTION
               "The number of outbound packets which were chosen to
               be discarded even though no errors had been detected
               to prevent their being transmitted.  One possible
               reason for discarding such a packet could be to free
               up buffer space.

               Discontinuities in the value of this counter can occur
               at re-initialization of the management system, or if the
               VCL is disconnected"
     ::= { nncPktVcl15MinCurEntry 14 }

     nncPktVcl15MinCurOutErrors OBJECT-TYPE
       SYNTAX      NncExtCounter64
       MAX-ACCESS  read-only
       STATUS      current
       DESCRIPTION
               "For packet-oriented interfaces, the number of
               outbound packets that could not be transmitted because
               of errors.  For character-oriented or fixed-length
               interfaces, the number of outbound transmission units
               that could not be transmitted because of errors.

               Discontinuities in the value of this counter can occur
               at re-initialization of the management system, or if the
               VCL is disconnected"
     ::= { nncPktVcl15MinCurEntry 15 }




-------------------------------------------------------------------------------
-- Virtual Channel Links 15 Minute Interval Statistics Table
-------------------------------------------------------------------------------

  nncPktVcl15MinIntTable        OBJECT-TYPE 
        SYNTAX                  SEQUENCE OF NncPktVcl15MinIntEntry 
        MAX-ACCESS              not-accessible
        STATUS                  current
        DESCRIPTION             "The nncPktVcl15MinIntTable contains
                                objects for monitoring the packet performance 
                                of a virtual channel link over a historical stratum
                                of M 15 minute intervals.
                                "
        ::= { nncPktStatisticsObjects 2 }


  nncPktVcl15MinIntEntry      OBJECT-TYPE 
        SYNTAX                  NncPktVcl15MinIntEntry 
        MAX-ACCESS              not-accessible
        STATUS                  current
        DESCRIPTION             "An entry in the 15 minute interval
                                statistics table. Each conceptual row
                                contains packet statistics for a particular
                                VCL and interval."
  INDEX                         { ifIndex, atmVclVpi, atmVclVci,
                                  nncPktVcl15MinIntNumber, nncPktVcl15MinIntCoS }
        ::= { nncPktVcl15MinIntTable 1 }

   NncPktVcl15MinIntEntry ::=
     SEQUENCE {
         nncPktVcl15MinIntNumber                  NncExtRelIntvlNumberType,
         nncPktVcl15MinIntCoS                     NncPktVclCoSType,
         nncPktVcl15MinIntState                   NncExtIntvlStateType,
         nncPktVcl15MinIntAbsoluteIntervalNumber  NncExtAbsIntvlNumberType,
         nncPktVcl15MinIntInOctets                NncExtCounter64,
         nncPktVcl15MinIntInUcastPkts             NncExtCounter64,
         nncPktVcl15MinIntInMulticastPkts         NncExtCounter64,
         nncPktVcl15MinIntInBroadcastPkts         NncExtCounter64,
         nncPktVcl15MinIntInDiscards              NncExtCounter64,
         nncPktVcl15MinIntInErrors                NncExtCounter64,
         nncPktVcl15MinIntOutOctets               NncExtCounter64,
         nncPktVcl15MinIntOutUcastPkts            NncExtCounter64,
         nncPktVcl15MinIntOutMulticastPkts        NncExtCounter64,
         nncPktVcl15MinIntOutBroadcastPkts        NncExtCounter64,
         nncPktVcl15MinIntOutDiscards             NncExtCounter64,
         nncPktVcl15MinIntOutErrors               NncExtCounter64
     }


   nncPktVcl15MinIntNumber     OBJECT-TYPE
        SYNTAX                  NncExtRelIntvlNumberType
        MAX-ACCESS              not-accessible
        STATUS                  current
        DESCRIPTION             "The interval number (N) of the statistics in
                                this row."
   ::= { nncPktVcl15MinIntEntry 1 }


   nncPktVcl15MinIntCoS     OBJECT-TYPE
       SYNTAX      NncPktVclCoSType
       MAX-ACCESS  not-accessible
       STATUS      current
       DESCRIPTION
               "The Class of Service provided for the cells in
                the current interval."
   ::= {nncPktVcl15MinIntEntry 2 }


   nncPktVcl15MinIntState      OBJECT-TYPE
        SYNTAX                  NncExtIntvlStateType
        MAX-ACCESS              read-only
        STATUS                  current
        DESCRIPTION             "The state of the interval represented by
                                this row. The object provides a status for
                                those entries which have been reset by the
                                user, or have been subject to a wall clock
                                time change.
                                "
    ::= { nncPktVcl15MinIntEntry 3 }

    nncPktVcl15MinIntAbsoluteIntervalNumber     OBJECT-TYPE
        SYNTAX                  NncExtAbsIntvlNumberType
        MAX-ACCESS              read-only
        STATUS                  current
        DESCRIPTION             "The absolute interval number of this
                                interval."
    ::= { nncPktVcl15MinIntEntry 4 }

    nncPktVcl15MinIntInOctets OBJECT-TYPE
        SYNTAX      NncExtCounter64
        MAX-ACCESS  read-only
        STATUS      current
        DESCRIPTION
               "The total number of octets received on the interface,
               including protocol overhead, but excluding ATMs & AAL
               overhead.  This object is a 64-bit version of ifInOctets.

               Discontinuities in the value of this counter can occur
               at re-initialization of the management system, or if the
               VCL is disconnected"
     ::= { nncPktVcl15MinIntEntry 5 }


    nncPktVcl15MinIntInUcastPkts OBJECT-TYPE
        SYNTAX      NncExtCounter64
        MAX-ACCESS  read-only
        STATUS      current
        DESCRIPTION
               "The number of packets, delivered by this sub-layer to
               a higher (sub-)layer, which were not addressed to a
               multicast or broadcast address at this sub-layer.
               This object is a 64-bit version of ifInUcastPkts.

               Discontinuities in the value of this counter can occur
               at re-initialization of the management system, or if the
               VCL is disconnected"
    ::= { nncPktVcl15MinIntEntry 6 }

    nncPktVcl15MinIntInMulticastPkts OBJECT-TYPE
        SYNTAX      NncExtCounter64
        MAX-ACCESS  read-only
        STATUS      current
        DESCRIPTION
               "The number of packets, delivered by this sub-layer to
               a higher (sub-)layer, which were addressed to a
               multicast address at this sub-layer.  For a MAC layer
               protocol, this includes both Group and Functional
               addresses.  This object is a 64-bit version of
               ifInMulticastPkts.

               Discontinuities in the value of this counter can occur
               at re-initialization of the management system, or if the
               VCL is disconnected"
    ::= { nncPktVcl15MinIntEntry 7 }

    nncPktVcl15MinIntInBroadcastPkts OBJECT-TYPE
        SYNTAX      NncExtCounter64
        MAX-ACCESS  read-only
        STATUS      current
        DESCRIPTION
               "The number of packets, delivered by this sub-layer to
               a higher (sub-)layer, which were addressed to a
               broadcast address at this sub-layer.  This object is a
               64-bit version of ifInBroadcastPkts.

               Discontinuities in the value of this counter can occur
               at re-initialization of the management system, or if the
               VCL is disconnected"
    ::= { nncPktVcl15MinIntEntry 8 }
 
    nncPktVcl15MinIntInDiscards OBJECT-TYPE
        SYNTAX      NncExtCounter64
        MAX-ACCESS  read-only
        STATUS      current
        DESCRIPTION
               "The number of inbound packets which were chosen to be
               discarded even though no errors had been detected to
               prevent their being deliverable to a higher-layer
               protocol.  One possible reason for discarding such a
               packet could be to free up buffer space.

               Discontinuities in the value of this counter can occur
               at re-initialization of the management system, or if the
               VCL is disconnected"
    ::= { nncPktVcl15MinIntEntry 9 }


    nncPktVcl15MinIntInErrors OBJECT-TYPE
        SYNTAX      NncExtCounter64
        MAX-ACCESS  read-only
        STATUS      current
        DESCRIPTION
               "For packet-oriented interfaces, the number of inbound
               packets that contained errors preventing them from
               being deliverable to a higher-layer protocol.  For
               character-oriented or fixed-length interfaces, the
               number of inbound transmission units that contained
               errors preventing them from being deliverable to a
               higher-layer protocol.

               Discontinuities in the value of this counter can occur
               at re-initialization of the management system, or if the
               VCL is disconnected"
    ::= { nncPktVcl15MinIntEntry 10 }


    nncPktVcl15MinIntOutOctets OBJECT-TYPE
        SYNTAX      NncExtCounter64
        MAX-ACCESS  read-only
        STATUS      current
        DESCRIPTION
               "The total number of octets transmitted out of the
               interface, including protocol overhead, but excluding ATMs
               & AAL overhead.  This object is a 64-bit version of
               ifOutOctets.

               Discontinuities in the value of this counter can occur
               at re-initialization of the management system, or if the
               VCL is disconnected"
    ::= { nncPktVcl15MinIntEntry 11 }
 

    nncPktVcl15MinIntOutUcastPkts OBJECT-TYPE
        SYNTAX      NncExtCounter64
        MAX-ACCESS  read-only
        STATUS      current
        DESCRIPTION
               "The total number of packets that higher-level
               protocols requested be transmitted, and which were not
               addressed to a multicast or broadcast address at this
               sub-layer, including those that were discarded or not
               sent.  This object is a 64-bit version of
               ifOutUcastPkts.

               Discontinuities in the value of this counter can occur
               at re-initialization of the management system, or if the
               VCL is disconnected"
       ::= { nncPktVcl15MinIntEntry 12 }

    nncPktVcl15MinIntOutMulticastPkts OBJECT-TYPE
        SYNTAX      NncExtCounter64
        MAX-ACCESS  read-only
        STATUS      current
        DESCRIPTION
               "The total number of packets that higher-level
               protocols requested be transmitted, and which were
               addressed to a multicast address at this sub-layer,
               including those that were discarded or not sent.  For
               a MAC layer protocol, this includes both Group and
               Functional addresses.  This object is a 64-bit version
               of ifOutMulticastPkts.
               Discontinuities in the value of this counter can occur
               at re-initialization of the management system, or if the
               VCL is disconnected"
    ::= { nncPktVcl15MinIntEntry 13 }

    nncPktVcl15MinIntOutBroadcastPkts OBJECT-TYPE
        SYNTAX      NncExtCounter64
        MAX-ACCESS  read-only
        STATUS      current
        DESCRIPTION
               "The total number of packets that higher-level
               protocols requested be transmitted, and which were
               addressed to a broadcast address at this sub-layer,
               including those that were discarded or not sent.  This
               object is a 64-bit version of ifOutBroadcastPkts.

               Discontinuities in the value of this counter can occur
               at re-initialization of the management system, or if the
               VCL is disconnected"
     ::= { nncPktVcl15MinIntEntry 14 }

    nncPktVcl15MinIntOutDiscards OBJECT-TYPE
        SYNTAX      NncExtCounter64
        MAX-ACCESS  read-only
        STATUS      current
        DESCRIPTION
               "The number of outbound packets which were chosen to
               be discarded even though no errors had been detected
               to prevent their being transmitted.  One possible
               reason for discarding such a packet could be to free
               up buffer space.

               Discontinuities in the value of this counter can occur
               at re-initialization of the management system, or if the
               VCL is disconnected"
    ::= { nncPktVcl15MinIntEntry 15 }

    nncPktVcl15MinIntOutErrors OBJECT-TYPE
        SYNTAX      NncExtCounter64
        MAX-ACCESS  read-only
        STATUS      current
        DESCRIPTION
               "For packet-oriented interfaces, the number of
               outbound packets that could not be transmitted because
               of errors.  For character-oriented or fixed-length
               interfaces, the number of outbound transmission units
               that could not be transmitted because of errors.

               Discontinuities in the value of this counter can occur
               at re-initialization of the management system, or if the
               VCL is disconnected"
    ::= { nncPktVcl15MinIntEntry 16 }



-------------------------------------------------------------------------------
-- Virtual Channel Links Statistics Table
-------------------------------------------------------------------------------

    nncPktVclStatTable       OBJECT-TYPE 
        SYNTAX                  SEQUENCE OF NncPktVclStatEntry 
        MAX-ACCESS              not-accessible
        STATUS                  current
        DESCRIPTION             "The nncPktVclStatTable contains objects
                                for monitoring the accumulated packet performance 
                                of a VCL since measurement started on the VCL."
    ::= { nncPktStatisticsObjects 3 }


    nncPktVclStatEntry       OBJECT-TYPE 
        SYNTAX                  NncPktVclStatEntry 
        MAX-ACCESS              not-accessible
        STATUS                  current
        DESCRIPTION             "An entry in the Stat table.
                                Each conceptual row contains accumulated 
                                stpacket atistics for a particular VCL."
        INDEX                   { ifIndex, atmVclVpi, atmVclVci, nncPktVclStatCoS }
    ::= { nncPktVclStatTable 1 }

    NncPktVclStatEntry ::=
      SEQUENCE {
         nncPktVclStatCoS                     NncPktVclCoSType,
         nncPktVclStatInOctets                NncExtCounter64,
         nncPktVclStatInUcastPkts             NncExtCounter64,
         nncPktVclStatInMulticastPkts         NncExtCounter64,
         nncPktVclStatInBroadcastPkts         NncExtCounter64,
         nncPktVclStatInDiscards              NncExtCounter64,
         nncPktVclStatInErrors                NncExtCounter64,
         nncPktVclStatOutOctets               NncExtCounter64,
         nncPktVclStatOutUcastPkts            NncExtCounter64,
         nncPktVclStatOutMulticastPkts        NncExtCounter64,
         nncPktVclStatOutBroadcastPkts        NncExtCounter64,
         nncPktVclStatOutDiscards             NncExtCounter64,
         nncPktVclStatOutErrors               NncExtCounter64
      }
  
    nncPktVclStatCoS     OBJECT-TYPE
       SYNTAX      NncPktVclCoSType
       MAX-ACCESS  not-accessible
       STATUS      current
       DESCRIPTION
               "The Class of Service provided for the cells in
                the current interval."
    ::= { nncPktVclStatEntry 1 }  

    nncPktVclStatInOctets OBJECT-TYPE
       SYNTAX      NncExtCounter64
       MAX-ACCESS  read-only
       STATUS      current
       DESCRIPTION
               "The total number of octets received on the interface,
               including protocol overhead, but excluding ATMs & AAL
               overhead.  This object is a 64-bit version of ifInOctets.

               Discontinuities in the value of this counter can occur
               at re-initialization of the management system, or if the
               VCL is disconnected"
    ::= { nncPktVclStatEntry 2 }


    nncPktVclStatInUcastPkts OBJECT-TYPE
       SYNTAX      NncExtCounter64
       MAX-ACCESS  read-only
       STATUS      current
       DESCRIPTION
               "The number of packets, delivered by this sub-layer to
               a higher (sub-)layer, which were not addressed to a
               multicast or broadcast address at this sub-layer.
               This object is a 64-bit version of ifInUcastPkts.

               Discontinuities in the value of this counter can occur
               at re-initialization of the management system, or if the
               VCL is disconnected"
     ::= { nncPktVclStatEntry 3 }

     nncPktVclStatInMulticastPkts OBJECT-TYPE
        SYNTAX      NncExtCounter64
        MAX-ACCESS  read-only
        STATUS      current
        DESCRIPTION
               "The number of packets, delivered by this sub-layer to
               a higher (sub-)layer, which were addressed to a
               multicast address at this sub-layer.  For a MAC layer
               protocol, this includes both Group and Functional
               addresses.  This object is a 64-bit version of
               ifInMulticastPkts.

               Discontinuities in the value of this counter can occur
               at re-initialization of the management system, or if the
               VCL is disconnected"
     ::= { nncPktVclStatEntry 4 }

     nncPktVclStatInBroadcastPkts OBJECT-TYPE
        SYNTAX      NncExtCounter64
        MAX-ACCESS  read-only
        STATUS      current
        DESCRIPTION
               "The number of packets, delivered by this sub-layer to
               a higher (sub-)layer, which were addressed to a
               broadcast address at this sub-layer.  This object is a
               64-bit version of ifInBroadcastPkts.

               Discontinuities in the value of this counter can occur
               at re-initialization of the management system, or if the
               VCL is disconnected"
     ::= { nncPktVclStatEntry 5 }
 
     nncPktVclStatInDiscards OBJECT-TYPE
        SYNTAX      NncExtCounter64
        MAX-ACCESS  read-only
        STATUS      current
        DESCRIPTION
               "The number of inbound packets which were chosen to be
               discarded even though no errors had been detected to
               prevent their being deliverable to a higher-layer
               protocol.  One possible reason for discarding such a
               packet could be to free up buffer space.

               Discontinuities in the value of this counter can occur
               at re-initialization of the management system, or if the
               VCL is disconnected"
     ::= { nncPktVclStatEntry 6 }


     nncPktVclStatInErrors OBJECT-TYPE
        SYNTAX      NncExtCounter64
        MAX-ACCESS  read-only
        STATUS      current
        DESCRIPTION
               "For packet-oriented interfaces, the number of inbound
               packets that contained errors preventing them from
               being deliverable to a higher-layer protocol.  For
               character-oriented or fixed-length interfaces, the
               number of inbound transmission units that contained
               errors preventing them from being deliverable to a
               higher-layer protocol.

               Discontinuities in the value of this counter can occur
               at re-initialization of the management system, or if the
               VCL is disconnected"
     ::= { nncPktVclStatEntry 7 }


     nncPktVclStatOutOctets OBJECT-TYPE
        SYNTAX      NncExtCounter64
        MAX-ACCESS  read-only
        STATUS      current
        DESCRIPTION
               "The total number of octets transmitted out of the
               interface, including protocol overhead, but excluding ATMs
               & AAL overhead.  This object is a 64-bit version of
               ifOutOctets.

               Discontinuities in the value of this counter can occur
               at re-initialization of the management system, or if the
               VCL is disconnected"
     ::= { nncPktVclStatEntry 8 }
 

     nncPktVclStatOutUcastPkts OBJECT-TYPE
        SYNTAX      NncExtCounter64
        MAX-ACCESS  read-only
        STATUS      current
        DESCRIPTION
               "The total number of packets that higher-level
               protocols requested be transmitted, and which were not
               addressed to a multicast or broadcast address at this
               sub-layer, including those that were discarded or not
               sent.  This object is a 64-bit version of
               ifOutUcastPkts.

               Discontinuities in the value of this counter can occur
               at re-initialization of the management system, or if the
               VCL is disconnected"
     ::= { nncPktVclStatEntry 9 }

     nncPktVclStatOutMulticastPkts OBJECT-TYPE
        SYNTAX      NncExtCounter64
        MAX-ACCESS  read-only
        STATUS      current
        DESCRIPTION
               "The total number of packets that higher-level
               protocols requested be transmitted, and which were
               addressed to a multicast address at this sub-layer,
               including those that were discarded or not sent.  For
               a MAC layer protocol, this includes both Group and
               Functional addresses.  This object is a 64-bit version
               of ifOutMulticastPkts.
               Discontinuities in the value of this counter can occur
               at re-initialization of the management system, or if the
               VCL is disconnected"
     ::= { nncPktVclStatEntry 10 }

     nncPktVclStatOutBroadcastPkts OBJECT-TYPE
        SYNTAX      NncExtCounter64
        MAX-ACCESS  read-only
        STATUS      current
        DESCRIPTION
               "The total number of packets that higher-level
               protocols requested be transmitted, and which were
               addressed to a broadcast address at this sub-layer,
               including those that were discarded or not sent.  This
               object is a 64-bit version of ifOutBroadcastPkts.

               Discontinuities in the value of this counter can occur
               at re-initialization of the management system, or if the
               VCL is disconnected"
     ::= { nncPktVclStatEntry 11 }

     nncPktVclStatOutDiscards OBJECT-TYPE
        SYNTAX      NncExtCounter64
        MAX-ACCESS  read-only
        STATUS      current
        DESCRIPTION
               "The number of outbound packets which were chosen to
               be discarded even though no errors had been detected
               to prevent their being transmitted.  One possible
               reason for discarding such a packet could be to free
               up buffer space.

               Discontinuities in the value of this counter can occur
               at re-initialization of the management system, or if the
               VCL is disconnected"
     ::= { nncPktVclStatEntry 12 }

     nncPktVclStatOutErrors OBJECT-TYPE
        SYNTAX      NncExtCounter64
        MAX-ACCESS  read-only
        STATUS      current
        DESCRIPTION
               "For packet-oriented interfaces, the number of
               outbound packets that could not be transmitted because
               of errors.  For character-oriented or fixed-length
               interfaces, the number of outbound transmission units
               that could not be transmitted because of errors.

               Discontinuities in the value of this counter can occur
               at re-initialization of the management system, or if the
               VCL is disconnected"
     ::= { nncPktVclStatEntry 13 }


-------------------------------------------------------------------------------
-- Non-table objects
-------------------------------------------------------------------------------

-------------------------------------------------------------------------------
-- Conformance Group Definitions
-------------------------------------------------------------------------------

        nncPktVcl15MinCurGroup         OBJECT-GROUP 
                OBJECTS {
                        nncPktVcl15MinCurState,
                        nncPktVcl15MinCurAbsoluteIntervalNumber,
                        nncPktVcl15MinCurInOctets,
                        nncPktVcl15MinCurInUcastPkts,
                        nncPktVcl15MinCurInMulticastPkts,
                        nncPktVcl15MinCurInBroadcastPkts,
                        nncPktVcl15MinCurInDiscards,
                        nncPktVcl15MinCurInErrors,
                        nncPktVcl15MinCurOutOctets,
                        nncPktVcl15MinCurOutUcastPkts,
                        nncPktVcl15MinCurOutMulticastPkts,
                        nncPktVcl15MinCurOutBroadcastPkts,
                        nncPktVcl15MinCurOutDiscards,
                        nncPktVcl15MinCurOutErrors
                }
                STATUS          current
                DESCRIPTION     "A collection of objects providing 15 Min
                                current statistics for a VCI endpoint"
                ::= { nncPktStatisticsGroups 5 }
 
        nncPktVcl15MinIntGroup        OBJECT-GROUP 
                OBJECTS {
                        nncPktVcl15MinIntAbsoluteIntervalNumber,
                        nncPktVcl15MinIntInOctets,
                        nncPktVcl15MinIntInUcastPkts,
                        nncPktVcl15MinIntInMulticastPkts,
                        nncPktVcl15MinIntInBroadcastPkts,
                        nncPktVcl15MinIntInDiscards,
                        nncPktVcl15MinIntInErrors,
                        nncPktVcl15MinIntOutOctets,
                        nncPktVcl15MinIntOutUcastPkts,
                        nncPktVcl15MinIntOutMulticastPkts,
                        nncPktVcl15MinIntOutBroadcastPkts,
                        nncPktVcl15MinIntOutDiscards,
                        nncPktVcl15MinIntOutErrors


                }
                STATUS          current
                DESCRIPTION     "A collection of objects providing 15 Min
                                interval statistics for a VCI endpoint"
                ::= { nncPktStatisticsGroups 6 }

        nncPktVclStatGroup        OBJECT-GROUP 
                OBJECTS {
                        nncPktVclStatInOctets,
                        nncPktVclStatInUcastPkts,
                        nncPktVclStatInMulticastPkts,
                        nncPktVclStatInBroadcastPkts,
                        nncPktVclStatInDiscards,
                        nncPktVclStatInErrors,
                        nncPktVclStatOutOctets,
                        nncPktVclStatOutUcastPkts,
                        nncPktVclStatOutMulticastPkts,
                        nncPktVclStatOutBroadcastPkts,
                        nncPktVclStatOutDiscards,
                        nncPktVclStatOutErrors
                }
                STATUS          current
                DESCRIPTION     "A collection of objects providing cumulative
                                 statistics for a VCI endpoint"
        ::= { nncPktStatisticsGroups 7 }

        nncVclIntervalStateGroup        OBJECT-GROUP 
                OBJECTS {
                        nncPktVcl15MinCurState,
                        nncPktVcl15MinIntState
                }
                STATUS          current
                DESCRIPTION     "A collection of objects providing the state
                                 of intervals in the VCL current and interval
                                 tables."
        ::= { nncPktStatisticsGroups 8 }


-------------------------------------------------------------------------------
-- Compliance Statements (mandatory)
-------------------------------------------------------------------------------
        nncPktStatisticsCompliance      MODULE-COMPLIANCE
                STATUS          current
                DESCRIPTION     "The compliance statement for Newbridge SNMP
                                entities which have Vpl endpoints which 
                                perform Bridging or IP Routing over ATM."
                MODULE
                        MANDATORY-GROUPS {
                                nncPktVcl15MinCurGroup,
                                nncPktVcl15MinIntGroup
                        }

                GROUP  nncPktVclStatGroup
                       DESCRIPTION    "The implementation of the
                                       nncPktVclStatGroup is optional"


        ::= { nncPktStatisticsCompliances 1 } 


-------------------------------------------------------------------------------
--      Review Minutes 
-------------------------------------------------------------------------------
--      MINUTES-BEGIN
--              REVIEW-DATE  "1998.01.23"
--              BODY  "
--
--      
--      TO:     Andrew Paterson*, Ron Veenamen*, Silvie Dobrota*
--              Joseph Provine*, Jason Paau*
--      FROM:   David Fowler*
--
--
--      A meeting was help on 1998.01.23 to review PKTStatistics.mib.
--      Attendees are marked in the list above with *
--
--      Outcome
--
--      It was the consensus of the review team that this file is 
--      acceptable with the indicated modifications
--
--      Action Items
--      A1 - Jason Paau to update the MIB as indicated in D1 and as
--           resulting from the action items below.  To be completed
--           by 1998.01.30.
--           Status Closed
--           1998.01.30   Document has been updated and submitted for
--                        check-in.
-- 
--      A2 - David Fowler to determine the values of CoSType by taking
--           into consideration the values in 34SD0138.  To be completed
--           by 1998.01.30   
--           Status Closed
--           1998.01.30  The values to be used are:
--           1(all), 8(premium), 24(standard)
--
--      A3 - Ron Veenamen to determine if accumulatd stats are required
--           by 46020.  To be completed by 1998.01.30
--           Status Closed
--           1998.01.23  They are not required.
--
--      A4 - David Fowler to determin if accumulated stats are required
--           by Product Management.  To be completed by 1998.01.30
--           Status Closed
--           1998.01.24  They are not required in Phase 1 but would be
--                       useful.
--
--      A5 - David Fowler to determine which activity number to use
--           for the SNMP access to statistics work.  To be completed by
--           1998.01.30
--           Status Closed
--           1998.01.30  The activity number will be 34A0505.
--
--      Decisions
--      D1 - The file PKTStatistics will be updated in the following places:
--        a) Add CoS to VclStatEntry
--        b) Use Pkt as part of the name for accumulated stats
--        c) Update definitions for octet objects to indicate that they
--           count AAL5 payload only.  ATM or AAQL overhead is not counted.
--        d) Fix compliance statement to reflect only devices which perform
--           Bridging or IP Routing over ATM support this MIB.
--        e) Remove depth of historical strata
--        f) Remove counter tables and compliances
--      "
--
--      END-MINUTES
-------------------------------------------------------------------------------
END -- DEFINITION OF NNC-PKT-STATISTICS-MIB
