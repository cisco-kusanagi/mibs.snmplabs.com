-- Network Systems Corporation Enterprise MIB for Switch Management
-- Wed Apr 15 1993
-- J. Miller

-- This MIB is to be used in conjunction with the NSC standard MIB to
-- define Switch specific information.  This MIB is common across all
-- NSC HIPPI switches.

		NSCPS32-MIB DEFINITIONS ::= BEGIN
 
		IMPORTS
		   Gauge, OBJECT-TYPE, enterprises, experimental, TimeTicks, IpAddress, Counter
			   FROM RFC1155-SMI
		   DisplayString, PhysAddress
			   FROM RFC1213-MIB
		   Party
			   FROM RFC1353-MIB  -- SNMP Party MIB
		   nsc, nscProducts
			   FROM NSC-MIB;

	nscHippiSwitch OBJECT IDENTIFIER ::= { nscProducts 4 }

    --  textual conventions

	-- For ease of lookup, the following are actually defined
	-- in the NSC MIB but are supplied here as comments.
	-- The content of this MIB definition is to define the
	-- objects under the nscHippiSwitch node.

	-- nsc		 	OBJECT IDENTIFIER ::= { enterprises 10 }
	-- nscMib	 	OBJECT IDENTIFIER ::= { nsc 2 }
	-- nscProducts	 	OBJECT IDENTIFIER ::= { nscMib 1 }
	--   nscDevices	 	OBJECT IDENTIFIER ::= { nscProducts 1 }
	--     nscObj	 	OBJECT IDENTIFIER ::= { nscDevices 1 }
	--   nscHippiSwitch	OBJECT IDENTIFIER ::= { nscProducts 4 }
	--     ps32General	OBJECT IDENTIFIER ::= { nscHippiSwitch 1 }
        --     ps32PowerSupply	OBJECT IDENTIFIER ::= { nscHippiSwitch 2 }
	--     ps32Environ	OBJECT IDENTIFIER ::= { nscHippiSwitch 3 }
	--     ps32Slot		OBJECT IDENTIFIER ::= { nscHippiSwitch 4 }
	--     ps32Port		OBJECT IDENTIFIER ::= { nscHippiSwitch 5 }
	--     ps32Pathway	OBJECT IDENTIFIER ::= { nscHippiSwitch 6 }
	--     ps32FieldDir	OBJECT IDENTIFIER ::= { nscHippiSwitch 7 }
	--     ps32FieldDisp	OBJECT IDENTIFIER ::= { nscHippiSwitch 8 }
	--     ps32FieldSet	OBJECT IDENTIFIER ::= { nscHippiSwitch 9 }


		-- Switch type and general information.

		ps32General OBJECT IDENTIFIER ::= { nscHippiSwitch 1 }

		ps32SwitchDescr OBJECT-TYPE
		   SYNTAX  DisplayString (SIZE (0..79))
		   ACCESS  read-only
		   STATUS  mandatory
		   DESCRIPTION
		       "A description of the NSC HIPPI switch."
		::= { ps32General 1 }

		ps32SwitchVersion  OBJECT-TYPE
		   SYNTAX  DisplayString (SIZE (0..255))
		   ACCESS  read-only
		   STATUS  mandatory
		   DESCRIPTION
		      "A textual description of the version/revision
                      level for the switch's software."
		::= { ps32General 2 }

		ps32SwitchDate OBJECT-TYPE
		   SYNTAX   DisplayString (SIZE (0..79))
		   ACCESS   read-write
		   STATUS   mandatory
		   DESCRIPTION
		       "The current date as kept in the real time clock
		       in the NVRAM chip on the switch board."
		::= { ps32General 3 }

		ps32SwitchTime OBJECT-TYPE
		   SYNTAX   DisplayString (SIZE (0..79))
		   ACCESS   read-write
		   STATUS   mandatory
		   DESCRIPTION
		       "The current date as kept in the real time clock
		       in the NVRAM chip on the switch board."
		::= { ps32General 4 }

		ps32SwitchAdminStatus OBJECT-TYPE
		    SYNTAX  INTEGER {
                       unknown(1),             --  none of the following
                       enable(2),
                       disable(3),
                       reset(4),
                       programload(5),
                       test(6)
              	       }
              	    ACCESS  read-write
              	    STATUS  mandatory
              	    DESCRIPTION
                      "Provides the administratively desired state of
                      the NSC Hippi Switch.

                      The switch is activated by writing a value of
                      enable(2).

                      The switch may be de-activated by writing a value
                      of disable(3).  The switch is available for 
		      subsequent activation.

                      Writing a value of reset(4) specifies the switch
                      should initiate a reset sequence.

                      Writing a value of programload(5) specifies the
                      switch should initiate a program load sequence.

                      Writing a value of test(6) specifies the switch
                      should initiate a testing sequence."
		::= { ps32General 5 }

		ps32SwitchOperStatus OBJECT-TYPE
              	    SYNTAX  INTEGER {
                        other(1),               --  none of the following
                        invalid(2),
                        testing(3),
                        operational(4),
                        resetInProgress(5),
                        warning(6),
                        nonFatalError(7),
                        fatalError(8),
                        loading(10)
              	        }
              	    ACCESS  read-only
              	    STATUS  mandatory
              	    DESCRIPTION
                      "Provides operational status of the switch.  The
                      following are possible definitions of the values.
                      The exact definition of the values is
                      implementation specific.  A value of other(1)
                      implies some undetermined state, possibly as a
                      result of setting ps32SwitchAdminStatus to a value
                      of disable(3).  A value of invalid(2) could have
                      the possible meaning that the agent has no direct 
		      control of the switch.  A value of testing(3) may 
		      be a diagnostic state.  A value of operational(4) 
		      implies that the switch is running with no errors 
		      or warnings.
                      State resetInProgress(5) implies equivalent of
                      setting ps32SwitchAdminStatus to reset(4). The
                      states of warning(6), nonFatalError(7),
                      fatalError(8) reflect conditions detected during
                      operation.  The switch may or may not be still
                      functional.  State loading(10) is a result of
                      asserting programload(5) in ps32SwitchAdminStatus."
		::= { ps32General 6 }

		ps32SwitchPhysicalChanges  OBJECT-TYPE
		    SYNTAX   Counter
		    ACCESS   read-only
		    STATUS   mandatory
		    DESCRIPTION
                      "The number of physical changes that have occurred
                      in the chassis since the agent was warm/cold
                      started.  This includes additions and removal of
                      modules and entities.  Other uses are
                      implementation specific."
		::= { ps32General 7 }

		ps32SwitchDiagnosticReg  OBJECT-TYPE
		    SYNTAX   DisplayString (SIZE (0..3))
		    ACCESS   read-only
		    STATUS   mandatory
		    DESCRIPTION
                      "The register on the NSC Hippi Switch Control Board
		      that contains many items of information on the 
		      configuration and performance of the switch."
		::= { ps32General 8 }

		ps32SwitchMiscellanReg  OBJECT-TYPE
		    SYNTAX   DisplayString (SIZE (0..3))
		    ACCESS   read-only
		    STATUS   mandatory
		    DESCRIPTION
                      "The register on the NSC Hippi Switch Control Board
		      that contains many items of miscellaneous data with
		      respect to the switch."
		::= { ps32General 9 }

		ps32SwitchDipSwitchReg  OBJECT-TYPE
		    SYNTAX   DisplayString (SIZE (0..3))
		    ACCESS   read-only
		    STATUS   mandatory
		    DESCRIPTION
                      "The register on the NSC Hippi Switch Control Board
		      that contains the dip switch settings and other
		      sensory information."
		::= { ps32General 10 }


		-- the Power Supply table

		ps32PowerSupply  OBJECT IDENTIFIER ::= { nscHippiSwitch 2 }

          	ps32NumPowerSupplies  OBJECT-TYPE
              	   SYNTAX  INTEGER (1..3)
              	   ACCESS  read-only
              	   STATUS  mandatory
              	   DESCRIPTION
                      "Number of power supplies installed in this chassis."
              	::= { ps32PowerSupply 1 }

		ps32PowerSupplyTable OBJECT-TYPE
		    SYNTAX SEQUENCE OF PS32PowerSupplyEntry
		    ACCESS not-accessible
		    STATUS mandatory
		    DESCRIPTION
		       "A list of power supply entries, one for each
			power supply in the NSC Hippi Switch."
		    --DEFAULT test-function test-ps32PowerSupplyField
		    --DEFAULT next-function next-ps32PowerSupplyField
		::= { ps32PowerSupply 2 }

		ps32PowerSupplyEntry OBJECT-TYPE
		    SYNTAX PS32PowerSupplyEntry
		    ACCESS not-accessible
		    STATUS mandatory
		    DESCRIPTION
		            "Values for a power supply."
		    INDEX { ps32PowerSupplyIndex }
		::= { ps32PowerSupplyTable 1 }

		PS32PowerSupplyEntry ::=
		    SEQUENCE {
		        ps32PowerSupplyIndex
		            INTEGER,
		        ps32PowerSupplyDescr
		            DisplayString,
		        ps32PowerSupplyAdminStatus
		            INTEGER,
		        ps32PowerSupplyOperStatus
		            INTEGER,
		        ps32PowerSupplyHealthText
		            DisplayString,
		        ps32PowerSupplyWarnings
		            Counter,
		        ps32PowerSupplyFailures
		            Counter
		    }

		ps32PowerSupplyIndex OBJECT-TYPE
		    SYNTAX INTEGER
		    ACCESS read-only
		    STATUS mandatory
		    DESCRIPTION
		            "An index value that uniquely identifies a power
		            supply installed in the NSC Hippi Switch."
		::= { ps32PowerSupplyEntry 1 }

		ps32PowerSupplyDescr OBJECT-TYPE
		    SYNTAX DisplayString (SIZE (0..255))
		    ACCESS read-only
		    STATUS mandatory
		    DESCRIPTION
		            "A textual description of the power supply,
		            including the vendor's name and version."
		::= { ps32PowerSupplyEntry 2 }

		ps32PowerSupplyAdminStatus OBJECT-TYPE
		    SYNTAX INTEGER {
		        unknown(1),
		        enable(2),
		        disable(3) }
		    ACCESS read-write
		    STATUS mandatory
		    DESCRIPTION
		            "Desired status of the power supply."
		::= { ps32PowerSupplyEntry 3 }

		ps32PowerSupplyOperStatus OBJECT-TYPE
		    SYNTAX INTEGER {
		        unknown(1),
		        empty(2),
		        disabled(3),
		        bad(4),
		        warning(5),
		        standby(6),
		        engaged(7),
		        redundant(8) }
		    ACCESS read-only
		    STATUS mandatory
		    DESCRIPTION
		            "Actual status of the power supply:

		            - unknown(1) - status not known.
		            - empty(2) - no power supply installed in slot
		            - disabled(3) - unable to supply power - control
			    register has requested this supply be disabled.
		            - bad(4) - unable to supply power due to failure
		            - warning(5) - supplying power but an output or
		            sensor is bad or warning
		            - standby(6) - believed usable but not supplying
		            power
		            - engaged(7) - supplying power
		            - redundant(8) - supplying power but not needed

		            It is an implementation specific matter whether
		            the agent keeps entries with status unknown(1) or
		            empty(2) in the table."
		::= { ps32PowerSupplyEntry 4 }

		ps32PowerSupplyHealthText OBJECT-TYPE
		    SYNTAX DisplayString (SIZE (0..255))
		    ACCESS read-only
		    STATUS mandatory
		    DESCRIPTION
		            "A textual description of the power supply's
		            operational status. Agents may use this string to
		            provide detailed information on current failures,
		            including how they were detected, and/or
		            instructions for problem resolution. The contents
		            are agent-specific."
		::= { ps32PowerSupplyEntry 5 }

		ps32PowerSupplyWarnings OBJECT-TYPE
		    SYNTAX Counter
		    ACCESS read-only
		    STATUS mandatory
		    DESCRIPTION
		            "The number of times ps32PowerSupplyOperStatus has
		            gone to warning(5)."
		::= { ps32PowerSupplyEntry 6 }

		ps32PowerSupplyFailures OBJECT-TYPE
		    SYNTAX Counter
		    ACCESS read-only
		    STATUS mandatory
		    DESCRIPTION
		            "The number of times ps32PowerSupplyOperStatus has
		            gone to bad(4)."
		::= { ps32PowerSupplyEntry 7 }

		-- the Power Supply Output table

          	ps32NumPowerOutputs  OBJECT-TYPE
              	   SYNTAX  INTEGER (1..65535)
              	   ACCESS  read-only
              	   STATUS  mandatory
              	   DESCRIPTION
                      "Number of power supply outputs (total) in the switch."
		::= { ps32PowerSupply 3 }

		ps32PowerOutputTable OBJECT-TYPE
		    SYNTAX SEQUENCE OF PS32PowerOutputEntry
		    ACCESS not-accessible
		    STATUS mandatory
		    DESCRIPTION
		            "A list of power supply output entries, one for
		            each output of each power supply in the chassis."
	      	    --DEFAULT test-function test-ps32PowerOutputField
	      	    --DEFAULT next-function next-ps32PowerOutputField
		::= { ps32PowerSupply 4 }

		ps32PowerOutputEntry OBJECT-TYPE
		    SYNTAX PS32PowerOutputEntry
		    ACCESS not-accessible
		    STATUS mandatory
		    DESCRIPTION
		            "Values for a power supply output."
		    INDEX { ps32PowerSupplyIndex, ps32PowerOutputIndex }
		::= { ps32PowerOutputTable 1 }

		PS32PowerOutputEntry ::=
		    SEQUENCE {
		        ps32PowerOutputIndex
		            INTEGER,
		        ps32PowerOutputStatus
		            INTEGER,
		        ps32PowerOutputNominalVoltage
		            Gauge,
		        ps32PowerOutputOfferedVoltage
		            Gauge,
		        ps32PowerOutputWarnings
		            Counter,
		        ps32PowerOutputFailures
		            Counter
		    }

		ps32PowerOutputIndex OBJECT-TYPE
		    SYNTAX INTEGER
		    ACCESS read-only
		    STATUS mandatory
		    DESCRIPTION
		            "An index value that uniquely identifies an output
		            for the power supply."
		::= { ps32PowerOutputEntry 1 }

		ps32PowerOutputStatus OBJECT-TYPE
		    SYNTAX INTEGER {
		        unknown(1),
		        bad(2),
		        warning(3),
		        good(4) }
		    ACCESS read-only
		    STATUS mandatory
		    DESCRIPTION
		            "Actual status of the power supply:

		            - unknown(1)     status not known
		            - bad(2)         unable to supply power due to
		            failure
		            - warning(3)     supplying power but marginally
		            - good(4)        supplying power

		            It is an implementation specific matter whether
		            the agent keeps entries with status unknown(1) in
		            the table.  If unknown(1), offered values and
		            counters are meaningless."
		::= { ps32PowerOutputEntry 2 }

		ps32PowerOutputNominalVoltage OBJECT-TYPE
		    SYNTAX INTEGER -- Gauge is unsigned integer
		    ACCESS read-only
		    STATUS mandatory
		    DESCRIPTION
		            "In hundredths of a volt, the voltage
		            the output is supposed to supply, such
		            as -5, +5, +12, -15, etc."
		::= { ps32PowerOutputEntry 3 }

		ps32PowerOutputOfferedVoltage OBJECT-TYPE
		    SYNTAX INTEGER
		    ACCESS read-only
		    STATUS mandatory
		    DESCRIPTION
		            "In hundredths of a volt, the voltage
		            actually supplied by the power output."
		::= { ps32PowerOutputEntry 4 }

		ps32PowerOutputWarnings OBJECT-TYPE
		    SYNTAX Counter
		    ACCESS read-only
		    STATUS mandatory
		    DESCRIPTION
		        "The number of times ps32PowerOutputStatus has 
			gone to warning(3)."
		::= { ps32PowerOutputEntry 5 }

		ps32PowerOutputFailures OBJECT-TYPE
		    SYNTAX Counter
		    ACCESS read-only
		    STATUS mandatory
		    DESCRIPTION
		            "The number of times ps32PowerOutputStatus has 
			    gone to bad(2)."
		::= { ps32PowerOutputEntry 6 }


		-- the Environment table.

		ps32Environ OBJECT IDENTIFIER ::= { nscHippiSwitch 3 }

          	ps32NumEnvironmentSensors  OBJECT-TYPE
              	   SYNTAX  INTEGER (1..65535)
              	   ACCESS  read-only
              	   STATUS  mandatory
              	   DESCRIPTION
                      "Number of environment sensors in this chassis."
              	::= { ps32Environ 1 }

		ps32EnvironTable OBJECT-TYPE
		    SYNTAX SEQUENCE OF PS32EnvironEntry
		    ACCESS not-accessible
		    STATUS mandatory
		    DESCRIPTION
		            "A list of environmental entries, one for
		            each environmental sensor in the chassis."
	      	    --DEFAULT test-function test-ps32EnvironField
	      	    --DEFAULT next-function next-ps32EnvironField
		::= { ps32Environ 2 }

		ps32EnvironEntry OBJECT-TYPE
		    SYNTAX PS32EnvironEntry
		    ACCESS not-accessible
		    STATUS mandatory
		    DESCRIPTION
		            "Values for an environmental sensor."
		    INDEX { ps32EnvironIndex }
		::= { ps32EnvironTable 1 }

		PS32EnvironEntry ::=
		    SEQUENCE {
		        ps32EnvironIndex
		            INTEGER,
		        ps32EnvironSensor
		            INTEGER,
		        ps32EnvironStatus
		            INTEGER,
		        ps32EnvironWarnings
		            Counter,
		        ps32EnvironFailures
		            Counter,
		        ps32EnvironDescriptor
		            DisplayString,
		        ps32EnvironHealthText
		            DisplayString
		    }

		ps32EnvironIndex OBJECT-TYPE
		    SYNTAX INTEGER
		    ACCESS read-only
		    STATUS mandatory
		    DESCRIPTION
		            "Index added to get draft past the MIB
		            compiler.  This needs to be fixed by the
		            working group."
		::= { ps32EnvironEntry 1 }

		ps32EnvironSensor OBJECT-TYPE
		    SYNTAX  INTEGER {
		        unknown(1),             --  none of the following
		        logicovertemp(2),
		        fanfailure(3)
		    }
		    ACCESS read-only
		    STATUS mandatory
		    DESCRIPTION
		            "The identification of an environmental
		            sensor.  Other AutonomousType values may be
		            defined elsewhere, in association with
		            specific protocols.  However, this document
		            assigns those of known interest as of this
		            writing."
		::= { ps32EnvironEntry 2 }

		ps32EnvironStatus OBJECT-TYPE
		    SYNTAX INTEGER {
		        unknown(1),
		        bad(2),
		        warning(3),
		        good(4) }
		    ACCESS read-only
		    STATUS mandatory
		    DESCRIPTION
		            "Actual status indicated by the sensor.  It is
		            an implementation specific matter whether the
		            agent keeps entries with status unknown(1) in
		            the table.  If unknown(1), counters are
		            meaningless."
		::= { ps32EnvironEntry 3 }

		ps32EnvironWarnings OBJECT-TYPE
		    SYNTAX Counter
		    ACCESS read-only
		    STATUS mandatory
		    DESCRIPTION
		            "The number of times ps32EnvironStatus has gone
		            to warning(3)."
		::= { ps32EnvironEntry 4 }

		ps32EnvironFailures OBJECT-TYPE
		    SYNTAX Counter
		    ACCESS read-only
		    STATUS mandatory
		    DESCRIPTION
		        "The number of times ps32EnvironStatus has gone
		        to bad(2)."
		::= { ps32EnvironEntry 5 }

		ps32EnvironDescriptor OBJECT-TYPE
		    SYNTAX DisplayString (SIZE (0..79))
		    ACCESS read-only
		    STATUS mandatory
		    DESCRIPTION
		        "A textual description of the environment sensor."
		::= { ps32EnvironEntry 6 }

		ps32EnvironHealthText OBJECT-TYPE
		    SYNTAX DisplayString (SIZE (0..79))
		    ACCESS read-only
		    STATUS mandatory
		    DESCRIPTION
		        "A textual description of the current status of the
			environment entity monitored by this sensor."
		::= { ps32EnvironEntry 7 }

		-- The slot table is a sparsely populated table consisting
		-- of one entry for each possible slot in the chassis.  The
		-- information included contains sufficient information to 
		-- identify the board and the installation time, which is 0
		-- except for a hot swap board that has been added during
		-- the current run.

		-- Slot table.

          	ps32Slot OBJECT IDENTIFIER ::= { nscHippiSwitch 4 }

          	ps32NumSlots  OBJECT-TYPE
              	   SYNTAX  INTEGER (1..65535)
              	   ACCESS  read-only
              	   STATUS  mandatory
              	   DESCRIPTION
                      "Number of slots in this chassis."
              	::= { ps32Slot 1 }

		ps32SlotTable OBJECT-TYPE
		   SYNTAX   SEQUENCE OF PS32SlotEntry
		   ACCESS   not-accessible
		   STATUS   mandatory
		   DESCRIPTION
		       "A densely populated table that can be used to
		       access individual slots in a HIPPI switch."
		   --DEFAULT test-function test-ps32Slot
		   --DEFAULT next-function next-ps32Slot
		::= { ps32Slot 2 }

		ps32SlotEntry OBJECT-TYPE
		   SYNTAX   PS32SlotEntry
		   ACCESS   not-accessible
		   STATUS   mandatory
		   DESCRIPTION
		       "An individual hippi switch slot entry consisting 
		       of all information required to monitor the status
		       of a given slot in the Hippi Switch."
		   INDEX { ps32SlotNumber }
		::= { ps32SlotTable 1 }

		PS32SlotEntry ::=
		   SEQUENCE {
        		ps32SlotNumber
			   INTEGER,
        		ps32SlotPartNumber
			   DisplayString,
        		ps32SlotBoardID
			   DisplayString,
        		ps32SlotBoardText
			   DisplayString,
          		ps32SlotLastChange
              	   	   TimeTicks
		   }

		ps32SlotNumber OBJECT-TYPE
		   SYNTAX   INTEGER (1..18)
		   ACCESS   read-only
		   STATUS   mandatory
		   DESCRIPTION
		       "The slot number in the switch.  Slot numbers are
		       officially designated as 0 through 18 in the switch
		       but each slot number is incremented in order to 
		       comply with SNMP standards."
		::= { ps32SlotEntry 1 }

		ps32SlotPartNumber OBJECT-TYPE
		   SYNTAX   DisplayString (SIZE (0..11))
		   ACCESS   read-only
		   STATUS   mandatory
		   DESCRIPTION
		       "The part number of the board residing in the slot."
		::= { ps32SlotEntry 2 }

		ps32SlotBoardID OBJECT-TYPE
		   SYNTAX   DisplayString (SIZE (0..5))
		   ACCESS   read-only
		   STATUS   mandatory
		   DESCRIPTION
		       "The identifier of the board residing in the slot."
		::= { ps32SlotEntry 3 }

		ps32SlotBoardText OBJECT-TYPE
		   SYNTAX   DisplayString (SIZE (0..79))
		   ACCESS   read-only
		   STATUS   mandatory
		   DESCRIPTION
		       "A textual description of the board residing in 
		       the slot."
		::= { ps32SlotEntry 4 }

          	ps32SlotLastChange OBJECT-TYPE
              	   SYNTAX  TimeTicks
              	   ACCESS  read-only
              	   STATUS  mandatory
              	   DESCRIPTION
                      "The value of MIB-II's sysUpTime (in the agent
                      supporting this chassis MIB) at which a module was
                      last inserted or removed from this slot.  If no
                      module has been inserted or removed from this slot
                      since the last time the network management system
                      was last re-initialized, then this object has a
                      zero value."
		::= { ps32SlotEntry 5 }


		-- The switch boards are accessed via the slot table but
		-- the slot table does not contain a method for discussing
		-- the hippi ports on the individual boards.  Since the
		-- access method to the ports usually isn't too concerned
		-- about the actual board that the port is on, a port table
		-- with a reverse reference to the slot table is defined
		-- to get to the port specfic information.  This port info-
		-- mation is stored in a densely populated table indexed by
		-- port number.

		-- HIPPI port table.

          	ps32Port OBJECT IDENTIFIER ::= { nscHippiSwitch 5 }

          	ps32MaximumPorts  OBJECT-TYPE
              	   SYNTAX  INTEGER (1..65535)
              	   ACCESS  read-only
              	   STATUS  mandatory
              	   DESCRIPTION
                      "Maximum number of ports in this chassis."
              	::= { ps32Port 1 }

          	ps32InstalledPorts  OBJECT-TYPE
              	   SYNTAX  INTEGER (1..65535)
              	   ACCESS  read-only
              	   STATUS  mandatory
              	   DESCRIPTION
                      "Number of ports actually installed in this chassis."
              	::= { ps32Port 2 }

		ps32PortTable OBJECT-TYPE
		   SYNTAX   SEQUENCE OF PS32PortEntry
		   ACCESS   not-accessible
		   STATUS   mandatory
		   DESCRIPTION
		       "A densely populated table that can be used to
		       access individual ports in a HIPPI switch."
		   --DEFAULT test-function test-ps32Port
		   --DEFAULT next-function next-ps32Port
		::= { ps32Port 3 }

		ps32PortEntry OBJECT-TYPE
		   SYNTAX   PS32PortEntry
		   ACCESS   not-accessible
		   STATUS   mandatory
		   DESCRIPTION
		       "An individual hippi switch port entry.  A switch
		       port contains input and output hippi device pointers."
		   INDEX { ps32PortNumber }
		::= { ps32PortTable 1 }

		PS32PortEntry ::=
		   SEQUENCE {
        		ps32PortNumber
			   INTEGER,
        		ps32PortBoard
			   OBJECT IDENTIFIER,
        		ps32PortInput
			   OBJECT IDENTIFIER,
        		ps32PortOutput
			   OBJECT IDENTIFIER,
        		ps32PortForce
			   INTEGER,
        		ps32PortCounterStatus
			   INTEGER,
        		ps32PortOverrunCount
			   INTEGER,
        		ps32PortSwitchRejectCount
			   INTEGER,
        		ps32PortCamponDelayCount
			   INTEGER,
        		ps32PortCurrentStatus
			   DisplayString,
        		ps32PortAdminStatus
			   INTEGER,
        		ps32PortOperStatus
			   INTEGER
		   }

		ps32PortNumber OBJECT-TYPE
		   SYNTAX   INTEGER (1..32)
		   ACCESS   read-only
		   STATUS   mandatory
		   DESCRIPTION
		       "The number of the hippi port."
		::= { ps32PortEntry 1 }

		ps32PortBoard OBJECT-TYPE
		   SYNTAX   OBJECT IDENTIFIER
		   ACCESS   read-only
		   STATUS   mandatory
		   DESCRIPTION
		       "The object identifier points to the PS32SlotEntry
		       for the board to allow users to locate information
		       about the board this port is located on."
		::= { ps32PortEntry 2 }

		ps32PortInput OBJECT-TYPE
		   SYNTAX   OBJECT IDENTIFIER
		   ACCESS   read-only
		   STATUS   mandatory
		   DESCRIPTION
		       "The object identifier points to the hippiEntry
		       for the HIPPI input device associated with this
		       port."
		::= { ps32PortEntry 3 }

		ps32PortOutput OBJECT-TYPE
		   SYNTAX   OBJECT IDENTIFIER
		   ACCESS   read-only
		   STATUS   mandatory
		   DESCRIPTION
		       "The object identifier points to the hippiEntry
		       for the HIPPI output device associated with this
		       port."
		::= { ps32PortEntry 4 }

		ps32PortForce OBJECT-TYPE
		   SYNTAX   INTEGER
		   ACCESS   read-write
		   STATUS   mandatory
		   DESCRIPTION
		       "This object displays the forced pathway that is
		       associated with this port.  If none is assigned
		       then the object has the value of -1.  Only one
		       output port is allowed for any particular input
		       port."
		::= { ps32PortEntry 5 }

		ps32PortCounterStatus OBJECT-TYPE
		   SYNTAX   INTEGER 
		   ACCESS   read-write
		   STATUS   mandatory
		   DESCRIPTION
		       "This object consists of a bit for each counter that
		       may have been overrun."
		::= { ps32PortEntry 6 }

		ps32PortOverrunCount OBJECT-TYPE
		   SYNTAX   INTEGER 
		   ACCESS   read-write
		   STATUS   mandatory
		   DESCRIPTION
		       "This object counts the overruns detected for this  
		       HIPPI port."
		::= { ps32PortEntry 7 }

		ps32PortSwitchRejectCount OBJECT-TYPE
		   SYNTAX   INTEGER 
		   ACCESS   read-write
		   STATUS   mandatory
		   DESCRIPTION
		       "This object consists of a bit for each counter that
		       may have been overrun."
		::= { ps32PortEntry 8 }

		ps32PortCamponDelayCount OBJECT-TYPE
		   SYNTAX   INTEGER 
		   ACCESS   read-write
		   STATUS   mandatory
		   DESCRIPTION
		       "This object counts the rejected connect attempts
		       using the Campon option."
		::= { ps32PortEntry 9 }

		ps32PortCurrentStatus OBJECT-TYPE
		   SYNTAX   DisplayString (SIZE (0..7))
		   ACCESS   read-only
		   STATUS   mandatory
		   DESCRIPTION
		       "This object consists of the status register at the 
		       instant of the last successful connection."
		::= { ps32PortEntry 10 }

		ps32PortAdminStatus OBJECT-TYPE
		   SYNTAX   INTEGER {
			unknown(1),
			enable(2),
			disable(3),
			reset(4),
			test(5),
			clrerrors(6),
			clrpaths(7),
			clrstats(8),
			clrall(9),
			rstrpath(10),
			savecfg(11),
			savepath(12)
		     }
		   ACCESS   read-write
		   STATUS   mandatory
		   DESCRIPTION
		       "This object allows various commands to be issued 
		       from the client and acted upon by the agent.  The
		       only commands supported currently are listed below.
			   1: unknown...not a supported command.
			   2: enable	activate the port requested.
			   3: disable	deactivate the port requested.
			   4: reset	reset the port requested.
			   5: test	run BIST upon the requested port.
			   6: clrerrors	clear current port errors.
			   7: clrpaths	clear the pathways assigned.
			   8: clrstats	clear the port's statistics.
			   9: clrall	clear errors, stats, and paths.
			  10: rstrpath	restore all pathways for this port.
			  11: savepath	save all pathways for this port.
			  12: savecfg 	save the configuration.
			These commands completely fulfill the actions that
			a client is allowed to demand from a port."
		::= { ps32PortEntry 11 }

		ps32PortOperStatus OBJECT-TYPE
		   SYNTAX   INTEGER {
			unknown(1),
			notinstalled(2),
			disabled(3),
			operational(4),
			connected(5),
			intest(6),
			inerror(7)
		     }
		   ACCESS   read-only
		   STATUS   mandatory
		   DESCRIPTION
		       "This object displays the actual status of the port
		       as determined by current registers and other indi-
		       cators.
			   1: unknown	   not a supported status.
			   2: notinstalled Port is not in the switch.
			   3: disabled	   Port is deactivated.
			   4: operational  Port is running normally.
			   5: connected    Port has source interconnect.
			   6: intest	   Port is in BIST operation.
			   7: inerror	   Port is in an error condition.
			These statuses completely indicate the possible
			conditions that a port may be experiencing."
		::= { ps32PortEntry 12 }

		-- The switch implements a sparsely populated pathway
		-- table that is used to direct an input port to up to
		-- four output ports.  To control this through a MIB it
		-- is implemented as a sparse table that is indexed by
		-- port number and hippi destination address.  In order
		-- to be more universal and allow for an arbitrary number
		-- of output ports (or none specified), the output ports
		-- are represented as a string.

		-- HIPPI pathway table.

          	ps32Pathway OBJECT IDENTIFIER ::= { nscHippiSwitch 6 }

          	ps32MaximumPathways  OBJECT-TYPE
              	   SYNTAX  INTEGER (1..65535)
              	   ACCESS  read-only
              	   STATUS  mandatory
              	   DESCRIPTION
                      "Maximum number of pathways for a single port."
              	::= { ps32Pathway 1 }

		ps32PathwayTable OBJECT-TYPE
		   SYNTAX   SEQUENCE OF PS32PathwayEntry
		   ACCESS   not-accessible
		   STATUS   mandatory
		   DESCRIPTION
		       "A sparsely populated table that can be used to
		       determine pathway information for a given port."
		   --DEFAULT test-function test-ps32Pathway
		   --DEFAULT next-function next-ps32Pathway
		::= { ps32Pathway 2 }

		ps32PathwayEntry OBJECT-TYPE
		   SYNTAX   PS32PathwayEntry
		   ACCESS   not-accessible
		   STATUS   mandatory
		   DESCRIPTION
		       "An individual hippi switch pathway entry."
		   INDEX { ps32PathwayPortNumber, ps32PathwayHDA }
		::= { ps32PathwayTable 1 }

		PS32PathwayEntry ::=
		   SEQUENCE {
			ps32PathwayPortNumber
			   INTEGER,
        		ps32PathwayHDA
			   PhysAddress,
        		ps32PathwayDest
			   DisplayString,
-- PathwaySet is identical to PathwayDest in all respects, so we are
-- deleting it.  Remember to renumber things if you change this.
--	24 Mar 1994 csh
--        		ps32PathwaySet
--			   DisplayString,
        		ps32PathwayClear
			   INTEGER
		   }

		ps32PathwayPortNumber OBJECT-TYPE
		   SYNTAX   INTEGER
		   ACCESS   read-only
		   STATUS   mandatory
		   DESCRIPTION
			"Index into the pathway entry table."
		::= { ps32PathwayEntry 1 }		   

		ps32PathwayHDA OBJECT-TYPE
		   SYNTAX   PhysAddress(SIZE (2))
		   ACCESS   read-only
		   STATUS   mandatory
		   DESCRIPTION
		       "The downline HIPPI Destination Address to which
		       the HIPPI connection is routed.  This address is
		       a 3 character hexadecimal address, packed into
		       two octets."
		::= { ps32PathwayEntry 2 }

		ps32PathwayDest OBJECT-TYPE
		   SYNTAX   DisplayString
		   ACCESS   read-write
		   STATUS   mandatory
		   DESCRIPTION
		       "This is a list of output port numbers that can
		       supply a path or a portion of the path to the
		       specified HDA.  The number of output ports and
		       the number of ports that can be defined are switch
		       specific.  ie: the PS32 can accept up to four
		       output ports with values of 0 to 31.

		       The port list contains decimal numbers and are
		       separated by spaces.  Specifying a new string
		       replaces any previous definitions including a
		       NULL string removing all definitions."
		::= { ps32PathwayEntry 3 }

--		ps32PathwaySet OBJECT-TYPE
--		   SYNTAX   DisplayString(0..11)
--		   ACCESS   read-write
--		   STATUS   mandatory
--		   DESCRIPTION
--		       "A command to set the requested pathway entry.
--		       The port(s) are entered into the string as ASCII
--		       numbers (decimal) delimited by spaces.  The agent
--		       is responsible for decoding the string into its
--		       individual ports and validating the ports received."
--		::= { ps32PathwayEntry 4 }

		ps32PathwayClear OBJECT-TYPE
		   SYNTAX   INTEGER
		   ACCESS   read-write
		   STATUS   mandatory
		   DESCRIPTION
		       "A command to clear the requested pathway entry.
		       The value is not used.  Any access of this function
		       causes the pathway indicated by the indices to be
		       cleared."
		::= { ps32PathwayEntry 4 }

		END
