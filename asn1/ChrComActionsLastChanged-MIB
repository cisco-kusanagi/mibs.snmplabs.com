ChrComActionsLastChanged-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComActions				FROM  Chromatis-MIB
	ChromatisTableName			FROM  TableNames-MIB
	DateAndTime			FROM  RFC1903-MIB;

-- chrComActionsLastChanged Table

chrComActionsLastChangedTable		OBJECT-TYPE
	SYNTAX		SEQUENCE OF ChrComActionsLastChangedEntry
	MAX-ACCESS	not-accessible
	STATUS		current
	DESCRIPTION
	""
	::= { chrComActions 1}

chrComActionsLastChangedEntry		OBJECT-TYPE
	SYNTAX		ChrComActionsLastChangedEntry
	MAX-ACCESS	not-accessible
	STATUS		current
	DESCRIPTION
	""
	INDEX  {  chrComActionsTableId }

--DEFAULT  get-function-async  MNIL_GetRoutine
--DEFAULT  set-function-async  MNIL_SetRoutine
--DEFAULT  next-function-async MNIL_NextRoutine
--DEFAULT  test-function-async MNIL_TestRoutine
--DEFAULT  cookie "LastChanged"
	::= { chrComActionsLastChangedTable  1 }

ChrComActionsLastChangedEntry  ::=
	SEQUENCE  {
	chrComActionsTableId			Unsigned32	(0..4294967295),
	chrComActionsTableName		ChromatisTableName,
	chrComActionsLastChange		DateAndTime
}

chrComActionsTableId 	OBJECT-TYPE
	SYNTAX		Unsigned32	(0..4294967295)
	MAX-ACCESS 	read-write
	STATUS 		current
	DESCRIPTION
	"Numeric ID of a table. It is the numeric value of the next field, which is TableName.
"
	::= { chrComActionsLastChangedEntry  1 }

chrComActionsTableName 	OBJECT-TYPE
	SYNTAX		ChromatisTableName
	MAX-ACCESS 	read-only
	STATUS 		current
	DESCRIPTION
	"The ID of the table that was changed"
	::= { chrComActionsLastChangedEntry  2 }

chrComActionsLastChange 	OBJECT-TYPE
	SYNTAX		DateAndTime
	MAX-ACCESS 	read-only
	STATUS 		current
	DESCRIPTION
	"The time in which the table was lastly changed"
	::= { chrComActionsLastChangedEntry  3 }


END
