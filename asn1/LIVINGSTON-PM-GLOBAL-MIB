LIVINGSTON-PM-GLOBAL-MIB DEFINITIONS ::= BEGIN

IMPORTS
	IpAddress, Counter, Gauge, TimeTicks
		FROM RFC1155-SMI
	OBJECT-TYPE
		FROM RFC-1212
	TRAP-TYPE
		FROM RFC-1215
	DisplayString
		FROM RFC1213-MIB
	lucentPMMib
		FROM LIVINGSTON-ROOT-MIB;

-- ++++++++++++++++++++++++++++++++++++++++++++++++++++++++++++++++++
-- The Lucent Globals Group
-- ++++++++++++++++++++++++++++++++++++++++++++++++++++++++++++++++++
lucentPMGlobal	OBJECT IDENTIFIER ::= { lucentPMMib 1}

-- ++++++++++++++++++++++++++++++++++++++++++++++++++++++++++++++++++
-- The Lucent Chassis Generic Global Parameters
-- ++++++++++++++++++++++++++++++++++++++++++++++++++++++++++++++++++
lucentPMGenGlobParams	OBJECT IDENTIFIER ::= { lucentPMGlobal 1 }

lucentPMGenPriNameSrvr	OBJECT-TYPE
	SYNTAX	IpAddress
	ACCESS	read-write
	STATUS	mandatory
	DESCRIPTION
	"The primary name server address. The name server allows the
	machines to be accessed using names instead of the IP addresses."
	::= { lucentPMGenGlobParams 1 }

lucentPMGenAltNameSrvr	OBJECT-TYPE
	SYNTAX	IpAddress
	ACCESS	read-write
	STATUS	mandatory
	DESCRIPTION
	"The alternate name server address. The alternate name server
	takes the responsibilities of the primary name server when the
	primary name server stops responding."
	::= { lucentPMGenGlobParams 3 }

lucentPMGenSyslogHost	OBJECT-TYPE
	SYNTAX	IpAddress
	ACCESS	read-write
	STATUS	mandatory
	DESCRIPTION
	"The host IP address where the syslog messages are sent."
	::= { lucentPMGenGlobParams 4 }

lucentPMGenAssignedAddr	OBJECT-TYPE
	SYNTAX	IpAddress
	ACCESS	read-write
	STATUS	mandatory
	DESCRIPTION
	"The starting address for a pool of consecutive temporary
	addresses to be allocated by the PortMaster. This setting
	enables network login users to use IP addresses from this
	pool."
	::= { lucentPMGenGlobParams 5 }

lucentPMGenReportedAddr	OBJECT-TYPE
	SYNTAX	IpAddress
	ACCESS	read-write
	STATUS	mandatory
	DESCRIPTION
	"The IP address different from ether0 interface address
	which is reported to the outside world during PPP or
	SLIP protocol negotiation. Use this feature, if your
	site should appear as a single IP address site."
	::= { lucentPMGenGlobParams 6 }

lucentPMGenNetMask	OBJECT-TYPE
	SYNTAX	INTEGER {
		disable(1),
		enable(2)
	}
	ACCESS	read-write
	STATUS	mandatory
	DESCRIPTION
	"The user netmask allows the PortMaster to add routes to
	dial-in users based on the netmask specified in the netmask
	object. This seting affects the routing and proxy ARP."
	::= { lucentPMGenGlobParams 7 }

lucentPMGenNameSvc	OBJECT-TYPE
	SYNTAX	INTEGER {
		none(1),
		dns(2),
		nis(3)
	}
	ACCESS	read-write
	STATUS	mandatory
	DESCRIPTION
	"Name service specifies the type of name resolution service used.
	The possible values are domain name service dns(2) or network
	information service nis(3). If either of them is not used, then
	the value of the object is none(1)."
	::= { lucentPMGenGlobParams 8 }

lucentPMGenDomainName	OBJECT-TYPE
	SYNTAX	DisplayString
	ACCESS	read-write
	STATUS	mandatory
	DESCRIPTION
	"Domain name of the system. Example xxxxxxx.com, yyyyyyyy.org,
	zzzzzzzz.edu or ppppppppp.net etc."
	::= { lucentPMGenGlobParams 9 }

lucentPMGenTelnetPortNum	OBJECT-TYPE
	SYNTAX	INTEGER
	ACCESS	read-write
	STATUS	mandatory
	DESCRIPTION
	"Telnet port number."
	::= { lucentPMGenGlobParams 10 }

lucentPMGenMaxConsConn	OBJECT-TYPE
	SYNTAX	INTEGER
	ACCESS	read-write
	STATUS	mandatory
	DESCRIPTION
	"Maximum number of console connections."
	::= { lucentPMGenGlobParams 11 }

lucentPMGenOSPF	OBJECT-TYPE
	SYNTAX	INTEGER {
		disable(1),
		enable(2)
	}
	ACCESS	read-write
	STATUS	mandatory
	DESCRIPTION
	"Enable or disable Open Shortest Path First routing
	algorithm."
	::= { lucentPMGenGlobParams 12 }

lucentPMGenBGP	OBJECT-TYPE
	SYNTAX	INTEGER {
		disable(1),
		enable(2)
	}
	ACCESS	read-write
	STATUS	mandatory
	DESCRIPTION
	"Enable or disable Border Gateway Protocol."
	::= { lucentPMGenGlobParams 13 }

lucentPMGenIPX	OBJECT-TYPE
	SYNTAX	INTEGER {
		disable(1),
		enable(2)
	}
	ACCESS	read-write
	STATUS	mandatory
	DESCRIPTION
	"Enable or disable IPX Protocol."
	::= { lucentPMGenGlobParams 14 }

lucentPMGenNetBIOS	OBJECT-TYPE
	SYNTAX	INTEGER {
		disable(1),
		enable(2)
	}
	ACCESS	read-write
	STATUS	mandatory
	DESCRIPTION
	"Enable or disable NetBIOS Protocol."
	::= { lucentPMGenGlobParams 15 }

lucentPMGenCallCheck	OBJECT-TYPE
	SYNTAX	INTEGER {
		disable(1),
		enable(2)
	}
	ACCESS	read-write
	STATUS	mandatory
	DESCRIPTION
	"Enable or disable RADIUS authentication before an
	ISDN PRI call is accepted. You must configure the
	RADIUS user entries for this option to work."
	::= { lucentPMGenGlobParams 16 }

-- ++++++++++++++++++++++++++++++++++++++++++++++++++++++++++++++++++
-- Lucent Radius Management objects
-- ++++++++++++++++++++++++++++++++++++++++++++++++++++++++++++++++++
lucentPMRadiusMgmt	OBJECT IDENTIFIER	::= { lucentPMGlobal 2 }

lucentPMRadiusPriIP	OBJECT-TYPE
	SYNTAX	IpAddress
	ACCESS	read-write
	STATUS	mandatory
	DESCRIPTION
	"The IP address of the primary RADIUS server."
	::= { lucentPMRadiusMgmt 1 }

lucentPMRadiusAltIP	OBJECT-TYPE
	SYNTAX	IpAddress
	ACCESS	read-write
	STATUS	mandatory
	DESCRIPTION
	"The alternate IP address of the RADIUS server."
	::= { lucentPMRadiusMgmt 2 }

lucentPMRadiusPriAcctIP	OBJECT-TYPE
	SYNTAX	IpAddress
	ACCESS	read-write
	STATUS	mandatory
	DESCRIPTION
	"The IP address of the primary RADIUS accounting server."
	::= { lucentPMRadiusMgmt 3 }

lucentPMRadiusAltAcctIP	OBJECT-TYPE
	SYNTAX	IpAddress
	ACCESS	read-write
	STATUS	mandatory
	DESCRIPTION
	"The IP address of the RADIUS alternate accounting
	server."
	::= { lucentPMRadiusMgmt 4 }
	
lucentPMRadiusPriPort	OBJECT-TYPE
	SYNTAX	INTEGER
	ACCESS	read-write
	STATUS	mandatory
	DESCRIPTION
	"The port number for the primary RADIUS server."
	::= { lucentPMRadiusMgmt 5 }

lucentPMRadiusAltPort	OBJECT-TYPE
	SYNTAX	INTEGER
	ACCESS	read-write
	STATUS	mandatory
	DESCRIPTION
	"The port number for the alternate RADIUS server."
	::= { lucentPMRadiusMgmt 6 }

lucentPMRadiusPriAcctPort	OBJECT-TYPE
	SYNTAX	INTEGER
	ACCESS	read-write
	STATUS	mandatory
	DESCRIPTION
	"The port number for the primary RADIUS accounting server."
	::= { lucentPMRadiusMgmt 7 }

lucentPMRadiusAltAcctPort	OBJECT-TYPE
	SYNTAX	IpAddress
	ACCESS	read-write
	STATUS	mandatory
	DESCRIPTION
	"The port number for the alternate RADIUS accounting
	server."
	::= { lucentPMRadiusMgmt 8 }

lucentPMRadiusAuthFails	OBJECT-TYPE
	SYNTAX	Counter
	ACCESS	read-only
	STATUS	mandatory
	DESCRIPTION
	"The number of radius authentication failures."
	::= { lucentPMRadiusMgmt 9 }

lucentPMRadiusRetrans	OBJECT-TYPE
	SYNTAX	INTEGER
	ACCESS	read-write
	STATUS	mandatory
	DESCRIPTION
	"The maximum number of times a timeout will occur when
	communicating with radius."	
	::= { lucentPMRadiusMgmt 10 }

lucentPMRadiusTimeout	OBJECT-TYPE
	SYNTAX	INTEGER
	ACCESS	read-write
	STATUS	mandatory
	DESCRIPTION
	"The maximum amount of time in seconds we will wait
	for a RADIUS response before retransmitting."
	::= { lucentPMRadiusMgmt 11 }

lucentPMRadiusAuth	OBJECT-TYPE
	SYNTAX	INTEGER {
		enabled(1),
		disabled(2)
	}
	ACCESS	read-write
	STATUS	mandatory
	DESCRIPTION
	"Is radius authentication on or off."
	::= { lucentPMRadiusMgmt 12 }

lucentPMRadiusSecret	OBJECT-TYPE
	SYNTAX	OCTET STRING (SIZE (1..15))
	ACCESS	write-only
	STATUS	mandatory
	DESCRIPTION
	"The shared secret between the RADIUS server and client."
	::= { lucentPMRadiusMgmt 13 }

-- ++++++++++++++++++++++++++++++++++++++++++++++++++++++++++++++++++
-- Lucent ChoiceNet Management objects
-- ++++++++++++++++++++++++++++++++++++++++++++++++++++++++++++++++++
lucentPMChoiceNetMgmt	OBJECT IDENTIFIER	::= { lucentPMGlobal 3 }

lucentPMChoiceNetPriIP	OBJECT-TYPE
	SYNTAX	IpAddress
	ACCESS	read-write
	STATUS	mandatory
	DESCRIPTION
	"The IP address of the primary ChoiceNet server."
	::= { lucentPMChoiceNetMgmt 1 }

lucentPMChoiceNetAltIP	OBJECT-TYPE
	SYNTAX	IpAddress
	ACCESS	read-write
	STATUS	mandatory
	DESCRIPTION
	"The alternate IP address of the ChoiceNet server."
	::= { lucentPMChoiceNetMgmt 2 }

lucentPMChoiceNetPriPort	OBJECT-TYPE
	SYNTAX	INTEGER
	ACCESS	read-write
	STATUS	mandatory
	DESCRIPTION
	"The port number of the primary ChoiceNet server."
	::= { lucentPMChoiceNetMgmt 3 }

lucentPMChoiceNetAltPort	OBJECT-TYPE
	SYNTAX	INTEGER
	ACCESS	read-write
	STATUS	mandatory
	DESCRIPTION
	"The port number of the alternate ChoiceNet server."
	::= { lucentPMChoiceNetMgmt 4 }
	
lucentPMChoiceNetSecret	OBJECT-TYPE
	SYNTAX	OCTET STRING (SIZE (1..15))
	ACCESS	write-only
	STATUS	mandatory
	DESCRIPTION
	"The shared secret between the ChoiceNet server and client."
	::= { lucentPMChoiceNetMgmt 5 }

END

-- ++++++++++++++++++++++++++++++++++++++++++++++++++++++++++++++++++++++++++
-- Lucent PortMaster 4 private MIB at a glance
-- ++++++++++++++++++++++++++++++++++++++++++++++++++++++++++++++++++++++++++
-- pm4mib.mib	@(#)pm4mib.mib	1.0
-- Copyright 1991,1997, 1998 Lucent Technologies
--
-- pm4mib.mib
-- MIB for the PortMaster 4 SNMP Agent
-- Release version = 4.0b1
--
--	mib-2
--	lucent
--		products
--			lucentPM
--				lucentPM3
--					lucentPM3Mib
--						lucentPM3MibRev
--				lucentPM4
--					lucentPM4Mib
--						lucentPM4MibRev
--						lucentPM4SWRev
--						lucentPM4Chassis
--							lucentPM4ChasSummary
--							lucentPM4ChasCmdTable
--						lucentPM4ConfigMgmt
--							lucentPM4Interfaces
--								lucentPM4SerialInterface
--								lucentPM4T1E1Interface
--								lucentPM4ModemInterface
--								lucentPM4EtherInterface
--							lucentPM4FaultMgmt
--								lucentPM4FaultIsolation
--									lucentPM4FaultMgmtChasTrap
--									lucentPM4FMBoardIndex
--									lucentPM4FMUnitIndex
--									lucentPM4FMUnitType
--									lucentPM4FMUnitTrapStatus
--									lucentPM4FMTrapSeverity
--							lucentPM4FMTrapConfig
--								lucentPM4EquipTrapConfig
--								lucentPM4T1E1ThreshTrapConfig
--								lucentPM4EnvTrapConfig
--						lucentPM4PerfMgmt
--							lucentPM4PerfMgmtT1E1
--								lucentPM4T1E1PMCur
--								lucentPM4T1E1PMInt
--								lucentPM4T1E1PMTotal
--							lucentPM4PerfMgmtMgrCard
--						lucentPM4SecurityMgmt
--						lucentPM4AcctMgmt
--							lucentPM4SnmpComm
--						lucentPM4Traps
--							lucentPM4BoardOfflineTrap
--							lucentPM4BoardOnlineTrap
--							lucentPM4PwrSupFailTrap
--							lucentPM4PwrSupWarnTrap
--							lucentPM4PwrSupRestoredTrap
--							lucentPM4FanFailTrap
--							lucentPM4FanRestoredTrap
--							lucentPM4BoardTempWarnTrap
--							lucentPM4BoardTempNormalTrap
--							lucentPM4BoardTooHotTrap
--							lucentPM4ModemFailTrap
--							lucentPM4T1E1LineDownTrap
--							lucentPM4T1E1LineUpTrap
--							lucentPM4T1E1LineThreshTrap
--							lucentPM4T1E1LineThreshTrap
--							lucentPM4BoardPwrOffTrap
--							lucentPM4RadiusAuthFailTrap
--
-- Modification History
-- --------------------
--
-- Pavan Kumar	10/27/98	Revised Draft
-- Pavan Kumar	11/03/98	Moved Radius configuration to PM4 Configuration
--					subtree Added choicenet and lucent global 
--					configuration parameters.
--
-- ++++++++++++++++++++++++++++++++++++++++++++++++++++++++++++++++++++++++++
