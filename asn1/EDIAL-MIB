-- This file machine generated on Wed Mar 29 20:51:38 2006
-- from $Id: edialmib.pl,v 1.32 2005/10/03 21:44:35 phil.budne Exp $
-- by $Id: mibmaker.pm,v 1.12 2005/08/08 23:00:53 phil.budne Exp $
-- DO NOT EDIT BY HAND!!!

EDIAL-MIB DEFINITIONS ::= BEGIN

IMPORTS
    MODULE-IDENTITY, NOTIFICATION-TYPE, OBJECT-TYPE,
      enterprises, Counter32, Integer32, Unsigned32
	FROM SNMPv2-SMI
    DateAndTime, DisplayString, TEXTUAL-CONVENTION
	FROM SNMPv2-TC
    InetAddressType, InetAddress
	FROM INET-ADDRESS-MIB;


edial MODULE-IDENTITY
    LAST-UPDATED "200510032144Z"
    ORGANIZATION "eDial, Inc (a division of Alcatel)"
    CONTACT-INFO
	"Postal: eDial, Inc
		 266 Second Avenue
		 Waltham, MA 02451
		 781-895-3600

	WWW:	 http://www.edial.com/"
    DESCRIPTION
	"This document contains the management information that is
	common to all elements in an eDial system."
    REVISION	"200402252000Z"
    DESCRIPTION
	"Released with ACS 5.6.0;
	Supports only NOTIFICATIONs."
    REVISION	"200510032144Z"
    DESCRIPTION
	"Released with ACS 6.0;
	Adds Monitoring (read only)."
    ::= { enterprises 19631 }


-- ****************
-- Textual Conventions
-- establish length limits for strings used as indices


-- ****************
-- Common Group

common OBJECT IDENTIFIER ::= { edial 1 }

systemFaults OBJECT IDENTIFIER ::= { common 1 }

-- ****************
-- System Faults Group

faultFields OBJECT IDENTIFIER ::= { systemFaults 1 }

timeStamp OBJECT-TYPE
    SYNTAX	DateAndTime
    MAX-ACCESS	accessible-for-notify
    STATUS	current
    DESCRIPTION
	"The date and time at which the fault was generated."
    ::= { faultFields 2 }

msgString OBJECT-TYPE
    SYNTAX	DisplayString
    MAX-ACCESS	accessible-for-notify
    STATUS	current
    DESCRIPTION
	"The fault message string."
    ::= { faultFields 3 }

systemName OBJECT-TYPE
    SYNTAX	DisplayString
    MAX-ACCESS	accessible-for-notify
    STATUS	current
    DESCRIPTION
	"The hostname of the system generating the fault."
    ::= { faultFields 4 }

problemText OBJECT-TYPE
    SYNTAX	DisplayString
    MAX-ACCESS	accessible-for-notify
    STATUS	current
    DESCRIPTION
	"Text describing the nature of the problem.
	The text consists of constant and variable portions."
    ::= { faultFields 9 }

notification NOTIFICATION-TYPE
    OBJECTS	{ timeStamp, msgString, systemName, problemText }
    STATUS	current
    DESCRIPTION
	"A notification indicates detection of an abnormal
	condition in the system."
    ::= { systemFaults 2 }


END
