-- 
-- Copyright 1999 by Fore Systems, Inc. 
-- Converted to SMIv2 rfc 2578,2579,2580 - STD 58
--
-- Copyright 1993-1999 by Fore Systems, Inc.

Fore-DS3-MIB DEFINITIONS ::= BEGIN

IMPORTS
	Counter32, Integer32,
	OBJECT-TYPE,
	MODULE-IDENTITY				FROM SNMPv2-SMI
	asx					FROM Fore-Common-MIB;

------------------------------------------------------------------------
--	The implementation of the foreDs3 tables is mandatory
--      for all switches that have DS3 port module.

foreDs3	  MODULE-IDENTITY
          LAST-UPDATED         "9911050000Z"
          ORGANIZATION         "FORE"
          CONTACT-INFO         
               "      Postal:   FORE Systems Inc.
                                1000 FORE Drive
                                Warrendale, PA 15086-7502
                      Tel:      +1 724 742 6900
                      Email:    nm_mibs@fore.com
                      Web:      http://www.fore.com"
          DESCRIPTION "
             This MIB module supports the FORE DS3 port module."
    ::= { asx 3 }

ds3ConfGroup		OBJECT IDENTIFIER ::= { foreDs3 1 }
ds3StatsGroup		OBJECT IDENTIFIER ::= { foreDs3 2 }

------------------------------------------------------------------------
-- The DS3 configuration Group

ds3ConfTable OBJECT-TYPE
	SYNTAX	SEQUENCE OF Ds3ConfEntry
	MAX-ACCESS	not-accessible
	STATUS	current
	DESCRIPTION
		"A table of DS3 switch port configuration information."
	::= { ds3ConfGroup 1 }

ds3ConfEntry OBJECT-TYPE
	SYNTAX	Ds3ConfEntry
	MAX-ACCESS	not-accessible
	STATUS	current
	DESCRIPTION
		"A table entry containing DS3 configuration information for
		each port. Not all RFC1407 configuration table variables are
		included, and some are modified."
	INDEX	{ ds3ConfBoard, ds3ConfModule, ds3ConfPort }
	::= { ds3ConfTable 1 }

Ds3ConfEntry ::=
	SEQUENCE {
		ds3ConfBoard		Integer32,
		ds3ConfModule		Integer32,
		ds3ConfPort		Integer32,
		ds3LineType		INTEGER,
		ds3LineCoding		INTEGER,
		ds3SendCode		INTEGER,
		ds3ReceiveCode		INTEGER,
		ds3LoopbackConfig	INTEGER,
		ds3TxClockSource	INTEGER,
		ds3RxScrambling		INTEGER,
		ds3TxScrambling		INTEGER,
		ds3LineStatus		Integer32,
		ds3IdleUnassignedCells	INTEGER,
		ds3LineTypeFraming	INTEGER,
		ds3LineLength		INTEGER,
		ds3PbitPErrThrSeconds	Integer32,
		ds3PbitPErrThrErrors	Integer32,
		ds3PbitPErrFailEnable	INTEGER,
		ds3SigFailBer		Integer32,
		ds3SigDegradeBer	Integer32,
		ds3BerErrorModel	INTEGER,
		ds3BerState             INTEGER
	}

ds3ConfBoard OBJECT-TYPE
	SYNTAX	Integer32
	MAX-ACCESS	read-only
	STATUS	current
	DESCRIPTION
		"The index of this port's switch board."
	::= { ds3ConfEntry 1 }

ds3ConfModule OBJECT-TYPE
	SYNTAX	Integer32
	MAX-ACCESS	read-only
	STATUS	current
	DESCRIPTION
		"The network module of this port."
	::= { ds3ConfEntry 2 }

ds3ConfPort OBJECT-TYPE
	SYNTAX	Integer32
	MAX-ACCESS	read-only
	STATUS	current
	DESCRIPTION
		"The number of this port."
	::= { ds3ConfEntry 3 }

ds3LineType OBJECT-TYPE
	SYNTAX	INTEGER {
		ds3Other (1),
		ds3M23 (2),
		ds3SYNTRAN (3),
		ds3CbitParity (4),
		ds3ClearChannel (5)
		}
	MAX-ACCESS	read-write
	STATUS	current
	DESCRIPTION
		"This variable indicates the variety of DS3 C-bit application
		implementing this interface. The type of interface affects the
		interpretation of the usage and error statistics. This variable
		is defined in the rfc1407 configuration table as dsx3LineType.
		According to rfc1407, the different values are:
		ds3M23		 specification: ANSI T1.107-1988
		ds3SYNTRAN	 specification: ANSI T1.107-1988
		ds3CbitParity	 specification: ANSI T1.107a-1989
		ds3CleatChannel	 specification: ANSI T1.102-1987."
	DEFVAL	{ ds3CbitParity }
	::= { ds3ConfEntry 4 }

ds3LineCoding OBJECT-TYPE
	SYNTAX	INTEGER {
		ds3Other (1),
		ds3B3ZS (2)
		}
	MAX-ACCESS	read-only
	STATUS	current
	DESCRIPTION
		"This variable describes the variety of Zero Code suppression
		used on this interface, which in turn affects a number of its
		characteristics. ds3B3ZS (2) refers to the use of specified
		pattern of normal bits and bipolar violations which are used to
		replaced sequences of zero bits of specified length. This
		variable is defined in the rfc1407 configuration table as
		dsx3LineCoding."
	DEFVAL	{ ds3B3ZS }
	::= { ds3ConfEntry 5 }

ds3SendCode OBJECT-TYPE
	SYNTAX	INTEGER {
		ds3SendNoCode (1),
		ds3SendLineCode (2),
		ds3SendPayloadCode (3),
		ds3SendResetCode (4),
		ds3SendDS1LoopCode (5),
		ds3SendTestPattern (6)
		}
	MAX-ACCESS	read-write
	STATUS	current
	DESCRIPTION
		"This variable indicates what type of code is being sent across
		the DS3/E3 interface by the device.

		The values mean:
		ds3SendNoCode		sending looped or normal data
		ds3SendLineCode		sending request for a line loopback
		ds3SendPayloadCode	sending a request for a payload loopback (i.e. all
					DS1/E1 in a DS3/E3 frame)
		ds3SendResetCode	sending a loopback deactivation request
		ds3SendDS1LoopCode	requesting to loopback a particular DS1/E1 within a
					DS3/E3 frame
		ds3SendTestPattern	sending a test pattern."
	DEFVAL	{ ds3SendNoCode }
	::= { ds3ConfEntry 6 }

ds3ReceiveCode OBJECT-TYPE
	SYNTAX	INTEGER {
		ds3ReceiveNoCode (1),
		ds3ReceiveLineCode (2),
		ds3ReceivePayloadCode (3),
		ds3ReceiveResetCode (4),
		ds3ReceiveDS1LoopCode (5),
		ds3ReceiveTestPattern (6)
		}
	MAX-ACCESS	read-only
	STATUS	current
	DESCRIPTION
		"This variable indicates the type of code that was received
		across the DS3/E3 interface.

		The values mean:
		ds3ReceiveNoCode	receiving looped or normal data
		ds3ReceiveLineCode	receiving request for a line loopback
		ds3ReceivePayloadCode	receiving a request for a payload loopback (i.e. all
					DS1/E1 in a DS3/E3 frame)
		ds3ReceiveResetCode	receiving a loopback deactivation request
		ds3ReceiveDS1LoopCode	receiving a request to loopback a particular DS1/E1
					within a DS3/E3 frame
		ds3ReceiveTestPattern	receiving a test pattern."
	DEFVAL	{ ds3ReceiveNoCode }
	::= { ds3ConfEntry 7 }

ds3LoopbackConfig OBJECT-TYPE
	SYNTAX	INTEGER {
		ds3NoLoop (1),
		ds3CellLoop (2),
		ds3PayloadLoop (3),
		ds3DiagLoop (4),
		ds3LineLoop (5),
		ds3OtherLoop (6)
		}
	MAX-ACCESS	read-write
	STATUS	current
	DESCRIPTION
		"This variable represents the loopback configuration of the DS3
		interface. This variable is defined in the rfc1407
		configuration table as dsx3LoopbackConfig, with slightly
		different values.

		ds3NoLoop (1) means that the interface is not in a loopback
		state.

		ds3CellLoop (2) means that cells that are processed by the
		receiving component are not written into the receive FIFO, but
		into the transmit FIFO for retransmission.

		ds3PayloadLoop (3) means that the receive signal is looped back
		for retransmission after it has passed through the port's
		reframing function.

		ds3DiagLoop (4) means that the transmit data stream is looped
		back to the receiver.

		ds3LineLoop (5) is only supported on series B and later
		netmods.

		ds3OtherLoop (6) means that the interface is in a loopback that
		is not defined here."
	DEFVAL	{ ds3NoLoop }
	::= { ds3ConfEntry 8 }

ds3TxClockSource OBJECT-TYPE
	SYNTAX	INTEGER {
		rxTiming (1),
		localTiming (2)
		}
	MAX-ACCESS	read-write
	STATUS	current
	DESCRIPTION
		"The source of the transmit clock."
	DEFVAL	{ localTiming }
	::= { ds3ConfEntry 9 }

ds3RxScrambling OBJECT-TYPE
	SYNTAX	INTEGER {
		descrambling(1),
		noDescrambling(2)
		}
	MAX-ACCESS	read-write
	STATUS	current
	DESCRIPTION
		"This variable indicates whether the information is being
		descrambled on receiving. It should be set the same as the
		transmitting side."
	DEFVAL	{ noDescrambling }
	::= { ds3ConfEntry 10 }

ds3TxScrambling OBJECT-TYPE
	SYNTAX	INTEGER {
		scrambling(1),
		noScrambling(2)
		}
	MAX-ACCESS	read-write
	STATUS	current
	DESCRIPTION
		"This variable indicates whether the information (48 octet
		payload) is being scrambled before transmitting. It should be
		set the same as the receiving side."
	DEFVAL	{ noScrambling }
	::= { ds3ConfEntry 11 }

ds3LineStatus OBJECT-TYPE
	SYNTAX	Integer32 (1..65534)
	MAX-ACCESS	read-only
	STATUS	current
	DESCRIPTION
		"This variable indicates the Line Status of the interface. A
		similar object is defined in the rfc1407 configuration table as
		dsx3LineStatus (the ds3RxFERF bit is not defined in rfc1407)
		. The variable contains loopback state information and failure
		state information. It is a bit map represented as a sum. The
		ds3NoAlarm should be set if and only if no other flag is set.

		The various bit positions are:
		1	No Alarm.
		2	Receiving PLCP Yellow Alarm Indication.
		4	Transmitting PLCP Yellow alarm indication.
		8	Receiving PLCP LOF.
		16	Receiving FERF.
		32	Transmiting FERF.
		64	Receiving AIS failure indication.
		128	Receiving LOF failure indication.
		256	Receiving LOS failure indication.
		512	Loopback State.
		1024	Receiving a test pattern.
		2048	Other failures.
		16384   Receiving IDLE failure indication.
		32768	Receiving LCD failure indication."
	DEFVAL	{ 1 }
	::= { ds3ConfEntry 12 }

ds3IdleUnassignedCells OBJECT-TYPE
	SYNTAX	INTEGER {
		unassigned(1),
		idle(2)
		}
	MAX-ACCESS	read-write
	STATUS	current
	DESCRIPTION
		"This variable indicates the types of cells that should be sent
		in case there is no real data to send. According to the ATM
		Forum, Unassigned cells should be sent (octet 1-3 are 0's,
		octet 4 is 0000xxx0, where x is 'don't care'). According to the
		CCITT specifications, Idle cells should be sent (everything is
		'0' except for the CLP bit which is '1'). By default,
		unassigned cells are transmitted is case there is no data to
		send."
	DEFVAL	{ unassigned }
	::= { ds3ConfEntry 13 }

ds3LineTypeFraming OBJECT-TYPE
	SYNTAX	INTEGER {
		ds3Hcs (1),
		ds3Plcp (2)
		}
	MAX-ACCESS	read-write
	STATUS	current
	DESCRIPTION
		"This variable indicates the way ATM cells are constructed from
		the DS3 stream. ds3Hcs(1) indicates that the ATM cells are
		constructed upon the Header Check Sequence (HCS) inside the ATM
		cell header. ds3Plcp(2) indicates that the ATM cells are
		constructed from the DS3 PLCP (Physical Layer Convergence
		Protocol) bits."
	DEFVAL	{ ds3Hcs }
	::= { ds3ConfEntry 14 }

ds3LineLength OBJECT-TYPE
	SYNTAX	INTEGER {
		ds3LineLt225 (1),
		ds3LineGt225 (2)
		}
	MAX-ACCESS	read-write
	STATUS	current
	DESCRIPTION
		"This variable represents the length of the physical cable
		connected to the ds3 port. The user has to set this object to
		match the physical cable in order to get the netmod to receive
		the signal on the cable. The different values are: ds3LineLt225
		(1) means the line is shorter than 225 ft, ds1LineGt225 (2)
		means the line length is greater than 220 ft. This value is not
		settable for Series A netmods and the value for these netmods
		is Gt225"
	DEFVAL	{ ds3LineGt225 }
	::= { ds3ConfEntry 15 }

ds3PbitPErrThrSeconds OBJECT-TYPE
	SYNTAX	Integer32
	MAX-ACCESS	read-write
	STATUS	current
	DESCRIPTION
		"This variable represents the consecutive number of
		 BAD/GOOD seconds to detect/clear an Excessive P-bit
		 Parity Error Defect. The range of values it can take
		 is between 2 and 10 inclusive."
	DEFVAL { 10 }
	::= { ds3ConfEntry 16 }

ds3PbitPErrThrErrors OBJECT-TYPE
	SYNTAX	Integer32
	MAX-ACCESS	read-write
	STATUS	current
	DESCRIPTION
		"This variable is a threshold for the number of P-bit
		 Parity Errors per second and is used as a parameter to
		 the Excessive P-bit Parity Error Defect.  If the number
		 of errors exceeds the threshold, the particular second is
		 declared BAD, otherwise it is declared GOOD."
	::= { ds3ConfEntry 17 }

ds3PbitPErrFailEnable OBJECT-TYPE
	SYNTAX	INTEGER {
		enabled(1),
		disabled(2)
		}
	MAX-ACCESS	read-write
	STATUS	current
	DESCRIPTION
		"This variable controls whether declaration of an
		 Excessive P-bit Parity Error Defect forces the port's
		 operState to Down."
	::= { ds3ConfEntry 18 }

ds3SigFailBer OBJECT-TYPE
	SYNTAX	Integer32
	MAX-ACCESS read-write
	STATUS	current
	DESCRIPTION
		"This is the exponent of 10 for the current signal
		 fail bit error rate (BER) threshold for this port.
		 The value -4, for example, represents a BER of 1E-4.
		 This variable is only applicable when ds3BerErrorModel
		 is set to errorModelRandom."
	::= { ds3ConfEntry 19 }

ds3SigDegradeBer OBJECT-TYPE
	SYNTAX	Integer32
	MAX-ACCESS read-write
	STATUS	current
	DESCRIPTION
		"This is the exponent of 10 for the current signal
		 degrade bit error rate (BER) threshold for this port.
		 The value -8, for example, represents a BER of 1E-8.
		 This variable is only applicable when ds3BerErrorModel
		 is set to errorModelRandom."
	::= { ds3ConfEntry 20 }

ds3BerErrorModel OBJECT-TYPE
	SYNTAX	INTEGER {
		errorModelNone(0),
		errorModelRandom(1),
		errorModelBurst(2)
		}
	MAX-ACCESS read-write
	STATUS	current
	DESCRIPTION
		"This is the error distribution model to be used to
		 identify signal degrade and signal fail conditions.
		 errorModelRandom selects a random error distribution
		 and declares signal conditions based on the thresholds
		 set in ds3SigDegradeBer and ds3SigFailBer.
		 errorModelBurst selects a burst error model and declares
		 signal degrade conditions based on the thresholds set in
		 ds3PErrThrSeconds and ds1PErrThrErrors.
		 errorModelNone disables detection of signal conditions."
	::= { ds3ConfEntry 21 }

ds3BerState OBJECT-TYPE
	SYNTAX	INTEGER {
		berStateOk(0),
		berStateSigDegrade(1),
		berStateSigFail(2)
		}
	MAX-ACCESS	read-only
	STATUS 	current
	DESCRIPTION
		"This value describes the current state of the port as 
		 determined through bit error rate analysis."
	::= { ds3ConfEntry 22 }


------------------------------------------------------------------------
-- The DS3 Statistics Group

ds3FramingTable OBJECT-TYPE
	SYNTAX	SEQUENCE OF Ds3FramingEntry
	MAX-ACCESS	not-accessible
	STATUS	current
	DESCRIPTION
		"A table of DS3 framing statistics information."
	::= { ds3StatsGroup 1 }

ds3FramingEntry OBJECT-TYPE
	SYNTAX	Ds3FramingEntry
	MAX-ACCESS	not-accessible
	STATUS	current
	DESCRIPTION
		"A table entry containing DS3 framing statistics information."
	INDEX	{ ds3FramingBoard, ds3FramingModule, ds3FramingPort }
	::= { ds3FramingTable 1 }

Ds3FramingEntry ::=
	SEQUENCE {
		ds3FramingBoard		Integer32,
		ds3FramingModule	Integer32,
		ds3FramingPort		Integer32,

		ds3FramingLOSs		Counter32,
		ds3FramingLCVs		Counter32,
		ds3FramingSumLCVs	Counter32,
		ds3FramingFERRs		Counter32,
		ds3FramingOOFs		Counter32,
		ds3FramingFERFs		Counter32,
		ds3FramingAISs		Counter32,
		ds3FramingPbitPERRs	Counter32,

		ds3FramingCbitPERRs	Counter32,
		ds3FramingFEBEs		Counter32,
		ds3FramingIDLEs		Counter32
	}

ds3FramingBoard OBJECT-TYPE
	SYNTAX	Integer32
	MAX-ACCESS	read-only
	STATUS	current
	DESCRIPTION
		"The index of this port's switch board."
	::= { ds3FramingEntry 1 }

ds3FramingModule OBJECT-TYPE
	SYNTAX	Integer32
	MAX-ACCESS	read-only
	STATUS	current
	DESCRIPTION
		"The network module of this port."
	::= { ds3FramingEntry 2 }

ds3FramingPort OBJECT-TYPE
	SYNTAX	Integer32
	MAX-ACCESS	read-only
	STATUS	current
	DESCRIPTION
		"The number of this port."
	::= { ds3FramingEntry 3 }

ds3FramingLOSs OBJECT-TYPE
	SYNTAX	Counter32
	MAX-ACCESS	read-only
	STATUS	current
	DESCRIPTION
		"The number of seconds in which Loss Of Signal (LOS) errors
		were detected by the DS3 Receive Framer block."
	::= { ds3FramingEntry 4 }

ds3FramingLCVs OBJECT-TYPE
	SYNTAX	Counter32
	MAX-ACCESS	read-only
	STATUS	current
	DESCRIPTION
		"The number of Line Code Violations (LCV) that were detected by
		the DS3 Receive Framer block."
	::= { ds3FramingEntry 5 }

ds3FramingSumLCVs OBJECT-TYPE
	SYNTAX	Counter32
	MAX-ACCESS	read-only
	STATUS	current
	DESCRIPTION
		"The number of DS3 information blocks (85 bits) which contain
		one or more Line Code Violations (LCV)."
	::= { ds3FramingEntry 6 }

ds3FramingFERRs OBJECT-TYPE
	SYNTAX	Counter32
	MAX-ACCESS	read-only
	STATUS	current
	DESCRIPTION
		"Number of DS3 framing error (FERR) events."
	::= { ds3FramingEntry 7 }

ds3FramingOOFs OBJECT-TYPE
	SYNTAX	Counter32
	MAX-ACCESS	read-only
	STATUS	current
	DESCRIPTION
		"Number of seconds DS3 Out Of Frame (OOF) error events were
		experienced."
	::= { ds3FramingEntry 8 }

ds3FramingFERFs OBJECT-TYPE
	SYNTAX	Counter32
	MAX-ACCESS	read-only
	STATUS	current
	DESCRIPTION
		"The number of seconds in which Far End Receive Failure (FERF)
		state has been detected by the DS3 Receive Framer block. FERF
		signal alerts the upstream terminal that a failure has been
		detected along the downstream line."
	::= { ds3FramingEntry 9 }

ds3FramingAISs OBJECT-TYPE
	SYNTAX	Counter32
	MAX-ACCESS	read-only
	STATUS	current
	DESCRIPTION
		"The number of seconds in which Alarm Indication Signals (AIS)
		were detected by the DS3 Receive Framer block. AIS indicates
		that an upstream failure has been detected by the far end."
	::= { ds3FramingEntry 10 }

ds3FramingPbitPERRs OBJECT-TYPE
	SYNTAX	Counter32
	MAX-ACCESS	read-only
	STATUS	current
	DESCRIPTION
		"Number of P-bit parity error (PERR) events."
	::= { ds3FramingEntry 11 }

ds3FramingCbitPERRs OBJECT-TYPE
	SYNTAX	Counter32
	MAX-ACCESS	read-only
	STATUS	current
	DESCRIPTION
		"Number of C-bit parity error (PERR) events."
	::= { ds3FramingEntry 12 }

ds3FramingFEBEs OBJECT-TYPE
	SYNTAX	Counter32
	MAX-ACCESS	read-only
	STATUS	current
	DESCRIPTION
		"Number of DS3 far end block error (FEBE) events."
	::= { ds3FramingEntry 13 }

ds3FramingIDLEs OBJECT-TYPE
	SYNTAX  Counter32
	MAX-ACCESS  read-only
	STATUS  current
	DESCRIPTION
		"The number of seconds in which IDLE signal
		was detected by the DS3 Receive Framer block."
	::= { ds3FramingEntry 14 }

------------------------------------------------------------------------

ds3PlcpTable OBJECT-TYPE
	SYNTAX	SEQUENCE OF Ds3PlcpEntry
	MAX-ACCESS	not-accessible
	STATUS	current
	DESCRIPTION
		"A table of DS3 Physical Layer Convergence Protocol (Procedure)
		statistics information."
	::= { ds3StatsGroup 2 }

ds3PlcpEntry OBJECT-TYPE
	SYNTAX	Ds3PlcpEntry
	MAX-ACCESS	not-accessible
	STATUS	current
	DESCRIPTION
		"A table entry containing DS3 PLCP statistics information."
	INDEX	{ ds3PlcpBoard, ds3PlcpModule, ds3PlcpPort }
	::= { ds3PlcpTable 1 }

Ds3PlcpEntry ::=
	SEQUENCE {
		ds3PlcpBoard		Integer32,
		ds3PlcpModule		Integer32,
		ds3PlcpPort		Integer32,

		ds3PlcpFERRs		Counter32,
		ds3PlcpLOFs		Counter32,
		ds3PlcpBIP8s		Counter32,
		ds3PlcpFEBEs		Counter32,
		ds3PlcpYellows		Counter32
	}

ds3PlcpBoard OBJECT-TYPE
	SYNTAX	Integer32
	MAX-ACCESS	read-only
	STATUS	current
	DESCRIPTION
		"The index of this port's switch board."
	::= { ds3PlcpEntry 1 }

ds3PlcpModule OBJECT-TYPE
	SYNTAX	Integer32
	MAX-ACCESS	read-only
	STATUS	current
	DESCRIPTION
		"The network module of this port."
	::= { ds3PlcpEntry 2 }

ds3PlcpPort OBJECT-TYPE
	SYNTAX	Integer32
	MAX-ACCESS	read-only
	STATUS	current
	DESCRIPTION
		"The number of this port."
	::= { ds3PlcpEntry 3 }

ds3PlcpFERRs OBJECT-TYPE
	SYNTAX	Counter32
	MAX-ACCESS	read-only
	STATUS	current
	DESCRIPTION
		"Number of Physical Layer Convergence Protocol (PLCP) octet
		error events."
	::= { ds3PlcpEntry 4 }

ds3PlcpLOFs OBJECT-TYPE
	SYNTAX	Counter32
	MAX-ACCESS	read-only
	STATUS	current
	DESCRIPTION
		"The number of seconds in which Loss Of Frame (LOF) errors were
		detected by the PLCP (Physical Layer Convergence Protocol)
		receiver. LOF is declared when an Out-Of-Frame state persists
		for more than 1ms. LOF is removed when in-frame state persists
		for more than 12ms."
	::= { ds3PlcpEntry 5 }

ds3PlcpBIP8s OBJECT-TYPE
	SYNTAX	Counter32
	MAX-ACCESS	read-only
	STATUS	current
	DESCRIPTION
		"Number of BIP-8 (Bit Interleaved Parity - 8) error events. The
		BIP-8 is calculated over the Path Overhead field and the
		associated ATM cell of the previous frame. A BIP-N is a method
		of error monitoring. An N bit code is generated by the
		transmitting equipment in such a manner that the first bit of
		the code provides even parity over the first bit of all N-bit
		sequences in the previous VT SPE, the second bit provides even
		parity over the second bits of all N-bit sequences within the
		specified portion, etc."
	::= { ds3PlcpEntry 6 }

ds3PlcpFEBEs OBJECT-TYPE
	SYNTAX	Counter32
	MAX-ACCESS	read-only
	STATUS	current
	DESCRIPTION
		"Number of ATM Far End Block Error (FEBE) events."
	::= { ds3PlcpEntry 7 }

ds3PlcpYellows OBJECT-TYPE
	SYNTAX	Counter32
	MAX-ACCESS	read-only
	STATUS	current
	DESCRIPTION
		"The number of seconds in which Yellow alarm errors were
		detected by the PLCP (Physical Layer Convergence Protocol)
		receiver. Yellow alarm is asserted when 10 consecutive yellow
		signal bits are set to logical 1. Yellow signals are used to
		alert upstream terminals of a downstream failure in order to
		initiate trunk conditioning on the failure circuit."
	::= { ds3PlcpEntry 8 }

------------------------------------------------------------------------

ds3AtmTable OBJECT-TYPE
	SYNTAX	SEQUENCE OF Ds3AtmEntry
	MAX-ACCESS	not-accessible
	STATUS	current
	DESCRIPTION
		"A table of DS3 ATM statistics information."
	::= { ds3StatsGroup 3 }

ds3AtmEntry OBJECT-TYPE
	SYNTAX	Ds3AtmEntry
	MAX-ACCESS	not-accessible
	STATUS	current
	DESCRIPTION
		"A table entry containing DS3 ATM statistics information."
	INDEX	{ ds3AtmBoard, ds3AtmModule, ds3AtmPort }
	::= { ds3AtmTable 1 }

Ds3AtmEntry ::=
	SEQUENCE {
		ds3AtmBoard		Integer32,
		ds3AtmModule		Integer32,
		ds3AtmPort		Integer32,

		ds3AtmHCSs		Counter32,
		ds3AtmRxCells		Counter32,
		ds3AtmTxCells		Counter32,
		ds3AtmLCDs		Counter32
	}

ds3AtmBoard OBJECT-TYPE
	SYNTAX	Integer32
	MAX-ACCESS	read-only
	STATUS	current
	DESCRIPTION
		"The index of this port's switch board."
	::= { ds3AtmEntry 1 }

ds3AtmModule OBJECT-TYPE
	SYNTAX	Integer32
	MAX-ACCESS	read-only
	STATUS	current
	DESCRIPTION
		"The network module of this port."
	::= { ds3AtmEntry 2 }

ds3AtmPort OBJECT-TYPE
	SYNTAX	Integer32
	MAX-ACCESS	read-only
	STATUS	current
	DESCRIPTION
		"The number of this port."
	::= { ds3AtmEntry 3 }

ds3AtmHCSs OBJECT-TYPE
	SYNTAX	Counter32
	MAX-ACCESS	read-only
	STATUS	current
	DESCRIPTION
		"Number of header check sequence (HCS) error events. The HCS is
		a CRC-8 calculation over the first 4 octets of the ATM cell
		header."
	::= { ds3AtmEntry 4 }

ds3AtmRxCells OBJECT-TYPE
	SYNTAX	Counter32
	MAX-ACCESS	read-only
	STATUS	current
	DESCRIPTION
		"Number of ATM cells that were received."
	::= { ds3AtmEntry 5 }

ds3AtmTxCells OBJECT-TYPE
	SYNTAX	Counter32
	MAX-ACCESS	read-only
	STATUS	current
	DESCRIPTION
		"Number of non-null ATM cells that were transmitted."
	::= { ds3AtmEntry 6 }

ds3AtmLCDs OBJECT-TYPE
	SYNTAX	Counter32
	MAX-ACCESS	read-only
	STATUS	current
	DESCRIPTION
		"The number of seconds in which Loss of Cell Delineation (LCD)
		has occurred.  An LCD defect is detected when an out of cell
		delination state has persisted for 4ms.  An LCD defect is
		cleared when the sync state has been maintained for 4ms."
	::= { ds3AtmEntry 7 }

END
