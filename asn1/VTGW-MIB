-- MIB definition for the VocalTec Telephony Gateway Server.

        VTGW-MIB DEFINITIONS ::= BEGIN

        IMPORTS
	TRAP-TYPE FROM RFC-1215
                enterprises, Counter, Gauge, TimeTicks
                        FROM RFC1155-SMI
                OBJECT-TYPE
                        FROM RFC-1212
                DisplayString
                        FROM RFC1213-MIB;

-------------------------------------------------------------------------------

        vocaltec             OBJECT IDENTIFIER ::= { enterprises 2516 }
        vtg                  OBJECT IDENTIFIER ::= { vocaltec 2 }

        tgw                  OBJECT IDENTIFIER ::= { vtg 1 }
        vnmvgk               OBJECT IDENTIFIER ::= { vtg 2 }
        hasp                 OBJECT IDENTIFIER ::= { vtg 3 }
        audio                OBJECT IDENTIFIER ::= { vtg 4 }
        ports                OBJECT IDENTIFIER ::= { vtg 5 }
        ivr                  OBJECT IDENTIFIER ::= { vtg 6 }
        telephonyProtocols   OBJECT IDENTIFIER ::= { vtg 7 }
        stat                 OBJECT IDENTIFIER ::= { vtg 8 }
        trapParameters       OBJECT IDENTIFIER ::= { vtg 9 }

        analog               OBJECT IDENTIFIER ::= { telephonyProtocols 1 }
        enm                  OBJECT IDENTIFIER ::= { telephonyProtocols 2 }
        gc                   OBJECT IDENTIFIER ::= { telephonyProtocols 3 }
        pri                  OBJECT IDENTIFIER ::= { telephonyProtocols 4 }
        erbium               OBJECT IDENTIFIER ::= { telephonyProtocols 5 }
	   --	Carbon               OBJECT IDENTIFIER ::= { telephonyProtocols 6 }
		iridium              OBJECT IDENTIFIER ::= { telephonyProtocols 7 }

-------------------------------------------------------------------------------

        -- Configuration Parameters--

        -- VTGW (TGW) section                                               

        softwareVersion OBJECT-TYPE
                SYNTAX  DisplayString
                ACCESS  read-only
                STATUS  mandatory
                DESCRIPTION  
			"The VTGW software version number."
        ::= { tgw 1 }

        cti2Service  	OBJECT-TYPE
                SYNTAX  DisplayString
                ACCESS  read-only
                STATUS  mandatory
                DESCRIPTION
			"CTI2 service name."
        ::= { tgw 2 }

        resloveMode	OBJECT-TYPE
                SYNTAX  INTEGER
                {
                        gatekeeper(1),
                        local     (2)
                }
                ACCESS  read-write
                STATUS  mandatory
                DESCRIPTION
			"Resolving mode of the destination gateway IP
			address: can be done by a gatekeeper or localy
			at the VTGW by dialing plan."
        ::= { tgw 3 }

        telephonyProtocol OBJECT-TYPE
                SYNTAX  INTEGER
                {
                        analog (1),
                        pri (2),
                        enm (3),
                        gc  (4),
						erbium (5),
						carbon (6),
						iridium (7)
                }
                ACCESS  read-write
                STATUS  mandatory
                DESCRIPTION
			"The telephony protocol used by VTGW."
        ::= { tgw 4 }

        internetProtocol OBJECT-TYPE
                SYNTAX  INTEGER
                {
                        classic (1),
                        h323    (2),
                        dm3     (3),
						cobalt  (4)
                }
                ACCESS  read-write
                STATUS  mandatory
                DESCRIPTION
			"The Internet protocol used by VTGW."
        ::= { tgw 5 }

        universalLinesNumber OBJECT-TYPE
                SYNTAX  INTEGER
                ACCESS  read-only
                STATUS  mandatory
                DESCRIPTION
			"The maximum number of universal (vioce and fax
			capability) lines,that can be licensed on this VTGW."
        ::= { tgw 6 }

        voiceLinesNumber OBJECT-TYPE
                SYNTAX  INTEGER
                ACCESS  read-only
                STATUS  mandatory
                DESCRIPTION
			"The maximum number of voice lines,that can be
			licensed on this VTGW."
        ::= { tgw 7 }

        faxLinesNumber  OBJECT-TYPE
                SYNTAX  INTEGER
                ACCESS  read-only
                STATUS  mandatory
                DESCRIPTION
			"The maximum number of fax lines,that can be
			licensed on this VTGW."
        ::= { tgw 8 }

        sncLinesNumber  OBJECT-TYPE
                SYNTAX  INTEGER
                ACCESS  read-only
                STATUS  mandatory
                DESCRIPTION
			"The maximum number of Surf & Call lines,that can be
			licensed on this VTGW."
        ::= { tgw 9 }

        iPhoneLinesNumber OBJECT-TYPE
                SYNTAX  INTEGER
                ACCESS  read-only
                STATUS  mandatory
                DESCRIPTION
			"The maximum number of iPhone lines,that can be
			licensed on this VTGW."
        ::= { tgw 10 }

        dialerLinesNumber OBJECT-TYPE
                SYNTAX  INTEGER
                ACCESS  read-only
                STATUS  mandatory
                DESCRIPTION
			"The maximum number of Dialer lines,that can be
			licensed on this VTGW."
        ::= { tgw 11 }

	cti2ServicePollingQuantum OBJECT-TYPE
		SYNTAX  INTEGER
		ACCESS  read-write
		STATUS  mandatory
		DESCRIPTION "CTI2 service polling quantum (sec)."
	::= { tgw 14 }


        -- VNM & VGK section

        rcamPort	OBJECT-TYPE
                SYNTAX  INTEGER
                ACCESS  read-only
                STATUS  mandatory
                DESCRIPTION
			"VNM (RCAM) port."
        ::= { vnmvgk 1 }

        id		OBJECT-TYPE
                SYNTAX  DisplayString
                ACCESS  read-only
                STATUS  mandatory
                DESCRIPTION
			"VGK ID."
        ::= { vnmvgk 2 }

        alias		OBJECT-TYPE
                SYNTAX  DisplayString
                ACCESS  read-only
                STATUS  mandatory
                DESCRIPTION
			"VGK Alias."
        ::= { vnmvgk 3 }

        time2Live	OBJECT-TYPE
                SYNTAX  INTEGER
                ACCESS  read-write
                STATUS  mandatory
                DESCRIPTION
			"Time in seconds to live acknowledge to VGK."
        ::= { vnmvgk 5 }

        loginSetAttempts OBJECT-TYPE
                SYNTAX  INTEGER
                ACCESS  read-write
                STATUS  mandatory
                DESCRIPTION
			"Login attempts to VGK within a set."
        ::= { vnmvgk 6 }

        timeB4LoginAttempt OBJECT-TYPE
                SYNTAX  INTEGER
                ACCESS  read-write
                STATUS  mandatory
                DESCRIPTION
			"Time in seconds before the next login 
                        attempt to VGK within a set."
        ::= { vnmvgk 7 }

        timeB4LoginSet	OBJECT-TYPE
                SYNTAX  INTEGER
                ACCESS  read-write
                STATUS  mandatory
                DESCRIPTION
			"Time in seconds before the next login 
                        set to VGK."
        ::= { vnmvgk 8 }

        rasPort	OBJECT-TYPE
                SYNTAX  INTEGER
                ACCESS  read-only
                STATUS  mandatory
                DESCRIPTION
			"The port for connecting the VGK."
        ::= { vnmvgk 30 }

        -- HASP section


        -- Audio section     

        codecsPriorities  OBJECT-TYPE
                SYNTAX  DisplayString
                ACCESS  read-write
                STATUS  mandatory
                DESCRIPTION
			"Prioritized list of active codecs ex: 7 1 2 5 8 20" 
        ::= { audio 1 }

        preferredCodec  OBJECT-TYPE
                SYNTAX  INTEGER
                ACCESS  read-write
                STATUS  mandatory
                DESCRIPTION
			"Preferred codec."
        ::= { audio 2 }

        outputGain  OBJECT-TYPE
                SYNTAX  DisplayString
                ACCESS  read-write
                STATUS  mandatory
                DESCRIPTION
			"Output volume gain." 
        ::= { audio 3 }

        inputGain  OBJECT-TYPE
                SYNTAX  DisplayString
                ACCESS  read-write
                STATUS  mandatory
                DESCRIPTION
			"Input volume gain." 
        ::= { audio 4 }


        codecsTable  OBJECT-TYPE
                SYNTAX  SEQUENCE OF CodecEntry
                ACCESS  not-accessible
                STATUS  mandatory
                DESCRIPTION "codecs array of structures."
        ::= { audio 5 }

        codecEntry  OBJECT-TYPE
                SYNTAX  CodecEntry
                ACCESS  not-accessible
                STATUS  mandatory
                DESCRIPTION "Codec entry."
                INDEX  { coder }
        ::= { codecsTable 1 }

        CodecEntry ::= 
                SEQUENCE {
                        coder
                                INTEGER,
                        vadEnable
                                INTEGER,
                        coderRate
                                INTEGER,
                        framesPerPkt
                                INTEGER,
                        framesSize
                                INTEGER,
                        jitter
                                DisplayString,
                        jitterOptFactor
                                DisplayString,
                        coderRedundency
                                INTEGER
                 }

        coder  OBJECT-TYPE
                SYNTAX  INTEGER
                {
                    g711a(1),	
					g711m(2),	
					g723 (3),
					g729 (4), 
					gsm  (5),
					g726 (6), 
					g727 (7), 
					g728 (8), 
					vsc  (9),
					vhqc4800(10), 
					vhqc5600(11), 
					vhqc6400(12),  
					vhqc7200(13), 
					vhqc8000(14),  
					vhqc8800(15),  
					vhqc9600(16)
                }
                ACCESS  read-only
                STATUS  mandatory
                DESCRIPTION "Coder number."
        ::= { codecEntry 1 }

        vadEnable  OBJECT-TYPE
                SYNTAX  INTEGER
                ACCESS  read-write
                STATUS  mandatory
                DESCRIPTION "VAD enable."
        ::= { codecEntry 2 }

        coderRate  OBJECT-TYPE
                SYNTAX  INTEGER
                ACCESS  read-write
                STATUS  mandatory
                DESCRIPTION "Coder Rate."
        ::= { codecEntry 3 }

        framesPerPkt  OBJECT-TYPE
                SYNTAX  INTEGER
                ACCESS  read-write
                STATUS  mandatory
                DESCRIPTION "Frames Per Pkt."
        ::= { codecEntry 4 }

        framesSize  OBJECT-TYPE
                SYNTAX   INTEGER
                ACCESS  read-write
                STATUS  mandatory
                DESCRIPTION "Frames Size."
        ::= { codecEntry 5 }

        jitter   OBJECT-TYPE
                SYNTAX  DisplayString
                ACCESS  read-write
                STATUS  mandatory
                DESCRIPTION "Jitter Min. Delay."
        ::= { codecEntry 6 }

        jitterOptFactor  OBJECT-TYPE
                SYNTAX  DisplayString
                ACCESS  read-write
                STATUS  mandatory
                DESCRIPTION "Jitter Opt Factor."
        ::= { codecEntry 7 }

        coderRedundency  OBJECT-TYPE
                SYNTAX  INTEGER
                ACCESS  read-write
                STATUS  mandatory
                DESCRIPTION "CoderRedundency."
        ::= { codecEntry 8 }



        -- Ports section 

        portsTable  OBJECT-TYPE
                SYNTAX  SEQUENCE OF PortEntry
                ACCESS  not-accessible
                STATUS  mandatory
                DESCRIPTION "Ports array of structures."
        ::= { ports 1 }

        portEntry  OBJECT-TYPE
                SYNTAX  PortEntry
                ACCESS  not-accessible
                STATUS  mandatory
                DESCRIPTION "Port entry."
                INDEX  { portNumber }
        ::= { portsTable 1 }

        PortEntry ::= 
                SEQUENCE {
                        portNumber
                                INTEGER,
                        portEnable
                                INTEGER,
                        connectedTo
                                INTEGER,
                        boundDirection
                                INTEGER,
                        dialingMode
                                INTEGER,
                        detectionMode
                                INTEGER,
                        ivrMode
                                INTEGER,
                        repeatIVR
                                INTEGER,
                        overSilenceTime
                                INTEGER,
                        comment
                                DisplayString
                }

        portNumber  OBJECT-TYPE
                SYNTAX  INTEGER
                ACCESS  read-write
                STATUS  mandatory
                DESCRIPTION "Port number."
        ::= { portEntry 1 }

        portEnable  OBJECT-TYPE
                SYNTAX  INTEGER
                ACCESS  read-write
                STATUS  mandatory
                DESCRIPTION "Port enable."
        ::= { portEntry 2 }

        connectedTo  OBJECT-TYPE
                SYNTAX  INTEGER
                {
                        pbx (1),
                        pstn(2)
                }
                ACCESS  read-write
                STATUS  mandatory
                DESCRIPTION "Connected to."
        ::= { portEntry 3 }

        boundDirection  OBJECT-TYPE
                SYNTAX  INTEGER
                {
                        inbound      (1),
                        outbound     (2),
                        bidirectional(3)
                }
                ACCESS  read-write
                STATUS  mandatory
                DESCRIPTION "Bound direction."
        ::= { portEntry 4 }

        dialingMode  OBJECT-TYPE
                SYNTAX   INTEGER
                {
                        dialing-dtmf (1),
                        dialing-pulse(2),
                        dialing-mf   (3)
                }
                ACCESS  read-write
                STATUS  mandatory
                DESCRIPTION "Dialing mode."
        ::= { portEntry 5 }

        detectionMode   OBJECT-TYPE
                SYNTAX  INTEGER
                {
                        detection-dtmf(1),
                        detection-lpd (2),
                        detection-apd (3),
                        detection-mf  (4),
                        detection-dpd (5),
                        detection-dpd2(6)
                }
                ACCESS  read-write
                STATUS  mandatory
                DESCRIPTION "Detection mode."
        ::= { portEntry 6 }

        ivrMode  OBJECT-TYPE
                SYNTAX   INTEGER
                {
                        numberphone(1),
                        numberpin  (2),
                        phonepin   (3),
                        pbx       (4),
                        ani        (5),
                        dnis       (6)
                }
                ACCESS  read-write
                STATUS  mandatory
                DESCRIPTION "IVR mode."
        ::= { portEntry 7 }

        repeatIVR  OBJECT-TYPE
                SYNTAX  INTEGER
                ACCESS  read-write
                STATUS  mandatory
                DESCRIPTION "Repeat IVR."
        ::= { portEntry 8 }


        overSilenceTime  OBJECT-TYPE
                SYNTAX   INTEGER
                ACCESS   read-write
                STATUS   mandatory
                DESCRIPTION "OverSilence time."
        ::= { portEntry 9 }

        comment  OBJECT-TYPE
                SYNTAX  DisplayString
                ACCESS  read-write
                STATUS  mandatory
                DESCRIPTION "Comment."
        ::= { portEntry 10 }


        -- IVR section

        interDigitTimeout OBJECT-TYPE
                SYNTAX  INTEGER
                ACCESS  read-write
                STATUS  mandatory
                DESCRIPTION
			"Inter digit timeout."
        ::= { ivr 1 }

        digitsTimeout  OBJECT-TYPE
                SYNTAX  INTEGER
                ACCESS  read-write
                STATUS  mandatory
                DESCRIPTION
			"Timeout for all digits."
        ::= { ivr 2 }


        -- Telephony Protocols section

		channelSelectionOrder OBJECT-TYPE
                SYNTAX  INTEGER
                {
                        up		(1),
                        down    (2)
                }
                ACCESS  read-write
                STATUS  mandatory
                DESCRIPTION
			"Order in which the selection is done - Up (1) or Down (2) only."
		::= { telephonyProtocols 20 }

        glareMode  OBJECT-TYPE
                 SYNTAX  INTEGER
                {
                        yield	(1),
                        stand   (2)
                }
                ACCESS  read-write
                STATUS  mandatory
				DESCRIPTION 	"Glare mode selection - YIELD (1) or STAND (2) only."
        ::= { telephonyProtocols 21 }



        -- Analog section             

		ringCount OBJECT-TYPE
                SYNTAX  INTEGER
                ACCESS  read-write
                STATUS  mandatory
                DESCRIPTION "Number of rings before returning the ring event."
        ::= { analog 21 }

		volume OBJECT-TYPE
                SYNTAX  INTEGER
                ACCESS  read-write
                STATUS  mandatory
                DESCRIPTION "Engine volume control."
        ::= { analog 22 }


        -- EnM section                                                  

        idle	OBJECT-TYPE
                SYNTAX  DisplayString
                ACCESS  read-write
                STATUS  mandatory
                DESCRIPTION "Idle bits, default=00--"
        ::= { enm 1 }

        outOfService	OBJECT-TYPE
                SYNTAX  DisplayString
                ACCESS  read-write
                STATUS  mandatory
                DESCRIPTION "Out Of Service bits, default=1101"
        ::= { enm 2 }

        seizeOutbound	OBJECT-TYPE
                SYNTAX  DisplayString
                ACCESS  read-write
                STATUS  mandatory
                DESCRIPTION "Seize Outbound bits, default=11--"
        ::= { enm 3 }

        seizeInbound	OBJECT-TYPE
                SYNTAX  DisplayString
                ACCESS  read-write
                STATUS  mandatory
                DESCRIPTION "Seize Inbound bits, default=11--"
        ::= { enm 4 }

        seizeAckOutbound OBJECT-TYPE
                SYNTAX  DisplayString
                ACCESS  read-write
                STATUS  mandatory
                DESCRIPTION "Seize Acknowledge Outbound bits, default=W---"
        ::= { enm 5 }

        seizeAckInbound OBJECT-TYPE
                SYNTAX  DisplayString
                ACCESS  read-write
                STATUS  mandatory
                DESCRIPTION "Seize Acknowledge Inbound bits, default=W---"
        ::= { enm 6 }

		answerOutbound OBJECT-TYPE
                SYNTAX  DisplayString
                ACCESS  read-write
                STATUS  mandatory
                DESCRIPTION "Answer Outbound bits, default=11--"
        ::= { enm 7 }

		answerInbound OBJECT-TYPE
                SYNTAX  DisplayString
                ACCESS  read-write
                STATUS  mandatory
                DESCRIPTION "Answer Inbound bits, default=11--"
        ::= { enm 8 }

		dropOutbound OBJECT-TYPE
                SYNTAX  DisplayString
                ACCESS  read-write
                STATUS  mandatory
                DESCRIPTION "Drop Outbound bits, default=00--"
        ::= { enm 9 }

		dropInbound OBJECT-TYPE
                SYNTAX  DisplayString
                ACCESS  read-write
                STATUS  mandatory
                DESCRIPTION "Drop Inbound bits, , default=00--"
        ::= { enm 10 }

		
		noAnswerSec OBJECT-TYPE
                SYNTAX  INTEGER
                ACCESS  read-write
                STATUS  mandatory
                DESCRIPTION "Length of time to wait after first ring back before deciding that the call isn't answered, in 10 mSec, default=3000."
        ::= { enm 11 }

		continuesNoSignal OBJECT-TYPE
                SYNTAX  INTEGER
                ACCESS  read-write
                STATUS  mandatory
                DESCRIPTION "The max. length of time that no ringback was returned, in 10 mSec, default=4000."
        ::= { enm 12 }

		helloEdge OBJECT-TYPE
                SYNTAX  INTEGER
                ACCESS  read-write
                STATUS  mandatory
                DESCRIPTION "When to tell the app. that the remote connected, 1=Rising Endge - Immediately when connect is detected, 2=Falling Endge - After the end of the solution."
        ::= { enm 13 }

		maxInterRing OBJECT-TYPE
                SYNTAX  INTEGER
                ACCESS  read-write
                STATUS  mandatory
                DESCRIPTION "The max time between ring backs to decide that the call connected, in 10 mSec, default=800."
        ::= { enm 14 }

	    
		dialToneLocal OBJECT-TYPE
                SYNTAX  DisplayString
                ACCESS  read-write
                STATUS  mandatory
                DESCRIPTION "Local Dial tone, default= ."
        ::= { enm 15 } 

        dialToneIntl OBJECT-TYPE
                SYNTAX  DisplayString
                ACCESS  read-write
                STATUS  mandatory
                DESCRIPTION "International Dial tone, default= ."
        ::= { enm 16 } 

        dialToneXtra OBJECT-TYPE
                SYNTAX  DisplayString
                ACCESS  read-write
                STATUS  mandatory
                DESCRIPTION "Extra Dial tone, default= ."
        ::= { enm 17 } 

		busy1Tone OBJECT-TYPE
                SYNTAX  DisplayString
                ACCESS  read-write
                STATUS  mandatory
                DESCRIPTION "Busy 1 tone, default= ."
        ::= { enm 18 } 

        busy2Tone OBJECT-TYPE
                SYNTAX  DisplayString
                ACCESS  read-write
                STATUS  mandatory
                DESCRIPTION "Busy 2 tone, default= ."
        ::= { enm 19 }

		ringback1Tone OBJECT-TYPE
                SYNTAX  DisplayString
                ACCESS  read-write
                STATUS  mandatory
                DESCRIPTION "Ringback 1 tone, default= ."
        ::= { enm 20 }                                               

        ringback2Tone OBJECT-TYPE
                SYNTAX  DisplayString
                ACCESS  read-write
                STATUS  mandatory
                DESCRIPTION "Ringback 2 tone, default= ."
        ::= { enm 21 } 

        disconnect1Tone OBJECT-TYPE
                SYNTAX  DisplayString
                ACCESS  read-write
                STATUS  mandatory
                DESCRIPTION "Disconnect 1 tone, default= ."
        ::= { enm 22 } 

        disconnect2Tone OBJECT-TYPE
                SYNTAX  DisplayString
                ACCESS  read-write
                STATUS  mandatory
                DESCRIPTION "Disconnect 2 tone, default= ."
        ::= { enm 23 } 


        waitForDropAckTimer OBJECT-TYPE
                SYNTAX  INTEGER
                ACCESS  read-write
                STATUS  mandatory
                DESCRIPTION "The time to wait for drop ack, in mSec, default=2000."
        ::= { enm 24 } 

        waitForSiezeAckTimer OBJECT-TYPE
                SYNTAX  INTEGER
                ACCESS  read-write
                STATUS  mandatory
                DESCRIPTION "The time to wait for sieze ack, in mSec, default=10000."
        ::= { enm 25 } 

		digitsMode OBJECT-TYPE
                SYNTAX  DisplayString
                ACCESS  read-write
                STATUS  mandatory
                DESCRIPTION "The pormat of sending the digits - 'T'=DTMF, 'M'=MF, 'P'=PULSE, default='T'."
        ::= { enm 26 }

 		isDnisBeforeAni OBJECT-TYPE
                SYNTAX  INTEGER
                ACCESS  read-write
                STATUS  mandatory
                DESCRIPTION "Does the ANI is previous to the DNIS, if 1(TRUE) - DNIS is before the ANI, default=1(TRUE)."
        ::= { enm 27 }

 		collectAni OBJECT-TYPE
                SYNTAX  INTEGER
                ACCESS  read-write
                STATUS  mandatory
                DESCRIPTION "Should the engine expect ANI. Default=1(TRUE)"
        ::= { enm 28 }

  		prewinkLength OBJECT-TYPE
                SYNTAX  INTEGER
                ACCESS  read-write
                STATUS  mandatory
                DESCRIPTION "The max. length in 10mSec of the pre-wink. Default=0"
        ::= { enm 29 }

  		winkLength OBJECT-TYPE
                SYNTAX  INTEGER
                ACCESS  read-write
                STATUS  mandatory
                DESCRIPTION "The max. length of the wink generation, in 10 mSec. Default=15"
        ::= { enm 30 }

  		minWinkDetection OBJECT-TYPE
                SYNTAX  INTEGER
                ACCESS  read-write
                STATUS  mandatory
                DESCRIPTION "The min. time in the receiver for detecting the wink, in 10 mSec. Default=10"
        ::= { enm 31 }

  		maxWinkDetection OBJECT-TYPE
                SYNTAX  INTEGER
                ACCESS  read-write
                STATUS  mandatory
                DESCRIPTION "The max. time in the receiver for detecting the wink, in 10 mSec. Default=32"
        ::= { enm 32 }

  		maxDigitsDnis OBJECT-TYPE
                SYNTAX  INTEGER
                ACCESS  read-write
                STATUS  mandatory
                DESCRIPTION "The max. # of DNIS digits for the receiver/transmiter. The max. # of digits for the DNIS+ANI in hardware dependenc-31."
        ::= { enm 33 }

  		maxDigitsAni OBJECT-TYPE
                SYNTAX  INTEGER
                ACCESS  read-write
                STATUS  mandatory
                DESCRIPTION "The max.# of ANI digits for the receiver/transmiter. The max.# of digits for the DNIS+ANI in hardware dependenc-31."
        ::= { enm 34 }

  		minTimeToDetectTransition OBJECT-TYPE
                SYNTAX  INTEGER
                ACCESS  read-write
                STATUS  mandatory
                DESCRIPTION "The min. time to detect transition from 0 to 1 and from 1 to 0, in 10mSec. Default=5 (max. value is 255)"
        ::= { enm 35 }

  		charBeforedigits OBJECT-TYPE
                SYNTAX  DisplayString
                ACCESS  read-write
                STATUS  mandatory
                DESCRIPTION "the character before the digits, Default - '*', if there isnt any '' will be used"
        ::= { enm 36 }

  		charBetweenAniAndDnis OBJECT-TYPE
                SYNTAX  DisplayString
                ACCESS  read-write
                STATUS  mandatory
                DESCRIPTION "If there is ANI - this is the char between the DNIS and the ANI, Default - '*', if there isnt any '' will be used"
        ::= { enm 37 }

  		charInTheEndOfDigits OBJECT-TYPE
                SYNTAX  DisplayString
                ACCESS  read-write
                STATUS  mandatory
                DESCRIPTION "The char in the end of digits, Default - '*', if there isnt any '' will be used"
        ::= { enm 38 }

  		sendCharBeforeDigits OBJECT-TYPE
                SYNTAX  DisplayString
                ACCESS  read-write
                STATUS  mandatory
                DESCRIPTION "The char before the digits, Default - '*', if there isnt any '' will be used"
        ::= { enm 39 }

  		sendDnisbeforeAni OBJECT-TYPE
                SYNTAX  DisplayString
                ACCESS  read-write
                STATUS  mandatory
                DESCRIPTION "Does ANI is previous to the DNIS, if TRUE DNIS will be sent before the ANI, default DNIS before the ANI"
        ::= { enm 40 }

  		sendCharBetweenAniAndDnis OBJECT-TYPE
                SYNTAX  DisplayString
                ACCESS  read-write
                STATUS  mandatory
                DESCRIPTION "If there is ANI - this is the char between the DNIS and the ANI, Default - '*', if there isnt any '' will be used"
        ::= { enm 41 }

		  sendCharcharInTheEndOfDigits OBJECT-TYPE
                SYNTAX  DisplayString
                ACCESS  read-write
                STATUS  mandatory
                DESCRIPTION "The char in the end of the digits, Default - '*', if there isnt any '' will be used"
        ::= { enm 42 }


 		fileToPlay OBJECT-TYPE
                SYNTAX  DisplayString
                ACCESS  read-write
                STATUS  mandatory
                DESCRIPTION "Path+name of .WAV file to play to user in case of Clear-Back."
        ::= { enm 43 }

		repeatPlayFile OBJECT-TYPE
                SYNTAX  DisplayString
                ACCESS  read-write
                STATUS  mandatory
                DESCRIPTION "Loop the playing of the Clear-Back .WAV file - '0' or '1' only."
        ::= { enm 44 }

 
        -- Global Call (GC) section 

		protocolConfigFileIn  OBJECT-TYPE
				SYNTAX  DisplayString
				ACCESS  read-write
				STATUS  mandatory
				DESCRIPTION "Protocol config file in."
		::= { gc 1 }

		protocolConfigFileOut  OBJECT-TYPE
				SYNTAX  DisplayString
				ACCESS  read-write
				STATUS  mandatory
				DESCRIPTION "Protocol config file out."
		::= { gc 2 }

		listOfProtocolConfigFilesIn  OBJECT-TYPE
				SYNTAX  DisplayString
				ACCESS  read-only
				STATUS  mandatory
				DESCRIPTION "A list of the possible protocol config files in."
		::= { gc 3 }

		listOfProtocolConfigFilesOut  OBJECT-TYPE
				SYNTAX  DisplayString
				ACCESS  read-only
				STATUS  mandatory
				DESCRIPTION "A list of the possible protocol config files out."
		::= { gc 4 }


        -- PRI section 

		--ISDNSetupMessage OBJECT-TYPE
        --       SYNTAX  DisplayString
		--	   ACCESS  read-write
		--	   STATUS  mandatory
		--	   DESCRIPTION "String of prameters according to the utility. Default = ?"
		--::= { pri 3 }

		protocolTrace OBJECT-TYPE
                SYNTAX  INTEGER
				ACCESS  read-write
				STATUS  mandatory
				DESCRIPTION "Activating Dialogic PRI log tracer."
		::= { pri 2 }


		-- iridium section

		hostID OBJECT-TYPE
                SYNTAX  INTEGER
				ACCESS  read-write
				STATUS  mandatory
				DESCRIPTION "SS#7 host ID can be from 0-31. Default = 0."
		::= { iridium 2 }

		sIUIPorID OBJECT-TYPE
                SYNTAX  DisplayString
				ACCESS  read-write
				STATUS  mandatory
				DESCRIPTION "SIU IP address or ID."
		::= { iridium 3 }




---------------------------------------------------------------------------

        -- Statistics 

        timeUpTotal	OBJECT-TYPE
                SYNTAX  DisplayString
                ACCESS  read-only
                STATUS  mandatory
                DESCRIPTION "Time up total."
        ::= { stat 1 }

        timeUpInterval  OBJECT-TYPE
                SYNTAX  DisplayString
                ACCESS  read-only
                STATUS  mandatory
                DESCRIPTION "Time up interval."
        ::= { stat 2 }

        timeSpanTotal	OBJECT-TYPE
                SYNTAX  DisplayString
                ACCESS  read-only
                STATUS  mandatory
                DESCRIPTION "Time span total."
        ::= { stat 3 }

        timeSpanInterval OBJECT-TYPE
                SYNTAX  DisplayString
                ACCESS  read-only
                STATUS  mandatory
                DESCRIPTION "Time span interval."
        ::= { stat 4 }


        vgkLoginAttemptTotal OBJECT-TYPE
                SYNTAX  Counter
                ACCESS  read-only
                STATUS  mandatory
                DESCRIPTION "GateKeeper login attempt total."
        ::= { stat 5 }

        vgkLoginAttemptInterval OBJECT-TYPE
                SYNTAX  Counter
                ACCESS  read-only
                STATUS  mandatory
                DESCRIPTION "GateKeeper login attempt interval."
        ::= { stat 6 }

        vgkLoginSuccessTotal OBJECT-TYPE
                SYNTAX   Counter
                ACCESS   read-only
                STATUS   mandatory
                DESCRIPTION "GateKeeper login success total."
        ::= { stat 7 }

        vgkLoginSuccessInterval OBJECT-TYPE
                SYNTAX   Counter
                ACCESS   read-only
                STATUS   mandatory
                DESCRIPTION "GateKeeper login success interval."
        ::= { stat 8 }

        vgkLoginFailureTotal OBJECT-TYPE
                SYNTAX   Counter
                ACCESS   read-only
                STATUS   mandatory
                DESCRIPTION "GateKeeper login failure total."
        ::= { stat 9 }

        vgkLoginFailureInterval OBJECT-TYPE
                SYNTAX  Counter
                ACCESS  read-only
                STATUS  mandatory
                DESCRIPTION "GateKeeper login failure interval."
        ::= { stat 10 }

        vgkLogoutAttemptTotal OBJECT-TYPE
                SYNTAX  Counter
                ACCESS  read-only
                STATUS  mandatory
                DESCRIPTION "GateKeeper logout attempt total."
        ::= { stat 11 }

        vgkLogoutAttemptInterval OBJECT-TYPE
                SYNTAX  Counter
                ACCESS  read-only
                STATUS  mandatory
                DESCRIPTION "GateKeeper logout attempt interval."
        ::= { stat 12 }

        vgkLogoutSuccessTotal OBJECT-TYPE
                SYNTAX  Counter
                ACCESS  read-only
                STATUS  mandatory
                DESCRIPTION "GateKeeper logout success total."
        ::= { stat 13 }

        vgkLogoutSuccessInterval OBJECT-TYPE
                SYNTAX  Counter
                ACCESS  read-only
                STATUS  mandatory
                DESCRIPTION "GateKeeper logout success interval."
        ::= { stat 14 }

        vgkLogoutFailureTotal OBJECT-TYPE
                SYNTAX  Counter
                ACCESS  read-only
                STATUS  mandatory
                DESCRIPTION "GateKeeper logout failure total."
        ::= { stat 15 }

        vgkLogoutFailureInterval OBJECT-TYPE
                SYNTAX  Counter
                ACCESS  read-only
                STATUS  mandatory
                DESCRIPTION "GateKeeper logout failure interval."
        ::= { stat 16 }

        vgkDisconnectionTotal OBJECT-TYPE
                SYNTAX  Counter
                ACCESS  read-only
                STATUS  mandatory
                DESCRIPTION "GateKeeper disconnection failure total."
        ::= { stat 17 }

        vgkDisconnectionInterval OBJECT-TYPE
                SYNTAX  Counter
                ACCESS  read-only
                STATUS  mandatory
                DESCRIPTION "GateKeeper disconnection failure interval."
        ::= { stat 18 }


        callValue	OBJECT-TYPE
                SYNTAX  INTEGER
                ACCESS  read-only
                STATUS  mandatory
                DESCRIPTION "Calls value."
        ::= { stat 19 }

        callInterval	OBJECT-TYPE
                SYNTAX  Counter
                ACCESS  read-only
                STATUS  mandatory
                DESCRIPTION "Calls interval."
        ::= { stat 20 }

        callMaxTotal	OBJECT-TYPE
                SYNTAX  INTEGER
                ACCESS  read-only
                STATUS  mandatory
                DESCRIPTION "Calls max total."
        ::= { stat 21 }

        callMaxInterval OBJECT-TYPE
                SYNTAX	INTEGER
                ACCESS  read-only
                STATUS  mandatory
                DESCRIPTION "Calls max interval."
        ::= { stat 22 }

        callAverageTotal OBJECT-TYPE
                SYNTAX  INTEGER
                ACCESS  read-only
                STATUS  mandatory
                DESCRIPTION "Calls average total."
        ::= { stat 23 }

        callAverageInterval OBJECT-TYPE
                SYNTAX  INTEGER
                ACCESS  read-only
                STATUS  mandatory
                DESCRIPTION "Calls average interval."
        ::= { stat 24 }

        callTotal	OBJECT-TYPE
                SYNTAX  Counter
                ACCESS  read-only
                STATUS  mandatory
                DESCRIPTION "Calls total."
        ::= { stat 25 }

        universalCallValue OBJECT-TYPE
                SYNTAX  INTEGER
                ACCESS  read-only
                STATUS  mandatory
                DESCRIPTION "Universal calls value."
        ::= { stat 26 }

        universalCallInterval OBJECT-TYPE
                SYNTAX  Counter
                ACCESS  read-only
                STATUS  mandatory
                DESCRIPTION "Universal calls interval."
        ::= { stat 27 }

        universalCallMaxTotal OBJECT-TYPE
                SYNTAX  INTEGER
                ACCESS  read-only
                STATUS  mandatory
                DESCRIPTION "Universal calls max total."
        ::= { stat 28 }

        universalCallMaxInterval OBJECT-TYPE
                SYNTAX  INTEGER
                ACCESS  read-only
                STATUS  mandatory
                DESCRIPTION "Universal calls max interval."
        ::= { stat 29 }

        universalCallAverageTotal OBJECT-TYPE
                SYNTAX   INTEGER
                ACCESS   read-only
                STATUS   mandatory
                DESCRIPTION "Universal calls average total."
        ::= { stat 30 }

        universalCallAverageInterval OBJECT-TYPE
                SYNTAX   INTEGER
                ACCESS   read-only
                STATUS   mandatory
                DESCRIPTION "Universal calls average interval."
        ::= { stat 31 }

        universalCallTotal OBJECT-TYPE
                SYNTAX  Counter
                ACCESS  read-only
                STATUS  mandatory
                DESCRIPTION "Universal calls total."
        ::= { stat 32 }

        voiceCallValue  OBJECT-TYPE
                SYNTAX  INTEGER
                ACCESS  read-only
                STATUS  mandatory
                DESCRIPTION "Voice calls value."
        ::= { stat 33 }

        voiceCallInterval OBJECT-TYPE
                SYNTAX  Counter
                ACCESS  read-only
                STATUS  mandatory
                DESCRIPTION "Voice calls interval."
        ::= { stat 34 }

        voiceCallMaxTotal OBJECT-TYPE
                SYNTAX  INTEGER
                ACCESS  read-only
                STATUS  mandatory
                DESCRIPTION "Voice calls max total."
        ::= { stat 35 }

        voiceCallMaxInterval OBJECT-TYPE
                SYNTAX  INTEGER
                ACCESS  read-only
                STATUS  mandatory
                DESCRIPTION "Voice calls max interval."
        ::= { stat 36 }

        voiceCallAverageTotal OBJECT-TYPE
                SYNTAX  INTEGER
                ACCESS  read-only
                STATUS  mandatory
                DESCRIPTION "Voice calls average total."
        ::= { stat 37 }

        voiceCallAverageInterval OBJECT-TYPE
                SYNTAX  INTEGER
                ACCESS  read-only
                STATUS  mandatory
                DESCRIPTION "Voice calls average interval."
        ::= { stat 38 }

        voiceCallTotal  OBJECT-TYPE
                SYNTAX  Counter
                ACCESS  read-only
                STATUS  mandatory
                DESCRIPTION "Voice calls total."
        ::= { stat 39 }

        faxCallValue	OBJECT-TYPE
                SYNTAX  INTEGER
                ACCESS  read-only
                STATUS  mandatory
                DESCRIPTION "Fax calls value."
        ::= { stat 40 }

        faxCallInterval OBJECT-TYPE
                SYNTAX  Counter
                ACCESS  read-only
                STATUS  mandatory
                DESCRIPTION "Fax calls interval."
        ::= { stat 41 }

        faxCallMaxTotal OBJECT-TYPE
                SYNTAX  INTEGER
                ACCESS  read-only
                STATUS  mandatory
                DESCRIPTION "Fax calls max total."
        ::= { stat 42 }

        faxCallMaxInterval OBJECT-TYPE
                SYNTAX  INTEGER
                ACCESS  read-only
                STATUS  mandatory
                DESCRIPTION "Fax calls max interval."
        ::= { stat 43 }

        faxCallAverageTotal OBJECT-TYPE
                SYNTAX  INTEGER
                ACCESS  read-only
                STATUS  mandatory
                DESCRIPTION "Fax calls average total."
        ::= { stat 44 }

        faxCallAverageInterval OBJECT-TYPE
                SYNTAX  INTEGER
                ACCESS  read-only
                STATUS  mandatory
                DESCRIPTION "Fax calls average interval."
        ::= { stat 45 }

        faxCallTotal	OBJECT-TYPE
                SYNTAX  Counter
                ACCESS  read-only
                STATUS  mandatory
                DESCRIPTION "Fax calls total."
        ::= { stat 46 }

        sncCallValue  	OBJECT-TYPE
                SYNTAX  INTEGER
                ACCESS  read-only
                STATUS  mandatory
                DESCRIPTION "S&C calls value."
        ::= { stat 47 }

        sncCallInterval OBJECT-TYPE
                SYNTAX  Counter
                ACCESS  read-only
                STATUS  mandatory
                DESCRIPTION "S&C calls interval."
        ::= { stat 48 }

        sncCallMaxTotal OBJECT-TYPE
                SYNTAX  INTEGER
                ACCESS  read-only
                STATUS  mandatory
                DESCRIPTION "S&C calls max total."
        ::= { stat 49 }

        sncCallMaxInterval OBJECT-TYPE
                SYNTAX   INTEGER
                ACCESS   read-only
                STATUS   mandatory
                DESCRIPTION "S&C calls max interval."
        ::= { stat 50 }

        sncCallAverageTotal OBJECT-TYPE
                SYNTAX  INTEGER
                ACCESS  read-only
                STATUS  mandatory
                DESCRIPTION "S&C calls average total."
        ::= { stat 51 }

        sncCallAverageInterval OBJECT-TYPE
                SYNTAX  INTEGER
                ACCESS  read-only
                STATUS  mandatory
                DESCRIPTION "S&C calls average interval."
        ::= { stat 52 }

        sncCallTotal  	OBJECT-TYPE
                SYNTAX  Counter
                ACCESS  read-only
                STATUS  mandatory
                DESCRIPTION "S&C calls total."
        ::= { stat 53 }

        iPhoneCallValue OBJECT-TYPE
                SYNTAX  INTEGER
                ACCESS  read-only
                STATUS  mandatory
                DESCRIPTION "iPhone calls value."
        ::= { stat 54 }

        iPhoneCallInterval OBJECT-TYPE
                SYNTAX  Counter
                ACCESS  read-only
                STATUS  mandatory
                DESCRIPTION "iPhone calls interval."
        ::= { stat 55 }

        iPhoneCallMaxTotal OBJECT-TYPE
                SYNTAX  INTEGER
                ACCESS  read-only
                STATUS  mandatory
                DESCRIPTION "iPhone calls max total."
        ::= { stat 56 }

        iPhoneCallMaxInterval OBJECT-TYPE
                SYNTAX  INTEGER
                ACCESS  read-only
                STATUS  mandatory
                DESCRIPTION "iPhone calls max interval."
        ::= { stat 57 }

        iPhoneCallAverageTotal OBJECT-TYPE
                SYNTAX  INTEGER
                ACCESS  read-only
                STATUS  mandatory
                DESCRIPTION "iPhone calls average total."
        ::= { stat 58 }

        iPhoneCallAverageInterval OBJECT-TYPE
                SYNTAX  INTEGER
                ACCESS  read-only
                STATUS  mandatory
                DESCRIPTION "iPhone calls average interval."
        ::= { stat 59 }

        iPhoneCallTotal OBJECT-TYPE
                SYNTAX  Counter
                ACCESS  read-only
                STATUS  mandatory
                DESCRIPTION "iPhone calls total."
        ::= { stat 60 }

        dialerCallValue OBJECT-TYPE
                SYNTAX  INTEGER
                ACCESS  read-only
                STATUS  mandatory
                DESCRIPTION "Dialer calls value."
        ::= { stat 61 }

        dialerCallInterval OBJECT-TYPE
                SYNTAX   Counter
                ACCESS   read-only
                STATUS   mandatory
                DESCRIPTION "Dialer calls interval."
        ::= { stat 62 }

        dialerCallMaxTotal OBJECT-TYPE
                SYNTAX  INTEGER
                ACCESS  read-only
                STATUS  mandatory
                DESCRIPTION "Dialer calls max total."
        ::= { stat 63 }

        dialerCallMaxInterval OBJECT-TYPE
                SYNTAX  INTEGER
                ACCESS  read-only
                STATUS  mandatory
                DESCRIPTION "Dialer calls max interval."
        ::= { stat 64 }

        dialerCallAverageTotal OBJECT-TYPE
                SYNTAX  INTEGER
                ACCESS  read-only
                STATUS  mandatory
                DESCRIPTION "Dialer calls average total."
        ::= { stat 65 }

        dialerCallAverageInterval OBJECT-TYPE
                SYNTAX  INTEGER
                ACCESS  read-only
                STATUS  mandatory
                DESCRIPTION "Dialer calls average interval."
        ::= { stat 66 }

        dialerCallTotal OBJECT-TYPE
                SYNTAX  Counter
                ACCESS  read-only
                STATUS  mandatory
                DESCRIPTION "Dialer calls total."
        ::= { stat 67 }


        incorrectPasswordCallTotal OBJECT-TYPE
                SYNTAX  Counter
                ACCESS  read-only
                STATUS  mandatory
                DESCRIPTION "incorrect password calls total."
        ::= { stat 68 }

        incorrectPasswordCallInterval OBJECT-TYPE
                SYNTAX  Counter
                ACCESS  read-only
                STATUS  mandatory
                DESCRIPTION "incorrect password calls interval."
        ::= { stat 69 }

        notSupportedCallTotal OBJECT-TYPE
                SYNTAX  Counter
                ACCESS  read-only
                STATUS  mandatory
                DESCRIPTION "not supported calls total."
        ::= { stat 72 }

        notSupportedCallInterval OBJECT-TYPE
                SYNTAX   Counter
                ACCESS   read-only
                STATUS   mandatory
                DESCRIPTION "not supported calls interval."
        ::= { stat 73 }


	incomingInternetAttemptCallValue OBJECT-TYPE
                SYNTAX  INTEGER
                ACCESS  read-only
                STATUS  mandatory
                DESCRIPTION "."
        ::= { stat 74 }

	incomingInternetAttemptCallInterval OBJECT-TYPE
                SYNTAX   Counter
                ACCESS   read-only
                STATUS   mandatory
                DESCRIPTION  "."
        ::= { stat 75 }

	incomingInternetAttemptCallMaxTotal OBJECT-TYPE
                SYNTAX  INTEGER
                ACCESS  read-only
                STATUS  mandatory
                DESCRIPTION  "."
        ::= { stat 76 }

	incomingInternetAttemptCallMaxInterval OBJECT-TYPE
                SYNTAX  INTEGER
                ACCESS  read-only
                STATUS  mandatory
                DESCRIPTION  "."
        ::= { stat 77 }

	incomingInternetAttemptCallAverageTotal OBJECT-TYPE
                SYNTAX  INTEGER
                ACCESS  read-only
                STATUS  mandatory
                DESCRIPTION  "."
        ::= { stat 78 }

	incomingInternetAttemptCallAverageInterval OBJECT-TYPE
                SYNTAX  INTEGER
                ACCESS  read-only
                STATUS  mandatory
                DESCRIPTION  "."
        ::= { stat 79 }

	incomingInternetAttemptCallTotal OBJECT-TYPE
                SYNTAX  Counter
                ACCESS  read-only
                STATUS  mandatory
                DESCRIPTION  "."
        ::= { stat 80 }

	incomingInternetSuccessCallValue OBJECT-TYPE
                SYNTAX  INTEGER
                ACCESS  read-only
                STATUS  mandatory
                DESCRIPTION  "."
        ::= { stat 81 }

	incomingInternetSuccessCallInterval OBJECT-TYPE
                SYNTAX   Counter
                ACCESS   read-only
                STATUS   mandatory
                DESCRIPTION  "."
        ::= { stat 82 }

	incomingInternetSuccessCallMaxTotal OBJECT-TYPE
                SYNTAX  INTEGER
                ACCESS  read-only
                STATUS  mandatory
                DESCRIPTION  "."
        ::= { stat 83 }

	incomingInternetSuccessCallMaxInterval OBJECT-TYPE
                SYNTAX  INTEGER
                ACCESS  read-only
                STATUS  mandatory
                DESCRIPTION  "."
        ::= { stat 84 }

	incomingInternetSuccessCallAverageTotal OBJECT-TYPE
                SYNTAX  INTEGER
                ACCESS  read-only
                STATUS  mandatory
                DESCRIPTION  "."
        ::= { stat 85 }

	incomingInternetSuccessCallAverageInterval OBJECT-TYPE
                SYNTAX  INTEGER
                ACCESS  read-only
                STATUS  mandatory
                DESCRIPTION  "."
        ::= { stat 86 }

	incomingInternetSuccessCallTotal OBJECT-TYPE
                SYNTAX  Counter
                ACCESS  read-only
                STATUS  mandatory
                DESCRIPTION  "."
        ::= { stat 87 }

	incomingTelephonyAttemptCallValue OBJECT-TYPE
                SYNTAX  INTEGER
                ACCESS  read-only
                STATUS  mandatory
                DESCRIPTION  "."
        ::= { stat 88 }

	incomingTelephonyAttemptCallInterval OBJECT-TYPE
                SYNTAX   Counter
                ACCESS   read-only
                STATUS   mandatory
                DESCRIPTION  "."
        ::= { stat 89 }

	incomingTelephonyAttemptCallMaxTotal OBJECT-TYPE
                SYNTAX  INTEGER
                ACCESS  read-only
                STATUS  mandatory
                DESCRIPTION  "."
        ::= { stat 90 }

	incomingTelephonyAttemptCallMaxInterval OBJECT-TYPE
                SYNTAX  INTEGER
                ACCESS  read-only
                STATUS  mandatory
                DESCRIPTION  "."
        ::= { stat 91 }

	incomingTelephonyAttemptCallAverageTotal OBJECT-TYPE
                SYNTAX  INTEGER
                ACCESS  read-only
                STATUS  mandatory
                DESCRIPTION  "."
        ::= { stat 92 }

	incomingTelephonyAttemptCallAverageInterval OBJECT-TYPE
                SYNTAX  INTEGER
                ACCESS  read-only
                STATUS  mandatory
                DESCRIPTION  "."
        ::= { stat 93 }

	incomingTelephonyAttemptCallTotal OBJECT-TYPE
                SYNTAX  Counter
                ACCESS  read-only
                STATUS  mandatory
                DESCRIPTION  "."
        ::= { stat 94 }

	incomingTelephonySuccessCallValue OBJECT-TYPE
                SYNTAX  INTEGER
                ACCESS  read-only
                STATUS  mandatory
                DESCRIPTION  "."
        ::= { stat 95 }

	incomingTelephonySuccessCallInterval OBJECT-TYPE
                SYNTAX   Counter
                ACCESS   read-only
                STATUS   mandatory
                DESCRIPTION  "."
        ::= { stat 96 }

	incomingTelephonySuccessCallMaxTotal OBJECT-TYPE
                SYNTAX  INTEGER
                ACCESS  read-only
                STATUS  mandatory
                DESCRIPTION  "."
        ::= { stat 97 }

	incomingTelephonySuccessCallMaxInterval OBJECT-TYPE
                SYNTAX  INTEGER
                ACCESS  read-only
                STATUS  mandatory
                DESCRIPTION  "."
        ::= { stat 98 }

	incomingTelephonySuccessCallAverageTotal OBJECT-TYPE
                SYNTAX  INTEGER
                ACCESS  read-only
                STATUS  mandatory
                DESCRIPTION  "."
        ::= { stat 99 }

	incomingTelephonySuccessCallAverageInterval OBJECT-TYPE
                SYNTAX  INTEGER
                ACCESS  read-only
                STATUS  mandatory
                DESCRIPTION  "."
        ::= { stat 100 }

	incomingTelephonySuccessCallTotal OBJECT-TYPE
                SYNTAX  Counter
                ACCESS  read-only
                STATUS  mandatory
                DESCRIPTION  "."
        ::= { stat 101}

	outgoingInternetCallValue OBJECT-TYPE
                SYNTAX  INTEGER
                ACCESS  read-only
                STATUS  mandatory
                DESCRIPTION  "."
        ::= { stat 102}

	outgoingInternetCallInterval OBJECT-TYPE
                SYNTAX   Counter
                ACCESS   read-only
                STATUS   mandatory
                DESCRIPTION  "."
        ::= { stat 103 }

	outgoingInternetCallMaxTotal OBJECT-TYPE
                SYNTAX  INTEGER
                ACCESS  read-only
                STATUS  mandatory
                DESCRIPTION  "."
        ::= { stat 104 }

	outgoingInternetCallMaxInterval OBJECT-TYPE
                SYNTAX  INTEGER
                ACCESS  read-only
                STATUS  mandatory
                DESCRIPTION  "."
        ::= { stat 105}

	outgoingInternetCallAverageTotal OBJECT-TYPE
                SYNTAX  INTEGER
                ACCESS  read-only
                STATUS  mandatory
                DESCRIPTION  "."
        ::= { stat 106 }

	outgoingInternetCallAverageInterval OBJECT-TYPE
                SYNTAX  INTEGER
                ACCESS  read-only
                STATUS  mandatory
                DESCRIPTION  "."
        ::= { stat 107 }

	outgoingInternetCallTotal OBJECT-TYPE
                SYNTAX  Counter
                ACCESS  read-only
                STATUS  mandatory
                DESCRIPTION  "."
        ::= { stat 108 }

	outgoingTelephonyCallValue OBJECT-TYPE
                SYNTAX  INTEGER
                ACCESS  read-only
                STATUS  mandatory
                DESCRIPTION  "."
        ::= { stat 109 }

	outgoingTelephonyCallInterval OBJECT-TYPE
                SYNTAX   Counter
                ACCESS   read-only
                STATUS   mandatory
                DESCRIPTION  "."
        ::= { stat  110}

	outgoingTelephonyCallMaxTotal OBJECT-TYPE
                SYNTAX  INTEGER
                ACCESS  read-only
                STATUS  mandatory
                DESCRIPTION  "."
        ::= { stat 111 }

	outgoingTelephonyCallMaxInterval OBJECT-TYPE
                SYNTAX  INTEGER
                ACCESS  read-only
                STATUS  mandatory
                DESCRIPTION  "."
        ::= { stat 112 }

	outgoingTelephonyCallAverageTotal OBJECT-TYPE
                SYNTAX  INTEGER
                ACCESS  read-only
                STATUS  mandatory
                DESCRIPTION  "."
        ::= { stat 113 }

	outgoingTelephonyCallAverageInterval OBJECT-TYPE
                SYNTAX  INTEGER
                ACCESS  read-only
                STATUS  mandatory
                DESCRIPTION  "."
        ::= { stat 114 }

	outgoingTelephonyCallTotal OBJECT-TYPE
                SYNTAX  Counter
                ACCESS  read-only
                STATUS  mandatory
                DESCRIPTION  "."
        ::= { stat 115 }


	accountExpiredCallTotal OBJECT-TYPE
                SYNTAX  Counter
                ACCESS  read-only
                STATUS  mandatory
                DESCRIPTION  "."
        ::= { stat 116 }

	accountExpiredCallInterval OBJECT-TYPE
                SYNTAX  Counter
                ACCESS  read-only
                STATUS  mandatory
                DESCRIPTION  "."
        ::= { stat 117 }

	vgkNotAvailableCallTotal OBJECT-TYPE
                SYNTAX  Counter
                ACCESS  read-only
                STATUS  mandatory
                DESCRIPTION  "."
        ::= { stat 118 }

	vgkNotAvailableCallInterval OBJECT-TYPE
                SYNTAX  Counter
                ACCESS  read-only
                STATUS  mandatory
                DESCRIPTION  "."
        ::= { stat 119 }

	vtgShutDownCallTotal OBJECT-TYPE
                SYNTAX  Counter
                ACCESS  read-only
                STATUS  mandatory
                DESCRIPTION  "."
        ::= { stat 120 }

	vtgShutDownCallInterval OBJECT-TYPE
                SYNTAX  Counter
                ACCESS  read-only
                STATUS  mandatory
                DESCRIPTION  "."
        ::= { stat 121 }

	vtgOutOfHoursCallTotal OBJECT-TYPE
                SYNTAX  Counter
                ACCESS  read-only
                STATUS  mandatory
                DESCRIPTION  "."
        ::= { stat 122 }

	vtgOutOfHoursCallInterval OBJECT-TYPE
                SYNTAX  Counter
                ACCESS  read-only
                STATUS  mandatory
                DESCRIPTION  "."
        ::= { stat 123 }

	vtgBusyCallTotal OBJECT-TYPE
                SYNTAX  Counter
                ACCESS  read-only
                STATUS  mandatory
                DESCRIPTION  "."
        ::= { stat 124 }

	vtgBusyCallInterval OBJECT-TYPE
                SYNTAX  Counter
                ACCESS  read-only
                STATUS  mandatory
                DESCRIPTION  "."
        ::= { stat 125 }

	vtgNoAnswerCallTotal OBJECT-TYPE
                SYNTAX  Counter
                ACCESS  read-only
                STATUS  mandatory
                DESCRIPTION  "."
        ::= { stat 126 }

	vtgNoAnswerCallInterval OBJECT-TYPE
                SYNTAX  Counter
                ACCESS  read-only
                STATUS  mandatory
                DESCRIPTION  "."
        ::= { stat 127 }

	telephoneBusyCallTotal OBJECT-TYPE
                SYNTAX  Counter
                ACCESS  read-only
                STATUS  mandatory
                DESCRIPTION  "."
        ::= { stat 128 }

	telephoneBusyCallInterval OBJECT-TYPE
                SYNTAX  Counter
                ACCESS  read-only
                STATUS  mandatory
                DESCRIPTION  "."
        ::= { stat 129 }

	telephoneNoAnswerCallTotal OBJECT-TYPE
                SYNTAX  Counter
                ACCESS  read-only
                STATUS  mandatory
                DESCRIPTION  "."
        ::= { stat 130 }

	telephoneNoAnswerCallInterval OBJECT-TYPE
                SYNTAX  Counter
                ACCESS  read-only
                STATUS  mandatory
                DESCRIPTION  "."
        ::= { stat 131 }

	miscReasonDisconnectedCallTotal OBJECT-TYPE
                SYNTAX  Counter
                ACCESS  read-only
                STATUS  mandatory
                DESCRIPTION  "."
        ::= { stat 132 }

	miscReasonDisconnectedCallInterval OBJECT-TYPE
                SYNTAX  Counter
                ACCESS  read-only
                STATUS  mandatory
                DESCRIPTION  "."
        ::= { stat 133 }

	totalDisconnectedCallsTotal OBJECT-TYPE
                SYNTAX  Counter
                ACCESS  read-only
                STATUS  mandatory
                DESCRIPTION  "."
        ::= { stat 134 }

	totalDisconnectedCallsInterval OBJECT-TYPE
                SYNTAX  Counter
                ACCESS  read-only
                STATUS  mandatory
                DESCRIPTION  "."
        ::= { stat 135 }


	vtgOutOfServiceCallTotal OBJECT-TYPE
                SYNTAX  Counter
                ACCESS  read-only
                STATUS  mandatory
                DESCRIPTION  "."
        ::= { stat 136 }

	vtgOutOfServiceCallInterval OBJECT-TYPE
                SYNTAX  Counter
                ACCESS  read-only
                STATUS  mandatory
                DESCRIPTION  "."
        ::= { stat 137 }

	unauthorizedUserCallTotal OBJECT-TYPE
                SYNTAX  Counter
                ACCESS  read-only
                STATUS  mandatory
                DESCRIPTION  "."
        ::= { stat 138 }

	unauthorizedUserCallInterval OBJECT-TYPE
                SYNTAX  Counter
                ACCESS  read-only
                STATUS  mandatory
                DESCRIPTION  "."
        ::= { stat 139 }

	resolveFailureCallTotal OBJECT-TYPE
                SYNTAX  Counter
                ACCESS  read-only
                STATUS  mandatory
                DESCRIPTION  "."
        ::= { stat 140 }

	resolveFailureCallInterval OBJECT-TYPE
                SYNTAX  Counter
                ACCESS  read-only
                STATUS  mandatory
                DESCRIPTION  "."
        ::= { stat 141 }

	pstnFailureCallTotal OBJECT-TYPE
                SYNTAX  Counter
                ACCESS  read-only
                STATUS  mandatory
                DESCRIPTION  "."
        ::= { stat 142 }

	pstnFailureCallInterval OBJECT-TYPE
                SYNTAX  Counter
                ACCESS  read-only
                STATUS  mandatory
                DESCRIPTION  "."
        ::= { stat 143 }

	abnormalTerminationCallTotal OBJECT-TYPE
                SYNTAX  Counter
                ACCESS  read-only
                STATUS  mandatory
                DESCRIPTION  "."
        ::= { stat 144 }

	abnormalTerminationCallInterval OBJECT-TYPE
                SYNTAX  Counter
                ACCESS  read-only
                STATUS  mandatory
                DESCRIPTION  "."
        ::= { stat 145 }

        -- Trap parameters

        telephonyErrorDescription  OBJECT-TYPE
                SYNTAX  DisplayString
                ACCESS  not-accessible
                STATUS  mandatory
                DESCRIPTION "Detailed description of telephony protocol
                            error occurs. Used with telephonyError 
                            enterprise trap."    
        ::= { trapParameters 1 }

------------------------------------------------------------------------------

        -- Traps section

        setParameterFailure	TRAP-TYPE
                ENTERPRISE	vtg
                DESCRIPTION  
                        "Setting parameter failed."
        ::= 1

        haspExistance		TRAP-TYPE
                ENTERPRISE	vtg
                DESCRIPTION  
                        "HASP existance failed."
        ::= 2

        cti2ServiceFailure	TRAP-TYPE
                ENTERPRISE	vtg
                DESCRIPTION  
                        "CTI2 service failed."
        ::= 3

        vgkLoginFailure		TRAP-TYPE
                ENTERPRISE	vtg
                DESCRIPTION  
                        "VTG has failed to login to VGK."
        ::= 4

        vgkLogoutFailure	TRAP-TYPE
                ENTERPRISE	vtg
                DESCRIPTION 
                        "VTG has failed to logout from VGK."
        ::= 5

        vgkDisconnection	TRAP-TYPE
                ENTERPRISE	vtg
                DESCRIPTION 
                        "VTG disconnected from VGK."
        ::= 6

        telephonyError		TRAP-TYPE
                ENTERPRISE	vtg
                VARIABLES   { telephonyErrorDescription }
                DESCRIPTION 
                        "Telephony error."
        ::= 7

        incorrectPasswordCalls	TRAP-TYPE
                ENTERPRISE	vtg
                DESCRIPTION  
                        "Incorrect password call."
        ::= 8

        disconnectedCalls	TRAP-TYPE
                ENTERPRISE	vtg
                DESCRIPTION  
                        "Disconnected call."
        ::= 9

        notSupportedCalls	TRAP-TYPE
                ENTERPRISE	vtg
                DESCRIPTION 
                        "Not supported Call."
        ::= 10

-------------------------------------------------------------------------------

END
