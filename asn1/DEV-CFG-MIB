--  =======================================================================
--  File        : dev-cfg.mib
--  Description : Private MIB for Device General Configuration
--  By          : Yaron, Sharon, Alon & Alex & Yakov
--  Version     : 0.1
--  Date        : 
--  =======================================================================
--
--
-- Copyright (c) 1999 NBase-Xyplex.  All Rights Reserved.
--
--
-- Reproduction of this document is authorized on condition that this
-- copyright notice is included.  This NBase-Xyplex SNMP MIB Specification
-- embodies NBase-Xyplex's proprietary intellectual property.  NBase-Xyplex
-- retains all title and ownership in the specification, including any
-- revisions.
--
-- It is NBase-Xyplex's intent to encourage the widespread use of this
-- specification in connection with the management of NBase-Xyplex's
-- products. NBase-Xyplex grants vendor, end-users, and other interested
-- parties a non-exclusive license to use this specification in
-- connection with the management of NBase-Xyplex's products.
--
-- This specification is supplied "AS IS," and NBase-Xyplex makes no
-- warranty, either express or implied, as to the use, operation,
-- condition, or performance of the specification.
--
-- Copyright text courtesy of NBase-Xyplex
--
-- If you have any questions about this MIB, please call NBase-Xyplex
-- Technical Support Center at 1-800-858-7815 from inside USA or
-- 1-818-773-0900 from outside USA.
--
--
-- NBase-Xyplex retains the right to change this MIB without notification.
--

DEV-CFG-MIB DEFINITIONS ::= BEGIN

		IMPORTS
				enterprises	FROM RFC1155-SMI
				DisplayString	FROM RFC1213-MIB
				OBJECT-TYPE	FROM RFC-1212;

-- ************************************************************
-- NBase Object Identifier Definition
-- ************************************************************

nbase              OBJECT IDENTIFIER ::= { enterprises 629 }
nbSwitchG1         OBJECT IDENTIFIER ::= { nbase 1 }
nbSwitchG1Il       OBJECT IDENTIFIER ::= { nbSwitchG1 50}

-- GROUPS for General Device Configuration
nbDeviceConfig     OBJECT IDENTIFIER ::= { nbSwitchG1Il 11}
nbDevGen           OBJECT IDENTIFIER ::= { nbDeviceConfig 1 }

-- -------------------------  nbDevGen ------------------------------------

nbDevOperationMode      OBJECT-TYPE
		SYNTAX  INTEGER
		{
		 accelerouter  (1),
		 router        (2),
		 switch        (3)
		}

		ACCESS  read-only
		STATUS  mandatory
		DESCRIPTION
		"The Operational mode of Device. This is for internal usage."
		::= { nbDevGen 1 }

nbDevErrorText		OBJECT-TYPE
		SYNTAX  DisplayString
		ACCESS  read-only
		STATUS  mandatory
		DESCRIPTION
		"This is the text of the last error that the agent found.
		 it is sent to the RS232 port, and it used by the manager
		 to show the cause of the last error."
		::= { nbDevGen 2 }

nbDevRouterSaveConfig	OBJECT-TYPE
		SYNTAX  INTEGER
		{
		 saveConfig  (1),
		 resetConfig (2)
		}
		ACCESS  read-write
		STATUS  mandatory
		DESCRIPTION
		"If operation SET is issued with value saveConfig(1), all
		 configuration is to be saved in relevant configuration files;
		 if operation SET is issued with value resetConfig(2), all
		 configuration is to get from relevant configuration files"
		::= { nbDevGen 4 }

-- ykfix39 - 21.09.00 - begin
nbsDevProperties	OBJECT-TYPE
		SYNTAX	INTEGER
		ACCESS    read-only
		STATUS    mandatory
		DESCRIPTION
                 "Additional Device Properties.
                  This MIB Object is created as a Bits Mask,
                  when the corresponding Bit says about the
                  specific property.
		  value=0 : If no additional properties exist.
		  value=1 : If Device have a Redundant Power Supply.
		  value=2 : If Device can include the High Density Fibre Ports.
		  value=4 : If Device have a Direct Current (DC) Power Supply for
		            extreme temperature conditions.
		  value=8 : If Device is of the OptiSwitch_100FX Type
		            (fixed schema of the OptiSwitch_400 Device).
		  value=16: If Device is of the Cheap Modification.
		  value=32: If Device is of the Expensive Modification.
		  For example: If Device have a the both properties
		  (Redundant Power Supply & High Density Fiber Ports), value=3
		  will be responded on the GET SNMP command (etc...)."
		::= { nbDevGen 5 }
-- ykfix39 - 15.10.00 - end

-- ykfix37 -  1.05.00 - begin
nbsDevTemperatureMode   OBJECT-TYPE
		SYNTAX  INTEGER
		{
		 none          (1),
		 normal        (2),
		 high          (3)
		}

		ACCESS  read-only
		STATUS  mandatory
		DESCRIPTION
		"The Temperature Mode of Device."
		::= { nbDevGen 6 }
-- ykfix37 -  1.05.00 - end

-- ************************************************************
-- Objects in the Device's Power Supplies Group
-- ************************************************************
        
nbsDevPS		OBJECT IDENTIFIER ::= { nbDevGen 8 }

nbsDevPSNumber		OBJECT-TYPE
		SYNTAX  INTEGER 
		ACCESS  read-only
		STATUS  mandatory
		DESCRIPTION
		 "The number of Power Supplies in the corresponding Device.
		  Value = 0 says, that Power Supply Table is not supported."
		::= { nbsDevPS 1 }

nbsDevPSTable		OBJECT-TYPE
		SYNTAX  SEQUENCE OF NbsDevPSEntry
		ACCESS  not-accessible
		STATUS  mandatory
		DESCRIPTION
		 "This table shows all the Power Supplies modules,
		  existing in the corresponding Device."
		::= { nbsDevPS 2 }

nbsDevPSEntry		OBJECT-TYPE
		SYNTAX  NbsDevPSEntry
		ACCESS  not-accessible
		STATUS  mandatory
		DESCRIPTION
		 "The entries of the table."
		INDEX { nbsDevPSIndex }
		::= { nbsDevPSTable 1 }

NbsDevPSEntry ::= SEQUENCE
		{
		 nbsDevPSIndex		INTEGER,
		 nbsDevPSType		INTEGER,
		 nbsDevPSDescription	DisplayString,
		 nbsDevPSRedundantMode	INTEGER,
		 nbsDevPSOperStatus	INTEGER,
		 nbsDevPSAdminStatus	INTEGER
		}

nbsDevPSIndex		OBJECT-TYPE
		SYNTAX  INTEGER
		ACCESS  read-only
		STATUS  mandatory
		DESCRIPTION
		 "The index of the table,
		  (MAX Value is equal to nbsDevPSNumber)."
		::= { nbsDevPSEntry 1 }

nbsDevPSType		OBJECT-TYPE
		SYNTAX  INTEGER
		{
		 none	(1),
		 acPS	(2),
		 dcPS	(3)
		}
		ACCESS  read-only
		STATUS  mandatory
		DESCRIPTION
		 "The physical Type of the Power Supply.
		  acPS (2) - alternating current PS,
		  dcPS (3) - dirrect     current PS."
		::= { nbsDevPSEntry 2 }

nbsDevPSDescription	OBJECT-TYPE
		SYNTAX  DisplayString
		ACCESS  read-only
		STATUS  mandatory
		DESCRIPTION
		 "The Text Decription of the Power Supply."
		::= { nbsDevPSEntry 3 }

nbsDevPSRedundantMode	OBJECT-TYPE
		SYNTAX  INTEGER
		{
		 none		(1),
		 mainPS		(2),
		 secondaryPS	(3)
		}
		ACCESS  read-only
		STATUS  mandatory
		DESCRIPTION
		 "The working mode of the Power Supply."
		::= { nbsDevPSEntry 4 }
		
nbsDevPSOperStatus	OBJECT-TYPE
		SYNTAX  INTEGER
		{
		 none		(1),
		 active         (2),
		 notActive	(3)
		}
		ACCESS  read-only
		STATUS  mandatory
		DESCRIPTION
		 "The Oper status of the Power Supply."
		::= { nbsDevPSEntry 5 }
		
nbsDevPSAdminStatus	OBJECT-TYPE
		SYNTAX  INTEGER
		{
		 none           (1),
		 active		(2),
		 notActive	(3)
		}
		ACCESS  read-write
		STATUS  mandatory
		DESCRIPTION
		 "The Admin status of the Power Supply."
		::= { nbsDevPSEntry 6 }

-- ************************************************************
-- Objects in the Device's Power Supplies Inputs Group
-- ************************************************************
nbsDevPSInput		OBJECT IDENTIFIER ::= { nbDevGen 9 }

nbsDevPSInputNumber		OBJECT-TYPE
		SYNTAX  INTEGER 
		ACCESS  read-only
		STATUS  mandatory
		DESCRIPTION
		 "The number of Power Suppliy Inputs in the corresponding Device.
		  Value = 0 says, that Power Supply Inputs Table is not supported."
		::= { nbsDevPSInput 1 }

nbsDevPSInputTable		OBJECT-TYPE
		SYNTAX  SEQUENCE OF NbsDevPSInputEntry
		ACCESS  not-accessible
		STATUS  mandatory
		DESCRIPTION
		 "This table shows all the Power Supply Inputs,
		  existing in the corresponding Device."
		::= { nbsDevPSInput 2 }

nbsDevPSInputEntry		OBJECT-TYPE
		SYNTAX  NbsDevPSInputEntry
		ACCESS  not-accessible
		STATUS  mandatory
		DESCRIPTION
		 "The entries of the table."
		INDEX { nbsDevPSInputIndex }
		::= { nbsDevPSInputTable 1 }

NbsDevPSInputEntry ::= SEQUENCE
		{
		 nbsDevPSInputIndex		INTEGER,
		 nbsDevPSInputType		INTEGER,
		 nbsDevPSInputDescription	DisplayString,
		 nbsDevPSInputRedundantMode	INTEGER,
		 nbsDevPSInputOperStatus	INTEGER,
		 nbsDevPSInputAdminStatus	INTEGER
		}

nbsDevPSInputIndex		OBJECT-TYPE
		SYNTAX  INTEGER
		ACCESS  read-only
		STATUS  mandatory
		DESCRIPTION
		 "The index of the table,
		  (MAX Value is equal to nbsDevPSInputNumber)."
		::= { nbsDevPSInputEntry 1 }

nbsDevPSInputType		OBJECT-TYPE
		SYNTAX  INTEGER
		{
		 none		(1),
		 acInput	(2),
		 dcInput	(3),
		 dcRedundInput	(4)
		}
		ACCESS  read-only
		STATUS  mandatory
		DESCRIPTION
		 "The physical Type of the Power Supply.
		  acInput       (2) - alternating current input,
		  dcInput       (3) - direct current input,
		  dcRedundInput	(4) - direct current Redundant input."
		::= { nbsDevPSInputEntry 2 }

nbsDevPSInputDescription	OBJECT-TYPE
		SYNTAX  DisplayString
		ACCESS  read-only
		STATUS  mandatory
		DESCRIPTION
		 "The Text Decription of the Power Supply Input."
		::= { nbsDevPSInputEntry 3 }

nbsDevPSInputRedundantMode	OBJECT-TYPE
		SYNTAX  INTEGER
		{
		 none		(1),
		 mainInput	(2),
		 secondaryInput	(3)
		}
		ACCESS  read-only
		STATUS  mandatory
		DESCRIPTION
		 "The Redundant mode of the Power Supply Input."
		::= { nbsDevPSInputEntry 4 }
		
nbsDevPSInputOperStatus	OBJECT-TYPE
		SYNTAX  INTEGER
		{
		 none		(1),
		 active		(2),
		 notActive	(3)
		}
		ACCESS  read-only
		STATUS  mandatory
		DESCRIPTION
		 "The Oper status of the Power Supply Input."
		::= { nbsDevPSInputEntry 5 }
		
nbsDevPSInputAdminStatus	OBJECT-TYPE
		SYNTAX  INTEGER
		{
		 none		(1),
		 active		(2),
		 notActive	(3)
		}
		ACCESS  read-write
		STATUS  mandatory
		DESCRIPTION
		 "The Admin status of the Power Supply Input."
		::= { nbsDevPSInputEntry 6 }

-- ************************************************************
-- Objects in the Device's CPU Group
-- ************************************************************
        
nbsDevCPU		OBJECT IDENTIFIER ::= { nbDevGen 10 }

nbsDevCPUNumber		OBJECT-TYPE
		SYNTAX  INTEGER 
		ACCESS  read-only
		STATUS  mandatory
		DESCRIPTION
		 "The number of CPU cards in the corresponding Device.
		  Value = 0 says, that CPU Table is not supported."
		::= { nbsDevCPU 1 }

nbsDevCPUTable		OBJECT-TYPE
		SYNTAX  SEQUENCE OF NbsDevCPUEntry
		ACCESS  not-accessible
		STATUS  mandatory
		DESCRIPTION
		 "This table shows all the CPU modules,
		  existing in the corresponding Device."
		::= { nbsDevCPU 2 }

nbsDevCPUEntry		OBJECT-TYPE
		SYNTAX  NbsDevCPUEntry
		ACCESS  not-accessible
		STATUS  mandatory
		DESCRIPTION
		 "The entries of the table."
		INDEX { nbsDevCPUIndex }
		::= { nbsDevCPUTable 1 }

NbsDevCPUEntry ::= SEQUENCE
		{
		 nbsDevCPUIndex		INTEGER,
		 nbsDevCPUType		INTEGER,
		 nbsDevCPUDescription	DisplayString,
		 nbsDevCPURedundantMode	INTEGER,
		 nbsDevCPUOperStatus	INTEGER,
		 nbsDevCPUAdminStatus	INTEGER,      -- ykfix37 -  1.05.00
		 nbsDevCPUOrderNumber	INTEGER       -- ykfix37 -  1.05.00
		}

nbsDevCPUIndex		OBJECT-TYPE
		SYNTAX  INTEGER
		ACCESS  read-only
		STATUS  mandatory
		DESCRIPTION
		 "The index of the table,
		  (MAX Value is equal to nbsDevCPUNumber)."
		::= { nbsDevCPUEntry 1 }

nbsDevCPUType		OBJECT-TYPE
		SYNTAX  INTEGER
		{
		 none		(1),
		 cx33CPU	(2)
		}
		ACCESS  read-only
		STATUS  mandatory
		DESCRIPTION
		 "The physical Type of the CPU.
		  cx33CPU (2) - CPU CX with 33Mhz clock."
		::= { nbsDevCPUEntry 2 }

nbsDevCPUDescription	OBJECT-TYPE
		SYNTAX  DisplayString
		ACCESS  read-only
		STATUS  mandatory
		DESCRIPTION
		 "The Text Decription of the CPU card."
		::= { nbsDevCPUEntry 3 }

nbsDevCPURedundantMode	OBJECT-TYPE
		SYNTAX  INTEGER
		{
		 none		(1),
		 mainCPU	(2),
		 redundantCPU	(3)
		}
		ACCESS  read-only
		STATUS  mandatory
		DESCRIPTION
		 "The Redundant mode of the CPU card."
		::= { nbsDevCPUEntry 4 }
		
nbsDevCPUOperStatus	OBJECT-TYPE
		SYNTAX  INTEGER
		{
		 none           (1),
		 enabled	(2),
		 disabled	(3)
		}
		ACCESS  read-only
		STATUS  mandatory
		DESCRIPTION
		 "The Oper status of the CPU card."
		::= { nbsDevCPUEntry 5 }
		
nbsDevCPUAdminStatus	OBJECT-TYPE
		SYNTAX  INTEGER
		{
		 none           (1),
		 enable		(2),
		 disable	(3)
		}
		ACCESS  read-write
		STATUS  mandatory
		DESCRIPTION
		 "The Admin status of the CPU card."
		::= { nbsDevCPUEntry 6 }

-- ykfix37 -  1.05.00 - begin
nbsDevCPUOrderNumber	OBJECT-TYPE
		SYNTAX  INTEGER
		ACCESS  read-only
		STATUS  mandatory
		DESCRIPTION
		 "The order number of the CPU card."
		::= { nbsDevCPUEntry 7 }
		
-- ************************************************************
-- Objects in the Device's FAN Group
-- ************************************************************
        
nbsDevFAN		OBJECT IDENTIFIER ::= { nbDevGen 11 }

nbsDevFANsNumber	OBJECT-TYPE
		SYNTAX  INTEGER 
		ACCESS  read-only
		STATUS  mandatory
		DESCRIPTION
		 "The number of FAN cards in the corresponding Device.
		  Value = 0 says, that FAN Table is not supported."
		::= { nbsDevFAN 1 }

nbsDevFANTable		OBJECT-TYPE
		SYNTAX  SEQUENCE OF NbsDevFANEntry
		ACCESS  not-accessible
		STATUS  mandatory
		DESCRIPTION
		 "This table shows all the FAN modules,
		  existing in the corresponding Device."
		::= { nbsDevFAN 2 }

nbsDevFANEntry		OBJECT-TYPE
		SYNTAX  NbsDevFANEntry
		ACCESS  not-accessible
		STATUS  mandatory
		DESCRIPTION
		 "The entries of the table."
		INDEX { nbsDevFANIndex }
		::= { nbsDevFANTable 1 }

NbsDevFANEntry ::= SEQUENCE
		{
		 nbsDevFANIndex		INTEGER,
		 nbsDevFANType		INTEGER,
		 nbsDevFANDescription	DisplayString,
		 nbsDevFANOperStatus	INTEGER,
		 nbsDevFANAdminStatus	INTEGER
		}

nbsDevFANIndex		OBJECT-TYPE
		SYNTAX  INTEGER
		ACCESS  read-only
		STATUS  mandatory
		DESCRIPTION
		 "The index of the table,
		  (MAX Value is equal to nbsDevFANsNumber)."
		::= { nbsDevFANEntry 1 }

nbsDevFANType		OBJECT-TYPE
		SYNTAX  INTEGER
		{
		 none		(1)
		}
		ACCESS  read-only
		STATUS  mandatory
		DESCRIPTION
		 "The physical Type of the FAN."
		::= { nbsDevFANEntry 2 }

nbsDevFANDescription	OBJECT-TYPE
		SYNTAX  DisplayString
		ACCESS  read-only
		STATUS  mandatory
		DESCRIPTION
		 "The Text Decription of the FAN card."
		::= { nbsDevFANEntry 3 }

nbsDevFANOperStatus	OBJECT-TYPE
		SYNTAX  INTEGER
		{
		 none           (1),
		 active		(2),
		 notActive	(3)
		}
		ACCESS  read-only
		STATUS  mandatory
		DESCRIPTION
		 "The Oper status of the FAN card."
		::= { nbsDevFANEntry 5 }
		
nbsDevFANAdminStatus	OBJECT-TYPE
		SYNTAX  INTEGER
		{
		 none           (1),
		 active		(2),
		 notActive	(3)
		}
		ACCESS  read-write
		STATUS  mandatory
		DESCRIPTION
		 "The Admin status of the FAN card."
		::= { nbsDevFANEntry 6 }
-- ykfix37 -  1.05.00 - end

END
