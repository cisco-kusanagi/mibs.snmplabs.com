--
-- This SMIv2 module has been generated by smidump 0.2-cvs. Do not edit.
--

SONUS-SS7-SERVICES-MIB DEFINITIONS ::= BEGIN

IMPORTS
    Integer32, IpAddress, MODULE-IDENTITY, NOTIFICATION-TYPE, 
    OBJECT-TYPE
        FROM SNMPv2-SMI
    DisplayString, RowStatus, TEXTUAL-CONVENTION
        FROM SNMPv2-TC
    sonusEventClass, sonusEventDescription, sonusEventLevel
        FROM SONUS-COMMON-MIB
    sonusServicesMIBs
        FROM SONUS-SMI
    PointCode, SonusName, SonusPointCode, SonusPointCodeFormat
        FROM SONUS-TC;

sonusSs7ServicesMIB MODULE-IDENTITY
    LAST-UPDATED    "200107310000Z"
    ORGANIZATION    
            "Sonus Networks, Inc."
    CONTACT-INFO    
            "   Customer Support    
             Sonus Networks, Inc,
             5 carlisle Road
             Westford, MA 01886
             USA
             
             Tel: 978-692-8999
             Fax: 978-392-9118
             E-mail: cs.snmp@sonusnet.com"
    DESCRIPTION     
            "The MIB Module for SS7 Gateway and SS7 Node Configuration."
    ::= { sonusServicesMIBs 3 }


SonusSs7GatewayLinkSelection ::= TEXTUAL-CONVENTION
    STATUS          current
    DESCRIPTION     
            "The SS7 Gateway link selection value."
    SYNTAX          INTEGER { primary(1), secondary(2), none(3), 
                        primaryAlt(4), secondaryAlt(5) }

sonusSs7ServicesMIBObjects OBJECT IDENTIFIER
    ::= { sonusSs7ServicesMIB 1 }

sonusSs7Gateway OBJECT IDENTIFIER
    ::= { sonusSs7ServicesMIBObjects 1 }

sonusSs7GatewayNextIndex OBJECT-TYPE
    SYNTAX          Integer32
    MAX-ACCESS      read-only
    STATUS          current
    DESCRIPTION     
            "The next valid index to use when creating an entry in
             the sonusSs7GatewayTable."
    ::= { sonusSs7Gateway 1 }

sonusSs7GatewayTable OBJECT-TYPE
    SYNTAX          SEQUENCE OF SonusSs7GatewayEntry
    MAX-ACCESS      not-accessible
    STATUS          current
    DESCRIPTION     
            "This table specifies the SS7 Gateway list for the GSX9000 node."
    ::= { sonusSs7Gateway 2 }

sonusSs7GatewayEntry OBJECT-TYPE
    SYNTAX          SonusSs7GatewayEntry
    MAX-ACCESS      not-accessible
    STATUS          current
    DESCRIPTION     
            ""
    INDEX           { sonusSs7GatewayIndex }
    ::= { sonusSs7GatewayTable 1 }

SonusSs7GatewayEntry ::=
    SEQUENCE {
        sonusSs7GatewayIndex            Integer32,
        sonusSs7GatewayState            INTEGER,
        sonusSs7GatewayName             SonusName,
        sonusSs7GatewaySocketType       INTEGER,
        sonusSs7GatewayActiveHost       INTEGER,
        sonusSs7GatewayPriHostName      DisplayString,
        sonusSs7GatewayPriHostIpaddr    IpAddress,
        sonusSs7GatewayPriHostMode      INTEGER,
        sonusSs7GatewayPriHostOosDelayTimer   Integer32,
        sonusSs7GatewaySecHostName      DisplayString,
        sonusSs7GatewaySecHostIpaddr    IpAddress,
        sonusSs7GatewaySecHostMode      INTEGER,
        sonusSs7GatewaySecHostOosDelayTimer   Integer32,
        sonusSs7GatewayRowStatus        RowStatus,
        sonusSs7GatewayPriAltHostIpaddr IpAddress,
        sonusSs7GatewaySecAltHostIpaddr IpAddress,
        sonusSs7GatewayGwType           INTEGER,
        sonusSs7GatewayServerTcpPort    Integer32,
        sonusSs7GatewayClientTcpPort    Integer32,
        sonusSs7GatewayPriTaliTrafficControl    INTEGER,
        sonusSs7GatewayPriAltTaliTrafficControl       INTEGER,
        sonusSs7GatewaySecTaliTrafficControl    INTEGER,
        sonusSs7GatewaySecAltTaliTrafficControl       INTEGER,
        sonusSs7GatewayTimerTaliT1      Integer32,
        sonusSs7GatewayTimerTaliT2      Integer32,
        sonusSs7GatewayTimerTaliT3      Integer32,
        sonusSs7GatewayTimerTaliT4      Integer32,
        sonusSs7GatewayTaliSs7Type      INTEGER,
        sonusSs7GatewaySlsBits          Integer32,
        sonusSs7GatewayTaliIsupNormalization    INTEGER,
        sonusSs7GatewayTaliPstnPresentation   INTEGER,
        sonusSs7GatewayTaliGroupCode    DisplayString
    }

sonusSs7GatewayIndex OBJECT-TYPE
    SYNTAX          Integer32
    MAX-ACCESS      read-only
    STATUS          current
    DESCRIPTION     
            "Identifies the target SS7 Gateway entry."
    ::= { sonusSs7GatewayEntry 1 }

sonusSs7GatewayState OBJECT-TYPE
    SYNTAX          INTEGER { disabled(1), enabled(2) }
    MAX-ACCESS      read-write
    STATUS          current
    DESCRIPTION     
            "The administrative state of this SS7 Gateway entry."
    DEFVAL          { disabled }
    ::= { sonusSs7GatewayEntry 2 }

sonusSs7GatewayName OBJECT-TYPE
    SYNTAX          SonusName
    MAX-ACCESS      read-write
    STATUS          current
    DESCRIPTION     
            "The name of this SS7 Gateway instance."
    ::= { sonusSs7GatewayEntry 3 }

sonusSs7GatewaySocketType OBJECT-TYPE
    SYNTAX          INTEGER { tcp(1) }
    MAX-ACCESS      read-write
    STATUS          current
    DESCRIPTION     
            "Indicates the type of socket interface used by the GSX9000 node for
             connections to the SS7 Gateway platform."
    DEFVAL          { tcp }
    ::= { sonusSs7GatewayEntry 4 }

sonusSs7GatewayActiveHost OBJECT-TYPE
    SYNTAX          INTEGER { primary(1), secondary(2), none(3) }
    MAX-ACCESS      read-only
    STATUS          deprecated
    DESCRIPTION     
            "This status value has been replaced by sonusSs7GatewayNextHost and
             sonusSs7GatewaySelectHost."
    ::= { sonusSs7GatewayEntry 5 }

sonusSs7GatewayPriHostName OBJECT-TYPE
    SYNTAX          DisplayString (SIZE(1..39))
    MAX-ACCESS      read-write
    STATUS          current
    DESCRIPTION     
            "The host name of the primary link to the SS7 Gateway platform."
    ::= { sonusSs7GatewayEntry 6 }

sonusSs7GatewayPriHostIpaddr OBJECT-TYPE
    SYNTAX          IpAddress
    MAX-ACCESS      read-write
    STATUS          current
    DESCRIPTION     
            "Specifies the IP Address of the primary link to the SS7 Gateway platform."
    ::= { sonusSs7GatewayEntry 7 }

sonusSs7GatewayPriHostMode OBJECT-TYPE
    SYNTAX          INTEGER { inService(1), outOfService(2) }
    MAX-ACCESS      read-write
    STATUS          current
    DESCRIPTION     
            "Specifies the service mode of the primary link to the SS7 Gateway platform."
    DEFVAL          { outOfService }
    ::= { sonusSs7GatewayEntry 8 }

sonusSs7GatewayPriHostOosDelayTimer OBJECT-TYPE
    SYNTAX          Integer32 (0..1440)
    MAX-ACCESS      read-write
    STATUS          current
    DESCRIPTION     
            "This element is used to delay the action of taking the primary host link out of
             service for a specified number of minutes."
    DEFVAL          { 0 }
    ::= { sonusSs7GatewayEntry 9 }

sonusSs7GatewaySecHostName OBJECT-TYPE
    SYNTAX          DisplayString (SIZE(1..39))
    MAX-ACCESS      read-write
    STATUS          current
    DESCRIPTION     
            "The host name of the secondary link to the SS7 Gateway platform."
    ::= { sonusSs7GatewayEntry 10 }

sonusSs7GatewaySecHostIpaddr OBJECT-TYPE
    SYNTAX          IpAddress
    MAX-ACCESS      read-write
    STATUS          current
    DESCRIPTION     
            "Specifies the IP Address of the secondary link to the SS7 Gateway platform."
    ::= { sonusSs7GatewayEntry 11 }

sonusSs7GatewaySecHostMode OBJECT-TYPE
    SYNTAX          INTEGER { inService(1), outOfService(2) }
    MAX-ACCESS      read-write
    STATUS          current
    DESCRIPTION     
            "Specifies the service mode of the secondary link to the SS7 Gateway platform."
    DEFVAL          { outOfService }
    ::= { sonusSs7GatewayEntry 12 }

sonusSs7GatewaySecHostOosDelayTimer OBJECT-TYPE
    SYNTAX          Integer32 (0..1440)
    MAX-ACCESS      read-write
    STATUS          current
    DESCRIPTION     
            "This element is used to delay the action of taking the secondary host link out of
             service for a specified number of minutes."
    DEFVAL          { 0 }
    ::= { sonusSs7GatewayEntry 13 }

sonusSs7GatewayRowStatus OBJECT-TYPE
    SYNTAX          RowStatus
    MAX-ACCESS      read-write
    STATUS          current
    DESCRIPTION     
            ""
    ::= { sonusSs7GatewayEntry 14 }

sonusSs7GatewayPriAltHostIpaddr OBJECT-TYPE
    SYNTAX          IpAddress
    MAX-ACCESS      read-write
    STATUS          current
    DESCRIPTION     
            "Specifies the alternate IP Address of the primary link to the SS7 Gateway platform."
    ::= { sonusSs7GatewayEntry 15 }

sonusSs7GatewaySecAltHostIpaddr OBJECT-TYPE
    SYNTAX          IpAddress
    MAX-ACCESS      read-write
    STATUS          current
    DESCRIPTION     
            "Specifies the alternate IP Address of the secondary link to the SS7 Gateway platform."
    ::= { sonusSs7GatewayEntry 16 }

sonusSs7GatewayGwType OBJECT-TYPE
    SYNTAX          INTEGER { tali(1), dgms(2) }
    MAX-ACCESS      read-write
    STATUS          current
    DESCRIPTION     
            "Gateway type is identified by the gateway protocol it uses"
    DEFVAL          { dgms }
    ::= { sonusSs7GatewayEntry 17 }

sonusSs7GatewayServerTcpPort OBJECT-TYPE
    SYNTAX          Integer32 (1024..65535)
    MAX-ACCESS      read-write
    STATUS          current
    DESCRIPTION     
            "TCP port for the server of TALI connection"
    ::= { sonusSs7GatewayEntry 18 }

sonusSs7GatewayClientTcpPort OBJECT-TYPE
    SYNTAX          Integer32 (1024..65535)
    MAX-ACCESS      read-write
    STATUS          current
    DESCRIPTION     
            "TCP port for the client of TALI connection"
    ::= { sonusSs7GatewayEntry 19 }

sonusSs7GatewayPriTaliTrafficControl OBJECT-TYPE
    SYNTAX          INTEGER { allow(1), prohibit(2) }
    MAX-ACCESS      read-write
    STATUS          current
    DESCRIPTION     
            "Control the ss7 traffic on the primary TALI connection"
    DEFVAL          { allow }
    ::= { sonusSs7GatewayEntry 20 }

sonusSs7GatewayPriAltTaliTrafficControl OBJECT-TYPE
    SYNTAX          INTEGER { allow(1), prohibit(2) }
    MAX-ACCESS      read-write
    STATUS          current
    DESCRIPTION     
            "Control the ss7 traffic on the primary TALI connection"
    DEFVAL          { allow }
    ::= { sonusSs7GatewayEntry 21 }

sonusSs7GatewaySecTaliTrafficControl OBJECT-TYPE
    SYNTAX          INTEGER { allow(1), prohibit(2) }
    MAX-ACCESS      read-write
    STATUS          current
    DESCRIPTION     
            "Control the ss7 traffic on the secondary TALI connection"
    DEFVAL          { allow }
    ::= { sonusSs7GatewayEntry 22 }

sonusSs7GatewaySecAltTaliTrafficControl OBJECT-TYPE
    SYNTAX          INTEGER { allow(1), prohibit(2) }
    MAX-ACCESS      read-write
    STATUS          current
    DESCRIPTION     
            "Control the ss7 traffic on the secondary TALI connection"
    DEFVAL          { allow }
    ::= { sonusSs7GatewayEntry 23 }

sonusSs7GatewayTimerTaliT1 OBJECT-TYPE
    SYNTAX          Integer32 (100..60000)
    MAX-ACCESS      read-write
    STATUS          current
    DESCRIPTION     
            "Send a TALI-TEST upon the expiry of T1 in millisecond."
    DEFVAL          { 4000 }
    ::= { sonusSs7GatewayEntry 24 }

sonusSs7GatewayTimerTaliT2 OBJECT-TYPE
    SYNTAX          Integer32 (100..60000)
    MAX-ACCESS      read-write
    STATUS          current
    DESCRIPTION     
            "Guard timer in millisecond for the return of TALI-ALLO or 
             TALI-PROH in response to a TALI-TEST sent earlier."
    DEFVAL          { 3000 }
    ::= { sonusSs7GatewayEntry 25 }

sonusSs7GatewayTimerTaliT3 OBJECT-TYPE
    SYNTAX          Integer32 (100..60000)
    MAX-ACCESS      read-write
    STATUS          current
    DESCRIPTION     
            "T3 in millisecond reprsents how long the near end can continue
             to process received messages after sending TALI-PROH."
    DEFVAL          { 5000 }
    ::= { sonusSs7GatewayEntry 26 }

sonusSs7GatewayTimerTaliT4 OBJECT-TYPE
    SYNTAX          Integer32 (100..60000)
    MAX-ACCESS      read-write
    STATUS          current
    DESCRIPTION     
            "Send a TALI-MONI upon the expiry of T4 in millisecond."
    DEFVAL          { 10000 }
    ::= { sonusSs7GatewayEntry 27 }

sonusSs7GatewayTaliSs7Type OBJECT-TYPE
    SYNTAX          INTEGER { ansi(1), ituIntl(2), ituNatl(3) }
    MAX-ACCESS      read-write
    STATUS          current
    DESCRIPTION     
            "SS7 protocol types used over TALI"
    DEFVAL          { ansi }
    ::= { sonusSs7GatewayEntry 28 }

sonusSs7GatewaySlsBits OBJECT-TYPE
    SYNTAX          Integer32 (4..8)
    MAX-ACCESS      read-write
    STATUS          current
    DESCRIPTION     
            "The number of SLS bits to use"
    DEFVAL          { 5 }
    ::= { sonusSs7GatewayEntry 29 }

sonusSs7GatewayTaliIsupNormalization OBJECT-TYPE
    SYNTAX          INTEGER { norm(1), raw(2) }
    MAX-ACCESS      read-write
    STATUS          current
    DESCRIPTION     
            "ISUP message format over TALI -- normalized or raw"
    DEFVAL          { norm }
    ::= { sonusSs7GatewayEntry 30 }

sonusSs7GatewayTaliPstnPresentation OBJECT-TYPE
    SYNTAX          INTEGER { q767(1), etsiIsup(2), ukIsup(3), grIsup(4) }
    MAX-ACCESS      read-write
    STATUS          current
    DESCRIPTION     
            "ISUP types over TALI"
    DEFVAL          { etsiIsup }
    ::= { sonusSs7GatewayEntry 31 }

sonusSs7GatewayTaliGroupCode OBJECT-TYPE
    SYNTAX          DisplayString (SIZE(2))
    MAX-ACCESS      read-write
    STATUS          current
    DESCRIPTION     
            "Group Code in ASCII"
    DEFVAL          { "aa" }
    ::= { sonusSs7GatewayEntry 32 }

sonusSs7GatewayStatusTable OBJECT-TYPE
    SYNTAX          SEQUENCE OF SonusSs7GatewayStatusEntry
    MAX-ACCESS      not-accessible
    STATUS          current
    DESCRIPTION     
            "Status Table of the SS7 Gateway for the GSX9000 node."
    ::= { sonusSs7Gateway 3 }

sonusSs7GatewayStatusEntry OBJECT-TYPE
    SYNTAX          SonusSs7GatewayStatusEntry
    MAX-ACCESS      not-accessible
    STATUS          current
    DESCRIPTION     
            "List of SS7 Gateway status elements."
    INDEX           { sonusSs7GatewayStatusIndex }
    ::= { sonusSs7GatewayStatusTable 1 }

SonusSs7GatewayStatusEntry ::=
    SEQUENCE {
        sonusSs7GatewayStatusIndex      Integer32,
        sonusSs7GatewayNextHost         SonusSs7GatewayLinkSelection,
        sonusSs7GatewaySelectHost       SonusSs7GatewayLinkSelection,
        sonusSs7GatewayPriTaliConnState INTEGER,
        sonusSs7GatewaySecTaliConnState INTEGER,
        sonusSs7GatewayPriAltTaliConnState  INTEGER,
        sonusSs7GatewaySecAltTaliConnState  INTEGER,
        sonusSs7GatewayPriNearEndTaliVersion    DisplayString,
        sonusSs7GatewayPriFarEndTaliVersion   DisplayString,
        sonusSs7GatewayPriAltNearEndTaliVersion       DisplayString,
        sonusSs7GatewayPriAltFarEndTaliVersion      DisplayString,
        sonusSs7GatewaySecNearEndTaliVersion    DisplayString,
        sonusSs7GatewaySecFarEndTaliVersion   DisplayString,
        sonusSs7GatewaySecAltNearEndTaliVersion       DisplayString,
        sonusSs7GatewaySecAltFarEndTaliVersion      DisplayString
    }

sonusSs7GatewayStatusIndex OBJECT-TYPE
    SYNTAX          Integer32
    MAX-ACCESS      read-only
    STATUS          current
    DESCRIPTION     
            "Identifies the SS7 Gateway status entry."
    ::= { sonusSs7GatewayStatusEntry 1 }

sonusSs7GatewayNextHost OBJECT-TYPE
    SYNTAX          SonusSs7GatewayLinkSelection
    MAX-ACCESS      read-only
    STATUS          current
    DESCRIPTION     
            "Indicates which host link connection to the SS7 Gateway is next to be
             selected. If there is none, then this element is set to none."
    DEFVAL          { none }
    ::= { sonusSs7GatewayStatusEntry 2 }

sonusSs7GatewaySelectHost OBJECT-TYPE
    SYNTAX          SonusSs7GatewayLinkSelection
    MAX-ACCESS      read-only
    STATUS          current
    DESCRIPTION     
            "Indicates which host link connection to the SS7 Gateway is selected
             to be tried. If there is none, then this element is set to none."
    DEFVAL          { none }
    ::= { sonusSs7GatewayStatusEntry 3 }

sonusSs7GatewayPriTaliConnState OBJECT-TYPE
    SYNTAX          INTEGER { oos(1), connecting(2), nepFep(3), 
                        nepFea(4), neaFep(5), neaFea(6) }
    MAX-ACCESS      read-only
    STATUS          current
    DESCRIPTION     
            "TALI state of the primary connection for this SS7 gateway."
    DEFVAL          { oos }
    ::= { sonusSs7GatewayStatusEntry 4 }

sonusSs7GatewaySecTaliConnState OBJECT-TYPE
    SYNTAX          INTEGER { oos(1), connecting(2), nepFep(3), 
                        nepFea(4), neaFep(5), neaFea(6) }
    MAX-ACCESS      read-only
    STATUS          current
    DESCRIPTION     
            "TALI state of the secondary connection for this SS7 gateway."
    DEFVAL          { oos }
    ::= { sonusSs7GatewayStatusEntry 5 }

sonusSs7GatewayPriAltTaliConnState OBJECT-TYPE
    SYNTAX          INTEGER { oos(1), connecting(2), nepFep(3), 
                        nepFea(4), neaFep(5), neaFea(6) }
    MAX-ACCESS      read-only
    STATUS          current
    DESCRIPTION     
            "TALI state of the primary alt connection for this SS7 gateway."
    DEFVAL          { oos }
    ::= { sonusSs7GatewayStatusEntry 6 }

sonusSs7GatewaySecAltTaliConnState OBJECT-TYPE
    SYNTAX          INTEGER { oos(1), connecting(2), nepFep(3), 
                        nepFea(4), neaFep(5), neaFea(6) }
    MAX-ACCESS      read-only
    STATUS          current
    DESCRIPTION     
            "TALI state of the secondary alt connection for this SS7 gateway."
    DEFVAL          { oos }
    ::= { sonusSs7GatewayStatusEntry 7 }

sonusSs7GatewayPriNearEndTaliVersion OBJECT-TYPE
    SYNTAX          DisplayString (SIZE(7))
    MAX-ACCESS      read-only
    STATUS          current
    DESCRIPTION     
            "TALI protocol version at the near end of the pri conncection"
    DEFVAL          { "001.000" }
    ::= { sonusSs7GatewayStatusEntry 8 }

sonusSs7GatewayPriFarEndTaliVersion OBJECT-TYPE
    SYNTAX          DisplayString (SIZE(7))
    MAX-ACCESS      read-only
    STATUS          current
    DESCRIPTION     
            "TALI protocol version at the far end of the pri connection"
    DEFVAL          { "001.000" }
    ::= { sonusSs7GatewayStatusEntry 9 }

sonusSs7GatewayPriAltNearEndTaliVersion OBJECT-TYPE
    SYNTAX          DisplayString (SIZE(7))
    MAX-ACCESS      read-only
    STATUS          current
    DESCRIPTION     
            "TALI protocol version at the near end of the pri-alt conn."
    DEFVAL          { "001.000" }
    ::= { sonusSs7GatewayStatusEntry 10 }

sonusSs7GatewayPriAltFarEndTaliVersion OBJECT-TYPE
    SYNTAX          DisplayString (SIZE(7))
    MAX-ACCESS      read-only
    STATUS          current
    DESCRIPTION     
            "TALI protocol version at the far end of the pri-alt connection"
    DEFVAL          { "001.000" }
    ::= { sonusSs7GatewayStatusEntry 11 }

sonusSs7GatewaySecNearEndTaliVersion OBJECT-TYPE
    SYNTAX          DisplayString (SIZE(7))
    MAX-ACCESS      read-only
    STATUS          current
    DESCRIPTION     
            "TALI protocol version at the near end of the sec conncection"
    DEFVAL          { "001.000" }
    ::= { sonusSs7GatewayStatusEntry 12 }

sonusSs7GatewaySecFarEndTaliVersion OBJECT-TYPE
    SYNTAX          DisplayString (SIZE(7))
    MAX-ACCESS      read-only
    STATUS          current
    DESCRIPTION     
            "TALI protocol version at the far end of the sec connection"
    DEFVAL          { "001.000" }
    ::= { sonusSs7GatewayStatusEntry 13 }

sonusSs7GatewaySecAltNearEndTaliVersion OBJECT-TYPE
    SYNTAX          DisplayString (SIZE(7))
    MAX-ACCESS      read-only
    STATUS          current
    DESCRIPTION     
            "TALI protocol version at the near end of the sec-alt conn."
    DEFVAL          { "001.000" }
    ::= { sonusSs7GatewayStatusEntry 14 }

sonusSs7GatewaySecAltFarEndTaliVersion OBJECT-TYPE
    SYNTAX          DisplayString (SIZE(7))
    MAX-ACCESS      read-only
    STATUS          current
    DESCRIPTION     
            "TALI protocol version at the far end of the sec-alt connection"
    DEFVAL          { "001.000" }
    ::= { sonusSs7GatewayStatusEntry 15 }

sonusSs7GatewayPSStatusTable OBJECT-TYPE
    SYNTAX          SEQUENCE OF SonusSs7GatewayPSStatusEntry
    MAX-ACCESS      not-accessible
    STATUS          current
    DESCRIPTION     
            "Status Table of the SS7 Gateway of a PRIMARY or SECONDARY for the
             GSX9000 node."
    ::= { sonusSs7Gateway 4 }

sonusSs7GatewayPSStatusEntry OBJECT-TYPE
    SYNTAX          SonusSs7GatewayPSStatusEntry
    MAX-ACCESS      not-accessible
    STATUS          current
    DESCRIPTION     
            "List of SS7 Gateway status elements."
    INDEX           { sonusSs7GatewayPSStatusIndex, 
                      sonusSs7GatewayPSStatusPSIndex }
    ::= { sonusSs7GatewayPSStatusTable 1 }

SonusSs7GatewayPSStatusEntry ::=
    SEQUENCE {
        sonusSs7GatewayPSStatusIndex    Integer32,
        sonusSs7GatewayPSStatusPSIndex  INTEGER,
        sonusSs7GatewayPSStatusPrimaryCE Integer32,
        sonusSs7GatewayPSStatusActiveLink Integer32
    }

sonusSs7GatewayPSStatusIndex OBJECT-TYPE
    SYNTAX          Integer32
    MAX-ACCESS      read-only
    STATUS          current
    DESCRIPTION     
            "Identifies the SS7 Gateway status entry."
    ::= { sonusSs7GatewayPSStatusEntry 1 }

sonusSs7GatewayPSStatusPSIndex OBJECT-TYPE
    SYNTAX          INTEGER { primary(0), secondary(1), primaryAlt(2), 
                        secondaryAlt(3) }
    MAX-ACCESS      read-only
    STATUS          current
    DESCRIPTION     
            "Identifies the SS7 Gateway link status entry."
    ::= { sonusSs7GatewayPSStatusEntry 2 }

sonusSs7GatewayPSStatusPrimaryCE OBJECT-TYPE
    SYNTAX          Integer32
    MAX-ACCESS      read-only
    STATUS          current
    DESCRIPTION     
            "Identifies the link Primary CE value."
    ::= { sonusSs7GatewayPSStatusEntry 3 }

sonusSs7GatewayPSStatusActiveLink OBJECT-TYPE
    SYNTAX          Integer32 (0..16)
    MAX-ACCESS      read-only
    STATUS          current
    DESCRIPTION     
            "Identifies the link active entry."
    ::= { sonusSs7GatewayPSStatusEntry 4 }

sonusSs7GatewayLinkStatusTable OBJECT-TYPE
    SYNTAX          SEQUENCE OF SonusSs7GatewayLinkStatusEntry
    MAX-ACCESS      not-accessible
    STATUS          current
    DESCRIPTION     
            "Link Status Table of a SS7 Gateway for the GSX9000 node."
    ::= { sonusSs7Gateway 5 }

sonusSs7GatewayLinkStatusEntry OBJECT-TYPE
    SYNTAX          SonusSs7GatewayLinkStatusEntry
    MAX-ACCESS      not-accessible
    STATUS          current
    DESCRIPTION     
            "List of SS7 Gateway Link Status elements."
    INDEX           { sonusSs7GatewayStatusLinkIndex, 
                      sonusSs7GatewayStatusLinkPSIndex, 
                      sonusSs7GatewayStatusLinkHostIndex }
    ::= { sonusSs7GatewayLinkStatusTable 1 }

SonusSs7GatewayLinkStatusEntry ::=
    SEQUENCE {
        sonusSs7GatewayStatusLinkIndex  Integer32,
        sonusSs7GatewayStatusLinkPSIndex INTEGER,
        sonusSs7GatewayStatusLinkHostIndex  Integer32,
        sonusSs7GatewayStatusHostName   DisplayString,
        sonusSs7GatewayStatusHostIpaddr IpAddress,
        sonusSs7GatewayStatusHostState  INTEGER,
        sonusSs7GatewayStatusHostCE     Integer32
    }

sonusSs7GatewayStatusLinkIndex OBJECT-TYPE
    SYNTAX          Integer32
    MAX-ACCESS      read-only
    STATUS          current
    DESCRIPTION     
            "Identifies the SS7 Gateway status link entry gateway index."
    ::= { sonusSs7GatewayLinkStatusEntry 1 }

sonusSs7GatewayStatusLinkPSIndex OBJECT-TYPE
    SYNTAX          INTEGER { primary(1), secondary(2), primaryAlt(3), 
                        secondaryAlt(4) }
    MAX-ACCESS      read-only
    STATUS          current
    DESCRIPTION     
            "Identifies the SS7 Gateway status link entry primary or secondary index."
    ::= { sonusSs7GatewayLinkStatusEntry 2 }

sonusSs7GatewayStatusLinkHostIndex OBJECT-TYPE
    SYNTAX          Integer32
    MAX-ACCESS      read-only
    STATUS          current
    DESCRIPTION     
            "Identifies the SS7 Gateway host status link entry index."
    ::= { sonusSs7GatewayLinkStatusEntry 3 }

sonusSs7GatewayStatusHostName OBJECT-TYPE
    SYNTAX          DisplayString (SIZE(1..39))
    MAX-ACCESS      read-only
    STATUS          current
    DESCRIPTION     
            "The host name of the Link link to the SS7 Gateway platform."
    ::= { sonusSs7GatewayLinkStatusEntry 4 }

sonusSs7GatewayStatusHostIpaddr OBJECT-TYPE
    SYNTAX          IpAddress
    MAX-ACCESS      read-only
    STATUS          current
    DESCRIPTION     
            "Specifies the IP Address of the link to the SS7 Gateway platform."
    ::= { sonusSs7GatewayLinkStatusEntry 5 }

sonusSs7GatewayStatusHostState OBJECT-TYPE
    SYNTAX          INTEGER { empty(1), init(2), available(3), broken(4) }
    MAX-ACCESS      read-only
    STATUS          current
    DESCRIPTION     
            "The state of host link to the SS7 Gateway platform."
    ::= { sonusSs7GatewayLinkStatusEntry 6 }

sonusSs7GatewayStatusHostCE OBJECT-TYPE
    SYNTAX          Integer32
    MAX-ACCESS      read-only
    STATUS          current
    DESCRIPTION     
            "The CE of host link to the SS7 Gateway platform."
    ::= { sonusSs7GatewayLinkStatusEntry 7 }

sonusSs7NodeStatusTable OBJECT-TYPE
    SYNTAX          SEQUENCE OF SonusSs7NodeStatusEntry
    MAX-ACCESS      not-accessible
    STATUS          current
    DESCRIPTION     
            "Status Table of the SS7 Node for the GSX9000 node."
    ::= { sonusSs7Gateway 6 }

sonusSs7NodeStatusEntry OBJECT-TYPE
    SYNTAX          SonusSs7NodeStatusEntry
    MAX-ACCESS      not-accessible
    STATUS          current
    DESCRIPTION     
            "List of SS7 Node status elements."
    INDEX           { sonusSs7NodeStatusIndex }
    ::= { sonusSs7NodeStatusTable 1 }

SonusSs7NodeStatusEntry ::=
    SEQUENCE {
        sonusSs7NodeStatusIndex         Integer32,
        sonusSs7NodeStatIsup            INTEGER,
        sonusSs7NodeStatMtp             INTEGER
    }

sonusSs7NodeStatusIndex OBJECT-TYPE
    SYNTAX          Integer32
    MAX-ACCESS      read-only
    STATUS          current
    DESCRIPTION     
            "Identifies the SS7 Node status entry."
    ::= { sonusSs7NodeStatusEntry 1 }

sonusSs7NodeStatIsup OBJECT-TYPE
    SYNTAX          INTEGER { offline(1), active(2), initializing(3), 
                        failed(4), disabled(5), congested(6) }
    MAX-ACCESS      read-only
    STATUS          current
    DESCRIPTION     
            "Specifies the operating status of the ISUP service within this SS7 Node."
    DEFVAL          { offline }
    ::= { sonusSs7NodeStatusEntry 2 }

sonusSs7NodeStatMtp OBJECT-TYPE
    SYNTAX          INTEGER { paused(1), resumed(2) }
    MAX-ACCESS      read-only
    STATUS          current
    DESCRIPTION     
            "Specifies the current MTP status for this SS7 Node."
    DEFVAL          { paused }
    ::= { sonusSs7NodeStatusEntry 3 }

sonusSs7Node OBJECT IDENTIFIER
    ::= { sonusSs7ServicesMIBObjects 2 }

sonusSs7NodeNextIndex OBJECT-TYPE
    SYNTAX          Integer32
    MAX-ACCESS      read-only
    STATUS          current
    DESCRIPTION     
            "The next valid index to use when creating an entry in
             the sonusSs7NodeTable."
    ::= { sonusSs7Node 1 }

sonusSs7NodeTable OBJECT-TYPE
    SYNTAX          SEQUENCE OF SonusSs7NodeEntry
    MAX-ACCESS      not-accessible
    STATUS          current
    DESCRIPTION     
            "This table specifies the SS7 Node list for the GSX9000 node."
    ::= { sonusSs7Node 2 }

sonusSs7NodeEntry OBJECT-TYPE
    SYNTAX          SonusSs7NodeEntry
    MAX-ACCESS      not-accessible
    STATUS          current
    DESCRIPTION     
            ""
    INDEX           { sonusSs7NodeIndex }
    ::= { sonusSs7NodeTable 1 }

SonusSs7NodeEntry ::=
    SEQUENCE {
        sonusSs7NodeIndex               Integer32,
        sonusSs7NodeState               INTEGER,
        sonusSs7NodeName                SonusName,
        sonusSs7NodePointCode           PointCode,
        sonusSs7NodeServices            INTEGER,
        sonusSs7NodeProtocol            INTEGER,
        sonusSs7NodeTcapSsn             Integer32,
        sonusSs7NodeIsupStatus          INTEGER,
        sonusSs7NodeTcapStatus          INTEGER,
        sonusSs7NodeMtpStatus           INTEGER,
        sonusSs7NodeGatewayAssignment   DisplayString,
        sonusSs7NodeNativePointCode     Integer32,
        sonusSs7NodeMode                INTEGER,
        sonusSs7NodeConnCntrl           INTEGER,
        sonusSs7NodeRowStatus           RowStatus,
        sonusSs7NodeStdPointCode        SonusPointCode,
        sonusSs7NodePointCodeSize       Integer32,
        sonusSs7NodePointCodeFormatType SonusPointCodeFormat,
        sonusSs7NodeServerProtocol      INTEGER,
        sonusSs7NodeHandShakeInterval   Integer32,
        sonusSs7NodeTimerT1             Integer32,
        sonusSs7NodeTimerT2             Integer32,
        sonusSs7NodeTimerT3             Integer32,
        sonusSs7NodeTimerT4             Integer32,
        sonusSs7NodeTimerT5             Integer32,
        sonusSs7NodeTimerT6             Integer32,
        sonusSs7NodeTimerT7             Integer32,
        sonusSs7NodeTimerT8             Integer32,
        sonusSs7NodeTimerT9             Integer32,
        sonusSs7NodeTimerT10            Integer32,
        sonusSs7NodeTimerT11            Integer32,
        sonusSs7NodeTimerT12            Integer32,
        sonusSs7NodeTimerT13            Integer32,
        sonusSs7NodeTimerT14            Integer32,
        sonusSs7NodeTimerT15            Integer32,
        sonusSs7NodeTimerT16            Integer32,
        sonusSs7NodeTimerT17            Integer32,
        sonusSs7NodeTimerT18            Integer32,
        sonusSs7NodeTimerT19            Integer32,
        sonusSs7NodeTimerT20            Integer32,
        sonusSs7NodeTimerT21            Integer32,
        sonusSs7NodeTimerT22            Integer32,
        sonusSs7NodeTimerT23            Integer32,
        sonusSs7NodeTimerT24            Integer32,
        sonusSs7NodeTimerT25            Integer32,
        sonusSs7NodeTimerT26            Integer32,
        sonusSs7NodeTimerT27            Integer32,
        sonusSs7NodeTimerT28            Integer32,
        sonusSs7NodeTimerT29            Integer32,
        sonusSs7NodeTimerT30            Integer32,
        sonusSs7NodeTimerT31            Integer32,
        sonusSs7NodeTimerT32            Integer32,
        sonusSs7NodeTimerT33            Integer32,
        sonusSs7NodeTimerT34            Integer32,
        sonusSs7NodeTimerT35            Integer32,
        sonusSs7NodeTimerT36            Integer32,
        sonusSs7NodeTimerT37            Integer32,
        sonusSs7NodeTimerT38            Integer32,
        sonusSs7NodeTimerT39            Integer32,
        sonusSs7NodeTimerT40            Integer32,
        sonusSs7NodeTimerTAcc           Integer32,
        sonusSs7NodeTimerTCcr           Integer32,
        sonusSs7NodeTimerTCcrr          Integer32,
        sonusSs7NodeTimerTCgb           Integer32,
        sonusSs7NodeTimerTCra           Integer32,
        sonusSs7NodeTimerTCrm           Integer32,
        sonusSs7NodeTimerTCvt           Integer32,
        sonusSs7NodeTimerTExm           Integer32,
        sonusSs7NodeTimerTGrs           Integer32,
        sonusSs7NodeTimerTHga           Integer32,
        sonusSs7NodeTimerTScga          Integer32,
        sonusSs7NodeTimerTScgad         Integer32,
        sonusSs7NodeApplProfileName     DisplayString,
        sonusSs7NodeNetworkInd          INTEGER,
        sonusSs7NodeSlsBits             Integer32,
        sonusSs7NodeTimerTA             Integer32,
        sonusSs7NodeTimerTBlom          Integer32,
        sonusSs7NodeTimerTCotd          Integer32,
        sonusSs7NodeTimerTCotl          Integer32,
        sonusSs7NodeTimerTSus           Integer32
    }

sonusSs7NodeIndex OBJECT-TYPE
    SYNTAX          Integer32
    MAX-ACCESS      read-only
    STATUS          current
    DESCRIPTION     
            "Identifies the target SS7 Node entry."
    ::= { sonusSs7NodeEntry 1 }

sonusSs7NodeState OBJECT-TYPE
    SYNTAX          INTEGER { disabled(1), enabled(2) }
    MAX-ACCESS      read-write
    STATUS          current
    DESCRIPTION     
            "The administrative state of this SS7 Node entry."
    DEFVAL          { disabled }
    ::= { sonusSs7NodeEntry 2 }

sonusSs7NodeName OBJECT-TYPE
    SYNTAX          SonusName
    MAX-ACCESS      read-write
    STATUS          current
    DESCRIPTION     
            "The name of this SS7 Node instance."
    ::= { sonusSs7NodeEntry 3 }

sonusSs7NodePointCode OBJECT-TYPE
    SYNTAX          PointCode
    MAX-ACCESS      read-write
    STATUS          current
    DESCRIPTION     
            "The SS7 point code assigned to this SS7 Node entry."
    ::= { sonusSs7NodeEntry 4 }

sonusSs7NodeServices OBJECT-TYPE
    SYNTAX          INTEGER { isupOnly(1), tcapOnly(2), isupAndTcap(3) }
    MAX-ACCESS      read-write
    STATUS          current
    DESCRIPTION     
            "The type of SS7 services (ISUP, TCAP, or both) supported by this SS7 Node entry. 
             As of GSX release 3.02.00, isupOnly is now the only vaild option for this entry."
    DEFVAL          { isupOnly }
    ::= { sonusSs7NodeEntry 5 }

sonusSs7NodeProtocol OBJECT-TYPE
    SYNTAX          INTEGER { ansi(1), itu(2), etsi(3), japan(4) }
    MAX-ACCESS      read-write
    STATUS          current
    DESCRIPTION     
            "The SS7 protocol type supported by this SS7 Node entry."
    DEFVAL          { ansi }
    ::= { sonusSs7NodeEntry 6 }

sonusSs7NodeTcapSsn OBJECT-TYPE
    SYNTAX          Integer32
    MAX-ACCESS      read-write
    STATUS          obsolete
    DESCRIPTION     
            "If Tcap is supported by this SS7 Node, specifies the Sub System Number for
             this node entry.
             This object is obsoleted as of GSX release 3.02.00."
    DEFVAL          { 0 }
    ::= { sonusSs7NodeEntry 7 }

sonusSs7NodeIsupStatus OBJECT-TYPE
    SYNTAX          INTEGER { offline(1), active(2), initializing(3), 
                        failed(4), disabled(5), congested(6) }
    MAX-ACCESS      read-only
    STATUS          deprecated
    DESCRIPTION     
            "This status value has been replaced by sonusSs7NodeStatIsup"
    ::= { sonusSs7NodeEntry 8 }

sonusSs7NodeTcapStatus OBJECT-TYPE
    SYNTAX          INTEGER { offline(1), active(2), initializing(3), 
                        failed(4), disabled(5), congested(6) }
    MAX-ACCESS      read-only
    STATUS          obsolete
    DESCRIPTION     
            "Specifies the operating status of the TCAP service within this SS7 Node. 
             This object is obsoleted as of GSX release 3.02.00."
    DEFVAL          { offline }
    ::= { sonusSs7NodeEntry 9 }

sonusSs7NodeMtpStatus OBJECT-TYPE
    SYNTAX          INTEGER { paused(1), resumed(2) }
    MAX-ACCESS      read-only
    STATUS          deprecated
    DESCRIPTION     
            "This status value has been replaced by sonusSs7NodeStatMtp"
    ::= { sonusSs7NodeEntry 10 }

sonusSs7NodeGatewayAssignment OBJECT-TYPE
    SYNTAX          DisplayString (SIZE(1..23))
    MAX-ACCESS      read-write
    STATUS          current
    DESCRIPTION     
            "The name of the SS7 Gateway to which this SS7 Node is assigned."
    ::= { sonusSs7NodeEntry 11 }

sonusSs7NodeNativePointCode OBJECT-TYPE
    SYNTAX          Integer32
    MAX-ACCESS      read-only
    STATUS          current
    DESCRIPTION     
            "The native point code of the SS7 node. e.g. For ITU the 
             point code is in 3 bit 8 bit 3 bit format adding up to 14 bits whereas
             ANSI uses a 8bit 8bit 8bit format adding up to 24 bits."
    DEFVAL          { 0 }
    ::= { sonusSs7NodeEntry 12 }

sonusSs7NodeMode OBJECT-TYPE
    SYNTAX          INTEGER { inService(1), outOfService(2) }
    MAX-ACCESS      read-write
    STATUS          current
    DESCRIPTION     
            "Specifies the service mode for this SS7 Node."
    DEFVAL          { outOfService }
    ::= { sonusSs7NodeEntry 13 }

sonusSs7NodeConnCntrl OBJECT-TYPE
    SYNTAX          INTEGER { always(1), asNeeded(2) }
    MAX-ACCESS      read-write
    STATUS          current
    DESCRIPTION     
            "Specifies when the Node will establish an ISUP connection with the SS7 Gateway. 
             This parameter is used to minimize unnecessary connections to the SS7 Gateway 
             for ISUP services, allowing the GSX to only establish the ISUP connections that 
             are required by ISUP circuits on a particular shelf. When set to always, 
             the ISUP service connection will be established when the node is enabled. When 
             set to asNeeded, the ISUP service connection will be established only if there 
             are ISUP circuits assigned to this node. This parameter only applies to ISUP 
             service registration."
    DEFVAL          { asNeeded }
    ::= { sonusSs7NodeEntry 14 }

sonusSs7NodeRowStatus OBJECT-TYPE
    SYNTAX          RowStatus
    MAX-ACCESS      read-write
    STATUS          current
    DESCRIPTION     
            ""
    ::= { sonusSs7NodeEntry 15 }

sonusSs7NodeStdPointCode OBJECT-TYPE
    SYNTAX          SonusPointCode
    MAX-ACCESS      read-write
    STATUS          current
    DESCRIPTION     
            "Octet string of the point code. This gives the actual representation
             the user entered."
    ::= { sonusSs7NodeEntry 16 }

sonusSs7NodePointCodeSize OBJECT-TYPE
    SYNTAX          Integer32 (1..32)
    MAX-ACCESS      read-write
    STATUS          current
    DESCRIPTION     
            "Indicates the total number of bits in the point code."
    DEFVAL          { 24 }
    ::= { sonusSs7NodeEntry 17 }

sonusSs7NodePointCodeFormatType OBJECT-TYPE
    SYNTAX          SonusPointCodeFormat
    MAX-ACCESS      read-write
    STATUS          current
    DESCRIPTION     
            "The Point Code format type being defined."
    ::= { sonusSs7NodeEntry 18 }

sonusSs7NodeServerProtocol OBJECT-TYPE
    SYNTAX          INTEGER { dgmsProp(1), dgmsRaw(2), tekTali(3) }
    MAX-ACCESS      read-write
    STATUS          current
    DESCRIPTION     
            "The interface used between the SS7 gateway and the SS7 client
             on the GSX9000"
    DEFVAL          { dgmsProp }
    ::= { sonusSs7NodeEntry 19 }

sonusSs7NodeHandShakeInterval OBJECT-TYPE
    SYNTAX          Integer32 (1..255)
    MAX-ACCESS      read-write
    STATUS          current
    DESCRIPTION     
            "HandShake interval between the client and the server in seconds."
    ::= { sonusSs7NodeEntry 20 }

sonusSs7NodeTimerT1 OBJECT-TYPE
    SYNTAX          Integer32 (4..60)
    MAX-ACCESS      read-write
    STATUS          current
    DESCRIPTION     
            "The Timer T1 could be changed from its default using this entry. The valid ranges are 
             4 - 15 seconds for ANSI and 15 - 60 Seconds for ITU."
    DEFVAL          { 10 }
    ::= { sonusSs7NodeEntry 21 }

sonusSs7NodeTimerT2 OBJECT-TYPE
    SYNTAX          Integer32 (1..255)
    MAX-ACCESS      read-write
    STATUS          current
    DESCRIPTION     
            "The Timer T2 could be changed from its default using this entry. The valid value for
             ITU is 3 Minutes. This timer has no relevence in the ANSI network. "
    DEFVAL          { 180 }
    ::= { sonusSs7NodeEntry 22 }

sonusSs7NodeTimerT3 OBJECT-TYPE
    SYNTAX          Integer32 (1..255)
    MAX-ACCESS      read-write
    STATUS          current
    DESCRIPTION     
            "The T3 timer is started on receipt of an Overload message in the ITU network. This has
             no relevence in the ANSI network. The valid ITU recommended value is 120 Seconds "
    DEFVAL          { 120 }
    ::= { sonusSs7NodeEntry 23 }

sonusSs7NodeTimerT4 OBJECT-TYPE
    SYNTAX          Integer32 (300..900)
    MAX-ACCESS      read-write
    STATUS          current
    DESCRIPTION     
            "The Timer T4 could be changed from its default using this entry."
    DEFVAL          { 600 }
    ::= { sonusSs7NodeEntry 24 }

sonusSs7NodeTimerT5 OBJECT-TYPE
    SYNTAX          Integer32 (60..900)
    MAX-ACCESS      read-write
    STATUS          current
    DESCRIPTION     
            "The T5 Timer is started when the release message is sent. The valid values
             as per the specifications are 60 seconds for the ANSI and 300 to 900 seconds for
             ITU."
    DEFVAL          { 60 }
    ::= { sonusSs7NodeEntry 25 }

sonusSs7NodeTimerT6 OBJECT-TYPE
    SYNTAX          Integer32 (1..120)
    MAX-ACCESS      read-write
    STATUS          current
    DESCRIPTION     
            "The timer T6 is started when the suspend message is received. The valid range
             for this timer is 1 to 120 seconds."
    DEFVAL          { 22 }
    ::= { sonusSs7NodeEntry 26 }

sonusSs7NodeTimerT7 OBJECT-TYPE
    SYNTAX          Integer32 (20..30)
    MAX-ACCESS      read-write
    STATUS          current
    DESCRIPTION     
            "The Timer T7 could be changed from its default using this entry."
    DEFVAL          { 25 }
    ::= { sonusSs7NodeEntry 27 }

sonusSs7NodeTimerT8 OBJECT-TYPE
    SYNTAX          Integer32 (10..15)
    MAX-ACCESS      read-write
    STATUS          current
    DESCRIPTION     
            "The T8 timer is timer to be started with continuity check has been indicated in the IAM.
             The valid range is 10 to 15 seconds."
    DEFVAL          { 13 }
    ::= { sonusSs7NodeEntry 28 }

sonusSs7NodeTimerT9 OBJECT-TYPE
    SYNTAX          Integer32 (120..240)
    MAX-ACCESS      read-write
    STATUS          current
    DESCRIPTION     
            "The Timer T9 started when outgoing international exchange recieves an ACM. The valid
             range is 120  to 240 seconds."
    DEFVAL          { 180 }
    ::= { sonusSs7NodeEntry 29 }

sonusSs7NodeTimerT10 OBJECT-TYPE
    SYNTAX          Integer32 (4..6)
    MAX-ACCESS      read-write
    STATUS          current
    DESCRIPTION     
            "The Timer T10 is started when the last digit is recived in interworking 
             situations. This timer has no relevence to ANSI."
    ::= { sonusSs7NodeEntry 30 }

sonusSs7NodeTimerT11 OBJECT-TYPE
    SYNTAX          Integer32 (15..20)
    MAX-ACCESS      read-write
    STATUS          current
    DESCRIPTION     
            "The Timer T11 is started when the latest address message is received in interworking 
             situations. The valid range is 15 to 20 seconds."
    DEFVAL          { 17 }
    ::= { sonusSs7NodeEntry 31 }

sonusSs7NodeTimerT12 OBJECT-TYPE
    SYNTAX          Integer32 (4..60)
    MAX-ACCESS      read-write
    STATUS          current
    DESCRIPTION     
            "The Timer T12 is started when a blocking message is sent. The valid ranges are 4 to 15 seconds
             for ANSI and 15 to 60 seconds for ITU."
    DEFVAL          { 10 }
    ::= { sonusSs7NodeEntry 32 }

sonusSs7NodeTimerT13 OBJECT-TYPE
    SYNTAX          Integer32 (60..900)
    MAX-ACCESS      read-write
    STATUS          current
    DESCRIPTION     
            "The Timer T13 is started when the initial blocking messge is sent. The valid
             value for ANSI is 60 seconds and for ITU is between 300 and 900 seconds."
    DEFVAL          { 60 }
    ::= { sonusSs7NodeEntry 33 }

sonusSs7NodeTimerT14 OBJECT-TYPE
    SYNTAX          Integer32 (4..60)
    MAX-ACCESS      read-write
    STATUS          current
    DESCRIPTION     
            "The Timer T14 is started when an unblocking message is sent. The valid
             values are 4 to 15 seconds for ANSI and 15 to 60 seconds for ITU"
    DEFVAL          { 10 }
    ::= { sonusSs7NodeEntry 34 }

sonusSs7NodeTimerT15 OBJECT-TYPE
    SYNTAX          Integer32 (60..900)
    MAX-ACCESS      read-write
    STATUS          current
    DESCRIPTION     
            "The Timer T15 is started when the initial unblocking message is sent. The
             valid values are 60 seconds for ANSI and 300 to 900 seconds for ITU."
    DEFVAL          { 60 }
    ::= { sonusSs7NodeEntry 35 }

sonusSs7NodeTimerT16 OBJECT-TYPE
    SYNTAX          Integer32 (4..60)
    MAX-ACCESS      read-write
    STATUS          current
    DESCRIPTION     
            "The Timer T16 is started when the reset circuit is started which was not due to expiry of
             T5. The valid ranges are 4 to 15 seconds for ANSI and 15 to 60 seconds for ITU."
    DEFVAL          { 10 }
    ::= { sonusSs7NodeEntry 36 }

sonusSs7NodeTimerT17 OBJECT-TYPE
    SYNTAX          Integer32 (60..900)
    MAX-ACCESS      read-write
    STATUS          current
    DESCRIPTION     
            "The Timer T17 is started when initial reset message is sent. The valid values are
             60 seconds for ANSI and 300 to 900 for ITU."
    DEFVAL          { 60 }
    ::= { sonusSs7NodeEntry 37 }

sonusSs7NodeTimerT18 OBJECT-TYPE
    SYNTAX          Integer32 (4..60)
    MAX-ACCESS      read-write
    STATUS          current
    DESCRIPTION     
            "The Timer T18 is started when circuit group blocking message is sent. The
             valid values are 4 to 15 seconds for ANSI and 15 to 60 seconds for ITU."
    DEFVAL          { 10 }
    ::= { sonusSs7NodeEntry 38 }

sonusSs7NodeTimerT19 OBJECT-TYPE
    SYNTAX          Integer32 (60..900)
    MAX-ACCESS      read-write
    STATUS          current
    DESCRIPTION     
            "The Timer T19 is started when initial group blocking message is sent. The valid values 
             are 60 seconds for ANSI and 300 to 900 seconds for ITU."
    DEFVAL          { 60 }
    ::= { sonusSs7NodeEntry 39 }

sonusSs7NodeTimerT20 OBJECT-TYPE
    SYNTAX          Integer32 (4..60)
    MAX-ACCESS      read-write
    STATUS          current
    DESCRIPTION     
            "The Timer T20 is started when group unblocking message is sent. The valid ranges are
             4 to 15 seconds for ANSI and 15 to 60 seconds for ITU."
    DEFVAL          { 10 }
    ::= { sonusSs7NodeEntry 40 }

sonusSs7NodeTimerT21 OBJECT-TYPE
    SYNTAX          Integer32 (60..900)
    MAX-ACCESS      read-write
    STATUS          current
    DESCRIPTION     
            "The Timer T21 is started when initial group blocking message is sent. The 
             valid values are 60 seconds for ANSI and 300 to 900 seconds for ITU."
    DEFVAL          { 60 }
    ::= { sonusSs7NodeEntry 41 }

sonusSs7NodeTimerT22 OBJECT-TYPE
    SYNTAX          Integer32 (4..60)
    MAX-ACCESS      read-write
    STATUS          current
    DESCRIPTION     
            "The Timer T22 is started when circuit group reset message is sent. The valid values are
             4 to 15 seconds for ANSI and 15 to 60 seconds for ITU."
    DEFVAL          { 10 }
    ::= { sonusSs7NodeEntry 42 }

sonusSs7NodeTimerT23 OBJECT-TYPE
    SYNTAX          Integer32 (60..900)
    MAX-ACCESS      read-write
    STATUS          current
    DESCRIPTION     
            "The Timer T23 is started when initial group reset message is sent. The valid values
             are 60 seconds for the ANSI and 300 to 900 seconds for the ITU."
    DEFVAL          { 60 }
    ::= { sonusSs7NodeEntry 43 }

sonusSs7NodeTimerT24 OBJECT-TYPE
    SYNTAX          Integer32 (1..2)
    MAX-ACCESS      read-write
    STATUS          current
    DESCRIPTION     
            "The Timer T24 is started when check tone is sent. The value is less
             than 2 seconds."
    DEFVAL          { 1 }
    ::= { sonusSs7NodeEntry 44 }

sonusSs7NodeTimerT25 OBJECT-TYPE
    SYNTAX          Integer32 (1..10)
    MAX-ACCESS      read-write
    STATUS          current
    DESCRIPTION     
            "The Timer T25 is started when initial continuity check failure is 
             detected. The range is 1 to 10 seconds."
    DEFVAL          { 5 }
    ::= { sonusSs7NodeEntry 45 }

sonusSs7NodeTimerT26 OBJECT-TYPE
    SYNTAX          Integer32 (60..180)
    MAX-ACCESS      read-write
    STATUS          current
    DESCRIPTION     
            "The Timer T26 is started when a second or subsequent continuity failure is detected.
             The valid value are 60 to 180 seconds."
    DEFVAL          { 120 }
    ::= { sonusSs7NodeEntry 46 }

sonusSs7NodeTimerT27 OBJECT-TYPE
    SYNTAX          Integer32 (180..36000)
    MAX-ACCESS      read-write
    STATUS          current
    DESCRIPTION     
            "The Timer T27 is started when a continuity fail message is recieved. The valid values are
             more than 180 seconds for ANSI and 240 seconds for ITU. "
    DEFVAL          { 240 }
    ::= { sonusSs7NodeEntry 47 }

sonusSs7NodeTimerT28 OBJECT-TYPE
    SYNTAX          Integer32 (5..12)
    MAX-ACCESS      read-write
    STATUS          current
    DESCRIPTION     
            "The Timer T28 is started when Circuit Query Message is sent. The valid value is 10 seconds."
    DEFVAL          { 10 }
    ::= { sonusSs7NodeEntry 48 }

sonusSs7NodeTimerT29 OBJECT-TYPE
    SYNTAX          Integer32 (300..600)
    MAX-ACCESS      read-write
    STATUS          current
    DESCRIPTION     
            "The Timer T29 is started when Congestion indication is received when T29
             is not running. The valid range is 300 to 600 milli second. This timer has
             no relevence for ANSI."
    ::= { sonusSs7NodeEntry 49 }

sonusSs7NodeTimerT30 OBJECT-TYPE
    SYNTAX          Integer32 (5..10)
    MAX-ACCESS      read-write
    STATUS          current
    DESCRIPTION     
            "The Timer T30 is stared when congestion indication is recieved when T29 is not running. The valid 
             range is 5 to 10 seconds for the ITU. This timer has no relevence under ANSI."
    ::= { sonusSs7NodeEntry 50 }

sonusSs7NodeTimerT31 OBJECT-TYPE
    SYNTAX          Integer32 (360..65520)
    MAX-ACCESS      read-write
    STATUS          current
    DESCRIPTION     
            "The Timer T31 is started on release of ISUP signalling connection based on
             CO SCCP. The value should be set to greater than 360 seconds"
    DEFVAL          { 420 }
    ::= { sonusSs7NodeEntry 51 }

sonusSs7NodeTimerT32 OBJECT-TYPE
    SYNTAX          Integer32 (3..5)
    MAX-ACCESS      read-write
    STATUS          current
    DESCRIPTION     
            "The Timer T32 is started when the first end-to-end message is recived. Under ANSI this
             timer is started after the response to such a message is sent. The valid values are 3 
             to 5 seconds. "
    DEFVAL          { 4 }
    ::= { sonusSs7NodeEntry 52 }

sonusSs7NodeTimerT33 OBJECT-TYPE
    SYNTAX          Integer32 (12..15)
    MAX-ACCESS      read-write
    STATUS          current
    DESCRIPTION     
            "The Timer T33 is started when Information Request Message is sent. The 
             valid range is 12 to 15 seconds."
    DEFVAL          { 14 }
    ::= { sonusSs7NodeEntry 53 }

sonusSs7NodeTimerT34 OBJECT-TYPE
    SYNTAX          Integer32 (2..15)
    MAX-ACCESS      read-write
    STATUS          current
    DESCRIPTION     
            "The Timer T34 is started when Loop Back Acknowledgement is sent under ANSI.
             The Timer T34 is started when segmentation is received for IAM, ACM, CPG,
             ANM or CON under ITU. The valid range for ANSI is 10 to 15 seconds. The valid
             range for ITU is 2 to 4 seconds."
    ::= { sonusSs7NodeEntry 54 }

sonusSs7NodeTimerT35 OBJECT-TYPE
    SYNTAX          Integer32 (15..20)
    MAX-ACCESS      read-write
    STATUS          current
    DESCRIPTION     
            "The Timer T35 is started when the last digit recieved is not an ST digit or
             the fixed number of digits have been recieved. This procedure is only valid
             for overlap hence ITU. This timer has no relevence in ANSI."
    DEFVAL          { 18 }
    ::= { sonusSs7NodeEntry 55 }

sonusSs7NodeTimerT36 OBJECT-TYPE
    SYNTAX          Integer32 (2..15)
    MAX-ACCESS      read-write
    STATUS          current
    DESCRIPTION     
            "The Timer T36 is started when IAM is recived with a segmentation indication for ANSI.
             This timer is started when transit or incoming international exchange recieves Continuity check
             request message. The valid range for ANSI is 2 to 4 seconds and 10 to 15 
             seconds for ITU. "
    ::= { sonusSs7NodeEntry 56 }

sonusSs7NodeTimerT37 OBJECT-TYPE
    SYNTAX          Integer32 (2..30)
    MAX-ACCESS      read-write
    STATUS          current
    DESCRIPTION     
            "The Timer T37 is started when User Part Availability test is started under ANSI. This
             timer is started when a request for and Echo control device is sent to another exchange
             under ITU. The valid value for ANSI is 30 seconds and for ITU is 2 to 4 seconds."
    ::= { sonusSs7NodeEntry 57 }

sonusSs7NodeTimerT38 OBJECT-TYPE
    SYNTAX          Integer32 (10..60)
    MAX-ACCESS      read-write
    STATUS          current
    DESCRIPTION     
            "The Timer T38 is started when a suspend message is sent to the preceding switch. This timer
             is only relevent under ITU."
    DEFVAL          { 30 }
    ::= { sonusSs7NodeEntry 58 }

sonusSs7NodeTimerT39 OBJECT-TYPE
    SYNTAX          Integer32 (1..65535)
    MAX-ACCESS      read-write
    STATUS          current
    DESCRIPTION     
            "The Timer T39 is started when MCID request is sent. It is only relevent in the ITU."
    ::= { sonusSs7NodeEntry 59 }

sonusSs7NodeTimerT40 OBJECT-TYPE
    SYNTAX          Integer32 (1..65535)
    MAX-ACCESS      read-write
    STATUS          current
    DESCRIPTION     
            "The Timer T40 could be changed from its default using this entry."
    ::= { sonusSs7NodeEntry 60 }

sonusSs7NodeTimerTAcc OBJECT-TYPE
    SYNTAX          Integer32 (3..8)
    MAX-ACCESS      read-write
    STATUS          current
    DESCRIPTION     
            "Automatic Congestion Control Timer as per ANSI T1.113.4 - 1995. The value
             of the timer is 5 Seconds."
    DEFVAL          { 5 }
    ::= { sonusSs7NodeEntry 61 }

sonusSs7NodeTimerTCcr OBJECT-TYPE
    SYNTAX          Integer32 (1..3)
    MAX-ACCESS      read-write
    STATUS          current
    DESCRIPTION     
            "Continuity Check Request Timer. The value As per ANSI T1.113.4 - 1995 is 2 Seconds."
    DEFVAL          { 2 }
    ::= { sonusSs7NodeEntry 62 }

sonusSs7NodeTimerTCcrr OBJECT-TYPE
    SYNTAX          Integer32 (16..31)
    MAX-ACCESS      read-write
    STATUS          current
    DESCRIPTION     
            "Continuity Check Failed Recived. The value as per ANSI T1.113.4 - 1995 is 20 Seconds."
    DEFVAL          { 20 }
    ::= { sonusSs7NodeEntry 63 }

sonusSs7NodeTimerTCgb OBJECT-TYPE
    SYNTAX          Integer32 (3..8)
    MAX-ACCESS      read-write
    STATUS          current
    DESCRIPTION     
            "Timer started on recipt of a Circuit Group Block Message. The value as per
             ANSI T1.113.4 - 1995 is 5 Seconds."
    DEFVAL          { 5 }
    ::= { sonusSs7NodeEntry 64 }

sonusSs7NodeTimerTCra OBJECT-TYPE
    SYNTAX          Integer32 (16..31)
    MAX-ACCESS      read-write
    STATUS          current
    DESCRIPTION     
            "Timer started when Circuit Reservation Acknowledgment is sent. The time value
             as per ANSI T1.113.4 - 1995 is 20 seconds."
    DEFVAL          { 20 }
    ::= { sonusSs7NodeEntry 65 }

sonusSs7NodeTimerTCrm OBJECT-TYPE
    SYNTAX          Integer32 (3..4)
    MAX-ACCESS      read-write
    STATUS          current
    DESCRIPTION     
            "This timer is started when the circuit reservation message is sent. The value 
             as per ANSI T1.113.4 - 1995 is 3 - 4 Seconds. The default is set to 4 seconds."
    DEFVAL          { 4 }
    ::= { sonusSs7NodeEntry 66 }

sonusSs7NodeTimerTCvt OBJECT-TYPE
    SYNTAX          Integer32 (5..12)
    MAX-ACCESS      read-write
    STATUS          current
    DESCRIPTION     
            "The Timer T CVT is started when the Circuit Validation Test message
             is sent. This message is only valid for ANSI."
    DEFVAL          { 10 }
    ::= { sonusSs7NodeEntry 67 }

sonusSs7NodeTimerTExm OBJECT-TYPE
    SYNTAX          Integer32 (1..65535)
    MAX-ACCESS      read-write
    STATUS          current
    DESCRIPTION     
            "The Timer Exm,d is started when IAM is sent to the succeeding network. This
             timer has no relevence in the ITU. This timer is in milliseconds"
    ::= { sonusSs7NodeEntry 68 }

sonusSs7NodeTimerTGrs OBJECT-TYPE
    SYNTAX          Integer32 (3..8)
    MAX-ACCESS      read-write
    STATUS          current
    DESCRIPTION     
            "This timer is started when a circuit group reset message is received. 
             This timer is only relevent in the ANSI network. "
    DEFVAL          { 5 }
    ::= { sonusSs7NodeEntry 69 }

sonusSs7NodeTimerTHga OBJECT-TYPE
    SYNTAX          Integer32 (0..300)
    MAX-ACCESS      read-write
    STATUS          current
    DESCRIPTION     
            "This timer is started on recognition of carrier loss. It is only relevent in ANSI
             network. The valid range is 0 to 300 seconds."
    DEFVAL          { 150 }
    ::= { sonusSs7NodeEntry 70 }

sonusSs7NodeTimerTScga OBJECT-TYPE
    SYNTAX          Integer32 (0..120)
    MAX-ACCESS      read-write
    STATUS          current
    DESCRIPTION     
            "This timer is started when initial demand continuity check fails in the
             SCGA group. The valid range for this timer is 0 to 120 seconds."
    DEFVAL          { 60 }
    ::= { sonusSs7NodeEntry 71 }

sonusSs7NodeTimerTScgad OBJECT-TYPE
    SYNTAX          Integer32 (5..120)
    MAX-ACCESS      read-write
    STATUS          current
    DESCRIPTION     
            "This timer is started failure of demand continuity check in the SCGA group."
    DEFVAL          { 65 }
    ::= { sonusSs7NodeEntry 72 }

sonusSs7NodeApplProfileName OBJECT-TYPE
    SYNTAX          DisplayString (SIZE(0..23))
    MAX-ACCESS      read-write
    STATUS          current
    DESCRIPTION     
            "The SS7 Node Profile to be applied to the node. The values here are
             a snap shot only and might have changed since they were set."
    ::= { sonusSs7NodeEntry 73 }

sonusSs7NodeNetworkInd OBJECT-TYPE
    SYNTAX          INTEGER { intl0(1), intl1(2), natl0(3), natl1(4) }
    MAX-ACCESS      read-write
    STATUS          current
    DESCRIPTION     
            "The setting of the Network Indicator used for this SS7 Node entry."
    DEFVAL          { natl0 }
    ::= { sonusSs7NodeEntry 74 }

sonusSs7NodeSlsBits OBJECT-TYPE
    SYNTAX          Integer32 (4..8)
    MAX-ACCESS      read-write
    STATUS          current
    DESCRIPTION     
            "The number of SLS bits to use"
    DEFVAL          { 5 }
    ::= { sonusSs7NodeEntry 75 }

sonusSs7NodeTimerTA OBJECT-TYPE
    SYNTAX          Integer32 (0..1000)
    MAX-ACCESS      read-write
    STATUS          current
    DESCRIPTION     
            "The Bellcore specific timer TA is the guard timer on outgoing SS7 circuit before
             idling. The value of this timer is 0 to 1000 milliseconds."
    DEFVAL          { 0 }
    ::= { sonusSs7NodeEntry 76 }

sonusSs7NodeTimerTBlom OBJECT-TYPE
    SYNTAX          Integer32 (240..360)
    MAX-ACCESS      read-write
    STATUS          current
    DESCRIPTION     
            "The Bellcore specific timer TBlom is started when blocking a circuit due to a
             BLO, and after any call is released; used to notify maintenance."
    DEFVAL          { 300 }
    ::= { sonusSs7NodeEntry 77 }

sonusSs7NodeTimerTCotd OBJECT-TYPE
    SYNTAX          Integer32 (0..500)
    MAX-ACCESS      read-write
    STATUS          current
    DESCRIPTION     
            "The Bellcore specific timer TCOTd is started when sending IAM requesting
             continuity check. The value of this timer is in milliseconds."
    DEFVAL          { 0 }
    ::= { sonusSs7NodeEntry 78 }

sonusSs7NodeTimerTCotl OBJECT-TYPE
    SYNTAX          Integer32 (240..300)
    MAX-ACCESS      read-write
    STATUS          current
    DESCRIPTION     
            "The Bellcore specific timer TCOTl is started when receiving second COT coded
             failed, awaiting receipt of CCR."
    DEFVAL          { 250 }
    ::= { sonusSs7NodeEntry 79 }

sonusSs7NodeTimerTSus OBJECT-TYPE
    SYNTAX          Integer32 (14..16)
    MAX-ACCESS      read-write
    STATUS          current
    DESCRIPTION     
            "The Bellcore specific timer TSUS is started when a SUS message is sent by the
             terminating switch, awaiting called party off-hook or REL."
    DEFVAL          { 15 }
    ::= { sonusSs7NodeEntry 80 }

sonusSs7NodeProfile OBJECT IDENTIFIER
    ::= { sonusSs7ServicesMIBObjects 3 }

sonusSs7NodeProfileNextIndex OBJECT-TYPE
    SYNTAX          Integer32
    MAX-ACCESS      read-only
    STATUS          current
    DESCRIPTION     
            "The next valid index to use when creating an entry in
             the sonusSs7NodeProfileTable."
    ::= { sonusSs7NodeProfile 1 }

sonusSs7NodeProfileTable OBJECT-TYPE
    SYNTAX          SEQUENCE OF SonusSs7NodeProfileEntry
    MAX-ACCESS      not-accessible
    STATUS          current
    DESCRIPTION     
            "This table specifies the SS7 Node Profile list for the GSX9000 node."
    ::= { sonusSs7NodeProfile 2 }

sonusSs7NodeProfileEntry OBJECT-TYPE
    SYNTAX          SonusSs7NodeProfileEntry
    MAX-ACCESS      not-accessible
    STATUS          current
    DESCRIPTION     
            ""
    INDEX           { sonusSs7NodeProfileIndex }
    ::= { sonusSs7NodeProfileTable 1 }

SonusSs7NodeProfileEntry ::=
    SEQUENCE {
        sonusSs7NodeProfileIndex        Integer32,
        sonusSs7NodeProfileName         SonusName,
        sonusSs7PointCodeSize           Integer32,
        sonusSs7PointCodeFormatType     SonusPointCodeFormat,
        sonusSs7ServerProtocol          INTEGER,
        sonusSs7HandShakeInterval       Integer32,
        sonusSs7TimerT1                 Integer32,
        sonusSs7TimerT2                 Integer32,
        sonusSs7TimerT3                 Integer32,
        sonusSs7TimerT4                 Integer32,
        sonusSs7TimerT5                 Integer32,
        sonusSs7TimerT6                 Integer32,
        sonusSs7TimerT7                 Integer32,
        sonusSs7TimerT8                 Integer32,
        sonusSs7TimerT9                 Integer32,
        sonusSs7TimerT10                Integer32,
        sonusSs7TimerT11                Integer32,
        sonusSs7TimerT12                Integer32,
        sonusSs7TimerT13                Integer32,
        sonusSs7TimerT14                Integer32,
        sonusSs7TimerT15                Integer32,
        sonusSs7TimerT16                Integer32,
        sonusSs7TimerT17                Integer32,
        sonusSs7TimerT18                Integer32,
        sonusSs7TimerT19                Integer32,
        sonusSs7TimerT20                Integer32,
        sonusSs7TimerT21                Integer32,
        sonusSs7TimerT22                Integer32,
        sonusSs7TimerT23                Integer32,
        sonusSs7TimerT24                Integer32,
        sonusSs7TimerT25                Integer32,
        sonusSs7TimerT26                Integer32,
        sonusSs7TimerT27                Integer32,
        sonusSs7TimerT28                Integer32,
        sonusSs7TimerT29                Integer32,
        sonusSs7TimerT30                Integer32,
        sonusSs7TimerT31                Integer32,
        sonusSs7TimerT32                Integer32,
        sonusSs7TimerT33                Integer32,
        sonusSs7TimerT34                Integer32,
        sonusSs7TimerT35                Integer32,
        sonusSs7TimerT36                Integer32,
        sonusSs7TimerT37                Integer32,
        sonusSs7TimerT38                Integer32,
        sonusSs7TimerT39                Integer32,
        sonusSs7TimerT40                Integer32,
        sonusSs7TimerTAcc               Integer32,
        sonusSs7TimerTCcr               Integer32,
        sonusSs7TimerTCcrr              Integer32,
        sonusSs7TimerTCgb               Integer32,
        sonusSs7TimerTCra               Integer32,
        sonusSs7TimerTCrm               Integer32,
        sonusSs7TimerTCvt               Integer32,
        sonusSs7TimerTExm               Integer32,
        sonusSs7TimerTGrs               Integer32,
        sonusSs7TimerTHga               Integer32,
        sonusSs7TimerTScga              Integer32,
        sonusSs7TimerTScgad             Integer32,
        sonusSs7NodeProfileState        INTEGER,
        sonusSs7NodeProfileRowStatus    RowStatus,
        sonusSs7NodeProfileNetworkInd   INTEGER,
        sonusSs7SlsBits                 Integer32,
        sonusSs7TimerTA                 Integer32,
        sonusSs7TimerTBlom              Integer32,
        sonusSs7TimerTCotd              Integer32,
        sonusSs7TimerTCotl              Integer32,
        sonusSs7TimerTSus               Integer32
    }

sonusSs7NodeProfileIndex OBJECT-TYPE
    SYNTAX          Integer32
    MAX-ACCESS      read-only
    STATUS          current
    DESCRIPTION     
            "Identifies the SS7 Node Profile entry"
    ::= { sonusSs7NodeProfileEntry 1 }

sonusSs7NodeProfileName OBJECT-TYPE
    SYNTAX          SonusName
    MAX-ACCESS      read-write
    STATUS          current
    DESCRIPTION     
            "The name of the Node Profile"
    ::= { sonusSs7NodeProfileEntry 2 }

sonusSs7PointCodeSize OBJECT-TYPE
    SYNTAX          Integer32 (1..32)
    MAX-ACCESS      read-write
    STATUS          current
    DESCRIPTION     
            "Indicates the total number of bits in the point code."
    DEFVAL          { 24 }
    ::= { sonusSs7NodeProfileEntry 3 }

sonusSs7PointCodeFormatType OBJECT-TYPE
    SYNTAX          SonusPointCodeFormat
    MAX-ACCESS      read-write
    STATUS          current
    DESCRIPTION     
            "The Point Code format type being defined."
    ::= { sonusSs7NodeProfileEntry 4 }

sonusSs7ServerProtocol OBJECT-TYPE
    SYNTAX          INTEGER { dgmsProp(1), dgmsRaw(2), tekTali(3) }
    MAX-ACCESS      read-write
    STATUS          current
    DESCRIPTION     
            "The interface used between the SS7 gateway and the SS7 client
             on the GSX9000"
    DEFVAL          { dgmsProp }
    ::= { sonusSs7NodeProfileEntry 5 }

sonusSs7HandShakeInterval OBJECT-TYPE
    SYNTAX          Integer32 (1..255)
    MAX-ACCESS      read-write
    STATUS          current
    DESCRIPTION     
            "HandShake interval between the client and the server in seconds."
    ::= { sonusSs7NodeProfileEntry 6 }

sonusSs7TimerT1 OBJECT-TYPE
    SYNTAX          Integer32 (4..60)
    MAX-ACCESS      read-write
    STATUS          current
    DESCRIPTION     
            "The Timer T1 could be changed from its default using this entry. The valid ranges are 
             4 - 15 seconds for ANSI and 15 - 60 Seconds for ITU."
    DEFVAL          { 10 }
    ::= { sonusSs7NodeProfileEntry 7 }

sonusSs7TimerT2 OBJECT-TYPE
    SYNTAX          Integer32 (1..255)
    MAX-ACCESS      read-write
    STATUS          current
    DESCRIPTION     
            "The Timer T2 could be changed from its default using this entry. The valid value for
             ITU is 3 Minutes. This timer has no relevence in the ANSI network. "
    DEFVAL          { 180 }
    ::= { sonusSs7NodeProfileEntry 8 }

sonusSs7TimerT3 OBJECT-TYPE
    SYNTAX          Integer32 (1..255)
    MAX-ACCESS      read-write
    STATUS          current
    DESCRIPTION     
            "The T3 timer is started on receipt of an Overload message in the ITU network. This has
             no relevence in the ANSI network. The valid ITU recommended value is 120 Seconds "
    DEFVAL          { 120 }
    ::= { sonusSs7NodeProfileEntry 9 }

sonusSs7TimerT4 OBJECT-TYPE
    SYNTAX          Integer32 (300..900)
    MAX-ACCESS      read-write
    STATUS          current
    DESCRIPTION     
            "The Timer T4 could be changed from its default using this entry."
    DEFVAL          { 600 }
    ::= { sonusSs7NodeProfileEntry 10 }

sonusSs7TimerT5 OBJECT-TYPE
    SYNTAX          Integer32 (60..900)
    MAX-ACCESS      read-write
    STATUS          current
    DESCRIPTION     
            "The T5 Timer is started when the release message is sent. The valid values
             as per the specifications are 60 seconds for the ANSI and 300 to 900 seconds for
             ITU."
    DEFVAL          { 60 }
    ::= { sonusSs7NodeProfileEntry 11 }

sonusSs7TimerT6 OBJECT-TYPE
    SYNTAX          Integer32 (10..32)
    MAX-ACCESS      read-write
    STATUS          current
    DESCRIPTION     
            "The timer T6 is started when the suspend message is received. The valid range
             for this timer is 10 to 32 seconds."
    DEFVAL          { 22 }
    ::= { sonusSs7NodeProfileEntry 12 }

sonusSs7TimerT7 OBJECT-TYPE
    SYNTAX          Integer32 (20..30)
    MAX-ACCESS      read-write
    STATUS          current
    DESCRIPTION     
            "The Timer T7 could be changed from its default using this entry."
    DEFVAL          { 25 }
    ::= { sonusSs7NodeProfileEntry 13 }

sonusSs7TimerT8 OBJECT-TYPE
    SYNTAX          Integer32 (10..15)
    MAX-ACCESS      read-write
    STATUS          current
    DESCRIPTION     
            "The T8 timer is timer to be started with continuity check has been indicated in the IAM.
             The valid range is 10 to 15 seconds."
    DEFVAL          { 13 }
    ::= { sonusSs7NodeProfileEntry 14 }

sonusSs7TimerT9 OBJECT-TYPE
    SYNTAX          Integer32 (120..240)
    MAX-ACCESS      read-write
    STATUS          current
    DESCRIPTION     
            "The Timer T9 started when outgoing international exchange recieves an ACM. The valid
             range is 120  to 240 seconds."
    DEFVAL          { 180 }
    ::= { sonusSs7NodeProfileEntry 15 }

sonusSs7TimerT10 OBJECT-TYPE
    SYNTAX          Integer32 (240..360)
    MAX-ACCESS      read-write
    STATUS          current
    DESCRIPTION     
            "The Timer T10 is started when the last digit is recived in interworking 
             situations. This timer has no relevence to ANSI."
    ::= { sonusSs7NodeProfileEntry 16 }

sonusSs7TimerT11 OBJECT-TYPE
    SYNTAX          Integer32 (15..20)
    MAX-ACCESS      read-write
    STATUS          current
    DESCRIPTION     
            "The Timer T11 is started when the latest address message is received in interworking 
             situations. The valid range is 15 to 20 seconds."
    DEFVAL          { 17 }
    ::= { sonusSs7NodeProfileEntry 17 }

sonusSs7TimerT12 OBJECT-TYPE
    SYNTAX          Integer32 (4..60)
    MAX-ACCESS      read-write
    STATUS          current
    DESCRIPTION     
            "The Timer T12 is started when a blocking message is sent. The valid ranges are 4 to 15 seconds
             for ANSI and 15 to 60 seconds for ITU."
    DEFVAL          { 10 }
    ::= { sonusSs7NodeProfileEntry 18 }

sonusSs7TimerT13 OBJECT-TYPE
    SYNTAX          Integer32 (60..900)
    MAX-ACCESS      read-write
    STATUS          current
    DESCRIPTION     
            "The Timer T13 is started when the initial blocking messge is sent. The valid
             value for ANSI is 60 seconds and for ITU is between 300 and 900 seconds."
    DEFVAL          { 60 }
    ::= { sonusSs7NodeProfileEntry 19 }

sonusSs7TimerT14 OBJECT-TYPE
    SYNTAX          Integer32 (4..60)
    MAX-ACCESS      read-write
    STATUS          current
    DESCRIPTION     
            "The Timer T14 is started when an unblocking message is sent. The valid
             values are 4 to 15 seconds for ANSI and 15 to 60 seconds for ITU"
    DEFVAL          { 10 }
    ::= { sonusSs7NodeProfileEntry 20 }

sonusSs7TimerT15 OBJECT-TYPE
    SYNTAX          Integer32 (60..900)
    MAX-ACCESS      read-write
    STATUS          current
    DESCRIPTION     
            "The Timer T15 is started when the initial unblocking message is sent. The
             valid values are 60 seconds for ANSI and 300 to 900 seconds for ITU."
    DEFVAL          { 60 }
    ::= { sonusSs7NodeProfileEntry 21 }

sonusSs7TimerT16 OBJECT-TYPE
    SYNTAX          Integer32 (4..60)
    MAX-ACCESS      read-write
    STATUS          current
    DESCRIPTION     
            "The Timer T16 is started when the reset circuit is started which was not due to expiry of
             T5. The valid ranges are 4 to 15 seconds for ANSI and 15 to 60 seconds for ITU."
    DEFVAL          { 10 }
    ::= { sonusSs7NodeProfileEntry 22 }

sonusSs7TimerT17 OBJECT-TYPE
    SYNTAX          Integer32 (60..900)
    MAX-ACCESS      read-write
    STATUS          current
    DESCRIPTION     
            "The Timer T17 is started when initial reset message is sent. The valid values are
             60 seconds for ANSI and 300 to 900 for ITU."
    DEFVAL          { 60 }
    ::= { sonusSs7NodeProfileEntry 23 }

sonusSs7TimerT18 OBJECT-TYPE
    SYNTAX          Integer32 (4..60)
    MAX-ACCESS      read-write
    STATUS          current
    DESCRIPTION     
            "The Timer T18 is started when circuit group blocking message is sent. The
             valid values are 4 to 15 seconds for ANSI and 15 to 60 seconds for ITU."
    DEFVAL          { 10 }
    ::= { sonusSs7NodeProfileEntry 24 }

sonusSs7TimerT19 OBJECT-TYPE
    SYNTAX          Integer32 (60..900)
    MAX-ACCESS      read-write
    STATUS          current
    DESCRIPTION     
            "The Timer T19 is started when initial group blocking message is sent. The valid values 
             are 60 seconds for ANSI and 300 to 900 seconds for ITU."
    DEFVAL          { 60 }
    ::= { sonusSs7NodeProfileEntry 25 }

sonusSs7TimerT20 OBJECT-TYPE
    SYNTAX          Integer32 (4..60)
    MAX-ACCESS      read-write
    STATUS          current
    DESCRIPTION     
            "The Timer T20 is started when group unblocking message is sent. The valid ranges are
             4 to 15 seconds for ANSI and 15 to 60 seconds for ITU."
    DEFVAL          { 10 }
    ::= { sonusSs7NodeProfileEntry 26 }

sonusSs7TimerT21 OBJECT-TYPE
    SYNTAX          Integer32 (60..900)
    MAX-ACCESS      read-write
    STATUS          current
    DESCRIPTION     
            "The Timer T21 is started when initial group blocking message is sent. The 
             valid values are 60 seconds for ANSI and 300 to 900 seconds for ITU."
    DEFVAL          { 60 }
    ::= { sonusSs7NodeProfileEntry 27 }

sonusSs7TimerT22 OBJECT-TYPE
    SYNTAX          Integer32 (4..60)
    MAX-ACCESS      read-write
    STATUS          current
    DESCRIPTION     
            "The Timer T22 is started when circuit group reset message is sent. The valid values are
             4 to 15 seconds for ANSI and 15 to 60 seconds for ITU."
    DEFVAL          { 10 }
    ::= { sonusSs7NodeProfileEntry 28 }

sonusSs7TimerT23 OBJECT-TYPE
    SYNTAX          Integer32 (60..900)
    MAX-ACCESS      read-write
    STATUS          current
    DESCRIPTION     
            "The Timer T23 is started when initial group reset message is sent. The valid values
             are 60 seconds for the ANSI and 300 to 900 seconds for the ITU."
    DEFVAL          { 60 }
    ::= { sonusSs7NodeProfileEntry 29 }

sonusSs7TimerT24 OBJECT-TYPE
    SYNTAX          Integer32 (1..2)
    MAX-ACCESS      read-write
    STATUS          current
    DESCRIPTION     
            "The Timer T24 is started when check tone is sent. The value is less
             than 2 seconds."
    DEFVAL          { 1 }
    ::= { sonusSs7NodeProfileEntry 30 }

sonusSs7TimerT25 OBJECT-TYPE
    SYNTAX          Integer32 (1..10)
    MAX-ACCESS      read-write
    STATUS          current
    DESCRIPTION     
            "The Timer T25 is started when initial continuity check failure is 
             detected. The range is 1 to 10 seconds."
    DEFVAL          { 5 }
    ::= { sonusSs7NodeProfileEntry 31 }

sonusSs7TimerT26 OBJECT-TYPE
    SYNTAX          Integer32 (60..180)
    MAX-ACCESS      read-write
    STATUS          current
    DESCRIPTION     
            "The Timer T26 is started when a second or subsequent continuity failure is detected.
             The valid value are 60 to 180 seconds."
    DEFVAL          { 120 }
    ::= { sonusSs7NodeProfileEntry 32 }

sonusSs7TimerT27 OBJECT-TYPE
    SYNTAX          Integer32 (180..36000)
    MAX-ACCESS      read-write
    STATUS          current
    DESCRIPTION     
            "The Timer T27 is started when a continuity fail message is recieved. The valid values are
             more than 180 seconds for ANSI and 240 seconds for ITU. "
    DEFVAL          { 240 }
    ::= { sonusSs7NodeProfileEntry 33 }

sonusSs7TimerT28 OBJECT-TYPE
    SYNTAX          Integer32 (5..12)
    MAX-ACCESS      read-write
    STATUS          current
    DESCRIPTION     
            "The Timer T28 is started when Circuit Query Message is sent. The valid value is 10 seconds."
    DEFVAL          { 10 }
    ::= { sonusSs7NodeProfileEntry 34 }

sonusSs7TimerT29 OBJECT-TYPE
    SYNTAX          Integer32 (300..600)
    MAX-ACCESS      read-write
    STATUS          current
    DESCRIPTION     
            "The Timer T29 is started when Congestion indication is received when T29
             is not running. The valid range is 300 to 600 milli second. This timer has
             no relevence for ANSI."
    ::= { sonusSs7NodeProfileEntry 35 }

sonusSs7TimerT30 OBJECT-TYPE
    SYNTAX          Integer32 (5..10)
    MAX-ACCESS      read-write
    STATUS          current
    DESCRIPTION     
            "The Timer T30 is stared when congestion indication is recieved when T29 is not running. The valid 
             range is 5 to 10 seconds for the ITU. This timer has no relevence under ANSI."
    ::= { sonusSs7NodeProfileEntry 36 }

sonusSs7TimerT31 OBJECT-TYPE
    SYNTAX          Integer32 (360..65520)
    MAX-ACCESS      read-write
    STATUS          current
    DESCRIPTION     
            "The Timer T31 is started on release of ISUP signalling connection based on
             CO SCCP. The value should be set to greater than 360 seconds"
    DEFVAL          { 420 }
    ::= { sonusSs7NodeProfileEntry 37 }

sonusSs7TimerT32 OBJECT-TYPE
    SYNTAX          Integer32 (3..5)
    MAX-ACCESS      read-write
    STATUS          current
    DESCRIPTION     
            "The Timer T32 is started when the first end-to-end message is recived. Under ANSI this
             timer is started after the response to such a message is sent. The valid values are 3 
             to 5 seconds. "
    DEFVAL          { 4 }
    ::= { sonusSs7NodeProfileEntry 38 }

sonusSs7TimerT33 OBJECT-TYPE
    SYNTAX          Integer32 (12..15)
    MAX-ACCESS      read-write
    STATUS          current
    DESCRIPTION     
            "The Timer T33 is started when Information Request Message is sent. The 
             valid range is 12 to 15 seconds."
    DEFVAL          { 14 }
    ::= { sonusSs7NodeProfileEntry 39 }

sonusSs7TimerT34 OBJECT-TYPE
    SYNTAX          Integer32 (2..15)
    MAX-ACCESS      read-write
    STATUS          current
    DESCRIPTION     
            "The Timer T34 is started when Loop Back Acknowledgement is sent under ANSI.
             The Timer T34 is started when segmentation is received for IAM, ACM, CPG,
             ANM or CON under ITU. The valid range for ANSI is 10 to 15 seconds. The valid
             range for ITU is 2 to 4 seconds."
    ::= { sonusSs7NodeProfileEntry 40 }

sonusSs7TimerT35 OBJECT-TYPE
    SYNTAX          Integer32 (15..20)
    MAX-ACCESS      read-write
    STATUS          current
    DESCRIPTION     
            "The Timer T35 is started when the last digit recieved is not an ST digit or
             the fixed number of digits have been recieved. This procedure is only valid
             for overlap hence ITU. This timer has no relevence in ANSI."
    DEFVAL          { 18 }
    ::= { sonusSs7NodeProfileEntry 41 }

sonusSs7TimerT36 OBJECT-TYPE
    SYNTAX          Integer32 (2..15)
    MAX-ACCESS      read-write
    STATUS          current
    DESCRIPTION     
            "The Timer T36 is started when IAM is recived with a segmentation indication for ANSI.
             This timer is started when transit or incoming international exchange recieves Continuity check
             request message. The valid range for ANSI is 2 to 4 seconds and 10 to 15 
             seconds for ITU. "
    ::= { sonusSs7NodeProfileEntry 42 }

sonusSs7TimerT37 OBJECT-TYPE
    SYNTAX          Integer32 (2..30)
    MAX-ACCESS      read-write
    STATUS          current
    DESCRIPTION     
            "The Timer T37 is started when User Part Availability test is started under ANSI. This
             timer is started when a request for and Echo control device is sent to another exchange
             under ITU. The valid value for ANSI is 30 seconds and for ITU is 2 to 4 seconds."
    ::= { sonusSs7NodeProfileEntry 43 }

sonusSs7TimerT38 OBJECT-TYPE
    SYNTAX          Integer32 (10..60)
    MAX-ACCESS      read-write
    STATUS          current
    DESCRIPTION     
            "The Timer T38 is started when a suspend message is sent to the preceding switch. This timer
             is only relevent under ITU."
    DEFVAL          { 30 }
    ::= { sonusSs7NodeProfileEntry 44 }

sonusSs7TimerT39 OBJECT-TYPE
    SYNTAX          Integer32 (1..65535)
    MAX-ACCESS      read-write
    STATUS          current
    DESCRIPTION     
            "The Timer T39 is started when MCID request is sent. It is only relevent in the ITU."
    ::= { sonusSs7NodeProfileEntry 45 }

sonusSs7TimerT40 OBJECT-TYPE
    SYNTAX          Integer32 (1..65535)
    MAX-ACCESS      read-write
    STATUS          current
    DESCRIPTION     
            "The Timer T40 could be changed from its default using this entry."
    ::= { sonusSs7NodeProfileEntry 46 }

sonusSs7TimerTAcc OBJECT-TYPE
    SYNTAX          Integer32 (3..8)
    MAX-ACCESS      read-write
    STATUS          current
    DESCRIPTION     
            "Automatic Congestion Control Timer as per ANSI T1.113.4 - 1995. The value
             of the timer is 5 Seconds."
    DEFVAL          { 5 }
    ::= { sonusSs7NodeProfileEntry 47 }

sonusSs7TimerTCcr OBJECT-TYPE
    SYNTAX          Integer32 (1..3)
    MAX-ACCESS      read-write
    STATUS          current
    DESCRIPTION     
            "Continuity Check Request Timer. The value As per ANSI T1.113.4 - 1995 is 2 Seconds."
    DEFVAL          { 2 }
    ::= { sonusSs7NodeProfileEntry 48 }

sonusSs7TimerTCcrr OBJECT-TYPE
    SYNTAX          Integer32 (16..31)
    MAX-ACCESS      read-write
    STATUS          current
    DESCRIPTION     
            "Continuity Check Failed Recived. The value as per ANSI T1.113.4 - 1995 is 20 Seconds."
    DEFVAL          { 20 }
    ::= { sonusSs7NodeProfileEntry 49 }

sonusSs7TimerTCgb OBJECT-TYPE
    SYNTAX          Integer32 (3..8)
    MAX-ACCESS      read-write
    STATUS          current
    DESCRIPTION     
            "Timer started on recipt of a Circuit Group Block Message. The value as per
             ANSI T1.113.4 - 1995 is 5 Seconds."
    DEFVAL          { 5 }
    ::= { sonusSs7NodeProfileEntry 50 }

sonusSs7TimerTCra OBJECT-TYPE
    SYNTAX          Integer32 (16..31)
    MAX-ACCESS      read-write
    STATUS          current
    DESCRIPTION     
            "Timer started when Circuit Reservation Acknowledgment is sent. The time value
             as per ANSI T1.113.4 - 1995 is 20 seconds."
    DEFVAL          { 20 }
    ::= { sonusSs7NodeProfileEntry 51 }

sonusSs7TimerTCrm OBJECT-TYPE
    SYNTAX          Integer32 (3..4)
    MAX-ACCESS      read-write
    STATUS          current
    DESCRIPTION     
            "This timer is started when the circuit reservation message is sent. The value 
             as per ANSI T1.113.4 - 1995 is 3 - 4 Seconds. The default is set to 4 seconds."
    DEFVAL          { 4 }
    ::= { sonusSs7NodeProfileEntry 52 }

sonusSs7TimerTCvt OBJECT-TYPE
    SYNTAX          Integer32 (5..12)
    MAX-ACCESS      read-write
    STATUS          current
    DESCRIPTION     
            "The Timer T CVT is started when the Circuit Validation Test message
             is sent. This message is only valid for ANSI."
    DEFVAL          { 10 }
    ::= { sonusSs7NodeProfileEntry 53 }

sonusSs7TimerTExm OBJECT-TYPE
    SYNTAX          Integer32 (1..65535)
    MAX-ACCESS      read-write
    STATUS          current
    DESCRIPTION     
            "The Timer Exm,d is started when IAM is sent to the succeeding network. This
             timer has no relevence in the ITU. This timer is in milliseconds."
    ::= { sonusSs7NodeProfileEntry 54 }

sonusSs7TimerTGrs OBJECT-TYPE
    SYNTAX          Integer32 (3..8)
    MAX-ACCESS      read-write
    STATUS          current
    DESCRIPTION     
            "This timer is started when a circuit group reset message is received. 
             This timer is only relevent in the ANSI network. "
    DEFVAL          { 5 }
    ::= { sonusSs7NodeProfileEntry 55 }

sonusSs7TimerTHga OBJECT-TYPE
    SYNTAX          Integer32 (0..300)
    MAX-ACCESS      read-write
    STATUS          current
    DESCRIPTION     
            "This timer is started on recognition of carrier loss. It is only relevent in ANSI
             network. The valid range is 0 to 300 seconds."
    DEFVAL          { 150 }
    ::= { sonusSs7NodeProfileEntry 56 }

sonusSs7TimerTScga OBJECT-TYPE
    SYNTAX          Integer32 (0..120)
    MAX-ACCESS      read-write
    STATUS          current
    DESCRIPTION     
            "This timer is started when initial demand continuity check fails in the
             SCGA group. The valid range for this timer is 0 to 120 seconds."
    DEFVAL          { 60 }
    ::= { sonusSs7NodeProfileEntry 57 }

sonusSs7TimerTScgad OBJECT-TYPE
    SYNTAX          Integer32 (5..120)
    MAX-ACCESS      read-write
    STATUS          current
    DESCRIPTION     
            "This timer is started failure of demand continuity check in the SCGA group."
    DEFVAL          { 65 }
    ::= { sonusSs7NodeProfileEntry 58 }

sonusSs7NodeProfileState OBJECT-TYPE
    SYNTAX          INTEGER { disabled(1), enabled(2) }
    MAX-ACCESS      read-write
    STATUS          current
    DESCRIPTION     
            "The administrative state of this object."
    DEFVAL          { disabled }
    ::= { sonusSs7NodeProfileEntry 59 }

sonusSs7NodeProfileRowStatus OBJECT-TYPE
    SYNTAX          RowStatus
    MAX-ACCESS      read-write
    STATUS          current
    DESCRIPTION     
            ""
    ::= { sonusSs7NodeProfileEntry 60 }

sonusSs7NodeProfileNetworkInd OBJECT-TYPE
    SYNTAX          INTEGER { intl0(1), intl1(2), natl0(3), natl1(4) }
    MAX-ACCESS      read-write
    STATUS          current
    DESCRIPTION     
            "The setting of the Network Indicator used for this SS7 Node entry."
    DEFVAL          { natl0 }
    ::= { sonusSs7NodeProfileEntry 61 }

sonusSs7SlsBits OBJECT-TYPE
    SYNTAX          Integer32 (4..8)
    MAX-ACCESS      read-write
    STATUS          current
    DESCRIPTION     
            "The number of SLS bits to use"
    DEFVAL          { 5 }
    ::= { sonusSs7NodeProfileEntry 62 }

sonusSs7TimerTA OBJECT-TYPE
    SYNTAX          Integer32 (0..1000)
    MAX-ACCESS      read-write
    STATUS          current
    DESCRIPTION     
            "The Bellcore specific timer TA is started when a RLC message is sent by the switch.
             The value of this timer is 0 to 1000 milliseconds."
    DEFVAL          { 500 }
    ::= { sonusSs7NodeProfileEntry 63 }

sonusSs7TimerTBlom OBJECT-TYPE
    SYNTAX          Integer32 (240..360)
    MAX-ACCESS      read-write
    STATUS          current
    DESCRIPTION     
            "The Bellcore specific timer TBlom is started when blocking a circuit due to a
             BLO, and after any call is released; used to notify maintenance."
    DEFVAL          { 300 }
    ::= { sonusSs7NodeProfileEntry 64 }

sonusSs7TimerTCotd OBJECT-TYPE
    SYNTAX          Integer32 (0..500)
    MAX-ACCESS      read-write
    STATUS          current
    DESCRIPTION     
            "The Bellcore specific timer TCOTd is started when sending IAM requesting
             continuity check. The value of this timer is in milliseconds."
    DEFVAL          { 250 }
    ::= { sonusSs7NodeProfileEntry 65 }

sonusSs7TimerTCotl OBJECT-TYPE
    SYNTAX          Integer32 (240..300)
    MAX-ACCESS      read-write
    STATUS          current
    DESCRIPTION     
            "The Bellcore specific timer TCOTl is started when receiving second COT
             coded failed, awaiting receipt of CCR."
    DEFVAL          { 300 }
    ::= { sonusSs7NodeProfileEntry 66 }

sonusSs7TimerTSus OBJECT-TYPE
    SYNTAX          Integer32 (14..16)
    MAX-ACCESS      read-write
    STATUS          current
    DESCRIPTION     
            "The Bellcore specific timer TSUS is started when a SUS message is sent by the
             terminating switch, awaiting called party off-hook or REL."
    DEFVAL          { 15 }
    ::= { sonusSs7NodeProfileEntry 67 }

sonusSs7ServicesMIBNotifications OBJECT IDENTIFIER
    ::= { sonusSs7ServicesMIB 2 }

sonusSs7ServicesMIBNotificationsPrefix OBJECT IDENTIFIER
    ::= { sonusSs7ServicesMIBNotifications 0 }

sonusSs7ServicesMIBNotificationsObjects OBJECT IDENTIFIER
    ::= { sonusSs7ServicesMIBNotifications 1 }

sonusSs7NodeServiceType OBJECT-TYPE
    SYNTAX          DisplayString (SIZE(1..6))
    MAX-ACCESS      read-only
    STATUS          current
    DESCRIPTION     
            "The type of service supported by this SS7 node connection (ISUP or TCAP)."
    ::= { sonusSs7ServicesMIBNotificationsObjects 1 }

sonusSs7NodeStateChangeReason OBJECT-TYPE
    SYNTAX          DisplayString (SIZE(1..101))
    MAX-ACCESS      read-only
    STATUS          current
    DESCRIPTION     
            "The reason why this SS7 node connection has  changed state."
    ::= { sonusSs7ServicesMIBNotificationsObjects 2 }

sonusSs7NodeCurrentState OBJECT-TYPE
    SYNTAX          INTEGER { offline(1), active(2), initializing(3), 
                        failed(4), disabled(5), congested(6) }
    MAX-ACCESS      read-only
    STATUS          current
    DESCRIPTION     
            "The current state of this SS7 node connection."
    ::= { sonusSs7ServicesMIBNotificationsObjects 3 }

sonusSs7NodeAffectedPointCode OBJECT-TYPE
    SYNTAX          PointCode
    MAX-ACCESS      read-only
    STATUS          current
    DESCRIPTION     
            "The SS7 point code affected by this MTP state change."
    ::= { sonusSs7ServicesMIBNotificationsObjects 4 }

sonusSs7NodeConnectionEstablishedNotification NOTIFICATION-TYPE
    OBJECTS         { sonusSs7NodeName, sonusSs7NodeGatewayAssignment, 
                      sonusSs7NodeServiceType, sonusEventDescription, 
                      sonusEventClass, sonusEventLevel }
    STATUS          current
    DESCRIPTION     
            "This trap indicates that a connection has been established to the
             specified SS7 gateway. Information provided by this trap includes
             the name of the connected SS7 node, the name of the SS7 gateway 
             on which the node resides, and the type of SS7 service that has been
             established (ISUP or TCAP)."
    ::= { sonusSs7ServicesMIBNotificationsPrefix 1 }

sonusSs7NodeConnectionFailedNotification NOTIFICATION-TYPE
    OBJECTS         { sonusSs7NodeName, sonusSs7NodeGatewayAssignment, 
                      sonusSs7NodeServiceType, 
                      sonusSs7NodeStateChangeReason, 
                      sonusEventDescription, sonusEventClass, 
                      sonusEventLevel }
    STATUS          current
    DESCRIPTION     
            "This trap indicates that an established connection to an SS7 gateway
             has failed. Information provided by this trap includes the name of the
             failed SS7 node, the name of the SS7 gateway on which the node resides,
             the type of SS7 service affected by this failure, and the reason why
             the connection has failed."
    ::= { sonusSs7ServicesMIBNotificationsPrefix 2 }

sonusSs7NodeConnectionStateChangeNotification NOTIFICATION-TYPE
    OBJECTS         { sonusSs7NodeName, sonusSs7NodeGatewayAssignment, 
                      sonusSs7NodeServiceType, sonusSs7NodeCurrentState, 
                      sonusSs7NodeStateChangeReason, 
                      sonusEventDescription, sonusEventClass, 
                      sonusEventLevel }
    STATUS          current
    DESCRIPTION     
            "This trap indicates that an established connection to an SS7 gateway
             has changed state. Information provided by this trap includes the name 
             of the affected SS7 node, the name of the SS7 gateway on which the node 
             resides, the type of SS7 service affected by this failure, the new state
             of the node, and the reason for the state change."
    ::= { sonusSs7ServicesMIBNotificationsPrefix 3 }

sonusSs7NodeMtpStateChangeNotification NOTIFICATION-TYPE
    OBJECTS         { sonusSs7NodeName, sonusSs7NodeGatewayAssignment, 
                      sonusSs7NodeServiceType, sonusSs7NodeMtpStatus, 
                      sonusSs7NodeAffectedPointCode, 
                      sonusEventDescription, sonusEventClass, 
                      sonusEventLevel }
    STATUS          current
    DESCRIPTION     
            "This trap indicates that a MTP state change event has been received from the
             SS7 gateway, affecting the specified destination (or remote) point 
             code (DPC). Information provided by this trap includes the name 
             of the affected SS7 node, the name of the SS7 gateway on which the node 
             resides, the updated MTP state, and the DPC affected by this event."
    ::= { sonusSs7ServicesMIBNotificationsPrefix 4 }

END -- end of module SONUS-SS7-SERVICES-MIB.
