PERIBIT-SR-MIB DEFINITIONS ::= BEGIN

	IMPORTS
		MODULE-IDENTITY, OBJECT-IDENTITY,
		OBJECT-TYPE, NOTIFICATION-TYPE,
		Integer32, Unsigned32, Gauge32, Counter64, IpAddress
			FROM SNMPv2-SMI
--		MODULE-COMPLIANCE, OBJECT-GROUP
--			FROM SNMPv2-CONF
		TimeStamp
			FROM SNMPv2-TC
		pnModules, pnSpecificMib
			FROM PERIBIT-GLOBAL-REG
		TcAppName
			FROM PERIBIT-GLOBAL-TC
		pnCommonEventDescr 
			FROM PERIBIT-COMMON-MIB;

	pnSrMibModule MODULE-IDENTITY
		LAST-UPDATED			"200203280000Z"
		ORGANIZATION			"Peribit Networks, Inc"
		CONTACT-INFO			"
					Customer Support
					Peribit Networks, Inc.
					2300 Central Expressway
					Santa Clara, CA 95050

					+1 866-PERIBIT
					support@peribit.com"

		DESCRIPTION				"
			A MIB module containing definitions of managed objects
			for Peribit Networks' Sequence Reducer family of products."

		REVISION				"200405240000Z"
		DESCRIPTION				"
			Add pnSrEventMultiPathStatusChange notification."

		REVISION				"200306230000Z"
		DESCRIPTION				"
			o Add reducer and throughput statistics
			  to the pnSrSysStats group.
			o Add bytes counts to pnSrAsmStatsTable.
			o Add bytes counts and bytes-in percentage
			  to pnSrAppStatsTable.
			o Add pnSrAppAggrStatsTable."

		REVISION				"200203280000Z"
		DESCRIPTION				"
			Add SessionOpened, RegServerUnreachable notifications."

		REVISION				"200203270000Z"
		DESCRIPTION				"
			Add SessionClosed, BufferOverflow notifications."

		REVISION				"200112191200Z"
		DESCRIPTION				"
			Rev 1.0
			Initial version of MIB module PERIBIT-SR-MIB."

		::= { pnModules 4 }

	pnSrMib OBJECT-IDENTITY
		STATUS					current
		DESCRIPTION				"
			Sub-tree for Sequence Reducer MIB."
		::= { pnSpecificMib 1 }

	pnSrConfMib OBJECT-IDENTITY
		STATUS					current
		DESCRIPTION				"
			Sub-tree for Sequence Reducer MIB conformance statements."
		::= { pnSrMib 1 }

	pnSrObjs OBJECT-IDENTITY
		STATUS					current
		DESCRIPTION				"
			Sub-tree for Sequence Reducer MIB objects."
		::= { pnSrMib 2 }

	pnSrEvents OBJECT-IDENTITY
		STATUS					current
		DESCRIPTION				"
			Sub-tree for Sequence Reducer MIB events."
		::= { pnSrMib 3 }

	----------------------------------------------------------------------
	-- Stats update time

	pnSrStatsUpdateTime OBJECT-TYPE
		SYNTAX  TimeStamp
		MAX-ACCESS  read-only
		STATUS  current
		DESCRIPTION
			"This is the value of sysUpTime when the SR stats (pnSrSysStats,
			pnSrAsm, pnSrApp) were last updated. The management station
			can use this information to tell if it's downloading a consistent set
			of stats."
		::= { pnSrObjs 1 }

	pnSrStatsAsmCount OBJECT-TYPE
		SYNTAX      Integer32
		MAX-ACCESS  read-only
		STATUS      current
		DESCRIPTION
			"The number of Assemblers this Reducer has had a session
			with at any time during the last two months."
		::= { pnSrObjs 2 }

	pnSrStatsAppCount OBJECT-TYPE
		SYNTAX      Integer32
		MAX-ACCESS  read-only
		STATUS      current
		DESCRIPTION
			"The number of applications currently being monitored on this Reducer."
		::= { pnSrObjs 3 }

	----------------------------------------------------------------------
	-- The Peribit System group

	pnSrSysStats OBJECT-IDENTITY
		STATUS					current
		DESCRIPTION				"
			Sub-tree for Sequence Reducer system statistics."
	::= { pnSrObjs 4 }

	-- Assembler stats

	pnSrSysStatsBytesInAe OBJECT-TYPE
		SYNTAX  Counter64
		MAX-ACCESS  read-only
		STATUS  current
		DESCRIPTION
			"Total number of bytes that entered the SR Assembly Engine
			since the system was started."
		::= { pnSrSysStats 1 }

	pnSrSysStatsBytesOutAe OBJECT-TYPE
		SYNTAX  Counter64
		MAX-ACCESS  read-only
		STATUS  current
		DESCRIPTION
			"Total number of bytes that exited the SR Assembly Engine
			after assembly since the system was started."
		::= { pnSrSysStats 2 }

	pnSrSysStatsPktsInAe OBJECT-TYPE
		SYNTAX  Counter64
		MAX-ACCESS  read-only
		STATUS  current
		DESCRIPTION
			"Total number of packets that entered the SR Assembly Engine
			since the system was started."
		::= { pnSrSysStats 3 }

	pnSrSysStatsPktsOutAe OBJECT-TYPE
		SYNTAX  Counter64
		MAX-ACCESS  read-only
		STATUS  current
		DESCRIPTION
			"Total number of packets that exited the SR Assembly Engine
			after assembly since the system was started."
		::= { pnSrSysStats 4 }

	-- Out-of-band stats

	pnSrSysStatsBytesOutOob OBJECT-TYPE
		SYNTAX  Counter64
		MAX-ACCESS  read-only
		STATUS  current
		DESCRIPTION
			"Total number of out-of-band bytes sent to the control channel
			since the system was started."
		::= { pnSrSysStats 5 }

	-- Pass-through stats

	pnSrSysStatsBytesPtNoAe OBJECT-TYPE
		SYNTAX  Counter64
		MAX-ACCESS  read-only
		STATUS  current
		DESCRIPTION
			"Total number of bytes that passed through the SR Reduction Engine
			because there was no corresponding Assembly Engine SR, since the
			system was started."
		::= { pnSrSysStats 6 }

	pnSrSysStatsPktsPtNoAe OBJECT-TYPE
		SYNTAX  Counter64
		MAX-ACCESS  read-only
		STATUS  current
		DESCRIPTION
			"Total number of packets that passed through the SR Reduction Engine
			because there was no corresponding Assembly Engine SR, since the
			system was started."
		::= { pnSrSysStats 7 }

	pnSrSysStatsBytesPtFilter OBJECT-TYPE
		SYNTAX  Counter64
		MAX-ACCESS  read-only
		STATUS  current
		DESCRIPTION
			"Total number of bytes that passed through the SR Reduction Engine
			due to a manually configured filter (such as an application
			filter), since the system was started."
		::= { pnSrSysStats 8 }

	pnSrSysStatsPktsPtFilter OBJECT-TYPE
		SYNTAX  Counter64
		MAX-ACCESS  read-only
		STATUS  current
		DESCRIPTION
			"Total number of packets that passed through the SR Reduction Engine
			due to a manually configured filter (such as an application
			filter), since the system was started."
		::= { pnSrSysStats 9 }

	pnSrSysStatsBytesOfPt OBJECT-TYPE
		SYNTAX  Counter64
		MAX-ACCESS  read-only
		STATUS  current
		DESCRIPTION
			"Total number of bytes that passed through the SR Reduction Engine
			due to device buffer overflow, since the system was started."
		::= { pnSrSysStats 10 }

	pnSrSysStatsPktsOfPt OBJECT-TYPE
		SYNTAX  Counter64
		MAX-ACCESS  read-only
		STATUS  current
		DESCRIPTION
			"Total number of packets that passed through the SR Reduction Engine
			due to device buffer overflow, since the system was started."
		::= { pnSrSysStats 11 }

	-- Peak stats

	pnSrSysStatsBytesTpIn OBJECT-TYPE
		SYNTAX  Counter64
		MAX-ACCESS  read-only
		STATUS  current
		DESCRIPTION
			"The number of bytes into the SR Reduction Engine at the peak
			five-second interval of data input, since the system was started."
		::= { pnSrSysStats 12 }

	pnSrSysStatsPktsTpIn OBJECT-TYPE
		SYNTAX  Counter64
		MAX-ACCESS  read-only
		STATUS  current
		DESCRIPTION
			"The number of packets into the SR Reduction Engine at the peak
			five-second interval of data input, since the system was started."
		::= { pnSrSysStats 13 }

	pnSrSysStatsBytesTpOut OBJECT-TYPE
		SYNTAX  Counter64
		MAX-ACCESS  read-only
		STATUS  current
		DESCRIPTION
			"The number of bytes out of the SR Reduction Engine at the peak
			five-second interval of data input, since the system was started."
		::= { pnSrSysStats 14 }

	pnSrSysStatsPktsTpOut OBJECT-TYPE
		SYNTAX  Counter64
		MAX-ACCESS  read-only
		STATUS  current
		DESCRIPTION
			"The number of packets out of the SR Reduction Engine at the peak
			five-second interval of data input, since the system was started."
		::= { pnSrSysStats 15 }

	pnSrSysStatsBytesTpPt OBJECT-TYPE
		SYNTAX  Counter64
		MAX-ACCESS  read-only
		STATUS  current
		DESCRIPTION
			"The number of bytes that passed through the SR Reduction Engine
			at the peak five-second interval of data input, since the system
			was started."
		::= { pnSrSysStats 16 }

	pnSrSysStatsPktsTpPt OBJECT-TYPE
		SYNTAX  Counter64
		MAX-ACCESS  read-only
		STATUS  current
		DESCRIPTION
			"The number of packets that passed through the SR Reduction Engine
			at the peak five-second interval of data input, since the system
			was started."
		::= { pnSrSysStats 17 }

	pnSrSysStatsPeakRdn OBJECT-TYPE
		SYNTAX  Unsigned32
		MAX-ACCESS  read-only
		STATUS  current
		DESCRIPTION
			"The maximum data reduction rate for a five second interval
			in the last minute.

			The value returned is (percentage * 1000). Applications should
			divide the returned value by 1000."
		::= { pnSrSysStats 18 }

	-- Througput stats

	pnSrSysStatsThruputIn OBJECT-TYPE
		SYNTAX  Gauge32
		MAX-ACCESS  read-only
		STATUS  current
		DESCRIPTION
			"Average throughput of incoming data in Kbps since the
			system was started."
		::= { pnSrSysStats 19 }

	pnSrSysStatsThruputOut OBJECT-TYPE
		SYNTAX  Gauge32
		MAX-ACCESS  read-only
		STATUS  current
		DESCRIPTION
			"Average throughput of outgoing data in Kbps since the
			system was started."
		::= { pnSrSysStats 20 }

	-- Reducer stats

	pnSrSysStatsBytesInRe OBJECT-TYPE
		SYNTAX  Counter64
		MAX-ACCESS  read-only
		STATUS  current
		DESCRIPTION
			"Total number of bytes that entered the SR Reduction Engine
			since the system was started."
		::= { pnSrSysStats 21 }

	pnSrSysStatsBytesOutRe OBJECT-TYPE
		SYNTAX  Counter64
		MAX-ACCESS  read-only
		STATUS  current
		DESCRIPTION
			"Total number of bytes that exited the SR Reduction Engine
			after reduction since the system was started."
		::= { pnSrSysStats 22 }

	pnSrSysStatsPktsInRe OBJECT-TYPE
		SYNTAX  Counter64
		MAX-ACCESS  read-only
		STATUS  current
		DESCRIPTION
			"Total number of packets that entered the SR Reduction Engine
			since the system was started."
		::= { pnSrSysStats 23 }

	pnSrSysStatsPktsOutRe OBJECT-TYPE
		SYNTAX  Counter64
		MAX-ACCESS  read-only
		STATUS  current
		DESCRIPTION
			"Total number of packets that exited the SR Reduction Engine
			after reduction since the system was started."
		::= { pnSrSysStats 24 }

	----------------------------------------------------------------------
	-- Information maintained by a Reducer about each Assembler it has
	-- a session with.

	pnSrAsm OBJECT-IDENTITY
		STATUS					current
		DESCRIPTION				"
			Information maintained by a Reducer for each Assembler it has
			a session with."
		::= { pnSrObjs 5 }

	pnSrAsmTable OBJECT-TYPE
		SYNTAX  SEQUENCE OF PeribitSrAsmEntry
		MAX-ACCESS  not-accessible
		STATUS  current
		DESCRIPTION
			"List of Assemblers the Reducer has sessions with."
		::= { pnSrAsm 1 }

	pnSrAsmEntry OBJECT-TYPE
		SYNTAX  PeribitSrAsmEntry
		MAX-ACCESS  not-accessible
		STATUS  current
		DESCRIPTION
			"A row in pnSrAsmTable."
		INDEX   { pnSrAsmIndex }
		::= { pnSrAsmTable 1 }

	PeribitSrAsmEntry ::=
		SEQUENCE
		{
			pnSrAsmIndex
				Integer32,
			pnSrAsmIpAddress
				IpAddress
		}

	pnSrAsmIndex OBJECT-TYPE
		SYNTAX  Integer32
		MAX-ACCESS not-accessible
		STATUS  current
		DESCRIPTION
			"This row's number, with range (1..pnSrStatsAsmCount)."
		::= { pnSrAsmEntry 1 }

	pnSrAsmIpAddress OBJECT-TYPE
		SYNTAX  IpAddress
		MAX-ACCESS  read-only
		STATUS  current
		DESCRIPTION
			"The IP address of the Assembler." 
		::= { pnSrAsmEntry 2 }

	----------------------------------------------------------------------
	-- Stats maintained by a Reducer for each Assembler it has
	-- a session with.

	pnSrAsmStatsTable OBJECT-TYPE
		SYNTAX  SEQUENCE OF PeribitSrAsmStatsEntry
		MAX-ACCESS  not-accessible
		STATUS  current
		DESCRIPTION
			"Statistics maintained by a Reducer for each Assembler it has
			a session with."
		::= { pnSrAsm 2 }

	pnSrAsmStatsEntry OBJECT-TYPE
		SYNTAX  PeribitSrAsmStatsEntry
		MAX-ACCESS  not-accessible
		STATUS  current
		DESCRIPTION
			"A row in pnSrAsmStatsTable."
		AUGMENTS   { pnSrAsmEntry }
		::= { pnSrAsmStatsTable 1 }

	PeribitSrAsmStatsEntry ::=
		SEQUENCE
		{
			pnSrAsmStatsPktsIn
				Counter64,
			pnSrAsmStatsPktsOut
				Counter64,
			pnSrAsmStatsBytesIn
				Counter64,
			pnSrAsmStatsBytesOut
				Counter64
		}

	pnSrAsmStatsPktsIn OBJECT-TYPE
		SYNTAX  Counter64
		MAX-ACCESS  read-only
		STATUS  current
		DESCRIPTION
			"The total number of packets into this SR, since
			the system was started, that were identified for
			reduction and addressed to the SR whose IP address
			is in the row in pnSrAsmTable that matches
			this row."

		::= { pnSrAsmStatsEntry 1 }

	pnSrAsmStatsPktsOut OBJECT-TYPE
		SYNTAX  Counter64
		MAX-ACCESS  read-only
		STATUS  current
		DESCRIPTION
			"The total number of packets out of this SR, since
			the system was started, that were identified for
			reduction and addressed to the SR whose IP address
			is in the row in pnSrAsmTable that matches
			this row."
		::= { pnSrAsmStatsEntry 2 }

	pnSrAsmStatsBytesIn OBJECT-TYPE
		SYNTAX  Counter64
		MAX-ACCESS  read-only
		STATUS  current
		DESCRIPTION
			"The total number of bytes into this SR, since
			the system was started, that were identified for
			reduction and addressed to the SR whose IP address
			is in the row in pnSrAsmTable that matches
			this row."
		::= { pnSrAsmStatsEntry 3 }

	pnSrAsmStatsBytesOut OBJECT-TYPE
		SYNTAX  Counter64
		MAX-ACCESS  read-only
		STATUS  current
		DESCRIPTION
			"The total number of bytes out of this SR, since
			the system was started, that were identified for
			reduction and addressed to the SR whose IP address
			is in the row in pnSrAsmTable that matches
			this row."
		::= { pnSrAsmStatsEntry 4 }

	----------------------------------------------------------------------
	-- Application information maintained by a Reducer

	pnSrApp OBJECT-IDENTITY
		STATUS					current
		DESCRIPTION				"
			Information maintained by a Reducer for each application
			that is monitored."
	::= { pnSrObjs 6 }

	pnSrAppTable OBJECT-TYPE
		SYNTAX  SEQUENCE OF PeribitSrAppEntry
		MAX-ACCESS  not-accessible
		STATUS  current
		DESCRIPTION
			"List of applications currently monitored."
		::= { pnSrApp 1 }

	pnSrAppEntry OBJECT-TYPE
		SYNTAX  PeribitSrAppEntry
		MAX-ACCESS  not-accessible
		STATUS  current
		DESCRIPTION
			"A row in pnSrAppTable."
		INDEX   { pnSrAppIndex }
		::= { pnSrAppTable 1 }

	PeribitSrAppEntry ::=
		SEQUENCE
		{
			pnSrAppIndex
				Integer32,
			pnSrAppAppName
				TcAppName
		}

	pnSrAppIndex OBJECT-TYPE
		SYNTAX  Integer32
		MAX-ACCESS not-accessible
		STATUS  current
		DESCRIPTION
			"This row's number, with range (1..pnSrStatsAppCount)."
		::= { pnSrAppEntry 1 }

	pnSrAppAppName OBJECT-TYPE
		SYNTAX  TcAppName
		MAX-ACCESS  read-only
		STATUS  current
		DESCRIPTION
			"The name of the application from which the data was
			received (e.g., FTP, HTTP, Lotus Notes)."
		::= { pnSrAppEntry 2 }

	----------------------------------------------------------------------
	-- Application stats maintained by a Reducer for each Assembler
	-- it has a session with.

	pnSrAppStatsTable OBJECT-TYPE
		SYNTAX  SEQUENCE OF PeribitSrAppStatsEntry
		MAX-ACCESS  not-accessible
		STATUS  current
		DESCRIPTION
			"Statistics maintained by a Reducer for each application
			that is monitored."
		::= { pnSrApp 2 }

	pnSrAppStatsEntry OBJECT-TYPE
		SYNTAX  PeribitSrAppStatsEntry
		MAX-ACCESS  not-accessible
		STATUS  current
		DESCRIPTION
			"A row in pnSrAppStatsTable.
			Note that the indices are from pnSrAsmTable and
			pnSrAppTable. For each Assembler this reducer has
			a session with (indexed by pnSrAsmIndex), statistics
			are maintained for each application that is monitored
			(indexed by pnSrAppIndex)."
		INDEX   { pnSrAsmIndex, pnSrAppIndex }
		::= { pnSrAppStatsTable 1 }

	PeribitSrAppStatsEntry ::=
		SEQUENCE
		{
			pnSrAppStatsBytesIn
				Counter64,
			pnSrAppStatsBytesOut
				Counter64,
			pnSrAppStatsBytesInPercent
				Gauge32,
			pnSrAppStatsAppName
				TcAppName
		}

	pnSrAppStatsBytesIn OBJECT-TYPE
		SYNTAX  Counter64
		MAX-ACCESS  read-only
		STATUS  current
		DESCRIPTION
			"The total number of bytes into the SR, since the system
			was started, that were identified for reduction,
			and addressed to the SR whose IP address is in the
			row in pnSrAsmTable that matches the index
			pnSrAsmIndex, and that was received from the
			application whose name is in the row in pnSrAppTable
			that matches the index pnSrAppIndex."
		::= { pnSrAppStatsEntry 1 }

	pnSrAppStatsBytesOut OBJECT-TYPE
		SYNTAX  Counter64
		MAX-ACCESS  read-only
		STATUS  current
		DESCRIPTION
			"The total number of bytes out of the SR, since the
			system was started, that were identified for reduction,
			and addressed to the SR whose IP address is in the
			row in pnSrAsmTable that matches the index
			pnSrAsmIndex, and that was received from the
			application whose name is in the row in pnSrAppTable."
		::= { pnSrAppStatsEntry 2 }

	pnSrAppStatsBytesInPercent OBJECT-TYPE
		SYNTAX  Gauge32
		MAX-ACCESS  read-only
		STATUS  current
		DESCRIPTION
			"The percentage of the bytes in for this application
			over the total bytes into the SR, since the system
			was started, that were identified for reduction,
			and addressed to the SR whose IP address is in the
			row in pnSrAsmTable that matches the index
			pnSrAsmIndex, and that was received from the
			application whose name is in the row in pnSrAppTable
			that matches the index pnSrAppIndex.

			The value returned is (percentage * 1000). Applications should
			divide the returned value by 1000."
		::= { pnSrAppStatsEntry 3 }

	pnSrAppStatsAppName OBJECT-TYPE
		SYNTAX  TcAppName
		MAX-ACCESS  read-only
		STATUS  current
		DESCRIPTION
			"The name of the application from which the data was
			received (e.g., FTP, HTTP, Lotus Notes).

			NOTE: This object is here even though it's also in
			pnSrAppTable. This is for the convenience of network
			monitoring tools that require all columns to be from the
			same table."
		::= { pnSrAppStatsEntry 4 }

	----------------------------------------------------------------------
	-- Aggregate application stats (across all assemblers)
	-- maintained by a Reducer. This table augments pnSrAppTable.

	pnSrAppAggrStatsTable OBJECT-TYPE
		SYNTAX  SEQUENCE OF PeribitSrAppAggrStatsEntry
		MAX-ACCESS  not-accessible
		STATUS  current
		DESCRIPTION
			"Aggregate statistics maintained by a Reducer for each application
			that is monitored. These statistics apply to the reducer as a whole
			and are summed over all assembler sessions maintained by the reducer."
		::= { pnSrApp 3 }

	pnSrAppAggrStatsEntry OBJECT-TYPE
		SYNTAX  PeribitSrAppAggrStatsEntry
		MAX-ACCESS  not-accessible
		STATUS  current
		DESCRIPTION
			"A row in pnSrAppAggrStatsTable."
		AUGMENTS   { pnSrAppEntry }
		::= { pnSrAppAggrStatsTable 1 }

	PeribitSrAppAggrStatsEntry ::=
		SEQUENCE
		{
			pnSrAppAggrStatsBytesInRe
				Counter64,
			pnSrAppAggrStatsBytesOutRe
				Counter64,
			pnSrAppAggrStatsBytesInPercent
				Gauge32
		}

	pnSrAppAggrStatsBytesInRe OBJECT-TYPE
		SYNTAX  Counter64
		MAX-ACCESS  read-only
		STATUS  current
		DESCRIPTION
			"Total number of bytes that entered the SR Reduction Engine
			for this application since the system was started."
		::= { pnSrAppAggrStatsEntry 1 }

	pnSrAppAggrStatsBytesOutRe OBJECT-TYPE
		SYNTAX  Counter64
		MAX-ACCESS  read-only
		STATUS  current
		DESCRIPTION
			"Total number of bytes that exited the SR Reduction Engine
			after reduction for this application since the system was started."
		::= { pnSrAppAggrStatsEntry 2 }

	pnSrAppAggrStatsBytesInPercent OBJECT-TYPE
		SYNTAX  Gauge32
		MAX-ACCESS  read-only
		STATUS  current
		DESCRIPTION
			"The percentage of the bytes in for this application over the
			total bytes into the SR Reduction Engine.

			The value returned is (percentage * 1000). Applications should
			divide the returned value by 1000."
		::= { pnSrAppAggrStatsEntry 3 }

	----------------------------------------------------------------------
	-- The burst stats over the past minute.
	-- NOTE: pnSrStatsUpdateTime does not apply to this group.

	pnSrBurstStats OBJECT-IDENTITY
		STATUS					current
		DESCRIPTION				"
			Sub-tree for Sequence Reducer system statistics."
		::= { pnSrObjs 7 }

	pnSrBurstStatsStartTime OBJECT-TYPE
		SYNTAX  Integer32
		MAX-ACCESS  read-only
		STATUS  current
		DESCRIPTION
			"The start of the minute in seconds since
			midnight (00:00:00), January 1, 1970, UTC
			over which the burst stats apply."
		::= { pnSrBurstStats 1 }

	pnSrBurstStatsBpsIn OBJECT-TYPE
		SYNTAX  Gauge32
		MAX-ACCESS  read-only
		STATUS  current
		DESCRIPTION
			"Burst bits per second into reduction engine for the past minute."
		::= { pnSrBurstStats 2 }

	pnSrBurstStatsBpsOut OBJECT-TYPE
		SYNTAX  Gauge32
		MAX-ACCESS  read-only
		STATUS  current
		DESCRIPTION
			"Burst bits per second out of reduction engine for the past minute."
		::= { pnSrBurstStats 3 }

	pnSrBurstStatsBpsPt OBJECT-TYPE
		SYNTAX  Gauge32
		MAX-ACCESS  read-only
		STATUS  current
		DESCRIPTION
			"Burst pass-through bits per second for the past minute."
		::= { pnSrBurstStats 4 }

	----------------------------------------------------------------------
	-- Events

	pnSrEventObjs OBJECT-IDENTITY
		STATUS					current
		DESCRIPTION				"
			Branch for objects meant only to be sent in event varbinds."
		::= { pnSrEvents 1 }

	pnSrEventEvents OBJECT-IDENTITY
		STATUS					current
		DESCRIPTION				"
			Branch for the events themselves."
		::= { pnSrEvents 2 }

	pnSrEventEventsV2 OBJECT-IDENTITY
		STATUS					current
		DESCRIPTION				"
			Branch for SNMPv2 events. The OIDs for SNMPv2 events should
			have a zero as the next-to-last sub-identifier (as specified
			in RFC1902)."
		::= { pnSrEventEvents 0 }

	-- Objects sent only in events
	-- None so far.

	-- Event descriptions

	pnSrEventRipAuthFailure NOTIFICATION-TYPE
		OBJECTS { pnCommonEventDescr }
		STATUS  current
		DESCRIPTION
			"RIP authentication failure"
		::= { pnSrEventEventsV2 1 }

	pnSrEventReducerBufferOverflow NOTIFICATION-TYPE
		OBJECTS { pnCommonEventDescr }
		STATUS  current
		DESCRIPTION
			"The reducer's input buffer is approaching full capacity."
		::= { pnSrEventEventsV2 2 }

	pnSrEventReducerSessionClosed NOTIFICATION-TYPE
		OBJECTS { pnCommonEventDescr }
		STATUS  current
		DESCRIPTION
			"The reducer's session to the device described in
			pnCommonEventDescr was terminated."
		::= { pnSrEventEventsV2 3 }

	pnSrEventAssemblerSessionClosed NOTIFICATION-TYPE
		OBJECTS { pnCommonEventDescr }
		STATUS  current
		DESCRIPTION
			"The assembler's session to the device described in
			pnCommonEventDescr was terminated."
		::= { pnSrEventEventsV2 4 }

	pnSrEventReducerSessionOpened NOTIFICATION-TYPE
		OBJECTS { pnCommonEventDescr }
		STATUS  current
		DESCRIPTION
			"The reducer's session to the device described in
			pnCommonEventDescr was opened."
		::= { pnSrEventEventsV2 5 }

	pnSrEventAssemblerSessionOpened NOTIFICATION-TYPE
		OBJECTS { pnCommonEventDescr }
		STATUS  current
		DESCRIPTION
			"The assembler's session to the device described in
			pnCommonEventDescr was opened."
		::= { pnSrEventEventsV2 6 }

	pnSrEventPrimaryRegServerUnreachable NOTIFICATION-TYPE
		OBJECTS { pnCommonEventDescr }
		STATUS  current
		DESCRIPTION
			"The primary registration server is
			currently unreachable."
		::= { pnSrEventEventsV2 7 }

	pnSrEventSecondaryRegServerUnreachable NOTIFICATION-TYPE
		OBJECTS { pnCommonEventDescr }
		STATUS  current
		DESCRIPTION
			"The secondary registration server is
			currently unreachable."
		::= { pnSrEventEventsV2 8 }

	pnSrEventMultiNodeMasterUp NOTIFICATION-TYPE
		OBJECTS { pnCommonEventDescr }
		STATUS  current
		DESCRIPTION
			"The system designated as the 'master' of a multi-node
			came up. This notification is generated by the
			system that's designated as the 'master' of the
			multi-node.

			Note that the corresponding Down notification is
			generated by the designated 'master-backup' of the
			same multi-node."
		::= { pnSrEventEventsV2 9 }

	pnSrEventMultiNodeMasterDown NOTIFICATION-TYPE
		OBJECTS { pnCommonEventDescr }
		STATUS  current
		DESCRIPTION
			"The system designated as the 'master' of a multi-node
			is currently down. This notification is generated by the
			system that's designated as the 'master-backup' of the
			same multi-node.

			Note that the corresponding Up notification is
			generated by the designated 'master' of the same
			multi-node."
		::= { pnSrEventEventsV2 10 }

	pnSrEventMultiNodeLastUp NOTIFICATION-TYPE
		OBJECTS { pnCommonEventDescr }
		STATUS  current
		DESCRIPTION
			"The system designated as the 'last-node' of a multi-node
			came up. This notification is generated by the
			system that's designated as the 'last-node' of the
			multi-node.

			Note that the corresponding Down notification is
			generated by the designated 'master' of the
			same multi-node."
		::= { pnSrEventEventsV2 11 }

	pnSrEventMultiNodeLastDown NOTIFICATION-TYPE
		OBJECTS { pnCommonEventDescr }
		STATUS  current
		DESCRIPTION
			"The system designated as the 'last-node' of a multi-node
			is currently down. This notification is generated by the
			system that's designated as the 'master' of the
			same multi-node.

			Note that the corresponding Up notification is
			generated by the designated 'last-node' of the same
			multi-node."
		::= { pnSrEventEventsV2 12 }
	pnSrEventPrimaryDownBackupEngaged NOTIFICATION-TYPE
		OBJECTS { pnCommonEventDescr }
		STATUS  current
		DESCRIPTION
			"The system designated as the 'primary' is currently 
			unreachable. This notification is generated by the
			system that's designated as the 'backup' device.
			The backup device is engaged for the primary device."
		::= { pnSrEventEventsV2 13 }
	pnSrEventPrimaryDownBackupEngageFailed NOTIFICATION-TYPE
		OBJECTS { pnCommonEventDescr }
		STATUS  current
		DESCRIPTION
			"The system designated as the 'primary' is currently 
			unreachable. This notification is generated by the
			system that's designated as the 'backup' device.
			The backup device failed to engage for the primary device."
		::= { pnSrEventEventsV2 14 }
	pnSrEventPrimaryUpBackupDisengaged NOTIFICATION-TYPE
		OBJECTS { pnCommonEventDescr }
		STATUS  current
		DESCRIPTION
			"The system designated as the 'primary' is currently 
			reachable. This notification is generated by the
			system that's designated as the 'backup' device.
			The backup device has disengaged itself."
		::= { pnSrEventEventsV2 15 }

	pnSrEventMultiPathStatusChange NOTIFICATION-TYPE
		OBJECTS { pnCommonEventDescr }
		STATUS  current
		DESCRIPTION
			"The status of the primary or secondary path to another
			multi-path enabled system changed. The path became inactive
			or failed after previously being active or vice versa.
			This might have caused traffic designated to flow over
			this path to be switched from or to this path."
		::= { pnSrEventEventsV2 16 }

	pnSrEventDiskFailure NOTIFICATION-TYPE
		OBJECTS { pnCommonEventDescr }
		STATUS  current
		DESCRIPTION
			"A hard disk failed on the system. The system was rebooted, 
			and will now operate without the downed disk, at a degraded 
			performance. Dictionary accumulated until this point was lost."
		::= { pnSrEventEventsV2 17 }
END

-- End - PERIBIT-SR-MIB Module
