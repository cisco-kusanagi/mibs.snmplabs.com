Wellfleet-LNM-MIB DEFINITIONS ::= BEGIN

-- Created by mdl2asn version 3.1
-- Creation date: Wed Aug 30 16:44:57 EDT 1995


    IMPORTS

      IpAddress, Counter, Gauge, TimeTicks, Opaque, enterprises, mgmt
        FROM RFC1155-SMI
      OBJECT-TYPE
        FROM RFC-1212
      TRAP-TYPE
        FROM RFC-1215
      DisplayString, mib-2
        FROM RFC1213-MIB
      wfLanManagerGroup
        FROM Wellfleet-COMMON-MIB;


    wfLnm		OBJECT IDENTIFIER ::= { wfLanManagerGroup 1 }

    wfLnmDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete the LNM Servers subsystem."
        DEFVAL	{ created }
        ::= { wfLnm 1 }

    wfLnmDisable OBJECT-TYPE
        SYNTAX	INTEGER {
    		    enabled(1),
    		    disabled(2)
    		}
        ACCESS	read-write
        STATUS	mandatory
        DESCRIPTION
                "Enable/Disable parameter. Default is enabled.
                Users perform an SNMP SET operation on this
                object in order to enable/disable the LNM Servers subsystem."
        DEFVAL	{ enabled }
        ::= { wfLnm 2 }

    wfLnmState OBJECT-TYPE
        SYNTAX	INTEGER {
    		    up(1),
    		    down(2),
    		    init(3),
    		    notpresent(4)
    		}
        ACCESS	read-only
        STATUS	mandatory
        DESCRIPTION
                "The current state of the LNM Servers subsystem."
        DEFVAL	{ down }
        ::= { wfLnm 3 }

    wfLnmLnmSetsDisable OBJECT-TYPE
        SYNTAX	INTEGER {
    		    enabled(1),
    		    disabled(2)
    		}
        ACCESS	read-write
        STATUS	mandatory
        DESCRIPTION
                "Allow or disallow Lan Manager to SET MIB values"
        DEFVAL	{ disabled }
        ::= { wfLnm 4 }

    wfLnmInternalLanId OBJECT-TYPE
        SYNTAX	INTEGER
        ACCESS	read-write
        STATUS	mandatory
        DESCRIPTION
                "The internal LAN id matches exactly wfBrSrBaseInternalLanId
                in the source routing mib.  It is written here, but not
                displayed."
        ::= { wfLnm 5 }

    wfLnmBridgeId OBJECT-TYPE
        SYNTAX	INTEGER
        ACCESS	read-write
        STATUS	mandatory
        DESCRIPTION
                "The bridge id matches exactly wfBrSrBaseBridgeId
                in the source routing mib.  It is written here, but not
                displayed."
        ::= { wfLnm 6 }

    wfLnmInterfaceTable OBJECT-TYPE
        SYNTAX	SEQUENCE OF WfLnmInterfaceEntry
        ACCESS	not-accessible
        STATUS	mandatory
        DESCRIPTION
                "table of instances"
        ::= { wfLanManagerGroup 2 }

    wfLnmInterfaceEntry OBJECT-TYPE
        SYNTAX	WfLnmInterfaceEntry
        ACCESS	not-accessible
        STATUS	mandatory
        DESCRIPTION
                "An entry in the LNM table"
        INDEX	{ wfLnmInterfaceMacCircuit }
        ::= { wfLnmInterfaceTable 1 }

    WfLnmInterfaceEntry ::= SEQUENCE {
    	    wfLnmInterfaceDelete
    		INTEGER,
    	    wfLnmInterfaceDisable
    		INTEGER,
    	    wfLnmInterfaceCircuit
    		INTEGER,
    	    wfLnmInterfaceMacCircuit
    		INTEGER,
    	    wfLnmInterfaceRemoteMac
    		OCTET STRING,
    	    wfLnmInterfaceLrmDisable
    		INTEGER,
    	    wfLnmInterfaceLrmState
    		INTEGER,
    	    wfLnmInterfaceLbsState
    		INTEGER,
    	    wfLnmInterfaceRemDisable
    		INTEGER,
    	    wfLnmInterfaceRemState
    		INTEGER,
    	    wfLnmInterfaceRpsDisable
    		INTEGER,
    	    wfLnmInterfaceRpsState
    		INTEGER,
    	    wfLnmInterfaceCrsDisable
    		INTEGER,
    	    wfLnmInterfaceCrsState
    		INTEGER,
    	    wfLnmInterfaceCtrlMgrPswd
    		DisplayString,
    	    wfLnmInterfaceOb1MgrPswd
    		DisplayString,
    	    wfLnmInterfaceOb2MgrPswd
    		DisplayString,
    	    wfLnmInterfaceOb3MgrPswd
    		DisplayString,
    	    wfLnmInterfaceCtrlMgrMac
    		OCTET STRING,
    	    wfLnmInterfaceOb1MgrMac
    		OCTET STRING,
    	    wfLnmInterfaceOb2MgrMac
    		OCTET STRING,
    	    wfLnmInterfaceOb3MgrMac
    		OCTET STRING,
    	    wfLnmInterfaceWghtTrshld
    		INTEGER,
    	    wfLnmInterfaceLrmCngstnErrs
    		Counter,
    	    wfLnmInterfaceLrmRxErrors
    		Counter,
    	    wfLnmInterfaceRemRxErrors
    		Counter,
    	    wfLnmInterfaceRpsRxErrors
    		Counter,
    	    wfLnmInterfaceCrsRxErrors
    		Counter,
    	    wfLnmInterfaceLbsRxErrors
    		Counter
        }

    wfLnmInterfaceDelete OBJECT-TYPE
        SYNTAX	INTEGER {
    		    created(1),
    		    deleted(2)
    		}
        ACCESS	read-write
        STATUS	mandatory
        DESCRIPTION
                "A flag to allow an entire row to be deleted"
        DEFVAL	{ created }
        ::= { wfLnmInterfaceEntry 1 }

    wfLnmInterfaceDisable OBJECT-TYPE
        SYNTAX	INTEGER {
    		    enabled(1),
    		    disabled(2)
    		}
        ACCESS	read-write
        STATUS	mandatory
        DESCRIPTION
                "- Enable/Disable parameter. Default is enabled.
                - Users perform an SNMP SET operation on this
                - object in order to enable/disable an interface."
        DEFVAL	{ enabled }
        ::= { wfLnmInterfaceEntry 2 }

    wfLnmInterfaceCircuit OBJECT-TYPE
        SYNTAX	INTEGER
        ACCESS	read-write
        STATUS	mandatory
        DESCRIPTION
                "circuit number for LLC2 - filled in by Site Man"
        ::= { wfLnmInterfaceEntry 3 }

    wfLnmInterfaceMacCircuit OBJECT-TYPE
        SYNTAX	INTEGER
        ACCESS	read-only
        STATUS	mandatory
        DESCRIPTION
                "circuit number for MAC"
        ::= { wfLnmInterfaceEntry 4 }

    wfLnmInterfaceRemoteMac OBJECT-TYPE
        SYNTAX	OCTET STRING
        ACCESS	read-write
        STATUS	mandatory
        DESCRIPTION
                "Site Man will suggest a value, but the user can override."
        ::= { wfLnmInterfaceEntry 5 }

    wfLnmInterfaceLrmDisable OBJECT-TYPE
        SYNTAX	INTEGER {
    		    enabled(1),
    		    disabled(2)
    		}
        ACCESS	read-write
        STATUS	mandatory
        DESCRIPTION
                "LRM server can be turned on/off"
        DEFVAL	{ enabled }
        ::= { wfLnmInterfaceEntry 6 }

    wfLnmInterfaceLrmState OBJECT-TYPE
        SYNTAX	INTEGER {
    		    up(1),
    		    down(2),
    		    init(3),
    		    notpresent(4)
    		}
        ACCESS	read-only
        STATUS	mandatory
        DESCRIPTION
                "There is only a state - enabling LNM Servers automatically enables LRM"
        DEFVAL	{ notpresent }
        ::= { wfLnmInterfaceEntry 7 }

    wfLnmInterfaceLbsState OBJECT-TYPE
        SYNTAX	INTEGER {
    		    up(1),
    		    down(2),
    		    init(3),
    		    notpresent(4)
    		}
        ACCESS	read-only
        STATUS	mandatory
        DESCRIPTION
                "There is no corresponding enable for LBS"
        DEFVAL	{ notpresent }
        ::= { wfLnmInterfaceEntry 8 }

    wfLnmInterfaceRemDisable OBJECT-TYPE
        SYNTAX	INTEGER {
    		    enabled(1),
    		    disabled(2)
    		}
        ACCESS	read-write
        STATUS	mandatory
        DESCRIPTION
                "REM server can be turned on/off"
        DEFVAL	{ enabled }
        ::= { wfLnmInterfaceEntry 9 }

    wfLnmInterfaceRemState OBJECT-TYPE
        SYNTAX	INTEGER {
    		    up(1),
    		    down(2),
    		    init(3),
    		    notpresent(4)
    		}
        ACCESS	read-only
        STATUS	mandatory
        DESCRIPTION
                "REM state parameter - can be active or not"
        DEFVAL	{ notpresent }
        ::= { wfLnmInterfaceEntry 10 }

    wfLnmInterfaceRpsDisable OBJECT-TYPE
        SYNTAX	INTEGER {
    		    enabled(1),
    		    disabled(2)
    		}
        ACCESS	read-write
        STATUS	mandatory
        DESCRIPTION
                "RPS server can be turned on/off"
        DEFVAL	{ enabled }
        ::= { wfLnmInterfaceEntry 11 }

    wfLnmInterfaceRpsState OBJECT-TYPE
        SYNTAX	INTEGER {
    		    up(1),
    		    down(2),
    		    init(3),
    		    notpresent(4)
    		}
        ACCESS	read-only
        STATUS	mandatory
        DESCRIPTION
                "RPS state - actively forwarding to LAN Manager, or only collecting stats"
        DEFVAL	{ notpresent }
        ::= { wfLnmInterfaceEntry 12 }

    wfLnmInterfaceCrsDisable OBJECT-TYPE
        SYNTAX	INTEGER {
    		    enabled(1),
    		    disabled(2)
    		}
        ACCESS	read-write
        STATUS	mandatory
        DESCRIPTION
                "CRS server can be turned on/off"
        DEFVAL	{ enabled }
        ::= { wfLnmInterfaceEntry 13 }

    wfLnmInterfaceCrsState OBJECT-TYPE
        SYNTAX	INTEGER {
    		    up(1),
    		    down(2),
    		    init(3),
    		    notpresent(4)
    		}
        ACCESS	read-only
        STATUS	mandatory
        DESCRIPTION
                "CRS state - actively forwarding to LAN Manager, or only collecting stats"
        DEFVAL	{ notpresent }
        ::= { wfLnmInterfaceEntry 14 }

    wfLnmInterfaceCtrlMgrPswd OBJECT-TYPE
        SYNTAX	DisplayString
        ACCESS	read-write
        STATUS	mandatory
        DESCRIPTION
                "Controlling LAN Manager Password; default = all 0s"
        ::= { wfLnmInterfaceEntry 15 }

    wfLnmInterfaceOb1MgrPswd OBJECT-TYPE
        SYNTAX	DisplayString
        ACCESS	read-write
        STATUS	mandatory
        DESCRIPTION
                "Observing LAN Manager Password; default = all 0s"
        ::= { wfLnmInterfaceEntry 16 }

    wfLnmInterfaceOb2MgrPswd OBJECT-TYPE
        SYNTAX	DisplayString
        ACCESS	read-write
        STATUS	mandatory
        DESCRIPTION
                "Observing LAN Manager Password; default = all 0s"
        ::= { wfLnmInterfaceEntry 17 }

    wfLnmInterfaceOb3MgrPswd OBJECT-TYPE
        SYNTAX	DisplayString
        ACCESS	read-write
        STATUS	mandatory
        DESCRIPTION
                "Observing LAN Manager Password; default = all 0s"
        ::= { wfLnmInterfaceEntry 18 }

    wfLnmInterfaceCtrlMgrMac OBJECT-TYPE
        SYNTAX	OCTET STRING
        ACCESS	read-only
        STATUS	mandatory
        DESCRIPTION
                "Controlling LAN Manager Location; default = all 0s"
        ::= { wfLnmInterfaceEntry 19 }

    wfLnmInterfaceOb1MgrMac OBJECT-TYPE
        SYNTAX	OCTET STRING
        ACCESS	read-only
        STATUS	mandatory
        DESCRIPTION
                "Observing LAN Manager Location; default = all 0s"
        ::= { wfLnmInterfaceEntry 20 }

    wfLnmInterfaceOb2MgrMac OBJECT-TYPE
        SYNTAX	OCTET STRING
        ACCESS	read-only
        STATUS	mandatory
        DESCRIPTION
                "Observing LAN Manager Location; default = all 0s"
        ::= { wfLnmInterfaceEntry 21 }

    wfLnmInterfaceOb3MgrMac OBJECT-TYPE
        SYNTAX	OCTET STRING
        ACCESS	read-only
        STATUS	mandatory
        DESCRIPTION
                "Observing LAN Manager Location; default = all 0s"
        ::= { wfLnmInterfaceEntry 22 }

    wfLnmInterfaceWghtTrshld OBJECT-TYPE
        SYNTAX	INTEGER(10..256)
        ACCESS	read-write
        STATUS	mandatory
        DESCRIPTION
                "Error rate threshold - defaults to 128"
        DEFVAL	{ 128 }
        ::= { wfLnmInterfaceEntry 23 }

    wfLnmInterfaceLrmCngstnErrs OBJECT-TYPE
        SYNTAX	Counter
        ACCESS	read-only
        STATUS	mandatory
        DESCRIPTION
                "Measure the number of packets LRM drops"
        ::= { wfLnmInterfaceEntry 24 }

    wfLnmInterfaceLrmRxErrors OBJECT-TYPE
        SYNTAX	Counter
        ACCESS	read-only
        STATUS	mandatory
        DESCRIPTION
                "Measure the number of packets LRM can't parse"
        ::= { wfLnmInterfaceEntry 25 }

    wfLnmInterfaceRemRxErrors OBJECT-TYPE
        SYNTAX	Counter
        ACCESS	read-only
        STATUS	mandatory
        DESCRIPTION
                "Measure the number of packets REM can't parse"
        ::= { wfLnmInterfaceEntry 26 }

    wfLnmInterfaceRpsRxErrors OBJECT-TYPE
        SYNTAX	Counter
        ACCESS	read-only
        STATUS	mandatory
        DESCRIPTION
                "Measure the number of packets RPS can't parse"
        ::= { wfLnmInterfaceEntry 27 }

    wfLnmInterfaceCrsRxErrors OBJECT-TYPE
        SYNTAX	Counter
        ACCESS	read-only
        STATUS	mandatory
        DESCRIPTION
                "Measure the number of packets CRS can't parse"
        ::= { wfLnmInterfaceEntry 28 }

    wfLnmInterfaceLbsRxErrors OBJECT-TYPE
        SYNTAX	Counter
        ACCESS	read-only
        STATUS	mandatory
        DESCRIPTION
                "Measure the number of packets LBS can't parse"
        ::= { wfLnmInterfaceEntry 29 }

    END  -- Wellfleet-LNM-MIB
