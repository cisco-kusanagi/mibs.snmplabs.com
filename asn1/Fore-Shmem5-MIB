-- 
-- Copyright 1999 by Fore Systems, Inc. 
-- Converted to SMIv2 rfc 2578,2579,2580 - STD 58
--
------------------------------------------------------------------------
-- Shmem5 MIB Definitions

Fore-Shmem5-MIB DEFINITIONS ::= BEGIN

IMPORTS
	Counter32, Gauge32, Integer32,
        OBJECT-TYPE,
        MODULE-IDENTITY                 FROM SNMPv2-SMI
        DisplayString, RowStatus        FROM SNMPv2-TC
	AAL5CountingMode, shmem		FROM Fore-Switch-MIB
        EntryStatus 			FROM Fore-Common-MIB;

	
------------------------------------------------------------------------
-- Define Shmem5 Group

shmem5Group MODULE-IDENTITY
          LAST-UPDATED         "9911050000Z"
          ORGANIZATION         "FORE"
          CONTACT-INFO         
               "      Postal:   FORE Systems Inc.
                                 1000 FORE Drive
                                 Warrendale, PA 15086-7502
                       Tel:      +1 724 742 6900
                       Email:    nm_mibs@fore.com
                       Web:      http://www.fore.com"
          DESCRIPTION "Shared memory network module."
    ::= { shmem 13 }
 

------------------------------------------------------------------------
-- netmodShmem5Table Definition

netmodShmem5Table OBJECT-TYPE
	SYNTAX	SEQUENCE OF NetmodShmem5Entry
	MAX-ACCESS	not-accessible
	STATUS	current
	DESCRIPTION
		"A table for shared memory network module configurations."
	::= { shmem5Group 1 }

netmodShmem5Entry OBJECT-TYPE
	SYNTAX	NetmodShmem5Entry
	MAX-ACCESS	not-accessible
	STATUS	current
	DESCRIPTION
		"A table entry containing shared memory network module 
		 configuration information."
	INDEX	{ nShmem5Index }
	::= { netmodShmem5Table 1 }

NetmodShmem5Entry ::=
	SEQUENCE {
		nShmem5Index				Integer32,
		nShmem5CellMemorySize			Integer32,
		nShmem5TableMemorySize			Integer32,
		nShmem5SchedulerMemorySize		Integer32,
		nShmem5SharedMemorySize			Integer32,
		nShmem5DupListUsed			Gauge32,
		nShmem5CurrMcastConns			Gauge32,
		nShmem5CurrUcastConns			Gauge32,
		nShmem5CellsBuffered			Gauge32,
		nShmem5DuplicationListSize		Integer32,
		nShmem5McastConns			Integer32,
		nShmem5UcastConns			Integer32,
		nShmem5ConfEfciOn			Integer32,
		nShmem5ConfEfciOff			Integer32,
		nShmem5AAL5CountingMode			AAL5CountingMode,
		nShmem5AAl5CountingModeOverride		INTEGER,
		nShmem5OverbookingHw			INTEGER
	}

nShmem5Index OBJECT-TYPE
        SYNTAX  Integer32
        MAX-ACCESS  not-accessible
        STATUS  current
        DESCRIPTION
		"The index of this netmodShmem5Entry. The same index is also
		 used as entity index for this entry within entPhysicalTable."
	::= { netmodShmem5Entry 1 }

nShmem5CellMemorySize OBJECT-TYPE
        SYNTAX  Integer32
        MAX-ACCESS  read-only
	STATUS  current
        DESCRIPTION
                "Cell RAM size of this shmem in 32 bits."
	::= { netmodShmem5Entry 2 }

nShmem5TableMemorySize OBJECT-TYPE
        SYNTAX  Integer32
        MAX-ACCESS  read-only
        STATUS  current
        DESCRIPTION
                "Table RAM size of this shmem in 32 bits."
        ::= { netmodShmem5Entry 3 }

nShmem5SchedulerMemorySize OBJECT-TYPE
        SYNTAX  Integer32
        MAX-ACCESS  read-only
        STATUS  current
        DESCRIPTION
                "Scheduler RAM size of this shmem in 32 bits."
        ::= { netmodShmem5Entry 4 }

nShmem5SharedMemorySize OBJECT-TYPE
        SYNTAX  Integer32
        MAX-ACCESS  read-only
        STATUS  current
        DESCRIPTION
                "Amount of shared memory of this shmem in cells."
        ::= { netmodShmem5Entry 5 }

nShmem5DupListUsed OBJECT-TYPE
        SYNTAX  Gauge32
        MAX-ACCESS  read-only
        STATUS  current
        DESCRIPTION
                "Current number of multicast duplication list entries used."
        ::= { netmodShmem5Entry 6 }

nShmem5CurrMcastConns OBJECT-TYPE
        SYNTAX  Gauge32
        MAX-ACCESS  read-only
        STATUS  current
        DESCRIPTION
                "Current number of multicast connections active on this shmem."
        ::= { netmodShmem5Entry 7 }

nShmem5CurrUcastConns OBJECT-TYPE
        SYNTAX  Gauge32
        MAX-ACCESS  read-only
        STATUS  current
        DESCRIPTION
                "Current number of unicast connections  active on this shmem."
        ::= { netmodShmem5Entry 8 }

nShmem5CellsBuffered OBJECT-TYPE
        SYNTAX  Gauge32
        MAX-ACCESS  read-only
        STATUS  current
        DESCRIPTION
                "Current number of cells buffered at this shmem."
        ::= { netmodShmem5Entry 9 }

nShmem5DuplicationListSize OBJECT-TYPE
        SYNTAX  Integer32
	MAX-ACCESS  read-only
        STATUS  current
        DESCRIPTION
                "Number of multicast duplication list entries that can be 
		 supported on this shmem."
        ::= { netmodShmem5Entry 11 }

nShmem5McastConns OBJECT-TYPE
        SYNTAX  Integer32
        MAX-ACCESS  read-only
        STATUS  current
        DESCRIPTION
                "Number of multicast connection roots that can be supported on 
		 this shmem."
        ::= { netmodShmem5Entry 12 }

nShmem5UcastConns OBJECT-TYPE
        SYNTAX  Integer32
        MAX-ACCESS  read-write
        STATUS  current
        DESCRIPTION
                "Number of unicast connection that can be supported on
                 this shmem."
        ::= { netmodShmem5Entry 13 }

nShmem5ConfEfciOn OBJECT-TYPE
        SYNTAX  Integer32
        MAX-ACCESS  read-write
        STATUS  current
        DESCRIPTION
                "The threshold on which the EFCI (Explicit Forward Congestion
		 Indication) is enabled (in cells)."
        ::= { netmodShmem5Entry 14 }

nShmem5ConfEfciOff OBJECT-TYPE
        SYNTAX  Integer32
        MAX-ACCESS  read-write
        STATUS  current
        DESCRIPTION
                "The threshold on which the EFCI (Explicit Forward Congestion
                 Indication) is disabled (in cells)."
        ::= { netmodShmem5Entry 15 }

nShmem5AAL5CountingMode OBJECT-TYPE
        SYNTAX  AAL5CountingMode
        MAX-ACCESS  read-write
        STATUS  current
        DESCRIPTION
                "AAL5 Counting mode on this shmem. The default option of 
		 AAL5CountingMode is not allowed. The default value is
		 packet-counting mode."
	DEFVAL { packet-counting }
	::= { netmodShmem5Entry 16 }

nShmem5AAl5CountingModeOverride OBJECT-TYPE
        SYNTAX  INTEGER {
                   on(1),
                   off(2)
                }
	MAX-ACCESS  read-write
        STATUS  current
        DESCRIPTION
                "Override option for AAL5 Counting mode. The default value is off."
	DEFVAL { off }
        ::= { netmodShmem5Entry 17 }

nShmem5OverbookingHw OBJECT-TYPE
        SYNTAX  INTEGER {
                   disable(1),
                   enable(2)
                }
	MAX-ACCESS  read-write
        STATUS  current
        DESCRIPTION
                "This is a switch to enable/disable the hardware overbooking 
		 feature on the griffin netmods. This is applicable only to
                 the rtVBR and nrtVBR service categories."
	DEFVAL { disable }
        ::= { netmodShmem5Entry 18 }

------------------------------------------------------------------------
-- bufferClassShmem5Table Definition

bufferClassShmem5Table OBJECT-TYPE
        SYNTAX  SEQUENCE OF BufferClassShmem5Entry
        MAX-ACCESS  not-accessible
        STATUS  current
        DESCRIPTION
                "A table for shared memory network module buffer class 
		 configuration. 8 buffer classes are provided"
        ::= { shmem5Group 2 }


bufferClassShmem5Entry OBJECT-TYPE
        SYNTAX  BufferClassShmem5Entry
        MAX-ACCESS  not-accessible
        STATUS  current
        DESCRIPTION
                "A table entry containing Buffer classes."
        INDEX   { bcShmem5Index , bcShmem5BufferClassIndex}
        ::= { bufferClassShmem5Table 1 }


BufferClassShmem5Entry ::=
        SEQUENCE {
                bcShmem5Index                          Integer32,
                bcShmem5BufferClassIndex               Integer32,
                bcShmem5Status                         EntryStatus,
                bcShmem5Name                           DisplayString,
                bcShmem5EpdThreshold                   Integer32
        }


bcShmem5Index OBJECT-TYPE
        SYNTAX  Integer32
        MAX-ACCESS  not-accessible
        STATUS  current
        DESCRIPTION
                "Index of this Shmem. Same value is also used to index
                the corresponding shmem entity within the entPhysicalTable."
        ::= { bufferClassShmem5Entry 1 }


bcShmem5BufferClassIndex OBJECT-TYPE
        SYNTAX  Integer32
        MAX-ACCESS  not-accessible
        STATUS  current
        DESCRIPTION
                "Index of this Buffer class."
        ::= { bufferClassShmem5Entry 2 }


bcShmem5Status OBJECT-TYPE
        SYNTAX  EntryStatus
        MAX-ACCESS  read-create
        STATUS  current
        DESCRIPTION
                "Status of this buffer class."
        ::= { bufferClassShmem5Entry 3 }


bcShmem5Name OBJECT-TYPE
        SYNTAX  DisplayString
        MAX-ACCESS  read-create
        STATUS  current
        DESCRIPTION
                "Name of this buffer class."
        ::= { bufferClassShmem5Entry 4 }


bcShmem5EpdThreshold OBJECT-TYPE
        SYNTAX  Integer32
        MAX-ACCESS  read-create
        STATUS  current
        DESCRIPTION
                "Early Packet drop threshold for this buffer class in
                 percentage of shared memory. Default value: 90% of
                 shared space."
        DEFVAL { 90 }
        ::= { bufferClassShmem5Entry 5 }




-----------------------------------------------------------------------
-- bufferClassAssignShmem5Table Definition

bufferClassAssignShmem5Table OBJECT-TYPE
        SYNTAX  SEQUENCE OF BufferClassAssignShmem5Entry
        MAX-ACCESS  not-accessible
        STATUS  current
        DESCRIPTION
                "A table for buffer class assignment."
        ::= { shmem5Group 3 }

bufferClassAssignShmem5Entry OBJECT-TYPE
        SYNTAX  BufferClassAssignShmem5Entry
        MAX-ACCESS  not-accessible
        STATUS  current
        DESCRIPTION
                "A table entry containing Buffer class assigned to a
		 service category and a subcategory"
        INDEX   { bcaShmem5Index , bcaShmem5ServCategory, bcaShmem5ServSubCategory}
        ::= { bufferClassAssignShmem5Table 1 }

BufferClassAssignShmem5Entry ::=
        SEQUENCE {
                bcaShmem5Index				Integer32,
                bcaShmem5ServCategory			Integer32,
                bcaShmem5ServSubCategory		Integer32,
                bcaShmem5Status				EntryStatus,
                bcaShmem5BuffClass			Integer32
        }

bcaShmem5Index OBJECT-TYPE
        SYNTAX  Integer32
        MAX-ACCESS  not-accessible
        STATUS  current
        DESCRIPTION
                "Index of this Shmem. Same value is also used to index
                the corresponding shmem entity within the entPhysicalTable."
        ::= { bufferClassAssignShmem5Entry 1 }

bcaShmem5ServCategory OBJECT-TYPE
        SYNTAX  Integer32
        MAX-ACCESS  not-accessible
        STATUS  current
        DESCRIPTION
                "Index of this Service Category within serviceCategoryTable defined in Fore-Switch-MIB"
        ::= { bufferClassAssignShmem5Entry 2 }

bcaShmem5ServSubCategory OBJECT-TYPE
        SYNTAX  Integer32
        MAX-ACCESS  not-accessible
        STATUS  current
        DESCRIPTION
                "Subcategory within this Service Category create
		 during upc creation."
        ::= { bufferClassAssignShmem5Entry 3 }

bcaShmem5Status OBJECT-TYPE
        SYNTAX  EntryStatus
        MAX-ACCESS  read-create
        STATUS  current
        DESCRIPTION
                "Status of this Buffer allocation"
        ::= { bufferClassAssignShmem5Entry 4 }

bcaShmem5BuffClass OBJECT-TYPE
        SYNTAX  Integer32
        MAX-ACCESS  read-create
        STATUS  current
        DESCRIPTION
                "Buffer class index within this shmem."
        ::= { bufferClassAssignShmem5Entry 5 }




-----------------------------------------------------------------------
-- ifBufferClassShmem5Table Definition

ifBufferClassShmem5Table  OBJECT-TYPE
	SYNTAX	SEQUENCE OF IfBufferClassShmem5Entry
	MAX-ACCESS	not-accessible
	STATUS 	current
	DESCRIPTION
		"A table for shared memory if/buffer class configuration."
	::= { shmem5Group 4 }


ifBufferClassShmem5Entry  OBJECT-TYPE
	SYNTAX  IfBufferClassShmem5Entry
	MAX-ACCESS	not-accessible
	STATUS	current
	DESCRIPTION
		"A table entry containing shared memory if/buffer class 
		 configuration."
	INDEX	{ ibShmem5Index, ibShmem5If, ibShmem5Buffer }
	::= { ifBufferClassShmem5Table 1 }


IfBufferClassShmem5Entry ::=
	SEQUENCE  {
		ibShmem5Index			Integer32,
		ibShmem5If			Integer32,
		ibShmem5Buffer			Integer32,
		ibShmem5Qsize			Integer32,
		ibShmem5CLP01Thresh		Integer32,
		ibShmem5CLP1Thresh		Integer32,
		ibShmem5TxCells			Counter32,
		ibShmem5CLP01Loss		Counter32,
		ibShmem5CLP1Loss		Counter32,
		ibShmem5EPDLoss			Counter32,
		ibShmem5PPDLoss			Counter32,
		ibShmem5OverflowLoss		Counter32,
		ibShmem5CurrentQsize		Gauge32,
		ibShmem5MaxQsize		Gauge32,
		ibShmem5IfName			DisplayString
	}


ibShmem5Index   OBJECT-TYPE
	SYNTAX	Integer32
	MAX-ACCESS	not-accessible
	STATUS	current
	DESCRIPTION
		"The index of this shmem5 entity. The same index is also used 
		 as the entity index for this entry within entPhysicalTable."
	::= { ifBufferClassShmem5Entry 1 }


ibShmem5If  	OBJECT-TYPE
        SYNTAX  Integer32
        MAX-ACCESS  not-accessible
        STATUS  current
        DESCRIPTION
		"The index of this shmem if."
	::= { ifBufferClassShmem5Entry 2 }


ibShmem5Buffer  OBJECT-TYPE
        SYNTAX  Integer32
        MAX-ACCESS  not-accessible
        STATUS  current
        DESCRIPTION
                "The index of this buffer class."
	::= { ifBufferClassShmem5Entry 3 }


ibShmem5Qsize  	OBJECT-TYPE
        SYNTAX  Integer32
        MAX-ACCESS  read-write
        STATUS  current
        DESCRIPTION
                "Dedicated queue size in cells."
	::= { ifBufferClassShmem5Entry 4 }


ibShmem5CLP01Thresh	OBJECT-TYPE
        SYNTAX  Integer32
        MAX-ACCESS  read-write
        STATUS  current
        DESCRIPTION
                "CLP01 cell discard threshold in cells."
	::= { ifBufferClassShmem5Entry 5 }


ibShmem5CLP1Thresh	OBJECT-TYPE
        SYNTAX  Integer32
	MAX-ACCESS  read-write
        STATUS  current
        DESCRIPTION
                "CLP1 cell discard threshold in cells."
        ::= { ifBufferClassShmem5Entry 6 }


ibShmem5TxCells	OBJECT-TYPE
        SYNTAX  Counter32
        MAX-ACCESS  read-only
        STATUS  current
        DESCRIPTION
                "Number of cells transmitted."
	::= { ifBufferClassShmem5Entry 7 }


ibShmem5CLP01Loss	OBJECT-TYPE
        SYNTAX  Counter32
        MAX-ACCESS  read-only
        STATUS  current
        DESCRIPTION
                "Number of cells lost due to CLP01 threshold."
	::= { ifBufferClassShmem5Entry 8 }


ibShmem5CLP1Loss	OBJECT-TYPE
        SYNTAX  Counter32
        MAX-ACCESS  read-only
        STATUS  current
        DESCRIPTION
                "Number of cells lost due to CLP1 threshold."
        ::= { ifBufferClassShmem5Entry 9 }


ibShmem5EPDLoss	OBJECT-TYPE
        SYNTAX  Counter32
        MAX-ACCESS  read-only
        STATUS  current
        DESCRIPTION
                "Number of cells lost due to EPD events."
        ::= { ifBufferClassShmem5Entry 10 }


ibShmem5PPDLoss	OBJECT-TYPE
        SYNTAX  Counter32
        MAX-ACCESS  read-only
        STATUS  current
        DESCRIPTION
                "Number of cells lost due to PPD events."
        ::= { ifBufferClassShmem5Entry 11 }


ibShmem5OverflowLoss	OBJECT-TYPE
        SYNTAX  Counter32
        MAX-ACCESS  read-only
        STATUS  current
        DESCRIPTION
                "Number of cells lost due to memory overflows."
	::= { ifBufferClassShmem5Entry 12 }


ibShmem5CurrentQsize	OBJECT-TYPE
        SYNTAX  Gauge32
	MAX-ACCESS  read-only
        STATUS  current
        DESCRIPTION
                "Current queue size in cells."
	::= { ifBufferClassShmem5Entry 13 }


ibShmem5MaxQsize	OBJECT-TYPE
        SYNTAX  Gauge32
        MAX-ACCESS  read-only
        STATUS  current
        DESCRIPTION
                "Max queue size since last read."
	::= { ifBufferClassShmem5Entry 14 }


ibShmem5IfName	OBJECT-TYPE
        SYNTAX  DisplayString
	MAX-ACCESS  read-only
	STATUS  current
        DESCRIPTION
                "Name of this shmem if."
	::= { ifBufferClassShmem5Entry 15 }



-----------------------------------------------------------------------
-- netmodShmem5CustomBCSTable Definition

netmodShmem5CustomBCSTable OBJECT-TYPE
        SYNTAX  SEQUENCE OF NetmodShmem5CustomBCSEntry
        MAX-ACCESS  not-accessible
        STATUS  current
        DESCRIPTION
                "A table for shared memory Custom BCS mappings"
        ::= { shmem5Group 5 }

netmodShmem5CustomBCSEntry OBJECT-TYPE
        SYNTAX  NetmodShmem5CustomBCSEntry
        MAX-ACCESS  not-accessible
        STATUS  current
        DESCRIPTION
                "A table entry containing shared memory Custom BCS mappings"
        INDEX   { nShmem5CustomBCSIndex,  nShmem5CustomBCSValue }
        ::= { netmodShmem5CustomBCSTable 1 }

NetmodShmem5CustomBCSEntry ::=
        SEQUENCE {
                nShmem5CustomBCSIndex           Integer32,
		nShmem5CustomBCSValue		Integer32,
		nShmem5CustomBCSWeight		Integer32,
		nShmem5CustomBCSBuffer		Integer32,
		nShmem5CustomBCSRowStatus	RowStatus
        }

nShmem5CustomBCSIndex OBJECT-TYPE
        SYNTAX  Integer32
        MAX-ACCESS  not-accessible
        STATUS  current
        DESCRIPTION
                "The index of this shared memory. The same index is also
                 used as entity index for this entry within entPhysicalTable"
        ::= { netmodShmem5CustomBCSEntry 1 }


nShmem5CustomBCSValue OBJECT-TYPE
        SYNTAX  Integer32
        MAX-ACCESS  not-accessible
        STATUS  current
        DESCRIPTION
                "The value of this BCS"
        ::= { netmodShmem5CustomBCSEntry 2 }

nShmem5CustomBCSWeight OBJECT-TYPE
        SYNTAX  Integer32
        MAX-ACCESS  read-write
        STATUS  current
        DESCRIPTION
                "The weight assigned to this BCS"
        ::= { netmodShmem5CustomBCSEntry 3 }


nShmem5CustomBCSBuffer OBJECT-TYPE
        SYNTAX  Integer32
        MAX-ACCESS  read-write
        STATUS  current
        DESCRIPTION
                "The buffer assigned to this BCS"
        ::= { netmodShmem5CustomBCSEntry 4 }

nShmem5CustomBCSRowStatus OBJECT-TYPE
        SYNTAX  RowStatus
        MAX-ACCESS  read-write
        STATUS  current
        DESCRIPTION
                "Administrative status of this entry"
        ::= { netmodShmem5CustomBCSEntry 5 }

-----------------------------------------------------------------------
--netmodShmem5CustomBCSGroup

netmodShmem5CustomBCSGroup OBJECT IDENTIFIER ::= { shmem5Group 6 }

nShmem5CustomBCSState      OBJECT-TYPE
	SYNTAX  INTEGER {
		disable(1),
		enable(2)
		}
	MAX-ACCESS  read-write
	STATUS  current
	DESCRIPTION
		"Enable default BCS values on all netmods on this switch."
	DEFVAL { disable }
	::= { netmodShmem5CustomBCSGroup 1 }


-----------------------------------------------------------------------
END
-----------------------------------------------------------------------
