-- Do not edit this file.
-- It is generated automatically by mib-expand
-- from event.mib.in and *.mibdef.
--			Ascend Event Mib
--
--			Ascend Communications, Inc
--			1275 Harbor Bay Pkwy
--			Alameda, CA 94502
--			+1 510 769 6001
--			info@ascend.com
--
--		Copyright (c) 1993-1998 Ascend Communications, Inc.
--		All rights reserved.
--
-- $Id: event.mib.in,v 29.5 1999/05/17 16:21:01 clai Exp $
-- This file is generated automatically for TAOS version 8.0.5.
--
-- 11 Mar 97:   rm  Initial creation
-- 24 Apr 97:   rm  Added eventTotalNoModems

ASCEND-EVENT-MIB DEFINITIONS ::= BEGIN

    IMPORTS
	eventGroup
	    FROM ASCEND-MIB
	IpAddress
	    FROM RFC1155-SMI
	Counter
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

	--
	-- Ascend Event group
	--
	-- This group contains a table of events.  The table is
	-- organized in a "ring" buffer fashion.  That is, when
	-- table is full, a new event will overwrite the oldest
	-- event in the table.
	--
	-- Each event is assigned a unique ID number which is also
	-- used as the "index" into the table.	The ID number
	-- increments successively by 1 for each new event.
	--
	-- SNMP should periodically poll this table and retrieve new
	-- events.  The poll scenario is as follows:
	--
	--    1.  Manager retrieves 'eventLatestEventIdNumber' and
	--	  compares it against the value retrieved from the
	--	  previous poll cycle.	No difference implies no
	--	  new events have occured and manager takes no
	--	  further action.  If theres a difference then the
	--	  magnitude of the difference indicates the number
	--	  of new events that have occured and needs to be
	--	  retrieved.
	--    2.  Manager retrieves the new events starting with
	--	  event ID 1 greater than the last one it read.
	--    3.  After retrieving the last event, manager saves
	--	  the event's ID number locally so it can be used
	--	  for comparison on the next poll cycle.
	--
	-- Depending on how often a manager polls this table, it is
	-- possible for the number of unread events to exceed the
	-- table's capacity (given in 'eventMaximumNumberOfEvents').
	-- Since table is organized as a "ring" buffer, retrieving
	-- the oldest unread entries may result in a noSuchName error.
	--
	-- Also note that event IDs may wrap around.  This should be taken
	-- into consideration when determining the number of new events.
	-- If wrap around occurs ('eventOldestEventIdNumber' is greater
	-- than 'eventLatestEventIdNumber') and manager is doing GET-NEXTs
	-- then note that some of the newer events will be retrieve first
	-- before older ones.
	--
	-- Information held in this group is NOT saved across power ups or
	-- restarts.  In particular, event ID assignments will start off at
	-- 1 and not from the last one assigned.  It is highly recommended
	-- that 'sysAbsoluteStartupTime' be retrieved at the start of every
	-- poll cycle.	Comparing it against the previous poll's value will
	-- indicate whether unit restarted or not.
	--

    eventMaximumNumberOfEvents	OBJECT-TYPE
--	SYNTAX		INTEGER (1..'7fffffff'h)
	SYNTAX		INTEGER
	ACCESS		read-only
	STATUS		mandatory
	DESCRIPTION	"The maximum number of event entries that can exist
			 in the event table."
	::= { eventGroup 1 }

    eventOldestEventIdNumber OBJECT-TYPE
--	SYNTAX		INTEGER (1..'7fffffff'h)
	SYNTAX		INTEGER
	ACCESS		read-only
	STATUS		mandatory
	DESCRIPTION	"The event ID number of the oldest event in the table.
			 This value will be 0 until the first event occurs."
	::= { eventGroup 2 }

    eventLatestEventIdNumber  OBJECT-TYPE
--	SYNTAX		INTEGER (1..'7fffffff'h)
	SYNTAX		INTEGER
	ACCESS		read-only
	STATUS		mandatory
	DESCRIPTION	"The event ID number of the most recent event in the
			 table. The SNMP manager should poll this variable
			 periodically and compare it with the previous poll's
			 value to detect the presence of new events.  A value
			 of 0 indicates no events exist in the table."
	::= { eventGroup 3 }

    eventTable		OBJECT-TYPE
	SYNTAX		SEQUENCE OF EventEntry
	ACCESS		not-accessible
	STATUS		mandatory
	DESCRIPTION	"A list of event entries."
	::= { eventGroup 4 }

    eventEntry		OBJECT-TYPE
	SYNTAX		EventEntry
	ACCESS		not-accessible
	STATUS		mandatory
	DESCRIPTION	"An entry containing object variables which
			 describes an event."
	INDEX		{ eventIdNumber }
	::= { eventTable 1 }

    EventEntry ::=
	SEQUENCE {
	    eventIdNumber
		INTEGER,
	    eventTimeStamp
		INTEGER,
	    eventType
		INTEGER,
	    eventCallReferenceNum
		INTEGER,
	    eventDataRate
		INTEGER,
	    eventSlotNumber
		INTEGER,
	    eventSlotLineNumber
		INTEGER,
	    eventSlotChannelNumber
		INTEGER,
	    eventModemSlotNumber
		INTEGER,
	    eventModemOnSlot
		INTEGER,
	    eventCurrentService
		INTEGER,
	    eventUserName
		DisplayString,
	    eventUserIPAddress
		IpAddress,
	    eventUserSubnetMask
		IpAddress,
	    eventDisconnectReason
		INTEGER,
	    eventConnectProgress
		INTEGER,
	    eventCallCharge
		INTEGER,
	    eventCalledPartyID
		DisplayString,
	    eventCallingPartyID
		DisplayString,
	    eventInOctets
		INTEGER,
	    eventOutOctets
		INTEGER,
            eventMultiLinkID
                INTEGER,
	    eventXmitRate
		INTEGER,
            eventTrunkGroup
                INTEGER

	}

    eventIdNumber	OBJECT-TYPE
--	SYNTAX		INTEGER (1..'7fffffff'h)
	SYNTAX		INTEGER
	ACCESS		read-only
	STATUS		mandatory
	DESCRIPTION	"A unique number assigned to every event entry.
			 Numbers are assigned incrementally starting with
			 1 and will wraparound if the upper limit (2147483648)
			 is reached.  Until number wraps around, it represents
			 the total number of events generated."
	::= { eventEntry 1 }

    eventTimeStamp	OBJECT-TYPE
	SYNTAX		INTEGER
	ACCESS		read-only
	STATUS		mandatory
	DESCRIPTION	"The time of occurence for this event in seconds
			 since startup. Use 'sysAbsoluteStartupTime'
			 to convert to absolute time."
	::= { eventEntry 2 }

    eventType		OBJECT-TYPE
	SYNTAX		INTEGER {
			    callOriginated(1),	-- unit dialed out
			    callAnswered(2),	-- unit answered call
			    callCleared(3),	-- call terminated
			    serviceChanged(4),	-- user service changed
			    nameChanged(5),	-- name, IP addr, mask, and
						-- maybe service changed (see
						-- description below)
			    baudRateChanged(6)	-- baud rate change, generated
						--   only for modem connections
						--   since rate is unknown at time
						--   incoming call is detected.
			}
	ACCESS		read-only
	STATUS		mandatory
	DESCRIPTION	"Identifies the type of event associated with
			 this entry.
			 For incoming MPP calls, the initial serviceChanged(4)
			 event will be ppp(3). After negotiations complete,
			 the nameChanged(5) event will specify mpp(5) along
			 with the name, IP addr, and netmask."
	::= { eventEntry 3 }

    eventCallReferenceNum  OBJECT-TYPE
--	SYNTAX		INTEGER (1..'7fffffff'h)
	SYNTAX		INTEGER
	ACCESS		read-only
	STATUS		mandatory
	DESCRIPTION	"A unique number assigned to identify a particular
			 session.  The start of a session is marked by either
			 a callOriginated(1) or a callAnswered(2) event. The
			 end of a session is marked by a callCleared(3) event.
			 Numbers are assigned incrementally starting with 1
			 and will wraparound if the upper limit (2147483648)
			 is reached."
	::= { eventEntry 4 }

    eventDataRate	OBJECT-TYPE
--	SYNTAX		INTEGER (1..'7fffffff'h)
	SYNTAX		INTEGER
	ACCESS		read-only
	STATUS		mandatory
	DESCRIPTION	"The receive data rate for ISDN calls or the baud rate
			 for modem calls.  Rate is given as bits-per-second.
			 Applicable for all 'eventType's except callCleared(3).
			 For callCleared(3), 0 will be returned.  For modem
			 calls, value will be 0 for callAnswered(2) events
			 since rate is unknown at the time incoming call is
			 detected."
	::= { eventEntry 5 }

    eventSlotNumber	OBJECT-TYPE
	SYNTAX		INTEGER
	ACCESS		read-only
	STATUS		mandatory
	DESCRIPTION	"Identifies the slot containing the line call was
			 received or sent over. It's value ranges between 1
			 and the value slotNumber in the 'slots' group. This
			 variable is equivalent to slotIndex in Ascend's
			 slot group.  Applicable only if 'eventType' is
			 callOriginated(1), callAnswered(2), callCleared(3),
			 or baudRateChanged(6) otherwise 0 will be returned."
	::= { eventEntry 6 }

    eventSlotLineNumber OBJECT-TYPE
	SYNTAX		INTEGER
	ACCESS		read-only
	STATUS		mandatory
	DESCRIPTION	"Identifies the line for network slots.	 This variable
			 is equivalent to slotItemIndex in Ascend's slot group.
			 Applicable only if 'eventType' is callOriginated(1),
			 callAnswered(2), callCleared(3), or baudRateChanged(6)
			 otherwise 0 will be returned."
	::= { eventEntry 7 }

    eventSlotChannelNumber  OBJECT-TYPE
	SYNTAX		INTEGER
	ACCESS		read-only
	STATUS		mandatory
	DESCRIPTION	"Identifies the channel for the particular line
			 identified by eventSlotLineNumber.
			 Applicable only if 'eventType' is callOriginated(1),
			 callAnswered(2), callCleared(3), or baudRateChanged(6)
			 otherwise 0 will be returned."
	::= { eventEntry 8 }

    eventModemSlotNumber OBJECT-TYPE
	SYNTAX		INTEGER
	ACCESS		read-only
	STATUS		mandatory
	DESCRIPTION	"Identifies the modem slot on the device.  It's value
			 ranges between 0 and the value slotNumber in Ascend's
			 slots group.  A value of 0 indicates modems are not
			 associated with this connection.  Applicable only if
			 'eventType' is callOriginated(1), callAnswered(2), or
			 baudRateChanged(6) otherwise 0 will be returned."
	::= { eventEntry 9 }

    eventModemOnSlot	OBJECT-TYPE
	SYNTAX		INTEGER
	ACCESS		read-only
	STATUS		mandatory
	DESCRIPTION	"Identifies the particular modem within a modem slot.
			 A value of 0 indicates modems are not associated with
			 this connection.  Applicable only if 'eventType' is
			 callOriginated(1), callAnswered(2), or baudRateChanged(6)
			 otherwise 0 will be returned."
	::= { eventEntry 10 }

    eventCurrentService OBJECT-TYPE
	SYNTAX		INTEGER {
			    none(1), -- not applicable
			    other(2), -- none of the following
			    ppp(3), -- Point-To-Point Protocol
			    slip(4), -- Serial Line IP
			    mpp(5), -- Multichannel PPP
			    x25(6), -- X.25
			    combinet(7), -- Combinet
			    frameRelay(8), -- Frame Relay
			    euraw(9), -- EUNET Raw HDLC Encapsulation
			    euui(10), -- EUNET UI HDLC Encapsulation
			    telnet(11), -- telnet
			    telnetBinary(12), -- binary telnet
			    rawTcp(13), -- raw TCP
			    terminalServer(14), -- terminal server
			    mp(15), -- Multilink PPP
			    virtualConnect(16), -- Virtual connect to a mode
			    dchannelX25(17), -- X.25 using the D Channel
			    dtpt(18), -- psuedo-tunneling PPP
			    ipFax(19), -- IP-Fax connection
			    atm(20), -- ATM connection
			    hdlcNrm(21), -- HDCL-NRM (SDLC) connection
			    voip(22), -- Voice-over-IP connection
			    visa2(23), -- Visa-II connection
			    netToNet(25) -- Net To Net Service ..
			}
	ACCESS		read-only
	STATUS		mandatory
	DESCRIPTION	"The current service provided to the remote user.
			 Applicable only if 'eventType' is serviceChanged(4)
			 or nameChanged(5) otherwise none(1) will be returned."
	::= { eventEntry 11 }

    eventUserName	OBJECT-TYPE
	SYNTAX		DisplayString
	ACCESS		read-only
	STATUS		mandatory
	DESCRIPTION	"The name of the remote user. Applicable only if
			 'eventType' is serviceChanged(4) or nameChanged(5).
			 The null string is returned if the name is unknown
			 or if not applicable. For a Radius DNIS authenticated
			 session, value of User-Name provided in Radius 
			 reply will be used if no second tier authentication 
			 is involved."
	::= { eventEntry 12 }

    eventUserIPAddress	OBJECT-TYPE
	SYNTAX		IpAddress
	ACCESS		read-only
	STATUS		mandatory
	DESCRIPTION	"The IP address of the remote user or login host.  
			 Applicable only if 'eventType' is serviceChanged(4) 
			 nameChanged(5) or callCleared. Value of a raw tcp 
			 login host IP address is returned once a raw tcp 
			 connection was successfully connected earlier in
			 a serviceChanged event.
			 The value 0.0.0.0 is returned if address is unknown
			 or if not applicable."
	::= { eventEntry 13 }

    eventUserSubnetMask OBJECT-TYPE
	SYNTAX		IpAddress
	ACCESS		read-only
	STATUS		mandatory
	DESCRIPTION	"The subnet mask of the remote user. Applicable only
			 if 'eventType' is serviceChanged(4) or nameChanged(5).
			 The value 0.0.0.0 is returned if mask is unknown or
			 if not applicable."
	::= { eventEntry 14 }

    eventDisconnectReason OBJECT-TYPE
	SYNTAX		INTEGER {
			    notApplicable(1), -- :DIS_NOT_APPLICABLE
			    unknown(2), -- catchall if we don't know
			    disconnected(3), -- :DIS_CALL_DISCONNECTED
			    clidAuthFailed(4), -- ID authentication failed
			    clidAuthServTimeout(5), -- RADIUS timeout during ID
			    clidAuthRequestCallback(6), -- ID ok request callback
			    preT310Timeout(7), -- "Send Disc" timer triggered
			    noModemAvailable(9), -- No modems available
			    noModemNoCarrier(10), -- modem never detected DCD
			    noModemLossCarrier(11), -- DCD detected but went inactive
			    noModemResultCodes(12), -- couldn't parse result codes
			    noModemOpenFailed(13), -- failed to open modem
			    noModemOpenFailedDiag(14), -- failed to open modem while modemDiagnostic is on
			    noModemMissingOK(15), -- failed to receive OK from CSMX modem
			    noModemStuckMsgQueue(16), -- stuck CSMX message queue
			    noModemPumpDead(17), -- CSMX modem data pump died
			    noModemForcedDisconnect(18), -- CSMX modem forced to be disconnected after the reboot timeout
			    tsUserExit(20), -- user quit
			    tsIdleTimeout(21), -- timeout waiting for input
			    tsExitTelnet(22), -- exiting telnet forces disconnect
			    tsNoIPAddr(23), -- no IP addr for switching to a framed protocol (eg. SLIP,PPP)
			    tsExitTcp(24), -- exiting raw TCP forces disconnect
			    tsPassWordFail(25), -- exceeded login attempts
			    tsRawTCPDisable(26), -- attempt to raw TCP when its disabled
			    tsControlC(27), -- saw <ctrl-C> during logins
			    tsDestroyed(28), -- :DIS_TERMSRV_DESTROYED
			    tsClosedVirtualConnect(29), -- user closed a virtual connect
			    tsVirtualConnectDestroyed(30), -- active call for a modem outdial session closed. Originating end terminated (ie. controlling terminal server session went down).
			    tsExitRlogin(31), -- rlogin exiting
			    tsRloginBadOption(32), -- bad rlogin command line option specified
			    tsErrorResource(33), -- not enough resources
			    mpNullMessageTimeout(35), -- Failed to receive a NULL MP message in CHANNEL_DEAD_PERIOD timeout.
			    dropUtilization(36), -- session disconnected due to drop in utilization (MPP/BACP/BOD)
			    pppLcpTimeout(40), -- LCP timed out waiting for rsp
			    pppLcpNegotiateFail(41), -- fail to converge on LCP negotiations
			    pppPAPAuthFail(42), -- PAP authentication failed
			    pppCHAPAuthFail(43), -- CHAP authentication failed
			    pppRemoteAuthFail(44), -- authen failed from remote server
			    pppRcvTerminate(45), -- LCP got Terminate rqst from far-end while LCP was in Open state
			    pppCloseEvent(46), -- LCP got Close rqst from upper layer while LCP was in Open state (ie. normal/graceful LCP closure)
			    pppCloseNoNcpsOpened(47), -- Closing LCP because no NCPs were opened
			    pppCloseUnknownMpBundle(48), -- For MP sessions, closing LCP because can't determine which "MP bundle" to add user to.
			    pppCloseMpAddChanFail(49), -- For MP sessions, closing LCP because can't add more channels
			    tsExitErrTooMany(50), -- session tables full
			    tsExitErrResource(51), -- no more resources
			    tsExitErrInvalidIP(52), -- ip address is invalid
			    tsExitErrHostName(53), -- cannot resolve hostname
			    tsExitErrBadPort(54), -- bad or missing port number
			    tsExitErrHostReset(60), -- host reset
			    tsExitErrConnRefused(61), -- connection was refused
			    tsExitErrTimedOut(62), -- connection timed out
			    tsExitErrClosed(63), -- connection closed by foreign host out
			    tsExitErrNetUnreach(64), -- network unreachable
			    tsExitErrHostUnreach(65), -- host unreachable
			    tsExitErrNetAdminUnreach(66), -- network admin unreachable
			    tsExitErrHostAdminUnreach(67), -- host admin unreachable
			    tsExitErrPortUnreach(68), -- port unreachable
			    noPortAvailable(90), -- no port is available
			    sessTimeOut(100), -- session timeout
			    sessFailSecurity(101), -- invalid incoming user
			    sessCallback(102), -- disconnect due to callback enable
			    sessOutgoingInvalid(103), -- disconnect due to validation failure on outgoing call.  May be due to a variety of reasons, e.g. another session has the same IP address, the IP address does not match the remote peers IP address, etc.
			    sessTimeoutEncaps(105), -- session timeout in encapfsm.c
			    sessTimeoutMp(106), -- session timeout in wansess.c (MP)
			    sessDtptSourceCleared(115), -- instigating call is gone
			    invalidProtocol(120), -- protocol disabled/unsupported
			    requestByRadiusClient(150), -- disconnect requested by RADIUS
			    localAdmin(151), -- Call killed by local admin
			    localSnmp(152), -- Call killed by local SNMP
			    v110Timeout(160), -- timeout, resync retries exceed MAX_V110_RETRIES
			    pppAuthTimeout(170), -- timeout waiting trying to authenticate
			    pppIffReleased(171), -- :DIS_PPP_IFF_RELEASED
			    userCallClearRequest(180), -- user performed call clear via Do Hangup
			    systemCallClearRequest(181), -- catchall for call clear requested by system...
			    remoteEndHungUp(185), -- Signal Loss from Remote End e.g. modem turned OFF
			    resourceQuiesced(190), -- Resource has been quiesced
			    maxCallDurationReached(195), -- Max connect time reached
			    lowMemory(201), -- Low Memory
			    slotCardDied(210), -- Slot card died (eg. TNT modem card dies w calls outstanding)
			    pppCbcpRequired(220), -- CBCP required, client failed to initiate
			    vrouterDeleted(230), -- :DIS_VROUTER_DELETED
			    lqmTerminated(240), -- LQM decided link was too lousy to live.
			    backupCleared(241), -- Connection torn down was a backup interface
			    ipfaxCallCleared(250), -- IP FAX call cleared
			    ipfaxLowMemory(251), -- IP FAX call Low Memory
			    ipfaxIncomingError(252), -- IP FAX incomming
			    ipfaxOutgoingError(253), -- IP FAX outgoing
			    ipfaxNoModemAvail(254), -- IP FAX no modem available
			    ipfaxOpenError(255), -- IP FAX should have opened
			    ipfaxTcpWrite(256), -- IP FAX tcp write
			    ipfaxNoSession(257), -- IP FAX session vanished
			    ipfaxParsePhonestr(258), -- IP FAX parse phone string
			    ipfaxBadDecode(260), -- IP FAX bad decode
			    ipfaxDecodeError(261), -- IP FAX bad decode
			    ipfaxNoServer(262), -- IP FAX no configured server
			    x25Termsrv(300), -- X25 unknown
			    mpMasterCardDied(350), -- :DIS_MP_MASTER_CARD_DIED
			    dnisDenied(370), -- DNIS Blocked
			    callbackDialoutFailed(400), -- Callback Dialout failed
			    privateRouteTableNotFound(420), -- Private Route Table Not found
			    filterProfileNotFound(425), -- Filter Profile not found
			    biDirectionalAuthFailed(450), -- bi-directional authentication failed
			    h323DropReasonNull(500),
			    h323DropReasonNormal(501),
			    h323DropReasonDestBusy(502),
			    h323DropReasonDestUnreachable(503),
			    h323DropReasonReject(504),
			    h323DropReasonWanFailure(505),
			    h323DropReasonGatewayResources(506),
			    h323DropReasonNoBandwidth(507),
			    h323DropReasonGwNotRegistered(508),
			    h323DropReasonInvalidPin(509),
			    h323DropReasonInvalidDnis(510),
			    h323DropReasonNoLanAnswer(511),
			    h323DropReasonStateMachine(512),
			    h323DropReasonNoLanDisconnect(513),
			    h323DropReasonFegwCauseCode(514),
			    h323DropReasonMaxPinAttempts(515),
			    h323DropReasonCoderDenied(516),
			    h323DropReasonHostDrop(517),
			    q850UnassignedNumber(801),
			    q850NoRoute(802),
			    q850NoRouteToDest(803),
			    q850ChannelUnacceptable(806),
			    q850NormalClearing(816),
			    q850UserBusy(817),
			    q850NoUserResponding(818),
			    q850UserAlertNoAnswer(819),
			    q850CallRejected(821),
			    q850NumberChanged(822),
			    q850DestOutOfOrder(827),
			    q850InvalidNumberFormat(828),
			    q850FacilityRejected(829),
			    q850RespToStatEnq(830),
			    q850UnspecifiedCause(831),
			    q850NoCircuitAvailable(834),
			    q850NetworkOutOfOrder(838),
			    q850TemporaryFailure(841),
			    q850NetworkCongestion(842),
			    q850AccessInfoDiscarded(843),
			    q850ReqChannelNotAvail(844),
			    q850PreEmpted(845),
			    q850ResourceNotAvail(847),
			    q850FacilityNotSubscribed(850),
			    q850OutgoingCallBarred(852),
			    q850IncomingCallBarred(854),
			    q850BearCapNotAvail(858),
			    q850ServiceNotAvail(863),
			    q850CapNotImplemented(865),
			    q850ChanNotImplemented(866),
			    q850FacilityNotImplement(869),
			    q850InvalidCallRef(881),
			    q850ChanDoesNotExist(882),
			    q850IncompatibleDest(888),
			    q850MandatoryIeMissing(896),
			    q850NonexistentMsg(897),
			    q850WrongMessage(898),
			    q850NonexistentIe(899),
			    q850InvalidElemContents(900),
			    q850WrongMsgForStat(901),
			    q850TimerExpiry(902),
			    q850MandatoryIeLenErr(903),
			    q850ProtocolError(911),
			    q850InterworkingUnspec(927)
			}
	ACCESS		read-only
	STATUS		mandatory
	DESCRIPTION	"Reason for call disconnecting.  Applicable only if
			 'eventType' is callCleared(3) otherwise notApplicable(1)
			 will be returned."
	::= { eventEntry 15 }

    eventConnectProgress OBJECT-TYPE
	SYNTAX		INTEGER {
                            prNotApplicable(1), -- :PR_NOT_APPLICABLE
                            prUnknown(2), -- :PR_UNKNOWN
                            prNotConnected(7), -- :PR_NOT_CONNECTED
                            prCallUp(10), -- :PR_CALL_UP
                            prDialSrvcBlocked(11), -- This dnis is blocked
                            prModemUp(30), -- :PR_MODEM_UP
                            prModemWaitDCD(31), -- :PR_MODEM_AWAITING_DCD
                            prModemWaitCodes(32), -- :PR_MODEM_AWAITING_CODES
                            prTermSrvStarted(40), -- terminal server sess started (needn't be logged in yet)
                            prRawTcpStarting(41), -- Started raw tcp
                            prTelnetStarting(42), -- Started immediate telnet
                            prRawTcpConnect(43), -- raw connected to host
                            prTelnetConnect(44), -- telnet connected to host
                            prRloginStarting(45), -- rlogin started
                            prRloginConnect(46), -- rlogin connect
                            prTermSrvStartedThruCR(47), -- termsrv authentication started through user entering carriage return
                            prModemOutdialCallUp(50), -- call is active on a modem outdial session
                            prLanSessionUp(60), -- routing/bridging session up
                            prOpeningLCP(61), -- :PR_OPENING_LCP
                            prOpeningCCP(62), -- :PR_OPENING_CCP
                            prOpeningIPNCP(63), -- :PR_OPENING_IPNCP
                            prOpeningBNCP(64), -- :PR_OPENING_BNCP
                            prLCPOpened(65), -- LCP in Open state
                            prCCPOpened(66), -- CCP in Open state
                            prIPNCPOpened(67), -- IP NCP in Open state
                            prBNCPOpened(68), -- Bridging NCP in Open state
                            prLCPStateInitial(69), -- LCP in Initial state
                            prLCPStateStarting(70), -- LCP in Starting state
                            prLCPStateClosed(71), -- LCP in Closed state
                            prLCPStateStopped(72), -- LCP in Stopped state
                            prLCPStateClosing(73), -- LCP in Closing state
                            prLCPStateStopping(74), -- LCP in Stopping state
                            prLCPStateReqSent(75), -- LCP in Req-Sent state
                            prLCPStateAckRecd(76), -- LCP in Ack-Rcvd state
                            prLCPStateAckSent(77), -- LCP in Ack-Sent state
                            prIPXNCPOpened(80), -- IPX NCP in Open state
                            prAtNcpOpened(81), -- AT NCP in Open state
                            prBACPOpening(82), -- BACP being opened
                            prBACPOpened(83), -- BACP is now open
                            prCBCPOpening(84), -- CBCP being opened
                            prCBCPOpened(85), -- CBCP is now open
                            prV110Up(90), -- V110 is connected
                            prV110StateOpened(91), -- V110 in V110_STATE_OPENED 	state
                            prV110StateCarrier(92), -- V110 in V110_STATE_CARRIER 	state
                            prV110StateReset(93), -- V110 in V110_STATE_RESET 	state
                            prV110StateClosed(94), -- V110 in V110_STATE_CLOSED 	state
                            prClidCallBackReq(100), -- CLID indicates callback required
                            prClidAuthFailed(101), -- CLID auth failed
                            prClidAuthTimeout(102), -- CLID auth timed out waiting for server response
                            prFRLinkInactive(120), -- Frame relay link inactive (ie. LMI negotiations in progress)
                            prFRLinkActive(121), -- Frame relay link has end-to-end connectivity (ie. PVCs can pass data)
                            prStartingAuth(200), -- Starting Auth layer
                            prOpeningAuth(201), -- Starting Auth layer
                            prSkippingAuth(202), -- Skipping Auth layer
                            prAuthOpened(203), -- Auth layer opened
                            prH323NewIncomingCallFromWan(300), -- h323 incoming call from wan
                            prH323DetectingPinFromWan(301), -- h323 detecting pin number
                            prH323DetectingDnisFromWan(302), -- h323 detecting dial number
                            prH323SendingArqToGatekeeper(303), -- h323 sending ARQ to gatekeeper
                            prH323ReceivedAcfFromGatekeeper(304), -- h323 received ACF from gatekeeper
                            prH323WaitingH225AlertingFromLan(305), -- h323 waiting for H225 alerting
                            prH323WaitingH225ProceedingFromLan(306), -- h323 waiting for H225 proceeding
                            prH323PlayingErrPromptToWan(307), -- h323 playing error prompt
                            prH323HairpinDialingOutToWan(308), -- h323 dialing out a hairpin call
                            prH323ReceivedH225SetupFromLan(309), -- h323 received H225 call setup
                            prH323DialingOutToWan(310), -- h323 dialing out to wan
                            prH323WanAnsweredAndRtpNotUpYet(311), -- h323 wan up and waiting for rtp up
                            prH323CallConnected(312), -- h323 call connected
                            prH323PlayingBusyPromptToWan(313), -- h323 playing busy prompt
                            prH323DisconnectingRtp(314), -- h323 disconnecting rtp connection
                            prH323RtpDisconnected(315), -- h323 rtp disconnected
                            prH323FaxDisconnected(316), -- h323 fax disconnected
                            prSs7VoipChangeParameter(400), -- changing rtp parameters
                            prSs7VoipRtpOpened(401), -- rtp-connection opened
                            prSs7VoipRtpClosed(402), -- rtp closed rtp-connection
                            prSs7VoipTerminateRtp(403), -- ss7 terminating rtp-connection
                            prSs7VoipCedDetected(404) -- ced tone detected
			}
	ACCESS		read-only
	STATUS		mandatory
	DESCRIPTION	"State of the connection before disconnecting.
			 Applicable only if 'eventType' is callCleared(3)
		 	 otherwise prNotApplicable(1) will be returned."
	::= { eventEntry 16 }

    eventCallCharge	OBJECT-TYPE
	SYNTAX		INTEGER
	ACCESS		read-only
	STATUS		mandatory
	DESCRIPTION	"The call charge for this user.
			 Applicable only if 'eventType' is callCleared( 3 )
			 otherwise 0 will be returned.
			 A value of 0 is returned if entry is invalid."
	::= { eventEntry 17 }

    eventCalledPartyID	OBJECT-TYPE
	SYNTAX		DisplayString
	ACCESS		read-only
	STATUS		mandatory
	DESCRIPTION	"The called party ID. Applicable only if
			 'eventType' is callCleared(3),
			 callAnswered(2) or callOriginated(2)
			 The null string is returned if
			 the called party ID is unknown or if is not
			 applicable."
	::= { eventEntry 18 }

    eventCallingPartyID	OBJECT-TYPE
	SYNTAX		DisplayString
	ACCESS		read-only
	STATUS		mandatory
	DESCRIPTION	"The calling party ID. Applicable only if
			 'eventType' is callCleared(3),
			 callAnswered(2) or callOriginated(2)
			 The null string is returned if
			 the calling party ID is unknown or if is not
			 applicable."
	::= { eventEntry 19 }

    eventInOctets OBJECT-TYPE
	SYNTAX		INTEGER
	ACCESS		read-only
	STATUS		mandatory
	DESCRIPTION	"Identifies the total number of InOctets
			 during this call.
			 Applicable only if 'eventType' is callCleared(3),
			 otherwise 0 will be returned."
	::= { eventEntry 20 }

    eventOutOctets OBJECT-TYPE
	SYNTAX		INTEGER
	ACCESS		read-only
	STATUS		mandatory
	DESCRIPTION	"Identifies the total number of OutOctets
			 during this call.
			 Applicable only if 'eventType' is callCleared(3),
			 otherwise 0 will be returned."
	::= { eventEntry 21 }

    eventMultiLinkID    OBJECT-TYPE
        SYNTAX          INTEGER
        ACCESS          read-only
        STATUS          mandatory
        DESCRIPTION     "MultiLinkID applies to sessions that are part of a
                        Multilink bundle. Applicable if 'eventType' is
                        callCleared(3), serviceChanged(4) or nameChanged(5)
                        else 0 will be returned."
        ::= { eventEntry 22 }

    eventXmitRate	OBJECT-TYPE
--	SYNTAX		INTEGER (1..'7fffffff'h)
	SYNTAX		INTEGER
	ACCESS		read-only
	STATUS		mandatory
	DESCRIPTION	"The transmit data rate for ISDN calls or the baud rate
			 for modem calls.  Rate is given as bits-per-second.
			 Applicable for all 'eventType's except callCleared(3).
			 For callCleared(3), 0 will be returned.  For modem
			 calls, value will be 0 for callAnswered(2) events
			 since rate is unknown at the time incoming call is
			 detected."
	::= { eventEntry 23 }

   eventTrunkGroup OBJECT-TYPE
        SYNTAX          INTEGER
        ACCESS          read-only
        STATUS          mandatory
        DESCRIPTION     "Trunk Group Number
                         for outgoing call only
                         Applicable only if 'eventType' is callEstablished or
                         callOrignated,
                         otherwise 0 will be returned."
        ::= { eventEntry 24 }


    eventCurrentActiveCalls	OBJECT-TYPE
	SYNTAX			INTEGER
	ACCESS			read-only
	STATUS			mandatory
	DESCRIPTION		"The number of calls currently active."
	::= { eventGroup 5 }

    eventCurrentActiveSessions	OBJECT-TYPE
	SYNTAX			INTEGER
	ACCESS			read-only
	STATUS			mandatory
	DESCRIPTION		"The number of sessions currently active."
	::= { eventGroup 6 }

    eventTotalCalls		OBJECT-TYPE
	SYNTAX			Counter
	ACCESS			read-only
	STATUS			mandatory
	DESCRIPTION		"The total number of active calls since system
				 startup."
	::= { eventGroup 7 }

    eventTotalSessions		OBJECT-TYPE
	SYNTAX			Counter
	ACCESS			read-only
	STATUS			mandatory
	DESCRIPTION		"The total number of active sessions since system
				 startup."
	::= { eventGroup 8 }

    eventTotalCallsAnswered 	OBJECT-TYPE
	SYNTAX			Counter
	ACCESS			read-only
	STATUS			mandatory
	DESCRIPTION		"The total number of calls answered since system
				 startup."
	::= { eventGroup 9 }

    eventTotalCallsOriginated	OBJECT-TYPE
	SYNTAX			Counter
	ACCESS			read-only
	STATUS			mandatory
	DESCRIPTION		"The total number of calls originated since system
				 startup."
	::= { eventGroup 10 }

    eventTotalCallsCleared	OBJECT-TYPE
	SYNTAX			Counter
	ACCESS			read-only
	STATUS			mandatory
	DESCRIPTION		"The total number of calls cleared since system
				 startup."
	::= { eventGroup 11 }

    eventTotalBaudRateChanges   OBJECT-TYPE
	SYNTAX			Counter
	ACCESS			read-only
	STATUS			mandatory
	DESCRIPTION		"The total number of baud rate change events
				 since system startup."
	::= { eventGroup 12 }

    eventTotalServiceChanges   OBJECT-TYPE
	SYNTAX			Counter
	ACCESS			read-only
	STATUS			mandatory
	DESCRIPTION		"The total number of service change events
				 since system startup."
	::= { eventGroup 13 }

    eventTotalNameChanges   OBJECT-TYPE
	SYNTAX			Counter
	ACCESS			read-only
	STATUS			mandatory
	DESCRIPTION		"The total number of name change events
				 since system startup."
	::= { eventGroup 14 }

    eventTotalNoModems          OBJECT-TYPE
	SYNTAX			Counter
	ACCESS			read-only
	STATUS			mandatory
	DESCRIPTION		"The total number of unaccepted calls because of
                                 the unavailability of modems, since system startup."
	::= { eventGroup 15 }

END
