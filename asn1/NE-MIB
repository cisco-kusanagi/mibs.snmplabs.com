NE-MIB 

          DEFINITIONS ::= BEGIN

          -- This file contains the defintion of the network elements 
	  -- configuration as configured by Gateway network element.

          IMPORTS
	          phyRingSlotNo, phyRingPortNo, logRingVPortNo 
                      FROM RING-MIB
                  IpAddress
                      FROM RFC1155-SMI
                  OBJECT-TYPE, MODULE-IDENTITY
                      FROM SNMPv2-SMI
                  ne
                      FROM CORIOLIS-MIB;

          neMIB MODULE-IDENTITY
              LAST-UPDATED "0007270000Z"
              ORGANIZATION "Coriolis Networks"
              CONTACT-INFO
                      "        Shubhra Garg

                       Postal: 330 Codman Hill Road,
                               Boxboro MA, 01719.

                          Tel: +1 978 264 1904
                          Fax: +1 978 264 1929

                       E-mail: shubhra@coriolisnet.com"
              DESCRIPTION
                      "The MIB module for network elements as
                       configured by Gateway Network Element"
              ::= { ne 2 }

         cfgNeTable  OBJECT-TYPE
              SYNTAX  SEQUENCE OF CfgNeEntry 
              MAX-ACCESS  not-accessible
              STATUS  current
              DESCRIPTION
              "A table that contains information about the network elements
               configuration as configured by Gateway network element."
              ::= { ne 1 }

          cfgNeEntry OBJECT-TYPE
              SYNTAX  CfgNeEntry
              MAX-ACCESS  not-accessible
              STATUS  current
              DESCRIPTION
              "Configuration information about a network element as configured
	       by gateway network element"
              INDEX  { cfgNeIPAddr }
              ::= { cfgNeTable 1 }


          CfgNeEntry ::=
              SEQUENCE {
                  cfgNeIPAddr
                      IpAddress,
		  cfgNePriMacAddr
		      OCTET STRING,
		  cfgNeSecMacAddr
		      OCTET STRING,
		  cfgNeSpareMacAddr
		       OCTET STRING
              }


	  cfgNeIPAddr OBJECT-TYPE
	      SYNTAX  IpAddress
	      MAX-ACCESS not-accessible
	      STATUS current
	      DESCRIPTION 
	      "The IP address of NE as configured by GNE"
              ::= { cfgNeEntry 1 }


	  cfgNePriMacAddr OBJECT-TYPE
	      SYNTAX  OCTET STRING(SIZE(6))
	      MAX-ACCESS read-write
	      STATUS current
	      DESCRIPTION 
	      "The MAC address of primary management module on network element"
              ::= { cfgNeEntry 2 }

	  cfgNeSecMacAddr OBJECT-TYPE
	      SYNTAX  OCTET STRING(SIZE(6))
	      MAX-ACCESS read-write
	      STATUS current
	      DESCRIPTION 
	      "The MAC address of secondary management module on network 
	      element"
              ::= { cfgNeEntry 3 }

	  cfgNeSpareMacAddr OBJECT-TYPE
	      SYNTAX  OCTET STRING(SIZE(6))
	      MAX-ACCESS read-write
	      STATUS current
	      DESCRIPTION 
	      "The MAC address of spare management module on network 
	      element. It is useful when swapping management modules on network
	      element."
              ::= { cfgNeEntry 4 }

        
         neReachTable  OBJECT-TYPE
              SYNTAX  SEQUENCE OF NeReachEntry 
              MAX-ACCESS  not-accessible
              STATUS  current
              DESCRIPTION
              "A table that lists rings to the reachable network elements."
              ::= { ne 3 }

	 neReachEntry OBJECT-TYPE
              SYNTAX  NeReachEntry
              MAX-ACCESS  not-accessible
              STATUS  current
              DESCRIPTION
              "Lists a ring to reachable network element."
              INDEX  { neReachIpAddr, phyRingSlotNo, phyRingPortNo, logRingVPortNo }
              ::= { neReachTable 1 }

          NeReachEntry ::=
              SEQUENCE {
                  neReachIpAddr
                      IpAddress
              }

	  neReachIpAddr OBJECT-TYPE
	      SYNTAX  IpAddress
	      MAX-ACCESS read-only
	      STATUS current
	      DESCRIPTION 
	      "The IP address of a reachable NE."
              ::= { neReachEntry 1 }

          END
