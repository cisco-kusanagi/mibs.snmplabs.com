-- *****************************************************************
-- CODAN-SMI.txt:  Codan Enterprise Structure of Management Information
--
-- July 1 2009, Magda Raltcheva
--
-- Copyright (c) 2009 by Codan Limited.
-- All rights reserved.
--
-- *****************************************************************

CODAN-SMI DEFINITIONS ::= BEGIN

IMPORTS
	MODULE-IDENTITY,
	enterprises
		FROM SNMPv2-SMI;  

codanGroup MODULE-IDENTITY
   LAST-UPDATED "200902110000Z"
   ORGANIZATION "Codan Limited."
   CONTACT-INFO
        "       Magda Raltcheva
        Postal: Codan Limited
                81 Graves St.
                Newton 5074
                Australia
        Tel:    +61-8-83050311
        Fax:    +61-8-83050411
        Web:	www.codan.com.au"

	DESCRIPTION
		"The Structure of Management Information for the
		 Codan enterprise.
		 Copyright(c) 2009 All rights reserved"

	REVISION      "200902110000Z"
	DESCRIPTION
		"1.0 Initial version of this MIB module."
        ::= { enterprises 23304 }   -- assigned by IANA

--
-- Subtree for all Codan products MIBs.
--
codanMibs		OBJECT IDENTIFIER ::= { codanGroup 1 }
satcomMibs		OBJECT IDENTIFIER ::= { codanGroup 2 }

END
