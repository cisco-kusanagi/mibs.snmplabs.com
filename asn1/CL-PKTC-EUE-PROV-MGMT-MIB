CL-PKTC-EUE-PROV-MGMT-MIB DEFINITIONS ::= BEGIN

IMPORTS
    OBJECT-TYPE,
    MODULE-IDENTITY,
    BITS                                      -- TBD: Do not import BITS
                       FROM SNMPv2-SMI        -- RFC2578
    OBJECT-GROUP,
    MODULE-COMPLIANCE  FROM SNMPv2-CONF       -- RFC2580
    SnmpAdminString
                       FROM SNMP-FRAMEWORK-MIB
    InetAddressType, 
    InetAddress
                       FROM INET-ADDRESS-MIB
    pktcEUEMibs        FROM CLAB-DEF-MIB;
    
                           
pktcEUEProvMgmtMIB MODULE-IDENTITY
    LAST-UPDATED "200708220000Z" -- TBD: Change date 
    ORGANIZATION "Cable Television Laboratories, Inc."
    CONTACT-INFO
            "Sumanth Channabasappa 
             Postal: Cable Television Laboratories, Inc
             858 Coal Creek Circle
             Louisville, CO 80027
             U.S.A.
             Phone: +1 303 661 9100
             Fax: +1 303 661 9199
             E-mail:mibs@cablelabs.com

             Acknowledgements:
             Eugene Nechamkin, Broadcom
             Thomas Clack, Broadcom  - Primary author
             Josh Littlefield, Cisco
 
             , and members of the PacketCable PACM Focus Team. "

    DESCRIPTION
            "This MIB module provides the provisioning and management 
            MIB module for the E-UE Provisioning Framework."
    ::= { pktcEUEMibs 4 }

-- Administrative assignments   
pktcEUEProvMgmtNotifications     OBJECT IDENTIFIER ::= { pktcEUEProvMgmtMIB 0 } 
pktcEUEProvMgmtObjects           OBJECT IDENTIFIER ::= { pktcEUEProvMgmtMIB 1 }
pktcEUEProvMgmtConformance       OBJECT IDENTIFIER ::= { pktcEUEProvMgmtMIB 2 } 



pktcEUEProvMgmtVersion OBJECT-TYPE
    SYNTAX      SnmpAdminString(SIZE(0..6))
    MAX-ACCESS  read-only
    STATUS      current
    DESCRIPTION
        " This MIB Object represents the Provisioning and Management Module 
          version. The eUE MUST set this MIB Object to value of '1.0'."
    ::= { pktcEUEProvMgmtObjects  1 }


-- DHCP Servers for IPv6
pktcEUEDhcpv6ServerId1   OBJECT-TYPE
       SYNTAX      OCTET STRING(SIZE(0..31))
       MAX-ACCESS  read-only
       STATUS      current
       DESCRIPTION
           " This MIB Object contains the primary DHCP Server identifier
             the EUE was provided with, during provisioning.

             The eUE MUST populate this MIB Object with the first
             thirty-two bytes of the DHCPv6 Server identifier 
             provided within the eCM's CL_OPTION_CCCV6, 
             sub-option 1."
       ::= { pktcEUEProvMgmtObjects 2 }

pktcEUEDhcpv6ServerId2  OBJECT-TYPE
       SYNTAX      InetAddress
       MAX-ACCESS  read-only
       STATUS      current
       DESCRIPTION
           " This MIB Object contains the secondary DHCP Server identifier
             the EUE was provided with, during provisioning.

             The eUE MUST populate this MIB Object with the first
             thirty-two bytes of the DHCPv6 Server identifier 
             provided within the eCM's CL_OPTION_CCCV6, 
             sub-option 2."
             ::= { pktcEUEProvMgmtObjects 3 }


pktcEUEDhcpv6ServerAddressType  OBJECT-TYPE
       SYNTAX      InetAddressType
       MAX-ACCESS  read-only
       STATUS      current
       DESCRIPTION
           "This MIB Object contains the DHCP Server Address type 
            contained in the MIB Object 'pktcEUEDhcpv6ServerAddress'.
            Valid values are 'ipv6(2)' and 'unknown(0)'."
             ::= { pktcEUEProvMgmtObjects 4 }


pktcEUEDhcpv6ServerAddress  OBJECT-TYPE
       SYNTAX      InetAddress
       MAX-ACCESS  read-only
       STATUS      current
       DESCRIPTION
           "This MIB Object contains the DHCPv6 Server address from
            which the eUE obtained its IPv6 address, if the eUE 
            is in IPv6 mode, and can obtain the information."
             ::= { pktcEUEProvMgmtObjects 5 }

-- DNS Servers for IPv6
pktcEUEDnsv6ServerAddressType  OBJECT-TYPE
       SYNTAX      InetAddressType
       MAX-ACCESS  read-only
       STATUS      current
       DESCRIPTION
           "This MIB Object contains the DHCP Server Address type 
            contained in the MIB Object 'pktcEUEDhcpv6ServerAddress'.
            Valid values are 'ipv6(2)' and 'unknown(0)'."
       ::= { pktcEUEProvMgmtObjects 6}

pktcEUEDnsv6ServerAddress1  OBJECT-TYPE
       SYNTAX      InetAddress
       MAX-ACCESS  read-write
       STATUS      current
       DESCRIPTION
           "This MIB Object contains the primary DNSv6 Server address 
            which the eUE obtained via DHCPv6, when the eUE 
            is in IPv6 mode."
       ::= { pktcEUEProvMgmtObjects 7 }

pktcEUEDnsv6ServerAddress2  OBJECT-TYPE
       SYNTAX      InetAddress
       MAX-ACCESS  read-write
       STATUS      current
       DESCRIPTION
           "This MIB Object contains the secondary DNSv6 Server address 
            which the eUE obtained via DHCPv6, when the eUE 
            is in IPv6 mode."
       ::= { pktcEUEProvMgmtObjects 8 }

-- Object Groups
-- The object groups used in this MIB module are imported from
-- the PKTC-IETF-MTA-MIB MIB (RFC4682).

-- Conformance Statements
pktcEUEProvMgmtCompliances  OBJECT IDENTIFIER ::= { pktcEUEProvMgmtConformance 1 }
pktcEUEProvMgmtGroups       OBJECT IDENTIFIER ::= { pktcEUEProvMgmtConformance 2 }

-- Compliance Statements
pktcEUEProvMgmtCompliance MODULE-COMPLIANCE
    STATUS  current
    DESCRIPTION
        "The compliance statement for PacketCable eUE devices
        that implement the PacketCable eUE Provisioning Framework.
        
        This compliance statement specifies, for the PacketCable 
        eUE Provisioning framework, the required objects from the 'Multimedia 
        Terminal Adapter(MTA)Management Information Base for 
        PacketCable and IPCablecom-Compliant Devices'(RFC 4682)MIB.
        
        Some objects from RFC4682 have been enhanced for applicability
        to eUEs. Similarly, inapplicable objects are clearly indicated.  

        As indicated in the eUE Provisioning specification, references
        to E-MTA and eMTA in RFC4682 are to be understood to be applicable
        to E-UE and eUE, respectively. "  
    REFERENCE
        "PacketCable E-UE Provisioning Framework Specification"
    
    MODULE   PKTC-IETF-MTA-MIB
        MANDATORY-GROUPS {
               pktcMtaGroup,
               pktcMtaNotificationGroup
        }


-- The following pktcEUEDevBase group describes the base eUE objects

  OBJECT  pktcMtaDevResetNow
  DESCRIPTION
      " This MIB Object controls the eUE software reset.
        The eUE MUST return a value of 'false' upon an Object read.  
        The eUE MUST reset itself when this object is set to a value of 
        'false', and perform the following actions:
          - All Services (if present) are immediately terminated.
          - Any sessions (even on the behalf of Users) are gracefully
            terminated.
          - The provisioning flow is started at step eUE-1.
          
        If a value is written into an instance of 'pktcMtaDevResetNow',
        the agent MUST NOT retain the supplied value across eUE 
        re-initializations or reboots. "
    
  --  OBJECT  pktcMtaDevSerialNumber                  - Same as PKTC-IETF-MTA-MIB  
  --  OBJECT  pktcMtaDevSwCurrentVers                 - Same as PKTC-IETF-MTA-MIB  
  --  OBJECT  pktcMtaDevFQDN                          - Same as PKTC-IETF-MTA-MIB

  OBJECT  pktcMtaDevEndPntCount                     
  MIN-ACCESS  not-accessible
  DESCRIPTION
      " Object not applicable for the eUE."
            
  OBJECT  pktcMtaDevEnabled
  DESCRIPTION
      " This MIB Object contains the eUE Admin Status of this device.
        If this object is set to 'true', the eUE is
        administratively enabled, and the eUE MUST be able to
        interact with the PacketCable entities, such as the
        Provisioning Server, KDC, and other eUEs on all
        PacketCable interfaces.
           
        If this object is set to 'false', the eUE is
        administratively disabled and MUST do the following:
        - Deregister any users;
        - Stop any applications. 
           
        Additionally, the eUE MUST maintain the SNMP Interface
        for management and also the SNMP Key management interface.
        Also, the eUE MUST NOT continue Kerberized key management
        with any devices, except with the Provisioning server,until 
        this object is set to 'true'.

        If a value is written into an instance of
        pktcMtaDevEnabled, the agent MUST NOT retain the supplied
        value across eUE re-initializations or reboots."
  --  OBJECT  pktcMtaDevTypeIdentifier                - Same as PKTC-IETF-MTA-MIB
  --  OBJECT  pktcMtaDevProvisioningState             - Same as PKTC-IETF-MTA-MIB
  --  OBJECT  pktcMtaDevHttpAccess                    - Same as PKTC-IETF-MTA-MIB 
  --  OBJECT  pktcMtaDevProvisioningTimer             - Same as PKTC-IETF-MTA-MIB
  --  OBJECT  pktcMtaDevProvisioningCounter           - Same as PKTC-IETF-MTA-MIB
  --  OBJECT  pktcMtaDevErrorOidIndex                 - Same as PKTC-IETF-MTA-MIB
  --  OBJECT  pktcMtaDevErrorOid                      - Same as PKTC-IETF-MTA-MIB
  --  OBJECT  pktcMtaDevErrorValue                    - Same as PKTC-IETF-MTA-MIB
  --  OBJECT  pktcMtaDevErrorReason                   - Same as PKTC-IETF-MTA-MIB


-- The following object group describes server access and parameters used
      
  OBJECT  pktcMtaDevDhcpServerAddressType          
  DESCRIPTION
      " This MIB Object is only required to support the DHCPv4 address type. "

-- NOTE: pktcMtaDevServerDhcp1 and pktcMtaDevServerDhcp2 are intended for
--       IPv4 DHCP Servers per RFC 4682. IPv6 DHCP information is contained 
--       in the prov-mgmt extension MIB module.
  --  OBJECT  pktcMtaDevServerDhcp1                   - Same as PKTC-IETF-MTA-MIB
  --  OBJECT  pktcMtaDevServerDhcp2                   - Same as PKTC-IETF-MTA-MIB


  OBJECT  pktcMtaDevDnsServerAddressType       
  DESCRIPTION
      " This MIB Object is only required to support the DHCPv4 address type. "

-- NOTE: pktcMtaDevServerDns1 and pktcMtaDevServerDns2 are intended for
--       IPv4 DNS Servers per RFC 4682. IPv6 DNS information is contained 
--       in the prov-mgmt extension MIB module.
 
  --  OBJECT  pktcMtaDevServerDns1                    - Same as PKTC-IETF-MTA-MIB
  --  OBJECT  pktcMtaDevServerDns2                    - Same as PKTC-IETF-MTA-MIB

  OBJECT  pktcMtaDevTimeServerAddressType     
  MIN-ACCESS  not-accessible
  DESCRIPTION
      " This MIB Object is not applicable for the eUE."
         
  OBJECT  pktcMtaDevTimeServer                
  MIN-ACCESS  not-accessible
  DESCRIPTION
      " This MIB Object not applicable for the eUE."  
                                                     
  --  OBJECT  pktcMtaDevConfigFile                    - Same as PKTC-IETF-MTA-MIB
  --  OBJECT  pktcMtaDevSnmpEntity                    - Same as PKTC-IETF-MTA-MIB
  --  OBJECT  pktcMtaDevProvConfigHash                - Same as PKTC-IETF-MTA-MIB
  --  OBJECT  pktcMtaDevProvConfigKey                 - Same as PKTC-IETF-MTA-MIB
  --  OBJECT  pktcMtaDevProvConfigEncryptAlg          - Same as PKTC-IETF-MTA-MIB
  --  OBJECT  pktcMtaDevProvSolicitedKeyTimeout       - Same as PKTC-IETF-MTA-MIB
  --  OBJECT  pktcMtaDevProvUnsolicitedKeyMaxTimeout  - Same as PKTC-IETF-MTA-MIB
  --  OBJECT  pktcMtaDevProvUnsolicitedKeyNomTimeout  - Same as PKTC-IETF-MTA-MIB
  --  OBJECT  pktcMtaDevProvUnsolicitedKeyMaxRetries  - Same as PKTC-IETF-MTA-MIB
  --  OBJECT  pktcMtaDevProvKerbRealmName             - Same as PKTC-IETF-MTA-MIB
  --  OBJECT  pktcMtaDevProvState                     - Same as PKTC-IETF-MTA-MIB


-- The following object group describes the security objects.

  --  OBJECT  pktcMtaDevManufacturerCertificate       - Same as PKTC-IETF-MTA-MIB
  --  OBJECT  pktcMtaDevCertificate                   - Same as PKTC-IETF-MTA-MIB
  --  OBJECT  pktcMtaDevCorrelationId                 - Same as PKTC-IETF-MTA-MIB
  --  OBJECT  pktcMtaDevTelephonyRootCertificate      - Same as PKTC-IETF-MTA-MIB
     
  OBJECT  pktcMtaDevRealmAvailSlot    
  MIN-ACCESS  not-accessible
  DESCRIPTION
      " Object not applicable for the eUE."
          
  OBJECT  pktcMtaDevRealmName  
  MIN-ACCESS  read-only
  DESCRIPTION
      " eUE will only have one row entry for this object." 
             
  OBJECT  pktcMtaDevRealmPkinitGracePeriod  
  MIN-ACCESS  read-write
  DESCRIPTION
      " eUE will only have one row entry for this object."
  
  OBJECT  pktcMtaDevRealmTgsGracePeriod  
  MIN-ACCESS  read-write
  DESCRIPTION
      " eUE will only have one row entry for this object."
    
  OBJECT  pktcMtaDevRealmOrgName 
  MIN-ACCESS  read-write
  DESCRIPTION
      " eUE will only have one row entry for this object."
    
  OBJECT  pktcMtaDevRealmUnsolicitedKeyMaxTimeout  
  MIN-ACCESS  read-write
  DESCRIPTION
      " eUE will only have one row entry for this object."
   
  OBJECT  pktcMtaDevRealmUnsolicitedKeyNomTimeout 
  MIN-ACCESS  read-write
  DESCRIPTION
      " eUE will only have one row entry for this object."    
    
  OBJECT  pktcMtaDevRealmUnsolicitedKeyMaxRetries  
  MIN-ACCESS  read-write  
  DESCRIPTION
      " eUE will only have one row entry for this object" 
            
  OBJECT  pktcMtaDevRealmStatus   
  MIN-ACCESS  read-write
  DESCRIPTION
      " Support for the values notInService(2), notReady(3), createAndGo(4),
        createAndWait(5), and destroy(6) is not required.
         
        This table only has one row." 
             
  OBJECT  pktcMtaDevCmsAvailSlot                   
  MIN-ACCESS   not-accessible
  DESCRIPTION
      " Object not applicable for the eUE."
                 
  OBJECT  pktcMtaDevCmsFqdn 
  MIN-ACCESS   not-accessible
  DESCRIPTION
      " Object not applicable for the eUE."
                     
  OBJECT  pktcMtaDevCmsKerbRealmName
  MIN-ACCESS   not-accessible
  DESCRIPTION
      " Object not applicable for the eUE."

  OBJECT  pktcMtaDevCmsMaxClockSkew
  MIN-ACCESS   not-accessible
  DESCRIPTION
      " Object not applicable for the eUE."

  OBJECT  pktcMtaDevCmsSolicitedKeyTimeout       
  MIN-ACCESS   not-accessible
  DESCRIPTION
      " Object not applicable for the eUE."

  OBJECT  pktcMtaDevCmsUnsolicitedKeyMaxTimeout  
  MIN-ACCESS   not-accessible
  DESCRIPTION
      " Object not applicable for the eUE."

  OBJECT  pktcMtaDevCmsUnsolicitedKeyNomTimeout  
  MIN-ACCESS   not-accessible
  DESCRIPTION
      " Object not applicable for the eUE."

  OBJECT  pktcMtaDevCmsUnsolicitedKeyMaxRetries  
  MIN-ACCESS   not-accessible
  DESCRIPTION
      " Object not applicable for the eUE."

  OBJECT  pktcMtaDevCmsIpsecCtrl                 
  MIN-ACCESS   not-accessible
  DESCRIPTION
      " Object not applicable for the eUE."

  OBJECT  pktcMtaDevCmsStatus                    
  MIN-ACCESS   not-accessible
  DESCRIPTION
      " Object not applicable for the eUE."
  
  OBJECT  pktcMtaDevResetKrbTickets 
  SYNTAX  BITS {
                 invalidateProvOnReboot   (0)
               }
  DESCRIPTION
      " the eUE only support the 
        invalidateProvOnReboot bit (bit 0) for this object. The 
        invalidateAllCmsOnReboot bit (bit 1) is not supported."

                
  MODULE   
        MANDATORY-GROUPS {
               pktcEUEProvMgmtGroup
        }
    ::= { pktcEUEProvMgmtCompliances 1 }
     
pktcEUEProvMgmtGroup OBJECT-GROUP
      OBJECTS { 
          pktcEUEProvMgmtVersion,
          pktcEUEDhcpv6ServerId1,
          pktcEUEDhcpv6ServerId2,
          pktcEUEDhcpv6ServerAddressType,
          pktcEUEDhcpv6ServerAddress,
          pktcEUEDnsv6ServerAddressType,
          pktcEUEDnsv6ServerAddress1,
          pktcEUEDnsv6ServerAddress2
      }
      STATUS  current
      DESCRIPTION
            "The eUE Operator Group."
      ::= { pktcEUEProvMgmtGroups 1} 
        
-- Notifications  
  --  pktcMtaDevProvisioningEnrollment  NOTIFICATION-TYPE     - Same as PKTC-IETF-MTA-MIB
  --  pktcMtaDevProvisioningStatus      NOTIFICATION-TYPE     - Same as PKTC-IETF-MTA-MIB

 END
