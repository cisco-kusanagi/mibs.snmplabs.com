-- 
-- Copyright 1999 by Fore Systems, Inc. 
-- Converted to SMIv2 rfc 2578,2579,2580 - STD 58
--
-- Copyright 1994-1995 by Fore Systems, Inc.

Fore-J2-MIB DEFINITIONS ::= BEGIN

IMPORTS
        Integer32,
	Counter32,
	OBJECT-TYPE,
	MODULE-IDENTITY				FROM SNMPv2-SMI
	asx					FROM Fore-Common-MIB;

------------------------------------------------------------------------
-- The implementation of the foreJ2 tables is mandatory
-- for all switches that have J2 port module.

foreJ2			           MODULE-IDENTITY
          LAST-UPDATED         "9911050000Z"
          ORGANIZATION         "FORE"
          CONTACT-INFO         
               "      Postal:   FORE Systems Inc.
                                 1000 FORE Drive
                                 Warrendale, PA 15086-7502
                       Tel:      +1 724 742 6900
                       Email:    nm_mibs@fore.com
                       Web:      http://www.fore.com"
          DESCRIPTION
           "write something interesting here"
    ::= { asx 6 }

j2ConfGroup		OBJECT IDENTIFIER ::= { foreJ2 1 }
j2StatsGroup		OBJECT IDENTIFIER ::= { foreJ2 2 }

------------------------------------------------------------------------
-- The J2 configuration Group

j2ConfTable OBJECT-TYPE
	SYNTAX	SEQUENCE OF J2ConfEntry
	MAX-ACCESS	not-accessible
	STATUS	current
	DESCRIPTION
		"A table of J2 switch port configuration information."
	::= { j2ConfGroup 1 }

j2ConfEntry OBJECT-TYPE
	SYNTAX	J2ConfEntry
	MAX-ACCESS	not-accessible
	STATUS	current
	DESCRIPTION
		"A table entry containing J2 configuration information for each
		port."
	INDEX	{ j2ConfBoard, j2ConfModule, j2ConfPort }
	::= { j2ConfTable 1 }

J2ConfEntry ::=
	SEQUENCE {
		j2ConfBoard		Integer32,
		j2ConfModule		Integer32,
		j2ConfPort		Integer32,
		j2LineLength		INTEGER,
		j2LoopbackConfig	INTEGER,
		j2TxClockSource		INTEGER,
		j2LineStatus		INTEGER,
		j2IdleUnassignedCells   INTEGER
	}

j2ConfBoard OBJECT-TYPE
	SYNTAX	Integer32
	MAX-ACCESS	read-only
	STATUS	current
	DESCRIPTION
		"The index of this port's switch board."
	::= { j2ConfEntry 1 }

j2ConfModule OBJECT-TYPE
	SYNTAX	Integer32
	MAX-ACCESS	read-only
	STATUS	current
	DESCRIPTION
		"The network module of this port."
	::= { j2ConfEntry 2 }

j2ConfPort OBJECT-TYPE
	SYNTAX	Integer32
	MAX-ACCESS	read-only
	STATUS	current
	DESCRIPTION
		"The number of this port."
	::= { j2ConfEntry 3 }

j2LineLength OBJECT-TYPE
	SYNTAX	INTEGER {
		j2ShortLine (1),
		j2LongLine (2)
		}
	MAX-ACCESS	read-write
	STATUS	current
	DESCRIPTION
		"This variable represents the length of the physical medium
		connected to the J2 interface:

		j2ShortLine (1) means the line is a short line with less than
		4db of attenuation from the transmitting source.

		j2LongLine (2) means the line is a long line, with greater than
		4db of attenuation from the transmitting source."
	DEFVAL	{ j2ShortLine }
	::= { j2ConfEntry 4 }

j2LoopbackConfig OBJECT-TYPE
	SYNTAX	INTEGER {
		j2NoLoop (1),
		j2LineLoop (2),
		j2DiagLoop (3),
		j2OtherLoop (4)
		}
	MAX-ACCESS	read-write
	STATUS	current
	DESCRIPTION
		"This variable represents the loopback configuration of the J2
		interface.

		j2NoLoop (1) means that the interface is not in a loopback
		state.

		j2LineLoop (2) means that receive signal is looped back for
		retransmission without passing through the port's reframing
		function.

		j2DiagLoop (3) means that the transmit data stream is looped
		back to the receiver.

		j2OtherLoop (4) means that the interface is in a loopback that
		is not defined here."
	DEFVAL	{ j2NoLoop }
	::= { j2ConfEntry 5 }

j2TxClockSource OBJECT-TYPE
	SYNTAX	INTEGER {
		rxTiming (1),
		localTiming (2)
		}
	MAX-ACCESS	read-write
	STATUS	current
	DESCRIPTION
		"The source of the transmit clock."
	DEFVAL	{ localTiming }
	::= { j2ConfEntry 6 }

j2LineStatus OBJECT-TYPE
	SYNTAX	INTEGER (1..65534)
	MAX-ACCESS	read-only
	STATUS	current
	DESCRIPTION
		"This variable indicates the Line Status of the interface. The
		variable contains loopback state information and failure state
		information. It is a bit map represented as a sum. The
		j2NoAlarm should be set if and only if no other flag is set.

		The various bit positions are:
		1	j2NoAlarm
		2	j2RxLOF	Receive Loss of Frame
		4	j2RxLOC	Receive Loss of Clock (Not used anymore)
		8	j2RxAIS	Receive Alarm Indication Signal
		16	j2TxLOC	Transmit Loss of Clock (Not used anymore)
		32	j2RxRAIS	Receive Remote Alarm Indication Signal
		64	j2RxLOS	Receive Loss of Signal
		128	j2TxRAIS Transmit Yellow
				( Remote Alarm Indication Signal)
		256	j2Other	any line status not defined here
		32768	j2RxLCD	Receiving LCD failure indication."
	DEFVAL	{ 1 }
	::= { j2ConfEntry 7 }


j2IdleUnassignedCells OBJECT-TYPE
	SYNTAX	INTEGER {
		unassigned(1),
		idle(2)
		}
	MAX-ACCESS	read-write
	STATUS	current
	DESCRIPTION
		"This variable indicates the types of cells that should be 
		sent in case there is no real data to send. According to the 
		ATM Forum, Unassigned cells should be sent (octet 1-3 are 
		0's, octet 4 is 0000xxx0, where x is 'don't care'). According
		to the CCITT specifications, Idle cells should be sent 
		(everything is '0' except for the CLP bit which is '1'). By 
		default, unassigned cells are transmitted in case there is 
		no data to send."
	DEFVAL { unassigned }
	::= { j2ConfEntry 8 }

------------------------------------------------------------------------
-- The J2 Statistics Group

j2ErrorTable OBJECT-TYPE
	SYNTAX	SEQUENCE OF J2ErrorEntry
	MAX-ACCESS	not-accessible
	STATUS	current
	DESCRIPTION
		"A table of J2 error counters."
	::= { j2StatsGroup 1 }

j2ErrorEntry OBJECT-TYPE
	SYNTAX	J2ErrorEntry
	MAX-ACCESS	not-accessible
	STATUS	current
	DESCRIPTION
		"A table entry containing J2 error counters."
	INDEX	{ j2ErrorBoard, j2ErrorModule, j2ErrorPort }
	::= { j2ErrorTable 1 }

J2ErrorEntry ::=
	SEQUENCE {
		j2ErrorBoard		Integer32,
		j2ErrorModule		Integer32,
		j2ErrorPort		Integer32,
		j2B8ZSCodingErrors	Counter32,
		j2CRC5Errors		Counter32,
		j2FramingErrors		Counter32,
		j2RxLossOfFrame		Counter32,
		j2RxLossOfClock		Counter32,
		j2RxAIS			Counter32,
		j2TxLossOfClock		Counter32,
		j2RxRemoteAIS		Counter32,
		j2RxLossOfSignal	Counter32
	}

j2ErrorBoard OBJECT-TYPE
	SYNTAX	Integer32
	MAX-ACCESS	read-only
	STATUS	current
	DESCRIPTION
		"The index of this port's switch board."
	::= { j2ErrorEntry 1 }

j2ErrorModule OBJECT-TYPE
	SYNTAX	Integer32
	MAX-ACCESS	read-only
	STATUS	current
	DESCRIPTION
		"The network module of this port."
	::= { j2ErrorEntry 2 }

j2ErrorPort OBJECT-TYPE
	SYNTAX	Integer32
	MAX-ACCESS	read-only
	STATUS	current
	DESCRIPTION
		"The number of this port."
	::= { j2ErrorEntry 3 }

j2B8ZSCodingErrors OBJECT-TYPE
	SYNTAX	Counter32
	MAX-ACCESS	read-only
	STATUS	current
	DESCRIPTION
		"The number of B8ZS coding violation errors."
	::= { j2ErrorEntry 4 }

j2CRC5Errors OBJECT-TYPE
	SYNTAX	Counter32
	MAX-ACCESS	read-only
	STATUS	current
	DESCRIPTION
		"The number of CRC-5 received errors."
	::= { j2ErrorEntry 5 }

j2FramingErrors OBJECT-TYPE
	SYNTAX	Counter32
	MAX-ACCESS	read-only
	STATUS	current
	DESCRIPTION
		"The number of framing patterns received in error."
	::= { j2ErrorEntry 6 }

j2RxLossOfFrame OBJECT-TYPE
	SYNTAX	Counter32
	MAX-ACCESS	read-only
	STATUS	current
	DESCRIPTION
		"The number of seconds during which the receiver was
		experiencing Loss Of Frame."
	::= { j2ErrorEntry 7 }

j2RxLossOfClock OBJECT-TYPE
	SYNTAX	Counter32
	MAX-ACCESS	read-only
	STATUS	current
	DESCRIPTION
		"The number of seconds during which the receiver was not
		observing transitions on the received clock signal."
	::= { j2ErrorEntry 8 }

j2RxAIS OBJECT-TYPE
	SYNTAX	Counter32
	MAX-ACCESS	read-only
	STATUS	current
	DESCRIPTION
		"The number of seconds during which the receiver detected an
		Alarm Indication Signal."
	::= { j2ErrorEntry 9 }

j2TxLossOfClock OBJECT-TYPE
	SYNTAX	Counter32
	MAX-ACCESS	read-only
	STATUS	current
	DESCRIPTION
		"The number of seconds during which the transmitter was
		experiencing Loss Of Clock."
	::= { j2ErrorEntry 10 }

j2RxRemoteAIS OBJECT-TYPE
	SYNTAX	Counter32
	MAX-ACCESS	read-only
	STATUS	current
	DESCRIPTION
		"The number of seconds during which the receiver observed the
		Alarm Indication Signal in the m-bits channel."
	::= { j2ErrorEntry 11 }

j2RxLossOfSignal OBJECT-TYPE
	SYNTAX	Counter32
	MAX-ACCESS	read-only
	STATUS	current
	DESCRIPTION
		"The number of seconds during which the transmitter was
		experien cing Loss Of Signal."
	::= { j2ErrorEntry 12 }

------------------------------------------------------------------------

j2AtmTable OBJECT-TYPE
	SYNTAX	SEQUENCE OF J2AtmEntry
	MAX-ACCESS	not-accessible
	STATUS	current
	DESCRIPTION
		"A table of J2 ATM statistics information."
	::= { j2StatsGroup 2 }

j2AtmEntry OBJECT-TYPE
	SYNTAX	J2AtmEntry
	MAX-ACCESS	not-accessible
	STATUS	current
	DESCRIPTION
		"A table entry containing J2 ATM statistics information."
	INDEX	{ j2AtmBoard, j2AtmModule, j2AtmPort }
	::= { j2AtmTable 1 }

J2AtmEntry ::=
	SEQUENCE {
		j2AtmBoard		Integer32,
		j2AtmModule		Integer32,
		j2AtmPort		Integer32,
		j2AtmHCSs		Counter32,
		j2AtmRxCells		Counter32,
		j2AtmTxCells		Counter32,
		j2AtmLCDs		Counter32
	}

j2AtmBoard OBJECT-TYPE
	SYNTAX	Integer32
	MAX-ACCESS	read-only
	STATUS	current
	DESCRIPTION
		"The index of this port's switch board."
	::= { j2AtmEntry 1 }

j2AtmModule OBJECT-TYPE
	SYNTAX	Integer32
	MAX-ACCESS	read-only
	STATUS	current
	DESCRIPTION
		"The network module of this port."
	::= { j2AtmEntry 2 }

j2AtmPort OBJECT-TYPE
	SYNTAX	Integer32
	MAX-ACCESS	read-only
	STATUS	current
	DESCRIPTION
		"The number of this port."
	::= { j2AtmEntry 3 }

j2AtmHCSs OBJECT-TYPE
	SYNTAX	Counter32
	MAX-ACCESS	read-only
	STATUS	current
	DESCRIPTION
		"Number of header check sequence (HCS) error events. The HCS
		is a CRC-8 calculation over the first 4 octets of the ATM cell
		header."
	::= { j2AtmEntry 4 }

j2AtmRxCells OBJECT-TYPE
	SYNTAX	Counter32
	MAX-ACCESS	read-only
	STATUS	current
	DESCRIPTION
		"Number of ATM cells that were received."
	::= { j2AtmEntry 5 }

j2AtmTxCells OBJECT-TYPE
	SYNTAX	Counter32
	MAX-ACCESS	read-only
	STATUS	current
	DESCRIPTION
		"Number of non-null ATM cells that were transmitted."
	::= { j2AtmEntry 6 }

j2AtmLCDs OBJECT-TYPE
	SYNTAX	Counter32
	MAX-ACCESS	read-only
	STATUS	current
	DESCRIPTION
		"The number of seconds in which Loss of Cell Delineation (LCD)
		has occurred.  An LCD defect is detected when an out of cell
		delination state has persisted for 4ms.  An LCD defect is
		cleared when the sync state has been maintained for 4ms."
	::= { j2AtmEntry 7 }

END
