-- extracted from draft-steinberger-frsi-00.txt
-- at Sat Jun 17 07:07:28 2000

FRCI-MIB DEFINITIONS ::= BEGIN

IMPORTS
    MODULE-IDENTITY, OBJECT-TYPE,
    mib-2                                   FROM SNMPv2-SMI
    TEXTUAL-CONVENTION, RowStatus,
    TimeStamp                               FROM SNMPv2-TC
    MODULE-COMPLIANCE, OBJECT-GROUP         FROM SNMPv2-CONF
    ifIndex, InterfaceIndex                 FROM IF-MIB;

    frciMIB MODULE-IDENTITY
        LAST-UPDATED "200006161500Z" -- June 16, 2000
        ORGANIZATION "IETF TBD Working Group"
        CONTACT-INFO
          "IETF TBD Working Group

           WG Charter:
           WG-email:
           Subscribe:
           Email Archive:

           Chair:
           Email:

           WG editor:  Robert Steinberger
                       Paradyne Networks
           Email:      rsteinberger@paradyne.com

           Co-author:  Orly Nicklass
                       RAD Data Communications Ltd.
           EMail:      Orly_n@rad.co.il"
        DESCRIPTION
            "The MIB module to allow insertion of selected circuit into
             the ifTable."
        REVISION "200006161500Z"
        DESCRIPTION
            "o  Original Draft"
        ::= { mib-2 xxx } -- RFC editor - IANA assigns xxx

    -- Textual Conventions

    FrciFlowDir ::= TEXTUAL-CONVENTION
        STATUS  current
        DESCRIPTION
            "The direction of data flow thru a circuit.

                transmit(1) - Only transmitted data
                receive(2)  - Only received data
                both(3)     - Both transmitted and received data."
        SYNTAX  INTEGER {
                  transmit(1),
                  receive(2),
                  both(3)
                }

    frciObjects      OBJECT IDENTIFIER ::= { frciMIB 1 }
    frciCapabilities OBJECT IDENTIFIER ::= { frciMIB 2 }
    frciConformance  OBJECT IDENTIFIER ::= { frciMIB 3 }

    -- The Frame Relay Circuit Interface Circuit Table
    --
    -- This table is used to define and display the frame relay
    -- circuits that are added to the ifTable.  It maps circuits
    -- to their respective ifIndex values.

    frciCircuitTable  OBJECT-TYPE
        SYNTAX      SEQUENCE OF FrciCircuitEntry
        MAX-ACCESS  not-accessible
        STATUS      current
        DESCRIPTION
            "The Frame Relay Circuit Interface Circuit Table."
        ::= { frciObjects 1 }

    frciCircuitEntry OBJECT-TYPE
        SYNTAX      FrciCircuitEntry
        MAX-ACCESS  not-accessible
        STATUS      current
        DESCRIPTION
            "An entry in the Frame Relay Circuit Interface
             Circuit Table."
        INDEX    { frciCircuitObject, frciCircuitFlow }
        ::= { frciCircuitTable 1 }

    FrciCircuitEntry ::=
        SEQUENCE {
            --
            -- Index Control Variables
            --
            frciCircuitObject      OBJECT IDENTIFIER,
            frciCircuitFlow        FrciFlowDir,
            frciCircuitStatus      RowStatus,
            --
            -- Data variables
            --
            frciCircuitIfIndex     InterfaceIndex,
            frciCircuitCreateTime  TimeStamp
        }

    frciCircuitObject OBJECT-TYPE
        SYNTAX      OBJECT IDENTIFIER
        MAX-ACCESS  not-accessible
        STATUS      current
        DESCRIPTION
            "This value contains the object identifier that uniquely
             describes the circuit that is to be added to this table.
             The object identifier should be that of the first field
             on the table that contains the circuit.  The index sub
             identifiers should uniquely define the circuit.

             The purpose of this object identifier is to point a
             network manager to the table in which the circuit was
             created as well as define the circuit on which the
             interface is defined.

             Valid tables for this object are the frCircuitTable from
             the Frame Relay DTE MIB(FRAME-RELAY-DTE-MIB) or the
             frPVCEndptTable from the Frame Relay Service MIB
             (FRNETSERV-MIB).  However, it does not exclude enterprise
             MIBs used for the same purpose."
        ::= { frciCircuitEntry 1 }

    frciCircuitFlow OBJECT-TYPE
        SYNTAX      FrciFlowDir
        MAX-ACCESS  not-accessible
        STATUS      current
        DESCRIPTION
            "The direction of data flow through the circuit for which
             the virtual interface is defined. The following define
             the information that the virtual interface will report.

                transmit(1) - Only transmitted frames
                receive(2)  - Only received frames
                both(3)     - Both transmitted and received frames.

             The need to monitor directional flow depends on the
             application for which the circuit is created.  For example,
             Monitoring of protocols passed on a circuit using
             RMON-II (RFC 2021) does not capture the direction the flow.
             This is left to the circuit."
        ::= { frciCircuitEntry 2 }

    frciCircuitStatus OBJECT-TYPE
        SYNTAX      RowStatus
        MAX-ACCESS  read-create
        STATUS      current
        DESCRIPTION
            "The status of the current row.  This object is
             used to add, delete, and disable rows in this
             table.  When the status changes to active(1), a row
             will also be added to the interface map table below
             and a row will be added to the ifTable.  These rows
             SHOULD not be removed until the status is changed
             from active(1).  The value of ifIndex for the row that
             is added to the ifTable is determined by the agent
             and MUST follow the rules of the ifTable.  The value
             of ifType for that interface will be <?need ifType?>.

             When this object is set to destroy(6), the associated
             row in the interface map table will be removed and the
             ifIndex will be removed from the ifTable.  Removing
             the ifIndex MAY initiate a chain of events that causes
             changes to other tables as well.

             The rows added to this table MUST have a valid object
             identifier for frciCircuitObject.  This means that the
             referenced object must exist and it must be in a table
             that supports circuits.

             The object referenced by frciCircuitObject MUST exist
             prior to transitioning a row to active(1).  If at any
             point the object referenced by frciCircuitObject does not
             exist or the row containing it is not in the active(1)
             state, the status SHOULD report notReady(3).  The effects
             transitioning from active(1) to notReady(3) are the same
             as those caused by setting the status to destroy(6)."
        ::= { frciCircuitEntry 3 }

    frciCircuitIfIndex OBJECT-TYPE
        SYNTAX      InterfaceIndex
        MAX-ACCESS  read-only
        STATUS      current
        DESCRIPTION
            "The ifIndex that the agent assigns to this row."
        ::= { frciCircuitEntry 4 }

    frciCircuitCreateTime OBJECT-TYPE
        SYNTAX      TimeStamp
        MAX-ACCESS  read-only
        STATUS      current
        DESCRIPTION
            "This object returns the value of sysUpTime at the time
             the value of frciCircuitStatus last transitioned to
             active(1).  If frciCircuitStatus has never been active(1),
             this object SHOULD return 0."
        ::= { frciCircuitEntry 5 }

    -- The Frame Relay Circuit Interface Map Table
    --
    -- This table maps the ifIndex values that are assigned to
    -- rows in the circuit table back to the objects that define
    -- the circuits.

    frciIfMapTable  OBJECT-TYPE
        SYNTAX      SEQUENCE OF FrciIfMapEntry
        MAX-ACCESS  not-accessible
        STATUS      current
        DESCRIPTION
            "The Frame Relay Circuit Interface Map Table."
        ::= { frciObjects 2 }

    frciIfMapEntry OBJECT-TYPE
        SYNTAX      FrciIfMapEntry
        MAX-ACCESS  not-accessible
        STATUS      current
        DESCRIPTION
            "An entry in the Frame Relay Circuit Interface
             Map Table."
        INDEX    { ifIndex }
        ::= { frciIfMapTable 1 }

    FrciIfMapEntry ::=
        SEQUENCE {
            --
            -- Mapped Object Variables
            --
            frciIfMapObject      OBJECT IDENTIFIER,
            frciIfMapFlow        FrciFlowDir
        }

    frciIfMapObject OBJECT-TYPE
        SYNTAX      OBJECT IDENTIFIER
        MAX-ACCESS  read-only
        STATUS      current
        DESCRIPTION
            "This value contains the value of frciCircuitObject that
             corresponds to the current ifIndex."
        ::= { frciIfMapEntry 1 }

    frciIfMapFlow   OBJECT-TYPE
        SYNTAX      FrciFlowDir
        MAX-ACCESS  read-only
        STATUS      current
        DESCRIPTION
            "The value contains the value of frciCircuitFlow that
             corresponds to the current ifIndex."
        ::= { frciIfMapEntry 2 }

    -- Conformance Information

    frciMIBGroups      OBJECT IDENTIFIER ::= { frciConformance 1 }
    frciMIBCompliances OBJECT IDENTIFIER ::= { frciConformance 2 }

    --
    -- Compliance Statements
    --

    frciCompliance MODULE-COMPLIANCE
        STATUS  current
        DESCRIPTION
            "The compliance statement for SNMPv2 entities
             which support with Frame Relay Circuit Interfaces.
             This group defines the minimum level of support
             required for compliance."
        MODULE -- this module
            MANDATORY-GROUPS { frciCircuitGroup,
                               frciIfMapGroup }

            OBJECT      frciCircuitStatus
            SYNTAX      INTEGER { active(1) } -- subset of RowStatus
            MIN-ACCESS  read-only
            DESCRIPTION
               "Write access is not required, and only one of the six
                enumerated values for the RowStatus textual convention
                need be supported, specifically: active(1)."

    ::= { frciMIBCompliances 1 }

    --
    -- Units of Conformance
    --
    frciCircuitGroup  OBJECT-GROUP
       OBJECTS {
            frciCircuitStatus,
            frciCircuitIfIndex,
            frciCircuitCreateTime
       }
       STATUS  current
       DESCRIPTION
           "A collection of required objects providing
            information from the circuit table."
       ::= { frciMIBGroups 1 }

    frciIfMapGroup OBJECT-GROUP
       OBJECTS {
            frciIfMapObject,
            frciIfMapFlow
       }
       STATUS  current
       DESCRIPTION
           "A collection of required objects providing
            information from the interface map table."
       ::= { frciMIBGroups 2 }
END
