WS-INFRA-NTP-MIB DEFINITIONS ::= BEGIN
 
		IMPORTS
			OBJECT-GROUP, MODULE-COMPLIANCE			
				FROM SNMPv2-CONF			
			IpAddress, OBJECT-TYPE, MODULE-IDENTITY			
				FROM SNMPv2-SMI			
			TruthValue, DateAndTime, DisplayString			
				FROM SNMPv2-TC			
			wsInfraNTP			
				FROM WS-INFRA-SMI-MIB;

		-- 1.3.6.1.4.1.388.14.1.10.1
		wsInfraNTPMIB MODULE-IDENTITY 
			LAST-UPDATED "200506271058Z"		-- June 27, 2005 at 10:58 GMT
			ORGANIZATION 
				"Symbol Technologies"
			CONTACT-INFO 
				"Symbol Technologies, Inc.
				Customer Service
				Postal:
				One Symbol Plaza
				Holtsville, NY 11742-1300
				USA
				Tel: +1. 631.738.6213
				E-mail: support@symbol.com
				Web: http://www.symbol.com/support"
			DESCRIPTION 
				"Description."
			REVISION "200605261237Z"		-- May 26, 2006 at 12:37 GMT
			DESCRIPTION 
				"01a13"
			REVISION "200510121421Z"		-- October 12, 2005 at 14:21 GMT
			DESCRIPTION 
				"01a12"
			REVISION "200508121358Z"		-- August 12, 2005 at 13:58 GMT
			DESCRIPTION 
				"01a11"
			REVISION "200506281158Z"		-- June 28, 2005 at 11:58 GMT
			DESCRIPTION 
				"01a10"
			REVISION "200506271434Z"		-- June 27, 2005 at 14:34 GMT
			DESCRIPTION 
				"01a09"
			REVISION "200506241207Z"		-- June 24, 2005 at 12:07 GMT
			DESCRIPTION 
				"01a08"
			REVISION "200506231317Z"		-- June 23, 2005 at 13:17 GMT
			DESCRIPTION 
				"01a07"
			REVISION "200506221034Z"		-- June 22, 2005 at 10:34 GMT
			DESCRIPTION 
				"01a06"
			REVISION "200506201105Z"		-- June 20, 2005 at 11:05 GMT
			DESCRIPTION 
				"01a05"
			REVISION "200506091524Z"		-- June 09, 2005 at 15:24 GMT
			DESCRIPTION 
				"01a04"
			REVISION "200506071843Z"		-- June 07, 2005 at 18:43 GMT
			DESCRIPTION 
				"01a03"
			REVISION "200505041613Z"		-- May 04, 2005 at 16:13 GMT
			DESCRIPTION 
				"01a02"
			REVISION "200505041058Z"		-- May 04, 2005 at 10:58 GMT
			DESCRIPTION 
				"01a01"
			::= { wsInfraNTP 1 }

		-- 1.3.6.1.4.1.388.14.1.10.1.1
		wsInfraNtpEnable OBJECT-TYPE
			SYNTAX TruthValue
			MAX-ACCESS read-write
			STATUS obsolete
			DESCRIPTION
				"Enable NTP."
			::= { wsInfraNTPMIB 1 }

		-- 1.3.6.1.4.1.388.14.1.10.1.2
		wsInfraNtp1Server OBJECT-TYPE
			SYNTAX IpAddress
			MAX-ACCESS read-write
			STATUS obsolete
			DESCRIPTION
				"Preffered NTP Server IPAddr."
			::= { wsInfraNTPMIB 2 }

		-- 1.3.6.1.4.1.388.14.1.10.1.3
		wsInfraNtp2Server OBJECT-TYPE
			SYNTAX IpAddress
			MAX-ACCESS read-write
			STATUS obsolete
			DESCRIPTION
				"1st alternate NTP Server IPAddr."
			::= { wsInfraNTPMIB 3 }

		-- 1.3.6.1.4.1.388.14.1.10.1.4
		wsInfraNtp3Server OBJECT-TYPE
			SYNTAX IpAddress
			MAX-ACCESS read-write
			STATUS obsolete
			DESCRIPTION
				"2nd alternate NTP Server IPAddr."
			::= { wsInfraNTPMIB 4 }

		-- 1.3.6.1.4.1.388.14.1.10.1.5
		wsInfraNtpTimeZone OBJECT-TYPE
			SYNTAX DisplayString
			MAX-ACCESS read-write
			STATUS current
			DESCRIPTION
				"NTP time zone
				currently support
				CET
				EET
				EST5EDT
				CST6CDT
				MST7MDT
				PST8PDT
				Africa/Cairo
				Africa/Casablanca
				Africa/Harare
				Africa/Johannesburg
				Africa/Lagos
				Africa/Nairobi
				America/Anchorage
				America/Bogota
				America/Buenos_Aires
				America/Caracas
				America/Chicago
				America/Costa_Rica
				America/Denver
				America/Indianapolis
				America/Los_Angeles
				America/Mexico_City
				America/Montreal
				America/New_York
				America/Phoenix
				America/Santiago
				America/Sao_Paulo
				America/St_Johns
				America/Tegucigalpa
				America/Thule
				America/Winnipeg
				Asia/Almaty
				Asia/Baghdad
				Asia/Baku
				Asia/Bangkok
				Asia/Calcutta
				Asia/Chongqing
				Asia/Colombo
				Asia/Dhaka
				Asia/Dubai
				Asia/Hong_Kong
				Asia/Irkutsk
				Asia/Jerusalem
				Asia/Kabul
				Asia/Karachi
				Asia/Katmandu
				Asia/Krasnoyarsk
				Asia/Kuala_Lumpur
				Asia/Kuwait
				Asia/Magadan
				Asia/Rangoon
				Asia/Seoul
				Asia/Singapore
				Asia/Shanghai
				Asia/Taipei
				Asia/Tehran
				Asia/Tokyo
				Asia/Vladivostok
				Asia/Yakutsk
				Asia/Yekaterinburg
				Atlantic/Azores
				Atlantic/Cape_Verde
				Atlantic/Reykjavik
				Atlantic/South_Georgia
				Australia/Adelaide
				Australia/Brisbane
				Australia/Hobart
				Australia/Perth
				Australia/Sydney
				Europe/Amsterdam
				Europe/Athens
				Europe/Belgrade
				Europe/Berlin
				Europe/Brussels
				Europe/Bucharest
				Europe/Copenhagen
				Europe/Dublin
				Europe/Helsinki
				Europe/Istanbul
				Europe/Lisbon
				Europe/London
				Europe/Madrid
				Europe/Moscow
				Europe/Paris
				Europe/Prague
				Europe/Rome
				Europe/Stockholm
				Europe/Warsaw
				Europe/Zurich
				Pacific/Apia
				Pacific/Auckland
				Pacific/Fiji
				Pacific/Guam
				Pacific/Honolulu
				Pacific/Tongatapu
				"
			::= { wsInfraNTPMIB 5 }

		-- 1.3.6.1.4.1.388.14.1.10.1.6
		wsInfraNtpCurrentDateTime OBJECT-TYPE
			SYNTAX DateAndTime
			MAX-ACCESS read-write
			STATUS current
			DESCRIPTION
				"Current Date and Time. If NTP is not running, or has not 
				yet synchronized time, this value will be 0."
			::= { wsInfraNTPMIB 6 }

		-- 1.3.6.1.4.1.388.14.1.10.1.7
		wsInfraNtpAllTimeZones OBJECT-TYPE
			SYNTAX OCTET STRING (SIZE (0..5000))
			MAX-ACCESS read-only
			STATUS current
			DESCRIPTION
				"Lists all possible timezones separated by newlines."
			::= { wsInfraNTPMIB 7 }

		-- 1.3.6.1.4.1.388.14.1.10.1.100
		wsInfraNTPMIBConformance OBJECT IDENTIFIER ::= { wsInfraNTPMIB 100 }

		-- 1.3.6.1.4.1.388.14.1.10.1.100.1
		wsInfraNTPMIBGroups OBJECT IDENTIFIER ::= { wsInfraNTPMIBConformance 1 }

		-- 1.3.6.1.4.1.388.14.1.10.1.100.1.1
		wsInfraNTPGroup OBJECT-GROUP
			OBJECTS { wsInfraNtpAllTimeZones, wsInfraNtpCurrentDateTime, wsInfraNtpTimeZone }
			STATUS current
			DESCRIPTION 
				"Description."
			::= { wsInfraNTPMIBGroups 1 }

		-- 1.3.6.1.4.1.388.14.1.10.1.100.1.2
		wsInfraNTPGroupObsolete OBJECT-GROUP
			OBJECTS { wsInfraNtpEnable, wsInfraNtp1Server, wsInfraNtp2Server, wsInfraNtp3Server }
			STATUS obsolete
			DESCRIPTION 
				"Description."
			::= { wsInfraNTPMIBGroups 2 }

		-- 1.3.6.1.4.1.388.14.1.10.1.100.2
		wsInfraNTPMIBCompliances OBJECT IDENTIFIER ::= { wsInfraNTPMIBConformance 2 }

		-- 1.3.6.1.4.1.388.14.1.10.1.100.2.1
		wsInfraNTPMIBCompliance MODULE-COMPLIANCE
			STATUS current
			DESCRIPTION 
				"Description."
			MODULE -- this module
				MANDATORY-GROUPS { wsInfraNTPGroup }
			::= { wsInfraNTPMIBCompliances 1 }
	END
