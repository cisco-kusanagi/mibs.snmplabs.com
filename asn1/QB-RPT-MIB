QB-RPT-MIB DEFINITIONS ::= BEGIN

	IMPORTS 
	MODULE-IDENTITY, OBJECT-TYPE, Unsigned32
			 FROM SNMPv2-SMI
	TEXTUAL-CONVENTION
		FROM SNMPv2-TC
	MODULE-COMPLIANCE, OBJECT-GROUP
		FROM SNMPv2-CONF
	qbMibs
		FROM QUANTUMBRIDGE-REG
    ;    

    qbSysRptMIB MODULE-IDENTITY
    LAST-UPDATED "0005221434Z" -- July 22, 2000
    ORGANIZATION "Quantum Bridge Inc."
    CONTACT-INFO
	    "mvaysman@quantumbridge.com"
    DESCRIPTION
        "This module defines objects for retrieving reports bi the QBCLI.
        in Quantum Bridge devices."
    ::= { qbMibs 8 }

 -- Top-level organization of the MIB

    qbSysRptObjects          OBJECT IDENTIFIER ::= { qbSysRptMIB 1 }
    qbSysRptTables	     OBJECT IDENTIFIER ::= { qbSysRptMIB 2 }
    qbSysRptConformance      OBJECT IDENTIFIER ::= { qbSysRptMIB 3 }

   -- *************************************************************
   -- Reports MIB to retriev generated reports using the SNMP agent 
   -- *************************************************************

    qbSysRptTable   OBJECT-TYPE
        SYNTAX      SEQUENCE OF QbSysRptEntry
        MAX-ACCESS  not-accessible
        STATUS      current
        DESCRIPTION
            "The Quantum Bridge qbSysReport table contains a list of
	    currently implemented reports. The table is visble only
	    for the  CLI community string"
    ::= { qbSysRptTables 1 }

    qbSysRptEntry  OBJECT-TYPE
       SYNTAX      QbSysRptEntry
       MAX-ACCESS  not-accessible
       STATUS      current
       DESCRIPTION
		"An entry in the Quantum Bridge qbSysReportTable. Every entry
		contains information related to a particular report"
		INDEX   { qbSysRptId, qbSysAid, qbSysArg1, qbSysArg2, qbSysArg3, qbSysArg4, qbSysArg5 }
       ::= { qbSysRptTable 1 }

    QbSysRptEntry ::=
       SEQUENCE {
		qbSysRptId	INTEGER,
		qbSysAid	Unsigned32,
		qbSysArg1	INTEGER,
		qbSysArg2	INTEGER,
		qbSysArg3	INTEGER,
		qbSysArg4	INTEGER,
		qbSysArg5	INTEGER,
		qbSysRptSize    INTEGER,
		qbSysRpt     	INTEGER
	}

    qbSysRptId      OBJECT-TYPE
	SYNTAX	    INTEGER
        MAX-ACCESS  not-accessible
        STATUS  current
        DESCRIPTION
                 "The requested report identifier"
        ::= { qbSysRptEntry 1 }

    qbSysAid      OBJECT-TYPE
	SYNTAX	   Unsigned32 
        MAX-ACCESS  not-accessible
        STATUS  current
        DESCRIPTION
                 "The system aid"
        ::= { qbSysRptEntry 2 }

    qbSysArg1 OBJECT-TYPE
       SYNTAX      INTEGER 
       MAX-ACCESS  read-only
       STATUS      current
       DESCRIPTION
	 "Argument needed to pass to report from climgr"
    ::= { qbSysRptEntry 3 }

    qbSysArg2 OBJECT-TYPE
       SYNTAX      INTEGER 
       MAX-ACCESS  read-only
       STATUS      current
       DESCRIPTION
	 "Argument needed to pass to report from climgr"
    ::= { qbSysRptEntry 4 }

    qbSysArg3 OBJECT-TYPE
       SYNTAX      INTEGER 
       MAX-ACCESS  read-only
       STATUS      current
       DESCRIPTION
	 "Argument needed to pass to report from climgr"
    ::= { qbSysRptEntry 5 }

    qbSysArg4 OBJECT-TYPE
       SYNTAX      INTEGER 
       MAX-ACCESS  read-only
       STATUS      current
       DESCRIPTION
	 "Argument needed to pass to report from climgr"
    ::= { qbSysRptEntry 6 }

    qbSysArg5 OBJECT-TYPE
       SYNTAX      INTEGER 
       MAX-ACCESS  read-only
       STATUS      current
       DESCRIPTION
	 "Argument needed to pass to report from climgr"
    ::= { qbSysRptEntry 7 }

    qbSysRptSize OBJECT-TYPE
	SYNTAX      INTEGER 
	UNITS	"bytes"
	MAX-ACCESS  read-only
	STATUS      current
	DESCRIPTION
		"The size of collected report in bytes."
	::= { qbSysRptEntry 8 }

    qbSysRpt OBJECT-TYPE
       SYNTAX      INTEGER 
       MAX-ACCESS  read-only
       STATUS      current
       DESCRIPTION
	 "The location of  gathered data. This is a memory address
	 where gathered report data is located"
    ::= { qbSysRptEntry 9 }


-- ****************************************************************
-- Conformance Information
-- ****************************************************************

qbSysRptCompliances OBJECT IDENTIFIER ::= { qbSysRptConformance 1 }
qbSysRptGroups      OBJECT IDENTIFIER ::= { qbSysRptConformance 2 }

--
-- Compliance Statements
--

qbSysRptCompliance MODULE-COMPLIANCE
    STATUS      current
    DESCRIPTION
        "The compliance statement for all agents that support this
        MIB. A compliant agent implements all objects defined in this
        MIB."
    MODULE  -- this module
    MANDATORY-GROUPS {
        qbSysRptAllGroup
    }
    ::= { qbSysRptCompliances 1 }

--
-- All Object Groups
--
qbSysRptAllGroup OBJECT-GROUP
    OBJECTS {
	    qbSysRptSize,
	    qbSysRpt    
    }
    STATUS      current
    DESCRIPTION
        "The set of all accessible objects in this MIB."
    ::= { qbSysRptGroups 1 }

END
