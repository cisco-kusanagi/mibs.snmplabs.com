--
-- This SMIv2 module has been generated by smidump 0.2-cvs. Do not edit.
--

SONUS-GATEWAY-SIGNALLING-MIB DEFINITIONS ::= BEGIN

IMPORTS
    Counter64, Integer32, IpAddress, MODULE-IDENTITY, NOTIFICATION-TYPE, 
    OBJECT-TYPE
        FROM SNMPv2-SMI
    DisplayString, RowStatus
        FROM SNMPv2-TC
    sonusEventClass, sonusEventDescription, sonusEventLevel
        FROM SONUS-COMMON-MIB
    sonusSignallingMIBs
        FROM SONUS-SMI
    SonusAdminState, SonusServiceState
        FROM SONUS-TC;

sonusGatewaySignallingMIB MODULE-IDENTITY
    LAST-UPDATED    "200107310000Z"
    ORGANIZATION    
            "Sonus Networks, Inc."
    CONTACT-INFO    
            "   Customer Support    
             Sonus Networks, Inc,
             5 carlisle Road
             Westford, MA 01886
             USA
             
             Tel: 978-692-8999
             Fax: 978-392-9118
             E-mail: cs.snmp@sonusnet.com"
    DESCRIPTION     
            "The MIB Module for IP Call Signal Channel Management."
    ::= { sonusSignallingMIBs 2 }


sonusGatewaySignallingMIBObjects OBJECT IDENTIFIER
    ::= { sonusGatewaySignallingMIB 1 }

sonusGwSigTimerObjects OBJECT IDENTIFIER
    ::= { sonusGatewaySignallingMIBObjects 1 }

sonusGwSigSrvTimerT301 OBJECT-TYPE
    SYNTAX          Integer32 (1..65535)
    MAX-ACCESS      read-write
    STATUS          obsolete
    DESCRIPTION     
            "This is the gateway to gateway call establishment timer T301 (in seconds). This value applies to all future GW-GW calls."
    DEFVAL          { 30 }
    ::= { sonusGwSigTimerObjects 1 }

sonusGwSigSrvTimerT303 OBJECT-TYPE
    SYNTAX          Integer32 (1..65535)
    MAX-ACCESS      read-write
    STATUS          obsolete
    DESCRIPTION     
            "This is the gateway to gateway call setup timer T303 (in seconds). This value applies to all future GW-GW calls."
    DEFVAL          { 180 }
    ::= { sonusGwSigTimerObjects 2 }

sonusGwSigTimerEstabish OBJECT-TYPE
    SYNTAX          Integer32 (1..65535)
    MAX-ACCESS      read-write
    STATUS          current
    DESCRIPTION     
            "This is the Gateway Signal Channel Establishment Timer (in seconds.)  This value applies to all signal channels."
    DEFVAL          { 10 }
    ::= { sonusGwSigTimerObjects 3 }

sonusGwSigTimerKeepalive OBJECT-TYPE
    SYNTAX          Integer32 (1..65535)
    MAX-ACCESS      read-write
    STATUS          current
    DESCRIPTION     
            "This is the Gateway Signal Channel Keepalive Timer (in seconds.)  This value applies to all signal channels."
    DEFVAL          { 3 }
    ::= { sonusGwSigTimerObjects 4 }

sonusGwSigActionObjects OBJECT IDENTIFIER
    ::= { sonusGatewaySignallingMIBObjects 2 }

sonusGwSigAction OBJECT-TYPE
    SYNTAX          INTEGER { open(1), close(2), none(3) }
    MAX-ACCESS      read-write
    STATUS          current
    DESCRIPTION     
            "The action to be taken on the specified link."
    DEFVAL          { none }
    ::= { sonusGwSigActionObjects 1 }

sonusGwSigActionDestIpAddr OBJECT-TYPE
    SYNTAX          IpAddress
    MAX-ACCESS      read-write
    STATUS          current
    DESCRIPTION     
            "The IP Address of the Destination Gateway to which the signalling link will be opened or closed."
    DEFVAL          { '00000000'H }
    ::= { sonusGwSigActionObjects 2 }

sonusGwSigActionDestPort OBJECT-TYPE
    SYNTAX          Integer32 (1..65535)
    MAX-ACCESS      read-write
    STATUS          current
    DESCRIPTION     
            "The Port Number to which a call sig link will be opened."
    DEFVAL          { 2569 }
    ::= { sonusGwSigActionObjects 3 }

sonusGwSigActionDir OBJECT-TYPE
    SYNTAX          INTEGER { to(1), from(2), both(3) }
    MAX-ACCESS      read-write
    STATUS          current
    DESCRIPTION     
            "The direction of the link which we will be opening or closing."
    DEFVAL          { to }
    ::= { sonusGwSigActionObjects 4 }

sonusGwSigPortTable OBJECT-TYPE
    SYNTAX          SEQUENCE OF SonusGwSigPortEntry
    MAX-ACCESS      not-accessible
    STATUS          current
    DESCRIPTION     
            "Table of Gateway Signal Listen Port configurations.  Limit of two ports."
    ::= { sonusGatewaySignallingMIBObjects 3 }

sonusGwSigPortEntry OBJECT-TYPE
    SYNTAX          SonusGwSigPortEntry
    MAX-ACCESS      not-accessible
    STATUS          current
    DESCRIPTION     
            "Gateway Signal Listen Port configuration."
    INDEX           { sonusGwSigPortIndex }
    ::= { sonusGwSigPortTable 1 }

SonusGwSigPortEntry ::=
    SEQUENCE {
        sonusGwSigPortIndex             Integer32,
        sonusGwSigPortIpAddress         IpAddress,
        sonusGwSigPortNum               Integer32,
        sonusGwSigPortInterface         INTEGER,
        sonusGwSigPortRole              INTEGER,
        sonusGwSigPortMode              SonusServiceState,
        sonusGwSigPortState             SonusAdminState,
        sonusGwSigPortRowStatus         RowStatus
    }

sonusGwSigPortIndex OBJECT-TYPE
    SYNTAX          Integer32
    MAX-ACCESS      read-only
    STATUS          current
    DESCRIPTION     
            "Identifies the Signal Listen Port entry."
    ::= { sonusGwSigPortEntry 1 }

sonusGwSigPortIpAddress OBJECT-TYPE
    SYNTAX          IpAddress
    MAX-ACCESS      read-write
    STATUS          current
    DESCRIPTION     
            "IP Address of the Gateway Signal Listen Port - this is a required parameter."
    DEFVAL          { '00000000'H }
    ::= { sonusGwSigPortEntry 2 }

sonusGwSigPortNum OBJECT-TYPE
    SYNTAX          Integer32 (1..65535)
    MAX-ACCESS      read-write
    STATUS          current
    DESCRIPTION     
            "TCP port number of Gateway Signal Listen Port (default is Sonus registered port 2569)."
    ::= { sonusGwSigPortEntry 3 }

sonusGwSigPortInterface OBJECT-TYPE
    SYNTAX          INTEGER { mgtNif(1), nif(2) }
    MAX-ACCESS      read-write
    STATUS          current
    DESCRIPTION     
            "The interface type of Gateway Signal Listen Port.  This element select which gateway network interfaces to use for GW-GW signaling traffic. 'mgtnif' routes traffic over the gateway Managment ports.  'nif' routes traffic over one of the gateway PNS ports."
    DEFVAL          { mgtNif }
    ::= { sonusGwSigPortEntry 4 }

sonusGwSigPortRole OBJECT-TYPE
    SYNTAX          INTEGER { primary(1), secondary(2) }
    MAX-ACCESS      read-write
    STATUS          current
    DESCRIPTION     
            "Role of the Gateway Signal Listen Port."
    DEFVAL          { primary }
    ::= { sonusGwSigPortEntry 5 }

sonusGwSigPortMode OBJECT-TYPE
    SYNTAX          SonusServiceState
    MAX-ACCESS      read-write
    STATUS          current
    DESCRIPTION     
            "Mode of the Gateway Signal Listen Port."
    DEFVAL          { inService }
    ::= { sonusGwSigPortEntry 6 }

sonusGwSigPortState OBJECT-TYPE
    SYNTAX          SonusAdminState
    MAX-ACCESS      read-write
    STATUS          current
    DESCRIPTION     
            "State of the Gateway Signal Listen Port."
    DEFVAL          { disabled }
    ::= { sonusGwSigPortEntry 7 }

sonusGwSigPortRowStatus OBJECT-TYPE
    SYNTAX          RowStatus
    MAX-ACCESS      read-write
    STATUS          current
    DESCRIPTION     
            "This is for SNMP use."
    ::= { sonusGwSigPortEntry 8 }

sonusGwSigPortStatTable OBJECT-TYPE
    SYNTAX          SEQUENCE OF SonusGwSigPortStatEntry
    MAX-ACCESS      not-accessible
    STATUS          current
    DESCRIPTION     
            "Table of the status of Gateway Signal Listen Ports."
    ::= { sonusGatewaySignallingMIBObjects 4 }

sonusGwSigPortStatEntry OBJECT-TYPE
    SYNTAX          SonusGwSigPortStatEntry
    MAX-ACCESS      not-accessible
    STATUS          current
    DESCRIPTION     
            "Status of Gateway Signal Listen Port."
    INDEX           { sonusGwSigPortStatIndex }
    ::= { sonusGwSigPortStatTable 1 }

SonusGwSigPortStatEntry ::=
    SEQUENCE {
        sonusGwSigPortStatIndex         Integer32,
        sonusGwSigPortStatIpAddress     IpAddress,
        sonusGwSigPortStatNum           Integer32,
        sonusGwSigPortStatInterface     INTEGER,
        sonusGwSigPortStatRole          INTEGER,
        sonusGwSigPortStatNif           Integer32,
        sonusGwSigPortStatState         SonusServiceState
    }

sonusGwSigPortStatIndex OBJECT-TYPE
    SYNTAX          Integer32
    MAX-ACCESS      read-only
    STATUS          current
    DESCRIPTION     
            "Identifies the Signal Listen Port entry."
    ::= { sonusGwSigPortStatEntry 1 }

sonusGwSigPortStatIpAddress OBJECT-TYPE
    SYNTAX          IpAddress
    MAX-ACCESS      read-only
    STATUS          current
    DESCRIPTION     
            "IP Address of the Gateway Signal Listen Port."
    ::= { sonusGwSigPortStatEntry 2 }

sonusGwSigPortStatNum OBJECT-TYPE
    SYNTAX          Integer32
    MAX-ACCESS      read-only
    STATUS          current
    DESCRIPTION     
            "TCP port number of Gateway Signal Listen Port."
    ::= { sonusGwSigPortStatEntry 3 }

sonusGwSigPortStatInterface OBJECT-TYPE
    SYNTAX          INTEGER { mgtNif(1), nif(2) }
    MAX-ACCESS      read-only
    STATUS          current
    DESCRIPTION     
            "The interface type of Gateway Signal Listen Port."
    ::= { sonusGwSigPortStatEntry 4 }

sonusGwSigPortStatRole OBJECT-TYPE
    SYNTAX          INTEGER { primary(1), secondary(2) }
    MAX-ACCESS      read-only
    STATUS          current
    DESCRIPTION     
            "Role of the Gateway Signal Listen Port."
    ::= { sonusGwSigPortStatEntry 5 }

sonusGwSigPortStatNif OBJECT-TYPE
    SYNTAX          Integer32
    MAX-ACCESS      read-only
    STATUS          current
    DESCRIPTION     
            "The network interface (NIF) ifIndex for this Gateway Signal Listen Port."
    ::= { sonusGwSigPortStatEntry 6 }

sonusGwSigPortStatState OBJECT-TYPE
    SYNTAX          SonusServiceState
    MAX-ACCESS      read-only
    STATUS          current
    DESCRIPTION     
            "State of the Gateway Signal Listen Port."
    ::= { sonusGwSigPortStatEntry 7 }

sonusGwSigActGwStatusTable OBJECT-TYPE
    SYNTAX          SEQUENCE OF SonusGwSigActGwStatusEntry
    MAX-ACCESS      not-accessible
    STATUS          current
    DESCRIPTION     
            "This table contains status of the active signaling channels with other gateways."
    ::= { sonusGatewaySignallingMIBObjects 5 }

sonusGwSigActGwStatusEntry OBJECT-TYPE
    SYNTAX          SonusGwSigActGwStatusEntry
    MAX-ACCESS      not-accessible
    STATUS          current
    DESCRIPTION     
            "Status of signaling channel another gateway."
    INDEX           { sonusGwSigActGwIpAddress }
    ::= { sonusGwSigActGwStatusTable 1 }

SonusGwSigActGwStatusEntry ::=
    SEQUENCE {
        sonusGwSigActGwName             DisplayString,
        sonusGwSigActGwIpAddress        IpAddress,
        sonusGwSigActGwLnkProto         INTEGER,
        sonusGwSigActGwNumActiveCalls   Integer32,
        sonusGwSigActGwNumActiveCallsTo Integer32,
        sonusGwSigActGwNumActiveCallsFrom Integer32,
        sonusGwSigActGwToState          SonusServiceState,
        sonusGwSigActGwFromState        SonusServiceState,
        sonusGwSigActGwInterface        INTEGER,
        sonusGwSigActGwFromBytesSent    Counter64,
        sonusGwSigActGwFromPdusSent     Counter64,
        sonusGwSigActGwFromBytesReceived Counter64,
        sonusGwSigActGwFromPdusReceived Counter64,
        sonusGwSigActGwFromTotalCalls   Counter64,
        sonusGwSigActGwFromCallRate     Integer32,
        sonusGwSigActGwToBytesSent      Counter64,
        sonusGwSigActGwToPdusSent       Counter64,
        sonusGwSigActGwToBytesReceived  Counter64,
        sonusGwSigActGwToPdusReceived   Counter64,
        sonusGwSigActGwToTotalCalls     Counter64,
        sonusGwSigActGwToCallRate       Integer32,
        sonusGwSigActGwFromLnkMajorVer  Integer32,
        sonusGwSigActGwFromLnkMinorVer  Integer32,
        sonusGwSigActGwToLnkMajorVer    Integer32,
        sonusGwSigActGwToLnkMinorVer    Integer32
    }

sonusGwSigActGwName OBJECT-TYPE
    SYNTAX          DisplayString (SIZE(0..23))
    MAX-ACCESS      read-only
    STATUS          deprecated
    DESCRIPTION     
            "Name of the remote Gateway."
    ::= { sonusGwSigActGwStatusEntry 1 }

sonusGwSigActGwIpAddress OBJECT-TYPE
    SYNTAX          IpAddress
    MAX-ACCESS      read-only
    STATUS          current
    DESCRIPTION     
            "IP Address of the remote Gateway."
    ::= { sonusGwSigActGwStatusEntry 2 }

sonusGwSigActGwLnkProto OBJECT-TYPE
    SYNTAX          INTEGER { ioi(1), h323(2) }
    MAX-ACCESS      read-only
    STATUS          current
    DESCRIPTION     
            "The protocol being used between gateways."
    ::= { sonusGwSigActGwStatusEntry 3 }

sonusGwSigActGwNumActiveCalls OBJECT-TYPE
    SYNTAX          Integer32
    MAX-ACCESS      read-only
    STATUS          current
    DESCRIPTION     
            "Number of active calls between local and remote Gateway."
    ::= { sonusGwSigActGwStatusEntry 4 }

sonusGwSigActGwNumActiveCallsTo OBJECT-TYPE
    SYNTAX          Integer32
    MAX-ACCESS      read-only
    STATUS          current
    DESCRIPTION     
            "Number of active calls to this remote Gateway."
    ::= { sonusGwSigActGwStatusEntry 5 }

sonusGwSigActGwNumActiveCallsFrom OBJECT-TYPE
    SYNTAX          Integer32
    MAX-ACCESS      read-only
    STATUS          current
    DESCRIPTION     
            "Number of active calls from this remote Gateway."
    ::= { sonusGwSigActGwStatusEntry 6 }

sonusGwSigActGwToState OBJECT-TYPE
    SYNTAX          SonusServiceState
    MAX-ACCESS      read-only
    STATUS          current
    DESCRIPTION     
            "Current state of the signaling link to this remote Gateway"
    ::= { sonusGwSigActGwStatusEntry 7 }

sonusGwSigActGwFromState OBJECT-TYPE
    SYNTAX          SonusServiceState
    MAX-ACCESS      read-only
    STATUS          current
    DESCRIPTION     
            "Current state of the signaling link from this remote Gateway"
    ::= { sonusGwSigActGwStatusEntry 8 }

sonusGwSigActGwInterface OBJECT-TYPE
    SYNTAX          INTEGER { mgtNif(1), nif(2) }
    MAX-ACCESS      read-only
    STATUS          current
    DESCRIPTION     
            "The interface used for this link."
    ::= { sonusGwSigActGwStatusEntry 9 }

sonusGwSigActGwFromBytesSent OBJECT-TYPE
    SYNTAX          Counter64
    MAX-ACCESS      read-only
    STATUS          current
    DESCRIPTION     
            "The total number of signalling bytes sent to this remote Gateway for incoming calls"
    ::= { sonusGwSigActGwStatusEntry 10 }

sonusGwSigActGwFromPdusSent OBJECT-TYPE
    SYNTAX          Counter64
    MAX-ACCESS      read-only
    STATUS          current
    DESCRIPTION     
            "The total number of signalling PDUS sent to this remote Gateway for incoming calls"
    ::= { sonusGwSigActGwStatusEntry 11 }

sonusGwSigActGwFromBytesReceived OBJECT-TYPE
    SYNTAX          Counter64
    MAX-ACCESS      read-only
    STATUS          current
    DESCRIPTION     
            "The total number of signalling bytes received from this remote Gateway for incoming calls"
    ::= { sonusGwSigActGwStatusEntry 12 }

sonusGwSigActGwFromPdusReceived OBJECT-TYPE
    SYNTAX          Counter64
    MAX-ACCESS      read-only
    STATUS          current
    DESCRIPTION     
            "The total number of signalling PDUS received from this remote Gateway for incoming calls"
    ::= { sonusGwSigActGwStatusEntry 13 }

sonusGwSigActGwFromTotalCalls OBJECT-TYPE
    SYNTAX          Counter64
    MAX-ACCESS      read-only
    STATUS          current
    DESCRIPTION     
            "The total number of calls originated by the remote on this link "
    ::= { sonusGwSigActGwStatusEntry 14 }

sonusGwSigActGwFromCallRate OBJECT-TYPE
    SYNTAX          Integer32
    MAX-ACCESS      read-only
    STATUS          current
    DESCRIPTION     
            "The number of calls/sec processed by the GWFE in the last minute on the link which was originated by the remote"
    ::= { sonusGwSigActGwStatusEntry 15 }

sonusGwSigActGwToBytesSent OBJECT-TYPE
    SYNTAX          Counter64
    MAX-ACCESS      read-only
    STATUS          current
    DESCRIPTION     
            "The total number of signalling bytes sent to this remote Gateway for outgoing calls"
    ::= { sonusGwSigActGwStatusEntry 16 }

sonusGwSigActGwToPdusSent OBJECT-TYPE
    SYNTAX          Counter64
    MAX-ACCESS      read-only
    STATUS          current
    DESCRIPTION     
            "The total number of signalling PDUS sent to this remote Gateway for outgoing calls"
    ::= { sonusGwSigActGwStatusEntry 17 }

sonusGwSigActGwToBytesReceived OBJECT-TYPE
    SYNTAX          Counter64
    MAX-ACCESS      read-only
    STATUS          current
    DESCRIPTION     
            "The total number of signalling bytes received from this remote Gateway for outgoing calls"
    ::= { sonusGwSigActGwStatusEntry 18 }

sonusGwSigActGwToPdusReceived OBJECT-TYPE
    SYNTAX          Counter64
    MAX-ACCESS      read-only
    STATUS          current
    DESCRIPTION     
            "The total number of signalling PDUS received from this remote Gateway for outgoing calls"
    ::= { sonusGwSigActGwStatusEntry 19 }

sonusGwSigActGwToTotalCalls OBJECT-TYPE
    SYNTAX          Counter64
    MAX-ACCESS      read-only
    STATUS          current
    DESCRIPTION     
            "The total number of calls originated locally on this link "
    ::= { sonusGwSigActGwStatusEntry 20 }

sonusGwSigActGwToCallRate OBJECT-TYPE
    SYNTAX          Integer32
    MAX-ACCESS      read-only
    STATUS          current
    DESCRIPTION     
            "The number of calls/sec processed by the GWFE in the last minute on the link which was originated locally"
    ::= { sonusGwSigActGwStatusEntry 21 }

sonusGwSigActGwFromLnkMajorVer OBJECT-TYPE
    SYNTAX          Integer32
    MAX-ACCESS      read-only
    STATUS          current
    DESCRIPTION     
            "The major version of link protocol being used between gateways."
    ::= { sonusGwSigActGwStatusEntry 22 }

sonusGwSigActGwFromLnkMinorVer OBJECT-TYPE
    SYNTAX          Integer32
    MAX-ACCESS      read-only
    STATUS          current
    DESCRIPTION     
            "The minor version of link protocol being used between gateways."
    ::= { sonusGwSigActGwStatusEntry 23 }

sonusGwSigActGwToLnkMajorVer OBJECT-TYPE
    SYNTAX          Integer32
    MAX-ACCESS      read-only
    STATUS          current
    DESCRIPTION     
            "The major version of link protocol being used between gateways."
    ::= { sonusGwSigActGwStatusEntry 24 }

sonusGwSigActGwToLnkMinorVer OBJECT-TYPE
    SYNTAX          Integer32
    MAX-ACCESS      read-only
    STATUS          current
    DESCRIPTION     
            "The minor version of link protocol being used between gateways."
    ::= { sonusGwSigActGwStatusEntry 25 }

sonusGatewaySignallingMIBNotifications OBJECT IDENTIFIER
    ::= { sonusGatewaySignallingMIB 2 }

sonusGatewaySignallingMIBNotificationsPrefix OBJECT IDENTIFIER
    ::= { sonusGatewaySignallingMIBNotifications 0 }

sonusGatewaySignallingMIBNotificationsObjects OBJECT IDENTIFIER
    ::= { sonusGatewaySignallingMIBNotifications 1 }

sonusGwRemoteGwName OBJECT-TYPE
    SYNTAX          DisplayString (SIZE(0..23))
    MAX-ACCESS      read-only
    STATUS          deprecated
    DESCRIPTION     
            "Name of the remote Gateway."
    ::= { sonusGatewaySignallingMIBNotificationsObjects 1 }

sonusGwCloseReasonCode OBJECT-TYPE
    SYNTAX          INTEGER { administratorInitiatedClose(1), 
                        closeRequestReceivedFromRemote(2), 
                        remoteNotResponding(3), internalError(4), 
                        configError(5), recvCallSigReqFromUnknownGw(6), 
                        socketErrNetworkDown(7), 
                        socketErrNetworkUnreachable(8), 
                        socketErrNetworkReset(9), 
                        socketErrSoftwareConnectionAbort(10), 
                        socketErrConnectionResetByPeer(11), 
                        socketErrNoBufferSpaceAvail(12), 
                        socketErrAlreadyConnected(13), 
                        socketErrNotConnected(14), 
                        socketErrCantSendAfterShutdown(15), 
                        socketErrTooManyReferences(16), 
                        socketErrConnectionTimedOut(17), 
                        socketErrUnknown(18), 
                        recvDuplicateLinkOpenReq(19), 
                        socketErrExceptionEvent(20), 
                        linkXmtCongestion(21), 
                        openNackReceivedFromRemote(22) }
    MAX-ACCESS      read-only
    STATUS          current
    DESCRIPTION     
            "Reason for close of Call Signalling Channel ."
    ::= { sonusGatewaySignallingMIBNotificationsObjects 2 }

sonusGwRemoteGwAddr OBJECT-TYPE
    SYNTAX          IpAddress
    MAX-ACCESS      read-only
    STATUS          current
    DESCRIPTION     
            "Ip Address of the remote Gateway."
    ::= { sonusGatewaySignallingMIBNotificationsObjects 3 }

sonusGwCallSigChanOpenNotification NOTIFICATION-TYPE
    OBJECTS         { sonusGwRemoteGwName, sonusEventDescription, 
                      sonusEventClass, sonusEventLevel }
    STATUS          deprecated
    DESCRIPTION     
            "This trap indicates that a Call Signalling channel to a Remote Gateway has been opened.
             This trap has been replaced with sonusGwSigChanOpenNotification."
    ::= { sonusGatewaySignallingMIBNotificationsPrefix 1 }

sonusGwCallSigChanCloseNotification NOTIFICATION-TYPE
    OBJECTS         { sonusGwRemoteGwName, sonusGwCloseReasonCode, 
                      sonusEventDescription, sonusEventClass, 
                      sonusEventLevel }
    STATUS          deprecated
    DESCRIPTION     
            "This trap indicates that a Call Signalling channel to a Remote Gateway has been closed.
             This trap has been replaced with sonusGwSigChanCloseNotification."
    ::= { sonusGatewaySignallingMIBNotificationsPrefix 2 }

sonusGwSigChanOpenNotification NOTIFICATION-TYPE
    OBJECTS         { sonusGwRemoteGwAddr, sonusEventDescription, 
                      sonusEventClass, sonusEventLevel }
    STATUS          current
    DESCRIPTION     
            "This trap indicates that a Call Signalling channel to a Remote Gateway has been opened."
    ::= { sonusGatewaySignallingMIBNotificationsPrefix 3 }

sonusGwSigChanCloseNotification NOTIFICATION-TYPE
    OBJECTS         { sonusGwRemoteGwAddr, sonusGwCloseReasonCode, 
                      sonusEventDescription, sonusEventClass, 
                      sonusEventLevel }
    STATUS          current
    DESCRIPTION     
            "This trap indicates that a Call Signalling channel to a Remote Gateway has been closed."
    ::= { sonusGatewaySignallingMIBNotificationsPrefix 4 }

END -- end of module SONUS-GATEWAY-SIGNALLING-MIB.
