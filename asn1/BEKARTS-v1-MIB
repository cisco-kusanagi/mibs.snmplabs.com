--
-- BEKARTS-v1-MIB       
-- http://bekarts.com
-- Copyright (C) 2004
-- BekArts International
--
BEKARTS-v1-MIB DEFINITIONS ::= BEGIN
IMPORTS
   OBJECT-TYPE FROM RFC-1212
   DisplayString FROM RFC1213-MIB
   enterprises FROM RFC1155-SMI
   TRAP-TYPE FROM RFC-1215;
bekarts					OBJECT IDENTIFIER
							::= { enterprises 18514 }
							
bekarts-software				OBJECT IDENTIFIER
							::= { bekarts 20 }
							
bekarts-hardware			OBJECT IDENTIFIER
							::= { bekarts 100 }
							
bekarts-mailshappy		OBJECT IDENTIFIER
							::= { bekarts-software 1 }
							
bekarts-mailshappy-on TRAP-TYPE
	ENTERPRISE bekarts-mailshappy
	DESCRIPTION 
	"BekArts Mails Happy has been started up."
	REFERENCE 	"BekArts On Trap"
	::= 1
	
bekarts-mailshappy-off TRAP-TYPE
	ENTERPRISE bekarts-mailshappy
	DESCRIPTION 
	"BekArts Mails Happy has been shut down."
	REFERENCE 	"BekArts Off Trap"
	::= 2
	
bekarts-mailshappy-active TRAP-TYPE
	ENTERPRISE bekarts-mailshappy
	DESCRIPTION 
	"BekArts Mails Happy has been Activated."
	REFERENCE 	"BekArts Active Trap"
	::= 3
	
bekarts-mailshappy-deactive TRAP-TYPE
	ENTERPRISE bekarts-mailshappy
	DESCRIPTION 
	"BekArts Mails Happy has been De-Activated."
	REFERENCE 	"BekArts De-Activated Trap"
	::= 4
	
bekarts-mailshappy-warning TRAP-TYPE
	ENTERPRISE bekarts-mailshappy
	DESCRIPTION 
	"BekArts Mails Happy has reached a warning state."
	REFERENCE 	"BekArts Warning Trap"
	::= 5
	
bekarts-mailshappy-clear-warning TRAP-TYPE
	ENTERPRISE bekarts-mailshappy
	DESCRIPTION 
	"BekArts Mails Happy has cleared a warning state."
	REFERENCE 	"BekArts Warning Cleared Trap"
	::= 6
	
bekarts-mailshappy-critical TRAP-TYPE
	ENTERPRISE bekarts-mailshappy
	DESCRIPTION 
	"BekArts Mails Happy has reached a critical state."
	REFERENCE 	"BekArts Critical Trap"
	::= 7
	
bekarts-mailshappy-clear-critical TRAP-TYPE
	ENTERPRISE bekarts-mailshappy
	DESCRIPTION 
	"BekArts Mails Happy has cleared a critical state."
	REFERENCE 	"BekArts Critical Cleared Trap"
	::= 8

bekarts-mailshappy-test TRAP-TYPE
	ENTERPRISE bekarts-mailshappy
	DESCRIPTION 
	"BekArts Mails Happy has sent a test trap."
	REFERENCE 	"BekArts Test Trap"
	::= 9

END
