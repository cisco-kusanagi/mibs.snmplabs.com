ChrComPmAtmATM-CELL-Interval-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComPmAtm				FROM  Chromatis-MIB
	chrComIfifIndex					FROM  ChrComIfifTable-MIB
	TruthValue				FROM  ChrTyp-MIB
	Gauge32				FROM  SNMPv2-SMI;

-- chrComPmAtmATM-CELL-Interval Table

chrComPmAtmATM-CELL-IntervalTable		OBJECT-TYPE
	SYNTAX		SEQUENCE OF ChrComPmAtmATM-CELL-IntervalEntry
	MAX-ACCESS	not-accessible
	STATUS		current
	DESCRIPTION
	""
	::= { chrComPmAtm 2}

chrComPmAtmATM-CELL-IntervalEntry		OBJECT-TYPE
	SYNTAX		ChrComPmAtmATM-CELL-IntervalEntry
	MAX-ACCESS	not-accessible
	STATUS		current
	DESCRIPTION
	""
	INDEX  {  chrComIfifIndex, chrComPmAtmIntervalNumber }

--DEFAULT  get-function-async  MNIL_GetRoutine
--DEFAULT  set-function-async  MNIL_SetRoutine
--DEFAULT  next-function-async MNIL_NextRoutine
--DEFAULT  test-function-async MNIL_TestRoutine
--DEFAULT  cookie "ATM-CELL-Interval"
	::= { chrComPmAtmATM-CELL-IntervalTable  1 }

ChrComPmAtmATM-CELL-IntervalEntry  ::=
	SEQUENCE  {
	chrComPmAtmIntervalNumber		Unsigned32	(1..32),
	chrComPmAtmSuspectedInterval	TruthValue,
	chrComPmAtmElapsedTime		Unsigned32	(0..4294967295),
	chrComPmAtmSuppressedIntrvls	Gauge32			(0..4294967295),
	chrComPmAtmOCDS			Gauge32			(0..4294967295),
	chrComPmAtmHECCells		Gauge32			(0..4294967295),
	chrComPmAtmCorrectableHECCells	Gauge32			(0..4294967295),
	chrComPmAtmDiscardedCells		Gauge32			(0..4294967295),
	chrComPmAtmReceivedCells		Gauge32			(0..4294967295),
	chrComPmAtmTransmittedCells	Gauge32			(0..4294967295),
	chrComPmAtmDiscardedIngCells	Gauge32			(0..4294967295),
	chrComPmAtmDiscardedIngHighPrCells	Gauge32			(0..4294967295),
	chrComPmAtmDiscardedEgCells	Gauge32			(0..4294967295),
	chrComPmAtmDiscardedEgHighPrCells	Gauge32			(0..4294967295),
	chrComPmAtmDiscardedUPC		Gauge32			(0..4294967295),
	chrComPmAtmTaggedUPC		Gauge32			(0..4294967295)
}

chrComPmAtmIntervalNumber 	OBJECT-TYPE
	SYNTAX		Unsigned32	(1..32)
	MAX-ACCESS 	read-only
	STATUS 		current
	DESCRIPTION
	""
	::= { chrComPmAtmATM-CELL-IntervalEntry  1 }

chrComPmAtmSuspectedInterval 	OBJECT-TYPE
	SYNTAX		TruthValue
	MAX-ACCESS 	read-only
	STATUS 		current
	DESCRIPTION
	""
	::= { chrComPmAtmATM-CELL-IntervalEntry  2 }

chrComPmAtmElapsedTime 	OBJECT-TYPE
	SYNTAX		Unsigned32	(0..4294967295)
	MAX-ACCESS 	read-only
	STATUS 		current
	DESCRIPTION
	""
	::= { chrComPmAtmATM-CELL-IntervalEntry  3 }

chrComPmAtmSuppressedIntrvls 	OBJECT-TYPE
	SYNTAX		Gauge32			(0..4294967295)
	MAX-ACCESS 	read-only
	STATUS 		current
	DESCRIPTION
	""
	::= { chrComPmAtmATM-CELL-IntervalEntry  4 }

chrComPmAtmOCDS 	OBJECT-TYPE
	SYNTAX		Gauge32			(0..4294967295)
	MAX-ACCESS 	read-only
	STATUS 		current
	DESCRIPTION
	""
	::= { chrComPmAtmATM-CELL-IntervalEntry  5 }

chrComPmAtmHECCells 	OBJECT-TYPE
	SYNTAX		Gauge32			(0..4294967295)
	MAX-ACCESS 	read-only
	STATUS 		current
	DESCRIPTION
	""
	::= { chrComPmAtmATM-CELL-IntervalEntry  6 }

chrComPmAtmCorrectableHECCells 	OBJECT-TYPE
	SYNTAX		Gauge32			(0..4294967295)
	MAX-ACCESS 	read-only
	STATUS 		current
	DESCRIPTION
	""
	::= { chrComPmAtmATM-CELL-IntervalEntry  7 }

chrComPmAtmDiscardedCells 	OBJECT-TYPE
	SYNTAX		Gauge32			(0..4294967295)
	MAX-ACCESS 	read-only
	STATUS 		current
	DESCRIPTION
	""
	::= { chrComPmAtmATM-CELL-IntervalEntry  8 }

chrComPmAtmReceivedCells 	OBJECT-TYPE
	SYNTAX		Gauge32			(0..4294967295)
	MAX-ACCESS 	read-only
	STATUS 		current
	DESCRIPTION
	""
	::= { chrComPmAtmATM-CELL-IntervalEntry  9 }

chrComPmAtmTransmittedCells 	OBJECT-TYPE
	SYNTAX		Gauge32			(0..4294967295)
	MAX-ACCESS 	read-only
	STATUS 		current
	DESCRIPTION
	""
	::= { chrComPmAtmATM-CELL-IntervalEntry  10 }

chrComPmAtmDiscardedIngCells 	OBJECT-TYPE
	SYNTAX		Gauge32			(0..4294967295)
	MAX-ACCESS 	read-only
	STATUS 		current
	DESCRIPTION
	""
	::= { chrComPmAtmATM-CELL-IntervalEntry  11 }

chrComPmAtmDiscardedIngHighPrCells 	OBJECT-TYPE
	SYNTAX		Gauge32			(0..4294967295)
	MAX-ACCESS 	read-only
	STATUS 		current
	DESCRIPTION
	""
	::= { chrComPmAtmATM-CELL-IntervalEntry  12 }

chrComPmAtmDiscardedEgCells 	OBJECT-TYPE
	SYNTAX		Gauge32			(0..4294967295)
	MAX-ACCESS 	read-only
	STATUS 		current
	DESCRIPTION
	""
	::= { chrComPmAtmATM-CELL-IntervalEntry  13 }

chrComPmAtmDiscardedEgHighPrCells 	OBJECT-TYPE
	SYNTAX		Gauge32			(0..4294967295)
	MAX-ACCESS 	read-only
	STATUS 		current
	DESCRIPTION
	""
	::= { chrComPmAtmATM-CELL-IntervalEntry  14 }

chrComPmAtmDiscardedUPC 	OBJECT-TYPE
	SYNTAX		Gauge32			(0..4294967295)
	MAX-ACCESS 	read-only
	STATUS 		current
	DESCRIPTION
	""
	::= { chrComPmAtmATM-CELL-IntervalEntry  15 }

chrComPmAtmTaggedUPC 	OBJECT-TYPE
	SYNTAX		Gauge32			(0..4294967295)
	MAX-ACCESS 	read-only
	STATUS 		current
	DESCRIPTION
	""
	::= { chrComPmAtmATM-CELL-IntervalEntry  16 }


END
