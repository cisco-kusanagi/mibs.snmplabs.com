PERF-STAT-MIB DEFINITIONS ::= BEGIN

 IMPORTS
     MODULE-IDENTITY, OBJECT-TYPE, Unsigned32, Integer32, Gauge32, Counter32, Counter64,
     NOTIFICATION-TYPE, enterprises, IpAddress, TimeTicks
         FROM SNMPv2-SMI
     TEXTUAL-CONVENTION, DisplayString, TruthValue, RowStatus, 
     DateAndTime, TimeStamp
         FROM SNMPv2-TC
     alarmInterval, alarmValue, alarmIndex, alarmRisingThreshold, 
     alarmVariable, alarmFallingThreshold
	 FROM RMON-MIB
     MODULE-COMPLIANCE, OBJECT-GROUP
         FROM SNMPv2-CONF;

    sitara                      OBJECT IDENTIFIER ::= { enterprises 2302 }

    sitaraCfg                   OBJECT IDENTIFIER ::= { sitara 1 }

    sitaraCfgPlcy               OBJECT IDENTIFIER ::= { sitaraCfg 1 }

    sitaraCfgSysGenlObjs        OBJECT IDENTIFIER ::= { sitaraCfgSys 2 }

    sitaraCfgSys                OBJECT IDENTIFIER ::= { sitaraCfg 2 }

    sitaraCfgSysMon             OBJECT IDENTIFIER ::= { sitaraCfgSys 6 }

    sitaraPerf                   OBJECT IDENTIFIER ::= { sitara 2 }

    sitaraPerfSys                OBJECT IDENTIFIER ::= { sitaraPerf 2 }

    sitaraPerfTraf               OBJECT IDENTIFIER ::= { sitaraPerf 3 }

    sitaraPerfPlcy               OBJECT IDENTIFIER ::= { sitaraPerf 4 }

    sitaraPerfCach               OBJECT IDENTIFIER ::= { sitaraPerf 5 }

    sitaraPerfNotifns            OBJECT IDENTIFIER ::= { sitaraPerf 6 }


 sitaraPerfMonMIB MODULE-IDENTITY
     LAST-UPDATED "200106151400Z"
     ORGANIZATION "Sitara, Incorporated"
     CONTACT-INFO
             "     Postal Address:
                   Sitara Networks
                   52 Second Avenue
                   Suite 200
                   Waltham MA. 02451
                   USA

                   Tel:     +1 781 487 5900
                   E-mail:  info@sitaranetworks.com
                   WWW:     http://www.sitaranetworks.com"
     DESCRIPTION
             "This MIB module provides Sitara QOSWorks performance monitoring capabilities."

     REVISION  "200106151400Z"
     DESCRIPTION
             "This Version of MIB consists of the Objects supported in
              QosDirector 1.5/QosWorks 1.10/QosArray 1.3.  
              Status of the Objects/Notification, supported only in the  
              QosWorks 1.7/1.8/1.9, are not supported any more is changed to obsolete"
             

     ::= { sitaraPerfSys 1 }

 --
 -- Textual Conventions
 --

 FilterType ::= TEXTUAL-CONVENTION
     STATUS      current
     DESCRIPTION
	  "This TC defines a traffic filter type.  It describes how TCP/IP
	   addresses and port numbers in a particular instance of a traffic
	   monitor are used to filter traffic."
     SYNTAX      INTEGER {
                   none                (1), -- No address or port specified
                   sourceAddr          (2), -- Filter source address
                   sourcePort          (3), -- Filter source port number
                   destinationAddr     (4), -- Filter destination address
                   destinationPort     (5), -- Filter destination port number
                   bothPorts           (6)  -- Filter both port numbers
		 }

 FilterDirection ::= TEXTUAL-CONVENTION
     STATUS      current
     DESCRIPTION
             "This TC defines the directions of traffic flows."
     SYNTAX      INTEGER {
                   inbound             (1), -- WAN to LAN
                   outbound            (2)  -- LAN to WAN
		 }

 PolicyName ::= TEXTUAL-CONVENTION
     STATUS       current
     DESCRIPTION  " [A-Za-z0-9_ + && not 'default'  (UTF-8 ever?))]
                   'default' A policy pathname."
     SYNTAX       OCTET STRING (SIZE (1..64))  

 CbqName ::= TEXTUAL-CONVENTION
     STATUS       current
     DESCRIPTION  "[Cc]_[0-9]{1,8}
		   This Tc represents an internal name used by CBQ to 
		   identify a policy being monitored."  
     SYNTAX       OCTET STRING (SIZE (3..10))  

 PolicyType ::= TEXTUAL-CONVENTION
     STATUS       current
     DESCRIPTION
             "Describes the type of a policy for which statistics are 
              being collected."
     SYNTAX	 INTEGER {
                      class(0),            -- class statistics
                      group(1),             -- group statistics
                      link(2)             -- link statistics
		 }
PolicyPathName ::= TEXTUAL-CONVENTION
    STATUS       current
    DESCRIPTION  "[A-Za-z0-9 _ / ] 'default' Name  is reserved for
                 internal use. Path is the full expression of the
                 part of the policy when an object with this textual
                 convention is used. A path must be unique, within a
                 schedule and is to be read and understood very much
                 like a directory structure such as /usr/var where var
                 is contained in usr. The format for path is
                 l_LinkAlias/g_GroupAlias/c_ClassAlias/f_FilterAlias.
                 At any point in this hierarchy, there is one and only
                 one unique path within a schedule."
    SYNTAX       OCTET STRING (SIZE (1..512))

PolicyCustomerId ::= TEXTUAL-CONVENTION
    STATUS       current
    DESCRIPTION  "[A-Za-z0-9 _  not 'default' or any reserved Policy name
                  like LINK, END , VERSION etc]. The 'default' alias  is
                  reserved for internal use. For example, a Customer ID can be
                  combination of Alpha numeric value GoldUser4527"
    SYNTAX       OCTET STRING (SIZE (1..30))
 
 PolicyDirection ::= TEXTUAL-CONVENTION
     STATUS      current
     DESCRIPTION
             "This TC defines the directions of traffic flows."
     SYNTAX      INTEGER {
                   inbound             (1), -- to LAN
                   outbound            (2)  -- to WAN
		 }

 SitaraOwnerString ::= TEXTUAL-CONVENTION
     STATUS current
     DESCRIPTION
         "This data type is used to model an administratively
         assigned name of the owner of a resource. Implementations
         must accept values composed of well-formed NVT ASCII
         sequences. In addition, implementations should accept
         values composed of well-formed UTF-8 sequences.

         It is suggested that this name contain one or more of
         the following: IP address, management station name,
         network manager's name, location, or phone number.
         In some cases the agent itself will be the owner of
         an entry.  In these cases, this string shall be set
         to a string starting with 'monitor'.

         SNMP access control is articulated entirely in terms
         of the contents of MIB views; access to a particular
         SNMP object instance depends only upon its presence
         or absence in a particular MIB view and never upon
         its value or the value of related object instances.
         Thus, objects of this type afford resolution of
         resource contention only among cooperating
         managers; they realize no access control function
         with respect to uncooperative parties."
     SYNTAX OCTET STRING (SIZE (0..127))

 -- End of TCs


 --
 -- Object Definitions 
 --
 --
 -- Object Definitions 
 --

 sitaraCfgSysWanSpeed  OBJECT-TYPE
     SYNTAX      Unsigned32
     MAX-ACCESS  read-write
     STATUS      current
     DESCRIPTION
	     "The speed of the WAN link.  Maximum allowable speed is
	      governed by the QosWorks model. "
     ::= { sitaraCfgSysGenlObjs 11 }

 sitaraCfgSysMonNextIndex  OBJECT-TYPE
     SYNTAX  INTEGER (1..65535)
     MAX-ACCESS  read-only
     STATUS  current
     DESCRIPTION
	     "Next available index in the sitaraCfgSysMonTable."
     ::= { sitaraCfgSysMon 1 }

 --
 -- sitaraCfgSysMonTable - Configured traffic monitors.
 --

 sitaraCfgSysMonTable OBJECT-TYPE
     SYNTAX      SEQUENCE OF SitaraCfgSysMonEntry
     MAX-ACCESS  not-accessible
     STATUS      current
     DESCRIPTION
             "The sitaraCfgSysMonTable contains an entry for each configured
	      traffic monitor instance."
     ::= { sitaraCfgSysMon 2 }

 sitaraCfgSysMonEntry OBJECT-TYPE
     SYNTAX      SitaraCfgSysMonEntry
     MAX-ACCESS  not-accessible
     STATUS      current
     DESCRIPTION
             "Locally held information about a particular traffic
              monitor instance."
     INDEX { sitaraCfgSysMonIndex }
     ::= { sitaraCfgSysMonTable 1 }

 SitaraCfgSysMonEntry ::=
     SEQUENCE {
         sitaraCfgSysMonIndex                INTEGER,
         sitaraCfgSysMonName                 DisplayString,
         sitaraCfgSysMonDirection            FilterDirection,
         sitaraCfgSysMonProtocol             INTEGER,
         sitaraCfgSysMonType                 FilterType,
         sitaraCfgSysMonIPAddr               IpAddress,
         sitaraCfgSysMonIPMask               IpAddress,
         sitaraCfgSysMonPort                 INTEGER,
         sitaraCfgSysMonOwner                SitaraOwnerString,
         sitaraCfgSysMonRowStatus            RowStatus
     }

 sitaraCfgSysMonIndex OBJECT-TYPE
     SYNTAX      INTEGER (1..65535)
     MAX-ACCESS  not-accessible
     STATUS      current
     DESCRIPTION
             "A unique value for each conceptual row."
     ::= { sitaraCfgSysMonEntry 1 }

 sitaraCfgSysMonName OBJECT-TYPE
     SYNTAX      DisplayString
     MAX-ACCESS  read-create
     STATUS      current
     DESCRIPTION
             "The user-assigned name of the traffic monitor instance."
     ::= { sitaraCfgSysMonEntry 2 }

 sitaraCfgSysMonDirection OBJECT-TYPE
     SYNTAX      FilterDirection
     MAX-ACCESS  read-create
     STATUS      current
     DESCRIPTION
             "The direction in which the traffic needs to be monitored."
     ::= { sitaraCfgSysMonEntry 3 }

 sitaraCfgSysMonProtocol OBJECT-TYPE
     SYNTAX      INTEGER (1..65535)
     MAX-ACCESS  read-create
     STATUS      current
     DESCRIPTION
             "Transport protocol to be monitored.  This could be IP, TCP
              UDP, IPX, etc..."
     ::= { sitaraCfgSysMonEntry 4 }

 sitaraCfgSysMonType OBJECT-TYPE
     SYNTAX      FilterType
     MAX-ACCESS  read-create
     STATUS      current
     DESCRIPTION
	     "The filter type used by this traffic monitor.  The filter
	      type defines how some of the other columnar objects in this 
	      row are used:

		sitaraCfgSysMonType == none

		  No filtering is done.

		sitaraCfgSysMonType == sourceAddr 

		  sitaraCfgSysMonIPAddr is the source address to filter.
		  sitaraCfgSysMonPort is not used.
			
		sitaraCfgSysMonType == sourcePort

		  sitaraCfgSysMonPort is the source port to filter.
		  sitaraCfgSysMonIPAddr is not used.
			
		sitaraCfgSysMonType == destinationAddr

		  sitaraCfgSysMonIPAddr is the destination address to filter.
		  sitaraCfgSysMonPort is not used.
			
		sitaraCfgSysMonType == destinationPort

		  sitaraCfgSysMonPort is the destination port to filter.
		  sitaraCfgSysMonIPAddr is not used.
			
		sitaraCfgSysMonType == bothPorts

		  sitaraCfgSysMonPort is the source and destination port to filter.
		  sitaraCfgSysMonIPAddr is not used.
	     "
     ::= { sitaraCfgSysMonEntry 5 }

 sitaraCfgSysMonIPAddr OBJECT-TYPE
     SYNTAX      IpAddress
     MAX-ACCESS  read-create
     STATUS      current
     DESCRIPTION
             "The IP address used by this traffic monitor."
     ::= { sitaraCfgSysMonEntry 6 }

 sitaraCfgSysMonIPMask OBJECT-TYPE
     SYNTAX      IpAddress
     MAX-ACCESS  read-create
     STATUS      current
     DESCRIPTION
             "An IP address mask that may be associated with the instance of 
	      sitaraCfgSysMonIPAddr.  This object is used to indicate a range
	      of IP addresses for the traffic monitor."
     ::= { sitaraCfgSysMonEntry 7 }

 sitaraCfgSysMonPort OBJECT-TYPE
     SYNTAX      INTEGER (1..65535)
     MAX-ACCESS  read-create
     STATUS      current
     DESCRIPTION
             "The TCP/IP port number for this traffic monitor."
     ::= { sitaraCfgSysMonEntry 8 }

 sitaraCfgSysMonOwner OBJECT-TYPE
      SYNTAX     SitaraOwnerString
      MAX-ACCESS  read-create
      STATUS  current
      DESCRIPTION
	      "This object is used to identify the owner of the conceptual row."
    ::= { sitaraCfgSysMonEntry 9 }

 sitaraCfgSysMonRowStatus OBJECT-TYPE
     SYNTAX      RowStatus
     MAX-ACCESS  read-create
     STATUS      current
     DESCRIPTION
             "The status of this conceptual row."
     ::= { sitaraCfgSysMonEntry 10 }

 --
 -- Control Object
 --

 sitaraCfgSysMonTableStatus OBJECT-TYPE
     SYNTAX  INTEGER { save(1), clear(2), none(3) }
     MAX-ACCESS  read-write
     STATUS  current
     DESCRIPTION
             "When this object value is set to 
                 save	: mon-user.conf is updated
                 clear	: All the entries in the table are cleared.
	         none   : default state"
     ::= { sitaraCfgSysMon 3 }

 --
 -- sitaraPerfSys - Statistics for system level resources
 --
 
sitaraPerfSysCPUUsage OBJECT-TYPE
      SYNTAX     INTEGER (0..100)
      MAX-ACCESS  read-only
      STATUS  current
      DESCRIPTION
              "Current System CPU Utilization Percent"
      ::= { sitaraPerfSys 2 }

 sitaraPerfSysMemoryUsage OBJECT-TYPE
      SYNTAX     INTEGER (0..100)
      MAX-ACCESS  read-only
      STATUS  current
      DESCRIPTION
              "Current System Memory Utilization Percent"
      ::= { sitaraPerfSys 3 }

 sitaraPerfSysDiskRootUtilization OBJECT-TYPE
      SYNTAX     INTEGER (0..100)
      MAX-ACCESS  read-only
      STATUS  current
      DESCRIPTION
              "Current Root Filesystem Utilization Percent"
      ::= { sitaraPerfSys 4 }

 sitaraPerfSysDiskSyslogUtilization OBJECT-TYPE
      SYNTAX     INTEGER (0..100)
      MAX-ACCESS  read-only
      STATUS  current
      DESCRIPTION
           "Current Syslog Disk Directory Utilization Percent"
      ::= { sitaraPerfSys 5 }

 sitaraPerfSysDiskCacheUtilization OBJECT-TYPE
      SYNTAX     INTEGER (0..100)
      MAX-ACCESS  read-only
      STATUS  current
      DESCRIPTION
              "Current Cache Filesystem Utilization Percent"
      ::= { sitaraPerfSys 6 }

 sitaraPerfAlarmStatus OBJECT-TYPE
     SYNTAX  INTEGER { save(1), clear(2), none(3) }
     MAX-ACCESS  read-write
     STATUS  current
     DESCRIPTION
             "When this object value is set to 
                 save	: perf-alarms.conf is updated from Alarm MIB Table
                 clear	: All the entries in the Alarm MIB Table are cleared.
       	         none   : default state"
     ::= { sitaraPerfSys 7 }

 sitaraPerfSysQosDirectorIpAddr OBJECT-TYPE
      SYNTAX     IpAddress
      MAX-ACCESS  read-write
      STATUS  current
      DESCRIPTION
              "Destination IP Address of the QOS Director "
      ::= { sitaraPerfSys 8 }

 sitaraPerfSysQosDirectorPort OBJECT-TYPE
      SYNTAX      INTEGER (1..65535)
      MAX-ACCESS  read-write
      STATUS  current
      DESCRIPTION
              "Receiving Port number on the QOS Director "
      ::= { sitaraPerfSys 9 }

 sitaraPerfAlarmMasks OBJECT-TYPE
     SYNTAX       OCTET STRING (SIZE (1..4))  
     MAX-ACCESS  read-write
     STATUS  current
     DESCRIPTION
             "sitaraPerfAlarmMasks is a hexadecimal bit defined field.
                Each bit position in the hexadecimal value of the instance
                 enable/disable the corresponding notification number.
                Notification                            BIT Definitions
                ------------                            --  -----------
                sitaraPerfNotifnsMemoryUtil             0x00000001
                sitaraPerfNotifnsCPU                    0x00000002
                sitaraPerfNotifnsDiskCache              0x00000004
                sitaraPerfNotifnsDiskSyslog             0x00000008
                sitaraPerfNotifnsDiskRoot               0x00000010
                sitaraPerfNotifnsUpdate                 0x00000020
                sitaraPerfNotifnsPlcyBandWidth          0x00000800
                sitaraPerfNotifnsPacketDrops            0x00001000
                sitaraPerfNotifnsPlcyAveQueueLength     0x00008000. "
     ::= { sitaraPerfSys 10 }

 sitaraPerfPlcyStatsCollection OBJECT-TYPE
      SYNTAX      INTEGER 	{
                   		enable           (1), 
                   		disable          (2)
		 		}
      MAX-ACCESS  read-write
      STATUS  current
      DESCRIPTION
              "The object controls the Policy Statistics collection."
      ::= { sitaraPerfSys 11 }

 sitaraPerfTrafStatsCollection OBJECT-TYPE
      SYNTAX      INTEGER 	{
                   		enable           (1), 
                   		disable          (2)
		 		}
      MAX-ACCESS  read-write
      STATUS  current
      DESCRIPTION
              "The object controls the Traffic monitor Statistics collection."
      ::= { sitaraPerfSys 12 }
 --
 -- sitaraPerfTraf - statistics for traffic monitors 
 --

 sitaraPerfTrafTable OBJECT-TYPE
     SYNTAX      SEQUENCE OF SitaraPerfTrafEntry
     MAX-ACCESS  not-accessible
     STATUS      current
     DESCRIPTION
             "The sitaraPerfTrafTable contains statistics for each traffic monitor instance."
     ::= { sitaraPerfTraf 1 }

 sitaraPerfTrafEntry OBJECT-TYPE
     SYNTAX      SitaraPerfTrafEntry
     MAX-ACCESS  not-accessible
     STATUS      current
     DESCRIPTION
             "Statistics about a particular traffic monitor instance for the most
	      recently completed interval."
     INDEX { sitaraCfgSysMonIndex }
     ::= { sitaraPerfTrafTable 1 }

 SitaraPerfTrafEntry ::=
     SEQUENCE {
         sitaraPerfTrafIndex                Unsigned32,
         sitaraPerfTrafName                 DisplayString,
         sitaraPerfTrafTime                 TimeTicks,
         sitaraPerfTrafInterval             INTEGER,
         sitaraPerfTrafPktCnt               Gauge32,
         sitaraPerfTrafByteCnt              Gauge32
     }

 sitaraPerfTrafIndex OBJECT-TYPE
     SYNTAX      Unsigned32
     MAX-ACCESS  not-accessible
     STATUS      current
     DESCRIPTION
             "A unique value for each sitaraPerfTraf instance. This table is indexed
              by sitaraCfgSysMonIndex."
     ::= { sitaraPerfTrafEntry 1 }

 sitaraPerfTrafName OBJECT-TYPE
     SYNTAX      DisplayString
     MAX-ACCESS  read-create
     STATUS      current
     DESCRIPTION
             "Indicates the name of the sitaraPerfTraf instance."
     ::= { sitaraPerfTrafEntry 2 }

 sitaraPerfTrafTime OBJECT-TYPE
     SYNTAX      TimeStamp
     MAX-ACCESS  read-only
     STATUS      current
     DESCRIPTION
             "Value of sysUptime when traffic monitoring for this instance began."
     ::= { sitaraPerfTrafEntry 3 }

 sitaraPerfTrafInterval OBJECT-TYPE
     SYNTAX      INTEGER(1..3600)
     MAX-ACCESS  read-only
     STATUS      current
     DESCRIPTION
             "Polling interval, in seconds, for this monitoring instance."
     DEFVAL   { 60 }
     ::= { sitaraPerfTrafEntry 4 }

 sitaraPerfTrafPktCnt OBJECT-TYPE
     SYNTAX      Gauge32 
     MAX-ACCESS  read-only
     STATUS      current
     DESCRIPTION
             "The number of packets sent during this interval.  
	      This is the delta value of packets sent since the last sampling interval."
     ::= { sitaraPerfTrafEntry 5 }

 sitaraPerfTrafByteCnt OBJECT-TYPE
     SYNTAX      Gauge32 
     MAX-ACCESS  read-only
     STATUS      current
     DESCRIPTION
             "The number of bytes sent during this interval.  
	      This is the delta value of bytes sent since the last sampling interval."
     ::= { sitaraPerfTrafEntry 6 }

 --
 -- sitaraPerfPlcy - statistics for policies
 --
 -- sitaraPerfPlcyTable - each row defined in this table describes the type
 -- of monitoring to be done for a given link, group, and class .
 --

 sitaraPerfPlcyNextIndex   OBJECT-TYPE
       SYNTAX  Unsigned32
       MAX-ACCESS  read-only
       STATUS  current
       DESCRIPTION
       "Next available index in the sitaraPerfPlcyTable."
       ::= { sitaraPerfPlcy 1 }

 sitaraPerfPlcyTable OBJECT-TYPE
     SYNTAX      SEQUENCE OF SitaraPerfPlcyEntry
     MAX-ACCESS  not-accessible
     STATUS      current
     DESCRIPTION
             "The sitaraPerfPlcyTable contains an entry for each policy instance."
     ::= { sitaraPerfPlcy 2 }

 sitaraPerfPlcyEntry OBJECT-TYPE
     SYNTAX      SitaraPerfPlcyEntry
     MAX-ACCESS  not-accessible
     STATUS      current
     DESCRIPTION
             "Statistics about a particular policy instance for the most
 	      recently completed interval."
     INDEX { sitaraPerfPlcyIndex }
     ::= { sitaraPerfPlcyTable 1 }

 SitaraPerfPlcyEntry ::=
     SEQUENCE {
         sitaraPerfPlcyIndex                Unsigned32,
         sitaraPerfPlcyTime                 TimeTicks,
         sitaraPerfPlcyInterval             INTEGER,
         sitaraPerfPlcyAlias                PolicyName,
         sitaraPerfPlcyType                 PolicyType,
         sitaraPerfPlcyLanBandWidth         Gauge32,
         sitaraPerfPlcyLanBurst             Gauge32,
         sitaraPerfPlcyWanBandWidth         Gauge32,
         sitaraPerfPlcyWanBurst             Gauge32,
         sitaraPerfPlcyPktCnt               Counter32,
         sitaraPerfPlcyPktCntDrop           Counter32,
         sitaraPerfPlcyPktCntBurst          Counter32,
         sitaraPerfPlcyByteCnt              Counter32,
         sitaraPerfPlcyByteCntDrop          Counter32,
         sitaraPerfPlcyQueuePkts            Counter32,
         sitaraPerfPlcyHandle               Unsigned32,
         sitaraPerfPlcyCbqName              CbqName,
         sitaraPerfPlcyAvgIdleTime          INTEGER,
	 sitaraPerfPlcyCustomerId	    PolicyCustomerId,
	 sitaraPerfPlcyOwner                SitaraOwnerString,
	 sitaraPerfPlcyPathName             PolicyPathName,
	 sitaraPerfPlcyDirection            PolicyDirection,
	 sitaraPerfPlcyStatus		    INTEGER,
	 sitaraPerfPlcyTimeStamp	    TimeTicks,
         sitaraPerfPlcyBandWidth  	    Gauge32,
         sitaraPerfPlcyBurst  	    	    Gauge32,
         sitaraPerfPlcyByteCntBurst         Counter64,
         sitaraPerfPlcyAvgQueSize           Counter32
     }


 sitaraPerfPlcyIndex OBJECT-TYPE
     SYNTAX      Unsigned32
     MAX-ACCESS  read-only
     STATUS      current
     DESCRIPTION
             "A unique value for each sitaraPerfTraf instance."
     ::= { sitaraPerfPlcyEntry 1 }

 sitaraPerfPlcyTime OBJECT-TYPE
     SYNTAX      TimeTicks
     MAX-ACCESS  read-only
     STATUS      obsolete
     DESCRIPTION
             "Value of sysUptime when policy statistics monitoring for 
	      this instance began"
     ::= { sitaraPerfPlcyEntry 2 }

 sitaraPerfPlcyInterval OBJECT-TYPE
     SYNTAX      INTEGER(1..3600)
     MAX-ACCESS  read-only
     STATUS      obsolete
     DESCRIPTION
             "Polling interval, in seconds, for this monitoring instance."
     DEFVAL   { 60 }
     ::= { sitaraPerfPlcyEntry 3 }

 sitaraPerfPlcyAlias OBJECT-TYPE
        SYNTAX      PolicyName
        MAX-ACCESS  read-only
        STATUS      obsolete
        DESCRIPTION
             "Alias (Nick Name) is the unique description for this Class
              that identifies the class to the user and displayed in the GUI."
     ::= { sitaraPerfPlcyEntry 4 }

sitaraPerfPlcyType OBJECT-TYPE
     SYNTAX      PolicyType
     MAX-ACCESS  read-only
     STATUS      current
     DESCRIPTION
             "Type of statistics being collected, currently 'class' is
              supported as policy type."
     ::= { sitaraPerfPlcyEntry 5 }

 sitaraPerfPlcyLanBandWidth OBJECT-TYPE
        SYNTAX      Gauge32
        MAX-ACCESS  read-only
        STATUS      obsolete
        DESCRIPTION
                "Link BandWidth Utilization in the Lan direction.  It is 
                 currently unused."
        ::= { sitaraPerfPlcyEntry 6 }

 sitaraPerfPlcyLanBurst OBJECT-TYPE
        SYNTAX      Gauge32
        MAX-ACCESS  read-only
        STATUS      obsolete
        DESCRIPTION
                "Link Burst BandWidth in the Lan direction.  It is currently unused."
        ::= { sitaraPerfPlcyEntry 7 }

 sitaraPerfPlcyWanBandWidth OBJECT-TYPE
        SYNTAX      Gauge32
        MAX-ACCESS  read-only
        STATUS      obsolete
        DESCRIPTION
        "Link BandWidth Utilization in the Wan direction.  It is currently unused."
        ::= { sitaraPerfPlcyEntry 8 }

 sitaraPerfPlcyWanBurst OBJECT-TYPE
        SYNTAX      Gauge32
        MAX-ACCESS  read-only
        STATUS      obsolete
        DESCRIPTION
        "Link Burst BandWidth in the Wan direction.  It is currently unused."
        ::= { sitaraPerfPlcyEntry 9 }

 sitaraPerfPlcyPktCnt OBJECT-TYPE
     SYNTAX      Counter32
     MAX-ACCESS  read-only
     STATUS      current
     DESCRIPTION
             "The number of packets sent during this interval."
     ::= { sitaraPerfPlcyEntry 10 }

 sitaraPerfPlcyPktCntDrop OBJECT-TYPE
     SYNTAX      Counter32 
     MAX-ACCESS  read-only
     STATUS      current
     DESCRIPTION
             "The number of packets for a class dropped during this interval as a
	      percentage of the total number of packets sent during this interval."
     ::= { sitaraPerfPlcyEntry 11 }

 sitaraPerfPlcyPktCntBurst OBJECT-TYPE
     SYNTAX      Counter32 
     MAX-ACCESS  read-only
     STATUS      current
     DESCRIPTION
             "The number of packets for this class exceeding class bandwidth as
	      a percentage of total packets sent during this interval.  
              It is currently unused."
     ::= { sitaraPerfPlcyEntry 12 }

 sitaraPerfPlcyByteCnt OBJECT-TYPE
     SYNTAX      Counter64 
     MAX-ACCESS  read-only
     STATUS      current
     DESCRIPTION
             "The number of bytes sent during the current period for this class."
     ::= { sitaraPerfPlcyEntry 13 }

 sitaraPerfPlcyByteCntDrop OBJECT-TYPE
     SYNTAX      Counter64 
     MAX-ACCESS  read-only
     STATUS      current
     DESCRIPTION
             "The number of bytes dropped during the current period for this class." 
     ::= { sitaraPerfPlcyEntry 14 }


 sitaraPerfPlcyQueuePkts OBJECT-TYPE
     SYNTAX      Counter32
     MAX-ACCESS  read-only
     STATUS      obsolete
     DESCRIPTION
             "The number of packets queued during this period for this class, as
	      a percent of the max queue size for this class."
     ::= { sitaraPerfPlcyEntry 15 }

 sitaraPerfPlcyHandle OBJECT-TYPE
     SYNTAX      Unsigned32
     MAX-ACCESS  read-only
     STATUS      obsolete
     DESCRIPTION
             "The handle of the policy class returned by a cbqd  
              ioctl() call.  Used to key in the stats info. into
              this table. "
     ::= { sitaraPerfPlcyEntry 16 }

sitaraPerfPlcyCbqName OBJECT-TYPE
     SYNTAX      CbqName
     MAX-ACCESS  read-only
     STATUS      current
     DESCRIPTION "Cbq Name"
     ::= { sitaraPerfPlcyEntry 17 }

 sitaraPerfPlcyAvgIdleTime OBJECT-TYPE
     SYNTAX      INTEGER (0..100)
     MAX-ACCESS  read-only
     STATUS      obsolete
     DESCRIPTION "Average Idle Time for a class as a percentage of the difference
                  between the Max Idle Time and the Min Idle Time."
     ::= { sitaraPerfPlcyEntry 18 }


 sitaraPerfPlcyCustomerId OBJECT-TYPE
    SYNTAX      PolicyCustomerId
    MAX-ACCESS  read-only
    STATUS      current
    DESCRIPTION
            "ID of customer uses this class"
		::= { sitaraPerfPlcyEntry 19 }

 sitaraPerfPlcyOwner OBJECT-TYPE
        SYNTAX      SitaraOwnerString 
        MAX-ACCESS  read-only
        STATUS      current
        DESCRIPTION
		"The owner name of this class."
		::= { sitaraPerfPlcyEntry 20 }

 sitaraPerfPlcyPathName OBJECT-TYPE
       SYNTAX      PolicyPathName
       MAX-ACCESS  read-only
       STATUS      current
       DESCRIPTION
       "Path Name gives the full specification of this link/Group/Class
       information.  See the PolicyPathName textual convention."
     		::= { sitaraPerfPlcyEntry 21 }

 sitaraPerfPlcyDirection  OBJECT-TYPE
       SYNTAX      PolicyDirection
       MAX-ACCESS  read-only
       STATUS      current
       DESCRIPTION
       "The policy group traffic direction object indicates the
       directionality of this flow. Based on the value of this object,
       the LAN and WAN bandwidth paramerts will be filled in. If this
       is a bi-directional flow, values for both the LAN and WAN
       objects should be supplied."
     		::= { sitaraPerfPlcyEntry 22 }

 sitaraPerfPlcyStatus OBJECT-TYPE
     SYNTAX      INTEGER 
		{
		active (1),
		inActive (2)
		}
     MAX-ACCESS  read-only
     STATUS      current
     DESCRIPTION
             " This specifies whether this Policy is active in the Current Schedule"
     ::= { sitaraPerfPlcyEntry 23 }
 
 sitaraPerfPlcyTimeStamp	   OBJECT-TYPE
     SYNTAX      TimeTicks
     MAX-ACCESS  read-only
     STATUS      current
     DESCRIPTION
             "TimeStamp is the SysupTime in number of ticks 
              at the time of reporting."
     ::= { sitaraPerfPlcyEntry 24 }

 sitaraPerfPlcyBandWidth OBJECT-TYPE
        SYNTAX      Gauge32
        MAX-ACCESS  read-only
        STATUS      current
        DESCRIPTION
        "Link BandWidth Utilization in the Wan direction.  It is currently unused."
        ::= { sitaraPerfPlcyEntry 25 }

 sitaraPerfPlcyBurst OBJECT-TYPE
        SYNTAX      Gauge32
        MAX-ACCESS  read-only
        STATUS      current
        DESCRIPTION
        "Link BandWidth Utilization in the Wan direction.  It is currently unused."
        ::= { sitaraPerfPlcyEntry 26 }

 sitaraPerfPlcyByteCntBurst OBJECT-TYPE
     SYNTAX      Counter64 
     MAX-ACCESS  read-only
     STATUS      current
     DESCRIPTION
             "The number of bytes sent as burst during this period for this class."
     ::= { sitaraPerfPlcyEntry 27 }

 sitaraPerfPlcyAvgQueSize     OBJECT-TYPE
     SYNTAX      Counter32
     MAX-ACCESS  read-only
     STATUS      current
     DESCRIPTION
             "The average of the number of packets queued so far for this class."
     ::= { sitaraPerfPlcyEntry 28 }






 --
 -- sitaraPerfCach - statistics for the web cache (SQUID)
 --
 -- The MIB objects for cache statistics are contained within the SQUID Mib
 -- are not reiterated in this MIB module.
 --

 --
 -- sitaraPerfNotifns - for Sitara Performance Monitoring MIB Module
 --
 --

 sitaraPerfNotifnsMemoryUtil NOTIFICATION-TYPE
    OBJECTS     {
		 alarmIndex,
		 alarmInterval,
		 alarmVariable,
		 alarmValue,
		 alarmRisingThreshold,
		 alarmFallingThreshold,
                 sitaraPerfSysMemoryUsage
                }
    STATUS      current
    DESCRIPTION
        "sitaraPerfNotifnsMemoryUtil notification is generated when the
         system memory utilization exceeds the configured threshold for
         system memory utilization as a percentage.
         sitaraPerfNotifnsMemoryUtil notification is maskable by
         setting the corresponding bit in the sitaraPerfAlarmMasks."
    ::= {  sitaraPerfNotifns  1 }

 sitaraPerfNotifnsCPU NOTIFICATION-TYPE
    OBJECTS     {
		 alarmIndex,
		 alarmInterval,
		 alarmVariable,
		 alarmValue,
		 alarmRisingThreshold,
		 alarmFallingThreshold,
                 sitaraPerfSysCPUUsage
                }
    STATUS      current
    DESCRIPTION
        "sitaraPerfNotifnsCPU notification is generated when the system
         CPU utilization exceeds the configured threshold for CPU
         utilization as a percentage. sitaraPerfNotifnsCPU
         notification is maskable by setting the corresponding bit
         in the sitaraPerfAlarmMasks."
    ::= {  sitaraPerfNotifns  2 }

 sitaraPerfNotifnsDiskCache NOTIFICATION-TYPE
    OBJECTS     {
		 alarmIndex,
		 alarmInterval,
		 alarmVariable,
		 alarmValue,
		 alarmRisingThreshold,
		 alarmFallingThreshold,
                 sitaraPerfSysDiskCacheUtilization
                }
    STATUS      current
    DESCRIPTION
        "sitaraPerfNotifnsDiskCache notification is generated when
         the disk space for the cache partition exceeds the configured
         threshold as a percentage. sitaraPerfNotifnsDiskCache
         notification is maskable by setting the corresponding bit
         in the sitaraPerfAlarmMasks."
    ::= {  sitaraPerfNotifns  3 }

 sitaraPerfNotifnsDiskSyslog NOTIFICATION-TYPE
    OBJECTS     {
		 alarmIndex,
		 alarmInterval,
		 alarmVariable,
		 alarmValue,
		 alarmRisingThreshold,
		 alarmFallingThreshold,
                 sitaraPerfSysDiskSyslogUtilization
                }
    STATUS      current
    DESCRIPTION
        "sitaraPerfNotifnsDiskSyslog notification is generated when
         the disk space for the syslog files partition exceeds the
         configured threshold as a percentage.
         sitaraPerfNotifnsDiskSyslog notification is maskable by
         setting the corresponding bit in the sitaraPerfAlarmMasks."
    ::= {  sitaraPerfNotifns  4 }

 sitaraPerfNotifnsDiskRoot NOTIFICATION-TYPE
    OBJECTS     {
		 alarmIndex,
		 alarmInterval,
		 alarmVariable,
		 alarmValue,
		 alarmRisingThreshold,
		 alarmFallingThreshold,
                 sitaraPerfSysDiskRootUtilization
                }
    STATUS      current
    DESCRIPTION
        "sitaraPerfNotifnsDiskRoot notification is generated when
         the utilized disk space for the root partition exceeds the
         configured threshold of the root partition as a percentage.
         sitaraPerfNotifnsDiskRoot notification is maskable by
         setting the corresponding bit in the sitaraPerfAlarmMasks."
    ::= {  sitaraPerfNotifns  5 }

 sitaraPerfNotifnsUpdate NOTIFICATION-TYPE
    STATUS      current
    DESCRIPTION
        "sitaraPerfNotifnsUpdate notification is generated when the Traffic Filter 
	 Table is updated"
    ::= {  sitaraPerfNotifns  6 }

 sitaraPerfNotifnsMonitorReStart NOTIFICATION-TYPE
    STATUS      current
    DESCRIPTION
        "sitaraPerfNotifnsMonitorReStart notification is generated when the Monitor 
         Table is updated after a Monitor restart.  It is currently unused."
    ::= {  sitaraPerfNotifns  7 }

 sitaraPerfNotifnsMonitorFailToReStart NOTIFICATION-TYPE
    STATUS      current
    DESCRIPTION
        "This failure notification is generated when the monitor process
         cannot be restarted.  It is currently unused."
    ::= {  sitaraPerfNotifns  8 }

 sitaraPerfNotifnsPlcyPktCnt NOTIFICATION-TYPE
    OBJECTS     {
		 alarmIndex,
		 alarmInterval,
		 alarmVariable,
		 alarmValue,
		 alarmRisingThreshold,
		 alarmFallingThreshold,
                 sitaraPerfPlcyAlias,
                 sitaraPerfPlcyType,
                 sitaraPerfPlcyLanBurst,
                 sitaraPerfPlcyWanBurst,
                 sitaraPerfPlcyPktCnt,
                 sitaraPerfPlcyPktCntBurst
                }
    STATUS      obsolete
    DESCRIPTION
        "This notification is generated when the packet count since the last
         interval for a policy class as a percentage of the total bandwidth
         exceeds the configured packet count threshold percent, specified in the 
         Alarm Table.  It is currently unused."
    ::= {  sitaraPerfNotifns  9 }

 sitaraPerfNotifnsPlcyPktCnt2 NOTIFICATION-TYPE
    OBJECTS     {
		 alarmIndex,
		 alarmInterval,
		 alarmVariable,
		 alarmValue,
		 alarmRisingThreshold,
		 alarmFallingThreshold,
                 sitaraPerfPlcyAlias,
                 sitaraPerfPlcyType,
                 sitaraPerfPlcyLanBurst,
                 sitaraPerfPlcyWanBurst,
                 sitaraPerfPlcyPktCnt,
                 sitaraPerfPlcyPktCntBurst
                }
    STATUS      obsolete
    DESCRIPTION
        "This notification is generated when the packet count as a 
	 percentage of wan speed for a policy exceeds a configured 
	 threshold, specified in the Alarm Table.  It is currently unused."
    ::= {  sitaraPerfNotifns  10 }

 sitaraPerfNotifnsPlcyBurst NOTIFICATION-TYPE
    OBJECTS     {
		 alarmIndex,
		 alarmInterval,
		 alarmVariable,
		 alarmValue,
		 alarmRisingThreshold,
		 alarmFallingThreshold,
                 sitaraPerfPlcyAlias,
                 sitaraPerfPlcyType,
                 sitaraPerfPlcyLanBurst,
                 sitaraPerfPlcyWanBurst,
                 sitaraPerfPlcyPktCnt,
                 sitaraPerfPlcyPktCntBurst
                }
    STATUS      obsolete
    DESCRIPTION
        "This notification is generated when the burst rate for a policy
         exceeds a configured threshold, specified in the Alarm Table.  
         It is currently unused."
    ::= {  sitaraPerfNotifns  11 }

 sitaraPerfNotifnsPlcyBandWidth NOTIFICATION-TYPE
    OBJECTS     {
                 alarmIndex,
                 alarmInterval,
                 alarmVariable,
                 alarmValue,
                 alarmRisingThreshold,
                 alarmFallingThreshold,
                 sitaraPerfPlcyIndex,
                 sitaraPerfPlcyCustomerId,
                 sitaraPerfPlcyOwner,
                 sitaraPerfPlcyPathName,
                 sitaraPerfPlcyDirection,
                 sitaraPerfPlcyType,
                 sitaraPerfPlcyBandWidth,

                 sitaraPerfPlcyPktCnt,
                 sitaraPerfPlcyPktCntDrop,
                 sitaraPerfPlcyPktCntBurst,
                 sitaraPerfPlcyByteCnt,
                 sitaraPerfPlcyByteCntDrop,
                 sitaraPerfPlcyByteCntBurst,

                 sitaraPerfPlcyAvgQueSize
                }
    STATUS      current
    DESCRIPTION
        "sitaraPerfNotifnsPlcyBandWidth notification is generated
         for a policy when the policy bandwidth
         (sitaraPerfPlcyByteCnt) utilized exceeds the configured
         rising threshold for the bandwidth of the same policy.
         sitaraPerfNotifnsPlcyBandWidt notification is maskable by
         setting the corresponding bit in the sitaraPerfAlarmMasks."
    ::= {  sitaraPerfNotifns  12 }

 sitaraPerfNotifnsPacketDrops NOTIFICATION-TYPE
    OBJECTS     {
		 alarmIndex,
		 alarmInterval,
		 alarmVariable,
		 alarmValue,
		 alarmRisingThreshold,
		 alarmFallingThreshold,
		 sitaraPerfPlcyIndex,
		 sitaraPerfPlcyCustomerId,
		 sitaraPerfPlcyOwner,
		 sitaraPerfPlcyPathName,
		 sitaraPerfPlcyDirection,
		 sitaraPerfPlcyType,
		 sitaraPerfPlcyBandWidth,

		 sitaraPerfPlcyPktCnt,
		 sitaraPerfPlcyPktCntDrop,
		 sitaraPerfPlcyPktCntBurst,
		 sitaraPerfPlcyByteCnt,
		 sitaraPerfPlcyByteCntDrop,
		 sitaraPerfPlcyByteCntBurst,

		 sitaraPerfPlcyAvgQueSize
                }
    STATUS      current
    DESCRIPTION
        "sitaraPerfNotifnsPacketDrops notification is generated
         for a policy when the policy dropped packet count
        (sitaraPerfPlcyPktCntDrop) exceeds the configured rising
         threshold for dropped packet count of the same policy.
         sitaraPerfNotifnsPacketDrops notification is maskable by
         setting the corresponding bit in the sitaraPerfAlarmMasks."
    ::= {  sitaraPerfNotifns  13 }


 sitaraPerfNotifnsCachHitsRatio NOTIFICATION-TYPE
    OBJECTS	{
		 alarmIndex,
		 alarmInterval,
		 alarmVariable,
		 alarmValue,
		 alarmRisingThreshold,
		 alarmFallingThreshold
		}
    STATUS      obsolete
    DESCRIPTION
        "This notification is generated when the cache miss/hit 
         ratio is lower than a configured threshold, specified in the 
         Alarm Table.  It is currently unused."
    ::= {  sitaraPerfNotifns  14 }

 sitaraPerfNotifnsPlcyMaxBandwidth NOTIFICATION-TYPE
    OBJECTS     {
		 alarmIndex,
		 alarmInterval,
		 alarmVariable,
		 alarmValue,
		 alarmRisingThreshold,
		 alarmFallingThreshold,
                 sitaraPerfPlcyAlias,
                 sitaraPerfPlcyType,
                 sitaraPerfPlcyLanBandWidth,
                 sitaraPerfPlcyWanBandWidth 
                }
    STATUS      obsolete
    DESCRIPTION
        "This notification is generated when the maximum bandwidth 
         for a policy, as a percentage  of total wan speed, exceeds 
         a configured threshold, specified in the Alarm Table.
         It is currently unused."
    ::= {  sitaraPerfNotifns  15 }

 sitaraPerfNotifnsPlcyQueuePkts NOTIFICATION-TYPE
    OBJECTS     {
		 alarmIndex,
		 alarmInterval,
		 alarmVariable,
		 alarmValue,
		 alarmRisingThreshold,
		 alarmFallingThreshold,
                 sitaraPerfPlcyAlias,
                 sitaraPerfPlcyCbqName,
                 sitaraPerfPlcyType,
                 sitaraPerfPlcyLanBandWidth,
                 sitaraPerfPlcyWanBandWidth, 
                 sitaraPerfPlcyQueuePkts
                }
    STATUS      obsolete
    DESCRIPTION
        "This notification is generated when the allowed maximum que size 
         for a policy, exceeds a configured allowed maximum que size, 
         specified in the Alarm Table."
    ::= {  sitaraPerfNotifns  16 }

 sitaraPerfNotifnsPlcyMaxIdleTime NOTIFICATION-TYPE
    OBJECTS     {
		 alarmIndex,
		 alarmInterval,
		 alarmVariable,
		 alarmValue,
		 alarmRisingThreshold,
		 alarmFallingThreshold,
                 sitaraPerfPlcyAlias,
                 sitaraPerfPlcyCbqName,
                 sitaraPerfPlcyType,
                 sitaraPerfPlcyLanBandWidth,
                 sitaraPerfPlcyWanBandWidth,
                 sitaraPerfPlcyAvgIdleTime  
                }
    STATUS      obsolete
    DESCRIPTION
            "This notification is generated when the Average Idle Time for a 
             class as a percentage of the difference between the Max Idle 
             Time and the Min Idle Time exceeds the configured (rising) 
             threshold specified in the Alarm Table."
    ::= {  sitaraPerfNotifns  17 }

 sitaraPerfNotifnsPlcyMinIdleTime NOTIFICATION-TYPE
    OBJECTS     {
		 alarmIndex,
		 alarmInterval,
		 alarmVariable,
		 alarmValue,
		 alarmRisingThreshold,
		 alarmFallingThreshold,
                 sitaraPerfPlcyAlias,
                 sitaraPerfPlcyCbqName,
                 sitaraPerfPlcyType,
                 sitaraPerfPlcyLanBandWidth,
                 sitaraPerfPlcyWanBandWidth,
                 sitaraPerfPlcyAvgIdleTime  
                }
    STATUS      obsolete
    DESCRIPTION
            "This notification is generated when the Average Idle Time for a 
             class as a percentage of the difference between the Max Idle 
             Time and the Min Idle Time falls below the configured (falling) 
             threshold specified in the Alarm Table."
    ::= {  sitaraPerfNotifns  18 }

 sitaraPerfNotifnsPlcyAveQueueLength NOTIFICATION-TYPE
    OBJECTS     {
		 alarmIndex,
		 alarmInterval,
		 alarmVariable,
		 alarmValue,
		 alarmRisingThreshold,
		 alarmFallingThreshold,
		 sitaraPerfPlcyIndex,
		 sitaraPerfPlcyCustomerId,
		 sitaraPerfPlcyOwner,
		 sitaraPerfPlcyPathName,
		 sitaraPerfPlcyDirection,
		 sitaraPerfPlcyType,
		 sitaraPerfPlcyBandWidth,

		 sitaraPerfPlcyPktCnt,
		 sitaraPerfPlcyPktCntDrop,
		 sitaraPerfPlcyPktCntBurst,
		 sitaraPerfPlcyByteCnt,
		 sitaraPerfPlcyByteCntDrop,
		 sitaraPerfPlcyByteCntBurst,

		 sitaraPerfPlcyAvgQueSize
                }
    STATUS      current
    DESCRIPTION
        "sitaraPerfNotifnsPlcyAveQueueLength notification is generated
         for a policy when the average que size of the policy exceeds
         the configured rising threshold for the average que size of
         the same policy.
         sitaraPerfNotifnsPlcyAveQueueLength notification is maskable
         by setting the corresponding bit in the sitaraPerfAlarmMasks."
    ::= {  sitaraPerfNotifns  19 }

 END
