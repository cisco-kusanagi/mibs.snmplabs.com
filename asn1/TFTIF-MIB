--
-- Based on the comments from OSCAR group 
-- MIB Revision Dated: 05-31-96
-- 
-- MIB Revision : 1.0 dated 1-17-97
-- Change Desc. : mcmTFTPDownload ACCESS changed from 
--                read-write to write-only. A.Llanes 
-- 
-- 
-- MIB Revision : 1.1 dated 2-25-97
-- Change Desc. : Added option defaultenabled to the 
--                object mcmTFTPDownload. 
-- 
-- 
-- MIB Revision : 1.2 dated 3-18-97
-- Change Desc. : Changed all occurences of Octet String to Display String.
--                Changed from msecs to seconds for Timeout Help description.
--                Modified the data values for LastErrorStatus parameter and
--                add extra description to the Help tag. All these changes 
--                were made per Tom Messick's request. - A. Llanes
-- 
-- MIB Revision : 1.3 dated 3-31-97
-- Change Desc. : Specified ranges for different objects. 
-- 
-- MIB Revision : 1.4 dated 4-22-97 by Shridhar.
-- Change Desc  : Capabilities for objects.
--
-- MIB Revision : 1.5 dated 5-17-97
-- Change Desc. : Updated description "DESC" entry. -BP
--
-- MIB Revision : 1.6 dated 6-27-97
-- Change Desc. : Added Trap descriptions. - M.B. 
-- 
-- MIB Revision : 1.7 dated 8-26-97
-- Change Desc. : Added mcmTFTPDownloadSuccess TRAP_TYPE - B. Jafari
-- 
-- MIB Revision : 1.8 dated 10-8-97
-- Change Desc. : Replaced MPA with 4400 - B. Jafari. 
-- 
-- *** RELEASE 3.0 ***
-- MIB Revision : 1.9 dated 6-24-98
-- Change Desc. : Removed and/or replaced "4400" with 
--				  "access device" wherever possible. -A. Llanes
--
-- MIB Revision : 2.0 dated 8-24-98
-- Change Desc. : Added mcm/(nvm)TFTPPortNumber OBJECT-TYPE
--                      mcm/(nvm)TFTPUpload OBJECT-TYPE
--                      mcm/(nvm)TFTPConfigUploadBank OBJECT-TYPE
--                      mcmTFTPTransferBank OBJECT-TYPE
-- Change Desc  : removed Tftp upload and download objects
--              : added tftp start object
--                      - N. Desai.  merged by BrianP

    TFTIF-MIB DEFINITIONS ::= BEGIN

    IMPORTS
           DisplayString
                    FROM RFC1213-MIB
            IpAddress
                    FROM RFC1155-SMI
            micom-oscar
                    FROM MICOM-OSCAR-MIB
            OBJECT-TYPE
                    FROM RFC-1212
            TRAP-TYPE
                    FROM RFC-1215
            mcmSysAsciiTimeOfDay
                    FROM MICOM-SYS-MIB;


          MemAddress ::= OCTET STRING (SIZE (4))    -- a 4 octet address
		-- the first byte signifies the MSB portion of the
		-- physical address, the second the next and the fourth
		-- the LSB portion of the physical address.

    --  This MIB module uses the extended OBJECT-TYPE macro as
    --  This MIB module uses the extended OBJECT-TYPE macro as
    --  defined in [13]


    --  this is the MIB module for TFTP Interface objects

   mcmTFTP	OBJECT IDENTIFIER ::= { micom-oscar 3 }


 -- TFTP Parameters Group

 -- The implementation of this group is mandatory for all RLR systems. cd

 -- This group consists of objects pertaining to the TFTP Operation
 -- commands and parameters.

mcmTFTPParamGroup    OBJECT IDENTIFIER ::= { mcmTFTP 1 }

mcmTFTPServerIpAddr OBJECT-TYPE
	SYNTAX	IpAddress
	ACCESS	read-write
	STATUS	mandatory
	DESCRIPTION
	  "NAME = ;
	   DESC = The IP Address of the TFTP Server.;
	   HELP = ;
	   CAPABILITIES = NET_CFG, VPN_NONE;"
	::= { mcmTFTPParamGroup 1 }

mcmTFTPFileName OBJECT-TYPE
	SYNTAX	DisplayString
	ACCESS	read-write
	STATUS	mandatory
	DESCRIPTION
	  "NAME = ;
	   DESC = The Filename with path (ASCII) to be downloaded;
	   HELP = ;
	   CAPABILITIES = NET_CFG, VPN_NONE;"
	::= { mcmTFTPParamGroup 2 }

mcmTFTPTimeOut OBJECT-TYPE
	SYNTAX	INTEGER (1..900)
	ACCESS	read-write
	STATUS	mandatory
	DESCRIPTION
	  "NAME = ;
	   DESC = The TFTP timeout period in seconds.;
	   HELP = Time is doubled for each retransmission.;
	   CAPABILITIES = NET_CFG, VPN_NONE;"
	::= { mcmTFTPParamGroup 3 }

mcmTFTPRetransmissions OBJECT-TYPE
	SYNTAX	INTEGER (1..100)
	ACCESS	read-write
	STATUS	mandatory
	DESCRIPTION
	  "NAME = ;
	   DESC = The number of times the TFTP request \
		  will be repeated for un-responsive \
		  TFTP servers.;
	   HELP = ;
	   CAPABILITIES = NET_CFG, VPN_NONE;"
	::= { mcmTFTPParamGroup 4 }

mcmTFTPDownload OBJECT-TYPE
	SYNTAX	INTEGER { 
                upldDefault(1), 
                upldSpecific(2), 
                dnldDefault(3),
                dnldSpecific(4),
                disabled(5) 

		}
	ACCESS	write-only
	STATUS	deprecated
	DESCRIPTION
	  "NAME = ;
	   DESC = This object when enabled results in \
		  the unit to attempt code download.;
	   HELP = ;
	   CAPABILITIES = NET_CFG, VPN_NONE;"
	::= { mcmTFTPParamGroup 5 }

mcmTFTPStart OBJECT-TYPE
        SYNTAX  INTEGER { 
                upldDefault(1), 
                upldSpecific(2), 
                dnldDefault(3),
                dnldSpecific(4),
                disabled(5) 
                }
        ACCESS  write-only
        STATUS  mandatory
        DESCRIPTION
          "NAME = ;
           DESC = initiates TFTP upload or download process\
                  based on previously provisioned values \
                  (default) or values passed at request \
                  time(specific) ; 
           HELP = ;
           CAPABILITIES = NET_CFG, VPN_NONE;"
        ::= { mcmTFTPParamGroup 6 }

mcmTFTPPortNumber OBJECT-TYPE
        SYNTAX  INTEGER (1..65535)
        ACCESS  read-write
        STATUS  mandatory
        DESCRIPTION
          "NAME = ;
           DESC = This object is used to specify the \
                  port <socket> number sent to the TFTP\ 
                  connection. ;
           HELP = ;
           CAPABILITIES = NET_CFG,  VPN_NONE;"
        ::= { mcmTFTPParamGroup 7 }


mcmTFTPConfigUploadBank OBJECT-TYPE
        SYNTAX  INTEGER {
                        bank3(1),
                        bank4(2)
                        }
        ACCESS  read-write
        STATUS  mandatory
        DESCRIPTION
          "NAME = ;
           DESC = The configuration bank number which\
                  will be uploaded to the TFTP host. ;
           HELP = ;
           CAPABILITIES = NET_CFG,  VPN_NONE;"
        ::= { mcmTFTPParamGroup 8 }



nvmTFTPParamGroup    OBJECT IDENTIFIER ::= { mcmTFTP 2 }

nvmTFTPServerIpAddr OBJECT-TYPE
	SYNTAX	IpAddress
	ACCESS	read-only
	STATUS	mandatory
	DESCRIPTION
	  "NAME = ;
	   DESC = The IP Address of the TFTP Server.;
	   HELP = ;
	   CAPABILITIES = NET_CFG, VPN_NONE;"
	::= { nvmTFTPParamGroup 1 }

nvmTFTPFileName OBJECT-TYPE
	SYNTAX	DisplayString
	ACCESS	read-only
	STATUS	mandatory
	DESCRIPTION
	  "NAME = ;
	   DESC = The Filename with path (ASCII) to be \
		  downloaded or to upload;
	   HELP = ;
	   CAPABILITIES = NET_CFG, VPN_NONE;"
	::= { nvmTFTPParamGroup 2 }

nvmTFTPTimeOut OBJECT-TYPE
	SYNTAX	INTEGER
	ACCESS	read-only
	STATUS	mandatory
	DESCRIPTION
	  "NAME = ;
	   DESC = The TFTP timeout period in seconds.;
	   HELP = Time is doubled for each retransmission;
	   CAPABILITIES = NET_CFG, VPN_NONE;"
	::= { nvmTFTPParamGroup 3 }

nvmTFTPRetransmissions OBJECT-TYPE
	SYNTAX	INTEGER
	ACCESS	read-only
	STATUS	mandatory
	DESCRIPTION
	  "NAME = ;
	   DESC = The number of times the TFTP request \
		  will be repeated for un-responsive \
		  TFTP servers.;
	   HELP = ;
	   CAPABILITIES = NET_CFG, VPN_NONE;"
	::= { nvmTFTPParamGroup 4 }

nvmTFTPPortNumber OBJECT-TYPE
        SYNTAX  INTEGER (1..65535)
        ACCESS  read-only
        STATUS  mandatory
        DESCRIPTION
          "NAME = ;
           DESC = This object is used to specify the \
                  port <socket> number sent to the TFTP\ 
                  connection. ;
           HELP = ;
           CAPABILITIES = NET_CFG,  VPN_NONE;"
        ::= { nvmTFTPParamGroup 5 }


nvmTFTPConfigUploadBank OBJECT-TYPE
        SYNTAX  INTEGER {
                        bank3(1),
                        bank4(2)
                        }
        ACCESS  read-only
        STATUS  mandatory
        DESCRIPTION
          "NAME = ;
           DESC = The configuration bank number which\
                  will be uploaded to the TFTP host. ;
           HELP = ;
           CAPABILITIES = NET_CFG,  VPN_NONE;"
        ::= { nvmTFTPParamGroup 6 }


 -- TFTP Status Group

 -- The implementation of this group is mandatory for all RLR systems. 
 -- This group consists of objects pertaining to the TFTP Status
 -- commands and parameters.

mcmTFTPStatusGroup    OBJECT IDENTIFIER ::= { mcmTFTP 3 }

mcmTFTPCurrentState OBJECT-TYPE
	SYNTAX	INTEGER { 
		idle(1), 
		retrieving-file(2)
		}
	ACCESS	read-only
	STATUS	mandatory
	DESCRIPTION
	  "NAME = ;
	   DESC = This object shows the current status \
		  of TFTP interface.;
	   HELP = ;
	   CAPABILITIES = NET_CFG, VPN_NONE;"
	::= { mcmTFTPStatusGroup 1 }

mcmTFTPErrorStatusGroup    OBJECT IDENTIFIER ::= { mcmTFTP 4 }

mcmTFTPLastErrorStatus OBJECT-TYPE
	SYNTAX	INTEGER { 
			idle(1), 
			download-success(2), 
			out-of-memory(4), 
			flash-error(5), 
			download-failed(6),
                        upload-failed(7),
                        upload-success(8), 
			chksum-error(11), 
                        transferring-file (13),
                        protocol-error (14),
                        server-error (15),
                        timeout (16),
                        connection-error (17),
                        bad-file (18)
			}
	ACCESS	read-only
	STATUS	mandatory
	DESCRIPTION
	  "NAME = ;
	   DESC = This object shows the error status of \
		  last TFTP operation.;
	   HELP = Error status values: \
                     value                 meaning      \
                  --------------------------------------------------\
                  idle               No download has been done         \
                  download-success   A download completed without error\
                  out-of-memory      Not enough free memory            \
                  flash-error        Could not write to flash memory   \
                  download-failed    Download failed for an unknown reason \
                  chksum-error       The file to download has a checksum error \
                  retrieving-file    The file to download is being retrieved \
                  protocol-error     TFTP had an error talking to server \
                  server-error       The TFTP server sent error message, Could be bad file name \
                  timeout            Could be bad ip address or network errors \
                  connection-error   Setup of connection failed \
                  bad-file           The file to be download was rejected;
	   CAPABILITIES = NET_CFG, VPN_NONE;"
	::= { mcmTFTPErrorStatusGroup 1 }

mcmTFTPLastServerIpAddr OBJECT-TYPE
	SYNTAX	IpAddress
	ACCESS	read-only
	STATUS	mandatory
	DESCRIPTION
	  "NAME = ;
	   DESC = The IP Address of the last TFTP Server.;
	   HELP = ;
	   CAPABILITIES = NET_CFG, VPN_NONE;"
	::= { mcmTFTPErrorStatusGroup 2 }

mcmTFTPLastFileName OBJECT-TYPE
	SYNTAX	DisplayString
	ACCESS	read-only
	STATUS	mandatory
	DESCRIPTION
	  "NAME = ;
	   DESC = The Filename path (ASCII) of the previously downloaded file.;
	   HELP = ;
	   CAPABILITIES = NET_CFG, VPN_NONE;"
	::= { mcmTFTPErrorStatusGroup 3 }

mcmTFTPTransferBank OBJECT-TYPE
        SYNTAX INTEGER {
                        none(1),
                        toboot(2),
                        toBank1(3),
                        toBank2(4),
                        toBank3(5),
                        toBank4(6),
                        fromBank3(7),
                        fromBank4(8),
                        fromDebug(9)
                        }
        ACCESS  read-only
        STATUS  mandatory
        DESCRIPTION
          "NAME = ;
           DESC = Specifies which flash bank is currently\
                  being uploaded/dwonloaded via the tftp \
                  application process ;
           HELP = ;
           CAPABILITIES = NET_CFG,  VPN_NONE;"
        ::= {mcmTFTPErrorStatusGroup 4 }

mcmTFTPLastPortNumber OBJECT-TYPE
        SYNTAX  INTEGER (1..65535)
        ACCESS  read-only
        STATUS  mandatory
        DESCRIPTION
          "NAME = ;
           DESC = This object is used to specify the \
                  port <socket> number sent to the TFTP\ 
                  connection. ;
           HELP = ;
           CAPABILITIES = NET_CFG,  VPN_NONE;"
        ::= { mcmTFTPErrorStatusGroup 5 }


-- Trap Messages

mcmTFTPDownloadFail TRAP-TYPE
	ENTERPRISE	mcmTFTP
	VARIABLES	{mcmSysAsciiTimeOfDay, mcmTFTPServerIpAddr, mcmTFTPFileName}
	DESCRIPTION
	  "NAME = ;
	   DESC =  A TFTP Code download has failed between the \
		   PP4400 and the Server.;
	   HELP = Please check Network cables, Server being alive, and retry \
                  again. If problem persists, contact Sys Admin., or Field \
                  Personnel.;"
	::= 1

mcmTFTPUploadFail TRAP-TYPE
	ENTERPRISE	mcmTFTP
	VARIABLES	{mcmSysAsciiTimeOfDay, mcmTFTPServerIpAddr, mcmTFTPFileName}
	DESCRIPTION
	  "NAME = ;
	   DESC = TFTP file upload to server has failed.;
	   HELP = See error status for type of transfer failure.;"
	::= 2

mcmTFTPDownloadSuccess TRAP-TYPE
	ENTERPRISE	mcmTFTP
	VARIABLES	{mcmSysAsciiTimeOfDay, mcmTFTPServerIpAddr, mcmTFTPFileName}
	DESCRIPTION
	  "NAME = ;
	   DESC =  A TFTP Code download has succeeded between the \
		   PP4400 and the Server.;
	   HELP = TFTP Code download was successful. \
                  Normal Status Indicator.;"
	::= 3


mcmTFTPUploadSuccess TRAP-TYPE
        ENTERPRISE      mcmTFTP
        VARIABLES       {mcmSysAsciiTimeOfDay, mcmTFTPServerIpAddr, mcmTFTPFileName}
        DESCRIPTION
          "NAME = ;
           DESC =  A TFTP file upload has succeeded between the \
                   4400 and the Server.;
           HELP = TFTP file upload was successful. \
                  Normal Status Indicator.;"
        ::= 4

-- End of Trap Messages

END
