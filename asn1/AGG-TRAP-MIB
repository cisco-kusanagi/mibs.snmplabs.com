AGG-TRAP-MIB DEFINITIONS ::= BEGIN
IMPORTS
    enterprises, Counter
        FROM RFC1155-SMI
    OBJECT-TYPE
        FROM RFC-1212
    DisplayString
        FROM RFC1213-MIB
    NOTIFICATION-TYPE, MODULE-IDENTITY, ObjectName, Integer32, Counter32, snmpModules
        FROM SNMPv2-SMI
    unknownDeviceTrapContents, pepName, devName, host, port, file, oldFile, newFile,
    reason, snName, myHost, myPort, mateHost, matePort, minutes, result, sbProducerHost, sbProducerPort
        FROM AGGREGATED-EXT-MIB
    TruthValue, DisplayString, TestAndIncr, TimeStamp, RowStatus
        FROM SNMPv2-TC;
lucent			OBJECT IDENTIFIER  ::=  {  enterprises  1751  }
products		OBJECT IDENTIFIER  ::=  {  lucent  1  }
mantraDevice	OBJECT IDENTIFIER  ::=  {  products 1198  }

mantraTraps   MODULE-IDENTITY    
        LAST-UPDATED "240701"
        ORGANIZATION "Lucent Technologies"    
        CONTACT-INFO 
                ""    
        DESCRIPTION
                "The MIB module for entities implementing the xxxx
                protocol."  

::=  {  mantraDevice 0 }

--
--	------------ TRAPS FOLLOW THIS LINE ----------------
--


	unParsedEvent NOTIFICATION-TYPE
	    OBJECTS  { unknownDeviceTrapContents }
        STATUS current 
	    DESCRIPTION
		"An event is sent up as unParsedEvent, 
		if there is an error in formatting, and event
		construction does not succeed.
		The variables are:
		1) unknownDeviceTrapContents - a string representing 
		   the event text as the pep received it.
		Severity: MAJOR"
	    ::= { mantraTraps  5 }

	styxProducerConnect NOTIFICATION-TYPE
	    OBJECTS  { pepName, devName, host, port, file }
        STATUS current
	    DESCRIPTION
		"Indicates that the pep was sucessfully able to 
		connect to the source of events specified in its
		config.
		The variables are:
		1)   pepName - this is the name of the PEP who
		     is raising the event
		2)   devName - this is the logical name of the 
		     device this pep is connected to
		3-4) host:port - these two identify the device 
		     that was mounted by the pep
		5)   file - this is the file name used internally
 		     start-up event, mainly.  
		Severity: INFO"
	    ::= { mantraTraps  6 }

	styxProducerUnReadable NOTIFICATION-TYPE
	    OBJECTS  { pepName, devName, host, port, file }
        STATUS current
	    DESCRIPTION
		"Indicates that the pep's connection exists to the
		device, but the file named in the trap is not 
		readable.
		The variables are:
		1)   pepName - this is the name of the PEP who
		     is raising the event
		2)   devName - this is the logical name of the 
		     device this pep is connected to
		3-4) host:port - these two identify the device 
		     that was mounted by the pep
		5)   file - this is the file name used internally
		Severity: MAJOR"
	    ::= { mantraTraps  7 }

	styxProducerDisconnect NOTIFICATION-TYPE
	    OBJECTS  { pepName, devName, host, port, file }
        STATUS current
	    DESCRIPTION
		"Indicates that the pep's connection to the source
		of events was severed.  This could either be because 
		device process died, or because there is a network outage.
		The variables are:
		1)   pepName - this is the name of the PEP who
		     is raising the event
		2)   devName - this is the logical name of the 
		     device this pep is connected to
		3-4) host:port - these two identify the device 
		     that was mounted by the pep
		5)   file - this is the file name used internally
		Severity: MAJOR"
	    ::= { mantraTraps  8 }

	styxProducerUnReachable NOTIFICATION-TYPE
	    OBJECTS  { pepName, devName, host, port, file, minutes }
        STATUS current
	    DESCRIPTION
		"Indicates that the pep's connection to the device 
		has not been up for some time now, indicated in 
		minutes.
		The variables are:
		1)   pepName - this is the name of the PEP who
		     is raising the event
		2)   devName - this is the logical name of the 
		     device this pep is connected to
		3-4) host, port - these two identify the device 
		     that was mounted by the pep
		5)   file - this is the file name used internally
		     minutes - the time in minutes for which the 
		     connection to the device has not been up.
		Severity: MAJOR"
	    ::= { mantraTraps  9 }

	logFileChanged NOTIFICATION-TYPE
	    OBJECTS  { oldFile, newFile, result, reason }
        STATUS current
	    DESCRIPTION
		"Indicates that a log-file-change attempt is successful or 
		failure.
		The variables are:
		1)   oldFile - this is the name of the old file which
		     was to be changed.
		2)   newFile - this is the new log file name 
		3)   result  - this indicates 'success' or failure of
		     logFileChange attempt.
		4)   reason - this describes the reason when log file change
		     has failed.
		Severity: INFO"
	    ::= { mantraTraps  10 }

	styxFTMateConnect NOTIFICATION-TYPE
	    OBJECTS  { snName, myHost, myPort, mateHost, matePort }
        STATUS current
	    DESCRIPTION
		"Indicates that this ServiceNode was sucessfully able to 
		connect to its redundant mate. This event is usually raised
		by the Backup mate who is responsible for monitoring its
		respective Primary.
		The variables are:
		1)   snName - this is the name of the ServiceNode who
		     is raising the event. 
		2-3)   myHost:myPort - these identify the host and port of the
		     ServiceNode raising the event.
		4-5) mateHost:matePort - these identify the host and port
		     of the mate to which this ServiceNode connected.
		Severity: INFO"
	    ::= { mantraTraps  11 }

	styxFTMateDisconnect NOTIFICATION-TYPE
	    OBJECTS  { snName, myHost, myPort, mateHost, matePort }
        STATUS current
	    DESCRIPTION
		"Indicates that this ServiceNode has lost connection 
		to its redundant mate due to either process or host failure. 
		This event is usually raised by the Backup mate who is
		monitoring its 	respective Primary. Connection will be
		established upon recovery of the mate.
		The variables are:
		1)   snName - this is the name of the ServiceNode who
		     is raising the event
		2-3)   myHost:myPort - these identify the host and port of the
		     ServiceNode raising the event.
		4-5) mateHost:matePort - these identify the host and port
		     of the mate to which this ServiceNode lost connection.

		Severity: MAJOR"
	    ::= { mantraTraps  12 }

	sBProducerUnreachable NOTIFICATION-TYPE
	    OBJECTS  { pepName, devName, sbProducerHost, sbProducerPort }
        STATUS current
	    DESCRIPTION
		"Indicates that this Socket Based Producer is not reachable by the Policy 
		Enforcement Point.  
		The variables are:
		1)   pepName - this is the name of the Policy Enforcement Point (PEP)  who
		     is raising the event
		2)   devName: Device which is unreachable
		3)   sbProducerHost: Host where the Socket Based event producer is on.
		4)   sbProducerPort: Port where the Socket Based event producer is running on.

		Severity: MAJOR"
	    ::= { mantraTraps  13 }

	sBProducerConnected NOTIFICATION-TYPE
	    OBJECTS  { pepName, devName, sbProducerHost, sbProducerPort }
        STATUS current
	    DESCRIPTION
		"Indicates that this Socket Based Producer has connected to the Policy 
		Enforcement Point (PEP).  
		The variables are:
		1)   pepName - this is the name of the Policy Enforcement Point (PEP)  who
		     is raising the event
		2)   devName: Device which is unreachable
		3)   sbProducerHost: Host where the Socket Based event producer is on.
		4)   sbProducerPort: Port where the Socket Based event producer is running on.

		Severity: MAJOR"
	    ::= { mantraTraps  14 }

	sBProducerRegistered NOTIFICATION-TYPE
	    OBJECTS  { pepName, devName, sbProducerHost, sbProducerPort }
        STATUS current
	    DESCRIPTION
		"Indicates that this Socket Based Producer has registered with the Policy 
		Enforcement Point (PEP).  
		The variables are:
		1)   pepName - this is the name of the Policy Enforcement Point (PEP)  who
		     is raising the event
		2)   devName: Device which is unreachable
		3)   sbProducerHost: Host where the Socket Based event producer is on.
		4)   sbProducerPort: Port where the Socket Based event producer is running on.

		Severity: INFO"
	    ::= { mantraTraps  15 }

	sBProducerDisconnected NOTIFICATION-TYPE
	    OBJECTS  { pepName, devName, sbProducerHost, sbProducerPort }
        STATUS current
	    DESCRIPTION
		"Indicates that this Socket Based Producer has disconnected from the Policy 
		Enforcement Point (PEP).  
		The variables are:
		1)   pepName - this is the name of the Policy Enforcement Point (PEP)  who
		     is raising the event
		2)   devName: Device which is unreachable
		3)   sbProducerHost: Host where the Socket Based event producer is on.
		4)   sbProducerPort: Port where the Socket Based event producer is running on.

		Severity: INFO"
	    ::= { mantraTraps  16 }

	sBProducerCannotRegister NOTIFICATION-TYPE
	    OBJECTS  { pepName, devName, sbProducerHost, sbProducerPort }
        STATUS current
	    DESCRIPTION
		"Indicates that this Socket Based Producer cannot register to the Policy 
		Enforcement Point (PEP).  
		The variables are:
		1)   pepName - this is the name of the Policy Enforcement Point (PEP)  who
		     is raising the event
		2)   devName: Device which is unreachable
		3)   sbProducerHost: Host where the Socket Based event producer is on.
		4)   sbProducerPort: Port where the Socket Based event producer is running on.

		Severity: INFO"
	    ::= { mantraTraps  17 }

	sBProducerCannotDisconnect NOTIFICATION-TYPE
	    OBJECTS  { pepName, devName, sbProducerHost, sbProducerPort }
        STATUS current
	    DESCRIPTION
		"Indicates that this Socket Based Producer cannot disconenct  from  the Policy 
		Enforcement Point (PEP).  
		The variables are:
		1)   pepName - this is the name of the Policy Enforcement Point (PEP)  who
		     is raising the event
		2)   devName: Device which is unreachable
		3)   sbProducerHost: Host where the Socket Based event producer is on.
		4)   sbProducerPort: Port where the Socket Based event producer is running on.

		Severity: INFO"
	    ::= { mantraTraps  18 }
END
