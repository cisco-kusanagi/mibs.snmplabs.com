--
-- COPYRIGHT NOTICE
-- Copyright (c) Alteon WebSystems, Inc. 2001-2002
-- All rights reserved.
--
-- Models Alteon Switched Firewall

ALTEON-ASF-MIB DEFINITIONS ::= BEGIN

IMPORTS
    OBJECT-IDENTITY, MODULE-IDENTITY, OBJECT-TYPE, Counter32, Gauge32, Counter64,
    Unsigned32, IpAddress, Integer32, TimeTicks,  NOTIFICATION-TYPE FROM SNMPv2-SMI
    DisplayString, TruthValue, MacAddress, TimeStamp    FROM SNMPv2-TC
    firewall                           	     FROM ALTEON-ROOT-MIB;

    alteonAsfMIB MODULE-IDENTITY
    LAST-UPDATED "0203140000Z"				-- 14 March 2002
    ORGANIZATION "Alteon WebSystems"
    CONTACT-INFO "  "
    DESCRIPTION "MIB for Alteon Switched Firewall."

	REVISION	"0203110000Z"
	DESCRIPTION "Added port statistics and iSD session statistics."
    ::= { firewall 1 }

-- ****************************************************************************
-- Proposed placeholders for eventual GET functionality

--  asfGlobal           OBJECT-IDENTITY
--  STATUS              current
--  DESCRIPTION         "Objects under this branch provide general monitoring
--                       information for the system."
--  ::= { alteonAsfMIB 1 }

--	asfMonitor          OBJECT-IDENTITY
--  STATUS              current
--  DESCRIPTION         "Objects under this branch provide general monitoring
--                       information for the system."
--  ::= { alteonAsfMIB 2 }

--	asfCluster          OBJECT-IDENTITY
--  STATUS              current
--  DESCRIPTION         "Objects under this branch provide general settings
--                       for the ASF cluster, which includes both iSDs and
--						 accelerators."
--  ::= { alteonAsfMIB 3 }

--	asfNetwork          OBJECT-IDENTITY
--  STATUS              current
--  DESCRIPTION         "Objects under this branch provide general settings
--                       for ASF networking."
--  ::= { alteonAsfMIB 4 }

--	asfFirewall         OBJECT-IDENTITY
--  STATUS              current
--  DESCRIPTION         "Objects under this branch provide general settings
--                       for Check Point firewall operation."
--  ::= { alteonAsfMIB 5 }

--	asfOperation        OBJECT-IDENTITY
--  STATUS              current
--  DESCRIPTION         "Objects under this branch provide general settings
--                       for operation."
--  ::= { alteonAsfMIB 6 }

--	asfAdministration   OBJECT-IDENTITY
--  STATUS              current
--  DESCRIPTION         "Objects under this branch provide general settings
--                       for ASF administration."
--  ::= { alteonAsfMIB 7 }

--	asfDiagnostics      OBJECT-IDENTITY
--  STATUS              current
--  DESCRIPTION         "Objects under this branch provide advanced settings
--                       for diagnosing ASF problems."
--  ::= { alteonAsfMIB 8 }

	asfStatistics       OBJECT-IDENTITY
    STATUS              current
    DESCRIPTION         "Objects under this branch provide statistics."
    ::= { alteonAsfMIB 9 }

-- Traps for ASF 

    asfNotifications OBJECT-IDENTITY
    STATUS           current
    DESCRIPTION      "This group lists various notifications sent by the
                      ASF system when it encounters defined exceptional
                      conditions."
    ::= { alteonAsfMIB 12 }

    asfEvents OBJECT-IDENTITY
    STATUS           current
    DESCRIPTION      "This group lists events generated by iSDs in the 
                      cluster."
    ::= { asfNotifications 1 }

    asfAlarms OBJECT-IDENTITY
    STATUS           current
    DESCRIPTION      "This group lists alarms generates by iSDs in the cluster.
                      An alarm is a special form of event which represents a
                      fault in the system that needs to be reported." 
    ::= { asfNotifications 2 }

    asfNotificationObjs  OBJECT-IDENTITY
    STATUS           current
    DESCRIPTION      "This branch consists of objects used to model traps sent 
                      to the management station."
    ::= { alteonAsfMIB 13 }

    deviceIpAddress  OBJECT-TYPE
    SYNTAX           IpAddress
    MAX-ACCESS       accessible-for-notify
    STATUS           current
    DESCRIPTION      "The IP address of the iSD/accelerator emitting the
                      notification."
    ::= { asfNotificationObjs 1 }

    deviceTimeStamp  OBJECT-TYPE
    SYNTAX           TimeStamp
    MAX-ACCESS       accessible-for-notify
    STATUS           current
    DESCRIPTION      "The value of the sysUpTime object (which defines when a 
                      specific occurrence happened)."
    ::= { asfNotificationObjs 2 }

    infoString       OBJECT-TYPE
    SYNTAX           DisplayString
    MAX-ACCESS       accessible-for-notify
    STATUS           current
    DESCRIPTION      "When applicable, a brief description about the 
                      notification."
    ::= { asfNotificationObjs 3 }

    memoryUsed       OBJECT-TYPE
    SYNTAX           Unsigned32
    MAX-ACCESS       accessible-for-notify
    STATUS           current
    DESCRIPTION      "The amount of disk space or memory consumed by the hard 
                      disk/RAM.  This value can be absolute or a percentage 
                      of total (determined by 'memoryUsageType').  If the 
                      memoryUsageType is 'absolute' (1) then the value of this 
                      object is defined by the unit specified by the 
                      memoryUsageUnit."
    ::= { asfNotificationObjs 4 }

    memoryUsageType  OBJECT-TYPE
    SYNTAX           INTEGER 
                     {
                          absolute (1),
                          percentage (2)
                     }
    MAX-ACCESS       accessible-for-notify
    STATUS           current
    DESCRIPTION      "The type of the value contained in 'memoryUsed' (which 
                      can be an 'absolute' value or a 'percentage' of the total 
                      value)."
    ::= { asfNotificationObjs 5 }

    memoryUsageUnit     OBJECT-TYPE
    SYNTAX           INTEGER 
                     {
                         kb (1),
                         mb (2),
                         gb (3),
                         none (4)
                     }
    MAX-ACCESS       accessible-for-notify
    STATUS           current
    DESCRIPTION      "The unit of measurement for the value contained in 
                      'memoryUsed'.  If the value of 'memoryUsageType' is
                      'absolute', then this object will have one of the first 
                      three values.  If the value of 'memoryUsageType' contains 
                      'percentage', then this object will have the value of 
                      'none'."
    ::= { asfNotificationObjs 6 }

    alarmSeverity     OBJECT-TYPE
    SYNTAX           INTEGER 
                     {
                         cleared       (1),
                         indeterminate (2),
                         critical      (3),
                         major         (4),
                         minor         (5),
                         warning       (6)
                     }
    MAX-ACCESS       accessible-for-notify
    STATUS           current
    DESCRIPTION      "These provide an indication of how the capability of the 
                      iSD/Switch has been affected.  These severity levels, 
                      which represent service affecting conditions, are ordered 
                      from most severe to least severe (ss defined in X.733 
                      standard)."
    ::= { asfNotificationObjs 7 }

    deviceMACAddress    OBJECT-TYPE
    SYNTAX            MacAddress 
    MAX-ACCESS       accessible-for-notify
    STATUS           current
    DESCRIPTION      "The MAC address of the iSD/switch emitting the 
                      notification."
    ::= { asfNotificationObjs 8 }

-- Trap Definitions 
    
    asfAcceleratorAddedTrap    NOTIFICATION-TYPE
    OBJECTS
    { 
        deviceMACAddress
    }
    STATUS         current
    DESCRIPTION    "Trap sent when an accelerator is added to the cluster."
    ::= { asfEvents 1 }

    asfAcceleratorRemovedTrap    NOTIFICATION-TYPE
    OBJECTS
    { 
        deviceMACAddress
    }
    STATUS         current
    DESCRIPTION    "Trap sent when an accelerator is removed from the cluster."
    ::= { asfEvents 2 }
    
    asfExtraAcceleratorDetected    NOTIFICATION-TYPE
    OBJECTS
    { 
        deviceMACAddress
    }
    STATUS         current
    DESCRIPTION    "Trap sent when an extra accelerator is detected in the
                    cluster.  This trap contains the MAC address of the extra 
                    accelerator." 
    ::= { asfEvents 3 }

    asfAcceleratorConnEstablished    NOTIFICATION-TYPE
    OBJECTS
    { 
        deviceMACAddress
    }
    STATUS         current
    DESCRIPTION    "Trap sent when a connection has been established with the 
                    accelerator.  This trap contains the MAC address of the 
                    accelerator." 
    ::= { asfEvents 4 }

    asfConfigUpdateSuccess    NOTIFICATION-TYPE
    OBJECTS
    { 
        deviceIpAddress,
        deviceMACAddress
    }
    STATUS         current
    DESCRIPTION   "Informative trap sent conveying that the configuration 
                   update request is successfully completed.  This trap sends 
                   the IP address and MAC address of the device whose update 
                   succeeded."
    ::= { asfEvents 8 }
 
    asfConfigUpdateFail    NOTIFICATION-TYPE
    OBJECTS
    { 
        deviceIpAddress,
        deviceMACAddress
    }
    STATUS         current
    DESCRIPTION   "Informative trap sent conveying that the configuration 
                   update request failed.  This trap sends the IP address and 
                   MAC address of the device whose update failed."
    ::= { asfEvents 9 }

    asfFirewallStarted    NOTIFICATION-TYPE
    OBJECTS
    {
        deviceIpAddress
    }
    STATUS         current
    DESCRIPTION    "Trap sent when the firewall has started running.  This trap 
                    contains the IP address of relevant iSD."
    ::= { asfEvents 10 }

-- ASF Alarm MIB definitions
	
    asfIsdFirewallFail    NOTIFICATION-TYPE
    OBJECTS
    { 
        deviceIpAddress
    }
    STATUS         current
    DESCRIPTION    "Trap sent when the firewall on one of the iSDs in the 
                    cluster is stopped.  This trap contains the IP address of 
                    the affected iSD."
    ::= { asfAlarms 1 }

    asfWebServerFail    NOTIFICATION-TYPE
    OBJECTS
    { 
        deviceIpAddress
    }
    STATUS         current
    DESCRIPTION    "Trap sent when webserver is stopped.  This trap contains 
                    the IP address of the affected iSD."
    ::= { asfAlarms 2 }

    asfWebServerStart    NOTIFICATION-TYPE
    OBJECTS
    { 
        deviceIpAddress
    }
    STATUS         current
    DESCRIPTION    "Trap sent when webserver is started after failing.  This 
					trap contains the IP address of the affected iSD."
    ::= { asfAlarms 3 }

    asfFileSystemWarning   NOTIFICATION-TYPE
    OBJECTS
    { 
        deviceIpAddress,
        infoString,
        memoryUsed
    }
    STATUS         current
    DESCRIPTION    "Trap sent when file system usage crosses 75% level.  For 
                    example, if level crosses 75% for 1 GB hard disk on iSD 
                    with IP address 123.45.67.89, then a trap is sent when 
                    usage of hard disk is reaches 750 MB.  The following 
                    objects will be in the trap: 123.45.67.89, bytes (used), 
                    bytes (available)."
    ::= { asfAlarms 5 }

    asfFileSystemCritical   NOTIFICATION-TYPE
    OBJECTS
    { 
        deviceIpAddress,
        infoString,
        memoryUsed
    }
    STATUS         current
    DESCRIPTION    "Trap sent when file system usage crosses 90% level.  For 
                    example, if level crosses 90% for 1 GB hard disk on iSD 
                    with IP address 123.45.67.89, then a trap is sent 
                    when usage of hard disk reaches 900 MB.  The following 
                    objects will be in the trap: 123.45.67.89, bytes (used), 
                    bytes (available)."
    ::= { asfAlarms 6 }

    asfMemoryWarning   NOTIFICATION-TYPE
    OBJECTS
    { 
        deviceIpAddress,
        memoryUsed
    }
    STATUS         current
    DESCRIPTION    "Trap sent when memory usage crosses 75% level.  The 
                    following objects will be in the trap: iSD IP address,
                    75% used, % memory available."
    ::= { asfAlarms 7 }

    asfMemoryCritical   NOTIFICATION-TYPE
    OBJECTS
    { 
        deviceIpAddress,
        memoryUsed
    }
    STATUS         current
    DESCRIPTION    "Trap sent when memory usage crosses 90% level.  The 
                   following objects will be in the trap: iSD IP address, 
                   90% used, % memory available."
    ::= { asfAlarms 8 }

    asfIsdStateDown    NOTIFICATION-TYPE
    OBJECTS
    { 
        deviceIpAddress
    }
    STATUS         current
    DESCRIPTION    "Trap sent when the iSD's state is down. This trap contains 
                    the IP address of the affected iSD." 
    ::= { asfAlarms 9 }

--  ASF Statistics MIB definitions.

--  Port Statistics

    asfPortStats        OBJECT-IDENTITY
    STATUS              current
    DESCRIPTION         "This group contains the byteCount and packet count
                         statistics per port."
    ::= { asfStatistics 1 }

    asfPortNetStatsTime OBJECT-TYPE
    SYNTAX              Integer32
                        MAX-ACCESS          read-only
    STATUS              current
    DESCRIPTION         "The current time at the accelerator."
    ::= { asfPortStats 1 }

    asfPortNetStatsTable OBJECT-TYPE
    SYNTAX              SEQUENCE OF ASFPORTNETSTATSEntry
    MAX-ACCESS          not-accessible
    STATUS              current
    DESCRIPTION         "Each row in the table gives the information about
                         an individual port."
    ::= { asfPortStats 2 }

    asfPortNetStatsEntry OBJECT-TYPE
    SYNTAX              ASFPORTNETSTATSEntry
    MAX-ACCESS          not-accessible
    STATUS              current
    DESCRIPTION         "The isd information about the row selected."
    INDEX               { asfPortCountIndex }
    ::= { asfPortNetStatsTable 1 }

    ASFPORTNETSTATSEntry    ::= SEQUENCE {
                            asfPortCountIndex          INTEGER,
                            asfPortInBytes             Counter64,
                            asfPortOutBytes            Counter64,
                            asfPortInPackets           Counter64,
                            asfPortOutPackets          Counter64,
                            asfPortInUcastPackets      Counter64,
                            asfPortOutUcastPackets     Counter64,
                            asfPortInBcastPackets      Counter64,
                            asfPortOutBcastPackets     Counter64,
                            asfPortInMcastPackets      Counter64,
                            asfPortOutMcastPackets     Counter64,
                            asfPortInDiscards     	   Counter64,
                            asfPortOutDiscards    	   Counter64,
                            asfPortInErrors    		   Counter64,
                            asfPortOutErrors    	   Counter64,
                            asfPortInUnknowns    	   Counter64
                            }

    asfPortCountIndex   OBJECT-TYPE
    SYNTAX              INTEGER (1..9)
                        MAX-ACCESS          read-only
    STATUS              current
    DESCRIPTION         "The index of the portStatsTable which specifies the
                         individual port."
    ::= { asfPortNetStatsEntry 1 }

    asfPortInBytes      OBJECT-TYPE
    SYNTAX              Counter64
                        MAX-ACCESS          read-only
    STATUS              current
    DESCRIPTION         "The number of bytes ingressing the port."
    ::= { asfPortNetStatsEntry 2 }

    asfPortOutBytes     OBJECT-TYPE
    SYNTAX              Counter64
                        MAX-ACCESS          read-only
    STATUS              current
    DESCRIPTION         "The number of bytes egressing the port."
    ::= { asfPortNetStatsEntry 3 }

    asfPortInPackets    OBJECT-TYPE
    SYNTAX              Counter64
                        MAX-ACCESS          read-only
    STATUS              current
    DESCRIPTION         "The number of packets ingressing the port.  This is
                         the sum of ingressing unicast, broadcast, multicast, 
                         discarded, unknown, and error packets."
    ::= { asfPortNetStatsEntry 4 }

    asfPortOutPackets   OBJECT-TYPE
    SYNTAX              Counter64
                        MAX-ACCESS          read-only
    STATUS              current
    DESCRIPTION         "The number of packets egressing the port.  This is 
                         the sum of egressing unicast, broadcast, multicast, 
                         discarded, and unknown packets."
    ::= { asfPortNetStatsEntry 5 }

    asfPortInUcastPackets  OBJECT-TYPE
    SYNTAX              Counter64
                        MAX-ACCESS          read-only
    STATUS              current
    DESCRIPTION         "The number of unicast packets ingressing the port."
    ::= { asfPortNetStatsEntry 6 }

    asfPortOutUcastPackets OBJECT-TYPE
    SYNTAX              Counter64
                        MAX-ACCESS          read-only
    STATUS              current
    DESCRIPTION         "The number of unicast packets egressing the port."
    ::= { asfPortNetStatsEntry 7 }

    asfPortInBcastPackets  OBJECT-TYPE
    SYNTAX              Counter64
                        MAX-ACCESS          read-only
    STATUS              current
    DESCRIPTION         "The number of broadcast packets ingressing the port."
    ::= { asfPortNetStatsEntry 8 }

    asfPortOutBcastPackets OBJECT-TYPE
    SYNTAX              Counter64
                        MAX-ACCESS          read-only
    STATUS              current
    DESCRIPTION         "The number of broadcast packets egressing the port."
    ::= { asfPortNetStatsEntry 9 }

    asfPortInMcastPackets  OBJECT-TYPE
    SYNTAX              Counter64
                        MAX-ACCESS          read-only
    STATUS              current
    DESCRIPTION         "The number of multicast packets ingressing the port."
    ::= { asfPortNetStatsEntry 10 }

    asfPortOutMcastPackets OBJECT-TYPE
    SYNTAX              Counter64
                        MAX-ACCESS          read-only
    STATUS              current
    DESCRIPTION         "The number of multicast packets egressing the port."
    ::= { asfPortNetStatsEntry 11 }

    asfPortInDiscards      OBJECT-TYPE
    SYNTAX              Counter64
                        MAX-ACCESS          read-only
    STATUS              current
    DESCRIPTION         "The number of ingressing packets discarded."
    ::= { asfPortNetStatsEntry 12 }

    asfPortOutDiscards     OBJECT-TYPE
    SYNTAX              Counter64
                        MAX-ACCESS          read-only
    STATUS              current
    DESCRIPTION         "The number of egressing packets discarded."
    ::= { asfPortNetStatsEntry 13 }

    asfPortInErrors        OBJECT-TYPE
    SYNTAX              Counter64
                        MAX-ACCESS          read-only
    STATUS              current
    DESCRIPTION         "The number of ingressing packets with errors."
    ::= { asfPortNetStatsEntry 14 }

    asfPortOutErrors       OBJECT-TYPE
    SYNTAX              Counter64
                        MAX-ACCESS          read-only
    STATUS              current
    DESCRIPTION         "The number of egressing packets with errors."
    ::= { asfPortNetStatsEntry 15 }

    asfPortInUnknowns      OBJECT-TYPE
    SYNTAX              Counter64
                        MAX-ACCESS          read-only
    STATUS              current
    DESCRIPTION         "The number of unknown ingressing packets."
    ::= { asfPortNetStatsEntry 16 }

--  iSD Statistics

    asfIsdStats         OBJECT-IDENTITY
    STATUS              current
    DESCRIPTION         "This group contains the session count statistics
                         per isd."
    ::= { asfStatistics 2 }

    asfIsdSessStatsTime OBJECT-TYPE
    SYNTAX              Integer32
                        MAX-ACCESS          read-only
    STATUS              current
    DESCRIPTION         "The current time at the accelerator."
    ::= { asfIsdStats 1 }

    asfIsdSessStatsTable OBJECT-TYPE
    SYNTAX              SEQUENCE OF ASFISDSESSSTATSEntry
    MAX-ACCESS          not-accessible
    STATUS              current
    DESCRIPTION         "Each row in the table gives the information about the
                         session count on  the isd which is per isd ."
    ::= { asfIsdStats 2 }

    asfIsdSessStatsEntry OBJECT-TYPE
    SYNTAX              ASFISDSESSSTATSEntry
    MAX-ACCESS          not-accessible
    STATUS              current
    DESCRIPTION         "The isd information about the row selected."
    INDEX               { asfIsdCountIndex }
    ::= { asfIsdSessStatsTable 1 }

    ASFISDSESSSTATSEntry ::= SEQUENCE {
                            asfIsdCountIndex           INTEGER,
                            asfIsdIPAddress            IpAddress,
                            asfNoOfSessions            Integer32
                            }

    asfIsdCountIndex    OBJECT-TYPE
    SYNTAX              INTEGER (1..6)
                        MAX-ACCESS          read-only
    STATUS              current
    DESCRIPTION         "The index of the isdStatsTable which specifies the
                         isd."
    ::= { asfIsdSessStatsEntry 1 }

    asfIsdIPAddress     OBJECT-TYPE
    SYNTAX              IpAddress
                        MAX-ACCESS          read-only
    STATUS              current
    DESCRIPTION         "The IP address of the isd."
    ::= { asfIsdSessStatsEntry 2 }

    asfNoOfSessions     OBJECT-TYPE
    SYNTAX              Integer32
                        MAX-ACCESS          read-only
    STATUS              current
    DESCRIPTION         "The number of sessions on this isd."
    ::= { asfIsdSessStatsEntry 3 }

-- **********************************

END
