NETGEAR-QOS-BW-MIB DEFINITIONS ::= BEGIN

-- NETGEAR Quality of Service Package MIB
-- Copyright LVL7 Systems (2001-2005) All rights reserved.

-- This SNMP Management Information Specification
-- embodies LVL7 System's confidential and proprietary
-- intellectual property.  LVL7 Systems retains all title
-- and ownership in the Specification including any revisions.

-- This Specification is supplied "AS IS", LVL7 Systems
-- makes no warranty, either expressed or implied,
-- as to the use, operation, condition, or performance of the
-- Specification.


IMPORTS
    Counter32, MODULE-IDENTITY, OBJECT-TYPE, NOTIFICATION-TYPE, Integer32, Gauge32        
                                        FROM SNMPv2-SMI
    RowStatus                           FROM SNMPv2-TC
    agentQOS                             FROM NETGEAR-QOS-MIB
    DisplayString                       FROM RFC1213-MIB;
                
    agentQOSBandwidth MODULE-IDENTITY
    LAST-UPDATED "200502231200Z" -- 23 Feb 2005 12:00:00 GMT
    ORGANIZATION "Netgear"
    CONTACT-INFO
       ""
        
    DESCRIPTION
       "The MIB definitaions for Quality of Service Flex package."
       
    -- revision history
    REVISION
       "200502231200Z" -- 23 Feb 2005 12:00:00 GMT
   	DESCRIPTION
       "Initial revision."
       
    ::= { agentQOS 1 }


    trafficClassGroup                  OBJECT IDENTIFIER ::= { agentQOSBandwidth 1 }
    
    trafficClassCreate OBJECT-TYPE
         SYNTAX      DisplayString (SIZE(1..15))
         MAX-ACCESS  read-write
         STATUS      current
         DESCRIPTION
                     "Set to a non-empty string to create a Traffic Class entry in
                     trafficClassTable."
         ::= { trafficClassGroup 1 }
         
    trafficClassTable OBJECT-TYPE
         SYNTAX      SEQUENCE OF TrafficClassEntry
         MAX-ACCESS  not-accessible
         STATUS      current
         DESCRIPTION 
                     "A table of Traffic Class instances."
         ::= { trafficClassGroup 2 }

    trafficClassEntry OBJECT-TYPE
         SYNTAX      TrafficClassEntry
         MAX-ACCESS  not-accessible
         STATUS      current
         DESCRIPTION 
                     ""
         INDEX       { trafficClassIndex }
         ::= { trafficClassTable 1 }
         
    TrafficClassEntry ::= SEQUENCE {         
           trafficClassIndex
               Integer32,
           trafficClassName
               DisplayString,
           trafficClassIfIndex
               Integer32,
           trafficClassVlanId
               Integer32,
           trafficClassWeight
               Integer32,
           trafficClassBandwidthAllocation
               Integer32,
           trafficClassAcceptByteCount
               Counter32,
           trafficClassStatus
               RowStatus
           }
    
    trafficClassIndex OBJECT-TYPE
         SYNTAX      Integer32
         MAX-ACCESS  not-accessible
         STATUS      current
         DESCRIPTION
                     "The index of this instance."
         ::= { trafficClassEntry 1 }

    trafficClassName OBJECT-TYPE
         SYNTAX      DisplayString (SIZE(1..15))
         MAX-ACCESS  read-only
         STATUS      current
         DESCRIPTION
                     "The name of the traffic class."
         ::= { trafficClassEntry 2 }

    trafficClassIfIndex OBJECT-TYPE
         SYNTAX      Integer32
         MAX-ACCESS  read-write
         STATUS      current
         DESCRIPTION
                     "The IfIndex of the port that this instance is associated with."
         ::= { trafficClassEntry 3 }
         
    trafficClassVlanId OBJECT-TYPE
         SYNTAX      Integer32
         MAX-ACCESS  read-write
         STATUS      current
         DESCRIPTION
                     "The VlanID of the VLAN that this instance is associated with."
         ::= { trafficClassEntry 4 }
         
    trafficClassWeight OBJECT-TYPE
         SYNTAX      Integer32 (1..1024)
         MAX-ACCESS  read-write
         STATUS      current
         DESCRIPTION
                     "The weight that this instances has."
         ::= { trafficClassEntry 5 }
         
    trafficClassBandwidthAllocation OBJECT-TYPE
         SYNTAX      Integer32
         MAX-ACCESS  read-write
         STATUS      current
         DESCRIPTION
                     "Index of Bandwidth Allocation entry this traffic class uses."
         ::= { trafficClassEntry 6 }

    trafficClassAcceptByteCount OBJECT-TYPE
         SYNTAX      Counter32
         MAX-ACCESS  read-only
         STATUS      current
         DESCRIPTION
                     "Byte count of packets accepted by this traffic class."
         ::= { trafficClassEntry 7 }
         
    trafficClassStatus OBJECT-TYPE
         SYNTAX      RowStatus
         MAX-ACCESS  read-write
         STATUS      current
         DESCRIPTION
                     "Status of this instance.
                     
                     active(1)    - this traffic class is active
                     destroy(6)   - set to this value to delete an instance"
         ::= { trafficClassEntry 8 }


    bandwidthAllocationGroup                  OBJECT IDENTIFIER ::= { agentQOSBandwidth 2 }
    
    bandwidthAllocationCreate OBJECT-TYPE
         SYNTAX      DisplayString (SIZE(1..15))
         MAX-ACCESS  read-write
         STATUS      current
         DESCRIPTION
                     "Set to a non-empty string to create a Bandwidth 
                     Allocation entry in bandwidthAllocationTable."
         ::= { bandwidthAllocationGroup 1 }
         
    
    bandwidthAllocationTable OBJECT-TYPE
         SYNTAX      SEQUENCE OF BandwidthAllocationEntry
         MAX-ACCESS  not-accessible
         STATUS      current
         DESCRIPTION 
                     "Table of bandwidth allocation instances."
         ::= { bandwidthAllocationGroup 2 }

    bandwidthAllocationEntry OBJECT-TYPE
         SYNTAX      BandwidthAllocationEntry
         MAX-ACCESS  not-accessible
         STATUS      current
         DESCRIPTION 
                     ""
         INDEX       { bandwidthAllocationIndex }
         ::= { bandwidthAllocationTable 1 }
         
    BandwidthAllocationEntry ::= SEQUENCE {         
           bandwidthAllocationIndex
               Integer32,
           bandwidthAllocationName
               DisplayString,
           bandwidthAllocationMinBandwidth
               Gauge32,
           bandwidthAllocationMaxBandwidth
               Gauge32,
           bandwidthAllocationStatus
               RowStatus
           }
    
    bandwidthAllocationIndex OBJECT-TYPE
         SYNTAX      Integer32
         MAX-ACCESS  not-accessible
         STATUS      current
         DESCRIPTION
                     "The index of the traffic class."
         ::= { bandwidthAllocationEntry 1 }

    bandwidthAllocationName OBJECT-TYPE
         SYNTAX      DisplayString (SIZE(1..15))
         MAX-ACCESS  read-only
         STATUS      current
         DESCRIPTION
                     "The name of the traffic class."
         ::= { bandwidthAllocationEntry 2 }

    bandwidthAllocationMinBandwidth OBJECT-TYPE
         SYNTAX      Gauge32
         MAX-ACCESS  read-write
         STATUS      current
         DESCRIPTION
                     "Minimum bandwidth allocated."
         ::= { bandwidthAllocationEntry 3 }
         
    bandwidthAllocationMaxBandwidth OBJECT-TYPE
         SYNTAX      Gauge32
         MAX-ACCESS  read-write
         STATUS      current
         DESCRIPTION
                     "Maximum bandwidth allocated."
         ::= { bandwidthAllocationEntry 4 }
         
    bandwidthAllocationStatus OBJECT-TYPE
         SYNTAX      RowStatus
         MAX-ACCESS  read-write
         STATUS      current
         DESCRIPTION
                     "Status of this instance.
                     
                     active(1)    - this bandwidth allocation is active
                     destroy(6)   - set to this value to delete an instance"
         ::= { bandwidthAllocationEntry 5 }
         
END
