-- ****************************************************************************
--
--                       HP Remote Assistant
--      Management Information Base for SNMP Network Management
--
--      Version A.01.01 (10/1/94)
-- 
--      Copyright 1994 Hewlett-Packard Company.
--      All Rights Reserved.
--
--      The information in this document is subject to change without notice.
--
--      The HP Enterprise number is 11.
--      The ASN.1 prefix to, and including the HP Enterprise is:
--      1.3.6.1.4.1.11
--
-- ****************************************************************************
-- Summary of HP Remote Assistant Information MIB
-- ****************************************************************************
--
-- hp  (1.3.6.1.4.1.11)
--    nm  (1.3.6.1.4.1.11.2)
--       hpnsa  (1.3.6.1.4.1.11.2.23)
--          hpnsaRemoteAssist Group  (hpnsa.8)
--
--             hpnsaRAMibRev Group    (hpnsa.8.1)             
--                hpnsaRAMibRevMajor  (hpnsa.8.1.1)  
--                hpnsaRAMibRevMinor  (hpnsa.8.1.2)
--
--             hpnsaRAAgent Group            (hpnsa.8.2)
--                hpnsaRAAgentTable          (hpnsa.8.2.1)
--                   hpnsaRAAgentEntry       (hpnsa.8.2.1.1)
--                      hpnsaRAAgentIndex    (hpnsa.8.2.1.1.1)
--                      hpnsaRAAgentName     (hpnsa.8.2.1.1.2)
--                      hpnsaRAAgentVersion  (hpnsa.8.2.1.1.3)
--                      hpnsaRAAgentDate     (hpnsa.8.2.1.1.4)
--
--             hpnsaRAInfo Group             (hpnsa.8.3)
--                hpnsaRAInfoBoardType       (hpnsa.8.3.1)
--                hpnsaRAInfoBoardName       (hpnsa.8.3.2)
--                hpnsaRAInfoBoardID         (hpnsa.8.3.3)
--                hpnsaRAInfoBoardVersion    (hpnsa.8.3.4)
--
--             hpnsaRATemp Group             (hpnsa.8.4)
--                hpnsaRATempMeasured        (hpnsa.8.4.1)
--                hpnsaRATempWarnLimit       (hpnsa.8.4.2)
--                hpnsaRATempGracefulSDLimit (hpnsa.8.4.3)
--                hpnsaRATempCriticalSDLimit (hpnsa.8.4.4)
--
--             hpnsaRAVolt Group             (hpnsa.8.5)
--                hpnsaRAVoltTable           (hpnsa.8.5.1)
--                   hpnsaRAVoltEntry        (hpnsa.8.5.1.1)
--                      hpnsaRAVoltTypeIndex (hpnsa.8.5.1.1.1)
--                      hpnsaRAVoltMeasured  (hpnsa.8.5.1.1.2)
--                      hpnsaRAVoltLoLimit   (hpnsa.8.5.1.1.3)
--                      hpnsaRAVoltHiLimit   (hpnsa.8.5.1.1.4)
--
--             hpnsaRABusUsage Group         (hpnsa.8.6)
--                hpnsaRABusUsage5SecAve     (hpnsa.8.6.1)
--                hpnsaRABusUsage15SecAve    (hpnsa.8.6.2)
--                hpnsaRABusUsage1MinAve     (hpnsa.8.6.3)
--                hpnsaRABusUsage5MinAve     (hpnsa.8.6.4)
--                hpnsaRABusUsageLimit       (hpnsa.8.6.5)
--
--             hpnsaRALog Group              (hpnsa.8.7)
--                hpnsaRALogTable            (hpnsa.8.7.1)
--                   hpnsaRALogEntry         (hpnsa.8.7.1.1)
--                      hpnsaRALogIndex      (hpnsa.8.7.1.1.1)
--                      hpnsaRALogEventCode  (hpnsa.8.7.1.1.2)
--                      hpnsaRALogDescription(hpnsa.8.7.1.1.3)
--                      hpnsaRALogViewed     (hpnsa.8.7.1.1.4)
--                      hpnsaRALogDateTime   (hpnsa.8.7.1.1.5)
--                      hpnsaRALogData       (hpnsa.8.7.1.1.6)
--
--             hpnsaRAEventConfig Group  (hpnsa.8.8)
--                hpnsaRAEventConfigGlobal   (hpnsa.8.8.1)
--                hpnsaRAEventConfigVolt     (hpnsa.8.8.2)
--                hpnsaRAEventConfigTemp     (hpnsa.8.8.3)
--                hpnsaRAEventConfigAsr      (hpnsa.8.8.4)
--                hpnsaRAEventConfigRemBoot  (hpnsa.8.8.5)
--                hpnsaRAEventConfigBusUsage (hpnsa.8.8.6)
--                hpnsaRAEventConfigRemAsst  (hpnsa.8.8.7)
--                hpnsaRAEventConfigTrapTest (hpnsa.8.8.8)
--                hpnsaRAEventConfigHostSys  (hpnsa.8.8.9)
--
-- Note: Remote Assistant has been abbreviated to the letters "RA"
--       to make the names more readable.
--
-- ******************************************************************************

HPNSAREMOTEASSIST-MIB DEFINITIONS ::= BEGIN
   IMPORTS
      enterprises    FROM RFC1155-SMI
      Counter        FROM RFC1155-SMI
      DisplayString  FROM RFC1213-MIB
      OBJECT-TYPE    FROM RFC-1212
      TRAP-TYPE      FROM RFC-1215;

   hp                OBJECT IDENTIFIER ::= { enterprises 11 }
   nm                OBJECT IDENTIFIER ::= { hp 2 }
   hpnsa             OBJECT IDENTIFIER ::= { nm 23 }  
   hpnsaRemoteAssist OBJECT IDENTIFIER ::= { hpnsa 8 }
   hpnsaRAMibRev     OBJECT IDENTIFIER ::= { hpnsaRemoteAssist 1 }
   hpnsaRAAgent      OBJECT IDENTIFIER ::= { hpnsaRemoteAssist 2 }      
   hpnsaRAInfo       OBJECT IDENTIFIER ::= { hpnsaRemoteAssist 3 }
   hpnsaRATemp       OBJECT IDENTIFIER ::= { hpnsaRemoteAssist 4 }
   hpnsaRAVolt       OBJECT IDENTIFIER ::= { hpnsaRemoteAssist 5 }
   hpnsaRABusUsage   OBJECT IDENTIFIER ::= { hpnsaRemoteAssist 6 }
   hpnsaRALog        OBJECT IDENTIFIER ::= { hpnsaRemoteAssist 7 }
   hpnsaRAEventConfig OBJECT IDENTIFIER ::= { hpnsaRemoteAssist 8 }
   
   

-- ****************************************************************************
--   HP Remote Assistant Information MIB 
--   ===================================
--
-- hp  (1.3.6.1.4.1.11)
--    nm  (1.3.6.1.4.1.11.2)
--       hpnsa  (1.3.6.1.4.1.11.2.23)
--          hpnsaRemoteAssist Group  (hpnsa.8)
--             hpnsaRAMibRev Group    (hpnsa.8.1)             
--                hpnsaRAMibRevMajor  (hpnsa.8.1.1)  
--                hpnsaRAMibRevMinor  (hpnsa.8.1.2)
--
--    Implementation of the MibRev group is mandatory for all HPNSA Agents
--    supporting the HP Remote Assistant MIB.
--
--    An HPNSA Agent conforming to this document will return a
--    hpnsaRAMibRevMajor of 1 and a hpnsaRAMibRevMinor of 0. 
--
-- ****************************************************************************

   hpnsaRAMibRevMajor OBJECT-TYPE
      SYNTAX  INTEGER (1..65535)
      ACCESS  read-only
      STATUS  mandatory
      DESCRIPTION
         "The major revision level of the MIB."
      ::= { hpnsaRAMibRev 1 }

   hpnsaRAMibRevMinor OBJECT-TYPE
      SYNTAX  INTEGER (0..65535)
      ACCESS  read-only
      STATUS  mandatory
      DESCRIPTION
          "The minor revision level of the MIB."
      ::= { hpnsaRAMibRev 2 }

  
-- ****************************************************************************
--   HP Remote Assistant MIB Agent Information
--   =========================================
--
-- hp  (1.3.6.1.4.1.11)
--    nm  (1.3.6.1.4.1.11.2)
--       hpnsa  (1.3.6.1.4.1.11.2.23)
--          hpnsaRemoteAssist Group  (hpnsa.8)
--             hpnsaRAAgent Group  (hpnsa.8.2)
--
--                hpnsaRAAgentTable          (hpnsa.8.2.1)
--                   hpnsaRAAgentEntry       (hpnsa.8.2.1.1)
--                      hpnsaRAAgentIndex    (hpnsa.8.2.1.1.1)
--                      hpnsaRAAgentName     (hpnsa.8.2.1.1.2)
--                      hpnsaRAAgentVersion  (hpnsa.8.2.1.1.3)
--                      hpnsaRAAgentDate     (hpnsa.8.2.1.1.4)
--
--  Implementation of the hpnsaRAAgent group is mandatory for all
--  HPNSA Agents that support the Remote Assistant MIB.
--
-- ****************************************************************************
--   HP Remote Assistant Agent Module Table
-- ****************************************************************************

   hpnsaRAAgentTable OBJECT-TYPE
      SYNTAX  SEQUENCE OF HPnsaRAAgentEntry
      ACCESS  not-accessible
      STATUS  mandatory
      DESCRIPTION
         "A table of SNMP agents that satisfy requests for this MIB."
      ::= { hpnsaRAAgent 1 }

   hpnsaRAAgentEntry OBJECT-TYPE
      SYNTAX  HPnsaRAAgentEntry
      ACCESS  not-accessible
      STATUS  mandatory
      DESCRIPTION
      	"A description of the agents that access related information
         in HP Remote Assistant."
      INDEX   { hpnsaRAAgentIndex }
      ::= { hpnsaRAAgentTable 1 }
	
      HPnsaRAAgentEntry ::= SEQUENCE {
   	 hpnsaRAAgentIndex       INTEGER,
   	 hpnsaRAAgentName        DisplayString,
   	 hpnsaRAAgentVersion     DisplayString,
   	 hpnsaRAAgentDate        OCTET STRING
      }

   hpnsaRAAgentIndex OBJECT-TYPE
      SYNTAX  INTEGER (0..255)
      ACCESS  read-only
      STATUS  mandatory
      DESCRIPTION
         "A unique index for this module description."
      ::= { hpnsaRAAgentEntry 1 }

   hpnsaRAAgentName OBJECT-TYPE
      SYNTAX  DisplayString (SIZE (0..255))
      ACCESS  read-only
      STATUS  mandatory
      DESCRIPTION
         "Name of the agent/agents satisfying SNMP requests for this MIB."
      ::= { hpnsaRAAgentEntry 2 }

   hpnsaRAAgentVersion OBJECT-TYPE
      SYNTAX  DisplayString (SIZE (0..5))
      ACCESS  read-only
      STATUS  mandatory
      DESCRIPTION
         "Version number of the agent/agents satisfying SNMP requests for
      	 this MIB."
      ::= { hpnsaRAAgentEntry 3 }

   hpnsaRAAgentDate OBJECT-TYPE
      SYNTAX  OCTET STRING (SIZE (6))
      ACCESS  read-only
      STATUS  mandatory
      DESCRIPTION
         "The date on which this agent was created.

	 field  octets  contents                  range
	 -------------------------------------------------
	   1       1    years since 1900          0..255
	   2       2    month                     1..12
	   3       3    day                       1..31
	   4       4    hour                      0..23
	   5       5    minute                    0..59  
	   6       6    second                    0..59
			 "
      ::= { hpnsaRAAgentEntry 4 }


-- *************************************************************************************
-- hp  (1.3.6.1.4.1.11)
--    nm  (1.3.6.1.4.1.11.2)
--       hpnsa  (1.3.6.1.4.1.11.2.23)
--          hpnsaRemoteAssist Group  (hpnsa.8)
--             hpnsaRAInfo Group  (hpnsa.8.3)
--
--                hpnsaRAInfoBoardType                  (hpnsa.8.3.1)
--                hpnsaRAInfoBoardName                  (hpnsa.8.3.2)
--                hpnsaRAInfoBoardID                    (hpnsa.8.3.3)
--                hpnsaRAInfoBoardVersion               (hpnsa.8.3.4)
-- ****************************************************************************************
--   HP Remote Assistant Information Table
-- ****************************************************************************

   hpnsaRAInfoBoardType OBJECT-TYPE
      SYNTAX DisplayString (SIZE (0..80))
      ACCESS read-only
      STATUS mandatory
      DESCRIPTION
         "A description of the type of HP Remote Assistant board."
      ::= {hpnsaRAInfo 1}

   hpnsaRAInfoBoardName OBJECT-TYPE
      SYNTAX DisplayString (SIZE (0..20))
      ACCESS read-only
      STATUS mandatory
      DESCRIPTION
         "The server name configured on the HP Remote Assistant
          board."
      ::= {hpnsaRAInfo 2}

   hpnsaRAInfoBoardID OBJECT-TYPE
      SYNTAX INTEGER
      ACCESS read-only
      STATUS mandatory
      DESCRIPTION
         "The server ID configured on the HP Remote Assistant
          board."
      ::= {hpnsaRAInfo 3}

   hpnsaRAInfoBoardVersion OBJECT-TYPE
      SYNTAX  DisplayString (SIZE (0..5))
      ACCESS read-only
      STATUS mandatory
      DESCRIPTION
         "The HP Remote Assistant firmware version."
      ::= {hpnsaRAInfo 4}


-- *************************************************************************************
-- hp  (1.3.6.1.4.1.11)
--    nm  (1.3.6.1.4.1.11.2)
--       hpnsa  (1.3.6.1.4.1.11.2.23)
--          hpnsaRemoteAssist Group  (hpnsa.8)
--             hpnsaRATemp Group  (hpnsa.8.4)
--
--                hpnsaRATempMeasured           (hpnsa.8.4.1)
--                hpnsaRATempWarnLimit          (hpnsa.8.4.2)
--                hpnsaRATempGracefulSDLimit    (hpnsa.8.4.3)
--                hpnsaRATempCriticalSDLimit    (hpnsa.8.4.4)
-- ****************************************************************************************
--   HP Remote Assistant Temperature
-- ****************************************************************************

   hpnsaRATempMeasured OBJECT-TYPE
      SYNTAX INTEGER
      ACCESS read-only
      STATUS mandatory
      DESCRIPTION
         "Current temperature in degrees Celsius as measured by
          the HP Remote Assistant on-board sensor."
      ::= {hpnsaRATemp 1}

   hpnsaRATempWarnLimit OBJECT-TYPE
      SYNTAX INTEGER
      ACCESS read-only
      STATUS mandatory
      DESCRIPTION
         "Temperature warning threshold value in degrees Celsius
          for the HP Remote Assistant on-board sensor."
      ::= {hpnsaRATemp 2}

   hpnsaRATempGracefulSDLimit OBJECT-TYPE
      SYNTAX INTEGER
      ACCESS read-only
      STATUS mandatory
      DESCRIPTION
         "Graceful shutdown temperature threshold value in degrees
	  Celsius for the HP Remote Assistant on-board sensor."
      ::= {hpnsaRATemp 3}

   hpnsaRATempCriticalSDLimit OBJECT-TYPE
      SYNTAX INTEGER
      ACCESS read-only
      STATUS mandatory
      DESCRIPTION
         "Critical shutdown temperature threshold value in degrees
          Celsius for the HP Remote Assistant on-board sensor."
      ::= {hpnsaRATemp 4}


-- *****************************************************************************
-- hp  (1.3.6.1.4.1.11)
--    nm  (1.3.6.1.4.1.11.2)
--       hpnsa  (1.3.6.1.4.1.11.2.23)
--          hpnsaRemoteAssist Group  (hpnsa.8)
--             hpnsaRAVolt Group  (hpnsa.8.5)
--
--                hpnsaRAVoltTable                    (hpnsa.8.5.1)
--                   hpnsaRAVoltEntry                 (hpnsa.8.5.1.1)
--                      hpnsaRAVoltTypeIndex          (hpnsa.8.5.1.1.1)
--                      hpnsaRAVoltMeasured           (hpnsa.8.5.1.1.2)
--                      hpnsaRAVoltLoLimit            (hpnsa.8.5.1.1.3)
--                      hpnsaRAVoltHiLimit            (hpnsa.8.5.1.1.4)
-- ****************************************************************************************
--   HP Remote Assistant Voltage Table
-- ****************************************************************************

   hpnsaRAVoltTable OBJECT-TYPE
      SYNTAX  SEQUENCE OF HpnsaRAVoltEntry
      ACCESS  not-accessible
      STATUS  mandatory
      DESCRIPTION
         "A table of HP Remote Assistant voltage entries."
      ::= { hpnsaRAVolt 1 }

   hpnsaRAVoltEntry OBJECT-TYPE
      SYNTAX  HpnsaRAVoltEntry
      ACCESS  not-accessible
      STATUS  mandatory
      DESCRIPTION
         "HP Remote Assistant voltage information."
      INDEX   { hpnsaRAVoltTypeIndex }
      ::= { hpnsaRAVoltTable 1 }

   HpnsaRAVoltEntry ::= SEQUENCE {
      hpnsaRAVoltTypeIndex       INTEGER,  
      hpnsaRAVoltMeasured        INTEGER,   
      hpnsaRAVoltLoLimit         INTEGER,   
      hpnsaRAVoltHiLimit         INTEGER
      }

   hpnsaRAVoltTypeIndex OBJECT-TYPE
      SYNTAX  INTEGER {
         negative12v(1),
         positive12v(2),
         positive5v(3),
         positive3v(4)
         }
      ACCESS  read-only
      STATUS  mandatory
      DESCRIPTION
         "A unique index for each voltage level."
      ::= { hpnsaRAVoltEntry 1 }

   hpnsaRAVoltMeasured OBJECT-TYPE
      SYNTAX  DisplayString
      ACCESS  read-only
      STATUS  mandatory
      DESCRIPTION
         "The measured value for the particular voltage level in volts."
      ::= { hpnsaRAVoltEntry 2 }

   hpnsaRAVoltLoLimit OBJECT-TYPE
      SYNTAX  DisplayString
      ACCESS  read-only
      STATUS  mandatory
      DESCRIPTION
         "The low threshold value in volts at which HP Remote Assistant
          pages the configured administrator."
      ::= { hpnsaRAVoltEntry 3 }

   hpnsaRAVoltHiLimit OBJECT-TYPE
      SYNTAX  DisplayString
      ACCESS  read-only
      STATUS  mandatory
      DESCRIPTION
         "The high threshold value in volts at which HP Remote Assistant
          pages the configured administrator."
      ::= { hpnsaRAVoltEntry 4 }


-- *************************************************************************************
-- hp  (1.3.6.1.4.1.11)
--    nm  (1.3.6.1.4.1.11.2)
--       hpnsa  (1.3.6.1.4.1.11.2.23)
--          hpnsaRemoteAssist Group  (hpnsa.8)
--             hpnsaRABusUsage Group  (hpnsa.8.6)
--
--                hpnsaRABusUsage5SecAve     (hpnsa.8.6.1)
--                hpnsaRABusUsage15SecAve    (hpnsa.8.6.2)
--                hpnsaRABusUsage1MinAve     (hpnsa.8.6.3)
--                hpnsaRABusUsage5MinAve     (hpnsa.8.6.4)
--                hpnsaRABusUsageLimit       (hpnsa.8.6.5)
-- ****************************************************************************************
--   HP Remote Assistant Bus Utilization
-- ****************************************************************************

   hpnsaRABusUsage5SecAve OBJECT-TYPE
      SYNTAX INTEGER
      ACCESS read-only
      STATUS mandatory
      DESCRIPTION
         "The EISA bus utilization averaged over the last 5 seconds."
      ::= {hpnsaRABusUsage 1}

   hpnsaRABusUsage15SecAve OBJECT-TYPE
      SYNTAX INTEGER
      ACCESS read-only
      STATUS mandatory
      DESCRIPTION
         "The EISA bus utilization averaged over the last 15 seconds."
      ::= {hpnsaRABusUsage 2}

   hpnsaRABusUsage1MinAve OBJECT-TYPE
      SYNTAX INTEGER
      ACCESS read-only
      STATUS mandatory
      DESCRIPTION
         "The EISA bus utilization averaged over the last minute."
      ::= {hpnsaRABusUsage 3}

   hpnsaRABusUsage5MinAve OBJECT-TYPE
      SYNTAX INTEGER
      ACCESS read-only
      STATUS mandatory
      DESCRIPTION
         "The EISA bus utilization averaged over the last 5 minutes."
      ::= {hpnsaRABusUsage 4}
      
   hpnsaRABusUsageLimit OBJECT-TYPE
      SYNTAX INTEGER
      ACCESS read-only
      STATUS mandatory
      DESCRIPTION
         "The EISA bus utilization threshold value at which HP Remote
          Assistant pages the configured administrator. HP Remote
          Assistant compares this threshold with the 5 minute average."
      ::= {hpnsaRABusUsage 5}
      
      
-- *****************************************************************************
-- hp  (1.3.6.1.4.1.11)
--    nm  (1.3.6.1.4.1.11.2)
--       hpnsa  (1.3.6.1.4.1.11.2.23)
--          hpnsaRemoteAssist Group  (hpnsa.8)
--             hpnsaRALog Group  (hpnsa.8.7)
--
--                hpnsaRALogTable               (hpnsa.8.7.1)
--                   hpnsaRALogEntry            (hpnsa.8.7.1.1)
--                      hpnsaRALogIndex         (hpnsa.8.7.1.1.1)
--                      hpnsaRALogEventCode     (hpnsa.8.7.1.1.2)
--                      hpnsaRALogDescription   (hpnsa.8.7.1.1.3)
--                      hpnsaRALogViewed        (hpnsa.8.7.1.1.4)
--                      hpnsaRALogDateTime      (hpnsa.8.7.1.1.5)
--                      hpnsaRALogData          (hpnsa.8.7.1.1.6)
-- ****************************************************************************************
--   HP Remote Assistant Log Table
-- ****************************************************************************

   hpnsaRALogTable OBJECT-TYPE
      SYNTAX  SEQUENCE OF HpnsaRALogEntry
      ACCESS  not-accessible
      STATUS  mandatory
      DESCRIPTION
         "A table of HP Remote Assistant log entries."
      ::= { hpnsaRALog 1 }

   hpnsaRALogEntry OBJECT-TYPE
      SYNTAX  HpnsaRALogEntry
      ACCESS  not-accessible
      STATUS  mandatory
      DESCRIPTION
         "HP Remote Assistant log information."
      INDEX   { hpnsaRALogIndex }
      ::= { hpnsaRALogTable 1 }

   HpnsaRALogEntry ::= SEQUENCE {
      hpnsaRALogIndex       INTEGER,  
      hpnsaRALogEventCode   INTEGER,  
      hpnsaRALogDescription OCTET STRING,  
      hpnsaRALogViewed      INTEGER,
      hpnsaRALogDateTime    OCTET STRING,  
      hpnsaRALogData        INTEGER  
      }

   hpnsaRALogIndex OBJECT-TYPE
      SYNTAX  INTEGER
      ACCESS  read-only
      STATUS  mandatory
      DESCRIPTION
         "A unique index for each log entry."
      ::= { hpnsaRALogEntry 1 }

   hpnsaRALogEventCode OBJECT-TYPE
      SYNTAX  INTEGER
      ACCESS  read-only
      STATUS  mandatory
      DESCRIPTION
         "The code for the logged event. Refer to the HP Remote
          Assistant User's Manual for event code descriptions."
      ::= { hpnsaRALogEntry 2 }

   hpnsaRALogDescription OBJECT-TYPE
      SYNTAX  DisplayString (SIZE (0..255))
      ACCESS  read-only
      STATUS  mandatory
      DESCRIPTION
         "A description of the logged event."
      ::= { hpnsaRALogEntry 3 }

   hpnsaRALogViewed OBJECT-TYPE
      SYNTAX  INTEGER {
         new(0),
         viewed(1)
         }
      ACCESS read-only
      STATUS mandatory
      DESCRIPTION
         "Indicates whether this log entry is new or has been
          previously viewed."
      ::= {hpnsaRALogEntry 4}

   hpnsaRALogDateTime OBJECT-TYPE
      SYNTAX  OCTET STRING (SIZE (6))
      ACCESS  read-only
      STATUS  mandatory
      DESCRIPTION
         "The date on which the event occured.

	   octets  contents                  range
	 --------------------------------------------
	      1    years since 1900          0..255
	      2    month                     1..12
	      3    day                       1..31
	      4    hour                      0..23
	      5    minute                    0..59  
	      6    second                    0..59
			 "
      ::= { hpnsaRALogEntry 5 }

   hpnsaRALogData OBJECT-TYPE
      SYNTAX  INTEGER
      ACCESS  read-only
      STATUS  mandatory
      DESCRIPTION
         "The data associated with the logged event."
      ::= { hpnsaRALogEntry 6 }

-- *************************************************************************************
-- hp  (1.3.6.1.4.1.11)
--    nm  (1.3.6.1.4.1.11.2)
--       hpnsa  (1.3.6.1.4.1.11.2.23)
--          hpnsaRemoteAssist Group  (hpnsa.8)
--             hpnsaRAEventConfig Group  (hpnsa.8.8)
--
--                hpnsaRAEventConfigGlobal   (hpnsa.8.8.1)
--                hpnsaRAEventConfigVolt     (hpnsa.8.8.2)
--                hpnsaRAEventConfigTemp     (hpnsa.8.8.3)
--                hpnsaRAEventConfigAsr      (hpnsa.8.8.4)
--                hpnsaRAEventConfigRemBoot  (hpnsa.8.8.5)
--                hpnsaRAEventConfigBusUsage (hpnsa.8.8.6)
--                hpnsaRAEventConfigRemAsst  (hpnsa.8.8.7)
--                hpnsaRAEventConfigTrapTest (hpnsa.8.8.8)
--                hpnsaRAEventConfigHostSys  (hpnsa.8.8.9)
-- ****************************************************************************************
--   HP Remote Assistant In-band Event Configuration
-- ****************************************************************************

   hpnsaRAEventConfigGlobal OBJECT-TYPE
      SYNTAX  INTEGER {
         disabled(0),
         enabled(1)
         }
      ACCESS read-write
      STATUS mandatory
      DESCRIPTION
         "Control for the HP Remote Assistant in-band traps. This is
          a global value that overrides all of the controls in this
          group. A value of 1 means all traps enabled; 0 means
          disabled."
      ::= {hpnsaRAEventConfig 1}

   hpnsaRAEventConfigVolt OBJECT-TYPE
      SYNTAX  INTEGER {
         disabled(0),
         enabled(1)
         }
      ACCESS read-write
      STATUS mandatory
      DESCRIPTION
         "Control for the HP Remote Assistant in-band voltage
          traps. A value of 1 means voltage traps enabled;
          0 means disabled."
      ::= {hpnsaRAEventConfig 2}

   hpnsaRAEventConfigTemp OBJECT-TYPE
      SYNTAX  INTEGER {
         disabled(0),
         enabled(1)
         }
      ACCESS read-write
      STATUS mandatory
      DESCRIPTION
         "Control for the HP Remote Assistant in-band temperature
          traps. A value of 1 means temperature traps enabled;
          0 means disabled."
      ::= {hpnsaRAEventConfig 3}

   hpnsaRAEventConfigAsr OBJECT-TYPE
      SYNTAX  INTEGER {
         disabled(0),
         enabled(1)
         }
      ACCESS read-write
      STATUS mandatory
      DESCRIPTION
         "Control for the HP Remote Assistant in-band ASR traps.
          A value of 1 means ASR traps enabled; 0 means disabled."
      ::= {hpnsaRAEventConfig 4}

   hpnsaRAEventConfigRemBoot OBJECT-TYPE
      SYNTAX  INTEGER {
         disabled(0),
         enabled(1)
         }
      ACCESS read-write
      STATUS mandatory
      DESCRIPTION
         "Control for the HP Remote Assistant in-band remote boot
          traps. A value of 1 means remote boot traps enabled;
          0 means disabled."
      ::= {hpnsaRAEventConfig 5}

   hpnsaRAEventConfigBusUsage OBJECT-TYPE
      SYNTAX  INTEGER {
         disabled(0),
         enabled(1)
         }
      ACCESS read-write
      STATUS mandatory
      DESCRIPTION
         "Control for the HP Remote Assistant in-band EISA bus
          utilization traps. A value of 1 means bus utilization
          traps enabled; 0 means disabled."
      ::= {hpnsaRAEventConfig 6}

   hpnsaRAEventConfigRemAsst OBJECT-TYPE
      SYNTAX  INTEGER {
         disabled(0),
         enabled(1)
         }
      ACCESS read-write
      STATUS mandatory
      DESCRIPTION
         "Control for the other HP Remote Assistant in-band traps.
          A value of 1 means traps enabled; 0 means disabled."
      ::= {hpnsaRAEventConfig 7}

   hpnsaRAEventConfigTrapTest OBJECT-TYPE
      SYNTAX  INTEGER {
         disabled(0),
         enabled(1)
         }
      ACCESS read-write
      STATUS mandatory
      DESCRIPTION
         "Control for the HP Remote Assistant in-band test
          trap. A value of 1 means test trap enabled; 0 means
          disabled."
      ::= {hpnsaRAEventConfig 8}

   hpnsaRAEventConfigHostSys OBJECT-TYPE
      SYNTAX  INTEGER {
         disabled(0),
         enabled(1)
         }
      ACCESS read-write
      STATUS mandatory
      DESCRIPTION
         "Control for the HP Remote Assistant in-band host system
          traps. A value of 1 means host system traps enabled;
          0 means disabled."
      ::= {hpnsaRAEventConfig 9}


END
