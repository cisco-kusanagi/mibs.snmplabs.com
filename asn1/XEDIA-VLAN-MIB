XEDIA-VLAN-MIB DEFINITIONS ::= BEGIN

IMPORTS
    MODULE-IDENTITY, OBJECT-TYPE, Gauge32
        FROM SNMPv2-SMI
    MODULE-COMPLIANCE, OBJECT-GROUP
        FROM SNMPv2-CONF
    TruthValue, TimeInterval
        FROM SNMPv2-TC
    xediaMibs
        FROM XEDIA-REG
    ifIndex
        FROM IF-MIB
    ;

xediaVlanMIB MODULE-IDENTITY
    LAST-UPDATED "9905212155Z" -- May 21, 1999
    ORGANIZATION "Xedia Corp."
    CONTACT-INFO
        "support@xedia.com"
    DESCRIPTION
        "This module defines objects for management of Xedia's
         support for VLANs and 802.1p and 802.1q Ethernet tagged
         frames."
    ::= { xediaMibs 34 }


-- ================================================================
-- Top-level organization of the MIB
-- ================================================================

xVlanObjects        OBJECT IDENTIFIER ::= { xediaVlanMIB 1 }
xVlanConformance    OBJECT IDENTIFIER ::= { xediaVlanMIB 2 } 

-- Kludge for older MIB compiler:
Unsigned32 ::= Gauge32

-- ================================================================
-- Object Definitions
-- ================================================================

xVlanIDTable OBJECT-TYPE
    SYNTAX      SEQUENCE OF XVlanIDEntry
    MAX-ACCESS  not-accessible
    STATUS      current
    DESCRIPTION
        "A table of VLAN IDs configured on Ethernet subinterfaces."
    ::= { xVlanObjects 1 }

xVlanIDEntry OBJECT-TYPE
    SYNTAX      XVlanIDEntry
    MAX-ACCESS  not-accessible
    STATUS      current
    DESCRIPTION
        "An association between an Ethernet subinterface and a
        VLAN ID."
    INDEX {ifIndex }
    ::= { xVlanIDTable 1 }

XVlanIDEntry ::= SEQUENCE {
    xVlanID           Unsigned32
}

xVlanID OBJECT-TYPE
    SYNTAX      Unsigned32 (1..4094)
    MAX-ACCESS  read-create
    STATUS      current
    DESCRIPTION
        "The 12-bit VLAN ID used in the VLAN Tag header."
    ::= { xVlanIDEntry 1 }

xVlanConfigTable OBJECT-TYPE
    SYNTAX      SEQUENCE OF XVlanConfigEntry
    MAX-ACCESS  not-accessible
    STATUS      current
    DESCRIPTION
        "A table of configuration information applicable to 
         VLANs indexed by Ethernet physical (integral) interface."
    ::= { xVlanObjects 2 }

xVlanConfigEntry OBJECT-TYPE
    SYNTAX      XVlanConfigEntry
    MAX-ACCESS  not-accessible
    STATUS      current
    DESCRIPTION
        "VLAN configuration information for a particular 
         Ethernet physical (integral) interface."
    INDEX {ifIndex }
    ::= { xVlanConfigTable 1 }

XVlanConfigEntry ::= SEQUENCE {
    xVlanConfigAdmitTaggedFrames         TruthValue,
    xVlanConfigAdmitConfiguredVlansOnly  TruthValue,
    xVlanConfigStripBridgedTags          TruthValue,
    xVlanConfigGVRP                      TruthValue,
    xVlanConfigGARPJoinTime              INTEGER
}

xVlanConfigAdmitTaggedFrames OBJECT-TYPE
    SYNTAX      TruthValue
    MAX-ACCESS  read-write
    STATUS      current
    DESCRIPTION
        "Whether 802.1q/802.1p tagged frames will be received
         by the box.  If this value is false, the frames will 
         be dropped."
    DEFVAL { true }
    ::= { xVlanConfigEntry 1 }

xVlanConfigAdmitConfiguredVlansOnly OBJECT-TYPE
    SYNTAX      TruthValue
    MAX-ACCESS  read-write
    STATUS      current
    DESCRIPTION
        "Whether only those 802.1q tagged frames that contain a
         VLAN ID that has been configured on the box will be
         received.  If this value is true, frames from VLANs with
         other VLAN IDs will be dropped.  This variable does not
         apply to bridged traffic."
    DEFVAL { true }
    ::= { xVlanConfigEntry 2 }

xVlanConfigStripBridgedTags OBJECT-TYPE
    SYNTAX      TruthValue
    MAX-ACCESS  read-write
    STATUS      current
    DESCRIPTION
        "Whether 802.1q/802.1p tagged frames that are being bridged
         will have the tag stripped out of the packet before it is
         forwarded.  This variable does not apply to routed traffic."
    DEFVAL { false }
    ::= { xVlanConfigEntry 3 }

xVlanConfigGVRP OBJECT-TYPE
    SYNTAX      TruthValue
    MAX-ACCESS  read-write
    STATUS      current
    DESCRIPTION
        "Whether the GVRP protocol for dynamically informing the network
         of the VLAN IDs configured in the box is enabled."
    DEFVAL { true }
    ::= { xVlanConfigEntry 4 }

xVlanConfigGARPJoinTime OBJECT-TYPE
    SYNTAX      INTEGER (1..21474800)
    MAX-ACCESS  read-write
    STATUS      current
    DESCRIPTION
        "The GARP Join time, in centiseconds.  This variable is a 
         component of the GVRP protocol."
    DEFVAL  { 20 }
    ::= { xVlanConfigEntry 5 }

-- ================================================================
-- Conformance Information
-- ================================================================

xVlanCompliances    OBJECT IDENTIFIER ::= { xVlanConformance 1 }
xVlanGroups         OBJECT IDENTIFIER ::= { xVlanConformance 2 }

--
-- Compliance Statements
--

xVlanCompliance MODULE-COMPLIANCE
    STATUS      current
    DESCRIPTION
        "The compliance statement for all agents that support this
        MIB. A compliant agent implements all objects defined in this
        MIB."
    MODULE  -- this module
    MANDATORY-GROUPS {
        xVlanGroup
    }
    ::= { xVlanCompliances 1 }

--
-- Object Groups
--

xVlanGroup OBJECT-GROUP
    OBJECTS {
        xVlanID,
        xVlanConfigAdmitTaggedFrames,
        xVlanConfigAdmitConfiguredVlansOnly,
        xVlanConfigStripBridgedTags,
        xVlanConfigGVRP,
        xVlanConfigGARPJoinTime
    }
    STATUS      current
    DESCRIPTION
        "The set of all accessible objects in this MIB."
    ::= { xVlanGroups 1 }


END
