ELSA-MIB DEFINITIONS ::= BEGIN

IMPORTS
    enterprises, TimeTicks, IpAddress
      FROM RFC1155-SMI
    OBJECT-TYPE
      FROM RFC-1212
    DisplayString
      FROM RFC1213-MIB;



elsa OBJECT IDENTIFIER ::= { enterprises 2356 }

isdn-Systems OBJECT IDENTIFIER ::= { elsa 400 }

isdn-Router OBJECT IDENTIFIER ::= { isdn-Systems 1 }

lancom-2000 OBJECT IDENTIFIER ::= { isdn-Router 2000 }

sta OBJECT IDENTIFIER ::= { lancom-2000 1 }
set OBJECT IDENTIFIER ::= { lancom-2000 2 }
fir OBJECT IDENTIFIER ::= { lancom-2000 3 }
oth OBJECT IDENTIFIER ::= { lancom-2000 4 }
staConne OBJECT-TYPE
         SYNTAX DisplayString
         ACCESS read-only
         STATUS mandatory
         DESCRIPTION "Connection-state"
         ::= {  sta 1 }

staCurre OBJECT-TYPE
         SYNTAX DisplayString
         ACCESS read-only
         STATUS mandatory
         DESCRIPTION "Current-time"
         ::= {  sta 18 }

staOpera OBJECT-TYPE
         SYNTAX DisplayString
         ACCESS read-only
         STATUS mandatory
         DESCRIPTION "Operating-time"
         ::= {  sta 2 }

staWanst OBJECT IDENTIFIER ::= { sta 4}
staWanstBytetrans OBJECT-TYPE
                  SYNTAX SEQUENCE OF StaWanstBytetransRows
                  ACCESS not-accessible
                  STATUS mandatory
                  DESCRIPTION "Byte-transport-statistics"
                  ::= {  staWanst 1 }

staWanstBytetransCols OBJECT-TYPE
                  SYNTAX StaWanstBytetransRows
                  ACCESS not-accessible
                  STATUS mandatory
                  DESCRIPTION "entry in table"
                  INDEX { staWanstBytetransIfc }
                  ::= {  staWanstBytetrans 1 }

StaWanstBytetransRows ::= SEQUENCE {
                  staWanstBytetransIfc INTEGER,
                  staWanstBytetransCrx INTEGER,
                  staWanstBytetransRxb INTEGER,
                  staWanstBytetransTxb INTEGER,
                  staWanstBytetransCtx INTEGER
                 }

staWanstBytetransIfc OBJECT-TYPE
                     SYNTAX INTEGER {
                       ch01(1),
                       ch02(2),
                       ch03(3),
                       ch04(4),
                       ch05(5),
                       ch06(6),
                       ch07(7),
                       ch08(8),
                       ch09(9),
                       ch10(10),
                       ch11(11),
                       ch12(12)
                     }
                     ACCESS read-only
                     STATUS mandatory
                     DESCRIPTION "Ifc"
                     ::= {  staWanstBytetransCols 1 }

staWanstBytetransCrx OBJECT-TYPE
                     SYNTAX INTEGER
                     ACCESS read-only
                     STATUS mandatory
                     DESCRIPTION "CRx-bytes"
                     ::= {  staWanstBytetransCols 2 }

staWanstBytetransRxb OBJECT-TYPE
                     SYNTAX INTEGER
                     ACCESS read-only
                     STATUS mandatory
                     DESCRIPTION "Rx-bytes"
                     ::= {  staWanstBytetransCols 3 }

staWanstBytetransTxb OBJECT-TYPE
                     SYNTAX INTEGER
                     ACCESS read-only
                     STATUS mandatory
                     DESCRIPTION "Tx-bytes"
                     ::= {  staWanstBytetransCols 4 }

staWanstBytetransCtx OBJECT-TYPE
                     SYNTAX INTEGER
                     ACCESS read-only
                     STATUS mandatory
                     DESCRIPTION "CTx-bytes"
                     ::= {  staWanstBytetransCols 5 }

staWanstPackettra OBJECT-TYPE
                  SYNTAX SEQUENCE OF StaWanstPackettraRows
                  ACCESS not-accessible
                  STATUS mandatory
                  DESCRIPTION "Packet-transport-statistics"
                  ::= {  staWanst 2 }

staWanstPackettraCols OBJECT-TYPE
                  SYNTAX StaWanstPackettraRows
                  ACCESS not-accessible
                  STATUS mandatory
                  DESCRIPTION "entry in table"
                  INDEX { staWanstPackettraIfc }
                  ::= {  staWanstPackettra 1 }

StaWanstPackettraRows ::= SEQUENCE {
                  staWanstPackettraIfc INTEGER,
                  staWanstPackettraRx INTEGER,
                  staWanstPackettraTxt INTEGER,
                  staWanstPackettraTxn INTEGER,
                  staWanstPackettraTxr INTEGER,
                  staWanstPackettraTxu INTEGER
                 }

staWanstPackettraIfc OBJECT-TYPE
                     SYNTAX INTEGER {
                       ch01(1),
                       ch02(2),
                       ch03(3),
                       ch04(4),
                       ch05(5),
                       ch06(6),
                       ch07(7),
                       ch08(8),
                       ch09(9),
                       ch10(10),
                       ch11(11),
                       ch12(12)
                     }
                     ACCESS read-only
                     STATUS mandatory
                     DESCRIPTION "Ifc"
                     ::= {  staWanstPackettraCols 1 }

staWanstPackettraRx OBJECT-TYPE
                     SYNTAX INTEGER
                     ACCESS read-only
                     STATUS mandatory
                     DESCRIPTION "Rx"
                     ::= {  staWanstPackettraCols 2 }

staWanstPackettraTxt OBJECT-TYPE
                     SYNTAX INTEGER
                     ACCESS read-only
                     STATUS mandatory
                     DESCRIPTION "Tx-total"
                     ::= {  staWanstPackettraCols 3 }

staWanstPackettraTxn OBJECT-TYPE
                     SYNTAX INTEGER
                     ACCESS read-only
                     STATUS mandatory
                     DESCRIPTION "Tx-normal"
                     ::= {  staWanstPackettraCols 4 }

staWanstPackettraTxr OBJECT-TYPE
                     SYNTAX INTEGER
                     ACCESS read-only
                     STATUS mandatory
                     DESCRIPTION "Tx-reliable"
                     ::= {  staWanstPackettraCols 5 }

staWanstPackettraTxu OBJECT-TYPE
                     SYNTAX INTEGER
                     ACCESS read-only
                     STATUS mandatory
                     DESCRIPTION "Tx-urgent"
                     ::= {  staWanstPackettraCols 6 }

staWanstErrorstat OBJECT-TYPE
                  SYNTAX SEQUENCE OF StaWanstErrorstatRows
                  ACCESS not-accessible
                  STATUS mandatory
                  DESCRIPTION "Error-statistics"
                  ::= {  staWanst 3 }

staWanstErrorstatCols OBJECT-TYPE
                  SYNTAX StaWanstErrorstatRows
                  ACCESS not-accessible
                  STATUS mandatory
                  DESCRIPTION "entry in table"
                  INDEX { staWanstErrorstatIfc }
                  ::= {  staWanstErrorstat 1 }

StaWanstErrorstatRows ::= SEQUENCE {
                  staWanstErrorstatIfc INTEGER,
                  staWanstErrorstatRxl1 INTEGER,
                  staWanstErrorstatRxl2 INTEGER,
                  staWanstErrorstatRxl3 INTEGER,
                  staWanstErrorstatStac INTEGER,
                  staWanstErrorstatTxer INTEGER
                 }

staWanstErrorstatIfc OBJECT-TYPE
                      SYNTAX INTEGER {
                        ch01(1),
                        ch02(2),
                        ch03(3),
                        ch04(4),
                        ch05(5),
                        ch06(6),
                        ch07(7),
                        ch08(8),
                        ch09(9),
                        ch10(10),
                        ch11(11),
                        ch12(12)
                      }
                      ACCESS read-only
                      STATUS mandatory
                      DESCRIPTION "Ifc"
                      ::= {  staWanstErrorstatCols 1 }

staWanstErrorstatRxl1 OBJECT-TYPE
                      SYNTAX INTEGER
                      ACCESS read-only
                      STATUS mandatory
                      DESCRIPTION "Rx-l1-error"
                      ::= {  staWanstErrorstatCols 2 }

staWanstErrorstatRxl2 OBJECT-TYPE
                      SYNTAX INTEGER
                      ACCESS read-only
                      STATUS mandatory
                      DESCRIPTION "Rx-l2-error"
                      ::= {  staWanstErrorstatCols 3 }

staWanstErrorstatRxl3 OBJECT-TYPE
                      SYNTAX INTEGER
                      ACCESS read-only
                      STATUS mandatory
                      DESCRIPTION "Rx-l3-error"
                      ::= {  staWanstErrorstatCols 4 }

staWanstErrorstatStac OBJECT-TYPE
                      SYNTAX INTEGER
                      ACCESS read-only
                      STATUS mandatory
                      DESCRIPTION "Stack-error"
                      ::= {  staWanstErrorstatCols 5 }

staWanstErrorstatTxer OBJECT-TYPE
                      SYNTAX INTEGER
                      ACCESS read-only
                      STATUS mandatory
                      DESCRIPTION "Tx-error"
                      ::= {  staWanstErrorstatCols 6 }

staWanstWantxdisc OBJECT-TYPE
                  SYNTAX INTEGER
                  ACCESS read-only
                  STATUS mandatory
                  DESCRIPTION "WAN-tx-discarded"
                  ::= {  staWanst 4 }

staWanstWanheappa OBJECT-TYPE
                  SYNTAX INTEGER
                  ACCESS read-only
                  STATUS mandatory
                  DESCRIPTION "WAN-heap-packets"
                  ::= {  staWanst 5 }

staWanstWanqueuep OBJECT-TYPE
                  SYNTAX INTEGER
                  ACCESS read-only
                  STATUS mandatory
                  DESCRIPTION "WAN-queue-packets"
                  ::= {  staWanst 6 }

staWanstWanqueuee OBJECT-TYPE
                  SYNTAX INTEGER
                  ACCESS read-only
                  STATUS mandatory
                  DESCRIPTION "WAN-queue-errors"
                  ::= {  staWanst 7 }

staWanstThroughpu OBJECT-TYPE
                  SYNTAX SEQUENCE OF StaWanstThroughpuRows
                  ACCESS not-accessible
                  STATUS mandatory
                  DESCRIPTION "Throughput-statistics"
                  ::= {  staWanst 8 }

staWanstThroughpuCols OBJECT-TYPE
                  SYNTAX StaWanstThroughpuRows
                  ACCESS not-accessible
                  STATUS mandatory
                  DESCRIPTION "entry in table"
                  INDEX { staWanstThroughpuIfc }
                  ::= {  staWanstThroughpu 1 }

StaWanstThroughpuRows ::= SEQUENCE {
                  staWanstThroughpuIfc INTEGER,
                  staWanstThroughpuRxsc INTEGER,
                  staWanstThroughpuTxsc INTEGER,
                  staWanstThroughpuRxsa INTEGER,
                  staWanstThroughpuTxsa INTEGER
                 }

staWanstThroughpuIfc OBJECT-TYPE
                      SYNTAX INTEGER {
                        ch01(1),
                        ch02(2),
                        ch03(3),
                        ch04(4),
                        ch05(5),
                        ch06(6),
                        ch07(7),
                        ch08(8),
                        ch09(9),
                        ch10(10),
                        ch11(11),
                        ch12(12)
                      }
                      ACCESS read-only
                      STATUS mandatory
                      DESCRIPTION "Ifc"
                      ::= {  staWanstThroughpuCols 1 }

staWanstThroughpuRxsc OBJECT-TYPE
                      SYNTAX INTEGER
                      ACCESS read-only
                      STATUS mandatory
                      DESCRIPTION "Rx/s current"
                      ::= {  staWanstThroughpuCols 2 }

staWanstThroughpuTxsc OBJECT-TYPE
                      SYNTAX INTEGER
                      ACCESS read-only
                      STATUS mandatory
                      DESCRIPTION "Tx/s current"
                      ::= {  staWanstThroughpuCols 3 }

staWanstThroughpuRxsa OBJECT-TYPE
                      SYNTAX INTEGER
                      ACCESS read-only
                      STATUS mandatory
                      DESCRIPTION "Rx/s average"
                      ::= {  staWanstThroughpuCols 4 }

staWanstThroughpuTxsa OBJECT-TYPE
                      SYNTAX INTEGER
                      ACCESS read-only
                      STATUS mandatory
                      DESCRIPTION "Tx/s average"
                      ::= {  staWanstThroughpuCols 5 }

staWanstDeleteval OBJECT-TYPE
                  SYNTAX INTEGER
                  ACCESS write-only
                  STATUS mandatory
                  DESCRIPTION "Delete-values"
                  ::= {  staWanst 9 }

staLanst OBJECT IDENTIFIER ::= { sta 5}
staLanstLanrxpack OBJECT-TYPE
                  SYNTAX INTEGER
                  ACCESS read-only
                  STATUS mandatory
                  DESCRIPTION "LAN-rx-packets"
                  ::= {  staLanst 1 }

staLanstLantxpack OBJECT-TYPE
                  SYNTAX INTEGER
                  ACCESS read-only
                  STATUS mandatory
                  DESCRIPTION "LAN-tx-packets"
                  ::= {  staLanst 2 }

staLanstLanrxerro OBJECT-TYPE
                  SYNTAX INTEGER
                  ACCESS read-only
                  STATUS mandatory
                  DESCRIPTION "LAN-rx-errors"
                  ::= {  staLanst 3 }

staLanstLanrxcrce OBJECT-TYPE
                  SYNTAX INTEGER
                  ACCESS read-only
                  STATUS mandatory
                  DESCRIPTION "LAN-rx-crc-errors"
                  ::= {  staLanst 26 }

staLanstLanrxalig OBJECT-TYPE
                  SYNTAX INTEGER
                  ACCESS read-only
                  STATUS mandatory
                  DESCRIPTION "LAN-rx-align-errors"
                  ::= {  staLanst 27 }

staLanstLantxerro OBJECT-TYPE
                  SYNTAX INTEGER
                  ACCESS read-only
                  STATUS mandatory
                  DESCRIPTION "LAN-tx-errors"
                  ::= {  staLanst 4 }

staLanstLanstacke OBJECT-TYPE
                  SYNTAX INTEGER
                  ACCESS read-only
                  STATUS mandatory
                  DESCRIPTION "LAN-stack-errors"
                  ::= {  staLanst 5 }

staLanstLannicerr OBJECT-TYPE
                  SYNTAX INTEGER
                  ACCESS read-only
                  STATUS mandatory
                  DESCRIPTION "LAN-NIC-errors"
                  ::= {  staLanst 6 }

staLanstLanheappa OBJECT-TYPE
                  SYNTAX INTEGER
                  ACCESS read-only
                  STATUS mandatory
                  DESCRIPTION "LAN-heap-packets"
                  ::= {  staLanst 7 }

staLanstLanqueuep OBJECT-TYPE
                  SYNTAX INTEGER
                  ACCESS read-only
                  STATUS mandatory
                  DESCRIPTION "LAN-queue-packets"
                  ::= {  staLanst 8 }

staLanstLanqueuee OBJECT-TYPE
                  SYNTAX INTEGER
                  ACCESS read-only
                  STATUS mandatory
                  DESCRIPTION "LAN-queue-errors"
                  ::= {  staLanst 9 }

staLanstLancollis OBJECT-TYPE
                  SYNTAX INTEGER
                  ACCESS read-only
                  STATUS mandatory
                  DESCRIPTION "LAN-collisions"
                  ::= {  staLanst 10 }

staLanstLanrxbyte OBJECT-TYPE
                  SYNTAX INTEGER
                  ACCESS read-only
                  STATUS mandatory
                  DESCRIPTION "LAN-rx-bytes"
                  ::= {  staLanst 18 }

staLanstLantxbyte OBJECT-TYPE
                  SYNTAX INTEGER
                  ACCESS read-only
                  STATUS mandatory
                  DESCRIPTION "LAN-tx-bytes"
                  ::= {  staLanst 19 }

staLanstLanrxbroa OBJECT-TYPE
                  SYNTAX INTEGER
                  ACCESS read-only
                  STATUS mandatory
                  DESCRIPTION "LAN-rx-broadcasts"
                  ::= {  staLanst 20 }

staLanstLanrxmult OBJECT-TYPE
                  SYNTAX INTEGER
                  ACCESS read-only
                  STATUS mandatory
                  DESCRIPTION "LAN-rx-multicasts"
                  ::= {  staLanst 21 }

staLanstLanrxunic OBJECT-TYPE
                  SYNTAX INTEGER
                  ACCESS read-only
                  STATUS mandatory
                  DESCRIPTION "LAN-rx-unicasts"
                  ::= {  staLanst 22 }

staLanstLantxbroa OBJECT-TYPE
                  SYNTAX INTEGER
                  ACCESS read-only
                  STATUS mandatory
                  DESCRIPTION "LAN-tx-broadcasts"
                  ::= {  staLanst 23 }

staLanstLantxmult OBJECT-TYPE
                  SYNTAX INTEGER
                  ACCESS read-only
                  STATUS mandatory
                  DESCRIPTION "LAN-tx-multicasts"
                  ::= {  staLanst 24 }

staLanstLantxunic OBJECT-TYPE
                  SYNTAX INTEGER
                  ACCESS read-only
                  STATUS mandatory
                  DESCRIPTION "LAN-tx-unicasts"
                  ::= {  staLanst 25 }

staLanstDeleteval OBJECT-TYPE
                  SYNTAX INTEGER
                  ACCESS write-only
                  STATUS mandatory
                  DESCRIPTION "Delete-values"
                  ::= {  staLanst 11 }

staPppst OBJECT IDENTIFIER ::= { sta 6}
staPppstPpp OBJECT-TYPE
            SYNTAX SEQUENCE OF StaPppstPppRows
            ACCESS not-accessible
            STATUS mandatory
            DESCRIPTION "PPP-phases"
            ::= {  staPppst 1 }

staPppstPppCols OBJECT-TYPE
            SYNTAX StaPppstPppRows
            ACCESS not-accessible
            STATUS mandatory
            DESCRIPTION "entry in table"
            INDEX { staPppstPppIfc }
            ::= {  staPppstPpp 1 }

StaPppstPppRows ::= SEQUENCE {
            staPppstPppIfc INTEGER,
            staPppstPppPha INTEGER,
            staPppstPppLcp INTEGER,
            staPppstPppIpc INTEGER,
            staPppstPppIpx INTEGER,
            staPppstPppCcp INTEGER,
            staPppstPppBac INTEGER
           }

staPppstPppIfc OBJECT-TYPE
               SYNTAX INTEGER {
                 ch01(1),
                 ch02(2),
                 ch03(3),
                 ch04(4),
                 ch05(5),
                 ch06(6),
                 ch07(7),
                 ch08(8),
                 ch09(9),
                 ch10(10),
                 ch11(11),
                 ch12(12)
               }
               ACCESS read-only
               STATUS mandatory
               DESCRIPTION "Ifc"
               ::= {  staPppstPppCols 1 }

staPppstPppPha OBJECT-TYPE
               SYNTAX INTEGER {
                 dead(1),
                 establish(2),
                 terminate(3),
                 authenticate(4),
                 callback(5),
                 network(6)
               }
               ACCESS read-only
               STATUS mandatory
               DESCRIPTION "Phase to"
               ::= {  staPppstPppCols 2 }

staPppstPppLcp OBJECT-TYPE
               SYNTAX INTEGER {
                 initial(1),
                 startng(2),
                 closed(3),
                 stopped(4),
                 closing(5),
                 stoppng(6),
                 reqsent(7),
                 ackrcvd(8),
                 acksent(9),
                 opened(10)
               }
               ACCESS read-only
               STATUS mandatory
               DESCRIPTION "LCP"
               ::= {  staPppstPppCols 3 }

staPppstPppIpc OBJECT-TYPE
               SYNTAX INTEGER {
                 initial(1),
                 startng(2),
                 closed(3),
                 stopped(4),
                 closing(5),
                 stoppng(6),
                 reqsent(7),
                 ackrcvd(8),
                 acksent(9),
                 opened(10)
               }
               ACCESS read-only
               STATUS mandatory
               DESCRIPTION "IPCP"
               ::= {  staPppstPppCols 4 }

staPppstPppIpx OBJECT-TYPE
               SYNTAX INTEGER {
                 initial(1),
                 startng(2),
                 closed(3),
                 stopped(4),
                 closing(5),
                 stoppng(6),
                 reqsent(7),
                 ackrcvd(8),
                 acksent(9),
                 opened(10)
               }
               ACCESS read-only
               STATUS mandatory
               DESCRIPTION "IPXCP"
               ::= {  staPppstPppCols 5 }

staPppstPppCcp OBJECT-TYPE
               SYNTAX INTEGER {
                 initial(1),
                 startng(2),
                 closed(3),
                 stopped(4),
                 closing(5),
                 stoppng(6),
                 reqsent(7),
                 ackrcvd(8),
                 acksent(9),
                 opened(10)
               }
               ACCESS read-only
               STATUS mandatory
               DESCRIPTION "CCP"
               ::= {  staPppstPppCols 6 }

staPppstPppBac OBJECT-TYPE
               SYNTAX INTEGER {
                 initial(1),
                 startng(2),
                 closed(3),
                 stopped(4),
                 closing(5),
                 stoppng(6),
                 reqsent(7),
                 ackrcvd(8),
                 acksent(9),
                 opened(10)
               }
               ACCESS read-only
               STATUS mandatory
               DESCRIPTION "BACP"
               ::= {  staPppstPppCols 7 }

staPppstLcp OBJECT IDENTIFIER ::= { staPppst 2}
staPppstLcpRxerrors OBJECT-TYPE
                        SYNTAX INTEGER
                        ACCESS read-only
                        STATUS mandatory
                        DESCRIPTION "Rx-errors"
                        ::= {  staPppstLcp 1 }

staPppstLcpRxdiscarded OBJECT-TYPE
                        SYNTAX INTEGER
                        ACCESS read-only
                        STATUS mandatory
                        DESCRIPTION "Rx-discarded"
                        ::= {  staPppstLcp 2 }

staPppstLcpRxconfigrequ OBJECT-TYPE
                        SYNTAX INTEGER
                        ACCESS read-only
                        STATUS mandatory
                        DESCRIPTION "Rx-config-request"
                        ::= {  staPppstLcp 3 }

staPppstLcpRxconfigack OBJECT-TYPE
                        SYNTAX INTEGER
                        ACCESS read-only
                        STATUS mandatory
                        DESCRIPTION "Rx-config-ack."
                        ::= {  staPppstLcp 4 }

staPppstLcpRxconfignak OBJECT-TYPE
                        SYNTAX INTEGER
                        ACCESS read-only
                        STATUS mandatory
                        DESCRIPTION "Rx-config-nak."
                        ::= {  staPppstLcp 5 }

staPppstLcpRxconfigreje OBJECT-TYPE
                        SYNTAX INTEGER
                        ACCESS read-only
                        STATUS mandatory
                        DESCRIPTION "Rx-config-reject"
                        ::= {  staPppstLcp 6 }

staPppstLcpRxterminater OBJECT-TYPE
                        SYNTAX INTEGER
                        ACCESS read-only
                        STATUS mandatory
                        DESCRIPTION "Rx-terminate-request"
                        ::= {  staPppstLcp 7 }

staPppstLcpRxterminatea OBJECT-TYPE
                        SYNTAX INTEGER
                        ACCESS read-only
                        STATUS mandatory
                        DESCRIPTION "Rx-terminate-ack."
                        ::= {  staPppstLcp 8 }

staPppstLcpRxcodereject OBJECT-TYPE
                        SYNTAX INTEGER
                        ACCESS read-only
                        STATUS mandatory
                        DESCRIPTION "Rx-code-reject"
                        ::= {  staPppstLcp 9 }

staPppstLcpRxprotocolre OBJECT-TYPE
                        SYNTAX INTEGER
                        ACCESS read-only
                        STATUS mandatory
                        DESCRIPTION "Rx-protocol-reject"
                        ::= {  staPppstLcp 10 }

staPppstLcpRxechoreques OBJECT-TYPE
                        SYNTAX INTEGER
                        ACCESS read-only
                        STATUS mandatory
                        DESCRIPTION "Rx-echo-request"
                        ::= {  staPppstLcp 11 }

staPppstLcpRxechoreply OBJECT-TYPE
                        SYNTAX INTEGER
                        ACCESS read-only
                        STATUS mandatory
                        DESCRIPTION "Rx-echo-reply"
                        ::= {  staPppstLcp 12 }

staPppstLcpRxdiscardreq OBJECT-TYPE
                        SYNTAX INTEGER
                        ACCESS read-only
                        STATUS mandatory
                        DESCRIPTION "Rx-discard-request"
                        ::= {  staPppstLcp 13 }

staPppstLcpTxconfigrequ OBJECT-TYPE
                        SYNTAX INTEGER
                        ACCESS read-only
                        STATUS mandatory
                        DESCRIPTION "Tx-config-request"
                        ::= {  staPppstLcp 14 }

staPppstLcpTxconfigack OBJECT-TYPE
                        SYNTAX INTEGER
                        ACCESS read-only
                        STATUS mandatory
                        DESCRIPTION "Tx-config-ack."
                        ::= {  staPppstLcp 15 }

staPppstLcpTxconfignak OBJECT-TYPE
                        SYNTAX INTEGER
                        ACCESS read-only
                        STATUS mandatory
                        DESCRIPTION "Tx-config-nak."
                        ::= {  staPppstLcp 16 }

staPppstLcpTxconfigreje OBJECT-TYPE
                        SYNTAX INTEGER
                        ACCESS read-only
                        STATUS mandatory
                        DESCRIPTION "Tx-config-reject"
                        ::= {  staPppstLcp 17 }

staPppstLcpTxterminater OBJECT-TYPE
                        SYNTAX INTEGER
                        ACCESS read-only
                        STATUS mandatory
                        DESCRIPTION "Tx-terminate-request"
                        ::= {  staPppstLcp 18 }

staPppstLcpTxterminatea OBJECT-TYPE
                        SYNTAX INTEGER
                        ACCESS read-only
                        STATUS mandatory
                        DESCRIPTION "Tx-terminate-ack."
                        ::= {  staPppstLcp 19 }

staPppstLcpTxcodereject OBJECT-TYPE
                        SYNTAX INTEGER
                        ACCESS read-only
                        STATUS mandatory
                        DESCRIPTION "Tx-code-reject"
                        ::= {  staPppstLcp 20 }

staPppstLcpTxprotocolre OBJECT-TYPE
                        SYNTAX INTEGER
                        ACCESS read-only
                        STATUS mandatory
                        DESCRIPTION "Tx-protocol-reject"
                        ::= {  staPppstLcp 21 }

staPppstLcpTxechoreques OBJECT-TYPE
                        SYNTAX INTEGER
                        ACCESS read-only
                        STATUS mandatory
                        DESCRIPTION "Tx-echo-request"
                        ::= {  staPppstLcp 22 }

staPppstLcpTxechoreply OBJECT-TYPE
                        SYNTAX INTEGER
                        ACCESS read-only
                        STATUS mandatory
                        DESCRIPTION "Tx-echo-reply"
                        ::= {  staPppstLcp 23 }

staPppstLcpTxdiscardreq OBJECT-TYPE
                        SYNTAX INTEGER
                        ACCESS read-only
                        STATUS mandatory
                        DESCRIPTION "Tx-discard-request"
                        ::= {  staPppstLcp 24 }

staPppstLcpDeletevalues OBJECT-TYPE
                        SYNTAX INTEGER
                        ACCESS write-only
                        STATUS mandatory
                        DESCRIPTION "Delete-values"
                        ::= {  staPppstLcp 25 }

staPppstPap OBJECT IDENTIFIER ::= { staPppst 3}
staPppstPapRxdis OBJECT-TYPE
                 SYNTAX INTEGER
                 ACCESS read-only
                 STATUS mandatory
                 DESCRIPTION "Rx-discarded"
                 ::= {  staPppstPap 1 }

staPppstPapRxreq OBJECT-TYPE
                 SYNTAX INTEGER
                 ACCESS read-only
                 STATUS mandatory
                 DESCRIPTION "Rx-request"
                 ::= {  staPppstPap 2 }

staPppstPapRxsuc OBJECT-TYPE
                 SYNTAX INTEGER
                 ACCESS read-only
                 STATUS mandatory
                 DESCRIPTION "Rx-success"
                 ::= {  staPppstPap 3 }

staPppstPapRxfai OBJECT-TYPE
                 SYNTAX INTEGER
                 ACCESS read-only
                 STATUS mandatory
                 DESCRIPTION "Rx-failure"
                 ::= {  staPppstPap 4 }

staPppstPapTxret OBJECT-TYPE
                 SYNTAX INTEGER
                 ACCESS read-only
                 STATUS mandatory
                 DESCRIPTION "Tx-retry"
                 ::= {  staPppstPap 5 }

staPppstPapTxreq OBJECT-TYPE
                 SYNTAX INTEGER
                 ACCESS read-only
                 STATUS mandatory
                 DESCRIPTION "Tx-request"
                 ::= {  staPppstPap 6 }

staPppstPapTxsuc OBJECT-TYPE
                 SYNTAX INTEGER
                 ACCESS read-only
                 STATUS mandatory
                 DESCRIPTION "Tx-success"
                 ::= {  staPppstPap 7 }

staPppstPapTxfai OBJECT-TYPE
                 SYNTAX INTEGER
                 ACCESS read-only
                 STATUS mandatory
                 DESCRIPTION "Tx-failure"
                 ::= {  staPppstPap 8 }

staPppstPapDelet OBJECT-TYPE
                 SYNTAX INTEGER
                 ACCESS write-only
                 STATUS mandatory
                 DESCRIPTION "Delete-values"
                 ::= {  staPppstPap 9 }

staPppstCha OBJECT IDENTIFIER ::= { staPppst 4}
staPppstChaRxdis OBJECT-TYPE
                 SYNTAX INTEGER
                 ACCESS read-only
                 STATUS mandatory
                 DESCRIPTION "Rx-discarded"
                 ::= {  staPppstCha 1 }

staPppstChaRxcha OBJECT-TYPE
                 SYNTAX INTEGER
                 ACCESS read-only
                 STATUS mandatory
                 DESCRIPTION "Rx-challenge"
                 ::= {  staPppstCha 2 }

staPppstChaRxres OBJECT-TYPE
                 SYNTAX INTEGER
                 ACCESS read-only
                 STATUS mandatory
                 DESCRIPTION "Rx-response"
                 ::= {  staPppstCha 3 }

staPppstChaRxsuc OBJECT-TYPE
                 SYNTAX INTEGER
                 ACCESS read-only
                 STATUS mandatory
                 DESCRIPTION "Rx-success"
                 ::= {  staPppstCha 4 }

staPppstChaRxfai OBJECT-TYPE
                 SYNTAX INTEGER
                 ACCESS read-only
                 STATUS mandatory
                 DESCRIPTION "Rx-failure"
                 ::= {  staPppstCha 5 }

staPppstChaTxret OBJECT-TYPE
                 SYNTAX INTEGER
                 ACCESS read-only
                 STATUS mandatory
                 DESCRIPTION "Tx-retry"
                 ::= {  staPppstCha 6 }

staPppstChaTxcha OBJECT-TYPE
                 SYNTAX INTEGER
                 ACCESS read-only
                 STATUS mandatory
                 DESCRIPTION "Tx-challenge"
                 ::= {  staPppstCha 7 }

staPppstChaTxres OBJECT-TYPE
                 SYNTAX INTEGER
                 ACCESS read-only
                 STATUS mandatory
                 DESCRIPTION "Tx-response"
                 ::= {  staPppstCha 8 }

staPppstChaTxsuc OBJECT-TYPE
                 SYNTAX INTEGER
                 ACCESS read-only
                 STATUS mandatory
                 DESCRIPTION "Tx-success"
                 ::= {  staPppstCha 9 }

staPppstChaTxfai OBJECT-TYPE
                 SYNTAX INTEGER
                 ACCESS read-only
                 STATUS mandatory
                 DESCRIPTION "Tx-failure"
                 ::= {  staPppstCha 10 }

staPppstChaDelet OBJECT-TYPE
                 SYNTAX INTEGER
                 ACCESS write-only
                 STATUS mandatory
                 DESCRIPTION "Delete-values"
                 ::= {  staPppstCha 11 }

staPppstCbc OBJECT IDENTIFIER ::= { staPppst 7}
staPppstCbcRxdis OBJECT-TYPE
                 SYNTAX INTEGER
                 ACCESS read-only
                 STATUS mandatory
                 DESCRIPTION "Rx-discarded"
                 ::= {  staPppstCbc 1 }

staPppstCbcRxreq OBJECT-TYPE
                 SYNTAX INTEGER
                 ACCESS read-only
                 STATUS mandatory
                 DESCRIPTION "Rx-request"
                 ::= {  staPppstCbc 2 }

staPppstCbcRxres OBJECT-TYPE
                 SYNTAX INTEGER
                 ACCESS read-only
                 STATUS mandatory
                 DESCRIPTION "Rx-response"
                 ::= {  staPppstCbc 3 }

staPppstCbcRxack OBJECT-TYPE
                 SYNTAX INTEGER
                 ACCESS read-only
                 STATUS mandatory
                 DESCRIPTION "Rx-acknowledge"
                 ::= {  staPppstCbc 4 }

staPppstCbcTxreq OBJECT-TYPE
                 SYNTAX INTEGER
                 ACCESS read-only
                 STATUS mandatory
                 DESCRIPTION "Tx-request"
                 ::= {  staPppstCbc 5 }

staPppstCbcTxres OBJECT-TYPE
                 SYNTAX INTEGER
                 ACCESS read-only
                 STATUS mandatory
                 DESCRIPTION "Tx-response"
                 ::= {  staPppstCbc 6 }

staPppstCbcTxack OBJECT-TYPE
                 SYNTAX INTEGER
                 ACCESS read-only
                 STATUS mandatory
                 DESCRIPTION "Tx-acknowledge"
                 ::= {  staPppstCbc 7 }

staPppstCbcDelet OBJECT-TYPE
                 SYNTAX INTEGER
                 ACCESS write-only
                 STATUS mandatory
                 DESCRIPTION "Delete-values"
                 ::= {  staPppstCbc 8 }

staPppstIpx OBJECT IDENTIFIER ::= { staPppst 5}
staPppstIpxRxdiscarded OBJECT-TYPE
                        SYNTAX INTEGER
                        ACCESS read-only
                        STATUS mandatory
                        DESCRIPTION "Rx-discarded"
                        ::= {  staPppstIpx 1 }

staPppstIpxRxconfigrequ OBJECT-TYPE
                        SYNTAX INTEGER
                        ACCESS read-only
                        STATUS mandatory
                        DESCRIPTION "Rx-config-request"
                        ::= {  staPppstIpx 2 }

staPppstIpxRxconfigack OBJECT-TYPE
                        SYNTAX INTEGER
                        ACCESS read-only
                        STATUS mandatory
                        DESCRIPTION "Rx-config-ack."
                        ::= {  staPppstIpx 3 }

staPppstIpxRxconfignak OBJECT-TYPE
                        SYNTAX INTEGER
                        ACCESS read-only
                        STATUS mandatory
                        DESCRIPTION "Rx-config-nak."
                        ::= {  staPppstIpx 4 }

staPppstIpxRxconfigreje OBJECT-TYPE
                        SYNTAX INTEGER
                        ACCESS read-only
                        STATUS mandatory
                        DESCRIPTION "Rx-config-reject"
                        ::= {  staPppstIpx 5 }

staPppstIpxRxterminater OBJECT-TYPE
                        SYNTAX INTEGER
                        ACCESS read-only
                        STATUS mandatory
                        DESCRIPTION "Rx-terminate-request"
                        ::= {  staPppstIpx 6 }

staPppstIpxRxterminatea OBJECT-TYPE
                        SYNTAX INTEGER
                        ACCESS read-only
                        STATUS mandatory
                        DESCRIPTION "Rx-terminate-ack."
                        ::= {  staPppstIpx 7 }

staPppstIpxRxcodereject OBJECT-TYPE
                        SYNTAX INTEGER
                        ACCESS read-only
                        STATUS mandatory
                        DESCRIPTION "Rx-code-reject"
                        ::= {  staPppstIpx 8 }

staPppstIpxTxconfigrequ OBJECT-TYPE
                        SYNTAX INTEGER
                        ACCESS read-only
                        STATUS mandatory
                        DESCRIPTION "Tx-config-request"
                        ::= {  staPppstIpx 9 }

staPppstIpxTxconfigack OBJECT-TYPE
                        SYNTAX INTEGER
                        ACCESS read-only
                        STATUS mandatory
                        DESCRIPTION "Tx-config-ack."
                        ::= {  staPppstIpx 10 }

staPppstIpxTxconfignak OBJECT-TYPE
                        SYNTAX INTEGER
                        ACCESS read-only
                        STATUS mandatory
                        DESCRIPTION "Tx-config-nak."
                        ::= {  staPppstIpx 11 }

staPppstIpxTxconfigreje OBJECT-TYPE
                        SYNTAX INTEGER
                        ACCESS read-only
                        STATUS mandatory
                        DESCRIPTION "Tx-config-reject"
                        ::= {  staPppstIpx 12 }

staPppstIpxTxterminater OBJECT-TYPE
                        SYNTAX INTEGER
                        ACCESS read-only
                        STATUS mandatory
                        DESCRIPTION "Tx-terminate-request"
                        ::= {  staPppstIpx 13 }

staPppstIpxTxterminatea OBJECT-TYPE
                        SYNTAX INTEGER
                        ACCESS read-only
                        STATUS mandatory
                        DESCRIPTION "Tx-terminate-ack."
                        ::= {  staPppstIpx 14 }

staPppstIpxTxcodereject OBJECT-TYPE
                        SYNTAX INTEGER
                        ACCESS read-only
                        STATUS mandatory
                        DESCRIPTION "Tx-code-reject"
                        ::= {  staPppstIpx 15 }

staPppstIpxDeletevalues OBJECT-TYPE
                        SYNTAX INTEGER
                        ACCESS write-only
                        STATUS mandatory
                        DESCRIPTION "Delete-values"
                        ::= {  staPppstIpx 16 }

staPppstIpc OBJECT IDENTIFIER ::= { staPppst 6}
staPppstIpcRxdiscarded OBJECT-TYPE
                        SYNTAX INTEGER
                        ACCESS read-only
                        STATUS mandatory
                        DESCRIPTION "Rx-discarded"
                        ::= {  staPppstIpc 1 }

staPppstIpcRxconfigrequ OBJECT-TYPE
                        SYNTAX INTEGER
                        ACCESS read-only
                        STATUS mandatory
                        DESCRIPTION "Rx-config-request"
                        ::= {  staPppstIpc 2 }

staPppstIpcRxconfigack OBJECT-TYPE
                        SYNTAX INTEGER
                        ACCESS read-only
                        STATUS mandatory
                        DESCRIPTION "Rx-config-ack."
                        ::= {  staPppstIpc 3 }

staPppstIpcRxconfignak OBJECT-TYPE
                        SYNTAX INTEGER
                        ACCESS read-only
                        STATUS mandatory
                        DESCRIPTION "Rx-config-nak."
                        ::= {  staPppstIpc 4 }

staPppstIpcRxconfigreje OBJECT-TYPE
                        SYNTAX INTEGER
                        ACCESS read-only
                        STATUS mandatory
                        DESCRIPTION "Rx-config-reject"
                        ::= {  staPppstIpc 5 }

staPppstIpcRxterminater OBJECT-TYPE
                        SYNTAX INTEGER
                        ACCESS read-only
                        STATUS mandatory
                        DESCRIPTION "Rx-terminate-request"
                        ::= {  staPppstIpc 6 }

staPppstIpcRxterminatea OBJECT-TYPE
                        SYNTAX INTEGER
                        ACCESS read-only
                        STATUS mandatory
                        DESCRIPTION "Rx-terminate-ack."
                        ::= {  staPppstIpc 7 }

staPppstIpcRxcodereject OBJECT-TYPE
                        SYNTAX INTEGER
                        ACCESS read-only
                        STATUS mandatory
                        DESCRIPTION "Rx-code-reject"
                        ::= {  staPppstIpc 8 }

staPppstIpcTxconfigrequ OBJECT-TYPE
                        SYNTAX INTEGER
                        ACCESS read-only
                        STATUS mandatory
                        DESCRIPTION "Tx-config-request"
                        ::= {  staPppstIpc 9 }

staPppstIpcTxconfigack OBJECT-TYPE
                        SYNTAX INTEGER
                        ACCESS read-only
                        STATUS mandatory
                        DESCRIPTION "Tx-config-ack."
                        ::= {  staPppstIpc 10 }

staPppstIpcTxconfignak OBJECT-TYPE
                        SYNTAX INTEGER
                        ACCESS read-only
                        STATUS mandatory
                        DESCRIPTION "Tx-config-nak."
                        ::= {  staPppstIpc 11 }

staPppstIpcTxconfigreje OBJECT-TYPE
                        SYNTAX INTEGER
                        ACCESS read-only
                        STATUS mandatory
                        DESCRIPTION "Tx-config-reject"
                        ::= {  staPppstIpc 12 }

staPppstIpcTxterminater OBJECT-TYPE
                        SYNTAX INTEGER
                        ACCESS read-only
                        STATUS mandatory
                        DESCRIPTION "Tx-terminate-request"
                        ::= {  staPppstIpc 13 }

staPppstIpcTxterminatea OBJECT-TYPE
                        SYNTAX INTEGER
                        ACCESS read-only
                        STATUS mandatory
                        DESCRIPTION "Tx-terminate-ack."
                        ::= {  staPppstIpc 14 }

staPppstIpcTxcodereject OBJECT-TYPE
                        SYNTAX INTEGER
                        ACCESS read-only
                        STATUS mandatory
                        DESCRIPTION "Tx-code-reject"
                        ::= {  staPppstIpc 15 }

staPppstIpcDeletevalues OBJECT-TYPE
                        SYNTAX INTEGER
                        ACCESS write-only
                        STATUS mandatory
                        DESCRIPTION "Delete-values"
                        ::= {  staPppstIpc 16 }

staPppstCcp OBJECT IDENTIFIER ::= { staPppst 10}
staPppstCcpRxdiscarded OBJECT-TYPE
                        SYNTAX INTEGER
                        ACCESS read-only
                        STATUS mandatory
                        DESCRIPTION "Rx-discarded"
                        ::= {  staPppstCcp 1 }

staPppstCcpRxconfigrequ OBJECT-TYPE
                        SYNTAX INTEGER
                        ACCESS read-only
                        STATUS mandatory
                        DESCRIPTION "Rx-config-request"
                        ::= {  staPppstCcp 2 }

staPppstCcpRxconfigack OBJECT-TYPE
                        SYNTAX INTEGER
                        ACCESS read-only
                        STATUS mandatory
                        DESCRIPTION "Rx-config-ack."
                        ::= {  staPppstCcp 3 }

staPppstCcpRxconfignak OBJECT-TYPE
                        SYNTAX INTEGER
                        ACCESS read-only
                        STATUS mandatory
                        DESCRIPTION "Rx-config-nak."
                        ::= {  staPppstCcp 4 }

staPppstCcpRxconfigreje OBJECT-TYPE
                        SYNTAX INTEGER
                        ACCESS read-only
                        STATUS mandatory
                        DESCRIPTION "Rx-config-reject"
                        ::= {  staPppstCcp 5 }

staPppstCcpRxterminater OBJECT-TYPE
                        SYNTAX INTEGER
                        ACCESS read-only
                        STATUS mandatory
                        DESCRIPTION "Rx-terminate-request"
                        ::= {  staPppstCcp 6 }

staPppstCcpRxterminatea OBJECT-TYPE
                        SYNTAX INTEGER
                        ACCESS read-only
                        STATUS mandatory
                        DESCRIPTION "Rx-terminate-ack."
                        ::= {  staPppstCcp 7 }

staPppstCcpRxcodereject OBJECT-TYPE
                        SYNTAX INTEGER
                        ACCESS read-only
                        STATUS mandatory
                        DESCRIPTION "Rx-code-reject"
                        ::= {  staPppstCcp 8 }

staPppstCcpRxresetreque OBJECT-TYPE
                        SYNTAX INTEGER
                        ACCESS read-only
                        STATUS mandatory
                        DESCRIPTION "Rx-reset-request"
                        ::= {  staPppstCcp 9 }

staPppstCcpRxresetack OBJECT-TYPE
                        SYNTAX INTEGER
                        ACCESS read-only
                        STATUS mandatory
                        DESCRIPTION "Rx-reset-ack"
                        ::= {  staPppstCcp 10 }

staPppstCcpTxconfigrequ OBJECT-TYPE
                        SYNTAX INTEGER
                        ACCESS read-only
                        STATUS mandatory
                        DESCRIPTION "Tx-config-request"
                        ::= {  staPppstCcp 11 }

staPppstCcpTxconfigack OBJECT-TYPE
                        SYNTAX INTEGER
                        ACCESS read-only
                        STATUS mandatory
                        DESCRIPTION "Tx-config-ack."
                        ::= {  staPppstCcp 12 }

staPppstCcpTxconfignak OBJECT-TYPE
                        SYNTAX INTEGER
                        ACCESS read-only
                        STATUS mandatory
                        DESCRIPTION "Tx-config-nak."
                        ::= {  staPppstCcp 13 }

staPppstCcpTxconfigreje OBJECT-TYPE
                        SYNTAX INTEGER
                        ACCESS read-only
                        STATUS mandatory
                        DESCRIPTION "Tx-config-reject"
                        ::= {  staPppstCcp 14 }

staPppstCcpTxterminater OBJECT-TYPE
                        SYNTAX INTEGER
                        ACCESS read-only
                        STATUS mandatory
                        DESCRIPTION "Tx-terminate-request"
                        ::= {  staPppstCcp 15 }

staPppstCcpTxterminatea OBJECT-TYPE
                        SYNTAX INTEGER
                        ACCESS read-only
                        STATUS mandatory
                        DESCRIPTION "Tx-terminate-ack."
                        ::= {  staPppstCcp 16 }

staPppstCcpTxcodereject OBJECT-TYPE
                        SYNTAX INTEGER
                        ACCESS read-only
                        STATUS mandatory
                        DESCRIPTION "Tx-code-reject"
                        ::= {  staPppstCcp 17 }

staPppstCcpTxresetreque OBJECT-TYPE
                        SYNTAX INTEGER
                        ACCESS read-only
                        STATUS mandatory
                        DESCRIPTION "Tx-reset-request"
                        ::= {  staPppstCcp 19 }

staPppstCcpTxresetack OBJECT-TYPE
                        SYNTAX INTEGER
                        ACCESS read-only
                        STATUS mandatory
                        DESCRIPTION "Tx-reset-ack"
                        ::= {  staPppstCcp 20 }

staPppstCcpCompressione OBJECT-TYPE
                        SYNTAX INTEGER
                        ACCESS read-only
                        STATUS mandatory
                        DESCRIPTION "Compression-errors"
                        ::= {  staPppstCcp 22 }

staPppstCcpDeletevalues OBJECT-TYPE
                        SYNTAX INTEGER
                        ACCESS write-only
                        STATUS mandatory
                        DESCRIPTION "Delete-values"
                        ::= {  staPppstCcp 21 }

staPppstMls OBJECT IDENTIFIER ::= { staPppst 11}
staPppstMlsBundlec OBJECT-TYPE
                   SYNTAX INTEGER
                   ACCESS read-only
                   STATUS mandatory
                   DESCRIPTION "Bundle-connections"
                   ::= {  staPppstMls 1 }

staPppstMlsRxseqlo OBJECT-TYPE
                   SYNTAX INTEGER
                   ACCESS read-only
                   STATUS mandatory
                   DESCRIPTION "Rx-Seq-lost"
                   ::= {  staPppstMls 2 }

staPppstMlsRxseqre OBJECT-TYPE
                   SYNTAX INTEGER
                   ACCESS read-only
                   STATUS mandatory
                   DESCRIPTION "Rx-Seq-repeat"
                   ::= {  staPppstMls 3 }

staPppstMlsRxmrrue OBJECT-TYPE
                   SYNTAX INTEGER
                   ACCESS read-only
                   STATUS mandatory
                   DESCRIPTION "Rx-Mrru-exceeded"
                   ::= {  staPppstMls 4 }

staPppstMlsRxheade OBJECT-TYPE
                   SYNTAX INTEGER
                   ACCESS read-only
                   STATUS mandatory
                   DESCRIPTION "Rx-Header-error"
                   ::= {  staPppstMls 5 }

staPppstMlsRxdisca OBJECT-TYPE
                   SYNTAX INTEGER
                   ACCESS read-only
                   STATUS mandatory
                   DESCRIPTION "Rx-discarded"
                   ::= {  staPppstMls 6 }

staPppstMlsRxfrags OBJECT-TYPE
                   SYNTAX INTEGER
                   ACCESS read-only
                   STATUS mandatory
                   DESCRIPTION "Rx-Frag-start"
                   ::= {  staPppstMls 7 }

staPppstMlsRxfragm OBJECT-TYPE
                   SYNTAX INTEGER
                   ACCESS read-only
                   STATUS mandatory
                   DESCRIPTION "Rx-Frag-mid"
                   ::= {  staPppstMls 8 }

staPppstMlsRxfrage OBJECT-TYPE
                   SYNTAX INTEGER
                   ACCESS read-only
                   STATUS mandatory
                   DESCRIPTION "Rx-Frag-end"
                   ::= {  staPppstMls 9 }

staPppstMlsRxnotfr OBJECT-TYPE
                   SYNTAX INTEGER
                   ACCESS read-only
                   STATUS mandatory
                   DESCRIPTION "Rx-not-fragmented"
                   ::= {  staPppstMls 10 }

staPppstMlsDeletev OBJECT-TYPE
                   SYNTAX INTEGER
                   ACCESS write-only
                   STATUS mandatory
                   DESCRIPTION "Delete-values"
                   ::= {  staPppstMls 11 }

staPppstBac OBJECT IDENTIFIER ::= { staPppst 12}
staPppstBacRxerrors OBJECT-TYPE
                         SYNTAX INTEGER
                         ACCESS read-only
                         STATUS mandatory
                         DESCRIPTION "Rx-errors"
                         ::= {  staPppstBac 1 }

staPppstBacRxdiscarded OBJECT-TYPE
                         SYNTAX INTEGER
                         ACCESS read-only
                         STATUS mandatory
                         DESCRIPTION "Rx-discarded"
                         ::= {  staPppstBac 2 }

staPppstBacRxcallrequest OBJECT-TYPE
                         SYNTAX INTEGER
                         ACCESS read-only
                         STATUS mandatory
                         DESCRIPTION "Rx-call-request"
                         ::= {  staPppstBac 3 }

staPppstBacRxcallrespons OBJECT-TYPE
                         SYNTAX INTEGER
                         ACCESS read-only
                         STATUS mandatory
                         DESCRIPTION "Rx-call-response"
                         ::= {  staPppstBac 4 }

staPppstBacRxcallbackreq OBJECT-TYPE
                         SYNTAX INTEGER
                         ACCESS read-only
                         STATUS mandatory
                         DESCRIPTION "Rx-callback-request"
                         ::= {  staPppstBac 5 }

staPppstBacRxcallbackres OBJECT-TYPE
                         SYNTAX INTEGER
                         ACCESS read-only
                         STATUS mandatory
                         DESCRIPTION "Rx-callback-response"
                         ::= {  staPppstBac 6 }

staPppstBacRxlinkdropreq OBJECT-TYPE
                         SYNTAX INTEGER
                         ACCESS read-only
                         STATUS mandatory
                         DESCRIPTION "Rx-link-Drop-request"
                         ::= {  staPppstBac 7 }

staPppstBacRxlinkdropres OBJECT-TYPE
                         SYNTAX INTEGER
                         ACCESS read-only
                         STATUS mandatory
                         DESCRIPTION "Rx-link-Drop-response"
                         ::= {  staPppstBac 8 }

staPppstBacRxstatusindic OBJECT-TYPE
                         SYNTAX INTEGER
                         ACCESS read-only
                         STATUS mandatory
                         DESCRIPTION "Rx-status-indicaion"
                         ::= {  staPppstBac 9 }

staPppstBacRxstatusreson OBJECT-TYPE
                         SYNTAX INTEGER
                         ACCESS read-only
                         STATUS mandatory
                         DESCRIPTION "Rx-status-resonse"
                         ::= {  staPppstBac 10 }

staPppstBacTxcallrequest OBJECT-TYPE
                         SYNTAX INTEGER
                         ACCESS read-only
                         STATUS mandatory
                         DESCRIPTION "Tx-call-request"
                         ::= {  staPppstBac 11 }

staPppstBacTxcallrespons OBJECT-TYPE
                         SYNTAX INTEGER
                         ACCESS read-only
                         STATUS mandatory
                         DESCRIPTION "Tx-call-response"
                         ::= {  staPppstBac 12 }

staPppstBacTxcallbackreq OBJECT-TYPE
                         SYNTAX INTEGER
                         ACCESS read-only
                         STATUS mandatory
                         DESCRIPTION "Tx-callback-request"
                         ::= {  staPppstBac 13 }

staPppstBacTxcallbackres OBJECT-TYPE
                         SYNTAX INTEGER
                         ACCESS read-only
                         STATUS mandatory
                         DESCRIPTION "Tx-callback-response"
                         ::= {  staPppstBac 14 }

staPppstBacTxlinkdropreq OBJECT-TYPE
                         SYNTAX INTEGER
                         ACCESS read-only
                         STATUS mandatory
                         DESCRIPTION "Tx-link-Drop-request"
                         ::= {  staPppstBac 15 }

staPppstBacTxlinkdropres OBJECT-TYPE
                         SYNTAX INTEGER
                         ACCESS read-only
                         STATUS mandatory
                         DESCRIPTION "Tx-link-Drop-response"
                         ::= {  staPppstBac 16 }

staPppstBacTxstatusindic OBJECT-TYPE
                         SYNTAX INTEGER
                         ACCESS read-only
                         STATUS mandatory
                         DESCRIPTION "Tx-status-indicaion"
                         ::= {  staPppstBac 17 }

staPppstBacTxstatusreson OBJECT-TYPE
                         SYNTAX INTEGER
                         ACCESS read-only
                         STATUS mandatory
                         DESCRIPTION "Tx-status-resonse"
                         ::= {  staPppstBac 18 }

staPppstBacDeletevalues OBJECT-TYPE
                         SYNTAX INTEGER
                         ACCESS write-only
                         STATUS mandatory
                         DESCRIPTION "Delete-values"
                         ::= {  staPppstBac 19 }

staPppstRxo OBJECT IDENTIFIER ::= { staPppst 8}
staPppstRxoLcp OBJECT-TYPE
               SYNTAX SEQUENCE OF StaPppstRxoLcpRows
               ACCESS not-accessible
               STATUS mandatory
               DESCRIPTION "LCP"
               ::= {  staPppstRxo 1 }

staPppstRxoLcpCols OBJECT-TYPE
               SYNTAX StaPppstRxoLcpRows
               ACCESS not-accessible
               STATUS mandatory
               DESCRIPTION "entry in table"
               INDEX { staPppstRxoLcpIfc }
               ::= {  staPppstRxoLcp 1 }

StaPppstRxoLcpRows ::= SEQUENCE {
               staPppstRxoLcpIfc INTEGER,
               staPppstRxoLcpMru INTEGER,
               staPppstRxoLcpAcc DisplayString,
               staPppstRxoLcpAut INTEGER,
               staPppstRxoLcpMag DisplayString,
               staPppstRxoLcpPfc INTEGER,
               staPppstRxoLcpAcf INTEGER,
               staPppstRxoLcpCal INTEGER
              }

staPppstRxoLcpIfc OBJECT-TYPE
                  SYNTAX INTEGER {
                    ch01(1),
                    ch02(2),
                    ch03(3),
                    ch04(4),
                    ch05(5),
                    ch06(6),
                    ch07(7),
                    ch08(8),
                    ch09(9),
                    ch10(10),
                    ch11(11),
                    ch12(12)
                  }
                  ACCESS read-only
                  STATUS mandatory
                  DESCRIPTION "Ifc"
                  ::= {  staPppstRxoLcpCols 1 }

staPppstRxoLcpMru OBJECT-TYPE
                  SYNTAX INTEGER
                  ACCESS read-only
                  STATUS mandatory
                  DESCRIPTION "MRU"
                  ::= {  staPppstRxoLcpCols 2 }

staPppstRxoLcpAcc OBJECT-TYPE
                  SYNTAX DisplayString
                  ACCESS read-only
                  STATUS mandatory
                  DESCRIPTION "ACCM"
                  ::= {  staPppstRxoLcpCols 3 }

staPppstRxoLcpAut OBJECT-TYPE
                  SYNTAX INTEGER {
                    none(0),
                    chap(8),
                    pap(4)
                  }
                  ACCESS read-only
                  STATUS mandatory
                  DESCRIPTION "Authent."
                  ::= {  staPppstRxoLcpCols 4 }

staPppstRxoLcpMag OBJECT-TYPE
                  SYNTAX DisplayString
                  ACCESS read-only
                  STATUS mandatory
                  DESCRIPTION "Magic-Num"
                  ::= {  staPppstRxoLcpCols 6 }

staPppstRxoLcpPfc OBJECT-TYPE
                  SYNTAX INTEGER {
                    yes(1),
                    no(0)
                  }
                  ACCESS read-only
                  STATUS mandatory
                  DESCRIPTION "PFC"
                  ::= {  staPppstRxoLcpCols 7 }

staPppstRxoLcpAcf OBJECT-TYPE
                  SYNTAX INTEGER {
                    yes(1),
                    no(0)
                  }
                  ACCESS read-only
                  STATUS mandatory
                  DESCRIPTION "ACFC"
                  ::= {  staPppstRxoLcpCols 8 }

staPppstRxoLcpCal OBJECT-TYPE
                  SYNTAX INTEGER {
                    none(0),
                    none(255),
                    lcp(1),
                    lcp(2),
                    lcp(3),
                    lcp(4),
                    lcp(5),
                    cbcp(6)
                  }
                  ACCESS read-only
                  STATUS mandatory
                  DESCRIPTION "Call-back"
                  ::= {  staPppstRxoLcpCols 5 }

staPppstRxoIpx OBJECT-TYPE
               SYNTAX SEQUENCE OF StaPppstRxoIpxRows
               ACCESS not-accessible
               STATUS mandatory
               DESCRIPTION "IPXCP"
               ::= {  staPppstRxo 2 }

staPppstRxoIpxCols OBJECT-TYPE
               SYNTAX StaPppstRxoIpxRows
               ACCESS not-accessible
               STATUS mandatory
               DESCRIPTION "entry in table"
               INDEX { staPppstRxoIpxIfc }
               ::= {  staPppstRxoIpx 1 }

StaPppstRxoIpxRows ::= SEQUENCE {
               staPppstRxoIpxIfc INTEGER,
               staPppstRxoIpxNet DisplayString,
               staPppstRxoIpxNod DisplayString,
               staPppstRxoIpxRou INTEGER
              }

staPppstRxoIpxIfc OBJECT-TYPE
                  SYNTAX INTEGER {
                    ch01(1),
                    ch02(2),
                    ch03(3),
                    ch04(4),
                    ch05(5),
                    ch06(6),
                    ch07(7),
                    ch08(8),
                    ch09(9),
                    ch10(10),
                    ch11(11),
                    ch12(12)
                  }
                  ACCESS read-only
                  STATUS mandatory
                  DESCRIPTION "Ifc"
                  ::= {  staPppstRxoIpxCols 1 }

staPppstRxoIpxNet OBJECT-TYPE
                  SYNTAX DisplayString
                  ACCESS read-only
                  STATUS mandatory
                  DESCRIPTION "Network"
                  ::= {  staPppstRxoIpxCols 2 }

staPppstRxoIpxNod OBJECT-TYPE
                  SYNTAX DisplayString
                  ACCESS read-only
                  STATUS mandatory
                  DESCRIPTION "Node-ID"
                  ::= {  staPppstRxoIpxCols 3 }

staPppstRxoIpxRou OBJECT-TYPE
                  SYNTAX INTEGER {
                    none(0),
                    rip-sap(2),
                    nlsp(4)
                  }
                  ACCESS read-only
                  STATUS mandatory
                  DESCRIPTION "Routing-method"
                  ::= {  staPppstRxoIpxCols 4 }

staPppstRxoIpc OBJECT-TYPE
               SYNTAX SEQUENCE OF StaPppstRxoIpcRows
               ACCESS not-accessible
               STATUS mandatory
               DESCRIPTION "IPCP"
               ::= {  staPppstRxo 3 }

staPppstRxoIpcCols OBJECT-TYPE
               SYNTAX StaPppstRxoIpcRows
               ACCESS not-accessible
               STATUS mandatory
               DESCRIPTION "entry in table"
               INDEX { staPppstRxoIpcIfc }
               ::= {  staPppstRxoIpc 1 }

StaPppstRxoIpcRows ::= SEQUENCE {
               staPppstRxoIpcIfc INTEGER,
               staPppstRxoIpcIpa IpAddress,
               staPppstRxoIpcDns IpAddress,
               staPppstRxoIpcNbn IpAddress
              }

staPppstRxoIpcIfc OBJECT-TYPE
                  SYNTAX INTEGER {
                    ch01(1),
                    ch02(2),
                    ch03(3),
                    ch04(4),
                    ch05(5),
                    ch06(6),
                    ch07(7),
                    ch08(8),
                    ch09(9),
                    ch10(10),
                    ch11(11),
                    ch12(12)
                  }
                  ACCESS read-only
                  STATUS mandatory
                  DESCRIPTION "Ifc"
                  ::= {  staPppstRxoIpcCols 1 }

staPppstRxoIpcIpa OBJECT-TYPE
                  SYNTAX IpAddress
                  ACCESS read-only
                  STATUS mandatory
                  DESCRIPTION "IP-address"
                  ::= {  staPppstRxoIpcCols 2 }

staPppstRxoIpcDns OBJECT-TYPE
                  SYNTAX IpAddress
                  ACCESS read-only
                  STATUS mandatory
                  DESCRIPTION "DNS-default"
                  ::= {  staPppstRxoIpcCols 3 }

staPppstRxoIpcNbn OBJECT-TYPE
                  SYNTAX IpAddress
                  ACCESS read-only
                  STATUS mandatory
                  DESCRIPTION "NBNS-default"
                  ::= {  staPppstRxoIpcCols 4 }

staPppstTxo OBJECT IDENTIFIER ::= { staPppst 9}
staPppstTxoLcp OBJECT-TYPE
               SYNTAX SEQUENCE OF StaPppstTxoLcpRows
               ACCESS not-accessible
               STATUS mandatory
               DESCRIPTION "LCP"
               ::= {  staPppstTxo 1 }

staPppstTxoLcpCols OBJECT-TYPE
               SYNTAX StaPppstTxoLcpRows
               ACCESS not-accessible
               STATUS mandatory
               DESCRIPTION "entry in table"
               INDEX { staPppstTxoLcpIfc }
               ::= {  staPppstTxoLcp 1 }

StaPppstTxoLcpRows ::= SEQUENCE {
               staPppstTxoLcpIfc INTEGER,
               staPppstTxoLcpMru INTEGER,
               staPppstTxoLcpAcc DisplayString,
               staPppstTxoLcpAut INTEGER,
               staPppstTxoLcpMag DisplayString,
               staPppstTxoLcpPfc INTEGER,
               staPppstTxoLcpAcf INTEGER,
               staPppstTxoLcpCal INTEGER
              }

staPppstTxoLcpIfc OBJECT-TYPE
                  SYNTAX INTEGER {
                    ch01(1),
                    ch02(2),
                    ch03(3),
                    ch04(4),
                    ch05(5),
                    ch06(6),
                    ch07(7),
                    ch08(8),
                    ch09(9),
                    ch10(10),
                    ch11(11),
                    ch12(12)
                  }
                  ACCESS read-only
                  STATUS mandatory
                  DESCRIPTION "Ifc"
                  ::= {  staPppstTxoLcpCols 1 }

staPppstTxoLcpMru OBJECT-TYPE
                  SYNTAX INTEGER
                  ACCESS read-only
                  STATUS mandatory
                  DESCRIPTION "MRU"
                  ::= {  staPppstTxoLcpCols 2 }

staPppstTxoLcpAcc OBJECT-TYPE
                  SYNTAX DisplayString
                  ACCESS read-only
                  STATUS mandatory
                  DESCRIPTION "ACCM"
                  ::= {  staPppstTxoLcpCols 3 }

staPppstTxoLcpAut OBJECT-TYPE
                  SYNTAX INTEGER {
                    none(0),
                    chap(8),
                    pap(4)
                  }
                  ACCESS read-only
                  STATUS mandatory
                  DESCRIPTION "Authent."
                  ::= {  staPppstTxoLcpCols 4 }

staPppstTxoLcpMag OBJECT-TYPE
                  SYNTAX DisplayString
                  ACCESS read-only
                  STATUS mandatory
                  DESCRIPTION "Magic-Num"
                  ::= {  staPppstTxoLcpCols 6 }

staPppstTxoLcpPfc OBJECT-TYPE
                  SYNTAX INTEGER {
                    yes(1),
                    no(0)
                  }
                  ACCESS read-only
                  STATUS mandatory
                  DESCRIPTION "PFC"
                  ::= {  staPppstTxoLcpCols 7 }

staPppstTxoLcpAcf OBJECT-TYPE
                  SYNTAX INTEGER {
                    yes(1),
                    no(0)
                  }
                  ACCESS read-only
                  STATUS mandatory
                  DESCRIPTION "ACFC"
                  ::= {  staPppstTxoLcpCols 8 }

staPppstTxoLcpCal OBJECT-TYPE
                  SYNTAX INTEGER {
                    none(0),
                    none(255),
                    lcp(1),
                    lcp(2),
                    lcp(3),
                    lcp(4),
                    lcp(5),
                    cbcp(6)
                  }
                  ACCESS read-only
                  STATUS mandatory
                  DESCRIPTION "Call-back"
                  ::= {  staPppstTxoLcpCols 5 }

staPppstTxoIpx OBJECT-TYPE
               SYNTAX SEQUENCE OF StaPppstTxoIpxRows
               ACCESS not-accessible
               STATUS mandatory
               DESCRIPTION "IPXCP"
               ::= {  staPppstTxo 2 }

staPppstTxoIpxCols OBJECT-TYPE
               SYNTAX StaPppstTxoIpxRows
               ACCESS not-accessible
               STATUS mandatory
               DESCRIPTION "entry in table"
               INDEX { staPppstTxoIpxIfc }
               ::= {  staPppstTxoIpx 1 }

StaPppstTxoIpxRows ::= SEQUENCE {
               staPppstTxoIpxIfc INTEGER,
               staPppstTxoIpxNet DisplayString,
               staPppstTxoIpxNod DisplayString,
               staPppstTxoIpxRou INTEGER
              }

staPppstTxoIpxIfc OBJECT-TYPE
                  SYNTAX INTEGER {
                    ch01(1),
                    ch02(2),
                    ch03(3),
                    ch04(4),
                    ch05(5),
                    ch06(6),
                    ch07(7),
                    ch08(8),
                    ch09(9),
                    ch10(10),
                    ch11(11),
                    ch12(12)
                  }
                  ACCESS read-only
                  STATUS mandatory
                  DESCRIPTION "Ifc"
                  ::= {  staPppstTxoIpxCols 1 }

staPppstTxoIpxNet OBJECT-TYPE
                  SYNTAX DisplayString
                  ACCESS read-only
                  STATUS mandatory
                  DESCRIPTION "Network"
                  ::= {  staPppstTxoIpxCols 2 }

staPppstTxoIpxNod OBJECT-TYPE
                  SYNTAX DisplayString
                  ACCESS read-only
                  STATUS mandatory
                  DESCRIPTION "Node-ID"
                  ::= {  staPppstTxoIpxCols 3 }

staPppstTxoIpxRou OBJECT-TYPE
                  SYNTAX INTEGER {
                    none(0),
                    rip-sap(2),
                    nlsp(4)
                  }
                  ACCESS read-only
                  STATUS mandatory
                  DESCRIPTION "Routing-method"
                  ::= {  staPppstTxoIpxCols 4 }

staPppstTxoIpc OBJECT-TYPE
               SYNTAX SEQUENCE OF StaPppstTxoIpcRows
               ACCESS not-accessible
               STATUS mandatory
               DESCRIPTION "IPCP"
               ::= {  staPppstTxo 3 }

staPppstTxoIpcCols OBJECT-TYPE
               SYNTAX StaPppstTxoIpcRows
               ACCESS not-accessible
               STATUS mandatory
               DESCRIPTION "entry in table"
               INDEX { staPppstTxoIpcIfc }
               ::= {  staPppstTxoIpc 1 }

StaPppstTxoIpcRows ::= SEQUENCE {
               staPppstTxoIpcIfc INTEGER,
               staPppstTxoIpcIpa IpAddress,
               staPppstTxoIpcDns IpAddress,
               staPppstTxoIpcNbn IpAddress
              }

staPppstTxoIpcIfc OBJECT-TYPE
                  SYNTAX INTEGER {
                    ch01(1),
                    ch02(2),
                    ch03(3),
                    ch04(4),
                    ch05(5),
                    ch06(6),
                    ch07(7),
                    ch08(8),
                    ch09(9),
                    ch10(10),
                    ch11(11),
                    ch12(12)
                  }
                  ACCESS read-only
                  STATUS mandatory
                  DESCRIPTION "Ifc"
                  ::= {  staPppstTxoIpcCols 1 }

staPppstTxoIpcIpa OBJECT-TYPE
                  SYNTAX IpAddress
                  ACCESS read-only
                  STATUS mandatory
                  DESCRIPTION "IP-address"
                  ::= {  staPppstTxoIpcCols 2 }

staPppstTxoIpcDns OBJECT-TYPE
                  SYNTAX IpAddress
                  ACCESS read-only
                  STATUS mandatory
                  DESCRIPTION "DNS-default"
                  ::= {  staPppstTxoIpcCols 3 }

staPppstTxoIpcNbn OBJECT-TYPE
                  SYNTAX IpAddress
                  ACCESS read-only
                  STATUS mandatory
                  DESCRIPTION "NBNS-default"
                  ::= {  staPppstTxoIpcCols 4 }

staPppstDel OBJECT-TYPE
            SYNTAX INTEGER
            ACCESS write-only
            STATUS mandatory
            DESCRIPTION "Delete-values"
            ::= {  staPppst 13 }

staBridg OBJECT IDENTIFIER ::= { sta 7}
staBridgBrglanr OBJECT-TYPE
                SYNTAX INTEGER
                ACCESS read-only
                STATUS mandatory
                DESCRIPTION "Brg-LAN-rx"
                ::= {  staBridg 1 }

staBridgBrglant OBJECT-TYPE
                SYNTAX INTEGER
                ACCESS read-only
                STATUS mandatory
                DESCRIPTION "Brg-LAN-tx"
                ::= {  staBridg 2 }

staBridgBrglanf OBJECT-TYPE
                SYNTAX INTEGER
                ACCESS read-only
                STATUS mandatory
                DESCRIPTION "Brg-LAN-filters"
                ::= {  staBridg 3 }

staBridgBrglanb OBJECT-TYPE
                SYNTAX INTEGER
                ACCESS read-only
                STATUS mandatory
                DESCRIPTION "Brg-LAN-broadcasts"
                ::= {  staBridg 4 }

staBridgBrglanm OBJECT-TYPE
                SYNTAX INTEGER
                ACCESS read-only
                STATUS mandatory
                DESCRIPTION "Brg-LAN-multicasts"
                ::= {  staBridg 5 }

staBridgBrgwanr OBJECT-TYPE
                SYNTAX INTEGER
                ACCESS read-only
                STATUS mandatory
                DESCRIPTION "Brg-WAN-rx"
                ::= {  staBridg 6 }

staBridgBrgwant OBJECT-TYPE
                SYNTAX INTEGER
                ACCESS read-only
                STATUS mandatory
                DESCRIPTION "Brg-WAN-tx"
                ::= {  staBridg 7 }

staBridgBrgwanf OBJECT-TYPE
                SYNTAX INTEGER
                ACCESS read-only
                STATUS mandatory
                DESCRIPTION "Brg-WAN-filters"
                ::= {  staBridg 8 }

staBridgBrgwanb OBJECT-TYPE
                SYNTAX INTEGER
                ACCESS read-only
                STATUS mandatory
                DESCRIPTION "Brg-WAN-broadcasts"
                ::= {  staBridg 9 }

staBridgBrgwanm OBJECT-TYPE
                SYNTAX INTEGER
                ACCESS read-only
                STATUS mandatory
                DESCRIPTION "Brg-WAN-multicasts"
                ::= {  staBridg 10 }

staBridgBrgaddr OBJECT-TYPE
                SYNTAX INTEGER
                ACCESS read-only
                STATUS mandatory
                DESCRIPTION "Brg-addresses"
                ::= {  staBridg 11 }

staBridgTablebr OBJECT-TYPE
                SYNTAX SEQUENCE OF StaBridgTablebrRows
                ACCESS not-accessible
                STATUS mandatory
                DESCRIPTION "Table-bridge"
                ::= {  staBridg 12 }

staBridgTablebrCols OBJECT-TYPE
                SYNTAX StaBridgTablebrRows
                ACCESS not-accessible
                STATUS mandatory
                DESCRIPTION "entry in table"
                INDEX { staBridgTablebrNod }
                ::= {  staBridgTablebr 1 }

StaBridgTablebrRows ::= SEQUENCE {
                staBridgTablebrNod DisplayString,
                staBridgTablebrLas INTEGER,
                staBridgTablebrFor DisplayString
               }

staBridgTablebrNod OBJECT-TYPE
                   SYNTAX DisplayString
                   ACCESS read-only
                   STATUS mandatory
                   DESCRIPTION "Node-ID"
                   ::= {  staBridgTablebrCols 1 }

staBridgTablebrLas OBJECT-TYPE
                   SYNTAX INTEGER
                   ACCESS read-only
                   STATUS mandatory
                   DESCRIPTION "Last-access"
                   ::= {  staBridgTablebrCols 2 }

staBridgTablebrFor OBJECT-TYPE
                   SYNTAX DisplayString
                   ACCESS read-only
                   STATUS mandatory
                   DESCRIPTION "Forward-Flag"
                   ::= {  staBridgTablebrCols 3 }

staBridgEstabli OBJECT-TYPE
                SYNTAX SEQUENCE OF StaBridgEstabliRows
                ACCESS not-accessible
                STATUS mandatory
                DESCRIPTION "Establish-table"
                ::= {  staBridg 13 }

staBridgEstabliCols OBJECT-TYPE
                SYNTAX StaBridgEstabliRows
                ACCESS not-accessible
                STATUS mandatory
                DESCRIPTION "entry in table"
                INDEX { staBridgEstabliTim }
                ::= {  staBridgEstabli 1 }

StaBridgEstabliRows ::= SEQUENCE {
                staBridgEstabliTim DisplayString,
                staBridgEstabliDes DisplayString,
                staBridgEstabliSou DisplayString
               }

staBridgEstabliTim OBJECT-TYPE
                   SYNTAX DisplayString
                   ACCESS read-only
                   STATUS mandatory
                   DESCRIPTION "Time"
                   ::= {  staBridgEstabliCols 1 }

staBridgEstabliDes OBJECT-TYPE
                   SYNTAX DisplayString
                   ACCESS read-only
                   STATUS mandatory
                   DESCRIPTION "Dest"
                   ::= {  staBridgEstabliCols 2 }

staBridgEstabliSou OBJECT-TYPE
                   SYNTAX DisplayString
                   ACCESS read-only
                   STATUS mandatory
                   DESCRIPTION "Source"
                   ::= {  staBridgEstabliCols 3 }

staBridgDeletev OBJECT-TYPE
                SYNTAX INTEGER
                ACCESS write-only
                STATUS mandatory
                DESCRIPTION "Delete-values"
                ::= {  staBridg 14 }

staIpxst OBJECT IDENTIFIER ::= { sta 8}
staIpxstMac OBJECT IDENTIFIER ::= { staIpxst 1}
staIpxstMacIpxlanrx OBJECT-TYPE
                     SYNTAX INTEGER
                     ACCESS read-only
                     STATUS mandatory
                     DESCRIPTION "IPX-LAN-rx"
                     ::= {  staIpxstMac 1 }

staIpxstMacIpxlanrxb OBJECT-TYPE
                     SYNTAX INTEGER
                     ACCESS read-only
                     STATUS mandatory
                     DESCRIPTION "IPX-LAN-rx-broadcasts"
                     ::= {  staIpxstMac 2 }

staIpxstMacIpxlanrxm OBJECT-TYPE
                     SYNTAX INTEGER
                     ACCESS read-only
                     STATUS mandatory
                     DESCRIPTION "IPX-LAN-rx-multicasts"
                     ::= {  staIpxstMac 3 }

staIpxstMacIpxlanrxu OBJECT-TYPE
                     SYNTAX INTEGER
                     ACCESS read-only
                     STATUS mandatory
                     DESCRIPTION "IPX-LAN-rx-unicasts"
                     ::= {  staIpxstMac 4 }

staIpxstMacIpxlantx OBJECT-TYPE
                     SYNTAX INTEGER
                     ACCESS read-only
                     STATUS mandatory
                     DESCRIPTION "IPX-LAN-tx"
                     ::= {  staIpxstMac 5 }

staIpxstMacIpxwanrx OBJECT-TYPE
                     SYNTAX INTEGER
                     ACCESS read-only
                     STATUS mandatory
                     DESCRIPTION "IPX-WAN-rx"
                     ::= {  staIpxstMac 6 }

staIpxstMacIpxwanrxb OBJECT-TYPE
                     SYNTAX INTEGER
                     ACCESS read-only
                     STATUS mandatory
                     DESCRIPTION "IPX-WAN-rx-broadcasts"
                     ::= {  staIpxstMac 7 }

staIpxstMacIpxwanrxm OBJECT-TYPE
                     SYNTAX INTEGER
                     ACCESS read-only
                     STATUS mandatory
                     DESCRIPTION "IPX-WAN-rx-multicasts"
                     ::= {  staIpxstMac 8 }

staIpxstMacIpxwanrxu OBJECT-TYPE
                     SYNTAX INTEGER
                     ACCESS read-only
                     STATUS mandatory
                     DESCRIPTION "IPX-WAN-rx-unicasts"
                     ::= {  staIpxstMac 9 }

staIpxstMacIpxwantx OBJECT-TYPE
                     SYNTAX INTEGER
                     ACCESS read-only
                     STATUS mandatory
                     DESCRIPTION "IPX-WAN-tx"
                     ::= {  staIpxstMac 10 }

staIpxstMacDeleteval OBJECT-TYPE
                     SYNTAX INTEGER
                     ACCESS write-only
                     STATUS mandatory
                     DESCRIPTION "Delete-values"
                     ::= {  staIpxstMac 11 }

staIpxstWat OBJECT IDENTIFIER ::= { staIpxst 2}
staIpxstWatIpxwatchdoglanr OBJECT-TYPE
                           SYNTAX INTEGER
                           ACCESS read-only
                           STATUS mandatory
                           DESCRIPTION "IPX-watchdog-LAN-rx"
                           ::= {  staIpxstWat 1 }

staIpxstWatIpxwatchdoglant OBJECT-TYPE
                           SYNTAX INTEGER
                           ACCESS read-only
                           STATUS mandatory
                           DESCRIPTION "IPX-watchdog-LAN-tx"
                           ::= {  staIpxstWat 2 }

staIpxstWatIpxwatchdogwanr OBJECT-TYPE
                           SYNTAX INTEGER
                           ACCESS read-only
                           STATUS mandatory
                           DESCRIPTION "IPX-watchdog-WAN-rx"
                           ::= {  staIpxstWat 3 }

staIpxstWatIpxwatchdogwant OBJECT-TYPE
                           SYNTAX INTEGER
                           ACCESS read-only
                           STATUS mandatory
                           DESCRIPTION "IPX-watchdog-WAN-tx"
                           ::= {  staIpxstWat 4 }

staIpxstWatSpxwatchdoglanr OBJECT-TYPE
                           SYNTAX INTEGER
                           ACCESS read-only
                           STATUS mandatory
                           DESCRIPTION "SPX-watchdog-LAN-rx"
                           ::= {  staIpxstWat 5 }

staIpxstWatSpxwatchdoglant OBJECT-TYPE
                           SYNTAX INTEGER
                           ACCESS read-only
                           STATUS mandatory
                           DESCRIPTION "SPX-watchdog-LAN-tx"
                           ::= {  staIpxstWat 6 }

staIpxstWatSpxwatchdogwanr OBJECT-TYPE
                           SYNTAX INTEGER
                           ACCESS read-only
                           STATUS mandatory
                           DESCRIPTION "SPX-watchdog-WAN-rx"
                           ::= {  staIpxstWat 7 }

staIpxstWatSpxwatchdogwant OBJECT-TYPE
                           SYNTAX INTEGER
                           ACCESS read-only
                           STATUS mandatory
                           DESCRIPTION "SPX-watchdog-WAN-tx"
                           ::= {  staIpxstWat 8 }

staIpxstWatDeletevalues OBJECT-TYPE
                           SYNTAX INTEGER
                           ACCESS write-only
                           STATUS mandatory
                           DESCRIPTION "Delete-values"
                           ::= {  staIpxstWat 9 }

staIpxstPro OBJECT IDENTIFIER ::= { staIpxst 3}
staIpxstProPropagatelanr OBJECT-TYPE
                         SYNTAX INTEGER
                         ACCESS read-only
                         STATUS mandatory
                         DESCRIPTION "Propagate-LAN-rx"
                         ::= {  staIpxstPro 1 }

staIpxstProPropagatelanf OBJECT-TYPE
                         SYNTAX INTEGER
                         ACCESS read-only
                         STATUS mandatory
                         DESCRIPTION "Propagate-LAN-filters"
                         ::= {  staIpxstPro 2 }

staIpxstProPropagatelant OBJECT-TYPE
                         SYNTAX INTEGER
                         ACCESS read-only
                         STATUS mandatory
                         DESCRIPTION "Propagate-LAN-tx"
                         ::= {  staIpxstPro 3 }

staIpxstProPropagatelans OBJECT-TYPE
                         SYNTAX INTEGER
                         ACCESS read-only
                         STATUS mandatory
                         DESCRIPTION "Propagate-LAN-socket-errors"
                         ::= {  staIpxstPro 4 }

staIpxstProPropagatelanh OBJECT-TYPE
                         SYNTAX INTEGER
                         ACCESS read-only
                         STATUS mandatory
                         DESCRIPTION "Propagate-LAN-hop-errors"
                         ::= {  staIpxstPro 5 }

staIpxstProPropagatelanb OBJECT-TYPE
                         SYNTAX INTEGER
                         ACCESS read-only
                         STATUS mandatory
                         DESCRIPTION "Propagate-LAN-backroute-errors"
                         ::= {  staIpxstPro 6 }

staIpxstProPropagatelanc OBJECT-TYPE
                         SYNTAX INTEGER
                         ACCESS read-only
                         STATUS mandatory
                         DESCRIPTION "Propagate-LAN-contention"
                         ::= {  staIpxstPro 7 }

staIpxstProPropagatewanr OBJECT-TYPE
                         SYNTAX INTEGER
                         ACCESS read-only
                         STATUS mandatory
                         DESCRIPTION "Propagate-WAN-rx"
                         ::= {  staIpxstPro 8 }

staIpxstProPropagatewanf OBJECT-TYPE
                         SYNTAX INTEGER
                         ACCESS read-only
                         STATUS mandatory
                         DESCRIPTION "Propagate-WAN-filters"
                         ::= {  staIpxstPro 9 }

staIpxstProPropagatewant OBJECT-TYPE
                         SYNTAX INTEGER
                         ACCESS read-only
                         STATUS mandatory
                         DESCRIPTION "Propagate-WAN-tx"
                         ::= {  staIpxstPro 10 }

staIpxstProPropagatewans OBJECT-TYPE
                         SYNTAX INTEGER
                         ACCESS read-only
                         STATUS mandatory
                         DESCRIPTION "Propagate-WAN-socket-errors"
                         ::= {  staIpxstPro 11 }

staIpxstProDeletevalues OBJECT-TYPE
                         SYNTAX INTEGER
                         ACCESS write-only
                         STATUS mandatory
                         DESCRIPTION "Delete-values"
                         ::= {  staIpxstPro 12 }

staIpxstRip OBJECT IDENTIFIER ::= { staIpxst 4}
staIpxstRipRiplanr OBJECT-TYPE
                   SYNTAX INTEGER
                   ACCESS read-only
                   STATUS mandatory
                   DESCRIPTION "RIP-LAN-rx"
                   ::= {  staIpxstRip 1 }

staIpxstRipRiplane OBJECT-TYPE
                   SYNTAX INTEGER
                   ACCESS read-only
                   STATUS mandatory
                   DESCRIPTION "RIP-LAN-errors"
                   ::= {  staIpxstRip 2 }

staIpxstRipRiplant OBJECT-TYPE
                   SYNTAX INTEGER
                   ACCESS read-only
                   STATUS mandatory
                   DESCRIPTION "RIP-LAN-tx"
                   ::= {  staIpxstRip 3 }

staIpxstRipRipwanr OBJECT-TYPE
                   SYNTAX INTEGER
                   ACCESS read-only
                   STATUS mandatory
                   DESCRIPTION "RIP-WAN-rx"
                   ::= {  staIpxstRip 4 }

staIpxstRipRipwane OBJECT-TYPE
                   SYNTAX INTEGER
                   ACCESS read-only
                   STATUS mandatory
                   DESCRIPTION "RIP-WAN-errors"
                   ::= {  staIpxstRip 5 }

staIpxstRipRipwant OBJECT-TYPE
                   SYNTAX INTEGER
                   ACCESS read-only
                   STATUS mandatory
                   DESCRIPTION "RIP-WAN-tx"
                   ::= {  staIpxstRip 6 }

staIpxstRipTableri OBJECT-TYPE
                   SYNTAX SEQUENCE OF StaIpxstRipTableriRows
                   ACCESS not-accessible
                   STATUS mandatory
                   DESCRIPTION "Table-RIP"
                   ::= {  staIpxstRip 7 }

staIpxstRipTableriCols OBJECT-TYPE
                   SYNTAX StaIpxstRipTableriRows
                   ACCESS not-accessible
                   STATUS mandatory
                   DESCRIPTION "entry in table"
                   INDEX { staIpxstRipTableriNet }
                   ::= {  staIpxstRipTableri 1 }

StaIpxstRipTableriRows ::= SEQUENCE {
                   staIpxstRipTableriNet DisplayString,
                   staIpxstRipTableriHop INTEGER,
                   staIpxstRipTableriTic INTEGER,
                   staIpxstRipTableriNod DisplayString,
                   staIpxstRipTableriTim INTEGER,
                   staIpxstRipTableriFla INTEGER
                  }

staIpxstRipTableriNet OBJECT-TYPE
                      SYNTAX DisplayString
                      ACCESS read-only
                      STATUS mandatory
                      DESCRIPTION "Network"
                      ::= {  staIpxstRipTableriCols 1 }

staIpxstRipTableriHop OBJECT-TYPE
                      SYNTAX INTEGER
                      ACCESS read-only
                      STATUS mandatory
                      DESCRIPTION "Hops"
                      ::= {  staIpxstRipTableriCols 2 }

staIpxstRipTableriTic OBJECT-TYPE
                      SYNTAX INTEGER
                      ACCESS read-only
                      STATUS mandatory
                      DESCRIPTION "Tics"
                      ::= {  staIpxstRipTableriCols 3 }

staIpxstRipTableriNod OBJECT-TYPE
                      SYNTAX DisplayString
                      ACCESS read-only
                      STATUS mandatory
                      DESCRIPTION "Node-ID"
                      ::= {  staIpxstRipTableriCols 4 }

staIpxstRipTableriTim OBJECT-TYPE
                      SYNTAX INTEGER
                      ACCESS read-only
                      STATUS mandatory
                      DESCRIPTION "Time"
                      ::= {  staIpxstRipTableriCols 5 }

staIpxstRipTableriFla OBJECT-TYPE
                      SYNTAX INTEGER {
                        local(2),
                        remote(1),
                        direct(128),
                        new(64),
                        down(32),
                        loop(16),
                        spare(8)
                      }
                      ACCESS read-only
                      STATUS mandatory
                      DESCRIPTION "Flags"
                      ::= {  staIpxstRipTableriCols 6 }

staIpxstRipDeletev OBJECT-TYPE
                   SYNTAX INTEGER
                   ACCESS write-only
                   STATUS mandatory
                   DESCRIPTION "Delete-values"
                   ::= {  staIpxstRip 8 }

staIpxstSap OBJECT IDENTIFIER ::= { staIpxst 5}
staIpxstSapSaplanr OBJECT-TYPE
                   SYNTAX INTEGER
                   ACCESS read-only
                   STATUS mandatory
                   DESCRIPTION "SAP-LAN-rx"
                   ::= {  staIpxstSap 1 }

staIpxstSapSaplane OBJECT-TYPE
                   SYNTAX INTEGER
                   ACCESS read-only
                   STATUS mandatory
                   DESCRIPTION "SAP-LAN-errors"
                   ::= {  staIpxstSap 2 }

staIpxstSapSaplant OBJECT-TYPE
                   SYNTAX INTEGER
                   ACCESS read-only
                   STATUS mandatory
                   DESCRIPTION "SAP-LAN-tx"
                   ::= {  staIpxstSap 3 }

staIpxstSapSapwanr OBJECT-TYPE
                   SYNTAX INTEGER
                   ACCESS read-only
                   STATUS mandatory
                   DESCRIPTION "SAP-WAN-rx"
                   ::= {  staIpxstSap 4 }

staIpxstSapSapwane OBJECT-TYPE
                   SYNTAX INTEGER
                   ACCESS read-only
                   STATUS mandatory
                   DESCRIPTION "SAP-WAN-errors"
                   ::= {  staIpxstSap 5 }

staIpxstSapSapwant OBJECT-TYPE
                   SYNTAX INTEGER
                   ACCESS read-only
                   STATUS mandatory
                   DESCRIPTION "SAP-WAN-tx"
                   ::= {  staIpxstSap 6 }

staIpxstSapTablesa OBJECT-TYPE
                   SYNTAX SEQUENCE OF StaIpxstSapTablesaRows
                   ACCESS not-accessible
                   STATUS mandatory
                   DESCRIPTION "Table-SAP"
                   ::= {  staIpxstSap 7 }

staIpxstSapTablesaCols OBJECT-TYPE
                   SYNTAX StaIpxstSapTablesaRows
                   ACCESS not-accessible
                   STATUS mandatory
                   DESCRIPTION "entry in table"
                   INDEX { staIpxstSapTablesaTyp }
                   ::= {  staIpxstSapTablesa 1 }

StaIpxstSapTablesaRows ::= SEQUENCE {
                   staIpxstSapTablesaTyp DisplayString,
                   staIpxstSapTablesaSer DisplayString,
                   staIpxstSapTablesaNet DisplayString,
                   staIpxstSapTablesaNod DisplayString,
                   staIpxstSapTablesaSoc DisplayString,
                   staIpxstSapTablesaHop INTEGER,
                   staIpxstSapTablesaTim INTEGER,
                   staIpxstSapTablesaFla INTEGER
                  }

staIpxstSapTablesaTyp OBJECT-TYPE
                      SYNTAX DisplayString
                      ACCESS read-only
                      STATUS mandatory
                      DESCRIPTION "Type"
                      ::= {  staIpxstSapTablesaCols 1 }

staIpxstSapTablesaSer OBJECT-TYPE
                      SYNTAX DisplayString
                      ACCESS read-only
                      STATUS mandatory
                      DESCRIPTION "Server-name"
                      ::= {  staIpxstSapTablesaCols 2 }

staIpxstSapTablesaNet OBJECT-TYPE
                      SYNTAX DisplayString
                      ACCESS read-only
                      STATUS mandatory
                      DESCRIPTION "Network"
                      ::= {  staIpxstSapTablesaCols 3 }

staIpxstSapTablesaNod OBJECT-TYPE
                      SYNTAX DisplayString
                      ACCESS read-only
                      STATUS mandatory
                      DESCRIPTION "Node-ID"
                      ::= {  staIpxstSapTablesaCols 4 }

staIpxstSapTablesaSoc OBJECT-TYPE
                      SYNTAX DisplayString
                      ACCESS read-only
                      STATUS mandatory
                      DESCRIPTION "Socket"
                      ::= {  staIpxstSapTablesaCols 5 }

staIpxstSapTablesaHop OBJECT-TYPE
                      SYNTAX INTEGER
                      ACCESS read-only
                      STATUS mandatory
                      DESCRIPTION "Hops"
                      ::= {  staIpxstSapTablesaCols 6 }

staIpxstSapTablesaTim OBJECT-TYPE
                      SYNTAX INTEGER
                      ACCESS read-only
                      STATUS mandatory
                      DESCRIPTION "Time"
                      ::= {  staIpxstSapTablesaCols 7 }

staIpxstSapTablesaFla OBJECT-TYPE
                      SYNTAX INTEGER {
                        local(2),
                        remote(1),
                        direct(128),
                        new(64),
                        down(32),
                        loop(16),
                        spare(8)
                      }
                      ACCESS read-only
                      STATUS mandatory
                      DESCRIPTION "Flags"
                      ::= {  staIpxstSapTablesaCols 8 }

staIpxstSapDeletev OBJECT-TYPE
                   SYNTAX INTEGER
                   ACCESS write-only
                   STATUS mandatory
                   DESCRIPTION "Delete-values"
                   ::= {  staIpxstSap 8 }

staIpxstIpx OBJECT IDENTIFIER ::= { staIpxst 6}
staIpxstIpxIpxrlanr OBJECT-TYPE
                    SYNTAX INTEGER
                    ACCESS read-only
                    STATUS mandatory
                    DESCRIPTION "IPXr-LAN-rx"
                    ::= {  staIpxstIpx 1 }

staIpxstIpxIpxrlant OBJECT-TYPE
                    SYNTAX INTEGER
                    ACCESS read-only
                    STATUS mandatory
                    DESCRIPTION "IPXr-LAN-tx"
                    ::= {  staIpxstIpx 2 }

staIpxstIpxIpxrlanh OBJECT-TYPE
                    SYNTAX INTEGER
                    ACCESS read-only
                    STATUS mandatory
                    DESCRIPTION "IPXr-LAN-hop-errors"
                    ::= {  staIpxstIpx 3 }

staIpxstIpxIpxrlans OBJECT-TYPE
                    SYNTAX INTEGER
                    ACCESS read-only
                    STATUS mandatory
                    DESCRIPTION "IPXr-LAN-socket-errors"
                    ::= {  staIpxstIpx 4 }

staIpxstIpxIpxrlann OBJECT-TYPE
                    SYNTAX INTEGER
                    ACCESS read-only
                    STATUS mandatory
                    DESCRIPTION "IPXr-LAN-net-errors"
                    ::= {  staIpxstIpx 5 }

staIpxstIpxIpxrlanb OBJECT-TYPE
                    SYNTAX INTEGER
                    ACCESS read-only
                    STATUS mandatory
                    DESCRIPTION "IPXr-LAN-backroute-errors"
                    ::= {  staIpxstIpx 6 }

staIpxstIpxIpxrlanc OBJECT-TYPE
                    SYNTAX INTEGER
                    ACCESS read-only
                    STATUS mandatory
                    DESCRIPTION "IPXr-LAN-contention"
                    ::= {  staIpxstIpx 7 }

staIpxstIpxIpxrland OBJECT-TYPE
                    SYNTAX INTEGER
                    ACCESS read-only
                    STATUS mandatory
                    DESCRIPTION "IPXr-LAN-down-errors"
                    ::= {  staIpxstIpx 8 }

staIpxstIpxIpxrwanr OBJECT-TYPE
                    SYNTAX INTEGER
                    ACCESS read-only
                    STATUS mandatory
                    DESCRIPTION "IPXr-WAN-rx"
                    ::= {  staIpxstIpx 9 }

staIpxstIpxIpxrwant OBJECT-TYPE
                    SYNTAX INTEGER
                    ACCESS read-only
                    STATUS mandatory
                    DESCRIPTION "IPXr-WAN-tx"
                    ::= {  staIpxstIpx 10 }

staIpxstIpxIpxrwanh OBJECT-TYPE
                    SYNTAX INTEGER
                    ACCESS read-only
                    STATUS mandatory
                    DESCRIPTION "IPXr-WAN-hop-errors"
                    ::= {  staIpxstIpx 11 }

staIpxstIpxIpxrwans OBJECT-TYPE
                    SYNTAX INTEGER
                    ACCESS read-only
                    STATUS mandatory
                    DESCRIPTION "IPXr-WAN-socket-errors"
                    ::= {  staIpxstIpx 12 }

staIpxstIpxIpxrwann OBJECT-TYPE
                    SYNTAX INTEGER
                    ACCESS read-only
                    STATUS mandatory
                    DESCRIPTION "IPXr-WAN-net-errors"
                    ::= {  staIpxstIpx 13 }

staIpxstIpxIpxrwanb OBJECT-TYPE
                    SYNTAX INTEGER
                    ACCESS read-only
                    STATUS mandatory
                    DESCRIPTION "IPXr-WAN-backroute-errors"
                    ::= {  staIpxstIpx 14 }

staIpxstIpxIpxrwand OBJECT-TYPE
                    SYNTAX INTEGER
                    ACCESS read-only
                    STATUS mandatory
                    DESCRIPTION "IPXr-WAN-down-errors"
                    ::= {  staIpxstIpx 15 }

staIpxstIpxIpxrinte OBJECT-TYPE
                    SYNTAX INTEGER
                    ACCESS read-only
                    STATUS mandatory
                    DESCRIPTION "IPXr-intern-rx"
                    ::= {  staIpxstIpx 16 }

staIpxstIpxNetworks OBJECT-TYPE
                    SYNTAX SEQUENCE OF StaIpxstIpxNetworksRows
                    ACCESS not-accessible
                    STATUS mandatory
                    DESCRIPTION "Networks"
                    ::= {  staIpxstIpx 17 }

staIpxstIpxNetworksCols OBJECT-TYPE
                    SYNTAX StaIpxstIpxNetworksRows
                    ACCESS not-accessible
                    STATUS mandatory
                    DESCRIPTION "entry in table"
                    INDEX { staIpxstIpxNetworksRem }
                    ::= {  staIpxstIpxNetworks 1 }

StaIpxstIpxNetworksRows ::= SEQUENCE {
                    staIpxstIpxNetworksRem DisplayString,
                    staIpxstIpxNetworksNet DisplayString,
                    staIpxstIpxNetworksBin INTEGER,
                    staIpxstIpxNetworksPro INTEGER,
                    staIpxstIpxNetworksBac INTEGER,
                    staIpxstIpxNetworksTim INTEGER,
                    staIpxstIpxNetworksNod DisplayString
                   }

staIpxstIpxNetworksRem OBJECT-TYPE
                       SYNTAX DisplayString
                       ACCESS read-only
                       STATUS mandatory
                       DESCRIPTION "Remote-ID"
                       ::= {  staIpxstIpxNetworksCols 1 }

staIpxstIpxNetworksNet OBJECT-TYPE
                       SYNTAX DisplayString
                       ACCESS read-only
                       STATUS mandatory
                       DESCRIPTION "Network"
                       ::= {  staIpxstIpxNetworksCols 2 }

staIpxstIpxNetworksBin OBJECT-TYPE
                       SYNTAX INTEGER {
                         auto(15),
                         auto(0),
                         ii(1),
                         dot802-3(2),
                         dot802-2(4),
                         snap(8)
                       }
                       ACCESS read-only
                       STATUS mandatory
                       DESCRIPTION "Binding"
                       ::= {  staIpxstIpxNetworksCols 3 }

staIpxstIpxNetworksPro OBJECT-TYPE
                       SYNTAX INTEGER {
                         filter(0),
                         route(3)
                       }
                       ACCESS read-only
                       STATUS mandatory
                       DESCRIPTION "Propagate"
                       ::= {  staIpxstIpxNetworksCols 4 }

staIpxstIpxNetworksBac OBJECT-TYPE
                       SYNTAX INTEGER
                       ACCESS read-only
                       STATUS mandatory
                       DESCRIPTION "Backoff"
                       ::= {  staIpxstIpxNetworksCols 5 }

staIpxstIpxNetworksTim OBJECT-TYPE
                       SYNTAX INTEGER
                       ACCESS read-only
                       STATUS mandatory
                       DESCRIPTION "Time"
                       ::= {  staIpxstIpxNetworksCols 6 }

staIpxstIpxNetworksNod OBJECT-TYPE
                       SYNTAX DisplayString
                       ACCESS read-only
                       STATUS mandatory
                       DESCRIPTION "Node-ID"
                       ::= {  staIpxstIpxNetworksCols 7 }

staIpxstIpxEstablis OBJECT-TYPE
                    SYNTAX SEQUENCE OF StaIpxstIpxEstablisRows
                    ACCESS not-accessible
                    STATUS mandatory
                    DESCRIPTION "Establish-table"
                    ::= {  staIpxstIpx 18 }

staIpxstIpxEstablisCols OBJECT-TYPE
                    SYNTAX StaIpxstIpxEstablisRows
                    ACCESS not-accessible
                    STATUS mandatory
                    DESCRIPTION "entry in table"
                    INDEX { staIpxstIpxEstablisTime }
                    ::= {  staIpxstIpxEstablis 1 }

StaIpxstIpxEstablisRows ::= SEQUENCE {
                    staIpxstIpxEstablisTime DisplayString,
                    staIpxstIpxEstablisDestnet DisplayString,
                    staIpxstIpxEstablisDestnode DisplayString,
                    staIpxstIpxEstablisDestsock DisplayString,
                    staIpxstIpxEstablisSourcene DisplayString,
                    staIpxstIpxEstablisSourceno DisplayString,
                    staIpxstIpxEstablisSourceso DisplayString
                   }

staIpxstIpxEstablisTime OBJECT-TYPE
                            SYNTAX DisplayString
                            ACCESS read-only
                            STATUS mandatory
                            DESCRIPTION "Time"
                            ::= {  staIpxstIpxEstablisCols 1 }

staIpxstIpxEstablisDestnet OBJECT-TYPE
                            SYNTAX DisplayString
                            ACCESS read-only
                            STATUS mandatory
                            DESCRIPTION "Dest.-net"
                            ::= {  staIpxstIpxEstablisCols 2 }

staIpxstIpxEstablisDestnode OBJECT-TYPE
                            SYNTAX DisplayString
                            ACCESS read-only
                            STATUS mandatory
                            DESCRIPTION "Dest.-node"
                            ::= {  staIpxstIpxEstablisCols 3 }

staIpxstIpxEstablisDestsock OBJECT-TYPE
                            SYNTAX DisplayString
                            ACCESS read-only
                            STATUS mandatory
                            DESCRIPTION "Dest.-socket"
                            ::= {  staIpxstIpxEstablisCols 4 }

staIpxstIpxEstablisSourcene OBJECT-TYPE
                            SYNTAX DisplayString
                            ACCESS read-only
                            STATUS mandatory
                            DESCRIPTION "Source-net"
                            ::= {  staIpxstIpxEstablisCols 5 }

staIpxstIpxEstablisSourceno OBJECT-TYPE
                            SYNTAX DisplayString
                            ACCESS read-only
                            STATUS mandatory
                            DESCRIPTION "Source-node"
                            ::= {  staIpxstIpxEstablisCols 6 }

staIpxstIpxEstablisSourceso OBJECT-TYPE
                            SYNTAX DisplayString
                            ACCESS read-only
                            STATUS mandatory
                            DESCRIPTION "Source-socket"
                            ::= {  staIpxstIpxEstablisCols 7 }

staIpxstIpxDeleteva OBJECT-TYPE
                    SYNTAX INTEGER
                    ACCESS write-only
                    STATUS mandatory
                    DESCRIPTION "Delete-values"
                    ::= {  staIpxstIpx 19 }

staIpxstDel OBJECT-TYPE
            SYNTAX INTEGER
            ACCESS write-only
            STATUS mandatory
            DESCRIPTION "Delete-values"
            ::= {  staIpxst 7 }

staTcpip OBJECT IDENTIFIER ::= { sta 9}
staTcpipArp OBJECT IDENTIFIER ::= { staTcpip 1}
staTcpipArpArplanr OBJECT-TYPE
                   SYNTAX INTEGER
                   ACCESS read-only
                   STATUS mandatory
                   DESCRIPTION "ARP-LAN-rx"
                   ::= {  staTcpipArp 1 }

staTcpipArpArplant OBJECT-TYPE
                   SYNTAX INTEGER
                   ACCESS read-only
                   STATUS mandatory
                   DESCRIPTION "ARP-LAN-tx"
                   ::= {  staTcpipArp 2 }

staTcpipArpArplane OBJECT-TYPE
                   SYNTAX INTEGER
                   ACCESS read-only
                   STATUS mandatory
                   DESCRIPTION "ARP-LAN-errors"
                   ::= {  staTcpipArp 3 }

staTcpipArpArpwanr OBJECT-TYPE
                   SYNTAX INTEGER
                   ACCESS read-only
                   STATUS mandatory
                   DESCRIPTION "ARP-WAN-rx"
                   ::= {  staTcpipArp 4 }

staTcpipArpArpwant OBJECT-TYPE
                   SYNTAX INTEGER
                   ACCESS read-only
                   STATUS mandatory
                   DESCRIPTION "ARP-WAN-tx"
                   ::= {  staTcpipArp 5 }

staTcpipArpArpwane OBJECT-TYPE
                   SYNTAX INTEGER
                   ACCESS read-only
                   STATUS mandatory
                   DESCRIPTION "ARP-WAN-errors"
                   ::= {  staTcpipArp 6 }

staTcpipArpTablear OBJECT-TYPE
                   SYNTAX SEQUENCE OF StaTcpipArpTablearRows
                   ACCESS not-accessible
                   STATUS mandatory
                   DESCRIPTION "Table-ARP"
                   ::= {  staTcpipArp 7 }

staTcpipArpTablearCols OBJECT-TYPE
                   SYNTAX StaTcpipArpTablearRows
                   ACCESS not-accessible
                   STATUS mandatory
                   DESCRIPTION "entry in table"
                   INDEX { staTcpipArpTablearIpa }
                   ::= {  staTcpipArpTablear 1 }

StaTcpipArpTablearRows ::= SEQUENCE {
                   staTcpipArpTablearIpa IpAddress,
                   staTcpipArpTablearNod DisplayString,
                   staTcpipArpTablearLas INTEGER,
                   staTcpipArpTablearCon INTEGER
                  }

staTcpipArpTablearIpa OBJECT-TYPE
                      SYNTAX IpAddress
                      ACCESS read-only
                      STATUS mandatory
                      DESCRIPTION "IP-address"
                      ::= {  staTcpipArpTablearCols 1 }

staTcpipArpTablearNod OBJECT-TYPE
                      SYNTAX DisplayString
                      ACCESS read-only
                      STATUS mandatory
                      DESCRIPTION "Node-ID"
                      ::= {  staTcpipArpTablearCols 2 }

staTcpipArpTablearLas OBJECT-TYPE
                      SYNTAX INTEGER
                      ACCESS read-only
                      STATUS mandatory
                      DESCRIPTION "Last-access"
                      ::= {  staTcpipArpTablearCols 3 }

staTcpipArpTablearCon OBJECT-TYPE
                      SYNTAX INTEGER {
                        local(2),
                        remote(1)
                      }
                      ACCESS read-only
                      STATUS mandatory
                      DESCRIPTION "Connect"
                      ::= {  staTcpipArpTablearCols 4 }

staTcpipArpDeletev OBJECT-TYPE
                   SYNTAX INTEGER
                   ACCESS write-only
                   STATUS mandatory
                   DESCRIPTION "Delete-values"
                   ::= {  staTcpipArp 8 }

staTcpipIps OBJECT IDENTIFIER ::= { staTcpip 2}
staTcpipIpsIplanrx OBJECT-TYPE
                                SYNTAX INTEGER
                                ACCESS read-only
                                STATUS mandatory
                                DESCRIPTION "IP-LAN-rx"
                                ::= {  staTcpipIps 1 }

staTcpipIpsIplantx OBJECT-TYPE
                                SYNTAX INTEGER
                                ACCESS read-only
                                STATUS mandatory
                                DESCRIPTION "IP-LAN-tx"
                                ::= {  staTcpipIps 2 }

staTcpipIpsIplanchecksumerrors OBJECT-TYPE
                                SYNTAX INTEGER
                                ACCESS read-only
                                STATUS mandatory
                                DESCRIPTION "IP-LAN-checksum-errors"
                                ::= {  staTcpipIps 3 }

staTcpipIpsIplanserviceerrors OBJECT-TYPE
                                SYNTAX INTEGER
                                ACCESS read-only
                                STATUS mandatory
                                DESCRIPTION "IP-LAN-service-errors"
                                ::= {  staTcpipIps 4 }

staTcpipIpsIplanfragmentationer OBJECT-TYPE
                                SYNTAX INTEGER
                                ACCESS read-only
                                STATUS mandatory
                                DESCRIPTION "IP-LAN-fragmentation-error"
                                ::= {  staTcpipIps 10 }

staTcpipIpsIplanfragmentations OBJECT-TYPE
                                SYNTAX INTEGER
                                ACCESS read-only
                                STATUS mandatory
                                DESCRIPTION "IP-LAN-fragmentations"
                                ::= {  staTcpipIps 13 }

staTcpipIpsIplanfragmentationsf OBJECT-TYPE
                                SYNTAX INTEGER
                                ACCESS read-only
                                STATUS mandatory
                                DESCRIPTION "IP-LAN-fragmentations-forced"
                                ::= {  staTcpipIps 14 }

staTcpipIpsIpwanrx OBJECT-TYPE
                                SYNTAX INTEGER
                                ACCESS read-only
                                STATUS mandatory
                                DESCRIPTION "IP-WAN-rx"
                                ::= {  staTcpipIps 5 }

staTcpipIpsIpwantx OBJECT-TYPE
                                SYNTAX INTEGER
                                ACCESS read-only
                                STATUS mandatory
                                DESCRIPTION "IP-WAN-tx"
                                ::= {  staTcpipIps 6 }

staTcpipIpsIpwanchecksumerrors OBJECT-TYPE
                                SYNTAX INTEGER
                                ACCESS read-only
                                STATUS mandatory
                                DESCRIPTION "IP-WAN-checksum-errors"
                                ::= {  staTcpipIps 7 }

staTcpipIpsIpwanserviceerrors OBJECT-TYPE
                                SYNTAX INTEGER
                                ACCESS read-only
                                STATUS mandatory
                                DESCRIPTION "IP-WAN-service-errors"
                                ::= {  staTcpipIps 8 }

staTcpipIpsIpwanfragmentationer OBJECT-TYPE
                                SYNTAX INTEGER
                                ACCESS read-only
                                STATUS mandatory
                                DESCRIPTION "IP-WAN-fragmentation-error"
                                ::= {  staTcpipIps 11 }

staTcpipIpsIpwanfragmentations OBJECT-TYPE
                                SYNTAX INTEGER
                                ACCESS read-only
                                STATUS mandatory
                                DESCRIPTION "IP-WAN-fragmentations"
                                ::= {  staTcpipIps 15 }

staTcpipIpsIpwanfragmentationsf OBJECT-TYPE
                                SYNTAX INTEGER
                                ACCESS read-only
                                STATUS mandatory
                                DESCRIPTION "IP-WAN-fragmentations-forced"
                                ::= {  staTcpipIps 16 }

staTcpipIpsIpwanrxdisconnect OBJECT-TYPE
                                SYNTAX INTEGER
                                ACCESS read-only
                                STATUS mandatory
                                DESCRIPTION "IP-WAN-rx-disconnect"
                                ::= {  staTcpipIps 9 }

staTcpipIpsDeletevalues OBJECT-TYPE
                                SYNTAX INTEGER
                                ACCESS write-only
                                STATUS mandatory
                                DESCRIPTION "Delete-values"
                                ::= {  staTcpipIps 12 }

staTcpipIcm OBJECT IDENTIFIER ::= { staTcpip 3}
staTcpipIcmIcmplanr OBJECT-TYPE
                    SYNTAX INTEGER
                    ACCESS read-only
                    STATUS mandatory
                    DESCRIPTION "ICMP-LAN-rx"
                    ::= {  staTcpipIcm 1 }

staTcpipIcmIcmplant OBJECT-TYPE
                    SYNTAX INTEGER
                    ACCESS read-only
                    STATUS mandatory
                    DESCRIPTION "ICMP-LAN-tx"
                    ::= {  staTcpipIcm 2 }

staTcpipIcmIcmplanc OBJECT-TYPE
                    SYNTAX INTEGER
                    ACCESS read-only
                    STATUS mandatory
                    DESCRIPTION "ICMP-LAN-checksum-errors"
                    ::= {  staTcpipIcm 3 }

staTcpipIcmIcmplans OBJECT-TYPE
                    SYNTAX INTEGER
                    ACCESS read-only
                    STATUS mandatory
                    DESCRIPTION "ICMP-LAN-service-errors"
                    ::= {  staTcpipIcm 4 }

staTcpipIcmIcmpwanr OBJECT-TYPE
                    SYNTAX INTEGER
                    ACCESS read-only
                    STATUS mandatory
                    DESCRIPTION "ICMP-WAN-rx"
                    ::= {  staTcpipIcm 5 }

staTcpipIcmIcmpwant OBJECT-TYPE
                    SYNTAX INTEGER
                    ACCESS read-only
                    STATUS mandatory
                    DESCRIPTION "ICMP-WAN-tx"
                    ::= {  staTcpipIcm 6 }

staTcpipIcmIcmpwanc OBJECT-TYPE
                    SYNTAX INTEGER
                    ACCESS read-only
                    STATUS mandatory
                    DESCRIPTION "ICMP-WAN-checksum-errors"
                    ::= {  staTcpipIcm 7 }

staTcpipIcmIcmpwans OBJECT-TYPE
                    SYNTAX INTEGER
                    ACCESS read-only
                    STATUS mandatory
                    DESCRIPTION "ICMP-WAN-service-errors"
                    ::= {  staTcpipIcm 8 }

staTcpipIcmDeleteva OBJECT-TYPE
                    SYNTAX INTEGER
                    ACCESS write-only
                    STATUS mandatory
                    DESCRIPTION "Delete-values"
                    ::= {  staTcpipIcm 9 }

staTcpipTft OBJECT IDENTIFIER ::= { staTcpip 4}
staTcpipTftTftplanrx OBJECT-TYPE
                      SYNTAX INTEGER
                      ACCESS read-only
                      STATUS mandatory
                      DESCRIPTION "TFTP-LAN-rx"
                      ::= {  staTcpipTft 1 }

staTcpipTftTftplanrxr OBJECT-TYPE
                      SYNTAX INTEGER
                      ACCESS read-only
                      STATUS mandatory
                      DESCRIPTION "TFTP-LAN-rx-read-request"
                      ::= {  staTcpipTft 2 }

staTcpipTftTftplanrxw OBJECT-TYPE
                      SYNTAX INTEGER
                      ACCESS read-only
                      STATUS mandatory
                      DESCRIPTION "TFTP-LAN-rx-write-request"
                      ::= {  staTcpipTft 3 }

staTcpipTftTftplanrxd OBJECT-TYPE
                      SYNTAX INTEGER
                      ACCESS read-only
                      STATUS mandatory
                      DESCRIPTION "TFTP-LAN-rx-data"
                      ::= {  staTcpipTft 4 }

staTcpipTftTftplanrxa OBJECT-TYPE
                      SYNTAX INTEGER
                      ACCESS read-only
                      STATUS mandatory
                      DESCRIPTION "TFTP-LAN-rx-ack."
                      ::= {  staTcpipTft 5 }

staTcpipTftTftplanrxo OBJECT-TYPE
                      SYNTAX INTEGER
                      ACCESS read-only
                      STATUS mandatory
                      DESCRIPTION "TFTP-LAN-rx-option-ack."
                      ::= {  staTcpipTft 6 }

staTcpipTftTftplanrxe OBJECT-TYPE
                      SYNTAX INTEGER
                      ACCESS read-only
                      STATUS mandatory
                      DESCRIPTION "TFTP-LAN-rx-errors"
                      ::= {  staTcpipTft 7 }

staTcpipTftTftplanrxb OBJECT-TYPE
                      SYNTAX INTEGER
                      ACCESS read-only
                      STATUS mandatory
                      DESCRIPTION "TFTP-LAN-rx-bad-packets"
                      ::= {  staTcpipTft 8 }

staTcpipTftTftplantx OBJECT-TYPE
                      SYNTAX INTEGER
                      ACCESS read-only
                      STATUS mandatory
                      DESCRIPTION "TFTP-LAN-tx"
                      ::= {  staTcpipTft 9 }

staTcpipTftTftplantxd OBJECT-TYPE
                      SYNTAX INTEGER
                      ACCESS read-only
                      STATUS mandatory
                      DESCRIPTION "TFTP-LAN-tx-data"
                      ::= {  staTcpipTft 10 }

staTcpipTftTftplantxa OBJECT-TYPE
                      SYNTAX INTEGER
                      ACCESS read-only
                      STATUS mandatory
                      DESCRIPTION "TFTP-LAN-tx-ack."
                      ::= {  staTcpipTft 11 }

staTcpipTftTftplantxo OBJECT-TYPE
                      SYNTAX INTEGER
                      ACCESS read-only
                      STATUS mandatory
                      DESCRIPTION "TFTP-LAN-tx-option-ack."
                      ::= {  staTcpipTft 12 }

staTcpipTftTftplantxe OBJECT-TYPE
                      SYNTAX INTEGER
                      ACCESS read-only
                      STATUS mandatory
                      DESCRIPTION "TFTP-LAN-tx-errors"
                      ::= {  staTcpipTft 13 }

staTcpipTftTftplantxr OBJECT-TYPE
                      SYNTAX INTEGER
                      ACCESS read-only
                      STATUS mandatory
                      DESCRIPTION "TFTP-LAN-tx-repeats"
                      ::= {  staTcpipTft 14 }

staTcpipTftTftplancon OBJECT-TYPE
                      SYNTAX INTEGER
                      ACCESS read-only
                      STATUS mandatory
                      DESCRIPTION "TFTP-LAN-connections"
                      ::= {  staTcpipTft 15 }

staTcpipTftTftpwanrx OBJECT-TYPE
                      SYNTAX INTEGER
                      ACCESS read-only
                      STATUS mandatory
                      DESCRIPTION "TFTP-WAN-rx"
                      ::= {  staTcpipTft 16 }

staTcpipTftTftpwanrxr OBJECT-TYPE
                      SYNTAX INTEGER
                      ACCESS read-only
                      STATUS mandatory
                      DESCRIPTION "TFTP-WAN-rx-read-request"
                      ::= {  staTcpipTft 17 }

staTcpipTftTftpwanrxw OBJECT-TYPE
                      SYNTAX INTEGER
                      ACCESS read-only
                      STATUS mandatory
                      DESCRIPTION "TFTP-WAN-rx-write-request"
                      ::= {  staTcpipTft 18 }

staTcpipTftTftpwanrxd OBJECT-TYPE
                      SYNTAX INTEGER
                      ACCESS read-only
                      STATUS mandatory
                      DESCRIPTION "TFTP-WAN-rx-data"
                      ::= {  staTcpipTft 19 }

staTcpipTftTftpwanrxa OBJECT-TYPE
                      SYNTAX INTEGER
                      ACCESS read-only
                      STATUS mandatory
                      DESCRIPTION "TFTP-WAN-rx-ack."
                      ::= {  staTcpipTft 20 }

staTcpipTftTftpwanrxo OBJECT-TYPE
                      SYNTAX INTEGER
                      ACCESS read-only
                      STATUS mandatory
                      DESCRIPTION "TFTP-WAN-rx-option-ack."
                      ::= {  staTcpipTft 21 }

staTcpipTftTftpwanrxe OBJECT-TYPE
                      SYNTAX INTEGER
                      ACCESS read-only
                      STATUS mandatory
                      DESCRIPTION "TFTP-WAN-rx-errors"
                      ::= {  staTcpipTft 22 }

staTcpipTftTftpwanrxb OBJECT-TYPE
                      SYNTAX INTEGER
                      ACCESS read-only
                      STATUS mandatory
                      DESCRIPTION "TFTP-WAN-rx-bad-packets"
                      ::= {  staTcpipTft 23 }

staTcpipTftTftpwantx OBJECT-TYPE
                      SYNTAX INTEGER
                      ACCESS read-only
                      STATUS mandatory
                      DESCRIPTION "TFTP-WAN-tx"
                      ::= {  staTcpipTft 24 }

staTcpipTftTftpwantxd OBJECT-TYPE
                      SYNTAX INTEGER
                      ACCESS read-only
                      STATUS mandatory
                      DESCRIPTION "TFTP-WAN-tx-data"
                      ::= {  staTcpipTft 25 }

staTcpipTftTftpwantxa OBJECT-TYPE
                      SYNTAX INTEGER
                      ACCESS read-only
                      STATUS mandatory
                      DESCRIPTION "TFTP-WAN-tx-ack."
                      ::= {  staTcpipTft 26 }

staTcpipTftTftpwantxo OBJECT-TYPE
                      SYNTAX INTEGER
                      ACCESS read-only
                      STATUS mandatory
                      DESCRIPTION "TFTP-WAN-tx-option-ack."
                      ::= {  staTcpipTft 27 }

staTcpipTftTftpwantxe OBJECT-TYPE
                      SYNTAX INTEGER
                      ACCESS read-only
                      STATUS mandatory
                      DESCRIPTION "TFTP-WAN-tx-errors"
                      ::= {  staTcpipTft 28 }

staTcpipTftTftpwantxr OBJECT-TYPE
                      SYNTAX INTEGER
                      ACCESS read-only
                      STATUS mandatory
                      DESCRIPTION "TFTP-WAN-tx-repeats"
                      ::= {  staTcpipTft 29 }

staTcpipTftTftpwancon OBJECT-TYPE
                      SYNTAX INTEGER
                      ACCESS read-only
                      STATUS mandatory
                      DESCRIPTION "TFTP-WAN-connections"
                      ::= {  staTcpipTft 30 }

staTcpipTftDeletevalu OBJECT-TYPE
                      SYNTAX INTEGER
                      ACCESS write-only
                      STATUS mandatory
                      DESCRIPTION "Delete-values"
                      ::= {  staTcpipTft 31 }

staTcpipTcp OBJECT IDENTIFIER ::= { staTcpip 5}
staTcpipTcpTcplanrx OBJECT-TYPE
                     SYNTAX INTEGER
                     ACCESS read-only
                     STATUS mandatory
                     DESCRIPTION "TCP-LAN-rx"
                     ::= {  staTcpipTcp 1 }

staTcpipTcpTcplantx OBJECT-TYPE
                     SYNTAX INTEGER
                     ACCESS read-only
                     STATUS mandatory
                     DESCRIPTION "TCP-LAN-tx"
                     ::= {  staTcpipTcp 2 }

staTcpipTcpTcplantxr OBJECT-TYPE
                     SYNTAX INTEGER
                     ACCESS read-only
                     STATUS mandatory
                     DESCRIPTION "TCP-LAN-tx-repeats"
                     ::= {  staTcpipTcp 3 }

staTcpipTcpTcplanche OBJECT-TYPE
                     SYNTAX INTEGER
                     ACCESS read-only
                     STATUS mandatory
                     DESCRIPTION "TCP-LAN-checksum-errors"
                     ::= {  staTcpipTcp 4 }

staTcpipTcpTcplanser OBJECT-TYPE
                     SYNTAX INTEGER
                     ACCESS read-only
                     STATUS mandatory
                     DESCRIPTION "TCP-LAN-service-errors"
                     ::= {  staTcpipTcp 5 }

staTcpipTcpTcplancon OBJECT-TYPE
                     SYNTAX INTEGER
                     ACCESS read-only
                     STATUS mandatory
                     DESCRIPTION "TCP-LAN-connections"
                     ::= {  staTcpipTcp 6 }

staTcpipTcpTcpwanrx OBJECT-TYPE
                     SYNTAX INTEGER
                     ACCESS read-only
                     STATUS mandatory
                     DESCRIPTION "TCP-WAN-rx"
                     ::= {  staTcpipTcp 7 }

staTcpipTcpTcpwantx OBJECT-TYPE
                     SYNTAX INTEGER
                     ACCESS read-only
                     STATUS mandatory
                     DESCRIPTION "TCP-WAN-tx"
                     ::= {  staTcpipTcp 8 }

staTcpipTcpTcpwantxr OBJECT-TYPE
                     SYNTAX INTEGER
                     ACCESS read-only
                     STATUS mandatory
                     DESCRIPTION "TCP-WAN-tx-repeats"
                     ::= {  staTcpipTcp 9 }

staTcpipTcpTcpwanche OBJECT-TYPE
                     SYNTAX INTEGER
                     ACCESS read-only
                     STATUS mandatory
                     DESCRIPTION "TCP-WAN-checksum-errors"
                     ::= {  staTcpipTcp 10 }

staTcpipTcpTcpwanser OBJECT-TYPE
                     SYNTAX INTEGER
                     ACCESS read-only
                     STATUS mandatory
                     DESCRIPTION "TCP-WAN-service-errors"
                     ::= {  staTcpipTcp 11 }

staTcpipTcpTcpwancon OBJECT-TYPE
                     SYNTAX INTEGER
                     ACCESS read-only
                     STATUS mandatory
                     DESCRIPTION "TCP-WAN-connections"
                     ::= {  staTcpipTcp 12 }

staTcpipTcpDeleteval OBJECT-TYPE
                     SYNTAX INTEGER
                     ACCESS write-only
                     STATUS mandatory
                     DESCRIPTION "Delete-values"
                     ::= {  staTcpipTcp 13 }

staTcpipDhc OBJECT IDENTIFIER ::= { staTcpip 6}
staTcpipDhcDhcplanrx OBJECT-TYPE
                     SYNTAX INTEGER
                     ACCESS read-only
                     STATUS mandatory
                     DESCRIPTION "DHCP-LAN-rx"
                     ::= {  staTcpipDhc 1 }

staTcpipDhcDhcplantx OBJECT-TYPE
                     SYNTAX INTEGER
                     ACCESS read-only
                     STATUS mandatory
                     DESCRIPTION "DHCP-LAN-tx"
                     ::= {  staTcpipDhc 2 }

staTcpipDhcDhcpwanrx OBJECT-TYPE
                     SYNTAX INTEGER
                     ACCESS read-only
                     STATUS mandatory
                     DESCRIPTION "DHCP-WAN-rx"
                     ::= {  staTcpipDhc 3 }

staTcpipDhcDhcpdisca OBJECT-TYPE
                     SYNTAX INTEGER
                     ACCESS read-only
                     STATUS mandatory
                     DESCRIPTION "DHCP-discard"
                     ::= {  staTcpipDhc 4 }

staTcpipDhcDhcprxdis OBJECT-TYPE
                     SYNTAX INTEGER
                     ACCESS read-only
                     STATUS mandatory
                     DESCRIPTION "DHCP-rx-discover"
                     ::= {  staTcpipDhc 5 }

staTcpipDhcDhcprxreq OBJECT-TYPE
                     SYNTAX INTEGER
                     ACCESS read-only
                     STATUS mandatory
                     DESCRIPTION "DHCP-rx-request"
                     ::= {  staTcpipDhc 6 }

staTcpipDhcDhcprxdec OBJECT-TYPE
                     SYNTAX INTEGER
                     ACCESS read-only
                     STATUS mandatory
                     DESCRIPTION "DHCP-rx-decline"
                     ::= {  staTcpipDhc 7 }

staTcpipDhcDhcprxinf OBJECT-TYPE
                     SYNTAX INTEGER
                     ACCESS read-only
                     STATUS mandatory
                     DESCRIPTION "DHCP-rx-inform"
                     ::= {  staTcpipDhc 8 }

staTcpipDhcDhcprxrel OBJECT-TYPE
                     SYNTAX INTEGER
                     ACCESS read-only
                     STATUS mandatory
                     DESCRIPTION "DHCP-rx-release"
                     ::= {  staTcpipDhc 9 }

staTcpipDhcDhcptxoff OBJECT-TYPE
                     SYNTAX INTEGER
                     ACCESS read-only
                     STATUS mandatory
                     DESCRIPTION "DHCP-tx-offer"
                     ::= {  staTcpipDhc 10 }

staTcpipDhcDhcptxack OBJECT-TYPE
                     SYNTAX INTEGER
                     ACCESS read-only
                     STATUS mandatory
                     DESCRIPTION "DHCP-tx-ack."
                     ::= {  staTcpipDhc 11 }

staTcpipDhcDhcptxnak OBJECT-TYPE
                     SYNTAX INTEGER
                     ACCESS read-only
                     STATUS mandatory
                     DESCRIPTION "DHCP-tx-nak."
                     ::= {  staTcpipDhc 12 }

staTcpipDhcDchpserve OBJECT-TYPE
                     SYNTAX INTEGER
                     ACCESS read-only
                     STATUS mandatory
                     DESCRIPTION "DchP-server-err."
                     ::= {  staTcpipDhc 13 }

staTcpipDhcDhcpassig OBJECT-TYPE
                     SYNTAX INTEGER
                     ACCESS read-only
                     STATUS mandatory
                     DESCRIPTION "DHCP-assigned"
                     ::= {  staTcpipDhc 14 }

staTcpipDhcDhcpmacco OBJECT-TYPE
                     SYNTAX INTEGER
                     ACCESS read-only
                     STATUS mandatory
                     DESCRIPTION "DHCP-MAC-conflicts"
                     ::= {  staTcpipDhc 15 }

staTcpipDhcTabledhcp OBJECT-TYPE
                     SYNTAX SEQUENCE OF StaTcpipDhcTabledhcpRows
                     ACCESS not-accessible
                     STATUS mandatory
                     DESCRIPTION "Table-DHCP"
                     ::= {  staTcpipDhc 16 }

staTcpipDhcTabledhcpCols OBJECT-TYPE
                     SYNTAX StaTcpipDhcTabledhcpRows
                     ACCESS not-accessible
                     STATUS mandatory
                     DESCRIPTION "entry in table"
                     INDEX { staTcpipDhcTabledhcpIpa }
                     ::= {  staTcpipDhcTabledhcp 1 }

StaTcpipDhcTabledhcpRows ::= SEQUENCE {
                     staTcpipDhcTabledhcpIpa IpAddress,
                     staTcpipDhcTabledhcpNod DisplayString,
                     staTcpipDhcTabledhcpTim INTEGER,
                     staTcpipDhcTabledhcpHos DisplayString,
                     staTcpipDhcTabledhcpTyp INTEGER
                    }

staTcpipDhcTabledhcpIpa OBJECT-TYPE
                        SYNTAX IpAddress
                        ACCESS read-only
                        STATUS mandatory
                        DESCRIPTION "IP-Address"
                        ::= {  staTcpipDhcTabledhcpCols 1 }

staTcpipDhcTabledhcpNod OBJECT-TYPE
                        SYNTAX DisplayString
                        ACCESS read-only
                        STATUS mandatory
                        DESCRIPTION "Node-ID"
                        ::= {  staTcpipDhcTabledhcpCols 2 }

staTcpipDhcTabledhcpTim OBJECT-TYPE
                        SYNTAX INTEGER
                        ACCESS read-only
                        STATUS mandatory
                        DESCRIPTION "Timeout"
                        ::= {  staTcpipDhcTabledhcpCols 3 }

staTcpipDhcTabledhcpHos OBJECT-TYPE
                        SYNTAX DisplayString
                        ACCESS read-only
                        STATUS mandatory
                        DESCRIPTION "Hostname"
                        ::= {  staTcpipDhcTabledhcpCols 4 }

staTcpipDhcTabledhcpTyp OBJECT-TYPE
                        SYNTAX INTEGER {
                          new(1),
                          new(2),
                          dyn(16),
                          unkn(4),
                          stat(8),
                          bootp(32),
                          relay(2048)
                        }
                        ACCESS read-only
                        STATUS mandatory
                        DESCRIPTION "Type"
                        ::= {  staTcpipDhcTabledhcpCols 5 }

staTcpipDhcServerfla OBJECT-TYPE
                     SYNTAX DisplayString
                     ACCESS read-only
                     STATUS mandatory
                     DESCRIPTION "Server-flags"
                     ::= {  staTcpipDhc 17 }

staTcpipDhcDeleteval OBJECT-TYPE
                     SYNTAX INTEGER
                     ACCESS write-only
                     STATUS mandatory
                     DESCRIPTION "Delete-values"
                     ::= {  staTcpipDhc 18 }

staTcpipDel OBJECT-TYPE
            SYNTAX INTEGER
            ACCESS write-only
            STATUS mandatory
            DESCRIPTION "Delete-values"
            ::= {  staTcpip 7 }

staTcpipNet OBJECT IDENTIFIER ::= { staTcpip 8}
staTcpipNetLanr OBJECT-TYPE
                SYNTAX INTEGER
                ACCESS read-only
                STATUS mandatory
                DESCRIPTION "LAN-Rx"
                ::= {  staTcpipNet 1 }

staTcpipNetLant OBJECT-TYPE
                SYNTAX INTEGER
                ACCESS read-only
                STATUS mandatory
                DESCRIPTION "LAN-Tx"
                ::= {  staTcpipNet 2 }

staTcpipNetWanr OBJECT-TYPE
                SYNTAX INTEGER
                ACCESS read-only
                STATUS mandatory
                DESCRIPTION "WAN-Rx"
                ::= {  staTcpipNet 3 }

staTcpipNetWant OBJECT-TYPE
                SYNTAX INTEGER
                ACCESS read-only
                STATUS mandatory
                DESCRIPTION "WAN-Tx"
                ::= {  staTcpipNet 4 }

staTcpipNetRegi OBJECT-TYPE
                SYNTAX INTEGER
                ACCESS read-only
                STATUS mandatory
                DESCRIPTION "Registers"
                ::= {  staTcpipNet 5 }

staTcpipNetConf OBJECT-TYPE
                SYNTAX INTEGER
                ACCESS read-only
                STATUS mandatory
                DESCRIPTION "Conflicts"
                ::= {  staTcpipNet 6 }

staTcpipNetRele OBJECT-TYPE
                SYNTAX INTEGER
                ACCESS read-only
                STATUS mandatory
                DESCRIPTION "Releases"
                ::= {  staTcpipNet 7 }

staTcpipNetRefr OBJECT-TYPE
                SYNTAX INTEGER
                ACCESS read-only
                STATUS mandatory
                DESCRIPTION "Refreshs"
                ::= {  staTcpipNet 8 }

staTcpipNetTime OBJECT-TYPE
                SYNTAX INTEGER
                ACCESS read-only
                STATUS mandatory
                DESCRIPTION "Timeouts"
                ::= {  staTcpipNet 9 }

staTcpipNetHost OBJECT-TYPE
                SYNTAX INTEGER
                ACCESS read-only
                STATUS mandatory
                DESCRIPTION "Hosts"
                ::= {  staTcpipNet 10 }

staTcpipNetGrou OBJECT-TYPE
                SYNTAX INTEGER
                ACCESS read-only
                STATUS mandatory
                DESCRIPTION "Groups"
                ::= {  staTcpipNet 11 }

staTcpipNetBnod OBJECT-TYPE
                SYNTAX INTEGER
                ACCESS read-only
                STATUS mandatory
                DESCRIPTION "B-Nodes"
                ::= {  staTcpipNet 12 }

staTcpipNetPnod OBJECT-TYPE
                SYNTAX INTEGER
                ACCESS read-only
                STATUS mandatory
                DESCRIPTION "P-Nodes"
                ::= {  staTcpipNet 13 }

staTcpipNetMnod OBJECT-TYPE
                SYNTAX INTEGER
                ACCESS read-only
                STATUS mandatory
                DESCRIPTION "M-Nodes"
                ::= {  staTcpipNet 14 }

staTcpipNetWnod OBJECT-TYPE
                SYNTAX INTEGER
                ACCESS read-only
                STATUS mandatory
                DESCRIPTION "W-Nodes"
                ::= {  staTcpipNet 15 }

staTcpipNetRemo OBJECT-TYPE
                SYNTAX SEQUENCE OF StaTcpipNetRemoRows
                ACCESS not-accessible
                STATUS mandatory
                DESCRIPTION "Remote-table"
                ::= {  staTcpipNet 16 }

staTcpipNetRemoCols OBJECT-TYPE
                SYNTAX StaTcpipNetRemoRows
                ACCESS not-accessible
                STATUS mandatory
                DESCRIPTION "entry in table"
                INDEX { staTcpipNetRemoNam }
                ::= {  staTcpipNetRemo 1 }

StaTcpipNetRemoRows ::= SEQUENCE {
                staTcpipNetRemoNam DisplayString,
                staTcpipNetRemoTyp INTEGER,
                staTcpipNetRemoBac INTEGER,
                staTcpipNetRemoTim INTEGER
               }

staTcpipNetRemoNam OBJECT-TYPE
                   SYNTAX DisplayString
                   ACCESS read-only
                   STATUS mandatory
                   DESCRIPTION "Name"
                   ::= {  staTcpipNetRemoCols 1 }

staTcpipNetRemoTyp OBJECT-TYPE
                   SYNTAX INTEGER {
                     workstation(1),
                     router(0)
                   }
                   ACCESS read-only
                   STATUS mandatory
                   DESCRIPTION "Type"
                   ::= {  staTcpipNetRemoCols 2 }

staTcpipNetRemoBac OBJECT-TYPE
                   SYNTAX INTEGER
                   ACCESS read-only
                   STATUS mandatory
                   DESCRIPTION "Backoff"
                   ::= {  staTcpipNetRemoCols 3 }

staTcpipNetRemoTim OBJECT-TYPE
                   SYNTAX INTEGER
                   ACCESS read-only
                   STATUS mandatory
                   DESCRIPTION "Time"
                   ::= {  staTcpipNetRemoCols 4 }

staTcpipNetDele OBJECT-TYPE
                SYNTAX INTEGER
                ACCESS read-write
                STATUS mandatory
                DESCRIPTION "Delete-values"
                ::= {  staTcpipNet 17 }

staTcpipDns OBJECT IDENTIFIER ::= { staTcpip 9}
staTcpipDnsLanr OBJECT-TYPE
                SYNTAX INTEGER
                ACCESS read-only
                STATUS mandatory
                DESCRIPTION "LAN-Rx"
                ::= {  staTcpipDns 1 }

staTcpipDnsLant OBJECT-TYPE
                SYNTAX INTEGER
                ACCESS read-only
                STATUS mandatory
                DESCRIPTION "LAN-Tx"
                ::= {  staTcpipDns 2 }

staTcpipDnsWanr OBJECT-TYPE
                SYNTAX INTEGER
                ACCESS read-only
                STATUS mandatory
                DESCRIPTION "WAN-Rx"
                ::= {  staTcpipDns 3 }

staTcpipDnsWant OBJECT-TYPE
                SYNTAX INTEGER
                ACCESS read-only
                STATUS mandatory
                DESCRIPTION "WAN-Tx"
                ::= {  staTcpipDns 4 }

staTcpipDnsForw OBJECT-TYPE
                SYNTAX INTEGER
                ACCESS read-only
                STATUS mandatory
                DESCRIPTION "Forwarded"
                ::= {  staTcpipDns 5 }

staTcpipDnsErro OBJECT-TYPE
                SYNTAX INTEGER
                ACCESS read-only
                STATUS mandatory
                DESCRIPTION "Errors"
                ::= {  staTcpipDns 6 }

staTcpipDnsDnsa OBJECT-TYPE
                SYNTAX INTEGER
                ACCESS read-only
                STATUS mandatory
                DESCRIPTION "DNS-access"
                ::= {  staTcpipDns 7 }

staTcpipDnsDhcp OBJECT-TYPE
                SYNTAX INTEGER
                ACCESS read-only
                STATUS mandatory
                DESCRIPTION "DHCP-access"
                ::= {  staTcpipDns 8 }

staTcpipDnsNetb OBJECT-TYPE
                SYNTAX INTEGER
                ACCESS read-only
                STATUS mandatory
                DESCRIPTION "NetBIOS-access"
                ::= {  staTcpipDns 9 }

staTcpipDnsFilt OBJECT-TYPE
                SYNTAX INTEGER
                ACCESS read-only
                STATUS mandatory
                DESCRIPTION "Filter"
                ::= {  staTcpipDns 10 }

staTcpipDnsHitl OBJECT-TYPE
                SYNTAX SEQUENCE OF StaTcpipDnsHitlRows
                ACCESS not-accessible
                STATUS mandatory
                DESCRIPTION "Hit-list"
                ::= {  staTcpipDns 11 }

staTcpipDnsHitlCols OBJECT-TYPE
                SYNTAX StaTcpipDnsHitlRows
                ACCESS not-accessible
                STATUS mandatory
                DESCRIPTION "entry in table"
                INDEX { staTcpipDnsHitlDom }
                ::= {  staTcpipDnsHitl 1 }

StaTcpipDnsHitlRows ::= SEQUENCE {
                staTcpipDnsHitlDom DisplayString,
                staTcpipDnsHitlReq INTEGER,
                staTcpipDnsHitlTim DisplayString,
                staTcpipDnsHitlIpa IpAddress
               }

staTcpipDnsHitlDom OBJECT-TYPE
                   SYNTAX DisplayString
                   ACCESS read-only
                   STATUS mandatory
                   DESCRIPTION "Domain"
                   ::= {  staTcpipDnsHitlCols 1 }

staTcpipDnsHitlReq OBJECT-TYPE
                   SYNTAX INTEGER
                   ACCESS read-only
                   STATUS mandatory
                   DESCRIPTION "Requests"
                   ::= {  staTcpipDnsHitlCols 2 }

staTcpipDnsHitlTim OBJECT-TYPE
                   SYNTAX DisplayString
                   ACCESS read-only
                   STATUS mandatory
                   DESCRIPTION "Time"
                   ::= {  staTcpipDnsHitlCols 3 }

staTcpipDnsHitlIpa OBJECT-TYPE
                   SYNTAX IpAddress
                   ACCESS read-only
                   STATUS mandatory
                   DESCRIPTION "IP-Address"
                   ::= {  staTcpipDnsHitlCols 4 }

staTcpipDnsDele OBJECT-TYPE
                SYNTAX INTEGER
                ACCESS write-only
                STATUS mandatory
                DESCRIPTION "Delete-values"
                ::= {  staTcpipDns 12 }

staTcpipHtt OBJECT IDENTIFIER ::= { staTcpip 10}
staTcpipHttHttpac OBJECT-TYPE
                  SYNTAX INTEGER
                  ACCESS read-only
                  STATUS mandatory
                  DESCRIPTION "HTTP-accesses"
                  ::= {  staTcpipHtt 1 }

staTcpipHttHttpno OBJECT-TYPE
                  SYNTAX INTEGER
                  ACCESS read-only
                  STATUS mandatory
                  DESCRIPTION "HTTP-notfound-errors"
                  ::= {  staTcpipHtt 2 }

staTcpipHttHttpau OBJECT-TYPE
                  SYNTAX INTEGER
                  ACCESS read-only
                  STATUS mandatory
                  DESCRIPTION "HTTP-authentication-errors"
                  ::= {  staTcpipHtt 3 }

staTcpipHttHttppr OBJECT-TYPE
                  SYNTAX INTEGER
                  ACCESS read-only
                  STATUS mandatory
                  DESCRIPTION "HTTP-protocol-errors"
                  ::= {  staTcpipHtt 4 }

staTcpipHttDelete OBJECT-TYPE
                  SYNTAX INTEGER
                  ACCESS read-write
                  STATUS mandatory
                  DESCRIPTION "Delete-values"
                  ::= {  staTcpipHtt 5 }

staIprou OBJECT IDENTIFIER ::= { sta 10}
staIprouIprlanrx OBJECT-TYPE
                 SYNTAX INTEGER
                 ACCESS read-only
                 STATUS mandatory
                 DESCRIPTION "IPr-LAN-rx"
                 ::= {  staIprou 1 }

staIprouIprlantx OBJECT-TYPE
                 SYNTAX INTEGER
                 ACCESS read-only
                 STATUS mandatory
                 DESCRIPTION "IPr-LAN-tx"
                 ::= {  staIprou 2 }

staIprouIprlanlo OBJECT-TYPE
                 SYNTAX INTEGER
                 ACCESS read-only
                 STATUS mandatory
                 DESCRIPTION "IPr-LAN-local-routings"
                 ::= {  staIprou 3 }

staIprouIprlanne OBJECT-TYPE
                 SYNTAX INTEGER
                 ACCESS read-only
                 STATUS mandatory
                 DESCRIPTION "IPr-LAN-network-errors"
                 ::= {  staIprou 4 }

staIprouIprlanro OBJECT-TYPE
                 SYNTAX INTEGER
                 ACCESS read-only
                 STATUS mandatory
                 DESCRIPTION "IPr-LAN-routing-errors"
                 ::= {  staIprou 5 }

staIprouIprlantt OBJECT-TYPE
                 SYNTAX INTEGER
                 ACCESS read-only
                 STATUS mandatory
                 DESCRIPTION "IPr-LAN-ttl-errors"
                 ::= {  staIprou 6 }

staIprouIprlanfi OBJECT-TYPE
                 SYNTAX INTEGER
                 ACCESS read-only
                 STATUS mandatory
                 DESCRIPTION "IPr-LAN-filters"
                 ::= {  staIprou 7 }

staIprouIprlandi OBJECT-TYPE
                 SYNTAX INTEGER
                 ACCESS read-only
                 STATUS mandatory
                 DESCRIPTION "IPr-LAN-discards"
                 ::= {  staIprou 8 }

staIprouIprwanrx OBJECT-TYPE
                 SYNTAX INTEGER
                 ACCESS read-only
                 STATUS mandatory
                 DESCRIPTION "IPr-WAN-rx"
                 ::= {  staIprou 9 }

staIprouIprwantx OBJECT-TYPE
                 SYNTAX INTEGER
                 ACCESS read-only
                 STATUS mandatory
                 DESCRIPTION "IPr-WAN-tx"
                 ::= {  staIprou 10 }

staIprouIprwanne OBJECT-TYPE
                 SYNTAX INTEGER
                 ACCESS read-only
                 STATUS mandatory
                 DESCRIPTION "IPr-WAN-network-errors"
                 ::= {  staIprou 11 }

staIprouIprwantt OBJECT-TYPE
                 SYNTAX INTEGER
                 ACCESS read-only
                 STATUS mandatory
                 DESCRIPTION "IPr-WAN-ttl-errors"
                 ::= {  staIprou 12 }

staIprouIprwanfi OBJECT-TYPE
                 SYNTAX INTEGER
                 ACCESS read-only
                 STATUS mandatory
                 DESCRIPTION "IPr-WAN-filters"
                 ::= {  staIprou 13 }

staIprouIprwandi OBJECT-TYPE
                 SYNTAX INTEGER
                 ACCESS read-only
                 STATUS mandatory
                 DESCRIPTION "IPr-WAN-discards"
                 ::= {  staIprou 14 }

staIprouIprwanty OBJECT-TYPE
                 SYNTAX INTEGER
                 ACCESS read-only
                 STATUS mandatory
                 DESCRIPTION "IPr-WAN-type-errors"
                 ::= {  staIprou 15 }

staIprouIprarper OBJECT-TYPE
                 SYNTAX INTEGER
                 ACCESS read-only
                 STATUS mandatory
                 DESCRIPTION "IPr-ARP-errors"
                 ::= {  staIprou 16 }

staIprouEstablis OBJECT-TYPE
                 SYNTAX SEQUENCE OF StaIprouEstablisRows
                 ACCESS not-accessible
                 STATUS mandatory
                 DESCRIPTION "Establish-table"
                 ::= {  staIprou 17 }

staIprouEstablisCols OBJECT-TYPE
                 SYNTAX StaIprouEstablisRows
                 ACCESS not-accessible
                 STATUS mandatory
                 DESCRIPTION "entry in table"
                 INDEX { staIprouEstablisTim }
                 ::= {  staIprouEstablis 1 }

StaIprouEstablisRows ::= SEQUENCE {
                 staIprouEstablisTim DisplayString,
                 staIprouEstablisDes IpAddress,
                 staIprouEstablisSrc IpAddress,
                 staIprouEstablisPro INTEGER,
                 staIprouEstablisDpo INTEGER,
                 staIprouEstablisSpo INTEGER
                }

staIprouEstablisTim OBJECT-TYPE
                    SYNTAX DisplayString
                    ACCESS read-only
                    STATUS mandatory
                    DESCRIPTION "Time"
                    ::= {  staIprouEstablisCols 1 }

staIprouEstablisDes OBJECT-TYPE
                    SYNTAX IpAddress
                    ACCESS read-only
                    STATUS mandatory
                    DESCRIPTION "Dest.-address"
                    ::= {  staIprouEstablisCols 2 }

staIprouEstablisSrc OBJECT-TYPE
                    SYNTAX IpAddress
                    ACCESS read-only
                    STATUS mandatory
                    DESCRIPTION "Src.-address"
                    ::= {  staIprouEstablisCols 3 }

staIprouEstablisPro OBJECT-TYPE
                    SYNTAX INTEGER {
                      icmp(1),
                      tcp(6),
                      udp(17),
                      igmp(2),
                      ggt(3),
                      egp(8),
                      cftp(62)
                    }
                    ACCESS read-only
                    STATUS mandatory
                    DESCRIPTION "Prot."
                    ::= {  staIprouEstablisCols 4 }

staIprouEstablisDpo OBJECT-TYPE
                    SYNTAX INTEGER
                    ACCESS read-only
                    STATUS mandatory
                    DESCRIPTION "D-port"
                    ::= {  staIprouEstablisCols 5 }

staIprouEstablisSpo OBJECT-TYPE
                    SYNTAX INTEGER
                    ACCESS read-only
                    STATUS mandatory
                    DESCRIPTION "S-port"
                    ::= {  staIprouEstablisCols 6 }

staConfi OBJECT IDENTIFIER ::= { sta 11}
staConfiLanactiv OBJECT-TYPE
                 SYNTAX INTEGER
                 ACCESS read-only
                 STATUS mandatory
                 DESCRIPTION "LAN-active-connections"
                 ::= {  staConfi 1 }

staConfiLantotal OBJECT-TYPE
                 SYNTAX INTEGER
                 ACCESS read-only
                 STATUS mandatory
                 DESCRIPTION "LAN-total-connections"
                 ::= {  staConfi 2 }

staConfiWanactiv OBJECT-TYPE
                 SYNTAX INTEGER
                 ACCESS read-only
                 STATUS mandatory
                 DESCRIPTION "WAN-active-connections"
                 ::= {  staConfi 3 }

staConfiWantotal OBJECT-TYPE
                 SYNTAX INTEGER
                 ACCESS read-only
                 STATUS mandatory
                 DESCRIPTION "WAN-total-connections"
                 ::= {  staConfi 4 }

staConfiOutbanda OBJECT-TYPE
                 SYNTAX INTEGER
                 ACCESS read-only
                 STATUS mandatory
                 DESCRIPTION "Outband-active-connections"
                 ::= {  staConfi 5 }

staConfiOutbandt OBJECT-TYPE
                 SYNTAX INTEGER
                 ACCESS read-only
                 STATUS mandatory
                 DESCRIPTION "Outband-total-connections"
                 ::= {  staConfi 6 }

staConfiOutbandb OBJECT-TYPE
                 SYNTAX INTEGER
                 ACCESS read-only
                 STATUS mandatory
                 DESCRIPTION "Outband-bitrate"
                 ::= {  staConfi 7 }

staConfiLoginerr OBJECT-TYPE
                 SYNTAX INTEGER
                 ACCESS read-only
                 STATUS mandatory
                 DESCRIPTION "Login-errors"
                 ::= {  staConfi 8 }

staConfiLoginloc OBJECT-TYPE
                 SYNTAX INTEGER
                 ACCESS read-only
                 STATUS mandatory
                 DESCRIPTION "Login-locks"
                 ::= {  staConfi 9 }

staConfiLoginrej OBJECT-TYPE
                 SYNTAX INTEGER
                 ACCESS read-only
                 STATUS mandatory
                 DESCRIPTION "Login-rejects"
                 ::= {  staConfi 10 }

staConfiDeleteva OBJECT-TYPE
                 SYNTAX INTEGER
                 ACCESS write-only
                 STATUS mandatory
                 DESCRIPTION "Delete-values"
                 ::= {  staConfi 11 }

staQueue OBJECT IDENTIFIER ::= { sta 12}
staQueueLanheap OBJECT-TYPE
                SYNTAX INTEGER
                ACCESS read-only
                STATUS mandatory
                DESCRIPTION "LAN-heap-packets"
                ::= {  staQueue 1 }

staQueueLanqueu OBJECT-TYPE
                SYNTAX INTEGER
                ACCESS read-only
                STATUS mandatory
                DESCRIPTION "LAN-queue-packets"
                ::= {  staQueue 2 }

staQueueWanheap OBJECT-TYPE
                SYNTAX INTEGER
                ACCESS read-only
                STATUS mandatory
                DESCRIPTION "WAN-heap-packets"
                ::= {  staQueue 3 }

staQueueWanqueu OBJECT-TYPE
                SYNTAX INTEGER
                ACCESS read-only
                STATUS mandatory
                DESCRIPTION "WAN-queue-packets"
                ::= {  staQueue 4 }

staQueueBridgei OBJECT-TYPE
                SYNTAX INTEGER
                ACCESS read-only
                STATUS mandatory
                DESCRIPTION "Bridge-internal-queue-packets"
                ::= {  staQueue 5 }

staQueueBridgee OBJECT-TYPE
                SYNTAX INTEGER
                ACCESS read-only
                STATUS mandatory
                DESCRIPTION "Bridge-external-queue-packets"
                ::= {  staQueue 6 }

staQueueArpquer OBJECT-TYPE
                SYNTAX INTEGER
                ACCESS read-only
                STATUS mandatory
                DESCRIPTION "ARP-query-queue-packets"
                ::= {  staQueue 7 }

staQueueArpqueu OBJECT-TYPE
                SYNTAX INTEGER
                ACCESS read-only
                STATUS mandatory
                DESCRIPTION "ARP-queue-packets"
                ::= {  staQueue 8 }

staQueueIpqueue OBJECT-TYPE
                SYNTAX INTEGER
                ACCESS read-only
                STATUS mandatory
                DESCRIPTION "IP-queue-packets"
                ::= {  staQueue 9 }

staQueueIpurgen OBJECT-TYPE
                SYNTAX INTEGER
                ACCESS read-only
                STATUS mandatory
                DESCRIPTION "IP-urgent-queue-packets"
                ::= {  staQueue 10 }

staQueueIcmpque OBJECT-TYPE
                SYNTAX INTEGER
                ACCESS read-only
                STATUS mandatory
                DESCRIPTION "ICMP-queue-packets"
                ::= {  staQueue 11 }

staQueueTcpqueu OBJECT-TYPE
                SYNTAX INTEGER
                ACCESS read-only
                STATUS mandatory
                DESCRIPTION "TCP-queue-packets"
                ::= {  staQueue 12 }

staQueueTftpser OBJECT-TYPE
                SYNTAX INTEGER
                ACCESS read-only
                STATUS mandatory
                DESCRIPTION "TFTP-server-queue-packets"
                ::= {  staQueue 13 }

staQueueSnmpque OBJECT-TYPE
                SYNTAX INTEGER
                ACCESS read-only
                STATUS mandatory
                DESCRIPTION "SNMP-queue-packets"
                ::= {  staQueue 14 }

staQueueIpxqueu OBJECT-TYPE
                SYNTAX INTEGER
                ACCESS read-only
                STATUS mandatory
                DESCRIPTION "IPX-queue-packets"
                ::= {  staQueue 15 }

staQueueRipquer OBJECT-TYPE
                SYNTAX INTEGER
                ACCESS read-only
                STATUS mandatory
                DESCRIPTION "RIP-query-queue-packets"
                ::= {  staQueue 16 }

staQueueSapqueu OBJECT-TYPE
                SYNTAX INTEGER
                ACCESS read-only
                STATUS mandatory
                DESCRIPTION "SAP-queue-packets"
                ::= {  staQueue 17 }

staQueueIpxwatc OBJECT-TYPE
                SYNTAX INTEGER
                ACCESS read-only
                STATUS mandatory
                DESCRIPTION "IPX-watchdog-queue-packets"
                ::= {  staQueue 18 }

staQueueSpxwatc OBJECT-TYPE
                SYNTAX INTEGER
                ACCESS read-only
                STATUS mandatory
                DESCRIPTION "SPX-watchdog-queue-packets"
                ::= {  staQueue 19 }

staQueueIpxrout OBJECT-TYPE
                SYNTAX INTEGER
                ACCESS read-only
                STATUS mandatory
                DESCRIPTION "IPX-router-queue-packets"
                ::= {  staQueue 21 }

staQueueProthea OBJECT-TYPE
                SYNTAX INTEGER
                ACCESS read-only
                STATUS mandatory
                DESCRIPTION "PROT-heap-packets"
                ::= {  staQueue 22 }

staQueueIprqueu OBJECT-TYPE
                SYNTAX INTEGER
                ACCESS read-only
                STATUS mandatory
                DESCRIPTION "IPR-queue-packets"
                ::= {  staQueue 24 }

staQueueDhcpser OBJECT-TYPE
                SYNTAX INTEGER
                ACCESS read-only
                STATUS mandatory
                DESCRIPTION "DHCP-server-queue-packets"
                ::= {  staQueue 27 }

staQueueDhcpcli OBJECT-TYPE
                SYNTAX INTEGER
                ACCESS read-only
                STATUS mandatory
                DESCRIPTION "DHCP-client-queue-packets"
                ::= {  staQueue 28 }

staQueueIprripq OBJECT-TYPE
                SYNTAX INTEGER
                ACCESS read-only
                STATUS mandatory
                DESCRIPTION "IPR-RIP-queue-packets"
                ::= {  staQueue 29 }

staQueueDnstxqu OBJECT-TYPE
                SYNTAX INTEGER
                ACCESS read-only
                STATUS mandatory
                DESCRIPTION "DNS-TX-queue-packets"
                ::= {  staQueue 30 }

staQueueDnsrxqu OBJECT-TYPE
                SYNTAX INTEGER
                ACCESS read-only
                STATUS mandatory
                DESCRIPTION "DNS-RX-queue-packets"
                ::= {  staQueue 31 }

staQueueIpmasqt OBJECT-TYPE
                SYNTAX INTEGER
                ACCESS read-only
                STATUS mandatory
                DESCRIPTION "IP-Masq-TX-queue-packets"
                ::= {  staQueue 32 }

staQueueIpmasqr OBJECT-TYPE
                SYNTAX INTEGER
                ACCESS read-only
                STATUS mandatory
                DESCRIPTION "IP-Masq-RX-queue-packets"
                ::= {  staQueue 33 }

staConns OBJECT-TYPE
         SYNTAX SEQUENCE OF StaConnsRows
         ACCESS not-accessible
         STATUS mandatory
         DESCRIPTION "Conn.-statistics"
         ::= {  sta 13 }

staConnsCols OBJECT-TYPE
         SYNTAX StaConnsRows
         ACCESS not-accessible
         STATUS mandatory
         DESCRIPTION "entry in table"
         INDEX { staConnsIfc }
         ::= {  staConns 1 }

StaConnsRows ::= SEQUENCE {
         staConnsIfc INTEGER,
         staConnsConn INTEGER,
         staConnsActi INTEGER,
         staConnsPass INTEGER,
         staConnsErro INTEGER,
         staConnsCont DisplayString,
         staConnsChar INTEGER
        }

staConnsIfc OBJECT-TYPE
             SYNTAX INTEGER {
               ch01(1),
               ch02(2),
               ch03(3),
               ch04(4),
               ch05(5),
               ch06(6),
               ch07(7),
               ch08(8),
               ch09(9),
               ch10(10),
               ch11(11),
               ch12(12)
             }
             ACCESS read-only
             STATUS mandatory
             DESCRIPTION "Ifc"
             ::= {  staConnsCols 1 }

staConnsConn OBJECT-TYPE
             SYNTAX INTEGER
             ACCESS read-only
             STATUS mandatory
             DESCRIPTION "Connections"
             ::= {  staConnsCols 2 }

staConnsActi OBJECT-TYPE
             SYNTAX INTEGER
             ACCESS read-only
             STATUS mandatory
             DESCRIPTION "active"
             ::= {  staConnsCols 3 }

staConnsPass OBJECT-TYPE
             SYNTAX INTEGER
             ACCESS read-only
             STATUS mandatory
             DESCRIPTION "passive"
             ::= {  staConnsCols 4 }

staConnsErro OBJECT-TYPE
             SYNTAX INTEGER
             ACCESS read-only
             STATUS mandatory
             DESCRIPTION "Errors"
             ::= {  staConnsCols 5 }

staConnsCont OBJECT-TYPE
             SYNTAX DisplayString
             ACCESS read-only
             STATUS mandatory
             DESCRIPTION "Con.-Time"
             ::= {  staConnsCols 6 }

staConnsChar OBJECT-TYPE
             SYNTAX INTEGER
             ACCESS read-only
             STATUS mandatory
             DESCRIPTION "Charge"
             ::= {  staConnsCols 7 }

staInfoc OBJECT-TYPE
         SYNTAX SEQUENCE OF StaInfocRows
         ACCESS not-accessible
         STATUS mandatory
         DESCRIPTION "Info-connection"
         ::= {  sta 14 }

staInfocCols OBJECT-TYPE
         SYNTAX StaInfocRows
         ACCESS not-accessible
         STATUS mandatory
         DESCRIPTION "entry in table"
         INDEX { staInfocIfc }
         ::= {  staInfoc 1 }

StaInfocRows ::= SEQUENCE {
         staInfocIfc INTEGER,
         staInfocSta DisplayString,
         staInfocMod INTEGER,
         staInfocDia DisplayString,
         staInfocDev DisplayString,
         staInfocB1d INTEGER,
         staInfocB2d INTEGER
        }

staInfocIfc OBJECT-TYPE
            SYNTAX INTEGER {
              ch01(1),
              ch02(2),
              ch03(3),
              ch04(4),
              ch05(5),
              ch06(6),
              ch07(7),
              ch08(8),
              ch09(9),
              ch10(10),
              ch11(11),
              ch12(12)
            }
            ACCESS read-only
            STATUS mandatory
            DESCRIPTION "Ifc"
            ::= {  staInfocCols 1 }

staInfocSta OBJECT-TYPE
            SYNTAX DisplayString
            ACCESS read-only
            STATUS mandatory
            DESCRIPTION "Status"
            ::= {  staInfocCols 2 }

staInfocMod OBJECT-TYPE
            SYNTAX INTEGER {
              unknown(0),
              active(4),
              passive(5),
              callback(9)
            }
            ACCESS read-only
            STATUS mandatory
            DESCRIPTION "Mode"
            ::= {  staInfocCols 3 }

staInfocDia OBJECT-TYPE
            SYNTAX DisplayString
            ACCESS read-only
            STATUS mandatory
            DESCRIPTION "Dialup-remote"
            ::= {  staInfocCols 4 }

staInfocDev OBJECT-TYPE
            SYNTAX DisplayString
            ACCESS read-only
            STATUS mandatory
            DESCRIPTION "Device-name"
            ::= {  staInfocCols 5 }

staInfocB1d OBJECT-TYPE
            SYNTAX INTEGER
            ACCESS read-only
            STATUS mandatory
            DESCRIPTION "B1-DT"
            ::= {  staInfocCols 6 }

staInfocB2d OBJECT-TYPE
            SYNTAX INTEGER
            ACCESS read-only
            STATUS mandatory
            DESCRIPTION "B2-DT"
            ::= {  staInfocCols 7 }

staLayer OBJECT-TYPE
         SYNTAX SEQUENCE OF StaLayerRows
         ACCESS not-accessible
         STATUS mandatory
         DESCRIPTION "Layer-connection"
         ::= {  sta 15 }

staLayerCols OBJECT-TYPE
         SYNTAX StaLayerRows
         ACCESS not-accessible
         STATUS mandatory
         DESCRIPTION "entry in table"
         INDEX { staLayerIfc }
         ::= {  staLayer 1 }

StaLayerRows ::= SEQUENCE {
         staLayerIfc INTEGER,
         staLayerWanl DisplayString,
         staLayerEnca INTEGER,
         staLayerLay3 INTEGER,
         staLayerLay2 INTEGER,
         staLayerL2op INTEGER,
         staLayerLay1 INTEGER,
         staLayerL1pa INTEGER
        }

staLayerIfc OBJECT-TYPE
             SYNTAX INTEGER {
               ch01(1),
               ch02(2),
               ch03(3),
               ch04(4),
               ch05(5),
               ch06(6),
               ch07(7),
               ch08(8),
               ch09(9),
               ch10(10),
               ch11(11),
               ch12(12)
             }
             ACCESS read-only
             STATUS mandatory
             DESCRIPTION "Ifc"
             ::= {  staLayerCols 1 }

staLayerWanl OBJECT-TYPE
             SYNTAX DisplayString
             ACCESS read-only
             STATUS mandatory
             DESCRIPTION "WAN-layer"
             ::= {  staLayerCols 2 }

staLayerEnca OBJECT-TYPE
             SYNTAX INTEGER {
               ether(0),
               trans(255)
             }
             ACCESS read-only
             STATUS mandatory
             DESCRIPTION "Encaps."
             ::= {  staLayerCols 3 }

staLayerLay3 OBJECT-TYPE
             SYNTAX INTEGER {
               ppp(4),
               appp(5),
               scppp(6),
               scappp(7),
               sctrans(8),
               elsa(0),
               trans(255)
             }
             ACCESS read-only
             STATUS mandatory
             DESCRIPTION "Lay-3"
             ::= {  staLayerCols 4 }

staLayerLay2 OBJECT-TYPE
             SYNTAX INTEGER {
               sscop(6),
               pppoe(5),
               x75lapb(0),
               trans(1)
             }
             ACCESS read-only
             STATUS mandatory
             DESCRIPTION "Lay-2"
             ::= {  staLayerCols 5 }

staLayerL2op OBJECT-TYPE
             SYNTAX INTEGER {
               none(255),
               compr(0),
               bundle(1),
               bnd-and-cmpr(2)
             }
             ACCESS read-only
             STATUS mandatory
             DESCRIPTION "L2-Opt."
             ::= {  staLayerCols 6 }

staLayerLay1 OBJECT-TYPE
             SYNTAX INTEGER {
               aal-5(2),
               eth-10(4),
               hdlc64k(0),
               hdlc56k(1),
               v110-9k6(3),
               v110-19k2(67),
               v110-38k4(131),
               modem(5)
             }
             ACCESS read-only
             STATUS mandatory
             DESCRIPTION "Lay-1"
             ::= {  staLayerCols 7 }

staLayerL1pa OBJECT-TYPE
             SYNTAX INTEGER {
               none(0),
               v21-300(1),
               v23-600(2),
               v23-1200(3),
               v22-1200(4),
               v22bis-2400(5),
               v32qam-4800(6),
               v32qam-9600(7),
               v32bis-7200(8),
               v32tcm-9600(9),
               v32bis-12000(10),
               v32bis-14400(11),
               v34-2400(12),
               v34-4800(13),
               v34-7200(14),
               v34-9600(15),
               v34-12000(16),
               v34-14400(17),
               v34-16800(18),
               v34-19200(19),
               v34-21600(20),
               v34-24000(21),
               v34-26400(22),
               v34-28800(23),
               v34-31200(24),
               v34-33600(25),
               v90-28000(26),
               v90-29333(27),
               v90-30667(28),
               v90-32000(29),
               v90-33333(30),
               v90-34667(31),
               v90-36000(32),
               v90-37333(33),
               v90-38667(34),
               v90-40000(35),
               v90-41333(36),
               v90-42667(37),
               v90-44000(38),
               v90-45333(39),
               v90-46667(40),
               v90-48000(41),
               v90-49333(42),
               v90-50667(43),
               v90-52000(44),
               v90-53333(45),
               v90-54667(46),
               v90-56000(47)
             }
             ACCESS read-only
             STATUS mandatory
             DESCRIPTION "L1-Parameter"
             ::= {  staLayerCols 8 }

staCalli OBJECT-TYPE
         SYNTAX SEQUENCE OF StaCalliRows
         ACCESS not-accessible
         STATUS mandatory
         DESCRIPTION "Call-info-table"
         ::= {  sta 16 }

staCalliCols OBJECT-TYPE
         SYNTAX StaCalliRows
         ACCESS not-accessible
         STATUS mandatory
         DESCRIPTION "entry in table"
         INDEX { staCalliSys }
         ::= {  staCalli 1 }

StaCalliRows ::= SEQUENCE {
         staCalliSys DisplayString,
         staCalliIfc INTEGER,
         staCalliCli DisplayString,
         staCalliDia DisplayString,
         staCalliCap INTEGER,
         staCalliBch INTEGER
        }

staCalliSys OBJECT-TYPE
            SYNTAX DisplayString
            ACCESS read-only
            STATUS mandatory
            DESCRIPTION "System-time"
            ::= {  staCalliCols 1 }

staCalliIfc OBJECT-TYPE
            SYNTAX INTEGER {
              s0-1(1),
              s0-2(2),
              s0-3(3),
              s0-4(4)
            }
            ACCESS read-only
            STATUS mandatory
            DESCRIPTION "Ifc"
            ::= {  staCalliCols 2 }

staCalliCli OBJECT-TYPE
            SYNTAX DisplayString
            ACCESS read-only
            STATUS mandatory
            DESCRIPTION "CLIP-Caller"
            ::= {  staCalliCols 3 }

staCalliDia OBJECT-TYPE
            SYNTAX DisplayString
            ACCESS read-only
            STATUS mandatory
            DESCRIPTION "Dial-Caller"
            ::= {  staCalliCols 4 }

staCalliCap OBJECT-TYPE
            SYNTAX INTEGER {
              unknown(255),
              hdlc64k(0),
              hdlc56k(1),
              v110-9k6(3),
              v110-19k2(67),
              v110-38k4(131),
              modem(5),
              a-3-1khz(13),
              speech(14),
              fax-g2-3(15)
            }
            ACCESS read-only
            STATUS mandatory
            DESCRIPTION "Capab."
            ::= {  staCalliCols 5 }

staCalliBch OBJECT-TYPE
            SYNTAX INTEGER
            ACCESS read-only
            STATUS mandatory
            DESCRIPTION "B-chan."
            ::= {  staCalliCols 6 }

staRemot OBJECT-TYPE
         SYNTAX SEQUENCE OF StaRemotRows
         ACCESS not-accessible
         STATUS mandatory
         DESCRIPTION "Remote-stat."
         ::= {  sta 17 }

staRemotCols OBJECT-TYPE
         SYNTAX StaRemotRows
         ACCESS not-accessible
         STATUS mandatory
         DESCRIPTION "entry in table"
         INDEX { staRemotConns }
         ::= {  staRemot 1 }

StaRemotRows ::= SEQUENCE {
         staRemotConns DisplayString,
         staRemotRemot DisplayString,
         staRemotMode INTEGER,
         staRemotIfc INTEGER,
         staRemotConnt DisplayString,
         staRemotCharg INTEGER
        }

staRemotConns OBJECT-TYPE
              SYNTAX DisplayString
              ACCESS read-only
              STATUS mandatory
              DESCRIPTION "Conn.-start"
              ::= {  staRemotCols 1 }

staRemotRemot OBJECT-TYPE
              SYNTAX DisplayString
              ACCESS read-only
              STATUS mandatory
              DESCRIPTION "Remote-ID"
              ::= {  staRemotCols 2 }

staRemotMode OBJECT-TYPE
              SYNTAX INTEGER {
                unknown(0),
                active(4),
                passive(5),
                callback(9)
              }
              ACCESS read-only
              STATUS mandatory
              DESCRIPTION "Mode"
              ::= {  staRemotCols 3 }

staRemotIfc OBJECT-TYPE
              SYNTAX INTEGER {
                ch01(1),
                ch02(2),
                ch03(3),
                ch04(4),
                ch05(5),
                ch06(6),
                ch07(7),
                ch08(8),
                ch09(9),
                ch10(10),
                ch11(11),
                ch12(12)
              }
              ACCESS read-only
              STATUS mandatory
              DESCRIPTION "Ifc"
              ::= {  staRemotCols 4 }

staRemotConnt OBJECT-TYPE
              SYNTAX DisplayString
              ACCESS read-only
              STATUS mandatory
              DESCRIPTION "Conn.-time"
              ::= {  staRemotCols 5 }

staRemotCharg OBJECT-TYPE
              SYNTAX INTEGER
              ACCESS read-only
              STATUS mandatory
              DESCRIPTION "Charge"
              ::= {  staRemotCols 6 }

staS0bus OBJECT IDENTIFIER ::= { sta 23}
staS0busDin OBJECT-TYPE
            SYNTAX SEQUENCE OF StaS0busDinRows
            ACCESS not-accessible
            STATUS mandatory
            DESCRIPTION "D-info"
            ::= {  staS0bus 1 }

staS0busDinCols OBJECT-TYPE
            SYNTAX StaS0busDinRows
            ACCESS not-accessible
            STATUS mandatory
            DESCRIPTION "entry in table"
            INDEX { staS0busDinCha }
            ::= {  staS0busDin 1 }

StaS0busDinRows ::= SEQUENCE {
            staS0busDinCha INTEGER,
            staS0busDinPro INTEGER,
            staS0busDinLay INTEGER,
            staS0busDinTei INTEGER,
            staS0busDinS0a INTEGER
           }

staS0busDinCha OBJECT-TYPE
               SYNTAX INTEGER {
                 s0-1(1),
                 s0-2(2),
                 s0-3(3),
                 s0-4(4)
               }
               ACCESS read-only
               STATUS mandatory
               DESCRIPTION "Channel"
               ::= {  staS0busDinCols 1 }

staS0busDinPro OBJECT-TYPE
               SYNTAX INTEGER {
                 dss1(1),
                 tr1-6(2),
                 p2p-dss1(4),
                 auto(255)
               }
               ACCESS read-only
               STATUS mandatory
               DESCRIPTION "Protocol"
               ::= {  staS0busDinCols 2 }

staS0busDinLay OBJECT-TYPE
               SYNTAX INTEGER {
                 yes(1),
                 no(0)
               }
               ACCESS read-only
               STATUS mandatory
               DESCRIPTION "Layer-2"
               ::= {  staS0busDinCols 3 }

staS0busDinTei OBJECT-TYPE
               SYNTAX INTEGER {
                 yes(1),
                 no(0)
               }
               ACCESS read-only
               STATUS mandatory
               DESCRIPTION "TEI"
               ::= {  staS0busDinCols 4 }

staS0busDinS0a OBJECT-TYPE
               SYNTAX INTEGER {
                 yes(1),
                 no(0)
               }
               ACCESS read-only
               STATUS mandatory
               DESCRIPTION "S0-activation"
               ::= {  staS0busDinCols 5 }

staS0busD2s OBJECT-TYPE
            SYNTAX SEQUENCE OF StaS0busD2sRows
            ACCESS not-accessible
            STATUS mandatory
            DESCRIPTION "D2-statistics"
            ::= {  staS0bus 3 }

staS0busD2sCols OBJECT-TYPE
            SYNTAX StaS0busD2sRows
            ACCESS not-accessible
            STATUS mandatory
            DESCRIPTION "entry in table"
            INDEX { staS0busD2sCha }
            ::= {  staS0busD2s 1 }

StaS0busD2sRows ::= SEQUENCE {
            staS0busD2sCha INTEGER,
            staS0busD2sTei INTEGER,
            staS0busD2sL2a INTEGER,
            staS0busD2sCon INTEGER
           }

staS0busD2sCha OBJECT-TYPE
               SYNTAX INTEGER {
                 s0-1(1),
                 s0-1(2),
                 s0-2(3),
                 s0-2(4),
                 s0-3(5),
                 s0-3(6),
                 s0-4(7),
                 s0-4(8)
               }
               ACCESS read-only
               STATUS mandatory
               DESCRIPTION "Channel"
               ::= {  staS0busD2sCols 1 }

staS0busD2sTei OBJECT-TYPE
               SYNTAX INTEGER {
                 none(128)
               }
               ACCESS read-only
               STATUS mandatory
               DESCRIPTION "TEI"
               ::= {  staS0busD2sCols 2 }

staS0busD2sL2a OBJECT-TYPE
               SYNTAX INTEGER {
                 yes(1),
                 no(0)
               }
               ACCESS read-only
               STATUS mandatory
               DESCRIPTION "L2-activation"
               ::= {  staS0busD2sCols 3 }

staS0busD2sCon OBJECT-TYPE
               SYNTAX INTEGER
               ACCESS read-only
               STATUS mandatory
               DESCRIPTION "Connections"
               ::= {  staS0busD2sCols 4 }

staChann OBJECT-TYPE
         SYNTAX SEQUENCE OF StaChannRows
         ACCESS not-accessible
         STATUS mandatory
         DESCRIPTION "Channel-statistics"
         ::= {  sta 19 }

staChannCols OBJECT-TYPE
         SYNTAX StaChannRows
         ACCESS not-accessible
         STATUS mandatory
         DESCRIPTION "entry in table"
         INDEX { staChannChan }
         ::= {  staChann 1 }

StaChannRows ::= SEQUENCE {
         staChannChan INTEGER,
         staChannPlci INTEGER,
         staChannBus INTEGER,
         staChannState INTEGER,
         staChannApp INTEGER,
         staChannMode INTEGER,
         staChannCause INTEGER,
         staChannNumbe DisplayString,
         staChannSubad INTEGER,
         staChannCharg INTEGER,
         staChannConns INTEGER,
         staChannConnt INTEGER,
         staChannExtra DisplayString,
         staChannIsdnd DisplayString
        }

staChannChan OBJECT-TYPE
              SYNTAX INTEGER {
                s0-1-err(1),
                s0-1-b1(2),
                s0-1-b2(3),
                ab-err(4),
                ab-1(5),
                ab-2(6),
                ab-3(7),
                ab-4(8)
              }
              ACCESS read-only
              STATUS mandatory
              DESCRIPTION "Chan."
              ::= {  staChannCols 1 }

staChannPlci OBJECT-TYPE
              SYNTAX INTEGER
              ACCESS read-only
              STATUS mandatory
              DESCRIPTION "PLCI"
              ::= {  staChannCols 2 }

staChannBus OBJECT-TYPE
              SYNTAX INTEGER
              ACCESS read-only
              STATUS mandatory
              DESCRIPTION "Bus"
              ::= {  staChannCols 3 }

staChannState OBJECT-TYPE
              SYNTAX INTEGER
              ACCESS read-only
              STATUS mandatory
              DESCRIPTION "State"
              ::= {  staChannCols 4 }

staChannApp OBJECT-TYPE
              SYNTAX INTEGER {
                none(0),
                router(1),
                capi(2),
                a-b(3),
                time-module(255)
              }
              ACCESS read-only
              STATUS mandatory
              DESCRIPTION "App"
              ::= {  staChannCols 5 }

staChannMode OBJECT-TYPE
              SYNTAX INTEGER {
                unk(0),
                act(1),
                pas(2),
                perm(3)
              }
              ACCESS read-only
              STATUS mandatory
              DESCRIPTION "Mode"
              ::= {  staChannCols 6 }

staChannCause OBJECT-TYPE
              SYNTAX INTEGER
              ACCESS read-write
              STATUS mandatory
              DESCRIPTION "Cause"
              ::= {  staChannCols 7 }

staChannNumbe OBJECT-TYPE
              SYNTAX DisplayString
              ACCESS read-only
              STATUS mandatory
              DESCRIPTION "Number"
              ::= {  staChannCols 8 }

staChannSubad OBJECT-TYPE
              SYNTAX INTEGER
              ACCESS read-only
              STATUS mandatory
              DESCRIPTION "Subaddress"
              ::= {  staChannCols 9 }

staChannCharg OBJECT-TYPE
              SYNTAX INTEGER
              ACCESS read-only
              STATUS mandatory
              DESCRIPTION "Charge"
              ::= {  staChannCols 10 }

staChannConns OBJECT-TYPE
              SYNTAX INTEGER
              ACCESS read-only
              STATUS mandatory
              DESCRIPTION "Conn.-start"
              ::= {  staChannCols 13 }

staChannConnt OBJECT-TYPE
              SYNTAX INTEGER
              ACCESS read-only
              STATUS mandatory
              DESCRIPTION "Conn.-time"
              ::= {  staChannCols 12 }

staChannExtra OBJECT-TYPE
              SYNTAX DisplayString
              ACCESS read-only
              STATUS mandatory
              DESCRIPTION "Extra"
              ::= {  staChannCols 11 }

staChannIsdnd OBJECT-TYPE
              SYNTAX DisplayString
              ACCESS read-only
              STATUS mandatory
              DESCRIPTION "ISDN-display"
              ::= {  staChannCols 14 }

staTimes OBJECT IDENTIFIER ::= { sta 21}
staTimesCur OBJECT-TYPE
            SYNTAX DisplayString
            ACCESS read-only
            STATUS mandatory
            DESCRIPTION "Current-time"
            ::= {  staTimes 1 }

staTimesSou OBJECT-TYPE
            SYNTAX INTEGER {
              manual(1),
              isdn(2),
              lan(3),
              ram(4),
              lanconfig(8),
              no(0)
            }
            ACCESS read-only
            STATUS mandatory
            DESCRIPTION "Source"
            ::= {  staTimes 2 }

staTimesSet OBJECT-TYPE
            SYNTAX INTEGER
            ACCESS read-only
            STATUS mandatory
            DESCRIPTION "Setup"
            ::= {  staTimes 3 }

staTimesIsd OBJECT IDENTIFIER ::= { staTimes 4}
staTimesIsdConne OBJECT-TYPE
                 SYNTAX INTEGER
                 ACCESS read-only
                 STATUS mandatory
                 DESCRIPTION "Connection"
                 ::= {  staTimesIsd 1 }

staTimesIsdInfor OBJECT-TYPE
                 SYNTAX INTEGER
                 ACCESS read-only
                 STATUS mandatory
                 DESCRIPTION "Information"
                 ::= {  staTimesIsd 2 }

staTimesIsdInfoe OBJECT-TYPE
                 SYNTAX INTEGER
                 ACCESS read-only
                 STATUS mandatory
                 DESCRIPTION "Info-error"
                 ::= {  staTimesIsd 3 }

staTimesIsdUnits OBJECT-TYPE
                 SYNTAX INTEGER
                 ACCESS read-only
                 STATUS mandatory
                 DESCRIPTION "Units"
                 ::= {  staTimesIsd 4 }

staTimesIsdDelet OBJECT-TYPE
                 SYNTAX INTEGER
                 ACCESS write-only
                 STATUS mandatory
                 DESCRIPTION "Delete-values"
                 ::= {  staTimesIsd 5 }

staLcrst OBJECT IDENTIFIER ::= { sta 22}
staLcrstTot OBJECT-TYPE
            SYNTAX INTEGER
            ACCESS read-only
            STATUS mandatory
            DESCRIPTION "Total-calls"
            ::= {  staLcrst 1 }

staLcrstFou OBJECT-TYPE
            SYNTAX INTEGER
            ACCESS read-only
            STATUS mandatory
            DESCRIPTION "Found-events"
            ::= {  staLcrst 2 }

staLcrstNot OBJECT-TYPE
            SYNTAX INTEGER
            ACCESS read-only
            STATUS mandatory
            DESCRIPTION "Notfound-errors"
            ::= {  staLcrst 3 }

staLcrstMis OBJECT-TYPE
            SYNTAX INTEGER
            ACCESS read-only
            STATUS mandatory
            DESCRIPTION "Missingtime-errors"
            ::= {  staLcrst 4 }

staLcrstPro OBJECT-TYPE
            SYNTAX SEQUENCE OF StaLcrstProRows
            ACCESS not-accessible
            STATUS mandatory
            DESCRIPTION "Provider-statistics"
            ::= {  staLcrst 6 }

staLcrstProCols OBJECT-TYPE
            SYNTAX StaLcrstProRows
            ACCESS not-accessible
            STATUS mandatory
            DESCRIPTION "entry in table"
            INDEX { staLcrstProPro }
            ::= {  staLcrstPro 1 }

StaLcrstProRows ::= SEQUENCE {
            staLcrstProPro DisplayString,
            staLcrstProFai INTEGER,
            staLcrstProSuc INTEGER
           }

staLcrstProPro OBJECT-TYPE
               SYNTAX DisplayString
               ACCESS read-only
               STATUS mandatory
               DESCRIPTION "Provider"
               ::= {  staLcrstProCols 1 }

staLcrstProFai OBJECT-TYPE
               SYNTAX INTEGER
               ACCESS read-only
               STATUS mandatory
               DESCRIPTION "Failures"
               ::= {  staLcrstProCols 2 }

staLcrstProSuc OBJECT-TYPE
               SYNTAX INTEGER
               ACCESS read-only
               STATUS mandatory
               DESCRIPTION "Successes"
               ::= {  staLcrstProCols 3 }

staLcrstDel OBJECT-TYPE
            SYNTAX INTEGER
            ACCESS write-only
            STATUS mandatory
            DESCRIPTION "Delete-values"
            ::= {  staLcrst 7 }

staCharg OBJECT IDENTIFIER ::= { sta 24}
staChargSpareda OBJECT-TYPE
                SYNTAX INTEGER
                ACCESS read-only
                STATUS mandatory
                DESCRIPTION "Spare-days/per."
                ::= {  staCharg 6 }

staChargSpareun OBJECT-TYPE
                SYNTAX INTEGER
                ACCESS read-only
                STATUS mandatory
                DESCRIPTION "Spare-units"
                ::= {  staCharg 4 }

staChargRouteru OBJECT-TYPE
                SYNTAX INTEGER
                ACCESS read-only
                STATUS mandatory
                DESCRIPTION "Router-units"
                ::= {  staCharg 7 }

staChargTotalun OBJECT-TYPE
                SYNTAX INTEGER
                ACCESS read-only
                STATUS mandatory
                DESCRIPTION "Total-units"
                ::= {  staCharg 8 }

staChargSparemi OBJECT-TYPE
                SYNTAX INTEGER
                ACCESS read-only
                STATUS mandatory
                DESCRIPTION "Spare-minutes"
                ::= {  staCharg 1 }

staChargRouterm OBJECT-TYPE
                SYNTAX INTEGER
                ACCESS read-only
                STATUS mandatory
                DESCRIPTION "Router-minutes-active"
                ::= {  staCharg 9 }

staChargTablebu OBJECT-TYPE
                SYNTAX SEQUENCE OF StaChargTablebuRows
                ACCESS not-accessible
                STATUS mandatory
                DESCRIPTION "Table-budget"
                ::= {  staCharg 5 }

staChargTablebuCols OBJECT-TYPE
                SYNTAX StaChargTablebuRows
                ACCESS not-accessible
                STATUS mandatory
                DESCRIPTION "entry in table"
                INDEX { staChargTablebuIfc }
                ::= {  staChargTablebu 1 }

StaChargTablebuRows ::= SEQUENCE {
                staChargTablebuIfc INTEGER,
                staChargTablebuBud INTEGER,
                staChargTablebuSpa INTEGER,
                staChargTablebuTot INTEGER
               }

staChargTablebuIfc OBJECT-TYPE
                   SYNTAX INTEGER {
                     router(1),
                     lancapi(2),
                     ab-1(3),
                     ab-2(4),
                     ab-3(5),
                     ab-4(6),
                     time-modul(255)
                   }
                   ACCESS read-only
                   STATUS mandatory
                   DESCRIPTION "Ifc"
                   ::= {  staChargTablebuCols 1 }

staChargTablebuBud OBJECT-TYPE
                   SYNTAX INTEGER
                   ACCESS read-only
                   STATUS mandatory
                   DESCRIPTION "Budget-units"
                   ::= {  staChargTablebuCols 2 }

staChargTablebuSpa OBJECT-TYPE
                   SYNTAX INTEGER
                   ACCESS read-only
                   STATUS mandatory
                   DESCRIPTION "Spare-Budget"
                   ::= {  staChargTablebuCols 3 }

staChargTablebuTot OBJECT-TYPE
                   SYNTAX INTEGER
                   ACCESS read-only
                   STATUS mandatory
                   DESCRIPTION "Total-units"
                   ::= {  staChargTablebuCols 4 }

staChargTimetab OBJECT-TYPE
                SYNTAX SEQUENCE OF StaChargTimetabRows
                ACCESS not-accessible
                STATUS mandatory
                DESCRIPTION "Time-table"
                ::= {  staCharg 2 }

staChargTimetabCols OBJECT-TYPE
                SYNTAX StaChargTimetabRows
                ACCESS not-accessible
                STATUS mandatory
                DESCRIPTION "entry in table"
                INDEX { staChargTimetabIfc }
                ::= {  staChargTimetab 1 }

StaChargTimetabRows ::= SEQUENCE {
                staChargTimetabIfc INTEGER,
                staChargTimetabBudgetmi INTEGER,
                staChargTimetabSparemin INTEGER,
                staChargTimetabMinutesa INTEGER,
                staChargTimetabMinutesp INTEGER
               }

staChargTimetabIfc OBJECT-TYPE
                        SYNTAX INTEGER {
                          router(1),
                          lancapi(2),
                          ab-1(3),
                          ab-2(4),
                          ab-3(5),
                          ab-4(6),
                          time-Modul(255)
                        }
                        ACCESS read-only
                        STATUS mandatory
                        DESCRIPTION "Ifc"
                        ::= {  staChargTimetabCols 1 }

staChargTimetabBudgetmi OBJECT-TYPE
                        SYNTAX INTEGER
                        ACCESS read-only
                        STATUS mandatory
                        DESCRIPTION "Budget-minutes"
                        ::= {  staChargTimetabCols 2 }

staChargTimetabSparemin OBJECT-TYPE
                        SYNTAX INTEGER
                        ACCESS read-only
                        STATUS mandatory
                        DESCRIPTION "Spare-minutes"
                        ::= {  staChargTimetabCols 3 }

staChargTimetabMinutesa OBJECT-TYPE
                        SYNTAX INTEGER
                        ACCESS read-only
                        STATUS mandatory
                        DESCRIPTION "Minutes-active"
                        ::= {  staChargTimetabCols 4 }

staChargTimetabMinutesp OBJECT-TYPE
                        SYNTAX INTEGER
                        ACCESS read-only
                        STATUS mandatory
                        DESCRIPTION "Minutes-passive"
                        ::= {  staChargTimetabCols 5 }

staChargDeletev OBJECT-TYPE
                SYNTAX INTEGER
                ACCESS write-only
                STATUS mandatory
                DESCRIPTION "Delete-values"
                ::= {  staCharg 3 }

staDelet OBJECT-TYPE
         SYNTAX INTEGER
         ACCESS write-only
         STATUS mandatory
         DESCRIPTION "Delete-values"
         ::= {  sta 20 }

staDhcpc OBJECT IDENTIFIER ::= { sta 32}
staDhcpcState OBJECT-TYPE
                SYNTAX INTEGER {
                  idle(0),
                  init-reboot(1),
                  rebooting(2),
                  init(3),
                  selecting(4),
                  request(5),
                  wait-arp-request(6),
                  bound(7),
                  renewing(8),
                  rebinding(9)
                }
                ACCESS read-only
                STATUS mandatory
                DESCRIPTION "State"
                ::= {  staDhcpc 1 }

staDhcpcLeaseti OBJECT-TYPE
                SYNTAX INTEGER
                ACCESS read-only
                STATUS mandatory
                DESCRIPTION "Lease-time"
                ::= {  staDhcpc 2 }

staDhcpcYouripa OBJECT-TYPE
                SYNTAX IpAddress
                ACCESS read-only
                STATUS mandatory
                DESCRIPTION "Your-IP-address"
                ::= {  staDhcpc 3 }

staDhcpcYouripn OBJECT-TYPE
                SYNTAX IpAddress
                ACCESS read-only
                STATUS mandatory
                DESCRIPTION "Your-IP-netmask"
                ::= {  staDhcpc 4 }

staDhcpcGateway OBJECT-TYPE
                SYNTAX IpAddress
                ACCESS read-only
                STATUS mandatory
                DESCRIPTION "Gateway-IP-address"
                ::= {  staDhcpc 5 }

staDhcpcServeri OBJECT-TYPE
                SYNTAX IpAddress
                ACCESS read-only
                STATUS mandatory
                DESCRIPTION "Server-IP-address"
                ::= {  staDhcpc 6 }

staDhcpcSecurit OBJECT-TYPE
                SYNTAX IpAddress
                ACCESS read-only
                STATUS mandatory
                DESCRIPTION "Security-server"
                ::= {  staDhcpc 7 }

staDhcpcTimeoff OBJECT-TYPE
                SYNTAX INTEGER
                ACCESS read-only
                STATUS mandatory
                DESCRIPTION "Time-offset"
                ::= {  staDhcpc 8 }

staDhcpcTimeser OBJECT-TYPE
                SYNTAX IpAddress
                ACCESS read-only
                STATUS mandatory
                DESCRIPTION "Time-server"
                ::= {  staDhcpc 9 }

staDhcpcTableti OBJECT-TYPE
                SYNTAX SEQUENCE OF StaDhcpcTabletiRows
                ACCESS not-accessible
                STATUS mandatory
                DESCRIPTION "Table-Time-server"
                ::= {  staDhcpc 10 }

staDhcpcTabletiCols OBJECT-TYPE
                SYNTAX StaDhcpcTabletiRows
                ACCESS not-accessible
                STATUS mandatory
                DESCRIPTION "entry in table"
                INDEX { staDhcpcTabletiIpa }
                ::= {  staDhcpcTableti 1 }

StaDhcpcTabletiRows ::= SEQUENCE {
                staDhcpcTabletiIpa IpAddress
               }

staDhcpcTabletiIpa OBJECT-TYPE
                   SYNTAX IpAddress
                   ACCESS read-only
                   STATUS mandatory
                   DESCRIPTION "IP-address"
                   ::= {  staDhcpcTabletiCols 1 }

staDhcpcTablero OBJECT-TYPE
                SYNTAX SEQUENCE OF StaDhcpcTableroRows
                ACCESS not-accessible
                STATUS mandatory
                DESCRIPTION "Table-router"
                ::= {  staDhcpc 11 }

staDhcpcTableroCols OBJECT-TYPE
                SYNTAX StaDhcpcTableroRows
                ACCESS not-accessible
                STATUS mandatory
                DESCRIPTION "entry in table"
                INDEX { staDhcpcTableroIpa }
                ::= {  staDhcpcTablero 1 }

StaDhcpcTableroRows ::= SEQUENCE {
                staDhcpcTableroIpa IpAddress
               }

staDhcpcTableroIpa OBJECT-TYPE
                   SYNTAX IpAddress
                   ACCESS read-only
                   STATUS mandatory
                   DESCRIPTION "IP-address"
                   ::= {  staDhcpcTableroCols 1 }

staDhcpcTablena OBJECT-TYPE
                SYNTAX SEQUENCE OF StaDhcpcTablenaRows
                ACCESS not-accessible
                STATUS mandatory
                DESCRIPTION "Table-name-server"
                ::= {  staDhcpc 12 }

staDhcpcTablenaCols OBJECT-TYPE
                SYNTAX StaDhcpcTablenaRows
                ACCESS not-accessible
                STATUS mandatory
                DESCRIPTION "entry in table"
                INDEX { staDhcpcTablenaIpa }
                ::= {  staDhcpcTablena 1 }

StaDhcpcTablenaRows ::= SEQUENCE {
                staDhcpcTablenaIpa IpAddress
               }

staDhcpcTablenaIpa OBJECT-TYPE
                   SYNTAX IpAddress
                   ACCESS read-only
                   STATUS mandatory
                   DESCRIPTION "IP-address"
                   ::= {  staDhcpcTablenaCols 1 }

staDhcpcTabledo OBJECT-TYPE
                SYNTAX SEQUENCE OF StaDhcpcTabledoRows
                ACCESS not-accessible
                STATUS mandatory
                DESCRIPTION "Table-domain-name-server"
                ::= {  staDhcpc 13 }

staDhcpcTabledoCols OBJECT-TYPE
                SYNTAX StaDhcpcTabledoRows
                ACCESS not-accessible
                STATUS mandatory
                DESCRIPTION "entry in table"
                INDEX { staDhcpcTabledoIpa }
                ::= {  staDhcpcTabledo 1 }

StaDhcpcTabledoRows ::= SEQUENCE {
                staDhcpcTabledoIpa IpAddress
               }

staDhcpcTabledoIpa OBJECT-TYPE
                   SYNTAX IpAddress
                   ACCESS read-only
                   STATUS mandatory
                   DESCRIPTION "IP-address"
                   ::= {  staDhcpcTabledoCols 1 }

staDhcpcTablelo OBJECT-TYPE
                SYNTAX SEQUENCE OF StaDhcpcTableloRows
                ACCESS not-accessible
                STATUS mandatory
                DESCRIPTION "Table-log-server"
                ::= {  staDhcpc 14 }

staDhcpcTableloCols OBJECT-TYPE
                SYNTAX StaDhcpcTableloRows
                ACCESS not-accessible
                STATUS mandatory
                DESCRIPTION "entry in table"
                INDEX { staDhcpcTableloIpa }
                ::= {  staDhcpcTablelo 1 }

StaDhcpcTableloRows ::= SEQUENCE {
                staDhcpcTableloIpa IpAddress
               }

staDhcpcTableloIpa OBJECT-TYPE
                   SYNTAX IpAddress
                   ACCESS read-only
                   STATUS mandatory
                   DESCRIPTION "IP-address"
                   ::= {  staDhcpcTableloCols 1 }

staDhcpcConfigu OBJECT-TYPE
                SYNTAX DisplayString
                ACCESS read-only
                STATUS mandatory
                DESCRIPTION "Configuration-file"
                ::= {  staDhcpc 15 }

setName OBJECT-TYPE
        SYNTAX DisplayString (SIZE(0..16))
        ACCESS read-write
        STATUS mandatory
        DESCRIPTION "Name"
        ::= {  set 1 }

setWanm OBJECT IDENTIFIER ::= { set 2}
setWanmInte OBJECT-TYPE
            SYNTAX SEQUENCE OF SetWanmInteRows
            ACCESS not-accessible
            STATUS mandatory
            DESCRIPTION "Interface-list"
            ::= {  setWanm 14 }

setWanmInteCols OBJECT-TYPE
            SYNTAX SetWanmInteRows
            ACCESS not-accessible
            STATUS mandatory
            DESCRIPTION "entry in table"
            INDEX { setWanmInteIfc }
            ::= {  setWanmInte 1 }

SetWanmInteRows ::= SEQUENCE {
            setWanmInteIfc INTEGER,
            setWanmInteProt INTEGER,
            setWanmInteLlmo INTEGER,
            setWanmInteLlbc INTEGER,
            setWanmInteDial DisplayString,
            setWanmInteMaxi INTEGER,
            setWanmInteMaxo INTEGER
           }

setWanmInteIfc OBJECT-TYPE
                SYNTAX INTEGER {
                  s0-1(1),
                  s0-2(2),
                  s0-3(3),
                  s0-4(4)
                }
                ACCESS read-only
                STATUS mandatory
                DESCRIPTION "Ifc"
                ::= {  setWanmInteCols 1 }

setWanmInteProt OBJECT-TYPE
                SYNTAX INTEGER {
                  dss1(1),
                  ltr6(2),
                  p2p-dss1(4),
                  auto(255)
                }
                ACCESS read-write
                STATUS mandatory
                DESCRIPTION "Protocol"
                ::= {  setWanmInteCols 2 }

setWanmInteLlmo OBJECT-TYPE
                SYNTAX INTEGER {
                  master(0),
                  slave(1)
                }
                ACCESS read-write
                STATUS mandatory
                DESCRIPTION "LL-mode"
                ::= {  setWanmInteCols 6 }

setWanmInteLlbc OBJECT-TYPE
                SYNTAX INTEGER {
                  none(0),
                  b1(1),
                  b2(2)
                }
                ACCESS read-write
                STATUS mandatory
                DESCRIPTION "LL-B-chan."
                ::= {  setWanmInteCols 7 }

setWanmInteDial OBJECT-TYPE
                SYNTAX DisplayString
                ACCESS read-write
                STATUS mandatory
                DESCRIPTION "Dial-prefix"
                ::= {  setWanmInteCols 9 }

setWanmInteMaxi OBJECT-TYPE
                SYNTAX INTEGER {
                  zero(2),
                  one(1),
                  two(0)
                }
                ACCESS read-write
                STATUS mandatory
                DESCRIPTION "Max-in-calls"
                ::= {  setWanmInteCols 13 }

setWanmInteMaxo OBJECT-TYPE
                SYNTAX INTEGER {
                  zero(2),
                  one(1),
                  two(0)
                }
                ACCESS read-write
                STATUS mandatory
                DESCRIPTION "Max-out-calls"
                ::= {  setWanmInteCols 14 }

setWanmRout OBJECT-TYPE
            SYNTAX SEQUENCE OF SetWanmRoutRows
            ACCESS not-accessible
            STATUS mandatory
            DESCRIPTION "Router-interface-list"
            ::= {  setWanm 11 }

setWanmRoutCols OBJECT-TYPE
            SYNTAX SetWanmRoutRows
            ACCESS not-accessible
            STATUS mandatory
            DESCRIPTION "entry in table"
            INDEX { setWanmRoutIfc }
            ::= {  setWanmRout 1 }

SetWanmRoutRows ::= SEQUENCE {
            setWanmRoutIfc INTEGER,
            setWanmRoutMsn DisplayString,
            setWanmRoutYc INTEGER,
            setWanmRoutCli INTEGER
           }

setWanmRoutIfc OBJECT-TYPE
               SYNTAX INTEGER {
                 s0-1(1),
                 s0-2(2),
                 s0-3(3),
                 s0-4(4)
               }
               ACCESS read-only
               STATUS mandatory
               DESCRIPTION "Ifc"
               ::= {  setWanmRoutCols 1 }

setWanmRoutMsn OBJECT-TYPE
               SYNTAX DisplayString
               ACCESS read-write
               STATUS mandatory
               DESCRIPTION "MSN/EAZ"
               ::= {  setWanmRoutCols 2 }

setWanmRoutYc OBJECT-TYPE
               SYNTAX INTEGER {
                 on(0),
                 off(1)
               }
               ACCESS read-write
               STATUS mandatory
               DESCRIPTION "YC."
               ::= {  setWanmRoutCols 8 }

setWanmRoutCli OBJECT-TYPE
               SYNTAX INTEGER {
                 yes(0),
                 no(1)
               }
               ACCESS read-write
               STATUS mandatory
               DESCRIPTION "CLIP"
               ::= {  setWanmRoutCols 3 }

setWanmName OBJECT-TYPE
            SYNTAX SEQUENCE OF SetWanmNameRows
            ACCESS not-accessible
            STATUS mandatory
            DESCRIPTION "Name-list"
            ::= {  setWanm 2 }

setWanmNameCols OBJECT-TYPE
            SYNTAX SetWanmNameRows
            ACCESS not-accessible
            STATUS mandatory
            DESCRIPTION "entry in table"
            INDEX { setWanmNameDev }
            ::= {  setWanmName 1 }

SetWanmNameRows ::= SEQUENCE {
            setWanmNameDev DisplayString,
            setWanmNameDia DisplayString,
            setWanmNameB1d INTEGER,
            setWanmNameB2d INTEGER,
            setWanmNameWan DisplayString,
            setWanmNameCal INTEGER
           }

setWanmNameDev OBJECT-TYPE
               SYNTAX DisplayString
               ACCESS read-write
               STATUS mandatory
               DESCRIPTION "Device-name"
               ::= {  setWanmNameCols 1 }

setWanmNameDia OBJECT-TYPE
               SYNTAX DisplayString
               ACCESS read-write
               STATUS mandatory
               DESCRIPTION "Dialup-remote"
               ::= {  setWanmNameCols 2 }

setWanmNameB1d OBJECT-TYPE
               SYNTAX INTEGER
               ACCESS read-write
               STATUS mandatory
               DESCRIPTION "B1-DT"
               ::= {  setWanmNameCols 3 }

setWanmNameB2d OBJECT-TYPE
               SYNTAX INTEGER
               ACCESS read-write
               STATUS mandatory
               DESCRIPTION "B2-DT"
               ::= {  setWanmNameCols 4 }

setWanmNameWan OBJECT-TYPE
               SYNTAX DisplayString
               ACCESS read-write
               STATUS mandatory
               DESCRIPTION "WAN-layer"
               ::= {  setWanmNameCols 5 }

setWanmNameCal OBJECT-TYPE
               SYNTAX INTEGER {
                 off(0),
                 auto(1),
                 name(5),
                 elsa(9),
                 looser(2)
               }
               ACCESS read-write
               STATUS mandatory
               DESCRIPTION "Callback"
               ::= {  setWanmNameCols 6 }

setWanmRoun OBJECT-TYPE
            SYNTAX SEQUENCE OF SetWanmRounRows
            ACCESS not-accessible
            STATUS mandatory
            DESCRIPTION "RoundRobin-list"
            ::= {  setWanm 3 }

setWanmRounCols OBJECT-TYPE
            SYNTAX SetWanmRounRows
            ACCESS not-accessible
            STATUS mandatory
            DESCRIPTION "entry in table"
            INDEX { setWanmRounDev }
            ::= {  setWanmRoun 1 }

SetWanmRounRows ::= SEQUENCE {
            setWanmRounDev DisplayString,
            setWanmRounRou DisplayString,
            setWanmRounHea INTEGER
           }

setWanmRounDev OBJECT-TYPE
               SYNTAX DisplayString
               ACCESS read-write
               STATUS mandatory
               DESCRIPTION "Device-name"
               ::= {  setWanmRounCols 1 }

setWanmRounRou OBJECT-TYPE
               SYNTAX DisplayString
               ACCESS read-write
               STATUS mandatory
               DESCRIPTION "Round-Robin"
               ::= {  setWanmRounCols 2 }

setWanmRounHea OBJECT-TYPE
               SYNTAX INTEGER {
                 last(0),
                 first(1)
               }
               ACCESS read-write
               STATUS mandatory
               DESCRIPTION "Head"
               ::= {  setWanmRounCols 3 }

setWanmLaye OBJECT-TYPE
            SYNTAX SEQUENCE OF SetWanmLayeRows
            ACCESS not-accessible
            STATUS mandatory
            DESCRIPTION "Layer-list"
            ::= {  setWanm 4 }

setWanmLayeCols OBJECT-TYPE
            SYNTAX SetWanmLayeRows
            ACCESS not-accessible
            STATUS mandatory
            DESCRIPTION "entry in table"
            INDEX { setWanmLayeWanl }
            ::= {  setWanmLaye 1 }

SetWanmLayeRows ::= SEQUENCE {
            setWanmLayeWanl DisplayString,
            setWanmLayeEnca INTEGER,
            setWanmLayeLay3 INTEGER,
            setWanmLayeLay2 INTEGER,
            setWanmLayeL2op INTEGER,
            setWanmLayeLay1 INTEGER
           }

setWanmLayeWanl OBJECT-TYPE
                SYNTAX DisplayString
                ACCESS read-write
                STATUS mandatory
                DESCRIPTION "WAN-layer"
                ::= {  setWanmLayeCols 1 }

setWanmLayeEnca OBJECT-TYPE
                SYNTAX INTEGER {
                  ether(0),
                  trans(255)
                }
                ACCESS read-write
                STATUS mandatory
                DESCRIPTION "Encaps."
                ::= {  setWanmLayeCols 2 }

setWanmLayeLay3 OBJECT-TYPE
                SYNTAX INTEGER {
                  ppp(4),
                  appp(5),
                  scppp(6),
                  scappp(7),
                  sctrans(8),
                  elsa(0),
                  trans(255)
                }
                ACCESS read-write
                STATUS mandatory
                DESCRIPTION "Lay-3"
                ::= {  setWanmLayeCols 3 }

setWanmLayeLay2 OBJECT-TYPE
                SYNTAX INTEGER {
                  x75lapb(0),
                  trans(1)
                }
                ACCESS read-write
                STATUS mandatory
                DESCRIPTION "Lay-2"
                ::= {  setWanmLayeCols 4 }

setWanmLayeL2op OBJECT-TYPE
                SYNTAX INTEGER {
                  none(255),
                  compr(0),
                  bundle(1),
                  bnd-and-cmpr(2)
                }
                ACCESS read-write
                STATUS mandatory
                DESCRIPTION "L2-Opt."
                ::= {  setWanmLayeCols 5 }

setWanmLayeLay1 OBJECT-TYPE
                SYNTAX INTEGER {
                  hdlc64k(0),
                  hdlc56k(1),
                  v110-9k6(3),
                  v110-19k2(67),
                  v110-38k4(131)
                }
                ACCESS read-write
                STATUS mandatory
                DESCRIPTION "Lay-1"
                ::= {  setWanmLayeCols 6 }

setWanmPppl OBJECT-TYPE
            SYNTAX SEQUENCE OF SetWanmPpplRows
            ACCESS not-accessible
            STATUS mandatory
            DESCRIPTION "PPP-list"
            ::= {  setWanm 5 }

setWanmPpplCols OBJECT-TYPE
            SYNTAX SetWanmPpplRows
            ACCESS not-accessible
            STATUS mandatory
            DESCRIPTION "entry in table"
            INDEX { setWanmPpplDev }
            ::= {  setWanmPppl 1 }

SetWanmPpplRows ::= SEQUENCE {
            setWanmPpplDev DisplayString,
            setWanmPpplAut INTEGER,
            setWanmPpplKey DisplayString,
            setWanmPpplTim INTEGER,
            setWanmPpplTry INTEGER,
            setWanmPpplCon INTEGER,
            setWanmPpplFai INTEGER,
            setWanmPpplTer INTEGER,
            setWanmPpplUse DisplayString
           }

setWanmPpplDev OBJECT-TYPE
               SYNTAX DisplayString
               ACCESS read-write
               STATUS mandatory
               DESCRIPTION "Device-name"
               ::= {  setWanmPpplCols 1 }

setWanmPpplAut OBJECT-TYPE
               SYNTAX INTEGER {
                 none(0),
                 chap(8),
                 pap(4)
               }
               ACCESS read-write
               STATUS mandatory
               DESCRIPTION "Authent."
               ::= {  setWanmPpplCols 2 }

setWanmPpplKey OBJECT-TYPE
               SYNTAX DisplayString
               ACCESS read-write
               STATUS mandatory
               DESCRIPTION "Key"
               ::= {  setWanmPpplCols 3 }

setWanmPpplTim OBJECT-TYPE
               SYNTAX INTEGER
               ACCESS read-write
               STATUS mandatory
               DESCRIPTION "Time"
               ::= {  setWanmPpplCols 4 }

setWanmPpplTry OBJECT-TYPE
               SYNTAX INTEGER
               ACCESS read-write
               STATUS mandatory
               DESCRIPTION "Try"
               ::= {  setWanmPpplCols 5 }

setWanmPpplCon OBJECT-TYPE
               SYNTAX INTEGER
               ACCESS read-write
               STATUS mandatory
               DESCRIPTION "Conf"
               ::= {  setWanmPpplCols 7 }

setWanmPpplFai OBJECT-TYPE
               SYNTAX INTEGER
               ACCESS read-write
               STATUS mandatory
               DESCRIPTION "Fail"
               ::= {  setWanmPpplCols 8 }

setWanmPpplTer OBJECT-TYPE
               SYNTAX INTEGER
               ACCESS read-write
               STATUS mandatory
               DESCRIPTION "Term"
               ::= {  setWanmPpplCols 9 }

setWanmPpplUse OBJECT-TYPE
               SYNTAX DisplayString
               ACCESS read-write
               STATUS mandatory
               DESCRIPTION "Username"
               ::= {  setWanmPpplCols 6 }

setWanmNumb OBJECT-TYPE
            SYNTAX SEQUENCE OF SetWanmNumbRows
            ACCESS not-accessible
            STATUS mandatory
            DESCRIPTION "Number-list"
            ::= {  setWanm 6 }

setWanmNumbCols OBJECT-TYPE
            SYNTAX SetWanmNumbRows
            ACCESS not-accessible
            STATUS mandatory
            DESCRIPTION "entry in table"
            INDEX { setWanmNumbDia }
            ::= {  setWanmNumb 1 }

SetWanmNumbRows ::= SEQUENCE {
            setWanmNumbDia DisplayString,
            setWanmNumbDev DisplayString
           }

setWanmNumbDia OBJECT-TYPE
               SYNTAX DisplayString
               ACCESS read-write
               STATUS mandatory
               DESCRIPTION "Dialup-remote"
               ::= {  setWanmNumbCols 1 }

setWanmNumbDev OBJECT-TYPE
               SYNTAX DisplayString
               ACCESS read-write
               STATUS mandatory
               DESCRIPTION "Device-name"
               ::= {  setWanmNumbCols 2 }

setWanmScri OBJECT-TYPE
            SYNTAX SEQUENCE OF SetWanmScriRows
            ACCESS not-accessible
            STATUS mandatory
            DESCRIPTION "Script-list"
            ::= {  setWanm 8 }

setWanmScriCols OBJECT-TYPE
            SYNTAX SetWanmScriRows
            ACCESS not-accessible
            STATUS mandatory
            DESCRIPTION "entry in table"
            INDEX { setWanmScriDev }
            ::= {  setWanmScri 1 }

SetWanmScriRows ::= SEQUENCE {
            setWanmScriDev DisplayString,
            setWanmScriScr DisplayString
           }

setWanmScriDev OBJECT-TYPE
               SYNTAX DisplayString
               ACCESS read-write
               STATUS mandatory
               DESCRIPTION "Device-name"
               ::= {  setWanmScriCols 1 }

setWanmScriScr OBJECT-TYPE
               SYNTAX DisplayString
               ACCESS read-write
               STATUS mandatory
               DESCRIPTION "Script"
               ::= {  setWanmScriCols 2 }

setWanmProt OBJECT-TYPE
            SYNTAX INTEGER {
              none(0),
              name(1),
              number(2),
              noname(3)
            }
            ACCESS read-write
            STATUS mandatory
            DESCRIPTION "Protect"
            ::= {  setWanm 9 }

setWanmCbat OBJECT-TYPE
            SYNTAX INTEGER
            ACCESS read-write
            STATUS mandatory
            DESCRIPTION "CB-attempts"
            ::= {  setWanm 10 }

setWanmManu OBJECT IDENTIFIER ::= { setWanm 13}
setWanmManuCon OBJECT-TYPE
               SYNTAX INTEGER
               ACCESS write-only
               STATUS mandatory
               DESCRIPTION "Connect"
               ::= {  setWanmManu 1 }

setWanmManuDis OBJECT-TYPE
               SYNTAX INTEGER
               ACCESS write-only
               STATUS mandatory
               DESCRIPTION "Disconnect"
               ::= {  setWanmManu 2 }

setWanmDial OBJECT-TYPE
            SYNTAX DisplayString (SIZE(0..8))
            ACCESS not-accessible
            STATUS mandatory
            DESCRIPTION "Dial-prefix"
            ::= {  setWanm 7 }

setAcco OBJECT IDENTIFIER ::= { set 18}
setAccoOpe OBJECT-TYPE
           SYNTAX INTEGER {
             on(1),
             off(0)
           }
           ACCESS read-write
           STATUS mandatory
           DESCRIPTION "Operating"
           ::= {  setAcco 1 }

setAccoSav OBJECT-TYPE
           SYNTAX INTEGER {
             no(0),
             yes(1)
           }
           ACCESS read-write
           STATUS mandatory
           DESCRIPTION "Save-to-flashrom"
           ::= {  setAcco 2 }

setAccoSor OBJECT-TYPE
           SYNTAX INTEGER {
             time(0),
             data(1)
           }
           ACCESS read-write
           STATUS mandatory
           DESCRIPTION "Sort-by"
           ::= {  setAcco 3 }

setAccoCur OBJECT-TYPE
           SYNTAX SEQUENCE OF SetAccoCurRows
           ACCESS not-accessible
           STATUS mandatory
           DESCRIPTION "Current-user"
           ::= {  setAcco 4 }

setAccoCurCols OBJECT-TYPE
           SYNTAX SetAccoCurRows
           ACCESS not-accessible
           STATUS mandatory
           DESCRIPTION "entry in table"
           INDEX { setAccoCurUsern }
           ::= {  setAccoCur 1 }

SetAccoCurRows ::= SEQUENCE {
           setAccoCurUsern DisplayString,
           setAccoCurMacad DisplayString,
           setAccoCurRemot DisplayString,
           setAccoCurConnt INTEGER,
           setAccoCurRxkby INTEGER,
           setAccoCurTxkby INTEGER,
           setAccoCurTotal INTEGER,
           setAccoCurConne INTEGER
          }

setAccoCurUsern OBJECT-TYPE
                SYNTAX DisplayString
                ACCESS read-only
                STATUS mandatory
                DESCRIPTION "Username"
                ::= {  setAccoCurCols 1 }

setAccoCurMacad OBJECT-TYPE
                SYNTAX DisplayString
                ACCESS read-only
                STATUS mandatory
                DESCRIPTION "MAC-Adr."
                ::= {  setAccoCurCols 2 }

setAccoCurRemot OBJECT-TYPE
                SYNTAX DisplayString
                ACCESS read-only
                STATUS mandatory
                DESCRIPTION "Remote-station"
                ::= {  setAccoCurCols 3 }

setAccoCurConnt OBJECT-TYPE
                SYNTAX INTEGER {
                  unknown(0),
                  dial-up(1),
                  leased-line(2),
                  dsl-line(4),
                  lancapi(5),
                  ab-ports(6)
                }
                ACCESS read-only
                STATUS mandatory
                DESCRIPTION "Conn.-type"
                ::= {  setAccoCurCols 4 }

setAccoCurRxkby OBJECT-TYPE
                SYNTAX INTEGER
                ACCESS read-only
                STATUS mandatory
                DESCRIPTION "Rx-KBytes"
                ::= {  setAccoCurCols 5 }

setAccoCurTxkby OBJECT-TYPE
                SYNTAX INTEGER
                ACCESS read-only
                STATUS mandatory
                DESCRIPTION "Tx-KBytes"
                ::= {  setAccoCurCols 6 }

setAccoCurTotal OBJECT-TYPE
                SYNTAX INTEGER
                ACCESS read-only
                STATUS mandatory
                DESCRIPTION "Total-time"
                ::= {  setAccoCurCols 8 }

setAccoCurConne OBJECT-TYPE
                SYNTAX INTEGER
                ACCESS read-only
                STATUS mandatory
                DESCRIPTION "Connections"
                ::= {  setAccoCurCols 9 }

setAccoAcc OBJECT-TYPE
           SYNTAX SEQUENCE OF SetAccoAccRows
           ACCESS not-accessible
           STATUS mandatory
           DESCRIPTION "Accounting-list"
           ::= {  setAcco 5 }

setAccoAccCols OBJECT-TYPE
           SYNTAX SetAccoAccRows
           ACCESS not-accessible
           STATUS mandatory
           DESCRIPTION "entry in table"
           INDEX { setAccoAccUsern }
           ::= {  setAccoAcc 1 }

SetAccoAccRows ::= SEQUENCE {
           setAccoAccUsern DisplayString,
           setAccoAccMacad DisplayString,
           setAccoAccRemot DisplayString,
           setAccoAccConnt INTEGER,
           setAccoAccRxkby INTEGER,
           setAccoAccTxkby INTEGER,
           setAccoAccTotal INTEGER,
           setAccoAccConne INTEGER
          }

setAccoAccUsern OBJECT-TYPE
                SYNTAX DisplayString
                ACCESS read-only
                STATUS mandatory
                DESCRIPTION "Username"
                ::= {  setAccoAccCols 1 }

setAccoAccMacad OBJECT-TYPE
                SYNTAX DisplayString
                ACCESS read-only
                STATUS mandatory
                DESCRIPTION "MAC-Adr."
                ::= {  setAccoAccCols 2 }

setAccoAccRemot OBJECT-TYPE
                SYNTAX DisplayString
                ACCESS read-only
                STATUS mandatory
                DESCRIPTION "Remote-station"
                ::= {  setAccoAccCols 3 }

setAccoAccConnt OBJECT-TYPE
                SYNTAX INTEGER {
                  unknown(0),
                  dial-up(1),
                  leased-line(2),
                  dsl-line(4),
                  lancapi(5),
                  ab-ports(6)
                }
                ACCESS read-only
                STATUS mandatory
                DESCRIPTION "Conn.-type"
                ::= {  setAccoAccCols 4 }

setAccoAccRxkby OBJECT-TYPE
                SYNTAX INTEGER
                ACCESS read-only
                STATUS mandatory
                DESCRIPTION "Rx-KBytes"
                ::= {  setAccoAccCols 5 }

setAccoAccTxkby OBJECT-TYPE
                SYNTAX INTEGER
                ACCESS read-only
                STATUS mandatory
                DESCRIPTION "Tx-KBytes"
                ::= {  setAccoAccCols 6 }

setAccoAccTotal OBJECT-TYPE
                SYNTAX INTEGER
                ACCESS read-only
                STATUS mandatory
                DESCRIPTION "Total-time"
                ::= {  setAccoAccCols 8 }

setAccoAccConne OBJECT-TYPE
                SYNTAX INTEGER
                ACCESS read-only
                STATUS mandatory
                DESCRIPTION "Connections"
                ::= {  setAccoAccCols 9 }

setAccoDel OBJECT-TYPE
           SYNTAX INTEGER
           ACCESS write-only
           STATUS mandatory
           DESCRIPTION "Delete-Accounting-list"
           ::= {  setAcco 6 }

setChar OBJECT IDENTIFIER ::= { set 3}
setCharDaysper OBJECT-TYPE
               SYNTAX INTEGER
               ACCESS read-write
               STATUS mandatory
               DESCRIPTION "Day(s)/period"
               ::= {  setChar 2 }

setCharBudgetu OBJECT-TYPE
               SYNTAX INTEGER
               ACCESS read-write
               STATUS mandatory
               DESCRIPTION "Budget-units"
               ::= {  setChar 1 }

setCharSpareun OBJECT-TYPE
               SYNTAX INTEGER
               ACCESS read-only
               STATUS mandatory
               DESCRIPTION "Spare-units"
               ::= {  setChar 3 }

setCharRouteru OBJECT-TYPE
               SYNTAX INTEGER
               ACCESS read-only
               STATUS mandatory
               DESCRIPTION "Router-units"
               ::= {  setChar 4 }

setCharTotalun OBJECT-TYPE
               SYNTAX INTEGER
               ACCESS read-only
               STATUS mandatory
               DESCRIPTION "Total-units"
               ::= {  setChar 6 }

setCharTablebu OBJECT-TYPE
               SYNTAX SEQUENCE OF SetCharTablebuRows
               ACCESS not-accessible
               STATUS mandatory
               DESCRIPTION "Table-budget"
               ::= {  setChar 5 }

setCharTablebuCols OBJECT-TYPE
               SYNTAX SetCharTablebuRows
               ACCESS not-accessible
               STATUS mandatory
               DESCRIPTION "entry in table"
               INDEX { setCharTablebuIfc }
               ::= {  setCharTablebu 1 }

SetCharTablebuRows ::= SEQUENCE {
               setCharTablebuIfc INTEGER,
               setCharTablebuBud INTEGER,
               setCharTablebuSpa INTEGER,
               setCharTablebuTot INTEGER
              }

setCharTablebuIfc OBJECT-TYPE
                  SYNTAX INTEGER {
                    router(1),
                    lancapi(2),
                    ab-1(3),
                    ab-2(4),
                    ab-3(5),
                    ab-4(6),
                    time-Modul(255)
                  }
                  ACCESS read-only
                  STATUS mandatory
                  DESCRIPTION "Ifc"
                  ::= {  setCharTablebuCols 1 }

setCharTablebuBud OBJECT-TYPE
                  SYNTAX INTEGER
                  ACCESS read-only
                  STATUS mandatory
                  DESCRIPTION "Budget-units"
                  ::= {  setCharTablebuCols 2 }

setCharTablebuSpa OBJECT-TYPE
                  SYNTAX INTEGER
                  ACCESS read-only
                  STATUS mandatory
                  DESCRIPTION "Spare-Budget"
                  ::= {  setCharTablebuCols 3 }

setCharTablebuTot OBJECT-TYPE
                  SYNTAX INTEGER
                  ACCESS read-only
                  STATUS mandatory
                  DESCRIPTION "Total-units"
                  ::= {  setCharTablebuCols 4 }

setCharTimetab OBJECT-TYPE
               SYNTAX SEQUENCE OF SetCharTimetabRows
               ACCESS not-accessible
               STATUS mandatory
               DESCRIPTION "Time-table"
               ::= {  setChar 7 }

setCharTimetabCols OBJECT-TYPE
               SYNTAX SetCharTimetabRows
               ACCESS not-accessible
               STATUS mandatory
               DESCRIPTION "entry in table"
               INDEX { setCharTimetabIfc }
               ::= {  setCharTimetab 1 }

SetCharTimetabRows ::= SEQUENCE {
               setCharTimetabIfc INTEGER,
               setCharTimetabBudgetmi INTEGER,
               setCharTimetabSparemin INTEGER,
               setCharTimetabMinutesa INTEGER,
               setCharTimetabMinutesp INTEGER
              }

setCharTimetabIfc OBJECT-TYPE
                       SYNTAX INTEGER {
                         router(1),
                         lancapi(2),
                         ab-1(3),
                         ab-2(4),
                         ab-3(5),
                         ab-4(6),
                         time-Modul(255)
                       }
                       ACCESS read-only
                       STATUS mandatory
                       DESCRIPTION "Ifc"
                       ::= {  setCharTimetabCols 1 }

setCharTimetabBudgetmi OBJECT-TYPE
                       SYNTAX INTEGER
                       ACCESS read-only
                       STATUS mandatory
                       DESCRIPTION "Budget-minutes"
                       ::= {  setCharTimetabCols 2 }

setCharTimetabSparemin OBJECT-TYPE
                       SYNTAX INTEGER
                       ACCESS read-only
                       STATUS mandatory
                       DESCRIPTION "Spare-minutes"
                       ::= {  setCharTimetabCols 3 }

setCharTimetabMinutesa OBJECT-TYPE
                       SYNTAX INTEGER
                       ACCESS read-only
                       STATUS mandatory
                       DESCRIPTION "Minutes-active"
                       ::= {  setCharTimetabCols 4 }

setCharTimetabMinutesp OBJECT-TYPE
                       SYNTAX INTEGER
                       ACCESS read-only
                       STATUS mandatory
                       DESCRIPTION "Minutes-passive"
                       ::= {  setCharTimetabCols 5 }

setCharMinutes OBJECT-TYPE
               SYNTAX INTEGER
               ACCESS read-write
               STATUS mandatory
               DESCRIPTION "Minutes-budget"
               ::= {  setChar 8 }

setCharSparemi OBJECT-TYPE
               SYNTAX INTEGER
               ACCESS read-only
               STATUS mandatory
               DESCRIPTION "Spare-minutes"
               ::= {  setChar 9 }

setCharRouterm OBJECT-TYPE
               SYNTAX INTEGER
               ACCESS read-only
               STATUS mandatory
               DESCRIPTION "Router-minutes-active"
               ::= {  setChar 10 }

setLanm OBJECT IDENTIFIER ::= { set 4}
setLanmCon OBJECT-TYPE
           SYNTAX INTEGER {
             ten-bt(32),
             ten-b2(33),
             auto(35)
           }
           ACCESS read-write
           STATUS mandatory
           DESCRIPTION "Connector"
           ::= {  setLanm 1 }

setLanmNod OBJECT-TYPE
           SYNTAX DisplayString (SIZE(0..16))
           ACCESS read-only
           STATUS mandatory
           DESCRIPTION "Node-ID"
           ::= {  setLanm 2 }

setLanmSpa OBJECT-TYPE
           SYNTAX INTEGER
           ACCESS read-write
           STATUS mandatory
           DESCRIPTION "Spare-heap"
           ::= {  setLanm 3 }

setBrid OBJECT IDENTIFIER ::= { set 5}
setBridOpe OBJECT-TYPE
           SYNTAX INTEGER {
             on(1),
             off(0)
           }
           ACCESS read-write
           STATUS mandatory
           DESCRIPTION "Operating"
           ::= {  setBrid 1 }

setBridRem OBJECT-TYPE
           SYNTAX DisplayString (SIZE(0..16))
           ACCESS read-write
           STATUS mandatory
           DESCRIPTION "Remote-ID"
           ::= {  setBrid 2 }

setBridTab OBJECT-TYPE
           SYNTAX SEQUENCE OF SetBridTabRows
           ACCESS not-accessible
           STATUS mandatory
           DESCRIPTION "Table-bridge"
           ::= {  setBrid 3 }

setBridTabCols OBJECT-TYPE
           SYNTAX SetBridTabRows
           ACCESS not-accessible
           STATUS mandatory
           DESCRIPTION "entry in table"
           INDEX { setBridTabNod }
           ::= {  setBridTab 1 }

SetBridTabRows ::= SEQUENCE {
           setBridTabNod DisplayString,
           setBridTabLas INTEGER,
           setBridTabFor DisplayString
          }

setBridTabNod OBJECT-TYPE
              SYNTAX DisplayString
              ACCESS read-only
              STATUS mandatory
              DESCRIPTION "Node-ID"
              ::= {  setBridTabCols 1 }

setBridTabLas OBJECT-TYPE
              SYNTAX INTEGER
              ACCESS read-only
              STATUS mandatory
              DESCRIPTION "Last-access"
              ::= {  setBridTabCols 2 }

setBridTabFor OBJECT-TYPE
              SYNTAX DisplayString
              ACCESS read-only
              STATUS mandatory
              DESCRIPTION "Forward-Flag"
              ::= {  setBridTabCols 3 }

setBridAgi OBJECT-TYPE
           SYNTAX INTEGER
           ACCESS read-write
           STATUS mandatory
           DESCRIPTION "Aging-minute(s)"
           ::= {  setBrid 4 }

setBridLan OBJECT IDENTIFIER ::= { setBrid 5}
setBridLanBro OBJECT-TYPE
              SYNTAX INTEGER {
                semi(2),
                positive(1),
                negative(0)
              }
              ACCESS read-write
              STATUS mandatory
              DESCRIPTION "Broadcast"
              ::= {  setBridLan 1 }

setBridLanMul OBJECT-TYPE
              SYNTAX INTEGER {
                semi(2),
                positive(1),
                negative(0)
              }
              ACCESS read-write
              STATUS mandatory
              DESCRIPTION "Multicast"
              ::= {  setBridLan 2 }

setBridLanDes OBJECT IDENTIFIER ::= { setBridLan 3}
setBridLanDesFilterty OBJECT-TYPE
                      SYNTAX INTEGER {
                        positive(4),
                        negative(0)
                      }
                      ACCESS read-write
                      STATUS mandatory
                      DESCRIPTION "Filter-type"
                      ::= {  setBridLanDes 1 }

setBridLanDesFilterta OBJECT-TYPE
                      SYNTAX SEQUENCE OF SetBridLanDesFiltertaRows
                      ACCESS not-accessible
                      STATUS mandatory
                      DESCRIPTION "Filter-table"
                      ::= {  setBridLanDes 2 }

setBridLanDesFiltertaCols OBJECT-TYPE
                      SYNTAX SetBridLanDesFiltertaRows
                      ACCESS not-accessible
                      STATUS mandatory
                      DESCRIPTION "entry in table"
                      INDEX { setBridLanDesFiltertaDes }
                      ::= {  setBridLanDesFilterta 1 }

SetBridLanDesFiltertaRows ::= SEQUENCE {
                      setBridLanDesFiltertaDes DisplayString
                     }

setBridLanDesFiltertaDes OBJECT-TYPE
                         SYNTAX DisplayString
                         ACCESS read-write
                         STATUS mandatory
                         DESCRIPTION "Dest.-address"
                         ::= {  setBridLanDesFiltertaCols 1 }

setBridLanSrc OBJECT IDENTIFIER ::= { setBridLan 4}
setBridLanSrcFilterty OBJECT-TYPE
                      SYNTAX INTEGER {
                        positive(8),
                        negative(0)
                      }
                      ACCESS read-write
                      STATUS mandatory
                      DESCRIPTION "Filter-type"
                      ::= {  setBridLanSrc 1 }

setBridLanSrcFilterta OBJECT-TYPE
                      SYNTAX SEQUENCE OF SetBridLanSrcFiltertaRows
                      ACCESS not-accessible
                      STATUS mandatory
                      DESCRIPTION "Filter-table"
                      ::= {  setBridLanSrc 2 }

setBridLanSrcFiltertaCols OBJECT-TYPE
                      SYNTAX SetBridLanSrcFiltertaRows
                      ACCESS not-accessible
                      STATUS mandatory
                      DESCRIPTION "entry in table"
                      INDEX { setBridLanSrcFiltertaSrc }
                      ::= {  setBridLanSrcFilterta 1 }

SetBridLanSrcFiltertaRows ::= SEQUENCE {
                      setBridLanSrcFiltertaSrc DisplayString
                     }

setBridLanSrcFiltertaSrc OBJECT-TYPE
                         SYNTAX DisplayString
                         ACCESS read-write
                         STATUS mandatory
                         DESCRIPTION "Src.-address"
                         ::= {  setBridLanSrcFiltertaCols 1 }

setBridWan OBJECT IDENTIFIER ::= { setBrid 6}
setBridWanBro OBJECT-TYPE
              SYNTAX INTEGER {
                semi(2),
                positive(1),
                negative(0)
              }
              ACCESS read-write
              STATUS mandatory
              DESCRIPTION "Broadcast"
              ::= {  setBridWan 1 }

setBridWanMul OBJECT-TYPE
              SYNTAX INTEGER {
                semi(2),
                positive(1),
                negative(0)
              }
              ACCESS read-write
              STATUS mandatory
              DESCRIPTION "Multicast"
              ::= {  setBridWan 2 }

setBridWanDes OBJECT IDENTIFIER ::= { setBridWan 3}
setBridWanDesFilterty OBJECT-TYPE
                      SYNTAX INTEGER {
                        positive(1),
                        negative(0)
                      }
                      ACCESS read-write
                      STATUS mandatory
                      DESCRIPTION "Filter-type"
                      ::= {  setBridWanDes 1 }

setBridWanDesFilterta OBJECT-TYPE
                      SYNTAX SEQUENCE OF SetBridWanDesFiltertaRows
                      ACCESS not-accessible
                      STATUS mandatory
                      DESCRIPTION "Filter-table"
                      ::= {  setBridWanDes 2 }

setBridWanDesFiltertaCols OBJECT-TYPE
                      SYNTAX SetBridWanDesFiltertaRows
                      ACCESS not-accessible
                      STATUS mandatory
                      DESCRIPTION "entry in table"
                      INDEX { setBridWanDesFiltertaDes }
                      ::= {  setBridWanDesFilterta 1 }

SetBridWanDesFiltertaRows ::= SEQUENCE {
                      setBridWanDesFiltertaDes DisplayString
                     }

setBridWanDesFiltertaDes OBJECT-TYPE
                         SYNTAX DisplayString
                         ACCESS read-write
                         STATUS mandatory
                         DESCRIPTION "Dest.-address"
                         ::= {  setBridWanDesFiltertaCols 1 }

setBridWanSrc OBJECT IDENTIFIER ::= { setBridWan 4}
setBridWanSrcFilterty OBJECT-TYPE
                      SYNTAX INTEGER {
                        positive(2),
                        negative(0)
                      }
                      ACCESS read-write
                      STATUS mandatory
                      DESCRIPTION "Filter-type"
                      ::= {  setBridWanSrc 1 }

setBridWanSrcFilterta OBJECT-TYPE
                      SYNTAX SEQUENCE OF SetBridWanSrcFiltertaRows
                      ACCESS not-accessible
                      STATUS mandatory
                      DESCRIPTION "Filter-table"
                      ::= {  setBridWanSrc 2 }

setBridWanSrcFiltertaCols OBJECT-TYPE
                      SYNTAX SetBridWanSrcFiltertaRows
                      ACCESS not-accessible
                      STATUS mandatory
                      DESCRIPTION "entry in table"
                      INDEX { setBridWanSrcFiltertaDes }
                      ::= {  setBridWanSrcFilterta 1 }

SetBridWanSrcFiltertaRows ::= SEQUENCE {
                      setBridWanSrcFiltertaDes DisplayString
                     }

setBridWanSrcFiltertaDes OBJECT-TYPE
                         SYNTAX DisplayString
                         ACCESS read-write
                         STATUS mandatory
                         DESCRIPTION "Dest.-address"
                         ::= {  setBridWanSrcFiltertaCols 1 }

setIpxm OBJECT IDENTIFIER ::= { set 6}
setIpxmOpe OBJECT-TYPE
           SYNTAX INTEGER {
             on(1),
             off(0)
           }
           ACCESS read-write
           STATUS mandatory
           DESCRIPTION "Operating"
           ::= {  setIpxm 1 }

setIpxmIpx OBJECT-TYPE
           SYNTAX INTEGER {
             on(1),
             off(0)
           }
           ACCESS read-write
           STATUS mandatory
           DESCRIPTION "IPX-router"
           ::= {  setIpxm 2 }

setIpxmLan OBJECT IDENTIFIER ::= { setIpxm 3}
setIpxmLanNetw OBJECT-TYPE
               SYNTAX DisplayString (SIZE(0..8))
               ACCESS read-write
               STATUS mandatory
               DESCRIPTION "Network"
               ::= {  setIpxmLan 1 }

setIpxmLanBind OBJECT-TYPE
               SYNTAX INTEGER {
                 auto(0),
                 ii(1),
                 dot802-3(2),
                 dot802-2(4),
                 snap(8)
               }
               ACCESS read-write
               STATUS mandatory
               DESCRIPTION "Binding"
               ::= {  setIpxmLan 2 }

setIpxmLanSpxw OBJECT-TYPE
               SYNTAX INTEGER {
                 filter(3),
                 spoof(0),
                 route(1)
               }
               ACCESS read-write
               STATUS mandatory
               DESCRIPTION "SPX-watch"
               ::= {  setIpxmLan 3 }

setIpxmLanIpxw OBJECT-TYPE
               SYNTAX INTEGER {
                 spoof(0),
                 route(1)
               }
               ACCESS read-write
               STATUS mandatory
               DESCRIPTION "IPX-watch"
               ::= {  setIpxmLan 4 }

setIpxmLanNetb OBJECT-TYPE
               SYNTAX INTEGER {
                 spoof(0),
                 route(3),
                 filter(1)
               }
               ACCESS read-write
               STATUS mandatory
               DESCRIPTION "NetBIOS-watch"
               ::= {  setIpxmLan 5 }

setIpxmLanSock OBJECT-TYPE
               SYNTAX SEQUENCE OF SetIpxmLanSockRows
               ACCESS not-accessible
               STATUS mandatory
               DESCRIPTION "Socket-filter"
               ::= {  setIpxmLan 6 }

setIpxmLanSockCols OBJECT-TYPE
               SYNTAX SetIpxmLanSockRows
               ACCESS not-accessible
               STATUS mandatory
               DESCRIPTION "entry in table"
               INDEX { setIpxmLanSockSta }
               ::= {  setIpxmLanSock 1 }

SetIpxmLanSockRows ::= SEQUENCE {
               setIpxmLanSockSta DisplayString,
               setIpxmLanSockEnd DisplayString
              }

setIpxmLanSockSta OBJECT-TYPE
                  SYNTAX DisplayString
                  ACCESS read-write
                  STATUS mandatory
                  DESCRIPTION "Start-socket"
                  ::= {  setIpxmLanSockCols 1 }

setIpxmLanSockEnd OBJECT-TYPE
                  SYNTAX DisplayString
                  ACCESS read-write
                  STATUS mandatory
                  DESCRIPTION "End-socket"
                  ::= {  setIpxmLanSockCols 2 }

setIpxmLanLocr OBJECT-TYPE
               SYNTAX INTEGER {
                 on(1),
                 off(0)
               }
               ACCESS read-write
               STATUS mandatory
               DESCRIPTION "Loc.-routing"
               ::= {  setIpxmLan 7 }

setIpxmLanRips OBJECT-TYPE
               SYNTAX INTEGER {
                 on(1),
                 off(0)
               }
               ACCESS read-write
               STATUS mandatory
               DESCRIPTION "RIP-SAP-scal."
               ::= {  setIpxmLan 8 }

setIpxmLanLoop OBJECT-TYPE
               SYNTAX INTEGER {
                 on(1),
                 off(0)
               }
               ACCESS read-write
               STATUS mandatory
               DESCRIPTION "LOOP-prop."
               ::= {  setIpxmLan 9 }

setIpxmWan OBJECT IDENTIFIER ::= { setIpxm 4}
setIpxmWanRou OBJECT-TYPE
              SYNTAX SEQUENCE OF SetIpxmWanRouRows
              ACCESS not-accessible
              STATUS mandatory
              DESCRIPTION "Routing-table"
              ::= {  setIpxmWan 1 }

setIpxmWanRouCols OBJECT-TYPE
              SYNTAX SetIpxmWanRouRows
              ACCESS not-accessible
              STATUS mandatory
              DESCRIPTION "entry in table"
              INDEX { setIpxmWanRouRem }
              ::= {  setIpxmWanRou 1 }

SetIpxmWanRouRows ::= SEQUENCE {
              setIpxmWanRouRem DisplayString,
              setIpxmWanRouNet DisplayString,
              setIpxmWanRouBin INTEGER,
              setIpxmWanRouPro INTEGER,
              setIpxmWanRouBac INTEGER
             }

setIpxmWanRouRem OBJECT-TYPE
                 SYNTAX DisplayString
                 ACCESS read-write
                 STATUS mandatory
                 DESCRIPTION "Remote-ID"
                 ::= {  setIpxmWanRouCols 1 }

setIpxmWanRouNet OBJECT-TYPE
                 SYNTAX DisplayString
                 ACCESS read-write
                 STATUS mandatory
                 DESCRIPTION "Network"
                 ::= {  setIpxmWanRouCols 2 }

setIpxmWanRouBin OBJECT-TYPE
                 SYNTAX INTEGER {
                   ii(1),
                   dot802-3(2),
                   dot802-2(4),
                   snap(8)
                 }
                 ACCESS read-write
                 STATUS mandatory
                 DESCRIPTION "Binding"
                 ::= {  setIpxmWanRouCols 3 }

setIpxmWanRouPro OBJECT-TYPE
                 SYNTAX INTEGER {
                   filter(0),
                   route(3)
                 }
                 ACCESS read-write
                 STATUS mandatory
                 DESCRIPTION "Propagate"
                 ::= {  setIpxmWanRouCols 4 }

setIpxmWanRouBac OBJECT-TYPE
                 SYNTAX INTEGER {
                   on(1),
                   off(0)
                 }
                 ACCESS read-write
                 STATUS mandatory
                 DESCRIPTION "Backoff"
                 ::= {  setIpxmWanRouCols 5 }

setIpxmWanSoc OBJECT-TYPE
              SYNTAX SEQUENCE OF SetIpxmWanSocRows
              ACCESS not-accessible
              STATUS mandatory
              DESCRIPTION "Socket-filter"
              ::= {  setIpxmWan 2 }

setIpxmWanSocCols OBJECT-TYPE
              SYNTAX SetIpxmWanSocRows
              ACCESS not-accessible
              STATUS mandatory
              DESCRIPTION "entry in table"
              INDEX { setIpxmWanSocSta }
              ::= {  setIpxmWanSoc 1 }

SetIpxmWanSocRows ::= SEQUENCE {
              setIpxmWanSocSta DisplayString,
              setIpxmWanSocEnd DisplayString
             }

setIpxmWanSocSta OBJECT-TYPE
                 SYNTAX DisplayString
                 ACCESS read-write
                 STATUS mandatory
                 DESCRIPTION "Start-socket"
                 ::= {  setIpxmWanSocCols 1 }

setIpxmWanSocEnd OBJECT-TYPE
                 SYNTAX DisplayString
                 ACCESS read-write
                 STATUS mandatory
                 DESCRIPTION "End-socket"
                 ::= {  setIpxmWanSocCols 2 }

setIpxmRip OBJECT IDENTIFIER ::= { setIpxm 5}
setIpxmRipTabl OBJECT-TYPE
               SYNTAX SEQUENCE OF SetIpxmRipTablRows
               ACCESS not-accessible
               STATUS mandatory
               DESCRIPTION "Table-RIP"
               ::= {  setIpxmRip 1 }

setIpxmRipTablCols OBJECT-TYPE
               SYNTAX SetIpxmRipTablRows
               ACCESS not-accessible
               STATUS mandatory
               DESCRIPTION "entry in table"
               INDEX { setIpxmRipTablNet }
               ::= {  setIpxmRipTabl 1 }

SetIpxmRipTablRows ::= SEQUENCE {
               setIpxmRipTablNet DisplayString,
               setIpxmRipTablHop INTEGER,
               setIpxmRipTablTic INTEGER,
               setIpxmRipTablNod DisplayString,
               setIpxmRipTablTim INTEGER,
               setIpxmRipTablFla INTEGER
              }

setIpxmRipTablNet OBJECT-TYPE
                  SYNTAX DisplayString
                  ACCESS read-only
                  STATUS mandatory
                  DESCRIPTION "Network"
                  ::= {  setIpxmRipTablCols 1 }

setIpxmRipTablHop OBJECT-TYPE
                  SYNTAX INTEGER
                  ACCESS read-only
                  STATUS mandatory
                  DESCRIPTION "Hops"
                  ::= {  setIpxmRipTablCols 2 }

setIpxmRipTablTic OBJECT-TYPE
                  SYNTAX INTEGER
                  ACCESS read-only
                  STATUS mandatory
                  DESCRIPTION "Tics"
                  ::= {  setIpxmRipTablCols 3 }

setIpxmRipTablNod OBJECT-TYPE
                  SYNTAX DisplayString
                  ACCESS read-only
                  STATUS mandatory
                  DESCRIPTION "Node-ID"
                  ::= {  setIpxmRipTablCols 4 }

setIpxmRipTablTim OBJECT-TYPE
                  SYNTAX INTEGER
                  ACCESS read-only
                  STATUS mandatory
                  DESCRIPTION "Time"
                  ::= {  setIpxmRipTablCols 5 }

setIpxmRipTablFla OBJECT-TYPE
                  SYNTAX INTEGER {
                    local(2),
                    remote(1),
                    direct(128),
                    new(64),
                    down(32),
                    loop(16),
                    spare(8)
                  }
                  ACCESS read-only
                  STATUS mandatory
                  DESCRIPTION "Flags"
                  ::= {  setIpxmRipTablCols 6 }

setIpxmRipLanf OBJECT-TYPE
               SYNTAX SEQUENCE OF SetIpxmRipLanfRows
               ACCESS not-accessible
               STATUS mandatory
               DESCRIPTION "LAN-filter-table"
               ::= {  setIpxmRip 2 }

setIpxmRipLanfCols OBJECT-TYPE
               SYNTAX SetIpxmRipLanfRows
               ACCESS not-accessible
               STATUS mandatory
               DESCRIPTION "entry in table"
               INDEX { setIpxmRipLanfSta }
               ::= {  setIpxmRipLanf 1 }

SetIpxmRipLanfRows ::= SEQUENCE {
               setIpxmRipLanfSta DisplayString,
               setIpxmRipLanfEnd DisplayString
              }

setIpxmRipLanfSta OBJECT-TYPE
                  SYNTAX DisplayString
                  ACCESS read-write
                  STATUS mandatory
                  DESCRIPTION "Start-net"
                  ::= {  setIpxmRipLanfCols 1 }

setIpxmRipLanfEnd OBJECT-TYPE
                  SYNTAX DisplayString
                  ACCESS read-write
                  STATUS mandatory
                  DESCRIPTION "End-net"
                  ::= {  setIpxmRipLanfCols 2 }

setIpxmRipWanf OBJECT-TYPE
               SYNTAX SEQUENCE OF SetIpxmRipWanfRows
               ACCESS not-accessible
               STATUS mandatory
               DESCRIPTION "WAN-filter-table"
               ::= {  setIpxmRip 3 }

setIpxmRipWanfCols OBJECT-TYPE
               SYNTAX SetIpxmRipWanfRows
               ACCESS not-accessible
               STATUS mandatory
               DESCRIPTION "entry in table"
               INDEX { setIpxmRipWanfSta }
               ::= {  setIpxmRipWanf 1 }

SetIpxmRipWanfRows ::= SEQUENCE {
               setIpxmRipWanfSta DisplayString,
               setIpxmRipWanfEnd DisplayString
              }

setIpxmRipWanfSta OBJECT-TYPE
                  SYNTAX DisplayString
                  ACCESS read-write
                  STATUS mandatory
                  DESCRIPTION "Start-net"
                  ::= {  setIpxmRipWanfCols 1 }

setIpxmRipWanfEnd OBJECT-TYPE
                  SYNTAX DisplayString
                  ACCESS read-write
                  STATUS mandatory
                  DESCRIPTION "End-net"
                  ::= {  setIpxmRipWanfCols 2 }

setIpxmRipRout OBJECT-TYPE
               SYNTAX INTEGER
               ACCESS read-write
               STATUS mandatory
               DESCRIPTION "Routes/Frm"
               ::= {  setIpxmRip 4 }

setIpxmRipAgin OBJECT-TYPE
               SYNTAX INTEGER
               ACCESS read-write
               STATUS mandatory
               DESCRIPTION "Aging-minute(s)"
               ::= {  setIpxmRip 5 }

setIpxmRipSpoo OBJECT-TYPE
               SYNTAX INTEGER {
                 off(0),
                 trig(1),
                 time(2),
                 pback(3)
               }
               ACCESS read-write
               STATUS mandatory
               DESCRIPTION "Spoofing"
               ::= {  setIpxmRip 6 }

setIpxmRipWanu OBJECT-TYPE
               SYNTAX INTEGER
               ACCESS read-write
               STATUS mandatory
               DESCRIPTION "WAN-update-min."
               ::= {  setIpxmRip 7 }

setIpxmSap OBJECT IDENTIFIER ::= { setIpxm 6}
setIpxmSapTabl OBJECT-TYPE
               SYNTAX SEQUENCE OF SetIpxmSapTablRows
               ACCESS not-accessible
               STATUS mandatory
               DESCRIPTION "Table-SAP"
               ::= {  setIpxmSap 1 }

setIpxmSapTablCols OBJECT-TYPE
               SYNTAX SetIpxmSapTablRows
               ACCESS not-accessible
               STATUS mandatory
               DESCRIPTION "entry in table"
               INDEX { setIpxmSapTablTyp }
               ::= {  setIpxmSapTabl 1 }

SetIpxmSapTablRows ::= SEQUENCE {
               setIpxmSapTablTyp DisplayString,
               setIpxmSapTablSer DisplayString,
               setIpxmSapTablNet DisplayString,
               setIpxmSapTablNod DisplayString,
               setIpxmSapTablSoc DisplayString,
               setIpxmSapTablHop INTEGER,
               setIpxmSapTablTim INTEGER,
               setIpxmSapTablFla INTEGER
              }

setIpxmSapTablTyp OBJECT-TYPE
                  SYNTAX DisplayString
                  ACCESS read-only
                  STATUS mandatory
                  DESCRIPTION "Type"
                  ::= {  setIpxmSapTablCols 1 }

setIpxmSapTablSer OBJECT-TYPE
                  SYNTAX DisplayString
                  ACCESS read-only
                  STATUS mandatory
                  DESCRIPTION "Server-name"
                  ::= {  setIpxmSapTablCols 2 }

setIpxmSapTablNet OBJECT-TYPE
                  SYNTAX DisplayString
                  ACCESS read-only
                  STATUS mandatory
                  DESCRIPTION "Network"
                  ::= {  setIpxmSapTablCols 3 }

setIpxmSapTablNod OBJECT-TYPE
                  SYNTAX DisplayString
                  ACCESS read-only
                  STATUS mandatory
                  DESCRIPTION "Node-ID"
                  ::= {  setIpxmSapTablCols 4 }

setIpxmSapTablSoc OBJECT-TYPE
                  SYNTAX DisplayString
                  ACCESS read-only
                  STATUS mandatory
                  DESCRIPTION "Socket"
                  ::= {  setIpxmSapTablCols 5 }

setIpxmSapTablHop OBJECT-TYPE
                  SYNTAX INTEGER
                  ACCESS read-only
                  STATUS mandatory
                  DESCRIPTION "Hops"
                  ::= {  setIpxmSapTablCols 6 }

setIpxmSapTablTim OBJECT-TYPE
                  SYNTAX INTEGER
                  ACCESS read-only
                  STATUS mandatory
                  DESCRIPTION "Time"
                  ::= {  setIpxmSapTablCols 7 }

setIpxmSapTablFla OBJECT-TYPE
                  SYNTAX INTEGER {
                    local(2),
                    remote(1),
                    direct(128),
                    new(64),
                    down(32),
                    loop(16),
                    spare(8)
                  }
                  ACCESS read-only
                  STATUS mandatory
                  DESCRIPTION "Flags"
                  ::= {  setIpxmSapTablCols 8 }

setIpxmSapLanf OBJECT-TYPE
               SYNTAX SEQUENCE OF SetIpxmSapLanfRows
               ACCESS not-accessible
               STATUS mandatory
               DESCRIPTION "LAN-filter-table"
               ::= {  setIpxmSap 2 }

setIpxmSapLanfCols OBJECT-TYPE
               SYNTAX SetIpxmSapLanfRows
               ACCESS not-accessible
               STATUS mandatory
               DESCRIPTION "entry in table"
               INDEX { setIpxmSapLanfSta }
               ::= {  setIpxmSapLanf 1 }

SetIpxmSapLanfRows ::= SEQUENCE {
               setIpxmSapLanfSta DisplayString,
               setIpxmSapLanfEnd DisplayString
              }

setIpxmSapLanfSta OBJECT-TYPE
                  SYNTAX DisplayString
                  ACCESS read-write
                  STATUS mandatory
                  DESCRIPTION "Start-service"
                  ::= {  setIpxmSapLanfCols 1 }

setIpxmSapLanfEnd OBJECT-TYPE
                  SYNTAX DisplayString
                  ACCESS read-write
                  STATUS mandatory
                  DESCRIPTION "End-service"
                  ::= {  setIpxmSapLanfCols 2 }

setIpxmSapWanf OBJECT-TYPE
               SYNTAX SEQUENCE OF SetIpxmSapWanfRows
               ACCESS not-accessible
               STATUS mandatory
               DESCRIPTION "WAN-filter-table"
               ::= {  setIpxmSap 3 }

setIpxmSapWanfCols OBJECT-TYPE
               SYNTAX SetIpxmSapWanfRows
               ACCESS not-accessible
               STATUS mandatory
               DESCRIPTION "entry in table"
               INDEX { setIpxmSapWanfSta }
               ::= {  setIpxmSapWanf 1 }

SetIpxmSapWanfRows ::= SEQUENCE {
               setIpxmSapWanfSta DisplayString,
               setIpxmSapWanfEnd DisplayString
              }

setIpxmSapWanfSta OBJECT-TYPE
                  SYNTAX DisplayString
                  ACCESS read-write
                  STATUS mandatory
                  DESCRIPTION "Start-service"
                  ::= {  setIpxmSapWanfCols 1 }

setIpxmSapWanfEnd OBJECT-TYPE
                  SYNTAX DisplayString
                  ACCESS read-write
                  STATUS mandatory
                  DESCRIPTION "End-service"
                  ::= {  setIpxmSapWanfCols 2 }

setIpxmSapServ OBJECT-TYPE
               SYNTAX INTEGER
               ACCESS read-write
               STATUS mandatory
               DESCRIPTION "Server/Frm"
               ::= {  setIpxmSap 4 }

setIpxmSapAgin OBJECT-TYPE
               SYNTAX INTEGER
               ACCESS read-write
               STATUS mandatory
               DESCRIPTION "Aging-minute(s)"
               ::= {  setIpxmSap 5 }

setIpxmSapSpoo OBJECT-TYPE
               SYNTAX INTEGER {
                 off(0),
                 trig(1),
                 time(2),
                 pback(3)
               }
               ACCESS read-write
               STATUS mandatory
               DESCRIPTION "Spoofing"
               ::= {  setIpxmSap 6 }

setIpxmSapWanu OBJECT-TYPE
               SYNTAX INTEGER
               ACCESS read-write
               STATUS mandatory
               DESCRIPTION "WAN-update-min."
               ::= {  setIpxmSap 7 }

setTcpi OBJECT IDENTIFIER ::= { set 7}
setTcpiOperating OBJECT-TYPE
                 SYNTAX INTEGER {
                   on(1),
                   off(0)
                 }
                 ACCESS read-write
                 STATUS mandatory
                 DESCRIPTION "Operating"
                 ::= {  setTcpi 1 }

setTcpiIpaddress OBJECT-TYPE
                 SYNTAX IpAddress
                 ACCESS read-write
                 STATUS mandatory
                 DESCRIPTION "IP-address"
                 ::= {  setTcpi 2 }

setTcpiIpnetmask OBJECT-TYPE
                 SYNTAX IpAddress
                 ACCESS read-write
                 STATUS mandatory
                 DESCRIPTION "IP-netmask"
                 ::= {  setTcpi 3 }

setTcpiIntraneta OBJECT-TYPE
                 SYNTAX IpAddress
                 ACCESS read-write
                 STATUS mandatory
                 DESCRIPTION "Intranet-addr."
                 ::= {  setTcpi 4 }

setTcpiIntranetm OBJECT-TYPE
                 SYNTAX IpAddress
                 ACCESS read-write
                 STATUS mandatory
                 DESCRIPTION "Intranetmask"
                 ::= {  setTcpi 5 }

setTcpiAccesslis OBJECT-TYPE
                 SYNTAX SEQUENCE OF SetTcpiAccesslisRows
                 ACCESS not-accessible
                 STATUS mandatory
                 DESCRIPTION "Access-list"
                 ::= {  setTcpi 6 }

setTcpiAccesslisCols OBJECT-TYPE
                 SYNTAX SetTcpiAccesslisRows
                 ACCESS not-accessible
                 STATUS mandatory
                 DESCRIPTION "entry in table"
                 INDEX { setTcpiAccesslisIpa }
                 ::= {  setTcpiAccesslis 1 }

SetTcpiAccesslisRows ::= SEQUENCE {
                 setTcpiAccesslisIpa IpAddress,
                 setTcpiAccesslisIpn IpAddress
                }

setTcpiAccesslisIpa OBJECT-TYPE
                    SYNTAX IpAddress
                    ACCESS read-write
                    STATUS mandatory
                    DESCRIPTION "IP-address"
                    ::= {  setTcpiAccesslisCols 1 }

setTcpiAccesslisIpn OBJECT-TYPE
                    SYNTAX IpAddress
                    ACCESS read-write
                    STATUS mandatory
                    DESCRIPTION "IP-netmask"
                    ::= {  setTcpiAccesslisCols 2 }

setTcpiDnsdefaul OBJECT-TYPE
                 SYNTAX IpAddress
                 ACCESS read-write
                 STATUS mandatory
                 DESCRIPTION "DNS-default"
                 ::= {  setTcpi 7 }

setTcpiDnsbackup OBJECT-TYPE
                 SYNTAX IpAddress
                 ACCESS read-write
                 STATUS mandatory
                 DESCRIPTION "DNS-backup"
                 ::= {  setTcpi 8 }

setTcpiNbnsdefau OBJECT-TYPE
                 SYNTAX IpAddress
                 ACCESS read-write
                 STATUS mandatory
                 DESCRIPTION "NBNS-default"
                 ::= {  setTcpi 9 }

setTcpiNbnsbacku OBJECT-TYPE
                 SYNTAX IpAddress
                 ACCESS read-write
                 STATUS mandatory
                 DESCRIPTION "NBNS-backup"
                 ::= {  setTcpi 10 }

setTcpiTablearp OBJECT-TYPE
                 SYNTAX SEQUENCE OF SetTcpiTablearpRows
                 ACCESS not-accessible
                 STATUS mandatory
                 DESCRIPTION "Table-ARP"
                 ::= {  setTcpi 16 }

setTcpiTablearpCols OBJECT-TYPE
                 SYNTAX SetTcpiTablearpRows
                 ACCESS not-accessible
                 STATUS mandatory
                 DESCRIPTION "entry in table"
                 INDEX { setTcpiTablearpIpa }
                 ::= {  setTcpiTablearp 1 }

SetTcpiTablearpRows ::= SEQUENCE {
                 setTcpiTablearpIpa IpAddress,
                 setTcpiTablearpNod DisplayString,
                 setTcpiTablearpLas INTEGER,
                 setTcpiTablearpCon INTEGER
                }

setTcpiTablearpIpa OBJECT-TYPE
                   SYNTAX IpAddress
                   ACCESS read-only
                   STATUS mandatory
                   DESCRIPTION "IP-address"
                   ::= {  setTcpiTablearpCols 1 }

setTcpiTablearpNod OBJECT-TYPE
                   SYNTAX DisplayString
                   ACCESS read-only
                   STATUS mandatory
                   DESCRIPTION "Node-ID"
                   ::= {  setTcpiTablearpCols 2 }

setTcpiTablearpLas OBJECT-TYPE
                   SYNTAX INTEGER
                   ACCESS read-only
                   STATUS mandatory
                   DESCRIPTION "Last-access"
                   ::= {  setTcpiTablearpCols 3 }

setTcpiTablearpCon OBJECT-TYPE
                   SYNTAX INTEGER {
                     local(2),
                     remote(1)
                   }
                   ACCESS read-only
                   STATUS mandatory
                   DESCRIPTION "Connect"
                   ::= {  setTcpiTablearpCols 4 }

setTcpiArpagingm OBJECT-TYPE
                 SYNTAX INTEGER
                 ACCESS read-write
                 STATUS mandatory
                 DESCRIPTION "ARP-aging-min."
                 ::= {  setTcpi 11 }

setTcpiTcpagingm OBJECT-TYPE
                 SYNTAX INTEGER
                 ACCESS read-write
                 STATUS mandatory
                 DESCRIPTION "TCP-aging-min."
                 ::= {  setTcpi 12 }

setTcpiTcpmaxcon OBJECT-TYPE
                 SYNTAX INTEGER
                 ACCESS read-write
                 STATUS mandatory
                 DESCRIPTION "TCP-max.-conn."
                 ::= {  setTcpi 13 }

setIpro OBJECT IDENTIFIER ::= { set 8}
setIproOpe OBJECT-TYPE
           SYNTAX INTEGER {
             on(1),
             off(0)
           }
           ACCESS read-write
           STATUS mandatory
           DESCRIPTION "Operating"
           ::= {  setIpro 1 }

setIproIpr OBJECT-TYPE
           SYNTAX SEQUENCE OF SetIproIprRows
           ACCESS not-accessible
           STATUS mandatory
           DESCRIPTION "IP-routing-table"
           ::= {  setIpro 2 }

setIproIprCols OBJECT-TYPE
           SYNTAX SetIproIprRows
           ACCESS not-accessible
           STATUS mandatory
           DESCRIPTION "entry in table"
           INDEX { setIproIprIpa }
           ::= {  setIproIpr 1 }

SetIproIprRows ::= SEQUENCE {
           setIproIprIpa IpAddress,
           setIproIprIpn IpAddress,
           setIproIprRou DisplayString,
           setIproIprDis INTEGER,
           setIproIprMas INTEGER
          }

setIproIprIpa OBJECT-TYPE
              SYNTAX IpAddress
              ACCESS read-write
              STATUS mandatory
              DESCRIPTION "IP-address"
              ::= {  setIproIprCols 1 }

setIproIprIpn OBJECT-TYPE
              SYNTAX IpAddress
              ACCESS read-write
              STATUS mandatory
              DESCRIPTION "IP-netmask"
              ::= {  setIproIprCols 2 }

setIproIprRou OBJECT-TYPE
              SYNTAX DisplayString
              ACCESS read-write
              STATUS mandatory
              DESCRIPTION "Router-name"
              ::= {  setIproIprCols 3 }

setIproIprDis OBJECT-TYPE
              SYNTAX INTEGER
              ACCESS read-write
              STATUS mandatory
              DESCRIPTION "Distance"
              ::= {  setIproIprCols 4 }

setIproIprMas OBJECT-TYPE
              SYNTAX INTEGER {
                off(0),
                on(1),
                static(2)
              }
              ACCESS read-write
              STATUS mandatory
              DESCRIPTION "masquerade"
              ::= {  setIproIprCols 5 }

setIproDef OBJECT-TYPE
           SYNTAX SEQUENCE OF SetIproDefRows
           ACCESS not-accessible
           STATUS mandatory
           DESCRIPTION "Default-timetable"
           ::= {  setIpro 13 }

setIproDefCols OBJECT-TYPE
           SYNTAX SetIproDefRows
           ACCESS not-accessible
           STATUS mandatory
           DESCRIPTION "entry in table"
           INDEX { setIproDefInd }
           ::= {  setIproDef 1 }

SetIproDefRows ::= SEQUENCE {
           setIproDefInd INTEGER,
           setIproDefDay INTEGER,
           setIproDefSta DisplayString,
           setIproDefSto DisplayString,
           setIproDefDev DisplayString
          }

setIproDefInd OBJECT-TYPE
              SYNTAX INTEGER
              ACCESS read-write
              STATUS mandatory
              DESCRIPTION "Index"
              ::= {  setIproDefCols 1 }

setIproDefDay OBJECT-TYPE
              SYNTAX INTEGER
              ACCESS read-write
              STATUS mandatory
              DESCRIPTION "Days"
              ::= {  setIproDefCols 2 }

setIproDefSta OBJECT-TYPE
              SYNTAX DisplayString
              ACCESS read-write
              STATUS mandatory
              DESCRIPTION "Start"
              ::= {  setIproDefCols 3 }

setIproDefSto OBJECT-TYPE
              SYNTAX DisplayString
              ACCESS read-write
              STATUS mandatory
              DESCRIPTION "Stop"
              ::= {  setIproDefCols 4 }

setIproDefDev OBJECT-TYPE
              SYNTAX DisplayString
              ACCESS read-write
              STATUS mandatory
              DESCRIPTION "Device-name"
              ::= {  setIproDefCols 5 }

setIproUsa OBJECT-TYPE
           SYNTAX INTEGER {
             on(1),
             off(0)
           }
           ACCESS read-write
           STATUS mandatory
           DESCRIPTION "Usage-default-timetable"
           ::= {  setIpro 14 }

setIproPro OBJECT-TYPE
           SYNTAX INTEGER {
             on(1),
             off(0)
           }
           ACCESS read-write
           STATUS mandatory
           DESCRIPTION "Proxy-ARP"
           ::= {  setIpro 5 }

setIproLoc OBJECT-TYPE
           SYNTAX INTEGER {
             on(1),
             off(0)
           }
           ACCESS read-write
           STATUS mandatory
           DESCRIPTION "Loc.-routing"
           ::= {  setIpro 6 }

setIproRou OBJECT IDENTIFIER ::= { setIpro 7}
setIproRouRou OBJECT-TYPE
              SYNTAX INTEGER {
                normal(0),
                type-of-service(1)
              }
              ACCESS read-write
              STATUS mandatory
              DESCRIPTION "Routing-method"
              ::= {  setIproRou 1 }

setIproRouIcm OBJECT-TYPE
              SYNTAX INTEGER {
                normal(0),
                reliable(1)
              }
              ACCESS read-write
              STATUS mandatory
              DESCRIPTION "ICMP-routing-method"
              ::= {  setIproRou 2 }

setIproRip OBJECT IDENTIFIER ::= { setIpro 8}
setIproRipRip OBJECT-TYPE
              SYNTAX INTEGER {
                off(0),
                rip-1(1),
                r1-comp(2),
                rip-2(3)
              }
              ACCESS read-write
              STATUS mandatory
              DESCRIPTION "RIP-type"
              ::= {  setIproRip 1 }

setIproRipR1m OBJECT-TYPE
              SYNTAX INTEGER {
                class(0),
                address(1),
                cl-and-addr(2)
              }
              ACCESS read-write
              STATUS mandatory
              DESCRIPTION "R1-mask"
              ::= {  setIproRip 2 }

setIproRipTab OBJECT-TYPE
              SYNTAX SEQUENCE OF SetIproRipTabRows
              ACCESS not-accessible
              STATUS mandatory
              DESCRIPTION "Table-IP-RIP"
              ::= {  setIproRip 3 }

setIproRipTabCols OBJECT-TYPE
              SYNTAX SetIproRipTabRows
              ACCESS not-accessible
              STATUS mandatory
              DESCRIPTION "entry in table"
              INDEX { setIproRipTabIpa }
              ::= {  setIproRipTab 1 }

SetIproRipTabRows ::= SEQUENCE {
              setIproRipTabIpa IpAddress,
              setIproRipTabIpn IpAddress,
              setIproRipTabTim INTEGER,
              setIproRipTabDis INTEGER,
              setIproRipTabRou DisplayString
             }

setIproRipTabIpa OBJECT-TYPE
                 SYNTAX IpAddress
                 ACCESS read-only
                 STATUS mandatory
                 DESCRIPTION "IP-address"
                 ::= {  setIproRipTabCols 1 }

setIproRipTabIpn OBJECT-TYPE
                 SYNTAX IpAddress
                 ACCESS read-only
                 STATUS mandatory
                 DESCRIPTION "IP-netmask"
                 ::= {  setIproRipTabCols 2 }

setIproRipTabTim OBJECT-TYPE
                 SYNTAX INTEGER
                 ACCESS read-only
                 STATUS mandatory
                 DESCRIPTION "Time"
                 ::= {  setIproRipTabCols 3 }

setIproRipTabDis OBJECT-TYPE
                 SYNTAX INTEGER
                 ACCESS read-only
                 STATUS mandatory
                 DESCRIPTION "distance"
                 ::= {  setIproRipTabCols 4 }

setIproRipTabRou OBJECT-TYPE
                 SYNTAX DisplayString
                 ACCESS read-only
                 STATUS mandatory
                 DESCRIPTION "Router"
                 ::= {  setIproRipTabCols 5 }

setIproMas OBJECT IDENTIFIER ::= { setIpro 9}
setIproMasTcpagings OBJECT-TYPE
                    SYNTAX INTEGER
                    ACCESS read-write
                    STATUS mandatory
                    DESCRIPTION "TCP-aging-second(s)"
                    ::= {  setIproMas 1 }

setIproMasUdpagings OBJECT-TYPE
                    SYNTAX INTEGER
                    ACCESS read-write
                    STATUS mandatory
                    DESCRIPTION "UDP-aging-second(s)"
                    ::= {  setIproMas 2 }

setIproMasIcmpaging OBJECT-TYPE
                    SYNTAX INTEGER
                    ACCESS read-write
                    STATUS mandatory
                    DESCRIPTION "ICMP-aging-second(s)"
                    ::= {  setIproMas 3 }

setIproMasServiceta OBJECT-TYPE
                    SYNTAX SEQUENCE OF SetIproMasServicetaRows
                    ACCESS not-accessible
                    STATUS mandatory
                    DESCRIPTION "Service-table"
                    ::= {  setIproMas 4 }

setIproMasServicetaCols OBJECT-TYPE
                    SYNTAX SetIproMasServicetaRows
                    ACCESS not-accessible
                    STATUS mandatory
                    DESCRIPTION "entry in table"
                    INDEX { setIproMasServicetaDpo }
                    ::= {  setIproMasServiceta 1 }

SetIproMasServicetaRows ::= SEQUENCE {
                    setIproMasServicetaDpo INTEGER,
                    setIproMasServicetaInt IpAddress
                   }

setIproMasServicetaDpo OBJECT-TYPE
                       SYNTAX INTEGER
                       ACCESS read-write
                       STATUS mandatory
                       DESCRIPTION "D-port"
                       ::= {  setIproMasServicetaCols 1 }

setIproMasServicetaInt OBJECT-TYPE
                       SYNTAX IpAddress
                       ACCESS read-write
                       STATUS mandatory
                       DESCRIPTION "Intranet-addr."
                       ::= {  setIproMasServicetaCols 2 }

setIproMasTablemasq OBJECT-TYPE
                    SYNTAX SEQUENCE OF SetIproMasTablemasqRows
                    ACCESS not-accessible
                    STATUS mandatory
                    DESCRIPTION "Table-masquerading"
                    ::= {  setIproMas 5 }

setIproMasTablemasqCols OBJECT-TYPE
                    SYNTAX SetIproMasTablemasqRows
                    ACCESS not-accessible
                    STATUS mandatory
                    DESCRIPTION "entry in table"
                    INDEX { setIproMasTablemasqInt }
                    ::= {  setIproMasTablemasq 1 }

SetIproMasTablemasqRows ::= SEQUENCE {
                    setIproMasTablemasqInt IpAddress,
                    setIproMasTablemasqSpo INTEGER,
                    setIproMasTablemasqPro INTEGER,
                    setIproMasTablemasqTim INTEGER
                   }

setIproMasTablemasqInt OBJECT-TYPE
                       SYNTAX IpAddress
                       ACCESS read-only
                       STATUS mandatory
                       DESCRIPTION "Intranet-addr."
                       ::= {  setIproMasTablemasqCols 1 }

setIproMasTablemasqSpo OBJECT-TYPE
                       SYNTAX INTEGER
                       ACCESS read-only
                       STATUS mandatory
                       DESCRIPTION "S-port"
                       ::= {  setIproMasTablemasqCols 2 }

setIproMasTablemasqPro OBJECT-TYPE
                       SYNTAX INTEGER {
                         tcp(1),
                         udp(2),
                         icmp(4)
                       }
                       ACCESS read-only
                       STATUS mandatory
                       DESCRIPTION "Protocol"
                       ::= {  setIproMasTablemasqCols 3 }

setIproMasTablemasqTim OBJECT-TYPE
                       SYNTAX INTEGER
                       ACCESS read-only
                       STATUS mandatory
                       DESCRIPTION "Timeout"
                       ::= {  setIproMasTablemasqCols 4 }

setIproMasFragments OBJECT-TYPE
                    SYNTAX INTEGER {
                      filter(0),
                      route(1),
                      reassemble(2)
                    }
                    ACCESS read-write
                    STATUS mandatory
                    DESCRIPTION "Fragments"
                    ::= {  setIproMas 6 }

setIproMasFragmenta OBJECT-TYPE
                    SYNTAX INTEGER
                    ACCESS read-write
                    STATUS mandatory
                    DESCRIPTION "Fragment-aging-second(s)"
                    ::= {  setIproMas 7 }

setIproFir OBJECT IDENTIFIER ::= { setIpro 10}
setIproFirObj OBJECT-TYPE
              SYNTAX SEQUENCE OF SetIproFirObjRows
              ACCESS not-accessible
              STATUS mandatory
              DESCRIPTION "Object-table"
              ::= {  setIproFir 1 }

setIproFirObjCols OBJECT-TYPE
              SYNTAX SetIproFirObjRows
              ACCESS not-accessible
              STATUS mandatory
              DESCRIPTION "entry in table"
              INDEX { setIproFirObjNam }
              ::= {  setIproFirObj 1 }

SetIproFirObjRows ::= SEQUENCE {
              setIproFirObjNam DisplayString,
              setIproFirObjDes DisplayString
             }

setIproFirObjNam OBJECT-TYPE
                 SYNTAX DisplayString
                 ACCESS read-write
                 STATUS mandatory
                 DESCRIPTION "Name"
                 ::= {  setIproFirObjCols 1 }

setIproFirObjDes OBJECT-TYPE
                 SYNTAX DisplayString
                 ACCESS read-write
                 STATUS mandatory
                 DESCRIPTION "Description"
                 ::= {  setIproFirObjCols 2 }

setIproFirRul OBJECT-TYPE
              SYNTAX SEQUENCE OF SetIproFirRulRows
              ACCESS not-accessible
              STATUS mandatory
              DESCRIPTION "Rule-table"
              ::= {  setIproFir 2 }

setIproFirRulCols OBJECT-TYPE
              SYNTAX SetIproFirRulRows
              ACCESS not-accessible
              STATUS mandatory
              DESCRIPTION "entry in table"
              INDEX { setIproFirRulNam }
              ::= {  setIproFirRul 1 }

SetIproFirRulRows ::= SEQUENCE {
              setIproFirRulNam DisplayString,
              setIproFirRulPro DisplayString,
              setIproFirRulSou DisplayString,
              setIproFirRulDes DisplayString,
              setIproFirRulAct INTEGER
             }

setIproFirRulNam OBJECT-TYPE
                 SYNTAX DisplayString
                 ACCESS read-write
                 STATUS mandatory
                 DESCRIPTION "Name"
                 ::= {  setIproFirRulCols 1 }

setIproFirRulPro OBJECT-TYPE
                 SYNTAX DisplayString
                 ACCESS read-write
                 STATUS mandatory
                 DESCRIPTION "Prot."
                 ::= {  setIproFirRulCols 2 }

setIproFirRulSou OBJECT-TYPE
                 SYNTAX DisplayString
                 ACCESS read-write
                 STATUS mandatory
                 DESCRIPTION "Source"
                 ::= {  setIproFirRulCols 3 }

setIproFirRulDes OBJECT-TYPE
                 SYNTAX DisplayString
                 ACCESS read-write
                 STATUS mandatory
                 DESCRIPTION "Destination"
                 ::= {  setIproFirRulCols 4 }

setIproFirRulAct OBJECT-TYPE
                 SYNTAX INTEGER {
                   always-filt(256),
                   connect-filt(512),
                   internet-filt(1024),
                   accept(1)
                 }
                 ACCESS read-write
                 STATUS mandatory
                 DESCRIPTION "Action"
                 ::= {  setIproFirRulCols 5 }

setIproFirFil OBJECT-TYPE
              SYNTAX SEQUENCE OF SetIproFirFilRows
              ACCESS not-accessible
              STATUS mandatory
              DESCRIPTION "Filter-list"
              ::= {  setIproFir 3 }

setIproFirFilCols OBJECT-TYPE
              SYNTAX SetIproFirFilRows
              ACCESS not-accessible
              STATUS mandatory
              DESCRIPTION "entry in table"
              INDEX { setIproFirFilIdx }
              ::= {  setIproFirFil 1 }

SetIproFirFilRows ::= SEQUENCE {
              setIproFirFilIdx INTEGER,
              setIproFirFilProt INTEGER,
              setIproFirFilSrca IpAddress,
              setIproFirFilSrcn IpAddress,
              setIproFirFilSst INTEGER,
              setIproFirFilSend INTEGER,
              setIproFirFilDsta IpAddress,
              setIproFirFilDstn IpAddress,
              setIproFirFilDst INTEGER,
              setIproFirFilDend INTEGER,
              setIproFirFilActi INTEGER
             }

setIproFirFilIdx OBJECT-TYPE
                  SYNTAX INTEGER
                  ACCESS read-only
                  STATUS mandatory
                  DESCRIPTION "Idx."
                  ::= {  setIproFirFilCols 1 }

setIproFirFilProt OBJECT-TYPE
                  SYNTAX INTEGER
                  ACCESS read-only
                  STATUS mandatory
                  DESCRIPTION "Prot."
                  ::= {  setIproFirFilCols 2 }

setIproFirFilSrca OBJECT-TYPE
                  SYNTAX IpAddress
                  ACCESS read-only
                  STATUS mandatory
                  DESCRIPTION "Src-address"
                  ::= {  setIproFirFilCols 3 }

setIproFirFilSrcn OBJECT-TYPE
                  SYNTAX IpAddress
                  ACCESS read-only
                  STATUS mandatory
                  DESCRIPTION "Src-netmask"
                  ::= {  setIproFirFilCols 4 }

setIproFirFilSst OBJECT-TYPE
                  SYNTAX INTEGER
                  ACCESS read-only
                  STATUS mandatory
                  DESCRIPTION "S-st."
                  ::= {  setIproFirFilCols 5 }

setIproFirFilSend OBJECT-TYPE
                  SYNTAX INTEGER
                  ACCESS read-only
                  STATUS mandatory
                  DESCRIPTION "S-end"
                  ::= {  setIproFirFilCols 6 }

setIproFirFilDsta OBJECT-TYPE
                  SYNTAX IpAddress
                  ACCESS read-only
                  STATUS mandatory
                  DESCRIPTION "Dst-address"
                  ::= {  setIproFirFilCols 7 }

setIproFirFilDstn OBJECT-TYPE
                  SYNTAX IpAddress
                  ACCESS read-only
                  STATUS mandatory
                  DESCRIPTION "Dst-netmask"
                  ::= {  setIproFirFilCols 8 }

setIproFirFilDst OBJECT-TYPE
                  SYNTAX INTEGER
                  ACCESS read-only
                  STATUS mandatory
                  DESCRIPTION "D-st."
                  ::= {  setIproFirFilCols 9 }

setIproFirFilDend OBJECT-TYPE
                  SYNTAX INTEGER
                  ACCESS read-only
                  STATUS mandatory
                  DESCRIPTION "D-end"
                  ::= {  setIproFirFilCols 10 }

setIproFirFilActi OBJECT-TYPE
                  SYNTAX INTEGER {
                    always-filt(256),
                    connect-filt(512),
                    internet-filt(1024),
                    accept(1)
                  }
                  ACCESS read-only
                  STATUS mandatory
                  DESCRIPTION "Action"
                  ::= {  setIproFirFilCols 11 }

setSnmp OBJECT IDENTIFIER ::= { set 9}
setSnmpSen OBJECT-TYPE
           SYNTAX INTEGER {
             yes(1),
             no(0)
           }
           ACCESS read-write
           STATUS mandatory
           DESCRIPTION "Send-Traps"
           ::= {  setSnmp 1 }

setSnmpIpt OBJECT-TYPE
           SYNTAX SEQUENCE OF SetSnmpIptRows
           ACCESS not-accessible
           STATUS mandatory
           DESCRIPTION "IP-Trap-Table"
           ::= {  setSnmp 2 }

setSnmpIptCols OBJECT-TYPE
           SYNTAX SetSnmpIptRows
           ACCESS not-accessible
           STATUS mandatory
           DESCRIPTION "entry in table"
           INDEX { setSnmpIptTra }
           ::= {  setSnmpIpt 1 }

SetSnmpIptRows ::= SEQUENCE {
           setSnmpIptTra IpAddress
          }

setSnmpIptTra OBJECT-TYPE
              SYNTAX IpAddress
              ACCESS read-write
              STATUS mandatory
              DESCRIPTION "Trap-IP"
              ::= {  setSnmpIptCols 1 }

setSnmpAdm OBJECT-TYPE
           SYNTAX DisplayString (SIZE(0..255))
           ACCESS read-write
           STATUS mandatory
           DESCRIPTION "Administrator"
           ::= {  setSnmp 3 }

setSnmpLoc OBJECT-TYPE
           SYNTAX DisplayString (SIZE(0..255))
           ACCESS read-write
           STATUS mandatory
           DESCRIPTION "Location"
           ::= {  setSnmp 4 }

setSnmpPas OBJECT-TYPE
           SYNTAX INTEGER {
             on(1),
             off(0)
           }
           ACCESS read-write
           STATUS mandatory
           DESCRIPTION "Password-required-for-SNMP-read-access"
           ::= {  setSnmp 10 }

setSnmpReg OBJECT-TYPE
           SYNTAX INTEGER
           ACCESS write-only
           STATUS mandatory
           DESCRIPTION "Register-monitor"
           ::= {  setSnmp 5 }

setSnmpDel OBJECT-TYPE
           SYNTAX INTEGER
           ACCESS write-only
           STATUS mandatory
           DESCRIPTION "Delete-Monitor"
           ::= {  setSnmp 6 }

setSnmpMon OBJECT-TYPE
           SYNTAX SEQUENCE OF SetSnmpMonRows
           ACCESS not-accessible
           STATUS mandatory
           DESCRIPTION "Monitor-table"
           ::= {  setSnmp 7 }

setSnmpMonCols OBJECT-TYPE
           SYNTAX SetSnmpMonRows
           ACCESS not-accessible
           STATUS mandatory
           DESCRIPTION "entry in table"
           INDEX { setSnmpMonIpa }
           ::= {  setSnmpMon 1 }

SetSnmpMonRows ::= SEQUENCE {
           setSnmpMonIpa IpAddress,
           setSnmpMonPor INTEGER,
           setSnmpMonMac DisplayString,
           setSnmpMonTim INTEGER,
           setSnmpMonDev DisplayString
          }

setSnmpMonIpa OBJECT-TYPE
              SYNTAX IpAddress
              ACCESS read-only
              STATUS mandatory
              DESCRIPTION "IP-Address"
              ::= {  setSnmpMonCols 1 }

setSnmpMonPor OBJECT-TYPE
              SYNTAX INTEGER
              ACCESS read-only
              STATUS mandatory
              DESCRIPTION "Port"
              ::= {  setSnmpMonCols 2 }

setSnmpMonMac OBJECT-TYPE
              SYNTAX DisplayString
              ACCESS read-only
              STATUS mandatory
              DESCRIPTION "MAC-Address"
              ::= {  setSnmpMonCols 4 }

setSnmpMonTim OBJECT-TYPE
              SYNTAX INTEGER
              ACCESS read-only
              STATUS mandatory
              DESCRIPTION "Timeout"
              ::= {  setSnmpMonCols 3 }

setSnmpMonDev OBJECT-TYPE
              SYNTAX DisplayString
              ACCESS read-only
              STATUS mandatory
              DESCRIPTION "Device-name"
              ::= {  setSnmpMonCols 5 }

setDhcp OBJECT IDENTIFIER ::= { set 10}
setDhcpOpe OBJECT-TYPE
           SYNTAX INTEGER {
             off(0),
             on(1),
             auto(2),
             relay(16)
           }
           ACCESS read-write
           STATUS mandatory
           DESCRIPTION "Operating"
           ::= {  setDhcp 1 }

setDhcpSta OBJECT-TYPE
           SYNTAX IpAddress
           ACCESS read-write
           STATUS mandatory
           DESCRIPTION "Start-address-pool"
           ::= {  setDhcp 2 }

setDhcpEnd OBJECT-TYPE
           SYNTAX IpAddress
           ACCESS read-write
           STATUS mandatory
           DESCRIPTION "End-address-pool"
           ::= {  setDhcp 3 }

setDhcpNet OBJECT-TYPE
           SYNTAX IpAddress
           ACCESS read-write
           STATUS mandatory
           DESCRIPTION "Netmask"
           ::= {  setDhcp 4 }

setDhcpBro OBJECT-TYPE
           SYNTAX IpAddress
           ACCESS read-write
           STATUS mandatory
           DESCRIPTION "Broadcast-address"
           ::= {  setDhcp 5 }

setDhcpGat OBJECT-TYPE
           SYNTAX IpAddress
           ACCESS read-write
           STATUS mandatory
           DESCRIPTION "Gateway-address"
           ::= {  setDhcp 14 }

setDhcpMax OBJECT-TYPE
           SYNTAX INTEGER
           ACCESS read-write
           STATUS mandatory
           DESCRIPTION "Max.-lease-time-minute(s)"
           ::= {  setDhcp 6 }

setDhcpDef OBJECT-TYPE
           SYNTAX INTEGER
           ACCESS read-write
           STATUS mandatory
           DESCRIPTION "Default-lease-time-minute(s)"
           ::= {  setDhcp 7 }

setDhcpTab OBJECT-TYPE
           SYNTAX SEQUENCE OF SetDhcpTabRows
           ACCESS not-accessible
           STATUS mandatory
           DESCRIPTION "Table-DHCP"
           ::= {  setDhcp 8 }

setDhcpTabCols OBJECT-TYPE
           SYNTAX SetDhcpTabRows
           ACCESS not-accessible
           STATUS mandatory
           DESCRIPTION "entry in table"
           INDEX { setDhcpTabIpa }
           ::= {  setDhcpTab 1 }

SetDhcpTabRows ::= SEQUENCE {
           setDhcpTabIpa IpAddress,
           setDhcpTabNod DisplayString,
           setDhcpTabTim INTEGER,
           setDhcpTabHos DisplayString,
           setDhcpTabTyp INTEGER
          }

setDhcpTabIpa OBJECT-TYPE
              SYNTAX IpAddress
              ACCESS read-only
              STATUS mandatory
              DESCRIPTION "IP-Address"
              ::= {  setDhcpTabCols 1 }

setDhcpTabNod OBJECT-TYPE
              SYNTAX DisplayString
              ACCESS read-only
              STATUS mandatory
              DESCRIPTION "Node-ID"
              ::= {  setDhcpTabCols 2 }

setDhcpTabTim OBJECT-TYPE
              SYNTAX INTEGER
              ACCESS read-only
              STATUS mandatory
              DESCRIPTION "Timeout"
              ::= {  setDhcpTabCols 3 }

setDhcpTabHos OBJECT-TYPE
              SYNTAX DisplayString
              ACCESS read-only
              STATUS mandatory
              DESCRIPTION "Hostname"
              ::= {  setDhcpTabCols 4 }

setDhcpTabTyp OBJECT-TYPE
              SYNTAX INTEGER {
                new(1),
                new(2),
                dyn(16),
                unkn(4),
                stat(8),
                bootp(32),
                relay(2048)
              }
              ACCESS read-only
              STATUS mandatory
              DESCRIPTION "Type"
              ::= {  setDhcpTabCols 5 }

setDhcpHos OBJECT-TYPE
           SYNTAX SEQUENCE OF SetDhcpHosRows
           ACCESS not-accessible
           STATUS mandatory
           DESCRIPTION "Host-table"
           ::= {  setDhcp 9 }

setDhcpHosCols OBJECT-TYPE
           SYNTAX SetDhcpHosRows
           ACCESS not-accessible
           STATUS mandatory
           DESCRIPTION "entry in table"
           INDEX { setDhcpHosNod }
           ::= {  setDhcpHos 1 }

SetDhcpHosRows ::= SEQUENCE {
           setDhcpHosNod DisplayString,
           setDhcpHosIpa IpAddress,
           setDhcpHosHos DisplayString,
           setDhcpHosIma DisplayString
          }

setDhcpHosNod OBJECT-TYPE
              SYNTAX DisplayString
              ACCESS read-write
              STATUS mandatory
              DESCRIPTION "Node-ID"
              ::= {  setDhcpHosCols 1 }

setDhcpHosIpa OBJECT-TYPE
              SYNTAX IpAddress
              ACCESS read-write
              STATUS mandatory
              DESCRIPTION "IP-Address"
              ::= {  setDhcpHosCols 2 }

setDhcpHosHos OBJECT-TYPE
              SYNTAX DisplayString
              ACCESS read-write
              STATUS mandatory
              DESCRIPTION "Hostname"
              ::= {  setDhcpHosCols 3 }

setDhcpHosIma OBJECT-TYPE
              SYNTAX DisplayString
              ACCESS read-write
              STATUS mandatory
              DESCRIPTION "Image-alias"
              ::= {  setDhcpHosCols 4 }

setDhcpAli OBJECT-TYPE
           SYNTAX SEQUENCE OF SetDhcpAliRows
           ACCESS not-accessible
           STATUS mandatory
           DESCRIPTION "Alias-table"
           ::= {  setDhcp 10 }

setDhcpAliCols OBJECT-TYPE
           SYNTAX SetDhcpAliRows
           ACCESS not-accessible
           STATUS mandatory
           DESCRIPTION "entry in table"
           INDEX { setDhcpAliImagea }
           ::= {  setDhcpAli 1 }

SetDhcpAliRows ::= SEQUENCE {
           setDhcpAliImagea DisplayString,
           setDhcpAliImages IpAddress,
           setDhcpAliImagef DisplayString
          }

setDhcpAliImagea OBJECT-TYPE
                 SYNTAX DisplayString
                 ACCESS read-write
                 STATUS mandatory
                 DESCRIPTION "Image-alias"
                 ::= {  setDhcpAliCols 1 }

setDhcpAliImages OBJECT-TYPE
                 SYNTAX IpAddress
                 ACCESS read-write
                 STATUS mandatory
                 DESCRIPTION "Image-server"
                 ::= {  setDhcpAliCols 3 }

setDhcpAliImagef OBJECT-TYPE
                 SYNTAX DisplayString
                 ACCESS read-write
                 STATUS mandatory
                 DESCRIPTION "Image-file"
                 ::= {  setDhcpAliCols 2 }

setDhcpMas OBJECT-TYPE
           SYNTAX IpAddress
           ACCESS read-write
           STATUS mandatory
           DESCRIPTION "Master-server"
           ::= {  setDhcp 12 }

setDhcpRep OBJECT-TYPE
           SYNTAX INTEGER {
             yes(1),
             no(0)
           }
           ACCESS read-write
           STATUS mandatory
           DESCRIPTION "Reply-adaption"
           ::= {  setDhcp 13 }

setDhcpRel OBJECT-TYPE
           SYNTAX INTEGER {
             yes(1),
             no(0)
           }
           ACCESS read-write
           STATUS mandatory
           DESCRIPTION "Relay-cache"
           ::= {  setDhcp 15 }

setDnsm OBJECT IDENTIFIER ::= { set 17}
setDnsmOpe OBJECT-TYPE
           SYNTAX INTEGER {
             on(1),
             off(0)
           }
           ACCESS read-write
           STATUS mandatory
           DESCRIPTION "Operating"
           ::= {  setDnsm 1 }

setDnsmDom OBJECT-TYPE
           SYNTAX DisplayString (SIZE(0..64))
           ACCESS read-write
           STATUS mandatory
           DESCRIPTION "Domain"
           ::= {  setDnsm 2 }

setDnsmDhc OBJECT-TYPE
           SYNTAX INTEGER {
             yes(1),
             no(0)
           }
           ACCESS read-write
           STATUS mandatory
           DESCRIPTION "DHCP-usage"
           ::= {  setDnsm 3 }

setDnsmNet OBJECT-TYPE
           SYNTAX INTEGER {
             yes(1),
             no(0)
           }
           ACCESS read-write
           STATUS mandatory
           DESCRIPTION "NetBIOS-usage"
           ::= {  setDnsm 4 }

setDnsmDns OBJECT-TYPE
           SYNTAX SEQUENCE OF SetDnsmDnsRows
           ACCESS not-accessible
           STATUS mandatory
           DESCRIPTION "DNS-table"
           ::= {  setDnsm 5 }

setDnsmDnsCols OBJECT-TYPE
           SYNTAX SetDnsmDnsRows
           ACCESS not-accessible
           STATUS mandatory
           DESCRIPTION "entry in table"
           INDEX { setDnsmDnsHos }
           ::= {  setDnsmDns 1 }

SetDnsmDnsRows ::= SEQUENCE {
           setDnsmDnsHos DisplayString,
           setDnsmDnsIpa IpAddress
          }

setDnsmDnsHos OBJECT-TYPE
              SYNTAX DisplayString
              ACCESS read-write
              STATUS mandatory
              DESCRIPTION "Host-name"
              ::= {  setDnsmDnsCols 1 }

setDnsmDnsIpa OBJECT-TYPE
              SYNTAX IpAddress
              ACCESS read-write
              STATUS mandatory
              DESCRIPTION "IP-Address"
              ::= {  setDnsmDnsCols 2 }

setDnsmFil OBJECT-TYPE
           SYNTAX SEQUENCE OF SetDnsmFilRows
           ACCESS not-accessible
           STATUS mandatory
           DESCRIPTION "Filter-list"
           ::= {  setDnsm 6 }

setDnsmFilCols OBJECT-TYPE
           SYNTAX SetDnsmFilRows
           ACCESS not-accessible
           STATUS mandatory
           DESCRIPTION "entry in table"
           INDEX { setDnsmFilIdx }
           ::= {  setDnsmFil 1 }

SetDnsmFilRows ::= SEQUENCE {
           setDnsmFilIdx DisplayString,
           setDnsmFilDom DisplayString,
           setDnsmFilIpa IpAddress,
           setDnsmFilNet IpAddress
          }

setDnsmFilIdx OBJECT-TYPE
              SYNTAX DisplayString
              ACCESS read-write
              STATUS mandatory
              DESCRIPTION "Idx."
              ::= {  setDnsmFilCols 1 }

setDnsmFilDom OBJECT-TYPE
              SYNTAX DisplayString
              ACCESS read-write
              STATUS mandatory
              DESCRIPTION "Domain"
              ::= {  setDnsmFilCols 2 }

setDnsmFilIpa OBJECT-TYPE
              SYNTAX IpAddress
              ACCESS read-write
              STATUS mandatory
              DESCRIPTION "IP-Address"
              ::= {  setDnsmFilCols 3 }

setDnsmFilNet OBJECT-TYPE
              SYNTAX IpAddress
              ACCESS read-write
              STATUS mandatory
              DESCRIPTION "Netmask"
              ::= {  setDnsmFilCols 4 }

setDnsmDyn OBJECT-TYPE
           SYNTAX SEQUENCE OF SetDnsmDynRows
           ACCESS not-accessible
           STATUS mandatory
           DESCRIPTION "Dyn.-DNS-table"
           ::= {  setDnsm 8 }

setDnsmDynCols OBJECT-TYPE
           SYNTAX SetDnsmDynRows
           ACCESS not-accessible
           STATUS mandatory
           DESCRIPTION "entry in table"
           INDEX { setDnsmDynHos }
           ::= {  setDnsmDyn 1 }

SetDnsmDynRows ::= SEQUENCE {
           setDnsmDynHos DisplayString,
           setDnsmDynIpa IpAddress,
           setDnsmDynTim INTEGER
          }

setDnsmDynHos OBJECT-TYPE
              SYNTAX DisplayString
              ACCESS read-only
              STATUS mandatory
              DESCRIPTION "Host-name"
              ::= {  setDnsmDynCols 1 }

setDnsmDynIpa OBJECT-TYPE
              SYNTAX IpAddress
              ACCESS read-only
              STATUS mandatory
              DESCRIPTION "IP-Address"
              ::= {  setDnsmDynCols 2 }

setDnsmDynTim OBJECT-TYPE
              SYNTAX INTEGER
              ACCESS read-only
              STATUS mandatory
              DESCRIPTION "Timeout"
              ::= {  setDnsmDynCols 3 }

setDnsmLea OBJECT-TYPE
           SYNTAX INTEGER
           ACCESS read-write
           STATUS mandatory
           DESCRIPTION "Leasetime"
           ::= {  setDnsm 7 }

setHttp OBJECT IDENTIFIER ::= { set 21}
setHttpDoc OBJECT-TYPE
           SYNTAX DisplayString (SIZE(0..99))
           ACCESS read-write
           STATUS mandatory
           DESCRIPTION "document-root"
           ::= {  setHttp 1 }

setSysl OBJECT IDENTIFIER ::= { set 22}
setSyslOpe OBJECT-TYPE
           SYNTAX INTEGER {
             on(1),
             off(0)
           }
           ACCESS read-write
           STATUS mandatory
           DESCRIPTION "Operating"
           ::= {  setSysl 1 }

setSyslTab OBJECT-TYPE
           SYNTAX SEQUENCE OF SetSyslTabRows
           ACCESS not-accessible
           STATUS mandatory
           DESCRIPTION "Table-SYSLOG"
           ::= {  setSysl 2 }

setSyslTabCols OBJECT-TYPE
           SYNTAX SetSyslTabRows
           ACCESS not-accessible
           STATUS mandatory
           DESCRIPTION "entry in table"
           INDEX { setSyslTabIdx }
           ::= {  setSyslTab 1 }

SetSyslTabRows ::= SEQUENCE {
           setSyslTabIdx DisplayString,
           setSyslTabIpa IpAddress,
           setSyslTabSou INTEGER,
           setSyslTabLev INTEGER
          }

setSyslTabIdx OBJECT-TYPE
              SYNTAX DisplayString
              ACCESS read-write
              STATUS mandatory
              DESCRIPTION "Idx."
              ::= {  setSyslTabCols 1 }

setSyslTabIpa OBJECT-TYPE
              SYNTAX IpAddress
              ACCESS read-write
              STATUS mandatory
              DESCRIPTION "IP-Address"
              ::= {  setSyslTabCols 2 }

setSyslTabSou OBJECT-TYPE
              SYNTAX INTEGER
              ACCESS read-write
              STATUS mandatory
              DESCRIPTION "Source"
              ::= {  setSyslTabCols 3 }

setSyslTabLev OBJECT-TYPE
              SYNTAX INTEGER
              ACCESS read-write
              STATUS mandatory
              DESCRIPTION "Level"
              ::= {  setSyslTabCols 4 }

setSyslFac OBJECT-TYPE
           SYNTAX SEQUENCE OF SetSyslFacRows
           ACCESS not-accessible
           STATUS mandatory
           DESCRIPTION "Facility-mapper"
           ::= {  setSysl 3 }

setSyslFacCols OBJECT-TYPE
           SYNTAX SetSyslFacRows
           ACCESS not-accessible
           STATUS mandatory
           DESCRIPTION "entry in table"
           INDEX { setSyslFacSou }
           ::= {  setSyslFac 1 }

SetSyslFacRows ::= SEQUENCE {
           setSyslFacSou INTEGER,
           setSyslFacFac INTEGER
          }

setSyslFacSou OBJECT-TYPE
              SYNTAX INTEGER {
                system(1),
                login(2),
                systemtime(4),
                console-login(8),
                connections(16),
                accounting(32),
                administration(64),
                router(128)
              }
              ACCESS read-only
              STATUS mandatory
              DESCRIPTION "Source"
              ::= {  setSyslFacCols 1 }

setSyslFacFac OBJECT-TYPE
              SYNTAX INTEGER {
                kern(0),
                user(1),
                mail(2),
                daemon(3),
                auth(4),
                syslog(5),
                lpr(6),
                news(7),
                uucp(8),
                cron(9),
                authpriv(10),
                local0(16),
                local1(17),
                local2(18),
                local3(19),
                local4(20),
                local5(21),
                local6(22),
                local7(23)
              }
              ACCESS read-write
              STATUS mandatory
              DESCRIPTION "Facility"
              ::= {  setSyslFacCols 2 }

setSyslPor OBJECT-TYPE
           SYNTAX INTEGER
           ACCESS read-write
           STATUS mandatory
           DESCRIPTION "Port"
           ::= {  setSysl 4 }

setNetb OBJECT IDENTIFIER ::= { set 16}
setNetbOpe OBJECT-TYPE
           SYNTAX INTEGER {
             on(1),
             off(0)
           }
           ACCESS read-write
           STATUS mandatory
           DESCRIPTION "Operating"
           ::= {  setNetb 1 }

setNetbSco OBJECT-TYPE
           SYNTAX DisplayString (SIZE(0..64))
           ACCESS read-write
           STATUS mandatory
           DESCRIPTION "Scope-ID"
           ::= {  setNetb 2 }

setNetbNtd OBJECT-TYPE
           SYNTAX DisplayString (SIZE(0..15))
           ACCESS read-write
           STATUS mandatory
           DESCRIPTION "NT-Domain"
           ::= {  setNetb 3 }

setNetbRem OBJECT-TYPE
           SYNTAX SEQUENCE OF SetNetbRemRows
           ACCESS not-accessible
           STATUS mandatory
           DESCRIPTION "Remote-table"
           ::= {  setNetb 4 }

setNetbRemCols OBJECT-TYPE
           SYNTAX SetNetbRemRows
           ACCESS not-accessible
           STATUS mandatory
           DESCRIPTION "entry in table"
           INDEX { setNetbRemNam }
           ::= {  setNetbRem 1 }

SetNetbRemRows ::= SEQUENCE {
           setNetbRemNam DisplayString,
           setNetbRemTyp INTEGER
          }

setNetbRemNam OBJECT-TYPE
              SYNTAX DisplayString
              ACCESS read-write
              STATUS mandatory
              DESCRIPTION "Name"
              ::= {  setNetbRemCols 1 }

setNetbRemTyp OBJECT-TYPE
              SYNTAX INTEGER {
                workstation(1),
                router(0)
              }
              ACCESS read-write
              STATUS mandatory
              DESCRIPTION "Type"
              ::= {  setNetbRemCols 3 }

setNetbGro OBJECT-TYPE
           SYNTAX SEQUENCE OF SetNetbGroRows
           ACCESS not-accessible
           STATUS mandatory
           DESCRIPTION "Group-list"
           ::= {  setNetb 5 }

setNetbGroCols OBJECT-TYPE
           SYNTAX SetNetbGroRows
           ACCESS not-accessible
           STATUS mandatory
           DESCRIPTION "entry in table"
           INDEX { setNetbGroGro }
           ::= {  setNetbGro 1 }

SetNetbGroRows ::= SEQUENCE {
           setNetbGroGro DisplayString,
           setNetbGroTyp DisplayString,
           setNetbGroIpa IpAddress,
           setNetbGroRem DisplayString,
           setNetbGroTim INTEGER,
           setNetbGroFla DisplayString
          }

setNetbGroGro OBJECT-TYPE
              SYNTAX DisplayString
              ACCESS read-only
              STATUS mandatory
              DESCRIPTION "Group/Domain"
              ::= {  setNetbGroCols 1 }

setNetbGroTyp OBJECT-TYPE
              SYNTAX DisplayString
              ACCESS read-only
              STATUS mandatory
              DESCRIPTION "Type"
              ::= {  setNetbGroCols 2 }

setNetbGroIpa OBJECT-TYPE
              SYNTAX IpAddress
              ACCESS read-only
              STATUS mandatory
              DESCRIPTION "IP-address"
              ::= {  setNetbGroCols 3 }

setNetbGroRem OBJECT-TYPE
              SYNTAX DisplayString
              ACCESS read-only
              STATUS mandatory
              DESCRIPTION "Remote-station"
              ::= {  setNetbGroCols 4 }

setNetbGroTim OBJECT-TYPE
              SYNTAX INTEGER
              ACCESS read-only
              STATUS mandatory
              DESCRIPTION "Timeout"
              ::= {  setNetbGroCols 5 }

setNetbGroFla OBJECT-TYPE
              SYNTAX DisplayString
              ACCESS read-only
              STATUS mandatory
              DESCRIPTION "Flags"
              ::= {  setNetbGroCols 6 }

setNetbHos OBJECT-TYPE
           SYNTAX SEQUENCE OF SetNetbHosRows
           ACCESS not-accessible
           STATUS mandatory
           DESCRIPTION "Host-list"
           ::= {  setNetb 6 }

setNetbHosCols OBJECT-TYPE
           SYNTAX SetNetbHosRows
           ACCESS not-accessible
           STATUS mandatory
           DESCRIPTION "entry in table"
           INDEX { setNetbHosNam }
           ::= {  setNetbHos 1 }

SetNetbHosRows ::= SEQUENCE {
           setNetbHosNam DisplayString,
           setNetbHosTyp DisplayString,
           setNetbHosIpa IpAddress,
           setNetbHosRem DisplayString,
           setNetbHosTim INTEGER,
           setNetbHosFla DisplayString
          }

setNetbHosNam OBJECT-TYPE
              SYNTAX DisplayString
              ACCESS read-only
              STATUS mandatory
              DESCRIPTION "Name"
              ::= {  setNetbHosCols 1 }

setNetbHosTyp OBJECT-TYPE
              SYNTAX DisplayString
              ACCESS read-only
              STATUS mandatory
              DESCRIPTION "Type"
              ::= {  setNetbHosCols 2 }

setNetbHosIpa OBJECT-TYPE
              SYNTAX IpAddress
              ACCESS read-only
              STATUS mandatory
              DESCRIPTION "IP-address"
              ::= {  setNetbHosCols 3 }

setNetbHosRem OBJECT-TYPE
              SYNTAX DisplayString
              ACCESS read-only
              STATUS mandatory
              DESCRIPTION "Remote-station"
              ::= {  setNetbHosCols 4 }

setNetbHosTim OBJECT-TYPE
              SYNTAX INTEGER
              ACCESS read-only
              STATUS mandatory
              DESCRIPTION "Timeout"
              ::= {  setNetbHosCols 5 }

setNetbHosFla OBJECT-TYPE
              SYNTAX DisplayString
              ACCESS read-only
              STATUS mandatory
              DESCRIPTION "Flags"
              ::= {  setNetbHosCols 6 }

setNetbSer OBJECT-TYPE
           SYNTAX SEQUENCE OF SetNetbSerRows
           ACCESS not-accessible
           STATUS mandatory
           DESCRIPTION "Server-list"
           ::= {  setNetb 7 }

setNetbSerCols OBJECT-TYPE
           SYNTAX SetNetbSerRows
           ACCESS not-accessible
           STATUS mandatory
           DESCRIPTION "entry in table"
           INDEX { setNetbSerHos }
           ::= {  setNetbSer 1 }

SetNetbSerRows ::= SEQUENCE {
           setNetbSerHos DisplayString,
           setNetbSerGro DisplayString,
           setNetbSerUpd DisplayString,
           setNetbSerIpa DisplayString,
           setNetbSerOsv DisplayString,
           setNetbSerSmb DisplayString,
           setNetbSerSer DisplayString,
           setNetbSerRem DisplayString,
           setNetbSerTim INTEGER,
           setNetbSerFla DisplayString
          }

setNetbSerHos OBJECT-TYPE
              SYNTAX DisplayString
              ACCESS read-only
              STATUS mandatory
              DESCRIPTION "Host"
              ::= {  setNetbSerCols 1 }

setNetbSerGro OBJECT-TYPE
              SYNTAX DisplayString
              ACCESS read-only
              STATUS mandatory
              DESCRIPTION "Group/Domain"
              ::= {  setNetbSerCols 2 }

setNetbSerUpd OBJECT-TYPE
              SYNTAX DisplayString
              ACCESS read-only
              STATUS mandatory
              DESCRIPTION "UPD"
              ::= {  setNetbSerCols 3 }

setNetbSerIpa OBJECT-TYPE
              SYNTAX DisplayString
              ACCESS read-only
              STATUS mandatory
              DESCRIPTION "IP-address"
              ::= {  setNetbSerCols 4 }

setNetbSerOsv OBJECT-TYPE
              SYNTAX DisplayString
              ACCESS read-only
              STATUS mandatory
              DESCRIPTION "OS-Ver."
              ::= {  setNetbSerCols 5 }

setNetbSerSmb OBJECT-TYPE
              SYNTAX DisplayString
              ACCESS read-only
              STATUS mandatory
              DESCRIPTION "SMB-Ver."
              ::= {  setNetbSerCols 6 }

setNetbSerSer OBJECT-TYPE
              SYNTAX DisplayString
              ACCESS read-only
              STATUS mandatory
              DESCRIPTION "Server-Typ"
              ::= {  setNetbSerCols 7 }

setNetbSerRem OBJECT-TYPE
              SYNTAX DisplayString
              ACCESS read-only
              STATUS mandatory
              DESCRIPTION "Remote-station"
              ::= {  setNetbSerCols 8 }

setNetbSerTim OBJECT-TYPE
              SYNTAX INTEGER
              ACCESS read-only
              STATUS mandatory
              DESCRIPTION "Timeout"
              ::= {  setNetbSerCols 9 }

setNetbSerFla OBJECT-TYPE
              SYNTAX DisplayString
              ACCESS read-only
              STATUS mandatory
              DESCRIPTION "Flags"
              ::= {  setNetbSerCols 10 }

setNetbWat OBJECT-TYPE
           SYNTAX INTEGER {
             spoof(1),
             route(0)
           }
           ACCESS read-write
           STATUS mandatory
           DESCRIPTION "Watchdogs"
           ::= {  setNetb 8 }

setNetbUpd OBJECT-TYPE
           SYNTAX INTEGER {
             pback(0),
             trig(1),
             time(2)
           }
           ACCESS read-write
           STATUS mandatory
           DESCRIPTION "Update"
           ::= {  setNetb 9 }

setNetbWan OBJECT-TYPE
           SYNTAX INTEGER
           ACCESS read-write
           STATUS mandatory
           DESCRIPTION "WAN-Update-Min."
           ::= {  setNetb 10 }

setConf OBJECT IDENTIFIER ::= { set 11}
setConfLanc OBJECT-TYPE
            SYNTAX INTEGER {
              on(1),
              read(4),
              off(0)
            }
            ACCESS read-write
            STATUS mandatory
            DESCRIPTION "LAN-config"
            ::= {  setConf 1 }

setConfWanc OBJECT-TYPE
            SYNTAX INTEGER {
              on(2),
              read(8),
              off(0)
            }
            ACCESS read-write
            STATUS mandatory
            DESCRIPTION "WAN-config"
            ::= {  setConf 2 }

setConfPass OBJECT-TYPE
            SYNTAX INTEGER {
              on(1),
              off(0)
            }
            ACCESS read-write
            STATUS mandatory
            DESCRIPTION "Password-required-for-SNMP-read-access"
            ::= {  setConf 3 }

setConfMaxi OBJECT-TYPE
            SYNTAX INTEGER
            ACCESS read-write
            STATUS mandatory
            DESCRIPTION "Maximum-connections"
            ::= {  setConf 4 }

setConfConf OBJECT-TYPE
            SYNTAX INTEGER
            ACCESS read-write
            STATUS mandatory
            DESCRIPTION "Config-aging-minute(s)"
            ::= {  setConf 5 }

setConfLogi OBJECT-TYPE
            SYNTAX INTEGER
            ACCESS read-write
            STATUS mandatory
            DESCRIPTION "Login-errors"
            ::= {  setConf 7 }

setConfLock OBJECT-TYPE
            SYNTAX INTEGER
            ACCESS read-write
            STATUS mandatory
            DESCRIPTION "Lock-minutes"
            ::= {  setConf 8 }

setConfFarc OBJECT-TYPE
            SYNTAX DisplayString (SIZE(0..31))
            ACCESS read-write
            STATUS mandatory
            DESCRIPTION "Farconfig-(EAZ-MSN)"
            ::= {  setConf 9 }

setConfLang OBJECT-TYPE
            SYNTAX INTEGER {
              english(1),
              deutsch(2)
            }
            ACCESS read-write
            STATUS mandatory
            DESCRIPTION "Language"
            ::= {  setConf 6 }

setAbmo OBJECT IDENTIFIER ::= { set 12}
setAbmoPor OBJECT-TYPE
           SYNTAX SEQUENCE OF SetAbmoPorRows
           ACCESS not-accessible
           STATUS mandatory
           DESCRIPTION "Port-list"
           ::= {  setAbmo 1 }

setAbmoPorCols OBJECT-TYPE
           SYNTAX SetAbmoPorRows
           ACCESS not-accessible
           STATUS mandatory
           DESCRIPTION "entry in table"
           INDEX { setAbmoPorPort }
           ::= {  setAbmoPor 1 }

SetAbmoPorRows ::= SEQUENCE {
           setAbmoPorPort INTEGER,
           setAbmoPorDevice INTEGER,
           setAbmoPorEazmsns DisplayString,
           setAbmoPorCapab INTEGER,
           setAbmoPorMode INTEGER,
           setAbmoPorClip INTEGER,
           setAbmoPorAutodialf INTEGER,
           setAbmoPorAutodialn DisplayString
          }

setAbmoPorPort OBJECT-TYPE
                    SYNTAX INTEGER {
                      ab-1(1),
                      ab-2(2),
                      ab-3(3),
                      ab-4(4)
                    }
                    ACCESS read-only
                    STATUS mandatory
                    DESCRIPTION "Port"
                    ::= {  setAbmoPorCols 1 }

setAbmoPorDevice OBJECT-TYPE
                    SYNTAX INTEGER {
                      none(0),
                      phone(1),
                      fax(2),
                      modem(3),
                      answ-mach(4),
                      combi(5)
                    }
                    ACCESS read-write
                    STATUS mandatory
                    DESCRIPTION "Device"
                    ::= {  setAbmoPorCols 10 }

setAbmoPorEazmsns OBJECT-TYPE
                    SYNTAX DisplayString
                    ACCESS read-write
                    STATUS mandatory
                    DESCRIPTION "EAZ/MSN(s)"
                    ::= {  setAbmoPorCols 3 }

setAbmoPorCapab OBJECT-TYPE
                    SYNTAX INTEGER {
                      speech(1),
                      a-3-1khz(8),
                      modem(2),
                      fax-g2-3(4)
                    }
                    ACCESS read-write
                    STATUS mandatory
                    DESCRIPTION "Capab."
                    ::= {  setAbmoPorCols 5 }

setAbmoPorMode OBJECT-TYPE
                    SYNTAX INTEGER
                    ACCESS read-write
                    STATUS mandatory
                    DESCRIPTION "Mode"
                    ::= {  setAbmoPorCols 6 }

setAbmoPorClip OBJECT-TYPE
                    SYNTAX INTEGER {
                      yes(1),
                      no(0)
                    }
                    ACCESS read-write
                    STATUS mandatory
                    DESCRIPTION "CLIP"
                    ::= {  setAbmoPorCols 7 }

setAbmoPorAutodialf OBJECT-TYPE
                    SYNTAX INTEGER
                    ACCESS read-write
                    STATUS mandatory
                    DESCRIPTION "Auto-dial-flag"
                    ::= {  setAbmoPorCols 8 }

setAbmoPorAutodialn OBJECT-TYPE
                    SYNTAX DisplayString
                    ACCESS read-write
                    STATUS mandatory
                    DESCRIPTION "Auto-dial-number"
                    ::= {  setAbmoPorCols 9 }

setAbmoPub OBJECT-TYPE
           SYNTAX SEQUENCE OF SetAbmoPubRows
           ACCESS not-accessible
           STATUS mandatory
           DESCRIPTION "Public-exchange-list"
           ::= {  setAbmo 6 }

setAbmoPubCols OBJECT-TYPE
           SYNTAX SetAbmoPubRows
           ACCESS not-accessible
           STATUS mandatory
           DESCRIPTION "entry in table"
           INDEX { setAbmoPubPor }
           ::= {  setAbmoPub 1 }

SetAbmoPubRows ::= SEQUENCE {
           setAbmoPubPor INTEGER,
           setAbmoPubOff INTEGER,
           setAbmoPubFla INTEGER,
           setAbmoPubExc DisplayString
          }

setAbmoPubPor OBJECT-TYPE
              SYNTAX INTEGER {
                ab-1(1),
                ab-2(2),
                ab-3(3),
                ab-4(4)
              }
              ACCESS read-only
              STATUS mandatory
              DESCRIPTION "Port"
              ::= {  setAbmoPubCols 1 }

setAbmoPubOff OBJECT-TYPE
              SYNTAX INTEGER {
                internal(0),
                private(1),
                public(2)
              }
              ACCESS read-write
              STATUS mandatory
              DESCRIPTION "Offhook-line"
              ::= {  setAbmoPubCols 4 }

setAbmoPubFla OBJECT-TYPE
              SYNTAX INTEGER {
                internal(0),
                private(1),
                public(2)
              }
              ACCESS read-write
              STATUS mandatory
              DESCRIPTION "Flash-line"
              ::= {  setAbmoPubCols 5 }

setAbmoPubExc OBJECT-TYPE
              SYNTAX DisplayString
              ACCESS read-write
              STATUS mandatory
              DESCRIPTION "exchange-code"
              ::= {  setAbmoPubCols 6 }

setAbmoCla OBJECT-TYPE
           SYNTAX SEQUENCE OF SetAbmoClaRows
           ACCESS not-accessible
           STATUS mandatory
           DESCRIPTION "Class-of-service-list"
           ::= {  setAbmo 7 }

setAbmoClaCols OBJECT-TYPE
           SYNTAX SetAbmoClaRows
           ACCESS not-accessible
           STATUS mandatory
           DESCRIPTION "entry in table"
           INDEX { setAbmoClaPort }
           ::= {  setAbmoCla 1 }

SetAbmoClaRows ::= SEQUENCE {
           setAbmoClaPort INTEGER,
           setAbmoClaClassofservice INTEGER,
           setAbmoClaBlockednumber1 DisplayString,
           setAbmoClaBlockednumber2 DisplayString
          }

setAbmoClaPort OBJECT-TYPE
                         SYNTAX INTEGER {
                           ab-1(1),
                           ab-2(2),
                           ab-3(3),
                           ab-4(4)
                         }
                         ACCESS read-only
                         STATUS mandatory
                         DESCRIPTION "Port"
                         ::= {  setAbmoClaCols 1 }

setAbmoClaClassofservice OBJECT-TYPE
                         SYNTAX INTEGER
                         ACCESS read-write
                         STATUS mandatory
                         DESCRIPTION "Class-of-service"
                         ::= {  setAbmoClaCols 2 }

setAbmoClaBlockednumber1 OBJECT-TYPE
                         SYNTAX DisplayString
                         ACCESS read-write
                         STATUS mandatory
                         DESCRIPTION "Blocked-number-1"
                         ::= {  setAbmoClaCols 3 }

setAbmoClaBlockednumber2 OBJECT-TYPE
                         SYNTAX DisplayString
                         ACCESS read-write
                         STATUS mandatory
                         DESCRIPTION "Blocked-number-2"
                         ::= {  setAbmoClaCols 4 }

setAbmoPri OBJECT-TYPE
           SYNTAX SEQUENCE OF SetAbmoPriRows
           ACCESS not-accessible
           STATUS mandatory
           DESCRIPTION "Priority-list"
           ::= {  setAbmo 8 }

setAbmoPriCols OBJECT-TYPE
           SYNTAX SetAbmoPriRows
           ACCESS not-accessible
           STATUS mandatory
           DESCRIPTION "entry in table"
           INDEX { setAbmoPriPor }
           ::= {  setAbmoPri 1 }

SetAbmoPriRows ::= SEQUENCE {
           setAbmoPriPor INTEGER,
           setAbmoPriPri INTEGER
          }

setAbmoPriPor OBJECT-TYPE
              SYNTAX INTEGER {
                ab-1(1),
                ab-2(2),
                ab-3(3),
                ab-4(4)
              }
              ACCESS read-only
              STATUS mandatory
              DESCRIPTION "Port"
              ::= {  setAbmoPriCols 1 }

setAbmoPriPri OBJECT-TYPE
              SYNTAX INTEGER {
                p1(0),
                p2(1),
                p3(2)
              }
              ACCESS read-write
              STATUS mandatory
              DESCRIPTION "Prio-out"
              ::= {  setAbmoPriCols 3 }

setAbmoRin OBJECT-TYPE
           SYNTAX INTEGER {
             single(1),
             paired(2),
             all(4)
           }
           ACCESS read-write
           STATUS mandatory
           DESCRIPTION "Ringinq-sequence"
           ::= {  setAbmo 3 }

setAbmoCou OBJECT-TYPE
           SYNTAX INTEGER {
             austria(43),
             belgium(32),
             switzerland(41),
             cyprus(357),
             germany(49),
             denmark(45),
             spain(34),
             france(33),
             great-britain(44),
             greece(30),
             italy(39),
             ireland(353),
             japan(81),
             luxembourg(352),
             norway(47),
             netherlands(31),
             portugal(351),
             sweden(46),
             finland(358),
             turkey(90),
             united-states-of-america(1)
           }
           ACCESS read-write
           STATUS mandatory
           DESCRIPTION "Country"
           ::= {  setAbmo 5 }

setLanc OBJECT IDENTIFIER ::= { set 13}
setLancAcces OBJECT-TYPE
             SYNTAX SEQUENCE OF SetLancAccesRows
             ACCESS not-accessible
             STATUS mandatory
             DESCRIPTION "Access-list"
             ::= {  setLanc 1 }

setLancAccesCols OBJECT-TYPE
             SYNTAX SetLancAccesRows
             ACCESS not-accessible
             STATUS mandatory
             DESCRIPTION "entry in table"
             INDEX { setLancAccesIpa }
             ::= {  setLancAcces 1 }

SetLancAccesRows ::= SEQUENCE {
             setLancAccesIpa IpAddress,
             setLancAccesIpn IpAddress
            }

setLancAccesIpa OBJECT-TYPE
                SYNTAX IpAddress
                ACCESS read-write
                STATUS mandatory
                DESCRIPTION "IP-address"
                ::= {  setLancAccesCols 1 }

setLancAccesIpn OBJECT-TYPE
                SYNTAX IpAddress
                ACCESS read-write
                STATUS mandatory
                DESCRIPTION "IP-netmask"
                ::= {  setLancAccesCols 2 }

setLancUdppo OBJECT-TYPE
             SYNTAX INTEGER
             ACCESS read-write
             STATUS mandatory
             DESCRIPTION "UDP-port"
             ::= {  setLanc 3 }

setLancInter OBJECT-TYPE
             SYNTAX SEQUENCE OF SetLancInterRows
             ACCESS not-accessible
             STATUS mandatory
             DESCRIPTION "Interface-list"
             ::= {  setLanc 6 }

setLancInterCols OBJECT-TYPE
             SYNTAX SetLancInterRows
             ACCESS not-accessible
             STATUS mandatory
             DESCRIPTION "entry in table"
             INDEX { setLancInterIfc }
             ::= {  setLancInter 1 }

SetLancInterRows ::= SEQUENCE {
             setLancInterIfc INTEGER,
             setLancInterOpe INTEGER,
             setLancInterEaz DisplayString,
             setLancInterFor INTEGER
            }

setLancInterIfc OBJECT-TYPE
                SYNTAX INTEGER {
                  s0-1(1),
                  s0-2(2),
                  s0-3(3),
                  s0-4(4)
                }
                ACCESS read-only
                STATUS mandatory
                DESCRIPTION "Ifc"
                ::= {  setLancInterCols 1 }

setLancInterOpe OBJECT-TYPE
                SYNTAX INTEGER {
                  off(0),
                  on(1),
                  dial-only(2)
                }
                ACCESS read-write
                STATUS mandatory
                DESCRIPTION "Operating"
                ::= {  setLancInterCols 2 }

setLancInterEaz OBJECT-TYPE
                SYNTAX DisplayString
                ACCESS read-write
                STATUS mandatory
                DESCRIPTION "EAZ-MSN(s)"
                ::= {  setLancInterCols 3 }

setLancInterFor OBJECT-TYPE
                SYNTAX INTEGER {
                  yes(1),
                  no(0)
                }
                ACCESS read-write
                STATUS mandatory
                DESCRIPTION "Force-out-MSN"
                ::= {  setLancInterCols 5 }

setLancPrior OBJECT-TYPE
             SYNTAX SEQUENCE OF SetLancPriorRows
             ACCESS not-accessible
             STATUS mandatory
             DESCRIPTION "Priority-list"
             ::= {  setLanc 7 }

setLancPriorCols OBJECT-TYPE
             SYNTAX SetLancPriorRows
             ACCESS not-accessible
             STATUS mandatory
             DESCRIPTION "entry in table"
             INDEX { setLancPriorIfc }
             ::= {  setLancPrior 1 }

SetLancPriorRows ::= SEQUENCE {
             setLancPriorIfc INTEGER,
             setLancPriorPri INTEGER
            }

setLancPriorIfc OBJECT-TYPE
                SYNTAX INTEGER {
                  s0-1(1),
                  s0-2(2),
                  s0-3(3),
                  s0-4(4)
                }
                ACCESS read-only
                STATUS mandatory
                DESCRIPTION "Ifc"
                ::= {  setLancPriorCols 1 }

setLancPriorPri OBJECT-TYPE
                SYNTAX INTEGER {
                  p1(0),
                  p2(1),
                  p3(2)
                }
                ACCESS read-write
                STATUS mandatory
                DESCRIPTION "Prio-out"
                ::= {  setLancPriorCols 2 }

setLancOpera OBJECT-TYPE
             SYNTAX INTEGER {
               off(0),
               on(1),
               dial-only(2)
             }
             ACCESS read-write
             STATUS mandatory
             DESCRIPTION "Operating"
             ::= {  setLanc 2 }

setLancEazms OBJECT-TYPE
             SYNTAX DisplayString (SIZE(0..31))
             ACCESS read-write
             STATUS mandatory
             DESCRIPTION "EAZ-MSN(s)"
             ::= {  setLanc 4 }

setLancPrioo OBJECT-TYPE
             SYNTAX INTEGER {
               p1(0),
               p2(1),
               p3(2)
             }
             ACCESS read-write
             STATUS mandatory
             DESCRIPTION "Prio-out"
             ::= {  setLanc 5 }

setLcrm OBJECT IDENTIFIER ::= { set 15}
setLcrmRou OBJECT-TYPE
           SYNTAX INTEGER {
             on(1),
             off(0)
           }
           ACCESS read-write
           STATUS mandatory
           DESCRIPTION "Router-usage"
           ::= {  setLcrm 1 }

setLcrmLan OBJECT-TYPE
           SYNTAX INTEGER {
             on(1),
             off(0)
           }
           ACCESS read-write
           STATUS mandatory
           DESCRIPTION "Lancapi-usage"
           ::= {  setLcrm 2 }

setLcrmAbp OBJECT-TYPE
           SYNTAX INTEGER {
             on(1),
             off(0)
           }
           ACCESS read-write
           STATUS mandatory
           DESCRIPTION "ab-port-usage"
           ::= {  setLcrm 3 }

setLcrmTim OBJECT-TYPE
           SYNTAX SEQUENCE OF SetLcrmTimRows
           ACCESS not-accessible
           STATUS mandatory
           DESCRIPTION "Timetable"
           ::= {  setLcrm 4 }

setLcrmTimCols OBJECT-TYPE
           SYNTAX SetLcrmTimRows
           ACCESS not-accessible
           STATUS mandatory
           DESCRIPTION "entry in table"
           INDEX { setLcrmTimInd }
           ::= {  setLcrmTim 1 }

SetLcrmTimRows ::= SEQUENCE {
           setLcrmTimInd INTEGER,
           setLcrmTimPre DisplayString,
           setLcrmTimDay INTEGER,
           setLcrmTimSta DisplayString,
           setLcrmTimSto DisplayString,
           setLcrmTimNum DisplayString,
           setLcrmTimFal INTEGER
          }

setLcrmTimInd OBJECT-TYPE
              SYNTAX INTEGER
              ACCESS read-write
              STATUS mandatory
              DESCRIPTION "Index"
              ::= {  setLcrmTimCols 1 }

setLcrmTimPre OBJECT-TYPE
              SYNTAX DisplayString
              ACCESS read-write
              STATUS mandatory
              DESCRIPTION "Prefix"
              ::= {  setLcrmTimCols 2 }

setLcrmTimDay OBJECT-TYPE
              SYNTAX INTEGER
              ACCESS read-write
              STATUS mandatory
              DESCRIPTION "Days"
              ::= {  setLcrmTimCols 3 }

setLcrmTimSta OBJECT-TYPE
              SYNTAX DisplayString
              ACCESS read-write
              STATUS mandatory
              DESCRIPTION "Start"
              ::= {  setLcrmTimCols 4 }

setLcrmTimSto OBJECT-TYPE
              SYNTAX DisplayString
              ACCESS read-write
              STATUS mandatory
              DESCRIPTION "Stop"
              ::= {  setLcrmTimCols 5 }

setLcrmTimNum OBJECT-TYPE
              SYNTAX DisplayString
              ACCESS read-write
              STATUS mandatory
              DESCRIPTION "number-list"
              ::= {  setLcrmTimCols 6 }

setLcrmTimFal OBJECT-TYPE
              SYNTAX INTEGER {
                on(1),
                off(0)
              }
              ACCESS read-write
              STATUS mandatory
              DESCRIPTION "Fallback"
              ::= {  setLcrmTimCols 7 }

setLcrmCel OBJECT-TYPE
           SYNTAX SEQUENCE OF SetLcrmCelRows
           ACCESS not-accessible
           STATUS mandatory
           DESCRIPTION "Celebration-day-table"
           ::= {  setLcrm 5 }

setLcrmCelCols OBJECT-TYPE
           SYNTAX SetLcrmCelRows
           ACCESS not-accessible
           STATUS mandatory
           DESCRIPTION "entry in table"
           INDEX { setLcrmCelInd }
           ::= {  setLcrmCel 1 }

SetLcrmCelRows ::= SEQUENCE {
           setLcrmCelInd INTEGER,
           setLcrmCelDat DisplayString
          }

setLcrmCelInd OBJECT-TYPE
              SYNTAX INTEGER
              ACCESS read-only
              STATUS mandatory
              DESCRIPTION "Index"
              ::= {  setLcrmCelCols 1 }

setLcrmCelDat OBJECT-TYPE
              SYNTAX DisplayString
              ACCESS read-write
              STATUS mandatory
              DESCRIPTION "Date"
              ::= {  setLcrmCelCols 2 }

setTime OBJECT IDENTIFIER ::= { set 14}
setTimeOpe OBJECT-TYPE
           SYNTAX INTEGER {
             on(1),
             off(0)
           }
           ACCESS read-write
           STATUS mandatory
           DESCRIPTION "Operating"
           ::= {  setTime 1 }

setTimeCur OBJECT-TYPE
           SYNTAX DisplayString
           ACCESS read-only
           STATUS mandatory
           DESCRIPTION "Current-time"
           ::= {  setTime 2 }

setTimeTim OBJECT-TYPE
           SYNTAX DisplayString (SIZE(0..39))
           ACCESS read-write
           STATUS mandatory
           DESCRIPTION "Time-call-number"
           ::= {  setTime 3 }

setTimeCal OBJECT-TYPE
           SYNTAX INTEGER
           ACCESS read-write
           STATUS mandatory
           DESCRIPTION "Call-attempts"
           ::= {  setTime 5 }

setTimeUtc OBJECT-TYPE
           SYNTAX INTEGER
           ACCESS read-only
           STATUS mandatory
           DESCRIPTION "UTC-in-secs"
           ::= {  setTime 7 }

firVer OBJECT-TYPE
       SYNTAX SEQUENCE OF FirVerRows
       ACCESS not-accessible
       STATUS mandatory
       DESCRIPTION "Version-table"
       ::= {  fir 1 }

firVerCols OBJECT-TYPE
       SYNTAX FirVerRows
       ACCESS not-accessible
       STATUS mandatory
       DESCRIPTION "entry in table"
       INDEX { firVerIfc }
       ::= {  firVer 1 }

FirVerRows ::= SEQUENCE {
       firVerIfc INTEGER,
       firVerMod DisplayString,
       firVerVer DisplayString,
       firVerSer DisplayString
      }

firVerIfc OBJECT-TYPE
          SYNTAX INTEGER {
            ifc(1)
          }
          ACCESS read-only
          STATUS mandatory
          DESCRIPTION "Ifc"
          ::= {  firVerCols 1 }

firVerMod OBJECT-TYPE
          SYNTAX DisplayString
          ACCESS read-only
          STATUS mandatory
          DESCRIPTION "Module"
          ::= {  firVerCols 2 }

firVerVer OBJECT-TYPE
          SYNTAX DisplayString
          ACCESS read-only
          STATUS mandatory
          DESCRIPTION "Version"
          ::= {  firVerCols 3 }

firVerSer OBJECT-TYPE
          SYNTAX DisplayString
          ACCESS read-only
          STATUS mandatory
          DESCRIPTION "Serial-number"
          ::= {  firVerCols 4 }

firTab OBJECT-TYPE
       SYNTAX SEQUENCE OF FirTabRows
       ACCESS not-accessible
       STATUS mandatory
       DESCRIPTION "Table-firmsafe"
       ::= {  fir 2 }

firTabCols OBJECT-TYPE
       SYNTAX FirTabRows
       ACCESS not-accessible
       STATUS mandatory
       DESCRIPTION "entry in table"
       INDEX { firTabPos }
       ::= {  firTab 1 }

FirTabRows ::= SEQUENCE {
       firTabPos INTEGER,
       firTabSta INTEGER,
       firTabVer DisplayString,
       firTabDat DisplayString,
       firTabSiz INTEGER,
       firTabInd INTEGER
      }

firTabPos OBJECT-TYPE
          SYNTAX INTEGER
          ACCESS read-only
          STATUS mandatory
          DESCRIPTION "Position"
          ::= {  firTabCols 1 }

firTabSta OBJECT-TYPE
          SYNTAX INTEGER {
            active(1),
            inactive(0),
            minimal-active(5),
            minimal-inactive(4)
          }
          ACCESS read-write
          STATUS mandatory
          DESCRIPTION "Status"
          ::= {  firTabCols 2 }

firTabVer OBJECT-TYPE
          SYNTAX DisplayString
          ACCESS read-only
          STATUS mandatory
          DESCRIPTION "Version"
          ::= {  firTabCols 3 }

firTabDat OBJECT-TYPE
          SYNTAX DisplayString
          ACCESS read-only
          STATUS mandatory
          DESCRIPTION "Date"
          ::= {  firTabCols 4 }

firTabSiz OBJECT-TYPE
          SYNTAX INTEGER
          ACCESS read-only
          STATUS mandatory
          DESCRIPTION "Size"
          ::= {  firTabCols 5 }

firTabInd OBJECT-TYPE
          SYNTAX INTEGER
          ACCESS read-only
          STATUS mandatory
          DESCRIPTION "Index"
          ::= {  firTabCols 6 }

firMod OBJECT-TYPE
       SYNTAX INTEGER {
         immediate(0),
         login(1),
         manual(2)
       }
       ACCESS read-write
       STATUS mandatory
       DESCRIPTION "Mode-firmsafe"
       ::= {  fir 3 }

firTim OBJECT-TYPE
       SYNTAX INTEGER
       ACCESS read-write
       STATUS mandatory
       DESCRIPTION "Timeout-firmsafe"
       ::= {  fir 4 }

othMan OBJECT IDENTIFIER ::= { oth 1}
othManCon OBJECT-TYPE
          SYNTAX INTEGER
          ACCESS write-only
          STATUS mandatory
          DESCRIPTION "Connect"
          ::= {  othMan 1 }

othManDis OBJECT-TYPE
          SYNTAX INTEGER
          ACCESS write-only
          STATUS mandatory
          DESCRIPTION "Disconnect"
          ::= {  othMan 2 }

othBoo OBJECT-TYPE
       SYNTAX INTEGER
       ACCESS not-accessible
       STATUS mandatory
       DESCRIPTION "Boot-system"
       ::= {  oth 2 }

END
