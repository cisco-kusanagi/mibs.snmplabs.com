-- 
-- FC-DS1-MIB module definition  
--
-- The definitions in this module specify an initial version of 
-- FC mib.
-- 
--

FC-DS1-MIB DEFINITIONS ::= BEGIN
IMPORTS
    enterprises, Counter
        FROM RFC1155-SMI
    OBJECT-TYPE
        FROM RFC-1212
    TRAP-TYPE
        FROM RFC-1215
    DisplayString
        FROM RFC1213-MIB
    MODULE-IDENTITY, ObjectName, Integer32, Counter32, snmpModules
        FROM SNMPv2-SMI
    TruthValue, DisplayString, TestAndIncr, TimeStamp, RowStatus
        FROM SNMPv2-TC;

	lucent		    OBJECT IDENTIFIER  ::=  {  enterprises  1751  }
	products	    OBJECT IDENTIFIER  ::=  {  lucent  1  }
    softSwitch	    OBJECT IDENTIFIER  ::=  {  products 1198  }
	fcDeviceServer  OBJECT IDENTIFIER  ::=  {  softSwitch 9 }
	
    fcDS1  MODULE-IDENTITY    
        LAST-UPDATED "240701"
        ORGANIZATION "Lucent Technologies"    
        CONTACT-INFO 
                ""    
        DESCRIPTION
                "The MIB module for entities implementing the xxxx
                protocol."  

::=  {  fcDeviceServer 1 }




	-- mib groups
	-- the fcSystem group - contains information about this deviceServer

	fcSystem	OBJECT IDENTIFIER  ::=  {  fcDS1 1 }	
	

	-- attrib definitions

        fCServer OBJECT-TYPE
            SYNTAX  INTEGER ( 1..2048 )
            MAX-ACCESS  read-only
            STATUS  current
            DESCRIPTION
                "fcServer is an integer, FC Server in the alarm origin field"

            ::= { fcSystem 1 }

        fCApp OBJECT-TYPE
            SYNTAX  INTEGER ( 0..2048 )
            MAX-ACCESS  read-only
            STATUS  current
            DESCRIPTION
                "fcApp is an integer, FC Application ID to identify the 
                application"

            ::= { fcSystem 2 }

        fCDescText OBJECT-TYPE
            SYNTAX  DisplayString
            MAX-ACCESS  read-only
            STATUS  current
            DESCRIPTION
                "Application Alarm description text"

            ::= { fcSystem 3 }

END
