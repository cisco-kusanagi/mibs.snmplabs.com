--			Ascend mibmaxpots MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBMAXPOTS-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibmaxpotsProfile  OBJECT IDENTIFIER ::= { configuration 94}

	-- The mibmaxpotsProfile table
	--
	-- This table contains parameters for the mibmaxpotsProfile profile
	--

    mibmaxpotsProfileTable	OBJECT-TYPE
	SYNTAX		SEQUENCE OF MibmaxpotsProfileEntry
	ACCESS		not-accessible
	STATUS		mandatory
	DESCRIPTION	"A list of mibmaxpotsProfile profile entries."
	::= { mibmaxpotsProfile 1 }

    mibmaxpotsProfileEntry	OBJECT-TYPE
	SYNTAX		MibmaxpotsProfileEntry
	ACCESS		not-accessible
	STATUS		mandatory
	DESCRIPTION	"A mibmaxpotsProfile entry containing objects that
			 maps to the parameters of mibmaxpotsProfile profile."
	INDEX		{ maxpotsProfile-Shelf-o, maxpotsProfile-Slot-o, maxpotsProfile-Item-o }
	::= { mibmaxpotsProfileTable 1 }

    MibmaxpotsProfileEntry ::=
	SEQUENCE {
	    maxpotsProfile-Shelf-o
		INTEGER,
	    maxpotsProfile-Slot-o
		INTEGER,
	    maxpotsProfile-Item-o
		INTEGER,
	    maxpotsProfile-ProfileNumber
		INTEGER,
	    maxpotsProfile-Name
		DisplayString,
	    maxpotsProfile-PhysicalAddress-Shelf
		INTEGER,
	    maxpotsProfile-PhysicalAddress-Slot
		INTEGER,
	    maxpotsProfile-PhysicalAddress-ItemNumber
		INTEGER,
	    maxpotsProfile-Action-o
		INTEGER
	}

    maxpotsProfile-Shelf-o	OBJECT-TYPE
	SYNTAX	INTEGER
	ACCESS	read-only
	STATUS	mandatory
	DESCRIPTION	""
	::= { mibmaxpotsProfileEntry 1 }

    maxpotsProfile-Slot-o	OBJECT-TYPE
	SYNTAX	INTEGER
	ACCESS	read-only
	STATUS	mandatory
	DESCRIPTION	""
	::= { mibmaxpotsProfileEntry 2 }

    maxpotsProfile-Item-o	OBJECT-TYPE
	SYNTAX	INTEGER
	ACCESS	read-only
	STATUS	mandatory
	DESCRIPTION	""
	::= { mibmaxpotsProfileEntry 3 }

    maxpotsProfile-ProfileNumber	OBJECT-TYPE
	SYNTAX	INTEGER
	ACCESS	read-write
	STATUS	mandatory
	DESCRIPTION	"If it is a stored profile, the number of the profile (1..MAX_NETWORK_PROFILES). If it is the current profile, the number of the stored profile from which it was loaded, or zero if it has never been loaded."
	::= { mibmaxpotsProfileEntry 4 }

    maxpotsProfile-Name	OBJECT-TYPE
	SYNTAX	DisplayString
	ACCESS	read-write
	STATUS	mandatory
	DESCRIPTION	"The null terminated ascii string that the user gave to this particular profile."
	::= { mibmaxpotsProfileEntry 5 }

    maxpotsProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibmaxpotsProfileEntry 6 }

    maxpotsProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibmaxpotsProfileEntry 7 }

    maxpotsProfile-PhysicalAddress-ItemNumber	OBJECT-TYPE
	SYNTAX	INTEGER
	ACCESS	read-write
	STATUS	mandatory
	DESCRIPTION	"A number that specifies an addressable entity within the context of shelf and slot."
	::= { mibmaxpotsProfileEntry 8 }

    maxpotsProfile-Action-o	OBJECT-TYPE
	SYNTAX	INTEGER {
		    noAction (1),
		    createProfile (2),
		    deleteProfile (3)
		}
	ACCESS	read-write
	STATUS	mandatory
	DESCRIPTION	""
	::= { mibmaxpotsProfileEntry 9 }


	-- The mibmaxpotsProfile__line_interface table
	--
	-- This table contains parameters for the mibmaxpotsProfile__line_interface profile
	--

    mibmaxpotsProfile-LineInterfaceTable	OBJECT-TYPE
	SYNTAX		SEQUENCE OF MibmaxpotsProfile-LineInterfaceEntry
	ACCESS		not-accessible
	STATUS		mandatory
	DESCRIPTION	"A list of mibmaxpotsProfile__line_interface profile entries."
	::= { mibmaxpotsProfile 2 }

    mibmaxpotsProfile-LineInterfaceEntry	OBJECT-TYPE
	SYNTAX		MibmaxpotsProfile-LineInterfaceEntry
	ACCESS		not-accessible
	STATUS		mandatory
	DESCRIPTION	"A mibmaxpotsProfile__line_interface entry containing objects that
			 maps to the parameters of mibmaxpotsProfile__line_interface profile."
	INDEX		{ maxpotsProfile-LineInterface-Shelf-o, maxpotsProfile-LineInterface-Slot-o, maxpotsProfile-LineInterface-Item-o, maxpotsProfile-LineInterface-Index-o }
	::= { mibmaxpotsProfile-LineInterfaceTable 1 }

    MibmaxpotsProfile-LineInterfaceEntry ::=
	SEQUENCE {
	    maxpotsProfile-LineInterface-Shelf-o
		INTEGER,
	    maxpotsProfile-LineInterface-Slot-o
		INTEGER,
	    maxpotsProfile-LineInterface-Item-o
		INTEGER,
	    maxpotsProfile-LineInterface-Index-o
		INTEGER,
	    maxpotsProfile-LineInterface-DialEnabled
		INTEGER,
	    maxpotsProfile-LineInterface-NetClidEnabled
		INTEGER,
	    maxpotsProfile-LineInterface-ClidNumber
		DisplayString,
	    maxpotsProfile-LineInterface-AnswerEnabled
		INTEGER,
	    maxpotsProfile-LineInterface-CallerIdEnabled
		INTEGER,
	    maxpotsProfile-LineInterface-FwdDiscEnabled
		INTEGER,
	    maxpotsProfile-LineInterface-RxGain
		INTEGER,
	    maxpotsProfile-LineInterface-TxGain
		INTEGER,
	    maxpotsProfile-LineInterface-Signaling
		INTEGER,
	    maxpotsProfile-LineInterface-GndStartRing
		INTEGER
	}

    maxpotsProfile-LineInterface-Shelf-o	OBJECT-TYPE
	SYNTAX	INTEGER
	ACCESS	read-only
	STATUS	mandatory
	DESCRIPTION	""
	::= { mibmaxpotsProfile-LineInterfaceEntry 1 }

    maxpotsProfile-LineInterface-Slot-o	OBJECT-TYPE
	SYNTAX	INTEGER
	ACCESS	read-only
	STATUS	mandatory
	DESCRIPTION	""
	::= { mibmaxpotsProfile-LineInterfaceEntry 2 }

    maxpotsProfile-LineInterface-Item-o	OBJECT-TYPE
	SYNTAX	INTEGER
	ACCESS	read-only
	STATUS	mandatory
	DESCRIPTION	""
	::= { mibmaxpotsProfile-LineInterfaceEntry 3 }

    maxpotsProfile-LineInterface-Index-o	OBJECT-TYPE
	SYNTAX	INTEGER
	ACCESS	read-only
	STATUS	mandatory
	DESCRIPTION	""
	::= { mibmaxpotsProfile-LineInterfaceEntry 4 }

    maxpotsProfile-LineInterface-DialEnabled	OBJECT-TYPE
	SYNTAX	INTEGER {
		    no (1),
		    yes (2)
		}
	ACCESS	read-write
	STATUS	mandatory
	DESCRIPTION	"TRUE to enable dialing on this port."
	::= { mibmaxpotsProfile-LineInterfaceEntry 5 }

    maxpotsProfile-LineInterface-NetClidEnabled	OBJECT-TYPE
	SYNTAX	INTEGER {
		    no (1),
		    yes (2)
		}
	ACCESS	read-write
	STATUS	mandatory
	DESCRIPTION	"TRUE to send CLID to network."
	::= { mibmaxpotsProfile-LineInterfaceEntry 6 }

    maxpotsProfile-LineInterface-ClidNumber	OBJECT-TYPE
	SYNTAX	DisplayString
	ACCESS	read-write
	STATUS	mandatory
	DESCRIPTION	"Number to send to network if to-net CLID enabled."
	::= { mibmaxpotsProfile-LineInterfaceEntry 7 }

    maxpotsProfile-LineInterface-AnswerEnabled	OBJECT-TYPE
	SYNTAX	INTEGER {
		    no (1),
		    yes (2)
		}
	ACCESS	read-write
	STATUS	mandatory
	DESCRIPTION	"TRUE to enable answering on this port."
	::= { mibmaxpotsProfile-LineInterfaceEntry 8 }

    maxpotsProfile-LineInterface-CallerIdEnabled	OBJECT-TYPE
	SYNTAX	INTEGER {
		    no (1),
		    yes (2)
		}
	ACCESS	read-write
	STATUS	mandatory
	DESCRIPTION	"TRUE to enable caller id on this port."
	::= { mibmaxpotsProfile-LineInterfaceEntry 9 }

    maxpotsProfile-LineInterface-FwdDiscEnabled	OBJECT-TYPE
	SYNTAX	INTEGER {
		    no (1),
		    yes (2)
		}
	ACCESS	read-write
	STATUS	mandatory
	DESCRIPTION	"TRUE to enable forward disconnect on this port."
	::= { mibmaxpotsProfile-LineInterfaceEntry 10 }

    maxpotsProfile-LineInterface-RxGain	OBJECT-TYPE
	SYNTAX	INTEGER {
		    n-0db (1),
		    n-plus-1db (2),
		    n-plus-2db (3),
		    n-plus-3db (4),
		    n-plus-4db (5),
		    n-plus-5db (6),
		    n-plus-6db (7),
		    n-plus-7db (8),
		    n-plus-8db (9),
		    n-plus-9db (10),
		    n-plus-10db (11),
		    n-plus-11db (12),
		    n-plus-12db (13),
		    n-1db (14),
		    n-2db (15),
		    n-3db (16),
		    n-4db (17),
		    n-5db (18),
		    n-6db (19),
		    n-7db (20),
		    n-8db (21),
		    n-9db (22),
		    n-10db (23),
		    n-11db (24),
		    n-12db (25)
		}
	ACCESS	read-write
	STATUS	mandatory
	DESCRIPTION	"Rx gain."
	::= { mibmaxpotsProfile-LineInterfaceEntry 11 }

    maxpotsProfile-LineInterface-TxGain	OBJECT-TYPE
	SYNTAX	INTEGER {
		    n-0db (1),
		    n-plus-1db (2),
		    n-plus-2db (3),
		    n-plus-3db (4),
		    n-plus-4db (5),
		    n-plus-5db (6),
		    n-plus-6db (7),
		    n-plus-7db (8),
		    n-plus-8db (9),
		    n-plus-9db (10),
		    n-plus-10db (11),
		    n-plus-11db (12),
		    n-plus-12db (13),
		    n-1db (14),
		    n-2db (15),
		    n-3db (16),
		    n-4db (17),
		    n-5db (18),
		    n-6db (19),
		    n-7db (20),
		    n-8db (21),
		    n-9db (22),
		    n-10db (23),
		    n-11db (24),
		    n-12db (25)
		}
	ACCESS	read-write
	STATUS	mandatory
	DESCRIPTION	"Tx gain."
	::= { mibmaxpotsProfile-LineInterfaceEntry 12 }

    maxpotsProfile-LineInterface-Signaling	OBJECT-TYPE
	SYNTAX	INTEGER {
		    loopStart (1),
		    groundStart (2)
		}
	ACCESS	read-write
	STATUS	mandatory
	DESCRIPTION	"Analog signaling."
	::= { mibmaxpotsProfile-LineInterfaceEntry 13 }

    maxpotsProfile-LineInterface-GndStartRing	OBJECT-TYPE
	SYNTAX	INTEGER {
		    no (1),
		    yes (2)
		}
	ACCESS	read-write
	STATUS	mandatory
	DESCRIPTION	"TRUE to ring when signaling is ground start"
	::= { mibmaxpotsProfile-LineInterfaceEntry 14 }

END
