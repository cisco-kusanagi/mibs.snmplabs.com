-- Copyright 1994 General DataComm Ind., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive licence to use
-- this Specification in connection with the management of GDC's products.
--
-- This Specification is supplied "AS IS," and GDC makes no warranty,
-- either expressed or implied, as to the use operation, condition, or
-- performance of the Specification.
--
-- Revision History
--
-- Version   Date       Name            Description
-- 1.00      02-Jun-94  B. Richards     Initial Revision
-- 2.00A     03-Jun-94  B. Richards     Phase II (remote config and
--					password verification)
-- 2.00B     20-Jun-94	E.M.L.		PL Talk/Data, Remote Configuration
--					Password, obsolete RemoteConfiguration
--                                      from modem options, comments from objects
--                                      that need to be blocked during Remote
--                                      Configuration.
--                                      Rework traps for Password operations.
-- 2.00C     05-Aug-94	B.Richards	-corrected discription on auto dial
--					 restoral for with and without end of
--					 session
--					-changed termination test to terminate
--					 test
--					-call statistics - added
--					 mdmCompressionEfficiency, mdmThruput
--					-call statistics trap - added
--					 mdmCallDuarationStat
--					 mdmCompressionEfficiency, mdmThruput
--					-added MIB version number
--					 mdmMIBVersion
--					-added mdmSwitchedPrivate to status
--					-removed password and roving callback
--					 number
--					-made mdmPLTalkData write only
--					-edited mdmDiscReason
--					-added 'notInTest' to diagnostic
--					 status
--					-added 'other' to dial status
-- 2.00D     12-Aug-94	B.Richards	-deleted obsolete objects
--					 mdmRemoteConfig,mdmDTEActive,
--					 mdmDTEBreak,mdmPswdFail,mdmPswdOK,
--					 mdmNoRspCall,mdmNoNamePswd,mdmCallBack,
--					 mdmNamePswdEnter,mdmAlarmInterval,
--					 mdmSignalQual.
--					-mdmPLTalkData deleted enums training
--					 and retrain and added description
--					-mdmDialStatus changed enum other to
--					 inTest
--					-mdmCallStatsTrap changed order of
--					 objects.
--					-mdmDTECard changed rs323A to EIA232
--					-expanded description of mdmTestStatus
-- 2.00E     16-Aug-94	B.Richards	-trap 1 and call statistics table
--					 mdmStatisticsEntry
--					 deleted objects mdmTxCharacter,
--					 mdmTxCompressionCharacter,
--					 mdmRxCharacter,
--					 mdmRxCompressionCharacter,
--					 mdmTxDataFrames,mdmTxRetDataFrames,
--					 mdmPhaseHitsCount,mdmGainHitsCount
--					-changed size of
--					 mdmPasswordRemoteConfiguration and
--					 mdmPassword from 1..10 to 0..10
--					-import of 'Counter' taken out of
--					 RFC1155-SMI
-- 2.00F     23-Aug-94	S. Zezima	-added enum to mdmTestStatus and
--					 mdmCallProgressStatus for when no status
--					 is available.
-- 2.00G     6-Sept-94	B. Richards	-changed enum mdmCPMResp from lastAT
--					 to lastConnectSpeed
--					-added mdmFrameRetransLimit to protocol
--					 configuration
--					-added mdmBackSpaceCharacter to DTE
--					 configuration
-- 2.00H     7-Sept-94	B. Richards	-changed value range for mdmSNTxLevel
-- 2.00I    26-Sept-94	B. Richards	-changed value range for mdmSNTxLevel



GDCMDM-MIB DEFINITIONS	   ::=	   BEGIN

IMPORTS

	enterprises, TimeTicks		FROM RFC1155-SMI
	DisplayString                   FROM RFC1213-MIB
	OBJECT-TYPE                     FROM RFC-1212
	TRAP-TYPE                       FROM RFC-1215
	SCinstance                      FROM GDCMACRO-MIB;


-- This is the GDC vfast MIB for vfast objects.
--
-- This MIB is only usable when the configuration is software controllable.
--
-- See the GDC MIB requirements document to determine how the standard MIB's
-- are supported.
--

gdc     OBJECT IDENTIFIER ::= { enterprises 498 }

mdm     OBJECT IDENTIFIER ::= { gdc 4 }

-- GDC VFAST MODEM Configuration Parameters
--
-- Implementation of this group is mandatory for all GDC VFAST MODEMS.

--*****************************************************************************
--            NETWORK CONFIGURATION TABLE
--*****************************************************************************

mdmNetworkConfigTable OBJECT-TYPE
	SYNTAX  SEQUENCE OF MdmNetworkEntry
	ACCESS  not-accessible
	STATUS  mandatory
	DESCRIPTION
		"The GDC VFAST modem network configuration table."
	::= { mdm 1 }


mdmNetworkEntry OBJECT-TYPE
	SYNTAX  MdmNetworkEntry
	ACCESS  not-accessible
	STATUS  mandatory
	DESCRIPTION
		"A listing of GDC VFAST modem network options."
	INDEX   { mdmNetworkIndex }
	::= { mdmNetworkConfigTable 1 }


MdmNetworkEntry ::=
	SEQUENCE        {
			mdmNetworkIndex
				SCinstance,
			mdmNetworkType
				INTEGER,
			mdmSNTxType
				INTEGER,
			mdmSNTxLevel
				INTEGER,
			mdmSNHandshakeMode
				INTEGER
			}

mdmNetworkIndex OBJECT-TYPE
	SYNTAX  SCinstance
	ACCESS  read-only
	STATUS  mandatory
	DESCRIPTION
		"A unique index for the Network Table."
	::= { mdmNetworkEntry 1 }

mdmNetworkType OBJECT-TYPE
	SYNTAX  INTEGER {
				switchedNetwork(1),
				privateLine2Wire(2),
				privateLine4Wire(3)
			}
	ACCESS    read-write
	STATUS    mandatory
	DESCRIPTION
			"Command to option the VF line type mode
			 of operation."
	::= { mdmNetworkEntry 2 }



mdmSNTxType OBJECT-TYPE
	SYNTAX  INTEGER {
				permissive(1),
				programmable(2),
				adjustable(3)
			}
	ACCESS    read-write
	STATUS    mandatory
	DESCRIPTION
			"Command used to select either Permissive or
			 Programable Switched Network Transmit Level.
			 This object is Country Code dependent"
	::= { mdmNetworkEntry 3 }


mdmSNTxLevel OBJECT-TYPE
	SYNTAX	INTEGER (0..15)

	ACCESS    read-write
	STATUS    mandatory
	DESCRIPTION     "Command to select(force) the Switched Network
			 Transmit Level when modem is optioned for adjustable.
			 This object is Country Code dependent"

	::= { mdmNetworkEntry 4 }


mdmSNHandshakeMode OBJECT-TYPE
	SYNTAX  INTEGER         {
				gdcVfastAuto(1),
				gdcVfastOnly(2),
				v32bisAuto(3),
				v32bisOnly(4),
				v32Auto(5),
				v32Only(6),
				v22bis(7),
				v22Only(8),
				bell212(9),
				bell103(10),
				v21(11)
				}
	ACCESS    read-write
	STATUS    mandatory
	DESCRIPTION     "Available handshake modes.
			 This object is Country Code dependent."

	::= { mdmNetworkEntry 5 }


--*****************************************************************************
--                    DTE CONFIGURATION TABLE
--*****************************************************************************

mdmDTEConfigTable OBJECT-TYPE
	SYNTAX  SEQUENCE OF     MdmDTEntry
	ACCESS    not-accessible
	STATUS    mandatory
	DESCRIPTION
			"The GDC VFAST modem Data Terminal Equipment
			 configuration table."
	::= { mdm 2 }


mdmDTEntry OBJECT-TYPE
	SYNTAX    MdmDTEntry
	ACCESS    not-accessible
	STATUS    mandatory
	DESCRIPTION
			"A listing of GDC VFAST modem DTE options."
	INDEX      { mdmDTEIndex }
	::= { mdmDTEConfigTable 1 }

MdmDTEntry      ::=
	SEQUENCE        {
			mdmDTEIndex
				SCinstance,
			mdmDTESpeed
				INTEGER,
			mdmCPMResp
				INTEGER,
			mdmCharLength
				INTEGER,
			mdmParity
				INTEGER,
			mdmOverspeed
				INTEGER,
			mdmFlowCntrl
				INTEGER,
			mdmTermEcho
				INTEGER,
			mdmDCDCntrl
				INTEGER,
			mdmCTSCntrl
				INTEGER,
			mdmDTRTrans
				INTEGER,
			mdmDSRCntrl
				INTEGER,
			mdmDSRCntrlAL
				INTEGER,
			mdmTXClockSource
				INTEGER,
			mdmRTSCTSDelay
				INTEGER,
			mdmCarriageReturnCharacter
				INTEGER,
			mdmCharacterAbortDialing
				INTEGER,
			mdmDelayDTR
				INTEGER,
			mdmEscapeCharacter
				INTEGER,
			mdmLineFeedCharacter
				INTEGER,
			mdmHangUpDelay
				INTEGER,
			mdmEscapeCharacterGuardTime
				INTEGER,
			mdmOperatingMode
				INTEGER,
			mdmBackSpaceCharacter
				INTEGER
			}


mdmDTEIndex OBJECT-TYPE
	SYNTAX    SCinstance
	ACCESS    read-only
	STATUS    mandatory
	DESCRIPTION
			"A unique index for the DTE Table."
	::= { mdmDTEntry 1 }


mdmDTESpeed OBJECT-TYPE
	SYNTAX    INTEGER       {
					autobaud(1),
					lastAT(2),
					bps300(3),
					bps1200(4),
					bps2400(5),
					bps4800(6),
					bps7200(7),
					bps9600(8),
					bps12000(9),
					bps14400(10),
					bps16800(11),
					bps19200(12),
					bps21600(13),
					bps24000(14),
					bps26400(15),
					bps28800(16),
					bps38400(17),
					bps57600(18),
					bps76800(19),
					bps115200(20),
					bps128000(21)
					}
	ACCESS    read-write
	STATUS    mandatory
	DESCRIPTION
			"This option selects DTE bit Rate."
	::= { mdmDTEntry 2 }


mdmCPMResp OBJECT-TYPE
	SYNTAX    INTEGER       {
					autobaud(1),
					lastConnectSpeed(2),
					bps300(3),
					bps1200(4),
					bps2400(5),
					bps4800(6),
					bps7200(7),
					bps9600(8),
					bps12000(9),
					bps14400(10),
					bps16800(11),
					bps19200(12),
					bps21600(13),
					bps24000(14),
					bps26400(15),
					bps28800(16),
					bps38400(17),
					bps57600(18),
					bps76800(19),
					bps115200(20),
					bps128000(21)
					}
	ACCESS    read-write
	STATUS    mandatory
	DESCRIPTION
			"Selects the response rate of the Call Progress
			 Monitor."
	::= { mdmDTEntry 3 }


mdmCharLength OBJECT-TYPE
	SYNTAX    INTEGER       {
					data6Stop1(1),
					data7Stop1(2),
					data7ParityStop1(3),
					data8Stop1(4),
					data7ParityStop2(5),
					data8ParityStop1(6)
					}
	ACCESS    read-write
	STATUS    mandatory
	DESCRIPTION
			"DTE charater length and format options of
			the DTE asynchronous data."
	::= { mdmDTEntry 4 }


mdmParity OBJECT-TYPE
	SYNTAX    INTEGER       {
					even(1),
					space(2),
					odd(3),
					mark(4),
					auto(5)
					}
	ACCESS    read-write
	STATUS    mandatory
	DESCRIPTION
			"Parity of the async data when the character length
			option selects parity."
	::= { mdmDTEntry 5 }


mdmOverspeed OBJECT-TYPE
	SYNTAX    INTEGER       {
					nominal(1),
					extended(2)
					}
	ACCESS    read-write
	STATUS    mandatory
	DESCRIPTION
			"Option to set DTE async overspeed data
			 tolerated by the modem.  Extended = 2.5%.
			 Nominal = 1.25%."
	::= { mdmDTEntry 6 }


mdmFlowCntrl OBJECT-TYPE
	SYNTAX    INTEGER       {
					disabled(1),
					xonXoffSig(2),
					cts(3),
					rtsCts(4),
					xonXoff(5)
					}
	ACCESS    read-write
	STATUS    mandatory
	DESCRIPTION
			"Options to set the modem DTE flow control.
			disable         Disables all flow control.
			xonXoffSig      Enables XON/XOFF signaling between
					modem and DTE.
			cts             Enables the modem to flow control the
					DTE via CTS.
			rtsCts          This option operates the same as CTS option
					as well as allowing RTS to flow control
					the modem as a ready to receive signal.
			xonOff          Allows the modem to XON/XOFF the DTE
					yet ignore these signals when sent by the
					DTE (unidirectional flow control)."
	::= { mdmDTEntry 7 }


mdmTermEcho OBJECT-TYPE
	SYNTAX    INTEGER       {
					disabled(1),
					enabled(2)
					}
	ACCESS    read-write
	STATUS    mandatory
	DESCRIPTION
			"Option to control the modem echo to the DTE."
	::= { mdmDTEntry 8 }


mdmDCDCntrl OBJECT-TYPE
	SYNTAX    INTEGER       {
					forceOn(1),
					real(2),
					forceOnToggleDisc(3)
					}
	ACCESS    read-write
	STATUS    mandatory
	DESCRIPTION
			"Option the EIA DCD mode of operation.
			ForceOn         DCD always ON.
			Real            DCD will follow CCITT specifications.
			ForceOnToggleDisc   DCD is On but toggle on disconnect
					as a signaling to the front end."
	::= { mdmDTEntry 9 }


mdmCTSCntrl OBJECT-TYPE
	SYNTAX    INTEGER       {
					cmdOnDataRTS(1),
					cmdOnDataReal(2),
					realCCITT(3),
					forceOn(4)
					}
	ACCESS    read-write
	STATUS    mandatory
	DESCRIPTION
			"Option the EIA CTS mode of operation.
			cmdOnDataRTS    On during command mode, during data mode
					will follow RTS.
			cmdOnDataReal   On during command mode, during data mode
					will follow CCITT specifications.
			realCCITT       It follows CCITT specifications always.
			ForceON         On all the times. "
	::= { mdmDTEntry 10 }


mdmDTRTrans OBJECT-TYPE
	SYNTAX    INTEGER       {
					forceon(1),
					offInCmdMode(2),
					offDisc(3),
					offDiscRecallUser(4)
					}
	ACCESS    read-write
	STATUS    mandatory
	DESCRIPTION
			"Option the modem to respond to loss
			 of DTR.
			forceon        Modem ignore DTR transitions.
			offInCmdMode   Upon transition detection
				       modem will enter command mode.
			offDisc        Upon transition detection
				       modem will disconnect.
			offDiscRecalUser  Upon transition detection
				       modem will disconect and recall
				       the selected User configuration.
			This object is Country Code dependent."
	::= { mdmDTEntry 11 }


mdmDSRCntrl OBJECT-TYPE
	SYNTAX    INTEGER       {
					onUntilDisc(1),
					normal(2),
					followDCD(3),
					forceOn(4)
					}
	ACCESS    read-write
	STATUS    mandatory
	DESCRIPTION
			"Option the EIA DSR mode of operation.
			onUntilDisc    Selects DSR to remain On and glitch
				       Off for disconnect.
			Normal         Causes DSR to be real.
			followDCD       Selects DSR to follow carrier detect.
			forceOn        Selects DSR forced On in all modes."
	::= { mdmDTEntry 12 }


mdmDSRCntrlAL OBJECT-TYPE
	SYNTAX    INTEGER       {
					onAnaloop(1),
					offAnaloop(2)
					}
	ACCESS    read-write
	STATUS    mandatory
	DESCRIPTION
			"Option the EIA DSR operation during analoop.
			onAnaloop      DSR will turn ON when in analoop
			offAnaloop     DSR is forced Off when in Analoop."
	::= { mdmDTEntry 13 }


mdmTXClockSource OBJECT-TYPE
	SYNTAX    INTEGER       {
					internal(1),
					external(2),
					receiverwrap(3)
					}
	ACCESS    read-write
	STATUS    mandatory
	DESCRIPTION
			"Selects the source for TX clock generation.
			internal        The modem uses the internally generated
					clock source.
			external        The modem uses the DTE clock as a source
			receiverwrap    The modem receiver derived timing clock
					to be used in the transmitter."
	::= { mdmDTEntry 14 }


mdmRTSCTSDelay OBJECT-TYPE
	SYNTAX    INTEGER       (0..255)
	ACCESS    read-write
	STATUS    mandatory
	DESCRIPTION
			"Selects the delay time between
			 RTS coming on and CTS being turned on (.001 sec)."
	::= { mdmDTEntry 15 }


mdmCarriageReturnCharacter OBJECT-TYPE
	SYNTAX    INTEGER        (0..127)
	ACCESS    read-write
	STATUS    mandatory
	DESCRIPTION
			"Select the ascii character to be
			 used as the carriage return."
	::= { mdmDTEntry 16 }

mdmCharacterAbortDialing OBJECT-TYPE
	SYNTAX    INTEGER {
				enabled(1),
				disabled(2)
				}
	ACCESS    read-write
	STATUS    mandatory
	DESCRIPTION
			"Enable/disable the option to abort
			 dialing if a DTE character is detected."
	::= { mdmDTEntry 17 }

mdmDelayDTR OBJECT-TYPE
	SYNTAX    INTEGER        (0..255)
	ACCESS    read-write
	STATUS    mandatory
	DESCRIPTION
			"Selects the delay time(in Seconds) between
			 making data mode and raising the DTR lead. It is dependent
			 on the mode of operation.
			 When configured for &M0 this register is used to debounce
			 the DTR signal. The default value is five hundredths of
			 a second (0.05second).
			 When configured for &M1 and in data mode, this register
			 sets the time available to the operator to switch the EIA
			 cable from asynchronous equipment to synchronous equipment.
			 When the timer expires, this register is used to debounce
			 the DTR signal as in &M0 mode. The default value is five
			 seconds."
	::= { mdmDTEntry 18 }

mdmEscapeCharacter OBJECT-TYPE
	SYNTAX    INTEGER        (0..127)
	ACCESS    read-write
	STATUS    mandatory
	DESCRIPTION
			"Select the ascii character to be
			 used as the 'escape to command mode' character."
	::= { mdmDTEntry 19 }

mdmLineFeedCharacter OBJECT-TYPE
	SYNTAX    INTEGER        (0..127)
	ACCESS    read-write
	STATUS    mandatory
	DESCRIPTION
			"Select the ascii character to be
			 used as the Line Feed character."
	::= { mdmDTEntry 20 }

mdmHangUpDelay OBJECT-TYPE
	SYNTAX    INTEGER        (0..255)
	ACCESS    read-write
	STATUS    mandatory
	DESCRIPTION
			"Select the delay time(in Sec) between
			 the modem detecting a command to hang up the line and
			 the disconnect operation."
	::= { mdmDTEntry 21 }

mdmEscapeCharacterGuardTime OBJECT-TYPE
	SYNTAX    INTEGER        (0..255)
	ACCESS    read-write
	STATUS    mandatory
	DESCRIPTION
			"This is the timer the modem will use when determining
			a valid escape sequence.
			Select the delay time(in 1/50 Sec).
			When a valid escape sequence is detected the modem will
			transfer from the data to command mode."
	::= { mdmDTEntry 22 }


mdmOperatingMode OBJECT-TYPE
	SYNTAX    INTEGER        {
					asyncDataMode(1),
					asyncCmdsyncData(2)
					}
	ACCESS    read-write
	STATUS    mandatory
	DESCRIPTION
			"Option to set the type of data transfer in
			 data mode.
			 asyncDataMode  modem operates in async mode during command
			 or data mode.
			 async CmdsyncData   In command mode the modem uses async
					data. In data mode operates in synchronous mode."
	::= { mdmDTEntry 23 }

mdmBackSpaceCharacter	 OBJECT-TYPE
	SYNTAX    INTEGER        (0..127)
	ACCESS    read-write
	STATUS    mandatory
	DESCRIPTION
			"Select the ascii character to be
			 used as the Back Space character."
	::= { mdmDTEntry 24 }

--*****************************************************************************
--                    MODEM CONFIGURATION TABLE
--*****************************************************************************
mdmModemConfigTable OBJECT-TYPE
	SYNTAX  SEQUENCE OF     MdmModemEntry
	ACCESS    not-accessible
	STATUS    mandatory
	DESCRIPTION
			"The GDC VFAST modem configuration table."
	::= { mdm 3 }


mdmModemEntry OBJECT-TYPE
	SYNTAX    MdmModemEntry
	ACCESS    not-accessible
	STATUS    mandatory
	DESCRIPTION
			"A listing of GDC VFAST modem options."
	INDEX      {mdmModemIndex}
	::= { mdmModemConfigTable 1 }

MdmModemEntry   ::=
	SEQUENCE        {
			mdmModemIndex
				SCinstance,
			mdmRingsToAns
				INTEGER,
			mdmFallFwrdBack
				INTEGER,
			mdmTrellis
				INTEGER,
			mdmSQRetrain
				INTEGER,
			mdmLongSpaceDisc
				INTEGER,
			mdmMakeBusy
				INTEGER,
			mdmRDLOptions
				INTEGER,
			mdmTestTimer
				INTEGER,
			mdmDTETestCntrl
				INTEGER,
			mdmDCDLossDisc
				INTEGER,
			mdmCDRespTime
				INTEGER,
			mdmAnswerOriginate
				INTEGER,
			mdmWaitForDCD
				INTEGER
			}


mdmModemIndex OBJECT-TYPE
	SYNTAX    SCinstance
	ACCESS    read-only
	STATUS    mandatory
	DESCRIPTION
			"A unique index for the Modem Option Table."
	::= { mdmModemEntry 1 }


mdmRingsToAns OBJECT-TYPE
	SYNTAX    INTEGER       (0..255)
	ACCESS    read-write
	STATUS    mandatory
	DESCRIPTION
			"Selects the number of rings received
			 before the modem Auto Answer.
			 This object is Country Code dependent"
	::= { mdmModemEntry 2 }


mdmFallFwrdBack OBJECT-TYPE
	SYNTAX    INTEGER       {
					disabled(1),
					enabled(2)
					}
	ACCESS    read-write
	STATUS    mandatory
	DESCRIPTION
			"Command the modem to enable/disable rate
			negotiation during a retrain."
	::= { mdmModemEntry 3 }


mdmTrellis OBJECT-TYPE
	SYNTAX    INTEGER       {
					enabled(1),
					disabled(2)
					}
	ACCESS    read-write
	STATUS    mandatory
	DESCRIPTION
			"Enable/disable Trellis negotiation
			 during a handshake."
	::= { mdmModemEntry 4 }


mdmSQRetrain OBJECT-TYPE
	SYNTAX    INTEGER       {
					disabled(1),
					sQThree(2),
					sQForever(3)
					}
	ACCESS    read-write
	STATUS    mandatory
	DESCRIPTION
			"Command to option Signal Quality Retrains."
	::= { mdmModemEntry 5 }


mdmLongSpaceDisc OBJECT-TYPE
	SYNTAX    INTEGER       {
					disabled(1),
					enabled(2)
					}
	ACCESS    read-write
	STATUS    mandatory
	DESCRIPTION
			"Command to enable/disable Long Space Disconnect.
			enable  The modem will transmit 4 seconds of continuous
				space (BREAK) when ever a disconnect request is
				detected. If the modem receives more than 1.5
				seconds of continuous space (BREAK) while on-line,
				it will hang up."
	::= { mdmModemEntry 6 }


mdmMakeBusy OBJECT-TYPE
	SYNTAX    INTEGER       {
					disabled(1),
					onLossDTR(2),
					inAL(3),
					inALorLossRTSorDTR(4),
					onLossRTS(5)
					}
	ACCESS    read-write
	STATUS    mandatory
	DESCRIPTION
			"Command to option the switched network
			 make busy function
			 disable        Does not make busy.
			 onLossDTR      Make busy on loss of DTR.
			 inAL           Make busy during analoop.
			 inALorLossRTSorDTR  Make busy in analoop, loss of
					RTS or DTR.
			 This object is Country Code dependent"
	::= { mdmModemEntry 7 }


mdmRDLOptions OBJECT-TYPE
	SYNTAX    INTEGER       {
					disable(1),
					enable(2)
					}
	ACCESS    read-write
	STATUS    mandatory
	DESCRIPTION
			"Command to enable/disable Remote
			 Digital Loopback Instigation.
			 disable        The modem ignores the inband request
					to initiate a remote digital loopback.
			 enable         The modem accept the inband request to
					initiated a remote digital loopback."
	::= { mdmModemEntry 8 }


mdmTestTimer OBJECT-TYPE
	SYNTAX    INTEGER       (0..255)
	ACCESS    read-write
	STATUS    mandatory
	DESCRIPTION
			"Command to limit any diagnostic test in
			 10 second intervals.
			 When the value is zero the test runs forever."
	::= { mdmModemEntry 9 }


mdmDTETestCntrl OBJECT-TYPE
	SYNTAX    INTEGER       {
					 disabled(1),
					 enabled(2)
					}
	ACCESS    read-write
	STATUS    mandatory
	DESCRIPTION
			"Command to enable/disable diagnostic tests from DTE
			 interface."
	::= { mdmModemEntry 10 }


mdmDCDLossDisc OBJECT-TYPE
	SYNTAX    INTEGER       (0..255)
	ACCESS    read-write
	STATUS    mandatory
	DESCRIPTION
			"Command to set the time (0.1sec) between loss
			 of carrier detected and a modem disconnect.
			 This object is Country Code dependent."

	::= { mdmModemEntry 11 }


mdmCDRespTime OBJECT-TYPE
	SYNTAX    INTEGER        (0..255)
	ACCESS    read-write
	STATUS    mandatory
	DESCRIPTION
			"Command to set the time (in Sec) a carrier
			 signal must be present for the modem to recognize it.
			 This object is Country Code dependent."

	::= { mdmModemEntry 12 }



mdmAnswerOriginate OBJECT-TYPE
	SYNTAX    INTEGER        {
					answerIfRingDetect(1),
					forceAnswer(2),
					autoAnswerInOriginate(3)
					}
	ACCESS    read-write
	STATUS    mandatory
	DESCRIPTION
			"Command to set the handshake band.
			answerIfRingDetect      Upon detecting a ring the modem
						will handshake in the answer mode.
			forceAnswer             The modem will be force to handshake
						in the answer mode.
			autoAnswerInOriginate   When the modem detect a ring it
						will answer in the originate mode."
	::= { mdmModemEntry 13 }

mdmWaitForDCD OBJECT-TYPE
	SYNTAX    INTEGER        (1..60)
	ACCESS    read-write
	STATUS    mandatory
	DESCRIPTION
			"This object is used to store the carrier wait time.
			 This is the time which the modem will wait after the
			 dial has been completed until the modem senses
			 carrier detect. It is also used for the dial command
			 modifiers W wait for dial tone before dialing and @
			 wait for quiet answer before dialing. It also sets
			 the amount of time the modem will wait for ringback
			 when originating a call.
			 This object is Country Code dependent."

	::= { mdmModemEntry 14 }

--*****************************************************************************
--            DIALER CONFIGURATION TABLE
--*****************************************************************************

mdmDialerConfigTable OBJECT-TYPE
	SYNTAX  SEQUENCE OF     MdmDialerEntry
	ACCESS    not-accessible
	STATUS    mandatory
	DESCRIPTION
			"The GDC VFAST dialer configuration table."
	::= { mdm 4 }


mdmDialerEntry OBJECT-TYPE
	SYNTAX    MdmDialerEntry
	ACCESS    not-accessible
	STATUS    mandatory
	DESCRIPTION
			"A listing of GDC VFAST modem dialer options."
	INDEX      { mdmDialerIndex }
	::= { mdmDialerConfigTable 1 }

MdmDialerEntry ::=
	SEQUENCE        {
			mdmDialerIndex
				SCinstance,
			mdmCPMMonitor
				INTEGER,
			mdmParserSelection
				INTEGER,
			mdmDTRDial
				INTEGER,
			mdmDialType
				INTEGER,
			mdmResponseMode
				INTEGER,
			mdmResponseType
				INTEGER,
			mdmPauseTime
				INTEGER,
			mdmWaitForDialtoneTime
				INTEGER
			}

mdmDialerIndex OBJECT-TYPE
	SYNTAX    SCinstance
	ACCESS    read-only
	STATUS    mandatory
	DESCRIPTION
			"A unique index for the Dialer Table."
	::= { mdmDialerEntry 1 }

mdmCPMMonitor OBJECT-TYPE
	SYNTAX  INTEGER {
				basic(1),
				extendedNoCPM(2),
				extendedDialtone(3),
				extendedBusy(4),
				extendedFullCPM(5),
				extendedFullCPMRingback(6)
				}
	ACCESS    read-write
	STATUS    mandatory
	DESCRIPTION
			"Command used to option the Call Progress Monitor
			 operation.
			 This object is Country Code dependent.
			 basic          The modem will blind dial and will only
					send a CONNECT message for all established
					links. All CPM is disabled.
			 extendedNoCPM  This command is the same as basic with the
					exception of the connect messages. The modem
					will send the appropiate connect response of
					CONNECT followed by the connected speed.
			 extendedDialTone   This command is the same as extendedNoCPM
					command but without blind dialing. The modem
					will send the NO DIALTONE message if dial
					tone is not detected.
			 extendedBusy   This command forces the modem to blind dial.
					The modem will not respond with the NO DIALTONE
					message while all other CPM responses are
					enabled.
			 extendedFullCPM      This command enables all CPM
					response codes and monitoring, except
					rinback detection.
			 extendedFullCPMRingback        This command enables all
					CPM response codes and monitoring, and
					includes ringback detection.
			 This object is Country Code dependent."

	::= { mdmDialerEntry 2 }

mdmParserSelection OBJECT-TYPE
	SYNTAX  INTEGER {
				at(1),
				v25async(2),
				v25HDLC(3),
				v25bisync(4),
				noparser(5)
				}
	ACCESS    read-write
	STATUS    mandatory
	DESCRIPTION
			"Command used to select the DTE parser.
			The following parsers are available: AT, v25async,
			v25HDLC, v25bisync, and no parser"
	::= { mdmDialerEntry 3 }


mdmDTRDial OBJECT-TYPE
	SYNTAX  INTEGER {
				disable(1),
				cellNumber0(2),
				cellNumber1(3),
				cellNumber2(4),
				cellNumber3(5),
				cellNumber4(6),
				cellNumber5(7),
				cellNumber6(8),
				cellNumber7(9),
				cellNumber8(10),
				cellNumber9(11),
				talkData(12)
				}

	ACCESS    read-write
	STATUS    mandatory
	DESCRIPTION
			"This command sets the modem operation upon detecting
			an Off to On transition on DTR.
			disable         Transition is ignored.
			cellNumber0     Dial number stored in cell 0.
			cellNumber1     Dial number stored in cell 1.
			cellNumber2     Dial number stored in cell 2.
			cellNumber3     Dial number stored in cell 3.
			cellNumber4     Dial number stored in cell 4.
			cellNumber5     Dial number stored in cell 5.
			cellNumber6     Dial number stored in cell 6.
			cellNumber7     Dial number stored in cell 7.
			cellNumber8     Dial number stored in cell 8.
			cellNumber9     Dial number stored in cell 9.
                        talkData        Starts a handshake."
	::= { mdmDialerEntry 4 }

mdmDialType OBJECT-TYPE
	SYNTAX  INTEGER {
				pulse(1),
				dtmf(2)
				}

	ACCESS    read-write
	STATUS    mandatory
	DESCRIPTION
			"This command selects the type of dial.
			Pulse or DTMF dial.
			 This object is Country Code dependent"

	::= { mdmDialerEntry 5 }

mdmResponseMode OBJECT-TYPE
	SYNTAX  INTEGER {
				enabled(1),
				disabled(2),
				enableInOriginate(3)
				}

	ACCESS    read-write
	STATUS    mandatory
	DESCRIPTION
			"This Command controls when to send responses.
			enabled         Requests the non-quiet mode, that is,
					to transmit result codes to the DTE
					as appropriate.
			disabled        Request the quiet mode which tells the modem
					not to send any result codes to the DTE.
			enableInOriginate       Disables Call Progress Monitor
					responses in the answer mode only. This mode
					is entered on detection of ring signal."
	::= { mdmDialerEntry 6 }

mdmResponseType OBJECT-TYPE
	SYNTAX  INTEGER {
				numeric(1),
				alpha(2)
				}

	ACCESS    read-write
	STATUS    mandatory
	DESCRIPTION
			"This command controls the type of responses.
			numeric         modem responses are in numeric code.
			alpha           modem responses are in alphabetical format."
	::= { mdmDialerEntry 7 }

mdmPauseTime OBJECT-TYPE
	SYNTAX  INTEGER (0..255)

	ACCESS    read-write
	STATUS    mandatory
	DESCRIPTION
			"This command selects the time for pause characters
			in the dial string.
			 This object is Country Code dependent."

	::= { mdmDialerEntry 8 }

mdmWaitForDialtoneTime OBJECT-TYPE
	SYNTAX  INTEGER (0..255)

	ACCESS    read-write
	STATUS    mandatory
	DESCRIPTION
			"This command selects the time for the modem to be
			looking for dialtone before disconnecting.
			 This object is Country Code dependent"

	::= { mdmDialerEntry 9  }



--*****************************************************************************
--                    PROTOCOL CONFIGURATION TABLE
--*****************************************************************************

mdmProtocolConfigTable OBJECT-TYPE
	SYNTAX  SEQUENCE OF     MdmProtocolEntry
	ACCESS    not-accessible
	STATUS    mandatory
	DESCRIPTION
			"The GDC VFAST modem Protocol configuration table."
	::= { mdm 5 }


mdmProtocolEntry OBJECT-TYPE
	SYNTAX    MdmProtocolEntry
	ACCESS    not-accessible
	STATUS    mandatory
	DESCRIPTION
			"A listing of GDC VFAST modem Protocol options."
	INDEX      { mdmProtocolIndex }
	::= { mdmProtocolConfigTable 1 }

MdmProtocolEntry      ::=
	SEQUENCE        {
			mdmProtocolIndex
				SCinstance,
			mdmCompression
				INTEGER,
			mdmAsyncProtocol
				INTEGER,
			mdmFlowControl
				INTEGER,
			mdmBreakHandling
				INTEGER,
			mdmConnAndLinkMessages
				INTEGER,
			mdmErrorCorrection
				INTEGER,
			mdmV13Mode
				INTEGER,
			mdmSyncProtocol
				INTEGER,
			mdmFrameRetransLimit
				INTEGER
			}


mdmProtocolIndex OBJECT-TYPE
	SYNTAX    SCinstance
	ACCESS    read-only
	STATUS    mandatory
	DESCRIPTION
			"A unique index for the DTE Table."
	::= { mdmProtocolEntry 1 }

mdmCompression OBJECT-TYPE
	SYNTAX  INTEGER {
				disabled(1),
				enabled(2),
				txpathonly(3),
				rxpathonly(4)
				}

	ACCESS    read-write
	STATUS    mandatory
	DESCRIPTION
			"This command controls the Compression operation when
			operating in asynchronous mode.
			disabled        No compression available.
			enabled         Compression available in both directions.
			txpathonly      Compression available in the transmitter
					path only when in V.42bis. In MNP 5 data
					compression is enabled in both directions.
			rxpathonly      Compression available in the receiver
					path only when in V.42bis. In MNP 5 data
					compression is enabled in both directions."
	::= { mdmProtocolEntry 2 }

mdmAsyncProtocol OBJECT-TYPE
	SYNTAX  INTEGER {
				wire(1),
				direct(2),
				mnpreliable(3),
				autoreliable(4),
				v42reliable(5),
				reliableLAPMorMNP(6),
				v13(7)
				}

	ACCESS    read-write
	STATUS    mandatory
	DESCRIPTION
			"This command controls the Protocols available
			at the handshake.
			wire            Options the modem to run in wire mode;
					copying characters from VF port to the DTE
					port and vice versa.
			direct          Options the modem to run in direct mode;
					where the DTE and the VF speeds must match,
					and there is no speed buffering. Direct
					mode is V.14 asynchronous mode.
			mnpreliable     This option limits error correction to
					MNP links only or hang up.
			autoreliable    Options the mode to run in autoreliable mode,
					and the modem will negotiate V.42 or alternate
					links. With no link, the modem will enter wire
					mode (speed buffering).
			v42reliable     This option limits error correction to a
					V.42 (LAPM) link or hang up.
			reliableLAPMorMNP       This option will attempt either a
					V.42 (LAPM) or MNP link and if either link
					fails, the modem will hang up.
			V.13            This option selects V.13 simulated
					controlled carrier."
	::= { mdmProtocolEntry 3 }

mdmFlowControl OBJECT-TYPE
	SYNTAX  INTEGER {
				disabled(1),
				enabled(2),
				unidirectional(3),
				bidirectional(4)
				}

	ACCESS    read-write
	STATUS    mandatory
	DESCRIPTION
			"This command controls the flow control type between
			the modem and the DTE available at the handshake.
			disabled        Disables modem to modem flow control.
			enabled         Enables bidirectional modem flow control
					based on XON/XOFF signaling. These signals
					are detected, acted on and optionally
					deleted from the data stream.
			Unidirectional  provides unidirectional flow control where
					a modem may send XON/XOFF signals to the
					remote modem, yet ignore and pass through
					any these VF received signals to its DTE.
			bidirectional   Acts the same as enabled with the addition of the
					XON/XOFF pass through option being enabled."
	::= { mdmProtocolEntry 4 }

mdmBreakHandling OBJECT-TYPE
	SYNTAX  INTEGER {
				expediteDest(1),
				expediteNonDest(2),
				nonExpediteNonDest(3),
				ignored(4),
				timedNonExpediteNonDest(5),
				timedNonExpediteNonDest2(6)
				}

	ACCESS    read-write
	STATUS    mandatory
	DESCRIPTION
			"This command controls the operation of breaks.
			expediteDest    This option will immediately transmit a
					break character for a fix time (300 msec)
					and destroy any currently bufered data.
			expediteNonDest This option is the same as expediteDest except
					all buffered data will be save.
			nonExpediteNonDest      This option will transmit a fixed
					time break character in sequence with
					the rest of the data.
			ignore          Ignores all break received from the DTE.
			timedNonExoediteNonDest This option transmits break characters
					in sequence with the rest of the data for the
					duration the DTE is transmitting this
					character.
			timedNonExpediteNonDest2 Same as above."
	::= { mdmProtocolEntry 5 }

mdmConnAndLinkMessages OBJECT-TYPE
	SYNTAX  INTEGER {
				separateMessages(1),
				bothAfterLink(2),
				microcomCompatible(3),
				connectAfterLink(4)
				}

	ACCESS    read-write
	STATUS    mandatory
	DESCRIPTION
			"This command controls when to send the protocol messages.
			separateMessages        This options the modem to send the
					standard GDC conect message upon reaching data
					mode plus V.42 message after the link
					negotiation. The connect message displays
					VF line speed.
			bothAfterLink   With this option the connect and link messages
					are send after link negotiation.
			microcomCompatible      This option is the same as bothAfterLink
					except adds a /RELIABLE at the end of the message
					when a V.42 error corrected link has been establish.
			connectAfterLink        This option sends only the connect
					message after the link negotiation. The message
					will indicate the VF rate for V.13 and V.14
					connections and the DTE rate for all other
					connections."
	::= { mdmProtocolEntry 6 }

mdmErrorCorrection OBJECT-TYPE
	SYNTAX  INTEGER {
				noBuffer(1),
				bufferRxData(2),
				fallbackWithFallbackChar(3),
				fallbackV14Buffer(4),
				fallbackV14WithFallbackChar(5)
				}

	ACCESS    read-write
	STATUS    mandatory
	DESCRIPTION
			"This command controls how the data is handled
			when running a protocol.
			noBuffer        This option discards all data coming in from
					the modem until the receiver modem sends a
					PROTOCOL: NONE message to the DTE at which
					time data will be passed through.
			bufferRxData    This option will buffer received data
					(up to 200 characters) until the
					PROTOCOL: NONE message is sent. The buffered
					data will be passed through to the DTE.
					The modem  will fall back to wire mode
					if more than 200 characters have been
					received prior to establishing an error
					correction link.
			fallbackWithFallbackChar        This command discards all
					incoming data until two consecutive fallback
					characters are detected at which point the
					receiver modem falls back to wire mode.
					One fallback character is passed through to
					its DTE as  data.
			fallbackV14Buffer       This option acts the same as bufferRxData
					except with no link it falls back to V.14
					(direct)mode.
		       fallbackV14WithFallbackChar      This option acts as
					fallbackWithFallbackChar except it also
					falls back to V.14 (direct) mode."
	::= { mdmProtocolEntry 7 }

mdmV13Mode OBJECT-TYPE
	SYNTAX  INTEGER {
				bidirectional(1),
				txEnable(2),
				rxEnable(3)
				}

	ACCESS    read-write
	STATUS    mandatory
	DESCRIPTION
			"This command controls the V13 function.
			bidirectional   Selects bidirectional V.13 simulated
					controlled carrier.
			txEnable        Selects V.13 Tx side enabled.
			rxEnable        Selects V.13 RX side enabled."
	::= { mdmProtocolEntry 8 }

mdmSyncProtocol OBJECT-TYPE
	SYNTAX  INTEGER {
				normalsync(1),
				v13sync(2)
				}

	ACCESS    read-write
	STATUS    mandatory
	DESCRIPTION
			"This command controls the type of sync protocol.
			normalsync      Selects normal synchronous mode.
			v13sync         Selects synchronous V13 mode."
	::= { mdmProtocolEntry 9 }

mdmFrameRetransLimit	OBJECT-TYPE
	SYNTAX  INTEGER (0..255)
	ACCESS    read-write
	STATUS    mandatory
	DESCRIPTION
			"This command limits the number of times the modem will
			 retransmit a frame while in an error correction
			 connection."

	::= { mdmProtocolEntry 10 }

--*****************************************************************************
--                    PRIVATE LINE CONFIGURATION TABLE
--*****************************************************************************

mdmPrivateLineConfigTable OBJECT-TYPE
	SYNTAX  SEQUENCE OF     MdmPrivateLineEntry
	ACCESS    not-accessible
	STATUS    mandatory
	DESCRIPTION
			"The GDC VFAST modem Private Line configuration table."
	::= { mdm 6 }


mdmPrivateLineEntry OBJECT-TYPE
	SYNTAX    MdmPrivateLineEntry
	ACCESS    not-accessible
	STATUS    mandatory
	DESCRIPTION
			"A listing of GDC VFAST Private Line
			configurations options."
	INDEX      { mdmPrivateLineIndex }
	::= { mdmPrivateLineConfigTable 1 }

MdmPrivateLineEntry      ::=
	SEQUENCE        {
			mdmPrivateLineIndex
				SCinstance,
			mdmPrivateLineTxLevel
				INTEGER,
			mdmPrivateLineHandshakeMode
				INTEGER,
			mdmAutoDialRestoral
				INTEGER,
			mdmPrivateLineDownTime
				INTEGER,
			mdmDBUtoPLLookbackTime
				INTEGER
			}


mdmPrivateLineIndex OBJECT-TYPE
	SYNTAX    SCinstance
	ACCESS    read-only
	STATUS    mandatory
	DESCRIPTION
			"A unique index for the Private Line
			Configurations Table."
	::= { mdmPrivateLineEntry 1 }

mdmPrivateLineTxLevel OBJECT-TYPE
	SYNTAX  INTEGER {
				dBm0(1),
				dBm1(2),
				dBm2(3),
				dBm3(4),
				dBm4(5),
				dBm5(6),
				dBm6(7),
				dBm7(8),
				dBm8(9),
				dBm9(10),
				dBm10(11),
				dBm11(12),
				dBm12(13),
				dBm13(14),
				dBm14(15),
				dBm15(16)
				}

	ACCESS    read-write
	STATUS    mandatory
	DESCRIPTION
			"This command selects the transmit level during
			 Private Line operation.
			 This object is Country Code dependent"

	::= { mdmPrivateLineEntry 2 }

mdmPrivateLineHandshakeMode OBJECT-TYPE
	SYNTAX  INTEGER {
				gdcVfastonly(1),
				v32bisonly(2),
				v32only(3)
				}

	ACCESS    read-write
	STATUS    mandatory
	DESCRIPTION
			"This command selects the Private Line Handshake modes"
	::= { mdmPrivateLineEntry 3 }

mdmAutoDialRestoral OBJECT-TYPE
	SYNTAX  INTEGER {
				disabled(1),
				enableWithEndOfSession(2),
				enableWithoutEndOfSession(3)
				}

	ACCESS    read-write
	STATUS    mandatory
	DESCRIPTION
			"This command selects the options for Auto Dial
			Restoral when the modem is in private line mode.
			disabled        No Auto Dial Restoral allowed.
			enableWithEndOfSession	     Enable Auto Dial Restoral
					with line failure indicator.
			enableWithoutEnOfSession	 Enable Auto Dial Restoral
					without line failure indicator."
	::= { mdmPrivateLineEntry 4 }

mdmPrivateLineDownTime OBJECT-TYPE
	SYNTAX  INTEGER (0..255)

	ACCESS    read-write
	STATUS    mandatory
	DESCRIPTION
			"This command selects for how long the
			Private Line must be lost before going to
			Dial Back Up mode"
	::= { mdmPrivateLineEntry 5 }

mdmDBUtoPLLookbackTime OBJECT-TYPE
	SYNTAX  INTEGER (0..255)

	ACCESS    read-write
	STATUS    mandatory
	DESCRIPTION
			"This command selects the time for how often the modem
			must lookback for Private Line restoral. The units are
			in 10 minutes. Valid range from 0 to 255. When the value 0
			is selected this option is disabled."
	::= { mdmPrivateLineEntry 6 }



--*****************************************************************************
--                    ALARMS SCAN TABLE
--*****************************************************************************

mdmAlarmScanTable OBJECT-TYPE
	SYNTAX  SEQUENCE OF MdmAlarmScanEntry
	ACCESS  not-accessible
	STATUS  mandatory
	DESCRIPTION
			"The GDC VFAST alarm Scan Table."
	::= { mdm 7 }

mdmAlarmScanEntry OBJECT-TYPE
	SYNTAX  MdmAlarmScanEntry
	ACCESS  not-accessible
	STATUS  mandatory
	DESCRIPTION
			"An entry in the GDC VFAST alarm table."
	INDEX   { mdmAlarmScanIndex }
	::= { mdmAlarmScanTable 1 }

MdmAlarmScanEntry ::=
	SEQUENCE {
		  mdmAlarmScanIndex
			 SCinstance,
		  mdmAlarmScan
			 OCTET STRING,
		  mdmResetSelfPowerBit
			 INTEGER
		  }

mdmAlarmScanIndex OBJECT-TYPE
	SYNTAX  SCinstance
	ACCESS  read-only
	STATUS  mandatory
	DESCRIPTION
	       "This object is the identifier of the VFAST alarm table."
	::= { mdmAlarmScanEntry 1 }


mdmAlarmScan OBJECT-TYPE
	SYNTAX  OCTET STRING (SIZE (8))
	ACCESS  read-only
	STATUS  mandatory
	DESCRIPTION   "Reads the alarm scan. There are 8 bytes.

	byte 1 bit 4 (bit 1.4) No DTR signal

	bit 2.0 No TXD Transitions
	bit 2.2 No RXD Transitions
	bit 2.3 Modem Fallback
	bit 2.6 Modem on Dial Back Up

	bit 3.2 Power Up

	bit 4.0 Poor Signal Quality

	bit 5.3 DCD Loss

	bit 6.0-6 no alarms

	bit 7.0 Modem Configuration Checksum Error
	bit 7.1 Call Failed
	bit 7.2 Call Length Exceeded Maximum Allowed
	bit 7.3 Retrain Count Exceeded Threshold
	bit 7.4 Ring No Answer
	bit 7.5 Remote Configuration session active
	bit 7.6 Test timeout

	bit 8.0-6 no alarms"

	       ::= { mdmAlarmScanEntry 2 }


mdmResetSelfPowerBit OBJECT-TYPE
	SYNTAX  INTEGER  {
				reset(1)
				}
	ACCESS  write-only
	STATUS  mandatory
	DESCRIPTION
		"This resets the modem power up alarm."
	::= { mdmAlarmScanEntry 3 }




--*****************************************************************************
--                    ALARMS MASK TABLE
--*****************************************************************************

mdmMaskAlarmTable OBJECT-TYPE
	SYNTAX  SEQUENCE OF MdmMaskAlarmEntry
	ACCESS  not-accessible
	STATUS  mandatory
	DESCRIPTION
			"The GDC VFAST alarm Mask Table."
	::= { mdm 8 }

mdmMaskAlarmEntry OBJECT-TYPE
	SYNTAX  MdmMaskAlarmEntry
	ACCESS  not-accessible
	STATUS  mandatory
	DESCRIPTION
			"An entry in the GDC VFAST alarm mask table."
	INDEX   { mdmMaskAlarmIndex }
	::= { mdmMaskAlarmTable 1 }

MdmMaskAlarmEntry ::=
	SEQUENCE {
			mdmMaskAlarmIndex
				SCinstance,
			mdmDTRLoss
				INTEGER,
			mdmFallback
				INTEGER,
			mdmRxdTran
				INTEGER,
			mdmTxdTran
				INTEGER,
			mdmDCDLoss
				INTEGER,
			mdmRingNoAnswer
				INTEGER,
			mdmRetrain
				INTEGER,
			mdmCallLength
				INTEGER,
			mdmCallFail
				INTEGER,
			mdmConfigErr
				INTEGER,
			mdmSignalQuality
				INTEGER,
			mdmOnDBU
				INTEGER,
			mdmRemoteConfigMask
				INTEGER,
			mdmTestTimeout
				INTEGER
		  }

mdmMaskAlarmIndex OBJECT-TYPE
	SYNTAX  SCinstance
	ACCESS  read-only
	STATUS  mandatory
	DESCRIPTION
	       "This object is the index of the VFAST alarm mask table."
	::= { mdmMaskAlarmEntry 1 }

mdmDTRLoss OBJECT-TYPE
	SYNTAX    INTEGER {
				mask(1),
				unmask(2)
				}
	ACCESS          read-write
	STATUS    mandatory
	DESCRIPTION
			"Mask for loss of DTR alarm."
	::= { mdmMaskAlarmEntry 2 }


mdmFallback OBJECT-TYPE
	SYNTAX    INTEGER {
				mask(1),
				unmask(2)
				}
	ACCESS    read-write
	STATUS    mandatory
	DESCRIPTION
			"Mask for fallback alarm."
	::= { mdmMaskAlarmEntry 3 }


mdmRxdTran OBJECT-TYPE
	SYNTAX    INTEGER {
				mask(1),
				unmask(2)
				}
	ACCESS          read-write
	STATUS    mandatory
	DESCRIPTION
			"Mask for Receive data transitions alarm."
	::= { mdmMaskAlarmEntry 4 }


mdmTxdTran OBJECT-TYPE
	SYNTAX    INTEGER {
				mask(1),
				unmask(2)
				}
	ACCESS          read-write
	STATUS    mandatory
	DESCRIPTION
			"Mask for transmit data transitions alarm."
	::= { mdmMaskAlarmEntry 5 }


mdmDCDLoss OBJECT-TYPE
	SYNTAX    INTEGER {
				mask(1),
				unmask(2)
				}
	ACCESS          read-write
	STATUS    mandatory
	DESCRIPTION
			"Mask for loss of DCD alarm."
	::= { mdmMaskAlarmEntry 6 }


mdmRingNoAnswer OBJECT-TYPE
	SYNTAX    INTEGER {
				mask(1),
				unmask(2)
				}
	ACCESS          read-write
	STATUS    mandatory
	DESCRIPTION
			"Mask for Rings no Answer alarm."
	::= { mdmMaskAlarmEntry 7 }


mdmRetrain OBJECT-TYPE
	SYNTAX    INTEGER {
				mask(1),
				unmask(2)
				}
	ACCESS          read-write
	STATUS    mandatory
	DESCRIPTION
			"Mask for Retrains count exceeded alarm."
	::= { mdmMaskAlarmEntry 8 }


mdmCallLength OBJECT-TYPE
	SYNTAX    INTEGER {
				mask(1),
				unmask(2)
				}
	ACCESS          read-write
	STATUS    mandatory
	DESCRIPTION
			"Mask for Call Length exceeded alarm."
	::= { mdmMaskAlarmEntry 9 }


mdmCallFail OBJECT-TYPE
	SYNTAX    INTEGER {
				mask(1),
				unmask(2)
				}
	ACCESS          read-write
	STATUS    mandatory
	DESCRIPTION
			"Mask for Call Failed alarm."
	::= { mdmMaskAlarmEntry 10 }

mdmConfigErr OBJECT-TYPE
	SYNTAX    INTEGER {
				mask(1),
				unmask(2)
				}
	ACCESS          read-write
	STATUS    mandatory
	DESCRIPTION
			"Mask for Configuration checksum error alarm."
	::= { mdmMaskAlarmEntry 11 }


mdmSignalQuality OBJECT-TYPE
	SYNTAX    INTEGER {
				mask(1),
				unmask(2)
				}
	ACCESS          read-write
	STATUS    mandatory
	DESCRIPTION
			"Mask for Poor Signal Quality alarm."
	::= { mdmMaskAlarmEntry 12 }

mdmOnDBU         OBJECT-TYPE
	SYNTAX    INTEGER {
				mask(1),
				unmask(2)
				}
	ACCESS          read-write
	STATUS    mandatory
	DESCRIPTION
			"Mask for On Dial Backup alarm."
	::= { mdmMaskAlarmEntry 13 }


mdmRemoteConfigMask         OBJECT-TYPE
	SYNTAX    INTEGER {
				mask(1),
				unmask(2)
				}
	ACCESS  read-write
	STATUS    mandatory
	DESCRIPTION
			"Mask for Remote Configuration."
	::= { mdmMaskAlarmEntry 14 }


mdmTestTimeout         OBJECT-TYPE
	SYNTAX    INTEGER {
				mask(1),
				unmask(2)
				}
	ACCESS          read-write
	STATUS    mandatory
	DESCRIPTION
			"Mask for Test timeout."
	::= { mdmMaskAlarmEntry 15 }

--*****************************************************************************
--                    SET/READ THRESHOLDS TABLE
--*****************************************************************************

mdmThresholdsTable OBJECT-TYPE
	SYNTAX  SEQUENCE OF MdmThresholdsEntry
	ACCESS  not-accessible
	STATUS  mandatory
	DESCRIPTION
			"The GDC VFAST Alarm Thresholds Table."
	::= { mdm 9 }

mdmThresholdsEntry OBJECT-TYPE
	SYNTAX  MdmThresholdsEntry
	ACCESS  not-accessible
	STATUS  mandatory
	DESCRIPTION
			"An entry in the GDC VFAST Alarm Thresholds table."
	INDEX   { mdmThresholdsIndex }
	::= { mdmThresholdsTable 1 }

MdmThresholdsEntry ::=
	SEQUENCE {
		  mdmThresholdsIndex
			 SCinstance,
		  mdmCallDuration
			 TimeTicks,
		  mdmRetrainThreshold
			 INTEGER
		  }

mdmThresholdsIndex OBJECT-TYPE
	SYNTAX  SCinstance
	ACCESS  read-only
	STATUS  mandatory
	DESCRIPTION
	       "This object is the identifier of the Thresholds table."
	::= { mdmThresholdsEntry 1 }

mdmCallDuration OBJECT-TYPE
	SYNTAX  TimeTicks
	ACCESS  read-write
	STATUS  mandatory
	DESCRIPTION
		"This option selects the call duration threshold for alarm."

	::= { mdmThresholdsEntry 2 }


mdmRetrainThreshold OBJECT-TYPE
	SYNTAX  INTEGER (0..65535)
	ACCESS  read-write
	STATUS  mandatory
	DESCRIPTION
		"This option selects the number of retrains threshold for
		 alarm."

	::= { mdmThresholdsEntry 3 }

--*****************************************************************************
--                    STATUS TABLE
--*****************************************************************************

mdmStatusTable OBJECT-TYPE
	SYNTAX  SEQUENCE OF MdmStatusEntry
	ACCESS  not-accessible
	STATUS  mandatory
	DESCRIPTION
			"The GDC VFAST Status Table."
	::= { mdm 10 }

mdmStatusEntry OBJECT-TYPE
	SYNTAX  MdmStatusEntry
	ACCESS  not-accessible
	STATUS  mandatory
	DESCRIPTION
			"An entry in the GDC VFAST Status table."
	INDEX   { mdmStatusIndex }
	::= { mdmStatusTable 1 }

MdmStatusEntry ::=
	SEQUENCE {
		  mdmStatusIndex
			 SCinstance,
		  mdmPLLookbackStatus
			 INTEGER,
		  mdmAutoDialRestoralStatus
			 INTEGER,
		  mdmTXDtransitions
			 INTEGER,
		  mdmRXDtransitions
			 INTEGER,
		  mdmRTStransitions
			 INTEGER,
		  mdmDTRtransitions
			 INTEGER,
		  mdmDCDtransitions
			 INTEGER,
		  mdmTXCLKtransitions
			 INTEGER,
		  mdmDTR
			 INTEGER,
		  mdmCTS
			 INTEGER,
		  mdmDSR
			 INTEGER,
		  mdmDCD
			 INTEGER,
		  mdmSQM
			 INTEGER,
		  mdmRTS
			 INTEGER,
		  mdmSwitchedPrivate
			 INTEGER
		  }

mdmStatusIndex OBJECT-TYPE
	SYNTAX  SCinstance
	ACCESS  read-only
	STATUS  mandatory
	DESCRIPTION
	       "This object is the identifier of the VFAST Status table."
	::= { mdmStatusEntry 1 }

mdmPLLookbackStatus OBJECT-TYPE
	SYNTAX  INTEGER {
			inactive(1),
			active(2)
			}
	ACCESS  read-only
	STATUS  mandatory
	DESCRIPTION

		" Shows the status of Private Line lookback. "
	::= { mdmStatusEntry 2 }

mdmAutoDialRestoralStatus OBJECT-TYPE
	SYNTAX  INTEGER {
			inactive(1),
			active(2)
			}
	ACCESS  read-only
	STATUS  mandatory
	DESCRIPTION

		" Shows the status of Auto Dial Restoral. "
	::= { mdmStatusEntry 3 }


mdmTXDtransitions       OBJECT-TYPE
	SYNTAX  INTEGER {
			notransition(1),
			transition(2)
			}
	ACCESS  read-only
	STATUS  mandatory
	DESCRIPTION

		" EIA Status of TXD data transitions. "
	::= { mdmStatusEntry 4 }

mdmRXDtransitions       OBJECT-TYPE
	SYNTAX  INTEGER {
			notransition(1),
			transition(2)
			}
	ACCESS  read-only
	STATUS  mandatory
	DESCRIPTION

		" EIA Status of RXD data transitions. "
	::= { mdmStatusEntry 5 }

mdmRTStransitions       OBJECT-TYPE
	SYNTAX  INTEGER {
			notransition(1),
			transition(2)
			}
	ACCESS  read-only
	STATUS  mandatory
	DESCRIPTION

		" EIA Status of Request to Send transitions. "
	::= { mdmStatusEntry 6 }

mdmDTRtransitions       OBJECT-TYPE
	SYNTAX  INTEGER {
			notransition(1),
			transition(2)
			}
	ACCESS  read-only
	STATUS  mandatory
	DESCRIPTION

		" EIA Status of Data Terminal Ready transitions. "
	::= { mdmStatusEntry 7 }

mdmDCDtransitions       OBJECT-TYPE
	SYNTAX  INTEGER {
			notransition(1),
			transition(2)
			}
	ACCESS  read-only
	STATUS  mandatory
	DESCRIPTION

		" EIA Status of Carrier Detect transitions. "
	::= { mdmStatusEntry 8 }

mdmTXCLKtransitions     OBJECT-TYPE
	SYNTAX  INTEGER {
			notransition(1),
			transition(2)
			}
	ACCESS  read-only
	STATUS  mandatory
	DESCRIPTION

		" EIA Status Transmit Clock transitions. "
	::= { mdmStatusEntry 9 }

mdmDTR                  OBJECT-TYPE
	SYNTAX  INTEGER {
			off(1),
			on(2)
			}
	ACCESS  read-only
	STATUS  mandatory
	DESCRIPTION

		" EIA Status of Data Terminal Ready. "
	::= { mdmStatusEntry 10 }

mdmCTS                  OBJECT-TYPE
	SYNTAX  INTEGER {
			off(1),
			on(2)
			}
	ACCESS  read-only
	STATUS  mandatory
	DESCRIPTION

		" EIA Status of Clear to Send. "
	::= { mdmStatusEntry 11 }

mdmDSR                  OBJECT-TYPE
	SYNTAX  INTEGER {
			off(1),
			on(2)
			}
	ACCESS  read-only
	STATUS  mandatory
	DESCRIPTION

		" EIA Status of Data Set Ready. "
	::= { mdmStatusEntry 12 }

mdmDCD                  OBJECT-TYPE
	SYNTAX  INTEGER {
			off(1),
			on(2)
			}
	ACCESS  read-only
	STATUS  mandatory
	DESCRIPTION

		" EIA Status of Carrier  Detect. "
	::= { mdmStatusEntry 13 }

mdmSQM                  OBJECT-TYPE
	SYNTAX  INTEGER {
			off(1),
			on(2)
			}
	ACCESS  read-only
	STATUS  mandatory
	DESCRIPTION

		" EIA Status of Signal Quality. "
	::= { mdmStatusEntry 14 }

mdmRTS			OBJECT-TYPE
	SYNTAX  INTEGER {
			off(1),
			on(2)
			}
	ACCESS  read-only
	STATUS	mandatory
	DESCRIPTION

		" EIA Status of Request to Send. "
	::= { mdmStatusEntry 15 }

mdmSwitchedPrivate	OBJECT-TYPE
	SYNTAX	INTEGER {
			switchedNetwork(1),
			privateLine(2)
			}
	ACCESS  read-only
	STATUS	mandatory
	DESCRIPTION

		"Switched Network or Private Line configuration setting."
	::= { mdmStatusEntry 16 }

--*****************************************************************************
--                    MODEM CONTROL TABLE
--*****************************************************************************

mdmControlTable OBJECT-TYPE
	SYNTAX  SEQUENCE OF MdmControlEntry
	ACCESS  not-accessible
	STATUS  mandatory
	DESCRIPTION
			"The GDC VFAST Control Table."
	::= { mdm 11 }

mdmControlEntry OBJECT-TYPE
	SYNTAX  MdmControlEntry
	ACCESS  not-accessible
	STATUS  mandatory
	DESCRIPTION
			"An entry in the GDC VFAST Control table."
	INDEX   { mdmControlIndex }
	::= { mdmControlTable 1 }

MdmControlEntry ::=
	SEQUENCE {
		  mdmControlIndex
			 SCinstance,
		  mdmSoftReset
			 INTEGER,
		  mdmFrontPanel
			 INTEGER,
		  mdmMakeClearBusy
			 INTEGER,
		  mdmPLTalkData
			 INTEGER
		  }

mdmControlIndex OBJECT-TYPE
	SYNTAX  SCinstance
	ACCESS  read-only
	STATUS  mandatory
	DESCRIPTION
	       "This object is the identifier of the VFAST Control table."
	::= { mdmControlEntry 1 }


mdmSoftReset OBJECT-TYPE
	SYNTAX  INTEGER  {
				reset(1)
				}
	ACCESS  write-only
	STATUS  mandatory
	DESCRIPTION
		"Forces a soft reset on the modem.
		Not applicable when the modem is in Remote Configuration session."
	::= { mdmControlEntry 2 }


mdmFrontPanel OBJECT-TYPE
	SYNTAX  INTEGER  {
				inhibit(1),
				enabled(2)
				}
	ACCESS    read-write
	STATUS    mandatory
	DESCRIPTION
			"This command controls the functionality
			of the front panel Switches."
	::= { mdmControlEntry 3 }


mdmMakeClearBusy OBJECT-TYPE
	SYNTAX  INTEGER {
				onHook(1),
				offHook(2)
				}
	ACCESS    read-write
	STATUS    mandatory
	DESCRIPTION
			"Command used to control the Offhook relay
			to make busy or clear the VF line.
		Not applicable when the modem is in Remote Configuration session."
	::= { mdmControlEntry 4 }

mdmPLTalkData OBJECT-TYPE
	SYNTAX	INTEGER {
				idle(1),
				data(2)
				}
	ACCESS	  write-only
	STATUS    mandatory
	DESCRIPTION
			"Object is used to force the modem to the idle or data
			 state while configured for Private line. Idle, allows
			 the modem to activate the private line option.
			 Data, forces the modem to retrain."
	::= { mdmControlEntry 5 }
--*****************************************************************************
--                    WHAT ARE YOU TABLE
--*****************************************************************************

mdmWhatAreYouTable OBJECT-TYPE
	SYNTAX  SEQUENCE OF MdmWhatAreYouEntry
	ACCESS  not-accessible
	STATUS  mandatory
	DESCRIPTION
			"The GDC VFAST What Are You Table."
	::= { mdm 12 }

mdmWhatAreYouEntry OBJECT-TYPE
	SYNTAX  MdmWhatAreYouEntry
	ACCESS  not-accessible
	STATUS  mandatory
	DESCRIPTION
			"An entry in the GDC VFAST What Are You table."
	INDEX   { mdmWhatAreYouIndex }
	::= { mdmWhatAreYouTable 1 }

MdmWhatAreYouEntry ::=
	SEQUENCE {
		  mdmWhatAreYouIndex
			 SCinstance,
		  mdmVFCard
			 INTEGER,
		  mdmDTECard
			 INTEGER,
		  mdmProductCode
			 INTEGER,
		  mdmCodeRev
			 DisplayString,
		  mdmBootRev
			 DisplayString,
		  mdmCountryCode
			 DisplayString
		  }

mdmWhatAreYouIndex OBJECT-TYPE
	SYNTAX  SCinstance
	ACCESS  read-only
	STATUS  mandatory
	DESCRIPTION
	       "This object is the identifier of the VFAST What Are You table."
	::= { mdmWhatAreYouEntry 1 }


mdmVFCard OBJECT-TYPE
	SYNTAX  INTEGER {
			domestic(1),
			cardA(65),
			cardB(66),
			cardC(67),
			cardD(68),
			cardE(69),
			cardF(70),
			cardG(71),
			cardH(72),
			cardJ(74),
			cardK(75),
			cardL(76),
			cardM(77),
			cardN(78),
			cardP(80),
			cardR(82),
			noCard(127)
			}
	ACCESS  read-only
	STATUS  mandatory
	DESCRIPTION
		"This function returns the value the VF card attached to
		the modem."
	::= { mdmWhatAreYouEntry 2 }

mdmDTECard OBJECT-TYPE
	SYNTAX  INTEGER {
			v35(1),
			eia530(2),
			eia232(3)
			}
	ACCESS  read-only
	STATUS  mandatory
	DESCRIPTION
		"This function returns the type of DTE card attached to
		the modem."
	::= { mdmWhatAreYouEntry 3 }

mdmProductCode OBJECT-TYPE
	SYNTAX  INTEGER
			{
			dmsVfast (23)
			}
	ACCESS  read-only
	STATUS  mandatory
	DESCRIPTION
		"This identifies what type of device this is."
	::= { mdmWhatAreYouEntry 4 }

mdmCodeRev OBJECT-TYPE
	SYNTAX  DisplayString (SIZE (2))
	ACCESS  read-only
	STATUS  mandatory
	DESCRIPTION
		"This function returns the firmware code level.
		example 01 - A-
			02 - B-"
	::= { mdmWhatAreYouEntry 5 }

mdmBootRev OBJECT-TYPE
	SYNTAX  DisplayString (SIZE (2))
	ACCESS  read-only
	STATUS  mandatory
	DESCRIPTION
		"This function returns the boot firmware level.
		example 01 - A-
			02 - B-"
	::= { mdmWhatAreYouEntry 6 }

mdmCountryCode OBJECT-TYPE
	SYNTAX  DisplayString (SIZE (3))
	ACCESS  read-only
	STATUS  mandatory
	DESCRIPTION
		"This function returns the country code number in three bytes.
		 Each byte is the hex value of an decimal number.
		Example    hex 30,30,31  is the country code of USA 001
			       30,34,34  is the country code of UK 044 "
	::= { mdmWhatAreYouEntry 7 }



--*****************************************************************************
--                    DIAGNOSTICS TABLE
--*****************************************************************************

mdmDiagnosticTable OBJECT-TYPE
	SYNTAX  SEQUENCE OF     MdmDiagnosticEntry
	ACCESS    not-accessible
	STATUS    mandatory
	DESCRIPTION
			"The GDC VFAST diagnostics table.

		Not applicable when the modem is in Remote Configuration session."
	::= { mdm 13 }


mdmDiagnosticEntry OBJECT-TYPE
	SYNTAX    MdmDiagnosticEntry
	ACCESS    not-accessible
	STATUS    mandatory
	DESCRIPTION
			"A listing of GDC VFAST diagnostic tests"
	INDEX      { mdmDiagnosticIndex }
	::= { mdmDiagnosticTable 1 }

MdmDiagnosticEntry      ::=
	SEQUENCE        {
			mdmDiagnosticIndex
				SCinstance,
			mdmDiagnosticTest
				INTEGER,
			mdmDiagnosticResults
				INTEGER,
			mdmDiagnosticStatus
				INTEGER,
			mdmTestStatus
				INTEGER,
			mdmTestDuration
				TimeTicks
			}

mdmDiagnosticIndex OBJECT-TYPE
	SYNTAX    SCinstance
	ACCESS    read-only
	STATUS    mandatory
	DESCRIPTION
			"A unique index for the Diagnostic Table."
	::= { mdmDiagnosticEntry 1 }

mdmDiagnosticTest OBJECT-TYPE
	SYNTAX  INTEGER {
				terminateTest(1),
				analoop(2),
				analoopSelfTest(3),
				remoteDigitalLoop(4),
				remoteDigitalLoopSelfTest(5),
				selfTest(6),
				digitalLoop(7)
				}

	ACCESS    write-only
	STATUS    mandatory
	DESCRIPTION
			"This function selects the test.
		Not applicable when the modem is in Remote Configuration session."
	::= { mdmDiagnosticEntry 2 }

mdmDiagnosticResults OBJECT-TYPE
	SYNTAX  INTEGER (0..65535)
	ACCESS    read-only
	STATUS    mandatory
	DESCRIPTION
			"This function reads the test results in bit errors."
	::= { mdmDiagnosticEntry 3 }

mdmDiagnosticStatus OBJECT-TYPE
	SYNTAX  INTEGER {
			rmtDigLpHsk(1),
			inboundRmtDigLp(2),
			rmtDigLp(4),
			localDigLp(8),
			analoopHsk(16),
			analoop(32),
			selftest(64),
			rmtDigLpSelftest(68),
			analoopSelftest(96),
			notInTest(97)
		}
	ACCESS  read-only
	STATUS  mandatory
	DESCRIPTION

		" Diagnostic status of which test is running.
		Not applicable when the modem is in Remote Configuration session."
	::= { mdmDiagnosticEntry 4 }

mdmTestStatus OBJECT-TYPE
	SYNTAX  INTEGER {
			canNotBeDone(4),
			terminated(8),
			timedout(16),
			noPrevStatus(17)
			}
	ACCESS  read-only
	STATUS  mandatory
	DESCRIPTION

		" Test Status
		canNotBeDone - means test can not be done at this time
		terminated   - means the test was terminated,
			       could be terminated via the front panel
		timedout     - the modem's test timer expired
		noPrevStatus - means that no status is currently available

		Not applicable when the modem is in Remote Configuration session."
	::= { mdmDiagnosticEntry 5 }

mdmTestDuration OBJECT-TYPE
	SYNTAX  TimeTicks
	ACCESS  read-only
	STATUS  mandatory
	DESCRIPTION

		" Time of modem in test, counted in timeticks.
		Not applicable when the modem is in Remote Configuration session."
	::= { mdmDiagnosticEntry 6 }


--*****************************************************************************
--                    MODEM DIALING FUNCTION TABLE
--*****************************************************************************
mdmDialingFunctionTable OBJECT-TYPE
	SYNTAX  SEQUENCE OF     MdmDialingFunctionEntry
	ACCESS          not-accessible
	STATUS          mandatory
	DESCRIPTION
			"The GDC VFAST modem dialing function table."
	::= { mdm 14 }

mdmDialingFunctionEntry OBJECT-TYPE
	SYNTAX          MdmDialingFunctionEntry
	ACCESS          not-accessible
	STATUS          mandatory
	DESCRIPTION
			"A listing of GDC VFAST modem dialing function
			 parameters."

	INDEX      { mdmDialFunctionIndex }
	::= { mdmDialingFunctionTable 1 }

MdmDialingFunctionEntry ::=
	SEQUENCE        {
			mdmDialFunctionIndex
				SCinstance,
			mdmManualDial
				DisplayString,
			mdmTerminateCall
				INTEGER,
			mdmDialStatus
				INTEGER,
			mdmCallProgressStatus
				INTEGER
			}

mdmDialFunctionIndex OBJECT-TYPE
	SYNTAX    SCinstance
	ACCESS    read-only
	STATUS    mandatory
	DESCRIPTION
			"A unique index for the Dialing Function Table."
	::= { mdmDialingFunctionEntry 1 }


mdmManualDial OBJECT-TYPE
	SYNTAX    DisplayString (SIZE(1..36))
	ACCESS    write-only
	STATUS    mandatory
	DESCRIPTION
			"Command to instruct the modem to dial the
			 following number, n.
			 Not applicable when modem in remote configuration session."
	::= { mdmDialingFunctionEntry 2 }


mdmTerminateCall OBJECT-TYPE
	SYNTAX    INTEGER       {
				goOnhook(1)
				}
	ACCESS    write-only
	STATUS    mandatory
	DESCRIPTION
			"Command to instruct the mode to disconnect the
			 call and go to idle."
	::= { mdmDialingFunctionEntry 3 }

mdmDialStatus OBJECT-TYPE
	SYNTAX  INTEGER {
			disconnect(1),
			idle(2),
			dial(4),
			training(8),
			retrain(16),
			data(32),
			inTest(33)
		}
	ACCESS  read-only
	STATUS  mandatory
	DESCRIPTION

		" Dial Status information
		  'inTest' means the modem is currently in a test mode."
	::= { mdmDialingFunctionEntry 4 }

mdmCallProgressStatus OBJECT-TYPE
	SYNTAX  INTEGER {
			ringback(1),
			incomingRing(2),
			busy(4),
			noAnswer(8),
			ringAndNoAnswer(10),
			noCarrier(16),
			ringbackNoCarrier(17),
			ringNoCarrier(18),
			ringNoCarrier2(19),
			noDialtone(32),
			noLoopCurrent(64),
			unobtainableNumber(128),
			connect(256),
			connectRingback(257),
			connectIncomingRing(258),
			connectIncomingRing2(259),
			noPrevStatus(260)
			}
	ACCESS  read-only
	STATUS  mandatory
	DESCRIPTION

		" Call Progress Status "
	::= { mdmDialingFunctionEntry 5}

--*****************************************************************************
--                    MODEM CELLS FUNCTION TABLE
--*****************************************************************************
mdmDialingCellsFunctionTable OBJECT-TYPE
	SYNTAX  SEQUENCE OF     MdmDialingCellsFunctionEntry
	ACCESS          not-accessible
	STATUS          mandatory
	DESCRIPTION
			"The GDC VFAST modem dialing cells function table."
	::= { mdm 15 }


mdmDialingCellsFunctionEntry OBJECT-TYPE
	SYNTAX    MdmDialingCellsFunctionEntry
	ACCESS          not-accessible
	STATUS          mandatory
	DESCRIPTION
			"A listing of GDC VFAST modem dialing cells function
			 parameters."
	INDEX      { mdmDialCellFunctionIndex, mdmCellNumber }
	::= { mdmDialingCellsFunctionTable 1 }


MdmDialingCellsFunctionEntry ::=
	SEQUENCE        {
			mdmDialCellFunctionIndex
				SCinstance,
			mdmCellNumber
				INTEGER,
			mdmDial
				INTEGER,
			mdmCellPhoneNumber
				DisplayString,
			mdmTerminateCellCall
				INTEGER
			}


mdmDialCellFunctionIndex OBJECT-TYPE
	SYNTAX    SCinstance
	ACCESS    read-only
	STATUS    mandatory
	DESCRIPTION
			"A unique index for the Dialing Function Table.
			 Not applicable when modem in remote configuration session."
	::= { mdmDialingCellsFunctionEntry 1 }


mdmCellNumber OBJECT-TYPE
	SYNTAX    INTEGER
	ACCESS    read-only
	STATUS    mandatory
	DESCRIPTION
			"Command to instruct the modem to attempt
			 dialing the phone number stored in Cell n.
			 Not applicable when modem in remote configuration session."
	::= { mdmDialingCellsFunctionEntry 2 }


mdmDial          OBJECT-TYPE
	SYNTAX    INTEGER {
				goDial(1)
				}
	ACCESS    write-only
	STATUS    mandatory
	DESCRIPTION
			" Command modem to dial.
			 Not applicable when modem in remote configuration session."

	::= { mdmDialingCellsFunctionEntry 3 }


mdmCellPhoneNumber OBJECT-TYPE
	SYNTAX    DisplayString (SIZE(1..36))
	ACCESS    read-write
	STATUS    mandatory
	DESCRIPTION
			" Command to cause the modem to display
			 the phone number stored in any of the 10 dial cell
			 locations (0-9)."
	::= { mdmDialingCellsFunctionEntry 4 }

mdmTerminateCellCall OBJECT-TYPE
	SYNTAX    INTEGER       {
				goOnhook(1)
				}
	ACCESS    write-only
	STATUS    mandatory
	DESCRIPTION
			" Command to instruct the mode to disconnect the
			 call and go to idle."
	::= { mdmDialingCellsFunctionEntry 5 }



--*****************************************************************************
--                    MAINTENANCE TABLE
--*****************************************************************************
mdmMaintenanceTable OBJECT-TYPE
	SYNTAX  SEQUENCE OF MdmMaintenanceEntry
	ACCESS  not-accessible
	STATUS  mandatory
	DESCRIPTION
			"The GDC VFAST Maintenance Table."
	::= { mdm 16 }

mdmMaintenanceEntry OBJECT-TYPE
	SYNTAX  MdmMaintenanceEntry
	ACCESS  not-accessible
	STATUS  mandatory
	DESCRIPTION
			"An entry in the GDC VFAST Maintenance table."
	INDEX   { mdmMaintenanceIndex }
	::= { mdmMaintenanceTable 1 }

MdmMaintenanceEntry ::=
	SEQUENCE {
		  mdmMaintenanceIndex
			 SCinstance,
		  mdmSaveRecallConfig
			 INTEGER,
		  mdmConfigCksum
			 OCTET STRING,
		  mdmPassword
			 DisplayString,
		  mdmSerialNumber
			 DisplayString,
		  mdmPowerUpProfile
			 INTEGER,
		  mdmPasswordOperation
			 INTEGER
		  }

mdmMaintenanceIndex OBJECT-TYPE
	SYNTAX  SCinstance
	ACCESS  read-only
	STATUS  mandatory
	DESCRIPTION
			"A unique index for the Maintenance Index Table."
	::= { mdmMaintenanceEntry 1 }


mdmSaveRecallConfig OBJECT-TYPE
	SYNTAX  INTEGER {
				recallFactoryDefault0(1),
				recallFactoryDefault1(2),
				recallFactoryDefault2(3),
				recallFactoryDefault3(4),
				recallUserProfile0(5),
				recallUserProfile1(6),
				recallUserProfile2(7),
				recallUserProfile3(8),
				saveUserProfile0(9),
				saveUserProfile1(10),
				saveUserProfile2(11),
				saveUserProfile3(12)
				}

	ACCESS    write-only
	STATUS    mandatory
	DESCRIPTION
			"This command allows the user to load or save factory or user
			profile configurations into the modem."
	::= { mdmMaintenanceEntry 2 }


mdmConfigCksum OBJECT-TYPE
	SYNTAX  OCTET STRING (SIZE (2))
	ACCESS  read-only
	STATUS  mandatory
	DESCRIPTION  "Reads the configuration checksum of the modem."

	::= { mdmMaintenanceEntry 3 }


mdmPassword OBJECT-TYPE
	SYNTAX	DisplayString (SIZE (0..10))
	ACCESS  write-only
	STATUS  mandatory
	DESCRIPTION
		"This function sets the modem password. The maximum
		number of digits in the password must be equal or less than 10.
		If no password is entered the password is non-functional."

	::= { mdmMaintenanceEntry 4 }


mdmSerialNumber OBJECT-TYPE
	SYNTAX    DisplayString (SIZE (16))
	ACCESS    read-write
	STATUS    mandatory
	DESCRIPTION
			"Network element serial number"
	::= { mdmMaintenanceEntry 5 }

mdmPowerUpProfile OBJECT-TYPE
	SYNTAX    INTEGER       {
					zero(1),
					one(2),
					two(3),
					three(4)
					}
	ACCESS    read-write
	STATUS    mandatory
	DESCRIPTION
			"Command to select 1 of 4 custom modem configurations
			 at power up."
	::= { mdmMaintenanceEntry 6 }

mdmPasswordOperation    OBJECT-TYPE
	SYNTAX  INTEGER  {
				disabled(1),
				enablehandshake(2),
				enableonline(3),
				enable(4)
				}
	ACCESS  read-write
	STATUS  mandatory
	DESCRIPTION
	       "This object identifies the Password Operation.  The GDC
	       proprietary handshake password validation operation and the
	       on line (entered by the remote user) password validation
	       operation can be enabled or disabled globally or selectively.
	       disabled        - password operations disabled
	       enablehandshake - enable the handshake password operation
	       enableonline    - enable the answering modem to locally validate
				 the remote user entered password
	       enable          - enable both handshake and online password
				 operations
	       Not applicable when the modem is in Remote Configuration session."
	::= {mdmMaintenanceEntry 7 }

--*****************************************************************************
--            STATISTICS TABLE
--*****************************************************************************

mdmStatisticsTable OBJECT-TYPE
	SYNTAX  SEQUENCE OF MdmStatisticsEntry
	ACCESS  not-accessible
	STATUS  mandatory
	DESCRIPTION
			"The GDC VFAST Statistics Table."
	::= { mdm 17 }

mdmStatisticsEntry OBJECT-TYPE
	SYNTAX  MdmStatisticsEntry
	ACCESS  not-accessible
	STATUS  mandatory
	DESCRIPTION
			"An entry in the GDC VFAST Statistics table."
	INDEX   { mdmStatisticsIndex }
	::= { mdmStatisticsTable 1 }

MdmStatisticsEntry ::=
	SEQUENCE {
		  mdmStatisticsIndex
			 SCinstance,
		  mdmDCERate
			 INTEGER,
		  mdmCallDurationStat
			 TimeTicks,
		  mdmRetrainCount
			 INTEGER,
		  mdmFallbackCount
			 INTEGER,
		  mdmFallforwardCount
			 INTEGER,
		  mdmRxSignalLevel
			 INTEGER,
		  mdmSignaltoNoiseRatio
			 INTEGER,
		  mdmAnswerOriginateStat
			 INTEGER,
		  mdmDiscReason
			 INTEGER,
		  mdmCompressionEfficiency
			 INTEGER,
		  mdmThruput
			 INTEGER
		  }

mdmStatisticsIndex OBJECT-TYPE
	SYNTAX  SCinstance
	ACCESS  read-only
	STATUS  mandatory
	DESCRIPTION
	       "This object is the identifier of the VFAST Statistics table."
	::= { mdmStatisticsEntry 1 }


mdmDCERate       OBJECT-TYPE
	SYNTAX  INTEGER  {
				bps300(2),
				bps1200(3),
				bps2400(4),
				bps4800(5),
				bps7200(6),
				bps9600(7),
				bps12000(8),
				bps14400(9),
				bps16800(10),
				bps19200(11),
				bps21600(12),
				bps24000(13),
				bps26400(14),
				bps28800(15)
				}
	ACCESS  read-only
	STATUS  mandatory
	DESCRIPTION
	       "This object identifies the DCE speed that the modem is operating."
	::= { mdmStatisticsEntry 2 }


mdmCallDurationStat  OBJECT-TYPE
	SYNTAX  TimeTicks
	ACCESS  read-only
	STATUS  mandatory
	DESCRIPTION
		" This function reads the duration of the last or current
		Switched Network connection in timeticks. "
	::= { mdmStatisticsEntry 3 }


mdmRetrainCount OBJECT-TYPE
	SYNTAX  INTEGER (0..127)
	ACCESS  read-only
	STATUS  mandatory
	DESCRIPTION
		" This function reads the number of retrains."
	::= { mdmStatisticsEntry 4 }


mdmFallbackCount       OBJECT-TYPE
	SYNTAX  INTEGER (0..127)
	ACCESS  read-only
	STATUS  mandatory
	DESCRIPTION
		" This function reads the number of times that the modem falls back."
	::= { mdmStatisticsEntry 5 }


mdmFallforwardCount      OBJECT-TYPE
	SYNTAX  INTEGER (0..127)
	ACCESS  read-only
	STATUS  mandatory
	DESCRIPTION
		" This function reads the number of times that the modem falls forward."
	::= { mdmStatisticsEntry 6 }


mdmRxSignalLevel     OBJECT-TYPE
	SYNTAX  INTEGER (0..127)
	ACCESS  read-only
	STATUS  mandatory
	DESCRIPTION
		" This function reads the input signal level in dB."
	::= { mdmStatisticsEntry 7 }


mdmSignaltoNoiseRatio     OBJECT-TYPE
	SYNTAX  INTEGER (0..127)
	ACCESS  read-only
	STATUS  mandatory
	DESCRIPTION
		" This function reads the signal to noise ratio in dB."
	::= { mdmStatisticsEntry 8 }


mdmAnswerOriginateStat  OBJECT-TYPE
	SYNTAX  INTEGER  {
				originate(1),
				answer(2)
				}
	ACCESS  read-only
	STATUS  mandatory
	DESCRIPTION
		" This function reads the band that the modem is operating
		  in data mode."
	::= { mdmStatisticsEntry 9 }


mdmDiscReason	OBJECT-TYPE
	SYNTAX	INTEGER {
			usertimeout(1),
			unknown(2)
			}
	ACCESS  read-only
	STATUS  mandatory
	DESCRIPTION
		"This function reads the reason why the modem has disconnected.
		 usertimeout - user timed out while entering prompted
		 information."
	::= { mdmStatisticsEntry 10 }

mdmCompressionEfficiency       OBJECT-TYPE
	SYNTAX	INTEGER (0..65535)
	ACCESS  read-only
	STATUS  mandatory
	DESCRIPTION
		"The number of bytes transferred into the compression encoder
		 divided by the number of bytes transferred out of the encoder,
		 multiplied by 100 for either the current or last call.
		 If a data compression protocol is not in use,
		 this value shall be '100'."
	::= { mdmStatisticsEntry 11 }

mdmThruput	OBJECT-TYPE
	SYNTAX	INTEGER (0..65535)
	ACCESS  read-only
	STATUS  mandatory
	DESCRIPTION
		"The data thruput rate is the number of bytes received from
		 the DCE and then sent to the DTE per second."
	::= { mdmStatisticsEntry 12 }

--*****************************************************************************
--            REMOTE CONFIGURATION TABLE
--*****************************************************************************

mdmRemoteConfigTable OBJECT-TYPE
	SYNTAX  SEQUENCE OF MdmRemoteConfigEntry
	ACCESS  not-accessible
	STATUS  mandatory
	DESCRIPTION
			"The GDC VFAST Remote Configuration Table."
	::= { mdm 18 }

mdmRemoteConfigEntry OBJECT-TYPE
	SYNTAX  MdmRemoteConfigEntry
	ACCESS  not-accessible
	STATUS  mandatory
	DESCRIPTION
			"An entry in the GDC VFAST Remote Config table."
	INDEX   { mdmRemoteConfigIndex }
	::= { mdmRemoteConfigTable 1 }

MdmRemoteConfigEntry ::=
	SEQUENCE {
		  mdmRemoteConfigIndex
			 SCinstance,
		  mdmRemoteConfiguration
			 INTEGER,
		  mdmEndRemoteConfiguration
			 INTEGER,
		  mdmPasswordRemoteConfiguration
			 DisplayString
		  }

mdmRemoteConfigIndex OBJECT-TYPE
	SYNTAX  SCinstance
	ACCESS  read-only
	STATUS  mandatory
	DESCRIPTION
	       "This object is the identifier of the VFAST Remote
	       Configuration table."
	::= { mdmRemoteConfigEntry 1 }


mdmRemoteConfiguration   OBJECT-TYPE
	SYNTAX  INTEGER  {
				disable(1),
                                enableDTE(2),
                                enableDMS(3)
				}
	ACCESS  read-write
	STATUS  mandatory
	DESCRIPTION
	       "This object options the Remote configuration for the
		local unit before dial."
	::= { mdmRemoteConfigEntry 2 }


mdmEndRemoteConfiguration  OBJECT-TYPE
	SYNTAX  INTEGER {
				noUpdate(1),
				update(2)
				}
        ACCESS  write-only
	STATUS  mandatory
	DESCRIPTION
		" This option tells the far end unit to disconnect and
		update the options or not that have been changed during the
		remote configuration session."
	 ::= { mdmRemoteConfigEntry 3 }


mdmPasswordRemoteConfiguration	OBJECT-TYPE
	SYNTAX	DisplayString (SIZE (0..10))
	ACCESS  write-only
	STATUS  mandatory
	DESCRIPTION
		" This option stores the Remote Configuration Password.
		When a password is stored in the answer modem it must be
		matched during the handshake by the originating modem. If the
		password matching fails, the answer modem will drop the
		connection.
		Not applicable when the modem is in Remote Configuration session."
	 ::= { mdmRemoteConfigEntry 4 }

--**************************************************************************
--		GDC V.F 28.8 MODEM MIB VERSION NUMBER
--**************************************************************************

mdmMIBVersion	OBJECT-TYPE
	SYNTAX	DisplayString (SIZE (5))
	ACCESS	read-only
	STATUS  mandatory
	DESCRIPTION
		"The version number of the MIB, to allow products to 
		know which MIB is being supported.  The version number
		will be x.yzT where x is a major revision (1-9), y is a minor
		revision(0-9), z is a typo revision (0-9) and T indicates the
		MIB is still a test revision(A-Z).  When a release is complete
		no T should exist."
	::= { mdm 19 }


--**************************************************************************
--                      TRAPS
--**************************************************************************

mdmCallStatsTrap        TRAP-TYPE
	ENTERPRISE      mdm
	VARIABLES	{ mdmDCERate, mdmRetrainCount, mdmFallbackCount,
	 mdmFallforwardCount, mdmRxSignalLevel, mdmSignaltoNoiseRatio,
	 mdmAnswerOriginateStat, mdmCallDurationStat, mdmDiscReason,
	 mdmCompressionEfficiency, mdmThruput }

	DESCRIPTION
		"This is the Call Statistics Trap.  When a V.F 28.8 modem
		 disconnects from a call after data has passed, it will send
		 call statistics information.  "
	::= 1

END
