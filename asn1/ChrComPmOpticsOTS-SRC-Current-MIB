ChrComPmOpticsOTS-SRC-Current-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComPmOptics				FROM  Chromatis-MIB
	chrComIfifIndex					FROM  ChrComIfifTable-MIB
	TruthValue				FROM  ChrTyp-MIB
	Gauge32				FROM  SNMPv2-SMI;

-- chrComPmOpticsOTS-SRC-Current Table

chrComPmOpticsOTS-SRC-CurrentTable		OBJECT-TYPE
	SYNTAX		SEQUENCE OF ChrComPmOpticsOTS-SRC-CurrentEntry
	MAX-ACCESS	not-accessible
	STATUS		current
	DESCRIPTION
	""
	::= { chrComPmOptics 4}

chrComPmOpticsOTS-SRC-CurrentEntry		OBJECT-TYPE
	SYNTAX		ChrComPmOpticsOTS-SRC-CurrentEntry
	MAX-ACCESS	not-accessible
	STATUS		current
	DESCRIPTION
	""
	INDEX  {  chrComIfifIndex }

--DEFAULT  get-function-async  MNIL_GetRoutine
--DEFAULT  set-function-async  MNIL_SetRoutine
--DEFAULT  next-function-async MNIL_NextRoutine
--DEFAULT  test-function-async MNIL_TestRoutine
--DEFAULT  cookie "OTS-SRC-Current"
	::= { chrComPmOpticsOTS-SRC-CurrentTable  1 }

ChrComPmOpticsOTS-SRC-CurrentEntry  ::=
	SEQUENCE  {
	chrComPmOpticsSuspectedIntrvl		TruthValue,
	chrComPmOpticsElapsedTime		Unsigned32	(0..4294967295),
	chrComPmOpticsSuppressedIntrvls	Gauge32			(0..4294967295),
	chrComPmOpticsORS			Gauge32			(0..4294967295),
	chrComPmOpticsSES			Gauge32			(0..4294967295),
	chrComPmOpticsUAS			Gauge32			(0..4294967295),
	chrComPmOpticsMean			Integer32	(0..2147483647),
	chrComPmOpticsMax			Integer32	(0..2147483647),
	chrComPmOpticsMin			Integer32	(0..2147483647),
	chrComPmOpticsSD			Integer32	(0..2147483647),
	chrComPmOpticsThresholdProfIndex	Unsigned32	(0..4294967295),
	chrComPmOpticsResetCountersAction	TruthValue
}

chrComPmOpticsSuspectedIntrvl 	OBJECT-TYPE
	SYNTAX		TruthValue
	MAX-ACCESS 	read-only
	STATUS 		current
	DESCRIPTION
	"a flag marking the validity of the entry data"
	::= { chrComPmOpticsOTS-SRC-CurrentEntry  1 }

chrComPmOpticsElapsedTime 	OBJECT-TYPE
	SYNTAX		Unsigned32	(0..4294967295)
	MAX-ACCESS 	read-only
	STATUS 		current
	DESCRIPTION
	"measurment duration, in 0.01 seconds"
	::= { chrComPmOpticsOTS-SRC-CurrentEntry  2 }

chrComPmOpticsSuppressedIntrvls 	OBJECT-TYPE
	SYNTAX		Gauge32			(0..4294967295)
	MAX-ACCESS 	read-only
	STATUS 		current
	DESCRIPTION
	"invalid for first version. indicates how many all-zero periods have passed."
	::= { chrComPmOpticsOTS-SRC-CurrentEntry  3 }

chrComPmOpticsORS 	OBJECT-TYPE
	SYNTAX		Gauge32			(0..4294967295)
	MAX-ACCESS 	read-only
	STATUS 		current
	DESCRIPTION
	""
	::= { chrComPmOpticsOTS-SRC-CurrentEntry  4 }

chrComPmOpticsSES 	OBJECT-TYPE
	SYNTAX		Gauge32			(0..4294967295)
	MAX-ACCESS 	read-only
	STATUS 		current
	DESCRIPTION
	""
	::= { chrComPmOpticsOTS-SRC-CurrentEntry  5 }

chrComPmOpticsUAS 	OBJECT-TYPE
	SYNTAX		Gauge32			(0..4294967295)
	MAX-ACCESS 	read-only
	STATUS 		current
	DESCRIPTION
	""
	::= { chrComPmOpticsOTS-SRC-CurrentEntry  6 }

chrComPmOpticsMean 	OBJECT-TYPE
	SYNTAX		Integer32	(0..2147483647)
	MAX-ACCESS 	read-only
	STATUS 		current
	DESCRIPTION
	""
	::= { chrComPmOpticsOTS-SRC-CurrentEntry  7 }

chrComPmOpticsMax 	OBJECT-TYPE
	SYNTAX		Integer32	(0..2147483647)
	MAX-ACCESS 	read-only
	STATUS 		current
	DESCRIPTION
	""
	::= { chrComPmOpticsOTS-SRC-CurrentEntry  8 }

chrComPmOpticsMin 	OBJECT-TYPE
	SYNTAX		Integer32	(0..2147483647)
	MAX-ACCESS 	read-only
	STATUS 		current
	DESCRIPTION
	""
	::= { chrComPmOpticsOTS-SRC-CurrentEntry  9 }

chrComPmOpticsSD 	OBJECT-TYPE
	SYNTAX		Integer32	(0..2147483647)
	MAX-ACCESS 	read-only
	STATUS 		current
	DESCRIPTION
	""
	::= { chrComPmOpticsOTS-SRC-CurrentEntry  10 }

chrComPmOpticsThresholdProfIndex 	OBJECT-TYPE
	SYNTAX		Unsigned32	(0..4294967295)
	MAX-ACCESS 	read-write
	STATUS 		current
	DESCRIPTION
	""
	::= { chrComPmOpticsOTS-SRC-CurrentEntry  11 }

chrComPmOpticsResetCountersAction 	OBJECT-TYPE
	SYNTAX		TruthValue
	MAX-ACCESS 	read-write
	STATUS 		current
	DESCRIPTION
	""
	::= { chrComPmOpticsOTS-SRC-CurrentEntry  12 }


END
