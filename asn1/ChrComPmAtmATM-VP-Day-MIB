ChrComPmAtmATM-VP-Day-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComPmAtm				FROM  Chromatis-MIB
	chrComIfifIndex					FROM  ChrComIfifTable-MIB
	atmVplVpi					FROM  ATM-MIB
	TruthValue				FROM  ChrTyp-MIB
	Gauge32				FROM  SNMPv2-SMI;

-- chrComPmAtmATM-VP-Day Table

chrComPmAtmATM-VP-DayTable		OBJECT-TYPE
	SYNTAX		SEQUENCE OF ChrComPmAtmATM-VP-DayEntry
	MAX-ACCESS	not-accessible
	STATUS		current
	DESCRIPTION
	""
	::= { chrComPmAtm 6}

chrComPmAtmATM-VP-DayEntry		OBJECT-TYPE
	SYNTAX		ChrComPmAtmATM-VP-DayEntry
	MAX-ACCESS	not-accessible
	STATUS		current
	DESCRIPTION
	""
	INDEX  {  chrComIfifIndex, atmVplVpi, chrComPmAtmDayNumber }

--DEFAULT  get-function-async  MNIL_GetRoutine
--DEFAULT  set-function-async  MNIL_SetRoutine
--DEFAULT  next-function-async MNIL_NextRoutine
--DEFAULT  test-function-async MNIL_TestRoutine
--DEFAULT  cookie "ATM-VP-Day"
	::= { chrComPmAtmATM-VP-DayTable  1 }

ChrComPmAtmATM-VP-DayEntry  ::=
	SEQUENCE  {
	chrComPmAtmDayNumber		Unsigned32	(1..2),
	chrComPmAtmSuspectedInterval	TruthValue,
	chrComPmAtmElapsedTime		Unsigned32	(0..4294967295),
	chrComPmAtmSuppressedIntrvls	Gauge32			(0..4294967295),
	chrComPmAtmReceivedCells		Gauge32			(0..4294967295),
	chrComPmAtmTransmittedCells	Gauge32			(0..4294967295),
	chrComPmAtmThresholdProfIndex	Unsigned32	(0..4294967295),
	chrComPmAtmResetPmCountersAction	TruthValue
}

chrComPmAtmDayNumber 	OBJECT-TYPE
	SYNTAX		Unsigned32	(1..2)
	MAX-ACCESS 	read-only
	STATUS 		current
	DESCRIPTION
	""
	::= { chrComPmAtmATM-VP-DayEntry  1 }

chrComPmAtmSuspectedInterval 	OBJECT-TYPE
	SYNTAX		TruthValue
	MAX-ACCESS 	read-only
	STATUS 		current
	DESCRIPTION
	""
	::= { chrComPmAtmATM-VP-DayEntry  2 }

chrComPmAtmElapsedTime 	OBJECT-TYPE
	SYNTAX		Unsigned32	(0..4294967295)
	MAX-ACCESS 	read-only
	STATUS 		current
	DESCRIPTION
	""
	::= { chrComPmAtmATM-VP-DayEntry  3 }

chrComPmAtmSuppressedIntrvls 	OBJECT-TYPE
	SYNTAX		Gauge32			(0..4294967295)
	MAX-ACCESS 	read-only
	STATUS 		current
	DESCRIPTION
	""
	::= { chrComPmAtmATM-VP-DayEntry  4 }

chrComPmAtmReceivedCells 	OBJECT-TYPE
	SYNTAX		Gauge32			(0..4294967295)
	MAX-ACCESS 	read-only
	STATUS 		current
	DESCRIPTION
	""
	::= { chrComPmAtmATM-VP-DayEntry  5 }

chrComPmAtmTransmittedCells 	OBJECT-TYPE
	SYNTAX		Gauge32			(0..4294967295)
	MAX-ACCESS 	read-only
	STATUS 		current
	DESCRIPTION
	""
	::= { chrComPmAtmATM-VP-DayEntry  6 }

chrComPmAtmThresholdProfIndex 	OBJECT-TYPE
	SYNTAX		Unsigned32	(0..4294967295)
	MAX-ACCESS 	read-write
	STATUS 		current
	DESCRIPTION
	""
	::= { chrComPmAtmATM-VP-DayEntry  7 }

chrComPmAtmResetPmCountersAction 	OBJECT-TYPE
	SYNTAX		TruthValue
	MAX-ACCESS 	read-write
	STATUS 		current
	DESCRIPTION
	""
	::= { chrComPmAtmATM-VP-DayEntry  8 }


END
