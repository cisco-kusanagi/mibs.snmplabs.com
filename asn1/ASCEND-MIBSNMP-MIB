--			Ascend mibsnmp MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBSNMP-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibusmUserProfile  OBJECT IDENTIFIER ::= { configuration 115}
    mibsnmpManagerProfile  OBJECT IDENTIFIER ::= { configuration 118}
    mibsnmpProfile  OBJECT IDENTIFIER ::= { configuration 114}
    mibsnmpv3NotifyProfile  OBJECT IDENTIFIER ::= { configuration 117}
    mibsnmpv3TargetParamProfile  OBJECT IDENTIFIER ::= { configuration 116}

	-- The mibusmUserProfile table
	--
	-- This table contains parameters for the mibusmUserProfile profile
	--

    mibusmUserProfileTable	OBJECT-TYPE
	SYNTAX		SEQUENCE OF MibusmUserProfileEntry
	ACCESS		not-accessible
	STATUS		mandatory
	DESCRIPTION	"A list of mibusmUserProfile profile entries."
	::= { mibusmUserProfile 1 }

    mibusmUserProfileEntry	OBJECT-TYPE
	SYNTAX		MibusmUserProfileEntry
	ACCESS		not-accessible
	STATUS		mandatory
	DESCRIPTION	"A mibusmUserProfile entry containing objects that
			 maps to the parameters of mibusmUserProfile profile."
	INDEX		{ usmUserProfile-Name }
	::= { mibusmUserProfileTable 1 }

    MibusmUserProfileEntry ::=
	SEQUENCE {
	    usmUserProfile-Name
		OCTET STRING,
	    usmUserProfile-ActiveEnabled
		INTEGER,
	    usmUserProfile-ReadWriteAccess
		INTEGER,
	    usmUserProfile-AuthProtocol
		INTEGER,
	    usmUserProfile-PrivProtocol
		INTEGER,
	    usmUserProfile-AuthKey
		OCTET STRING,
	    usmUserProfile-PrivKey
		OCTET STRING,
	    usmUserProfile-Action-o
		INTEGER
	}

    usmUserProfile-Name	OBJECT-TYPE
	SYNTAX	OCTET STRING
	ACCESS	read-only
	STATUS	mandatory
	DESCRIPTION	"The user (principal) on whose behalf the message is being exchange."
	::= { mibusmUserProfileEntry 1 }

    usmUserProfile-ActiveEnabled	OBJECT-TYPE
	SYNTAX	INTEGER {
		    no (1),
		    yes (2)
		}
	ACCESS	read-write
	STATUS	mandatory
	DESCRIPTION	"TRUE if this user is enabled for message exchange."
	::= { mibusmUserProfileEntry 2 }

    usmUserProfile-ReadWriteAccess	OBJECT-TYPE
	SYNTAX	INTEGER {
		    no (1),
		    yes (2)
		}
	ACCESS	read-write
	STATUS	mandatory
	DESCRIPTION	"TRUE if this user is configured for read-write access to MIB view."
	::= { mibusmUserProfileEntry 3 }

    usmUserProfile-AuthProtocol	OBJECT-TYPE
	SYNTAX	INTEGER {
		    noAuth (1),
		    md5Auth (2),
		    shaAuth (3)
		}
	ACCESS	read-write
	STATUS	mandatory
	DESCRIPTION	"Indicate whether messages sent on behalf of this user to/from the SNMP engine can be authenticated and,if so, the type of authentication protocol to be used."
	::= { mibusmUserProfileEntry 4 }

    usmUserProfile-PrivProtocol	OBJECT-TYPE
	SYNTAX	INTEGER {
		    noPriv (1),
		    desPriv (2)
		}
	ACCESS	read-write
	STATUS	mandatory
	DESCRIPTION	"Indicate whether messages sent on behalf of this user to/from the SNMP engine can be protected by encryption and,if so, the type of privacy protocol to be used."
	::= { mibusmUserProfileEntry 5 }

    usmUserProfile-AuthKey	OBJECT-TYPE
	SYNTAX	OCTET STRING
	ACCESS	read-write
	STATUS	mandatory
	DESCRIPTION	"The user's authkey: calculated based on password and auth protocol. This can be set using snmpAuthPass command"
	::= { mibusmUserProfileEntry 6 }

    usmUserProfile-PrivKey	OBJECT-TYPE
	SYNTAX	OCTET STRING
	ACCESS	read-write
	STATUS	mandatory
	DESCRIPTION	"The user's privacy: key calculated based on priv-password and auth protocol. This can be set using snmpPrivPass command"
	::= { mibusmUserProfileEntry 7 }

    usmUserProfile-Action-o	OBJECT-TYPE
	SYNTAX	INTEGER {
		    noAction (1),
		    createProfile (2),
		    deleteProfile (3)
		}
	ACCESS	read-write
	STATUS	mandatory
	DESCRIPTION	""
	::= { mibusmUserProfileEntry 8 }


	-- The mibsnmpManagerProfile table
	--
	-- This table contains parameters for the mibsnmpManagerProfile profile
	--

    mibsnmpManagerProfileTable	OBJECT-TYPE
	SYNTAX		SEQUENCE OF MibsnmpManagerProfileEntry
	ACCESS		not-accessible
	STATUS		mandatory
	DESCRIPTION	"A list of mibsnmpManagerProfile profile entries."
	::= { mibsnmpManagerProfile 1 }

    mibsnmpManagerProfileEntry	OBJECT-TYPE
	SYNTAX		MibsnmpManagerProfileEntry
	ACCESS		not-accessible
	STATUS		mandatory
	DESCRIPTION	"A mibsnmpManagerProfile entry containing objects that
			 maps to the parameters of mibsnmpManagerProfile profile."
	INDEX		{ snmpManagerProfile-Name }
	::= { mibsnmpManagerProfileTable 1 }

    MibsnmpManagerProfileEntry ::=
	SEQUENCE {
	    snmpManagerProfile-Name
		DisplayString,
	    snmpManagerProfile-Active
		INTEGER,
	    snmpManagerProfile-WriteAccess
		INTEGER,
	    snmpManagerProfile-SnmpMessageType
		INTEGER,
	    snmpManagerProfile-Action-o
		INTEGER
	}

    snmpManagerProfile-Name	OBJECT-TYPE
	SYNTAX	DisplayString
	ACCESS	read-only
	STATUS	mandatory
	DESCRIPTION	"The name or the ip-address in dot format of the SNMP Manager (host) to send SNMP requests to the TAOS SNMP Agent. When DNS or YP/NIS is supported this name will be used to look up the LAN address."
	::= { mibsnmpManagerProfileEntry 1 }

    snmpManagerProfile-Active	OBJECT-TYPE
	SYNTAX	INTEGER {
		    no (1),
		    yes (2)
		}
	ACCESS	read-write
	STATUS	mandatory
	DESCRIPTION	"TRUE if SNMP messages from a particular SNMP Manager should be processed. This implies read-access for SNMPv1."
	::= { mibsnmpManagerProfileEntry 2 }

    snmpManagerProfile-WriteAccess	OBJECT-TYPE
	SYNTAX	INTEGER {
		    no (1),
		    yes (2)
		}
	ACCESS	read-write
	STATUS	mandatory
	DESCRIPTION	"When set to `no' (its default value), the SNMP agent only allows read requests. When set to 'yes', the SNMP agent allows write requests in addition to read requests."
	::= { mibsnmpManagerProfileEntry 3 }

    snmpManagerProfile-SnmpMessageType	OBJECT-TYPE
	SYNTAX	INTEGER {
		    v1AndV3 (1),
		    v1Only (2),
		    v3Only (3)
		}
	ACCESS	read-write
	STATUS	mandatory
	DESCRIPTION	"Indicate the message type that the SNMP agent should allow for this SNMP Manager."
	::= { mibsnmpManagerProfileEntry 4 }

    snmpManagerProfile-Action-o	OBJECT-TYPE
	SYNTAX	INTEGER {
		    noAction (1),
		    createProfile (2),
		    deleteProfile (3)
		}
	ACCESS	read-write
	STATUS	mandatory
	DESCRIPTION	""
	::= { mibsnmpManagerProfileEntry 5 }


	-- The mibsnmpProfile table
	--
	-- This table contains parameters for the mibsnmpProfile profile
	--

    mibsnmpProfileTable	OBJECT-TYPE
	SYNTAX		SEQUENCE OF MibsnmpProfileEntry
	ACCESS		not-accessible
	STATUS		mandatory
	DESCRIPTION	"A list of mibsnmpProfile profile entries."
	::= { mibsnmpProfile 1 }

    mibsnmpProfileEntry	OBJECT-TYPE
	SYNTAX		MibsnmpProfileEntry
	ACCESS		not-accessible
	STATUS		mandatory
	DESCRIPTION	"A mibsnmpProfile entry containing objects that
			 maps to the parameters of mibsnmpProfile profile."
	INDEX		{ snmpProfile-Index-o }
	::= { mibsnmpProfileTable 1 }

    MibsnmpProfileEntry ::=
	SEQUENCE {
	    snmpProfile-Index-o
		INTEGER,
	    snmpProfile-Enabled
		INTEGER,
	    snmpProfile-ReadCommunity
		DisplayString,
	    snmpProfile-ReadWriteEnabled
		INTEGER,
	    snmpProfile-ReadWriteCommunity
		DisplayString,
	    snmpProfile-EnforceAddressSecurity
		INTEGER,
	    snmpProfile-EarlyQueueDiscard
		INTEGER,
	    snmpProfile-Contact
		DisplayString,
	    snmpProfile-Location
		DisplayString,
	    snmpProfile-QueueDepth
		INTEGER,
	    snmpProfile-CsmModemDiag
		INTEGER,
	    snmpProfile-SnmpMessageType
		INTEGER,
	    snmpProfile-SecurityLevel
		INTEGER,
	    snmpProfile-EnableVacm
		INTEGER,
	    snmpProfile-NotificationLogAgeOut
		INTEGER,
	    snmpProfile-BitStringsAllowed
		INTEGER,
	    snmpProfile-AlarmClearTableLimit
		INTEGER,
	    snmpProfile-Action-o
		INTEGER
	}

    snmpProfile-Index-o	OBJECT-TYPE
	SYNTAX	INTEGER
	ACCESS	read-only
	STATUS	mandatory
	DESCRIPTION	""
	::= { mibsnmpProfileEntry 1 }

    snmpProfile-Enabled	OBJECT-TYPE
	SYNTAX	INTEGER {
		    no (1),
		    yes (2)
		}
	ACCESS	read-write
	STATUS	mandatory
	DESCRIPTION	"When set to `no' (its default value), the unit cannot be accessed via SNMP."
	::= { mibsnmpProfileEntry 2 }

    snmpProfile-ReadCommunity	OBJECT-TYPE
	SYNTAX	DisplayString
	ACCESS	read-write
	STATUS	mandatory
	DESCRIPTION	"The SNMP community name for read access."
	::= { mibsnmpProfileEntry 3 }

    snmpProfile-ReadWriteEnabled	OBJECT-TYPE
	SYNTAX	INTEGER {
		    no (1),
		    yes (2)
		}
	ACCESS	read-write
	STATUS	mandatory
	DESCRIPTION	"When set to `no' (its default value), the write community cannot be accessed via SNMP."
	::= { mibsnmpProfileEntry 4 }

    snmpProfile-ReadWriteCommunity	OBJECT-TYPE
	SYNTAX	DisplayString
	ACCESS	read-write
	STATUS	mandatory
	DESCRIPTION	"The SNMP community name for read/write access."
	::= { mibsnmpProfileEntry 5 }

    snmpProfile-EnforceAddressSecurity	OBJECT-TYPE
	SYNTAX	INTEGER {
		    no (1),
		    yes (2)
		}
	ACCESS	read-write
	STATUS	mandatory
	DESCRIPTION	"When set to `no' (its default value), we will allow access to all SNMP managers that know the community string. When set to `yes', we will check the source IP address against the ones that are defined in the SNMP-MANAGER profiles before allowing access."
	::= { mibsnmpProfileEntry 6 }

    snmpProfile-EarlyQueueDiscard	OBJECT-TYPE
	SYNTAX	INTEGER {
		    no (1),
		    yes (2)
		}
	ACCESS	read-write
	STATUS	mandatory
	DESCRIPTION	"If this parameter is set to yes, the system will filter and discard the requests from unauthorized host before queuing to the SNMP UDP port 161. If this parameter is set to no, the system will queue all incoming SNMP requests to SNMP layer which will discard the requests later if they are from unauthorized host."
	::= { mibsnmpProfileEntry 16 }

    snmpProfile-Contact	OBJECT-TYPE
	SYNTAX	DisplayString
	ACCESS	read-write
	STATUS	mandatory
	DESCRIPTION	"The name of the contact for this device. SNMP readable and settable."
	::= { mibsnmpProfileEntry 7 }

    snmpProfile-Location	OBJECT-TYPE
	SYNTAX	DisplayString
	ACCESS	read-write
	STATUS	mandatory
	DESCRIPTION	"The location of this device. SNMP readable and settable."
	::= { mibsnmpProfileEntry 8 }

    snmpProfile-QueueDepth	OBJECT-TYPE
	SYNTAX	INTEGER
	ACCESS	read-write
	STATUS	mandatory
	DESCRIPTION	"The maximum number of SNMP packets waiting to be serviced. Additional packets will be dropped. When setting this value, you're trading memory resources versus SNMP retries (only when the box is busy and gets behind on servicing the SNMP packets). Zero indicates there is no limit. "
	::= { mibsnmpProfileEntry 9 }

    snmpProfile-CsmModemDiag	OBJECT-TYPE
	SYNTAX	INTEGER {
		    no (1),
		    yes (2)
		}
	ACCESS	read-write
	STATUS	mandatory
	DESCRIPTION	"When set to `no' (its default value), SNMP CSM modem card diag is disabled. A JEDEC card is required to turn on this feature. "
	::= { mibsnmpProfileEntry 10 }

    snmpProfile-SnmpMessageType	OBJECT-TYPE
	SYNTAX	INTEGER {
		    v1AndV3 (1),
		    v1Only (2),
		    v3Only (3)
		}
	ACCESS	read-write
	STATUS	mandatory
	DESCRIPTION	"Indicate the message type that the SNMP agent should handle."
	::= { mibsnmpProfileEntry 11 }

    snmpProfile-SecurityLevel	OBJECT-TYPE
	SYNTAX	INTEGER {
		    none (1),
		    authNopriv (2),
		    authPriv (3)
		}
	ACCESS	read-write
	STATUS	mandatory
	DESCRIPTION	"Indicate the security level of the SNMP agent. Applicable only if SNMPv3 message handling enabled"
	::= { mibsnmpProfileEntry 12 }

    snmpProfile-EnableVacm	OBJECT-TYPE
	SYNTAX	INTEGER {
		    no (1),
		    yes (2)
		}
	ACCESS	read-write
	STATUS	mandatory
	DESCRIPTION	"If set to TRUE, View Based Access Control Model (VACM) would be enabled, otherwise VACM is disabled."
	::= { mibsnmpProfileEntry 13 }

    snmpProfile-NotificationLogAgeOut	OBJECT-TYPE
	SYNTAX	INTEGER
	ACCESS	read-write
	STATUS	mandatory
	DESCRIPTION	"The number of minutes a Notification SHOULD be kept in a log before it is automatically removed. A value of 0 means no age out."
	::= { mibsnmpProfileEntry 15 }

    snmpProfile-BitStringsAllowed	OBJECT-TYPE
	SYNTAX	INTEGER {
		    no (1),
		    yes (2)
		}
	ACCESS	read-write
	STATUS	mandatory
	DESCRIPTION	"If enabled, TAOS agent responds to BITS data type in bit string format. If disabled, TAOS agent responds in numeric format."
	::= { mibsnmpProfileEntry 17 }

    snmpProfile-AlarmClearTableLimit	OBJECT-TYPE
	SYNTAX	INTEGER
	ACCESS	read-write
	STATUS	mandatory
	DESCRIPTION	"The maximum number of alarmCleared entries that can be held in the alarmCleared table."
	::= { mibsnmpProfileEntry 18 }

    snmpProfile-Action-o	OBJECT-TYPE
	SYNTAX	INTEGER {
		    noAction (1),
		    createProfile (2),
		    deleteProfile (3)
		}
	ACCESS	read-write
	STATUS	mandatory
	DESCRIPTION	""
	::= { mibsnmpProfileEntry 14 }


	-- The mibsnmpv3NotifyProfile table
	--
	-- This table contains parameters for the mibsnmpv3NotifyProfile profile
	--

    mibsnmpv3NotifyProfileTable	OBJECT-TYPE
	SYNTAX		SEQUENCE OF Mibsnmpv3NotifyProfileEntry
	ACCESS		not-accessible
	STATUS		mandatory
	DESCRIPTION	"A list of mibsnmpv3NotifyProfile profile entries."
	::= { mibsnmpv3NotifyProfile 1 }

    mibsnmpv3NotifyProfileEntry	OBJECT-TYPE
	SYNTAX		Mibsnmpv3NotifyProfileEntry
	ACCESS		not-accessible
	STATUS		mandatory
	DESCRIPTION	"A mibsnmpv3NotifyProfile entry containing objects that
			 maps to the parameters of mibsnmpv3NotifyProfile profile."
	INDEX		{ snmpv3NotifyProfile-Name }
	::= { mibsnmpv3NotifyProfileTable 1 }

    Mibsnmpv3NotifyProfileEntry ::=
	SEQUENCE {
	    snmpv3NotifyProfile-Name
		OCTET STRING,
	    snmpv3NotifyProfile-ActiveEnabled
		INTEGER,
	    snmpv3NotifyProfile-Tag
		OCTET STRING,
	    snmpv3NotifyProfile-Type
		INTEGER,
	    snmpv3NotifyProfile-Action-o
		INTEGER
	}

    snmpv3NotifyProfile-Name	OBJECT-TYPE
	SYNTAX	OCTET STRING
	ACCESS	read-only
	STATUS	mandatory
	DESCRIPTION	"Any arbitrary, but unique identifier associated with this profile"
	::= { mibsnmpv3NotifyProfileEntry 1 }

    snmpv3NotifyProfile-ActiveEnabled	OBJECT-TYPE
	SYNTAX	INTEGER {
		    no (1),
		    yes (2)
		}
	ACCESS	read-write
	STATUS	mandatory
	DESCRIPTION	"TRUE if this profile is enabled for generation of SNMP messages"
	::= { mibsnmpv3NotifyProfileEntry 2 }

    snmpv3NotifyProfile-Tag	OBJECT-TYPE
	SYNTAX	OCTET STRING
	ACCESS	read-write
	STATUS	mandatory
	DESCRIPTION	"Single tag value that is used to select entries in the snmpTargetAddrTable ( 'trap' profile). If this contains a string of zero length, no entries are selected."
	::= { mibsnmpv3NotifyProfileEntry 3 }

    snmpv3NotifyProfile-Type	OBJECT-TYPE
	SYNTAX	INTEGER {
		    trap (2),
		    inform (3)
		}
	ACCESS	read-only
	STATUS	mandatory
	DESCRIPTION	"Type of notification to be generated, i.e., Trap (unconfirmed class) or Inform (confirmed class). This field is for future use. Agent does not generate INFORM pdus."
	::= { mibsnmpv3NotifyProfileEntry 4 }

    snmpv3NotifyProfile-Action-o	OBJECT-TYPE
	SYNTAX	INTEGER {
		    noAction (1),
		    createProfile (2),
		    deleteProfile (3)
		}
	ACCESS	read-write
	STATUS	mandatory
	DESCRIPTION	""
	::= { mibsnmpv3NotifyProfileEntry 5 }


	-- The mibsnmpv3TargetParamProfile table
	--
	-- This table contains parameters for the mibsnmpv3TargetParamProfile profile
	--

    mibsnmpv3TargetParamProfileTable	OBJECT-TYPE
	SYNTAX		SEQUENCE OF Mibsnmpv3TargetParamProfileEntry
	ACCESS		not-accessible
	STATUS		mandatory
	DESCRIPTION	"A list of mibsnmpv3TargetParamProfile profile entries."
	::= { mibsnmpv3TargetParamProfile 1 }

    mibsnmpv3TargetParamProfileEntry	OBJECT-TYPE
	SYNTAX		Mibsnmpv3TargetParamProfileEntry
	ACCESS		not-accessible
	STATUS		mandatory
	DESCRIPTION	"A mibsnmpv3TargetParamProfile entry containing objects that
			 maps to the parameters of mibsnmpv3TargetParamProfile profile."
	INDEX		{ snmpv3TargetParamProfile-Name }
	::= { mibsnmpv3TargetParamProfileTable 1 }

    Mibsnmpv3TargetParamProfileEntry ::=
	SEQUENCE {
	    snmpv3TargetParamProfile-Name
		OCTET STRING,
	    snmpv3TargetParamProfile-ActiveEnabled
		INTEGER,
	    snmpv3TargetParamProfile-MsgProcModel
		INTEGER,
	    snmpv3TargetParamProfile-SecurityModel
		INTEGER,
	    snmpv3TargetParamProfile-SecurityName
		OCTET STRING,
	    snmpv3TargetParamProfile-SecurityLevel
		INTEGER,
	    snmpv3TargetParamProfile-Action-o
		INTEGER
	}

    snmpv3TargetParamProfile-Name	OBJECT-TYPE
	SYNTAX	OCTET STRING
	ACCESS	read-only
	STATUS	mandatory
	DESCRIPTION	"Any arbitrary, but unique identifier associated with this profile"
	::= { mibsnmpv3TargetParamProfileEntry 1 }

    snmpv3TargetParamProfile-ActiveEnabled	OBJECT-TYPE
	SYNTAX	INTEGER {
		    no (1),
		    yes (2)
		}
	ACCESS	read-write
	STATUS	mandatory
	DESCRIPTION	"TRUE if this profile is enabled for generation of SNMP messages"
	::= { mibsnmpv3TargetParamProfileEntry 2 }

    snmpv3TargetParamProfile-MsgProcModel	OBJECT-TYPE
	SYNTAX	INTEGER {
		    v1 (1),
		    v3 (4)
		}
	ACCESS	read-write
	STATUS	mandatory
	DESCRIPTION	"Message processing model used when generating SNMP messages using this entry"
	::= { mibsnmpv3TargetParamProfileEntry 3 }

    snmpv3TargetParamProfile-SecurityModel	OBJECT-TYPE
	SYNTAX	INTEGER {
		    v1 (2),
		    v3Usm (4)
		}
	ACCESS	read-write
	STATUS	mandatory
	DESCRIPTION	"Security model to be used when generating SNMP messages using this entry"
	::= { mibsnmpv3TargetParamProfileEntry 4 }

    snmpv3TargetParamProfile-SecurityName	OBJECT-TYPE
	SYNTAX	OCTET STRING
	ACCESS	read-write
	STATUS	mandatory
	DESCRIPTION	"Security name which identifies the principal on whose behalf SNMP messages will be generated using this entry. This name should be a valid snmpv3-usm-user"
	::= { mibsnmpv3TargetParamProfileEntry 5 }

    snmpv3TargetParamProfile-SecurityLevel	OBJECT-TYPE
	SYNTAX	INTEGER {
		    none (1),
		    authNopriv (2),
		    authPriv (3)
		}
	ACCESS	read-write
	STATUS	mandatory
	DESCRIPTION	"Level of security to be used when generating messages using this entry."
	::= { mibsnmpv3TargetParamProfileEntry 6 }

    snmpv3TargetParamProfile-Action-o	OBJECT-TYPE
	SYNTAX	INTEGER {
		    noAction (1),
		    createProfile (2),
		    deleteProfile (3)
		}
	ACCESS	read-write
	STATUS	mandatory
	DESCRIPTION	""
	::= { mibsnmpv3TargetParamProfileEntry 7 }

END
