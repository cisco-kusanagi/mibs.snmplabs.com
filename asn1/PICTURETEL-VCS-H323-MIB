PICTURETEL-VCS-H323-MIB DEFINITIONS ::= BEGIN

IMPORTS
	MODULE-IDENTITY, OBJECT-TYPE, OBJECT-IDENTITY, Gauge32, Integer32, enterprises
FROM SNMPv2-SMI
	TruthValue, DisplayString
FROM SNMPv2-TC
	CallBandwidthType, VideoAlgorithmType, AudioAlgorithmType, DataProtocolType, VideoResolutionType, MediaChannelStatusType, ptH323
FROM PICTURETEL-VCS-MIB;

pictureTelVCSH323Module MODULE-IDENTITY
	LAST-UPDATED "0101030000Z"
	ORGANIZATION "PictureTel Corporation"
	CONTACT-INFO
		"
		Postal:	PictureTel Corporation
				100 Minuteman Drive
				Andover, MA 01810-1031
				USA"
	DESCRIPTION
		"Final version of the PictureTel H.323 MIB"
	REVISION	"0101030000Z"
	DESCRIPTION
		"Rev 0.0.11
		3 Jan 2001 12:00  
		Latest version of MIB module PICTURETEL-VCS-H323-MIB"

::= { ptH323 1 }


--
-- H323 placeholders
--


ptH323Statistics           OBJECT-IDENTITY
	STATUS          current
	DESCRIPTION     "Subtree for H.323 statistics"
	::= { pictureTelVCSH323Module 1 }


ptH323CallStat             OBJECT-IDENTITY
	STATUS          current
	DESCRIPTION     "Subtree for H.323 call statistics"
	::= { ptH323Statistics 1 }


ptH323ChannelStat             OBJECT-IDENTITY
	STATUS          current
	DESCRIPTION     "Subtree for H.245 logical channel statistics"
	::= { ptH323Statistics 2 }


ptH323VideoStat             OBJECT-IDENTITY
	STATUS          current
	DESCRIPTION     "Subtree for H.323 video statistics"
	::= { ptH323Statistics 3 }


ptH323AudioStat             OBJECT-IDENTITY
	STATUS          current
	DESCRIPTION     "Subtree for H.323 audio statistics"
	::= { ptH323Statistics 4 }


ptH323MUXStat             OBJECT-IDENTITY
	STATUS          current
	DESCRIPTION     "Subtree for H.323 MUX call statistics"
	::= { ptH323Statistics 5 }

ptH323VideoNumberOfEncoders   OBJECT-TYPE
	SYNTAX Integer32
	MAX-ACCESS	read-only
	STATUS          current
	DESCRIPTION     "Number of video encoders/decoders"
	::= { ptH323Statistics 6 }




--
-- H.323 Call Statistics
--

ptH323CallBandwidth  OBJECT-TYPE
	SYNTAX CallBandwidthType
	MAX-ACCESS	read-only
	STATUS          current
	DESCRIPTION     "Current call bandwidth"
	::= { ptH323CallStat 1 }


ptH323CallRestricted  OBJECT-TYPE
	SYNTAX TruthValue
	MAX-ACCESS	read-only
	STATUS          current
	DESCRIPTION     "Call in restricted mode"
	::= { ptH323CallStat 2 }




--
-- H.245 Logical Channel Statistic
--


ptH323ChannelStatTable         OBJECT-TYPE
	SYNTAX SEQUENCE OF PtH323ChannelStatEntry
	MAX-ACCESS	not-accessible
	STATUS          current
	DESCRIPTION     "H.245 logical channel statistics table"
	::= { ptH323ChannelStat 1 }


ptH323ChannelStatEntry         OBJECT-TYPE
	SYNTAX PtH323ChannelStatEntry
	MAX-ACCESS	not-accessible
	STATUS          current
	DESCRIPTION     "Logical row describing an entry in the
	                 H.245 logical channel statistics table"
	INDEX	{ ptH323ChannelStatIndex }
	::= { ptH323ChannelStatTable 1 }


PtH323ChannelStatEntry ::= SEQUENCE {
	ptH323ChannelStatIndex                   Integer32,
	ptH323ChannelVideoTransmitToFarEnd       MediaChannelStatusType,
	ptH323ChannelVideoReceiveFromFarEnd      MediaChannelStatusType
	}


ptH323ChannelStatIndex  OBJECT-TYPE
	SYNTAX	Integer32
	MAX-ACCESS	read-only
	STATUS	current
	DESCRIPTION     "Index of the H245 logical video channel 
	                 statistics in the table."
	::= { ptH323ChannelStatEntry 1 }


ptH323ChannelVideoTransmitToFarEnd  OBJECT-TYPE
	SYNTAX MediaChannelStatusType
	MAX-ACCESS	read-only
	STATUS          current
	DESCRIPTION      "Status of the video channel that is used 
	                  to transmit data to the far end"
	::= { ptH323ChannelStatEntry 2 }


ptH323ChannelVideoReceiveFromFarEnd  OBJECT-TYPE
	SYNTAX MediaChannelStatusType
	MAX-ACCESS	read-only
	STATUS          current
	DESCRIPTION      "Status of the video channel that is used 
	                  to receive data from the far end"
	::= { ptH323ChannelStatEntry 3 }


ptH323ChannelAudioTransmitToFarEnd  OBJECT-TYPE
	SYNTAX MediaChannelStatusType
	MAX-ACCESS	read-only
	STATUS          current
	DESCRIPTION      "Status of the audio channel that is used 
	                  to transmit data to the far end"
	::= { ptH323ChannelStat 2 }


ptH323ChannelAudioReceiveFromFarEnd  OBJECT-TYPE
	SYNTAX MediaChannelStatusType
	MAX-ACCESS	read-only
	STATUS          current
	DESCRIPTION      "Status of the audio channel that is used 
	                  to receive data from the far end"
	::= { ptH323ChannelStat 3 }


ptH323ChannelTransmitT120Data  OBJECT-TYPE
	SYNTAX MediaChannelStatusType
	MAX-ACCESS	read-only
	STATUS          current
	DESCRIPTION     "Status of the T.120 transmit data channel"
	::= { ptH323ChannelStat 4 }


ptH323ChannelReceiveT120Data  OBJECT-TYPE
	SYNTAX MediaChannelStatusType
	MAX-ACCESS	read-only
	STATUS          current
	DESCRIPTION     "Status of the T.120 receive data channel"
	::= { ptH323ChannelStat 5 }



--
-- Video Statistics
--


ptH323VideoStatTable         OBJECT-TYPE
	SYNTAX SEQUENCE OF PtH323VideoStatEntry
	MAX-ACCESS	not-accessible
	STATUS          current
	DESCRIPTION     "H.323 video statistics table"
	::= { ptH323VideoStat 1 }


ptH323VideoStatEntry         OBJECT-TYPE
	SYNTAX PtH323VideoStatEntry
	MAX-ACCESS	not-accessible
	STATUS          current
	DESCRIPTION      "Logical row describing an entry in
	                  the H.323 video statistics table"
	INDEX	{ ptH323VideoStatIndex }
	::= { ptH323VideoStatTable 1 }


PtH323VideoStatEntry ::= SEQUENCE {
	ptH323VideoStatIndex                   Integer32,
	ptH323VideoTransmitAlgorithm           VideoAlgorithmType,
	ptH323VideoTransmitAnnex               DisplayString,
	ptH323VideoReceiveAlgorithm            VideoAlgorithmType,
	ptH323VideoReceiveAnnex                DisplayString,
	ptH323VideoTransmitTargetFrameRate     Gauge32,
	ptH323VideoTransmitActualFrameRate     Gauge32,
	ptH323VideoReceiveActualFrameRate      Gauge32,
	ptH323VideoTransmitPictureFormat       VideoResolutionType,
	ptH323VideoReceivePictureFormat        VideoResolutionType,
	ptH323VideoTransmitTargetBitRate       Gauge32,
	ptH323VideoReceiveTargetBitRate        Gauge32,
	ptH323VideoTransmitActualBitRate       Gauge32,
	ptH323VideoReceiveActualBitRate        Gauge32,
	ptH323VideoTransmittedKeyFrames        Gauge32,
	ptH323VideoReceivedKeyFrames           Gauge32,
	ptH323VideoReceivedBitstreamErrors     Gauge32,
	ptH323VideoEncoderNoiseReductionFilter TruthValue,
	ptH323VideoDecoderPostFilters          TruthValue,
	ptH323VideoReceivedChecksumErrors      Gauge32,
	ptH323VideoTransmittedFrames           Gauge32,
	ptH323VideoReceivedFrames              Gauge32
	}


ptH323VideoStatIndex  OBJECT-TYPE
	SYNTAX	Integer32
	MAX-ACCESS	read-only
	STATUS	current
	DESCRIPTION
		"Index of the H.323 video statistics in the table"
	::= { ptH323VideoStatEntry 1 }


ptH323VideoTransmitAlgorithm   OBJECT-TYPE
	SYNTAX VideoAlgorithmType
	MAX-ACCESS	read-only
	STATUS          current
	DESCRIPTION      "Current transmit video algorithm 
	                  (for active state only)"
	::= { ptH323VideoStatEntry 2 }


ptH323VideoTransmitAnnex   OBJECT-TYPE
	SYNTAX DisplayString
	MAX-ACCESS	read-only
	STATUS          current
	DESCRIPTION      "Current transmit video annex 
	                  (for active state only)
	                  BOOL AnnexFAdvancedPrediction        : 1 bit
	                  BOOL AnnexJDeblockingFilter          : 1 bit
	                  BOOL AnnexNReferencePictureSelection : 1 bit
	                  BOOL AppendixIErrorTracking          : 1 bit
	                  int  AdditionalPictureMemory         : 3 bits
	                  BOOL CustomPicture640x480            : 1 bit
	                  BOOL CustomPicture704x480            : 1 bit
	                  BOOL CustomPicture800x600            : 1 bit
	                  BOOL CustomPicture1024x768           : 1 bit"
	::= { ptH323VideoStatEntry 3 }


ptH323VideoReceiveAlgorithm   OBJECT-TYPE
	SYNTAX VideoAlgorithmType
	MAX-ACCESS	read-only
	STATUS          current
	DESCRIPTION      "Current receive video algorithm 
	                  (for active state only)"
	::= { ptH323VideoStatEntry 4}


ptH323VideoReceiveAnnex   OBJECT-TYPE
	SYNTAX DisplayString
	MAX-ACCESS	read-only
	STATUS          current
	DESCRIPTION      "Current receive video annex 
	                  (for active state only)
	                  BOOL AnnexFAdvancedPrediction        : 1 bit
	                  BOOL AnnexJDeblockingFilter          : 1 bit
	                  BOOL AnnexNReferencePictureSelection : 1 bit
	                  BOOL AppendixIErrorTracking          : 1 bit
	                  int  AdditionalPictureMemory         : 3 bits
	                  BOOL CustomPicture640x480            : 1 bit
	                  BOOL CustomPicture704x480            : 1 bit
	                  BOOL CustomPicture800x600            : 1 bit
	                  BOOL CustomPicture1024x768           : 1 bit"
	::= { ptH323VideoStatEntry 5 }


ptH323VideoTransmitTargetFrameRate   OBJECT-TYPE
	SYNTAX Gauge32
	MAX-ACCESS	read-only
	STATUS          current
	DESCRIPTION      "Target transmit frame rate (for active 
	                  state only) - frames/sec"
	::= { ptH323VideoStatEntry 6 }


ptH323VideoTransmitActualFrameRate   OBJECT-TYPE
	SYNTAX Gauge32
	MAX-ACCESS	read-only
	STATUS          current
	DESCRIPTION      "Current average transmit frame rate 
	                  (for active state only) - frames/sec"
	::= { ptH323VideoStatEntry 7 }


ptH323VideoReceiveActualFrameRate   OBJECT-TYPE
	SYNTAX Gauge32
	MAX-ACCESS	read-only
	STATUS          current
	DESCRIPTION      "Current average receive frame rate 
	                  (for active state only) - frames/sec"
	::= { ptH323VideoStatEntry 8 }


ptH323VideoTransmitPictureFormat   OBJECT-TYPE
	SYNTAX VideoResolutionType
	MAX-ACCESS	read-only
	STATUS          current
	DESCRIPTION      "Current video picture format transmitted 
	                  (for active state only)"
	::= { ptH323VideoStatEntry 9 }


ptH323VideoReceivePictureFormat   OBJECT-TYPE
	SYNTAX VideoResolutionType
	MAX-ACCESS	read-only
	STATUS          current
	DESCRIPTION      "Current video picture format received 
	                  (for active state only)"
	::= { ptH323VideoStatEntry 10 }


ptH323VideoTransmitTargetBitRate   OBJECT-TYPE
	SYNTAX Gauge32
	MAX-ACCESS	read-only
	STATUS          current
	DESCRIPTION      "Number of bits per second allocated for video Tx"
	::= { ptH323VideoStatEntry 11 }


ptH323VideoReceiveTargetBitRate   OBJECT-TYPE
	SYNTAX Gauge32
	MAX-ACCESS	read-only
	STATUS          current
	DESCRIPTION      "Number of bits per second allocated for video Rx"
	::= { ptH323VideoStatEntry 12 }


ptH323VideoTransmitActualBitRate   OBJECT-TYPE
	SYNTAX Gauge32
	MAX-ACCESS	read-only
	STATUS          current
	DESCRIPTION      "Actual number of bits per second for video Tx
	                  (Active state only)"
	::= { ptH323VideoStatEntry 13 }


ptH323VideoReceiveActualBitRate   OBJECT-TYPE
	SYNTAX Gauge32
	MAX-ACCESS	read-only
	STATUS          current
	DESCRIPTION      "Actual number of bits per second for video Rx
	                  (Active state only)"
	::= { ptH323VideoStatEntry 14 }


ptH323VideoTransmittedKeyFrames   OBJECT-TYPE
	SYNTAX Gauge32
	MAX-ACCESS	read-only
	STATUS          current
	DESCRIPTION      "Number of the key (intra) frames sent"
	::= { ptH323VideoStatEntry 15 }


ptH323VideoReceivedKeyFrames   OBJECT-TYPE
	SYNTAX Gauge32
	MAX-ACCESS	read-only
	STATUS          current
	DESCRIPTION      "Number of the key (intra) frames received"
	::= { ptH323VideoStatEntry 16 }


ptH323VideoReceivedBitstreamErrors   OBJECT-TYPE
	SYNTAX Gauge32
	MAX-ACCESS	read-only
	STATUS          current
	DESCRIPTION      "Number of the bitstream errors received"
	::= { ptH323VideoStatEntry 17}


ptH323VideoEncoderNoiseReductionFilter   OBJECT-TYPE
	SYNTAX TruthValue
	MAX-ACCESS	read-only
	STATUS          current
	DESCRIPTION      "State of noise reduction filter
	                  (true/false)"
	::= { ptH323VideoStatEntry 18}


ptH323VideoDecoderPostFilters   OBJECT-TYPE
	SYNTAX TruthValue
	MAX-ACCESS	read-only
	STATUS          current
	DESCRIPTION      "State of decoder post filters
	                  (true/false)"
	::= { ptH323VideoStatEntry 19}


ptH323VideoReceivedChecksumErrors   OBJECT-TYPE
	SYNTAX Gauge32
	MAX-ACCESS	read-only
	STATUS          current
	DESCRIPTION      "Number of checksum errors received"
	::= { ptH323VideoStatEntry 20}


ptH323VideoTransmittedFrames   OBJECT-TYPE
	SYNTAX Gauge32
	MAX-ACCESS	read-only
	STATUS          current
	DESCRIPTION      "Number of transmitted frames"
	::= { ptH323VideoStatEntry 21}


ptH323VideoReceivedFrames   OBJECT-TYPE
	SYNTAX Gauge32
	MAX-ACCESS	read-only
	STATUS          current
	DESCRIPTION      "Number of received frames"
	::= { ptH323VideoStatEntry 22}


--
-- H323 Audio Statistics
--

ptH323AudioTransmitAlgorithm         OBJECT-TYPE
	SYNTAX AudioAlgorithmType
	MAX-ACCESS	read-only
	STATUS          current
	DESCRIPTION      "Current transmit audio algorithm"
	::= { ptH323AudioStat 1 }


ptH323AudioReceiveAlgorithm          OBJECT-TYPE
	SYNTAX AudioAlgorithmType
	MAX-ACCESS	read-only
	STATUS          current
	DESCRIPTION      "Current receive audio algorithm"
	::= { ptH323AudioStat 2 }


ptH323AudioTransmitActualBitRate     OBJECT-TYPE
	SYNTAX Gauge32
	MAX-ACCESS	read-only
	STATUS          current
	DESCRIPTION      "Actual transmit bit rate (bits/sec)"
	::= { ptH323AudioStat 3 }


ptH323AudioReceiveActualBitRate      OBJECT-TYPE
	SYNTAX Gauge32
	MAX-ACCESS	read-only
	STATUS          current
	DESCRIPTION      "Actual receive bit rate (bits/sec)"
	::= { ptH323AudioStat 4 }


ptH323AudioSilentPacketsToMUX      OBJECT-TYPE
	SYNTAX Gauge32
	MAX-ACCESS	read-only
	STATUS          current
	DESCRIPTION     "Number of silent audio packets sent to MUX"
	::= { ptH323AudioStat 5 }


ptH323AudioDecoderDiscardedFrames      OBJECT-TYPE
	SYNTAX Gauge32
	MAX-ACCESS	read-only
	STATUS          current
	DESCRIPTION      "Number of discarded decoder frames "
	::= { ptH323AudioStat 6 }


ptH323AudioDecoderInsertedSilenceFrames    OBJECT-TYPE
	SYNTAX Gauge32
	MAX-ACCESS	read-only
	STATUS          current
	DESCRIPTION     "Number of inserted silence frames"
	::= { ptH323AudioStat 7 }





--
-- MUX Statistic
--


ptH323MUXCurrentJitterDelay             OBJECT-TYPE
	SYNTAX Gauge32
	MAX-ACCESS	read-only
	STATUS          current
	DESCRIPTION     "Current jitter delay (msec)"
	::= { ptH323MUXStat 1 }


ptH323MUXAudioStat             OBJECT-IDENTITY
	STATUS          current
	DESCRIPTION     "Subtree for H.323 MUX audio channel statistics"
	::= { ptH323MUXStat 2 }


ptH323MUXVideoStat             OBJECT-IDENTITY
	STATUS          current
	DESCRIPTION     "Subtree for H.323 MUX video channel statistics"
	::= { ptH323MUXStat 3 }


ptH323MUXH245Stat             OBJECT-IDENTITY
	STATUS          current
	DESCRIPTION     "Subtree for H.323 MUX H.245 channel statistics"
	::= { ptH323MUXStat 4 }


--
-- MUX Audio channel Statistic
--


ptH323MUXAudioPacketsSent           OBJECT-TYPE
	SYNTAX Gauge32
	MAX-ACCESS	read-only
	STATUS          current
	DESCRIPTION     "Total number of packets sent by MUX
	                  for the audio channel"
	::= { ptH323MUXAudioStat 1 }


ptH323MUXAudioBytesSent             OBJECT-TYPE
	SYNTAX Gauge32
	MAX-ACCESS	read-only
	STATUS          current
	DESCRIPTION     "Total number of bytes sent by MUX
	                  for the audio channel"
	::= { ptH323MUXAudioStat 2 }


ptH323MUXAudioPacketsReceived       OBJECT-TYPE
	SYNTAX Gauge32
	MAX-ACCESS	read-only
	STATUS          current
	DESCRIPTION     "Total number of packets received by MUX
	                  for the audio channel"
	::= { ptH323MUXAudioStat 3 }


ptH323MUXAudioBytesReceived         OBJECT-TYPE
	SYNTAX Gauge32
	MAX-ACCESS	read-only
	STATUS          current
	DESCRIPTION     "Total number of bytes received by MUX
	                  for the audio channel"
	::= { ptH323MUXAudioStat 4 }


ptH323MUXAudioPacketsLost           OBJECT-TYPE
	SYNTAX Gauge32
	MAX-ACCESS	read-only
	STATUS          current
	DESCRIPTION     "Total number of packets lost in 
	                  network - never received by MUX - 
	                  for the audio channel"
	::= { ptH323MUXAudioStat 5 }


ptH323MUXAudioPacketsOutOfOrder     OBJECT-TYPE
	SYNTAX Gauge32
	MAX-ACCESS	read-only
	STATUS          current
	DESCRIPTION     "Total number of packets received by MUX 
	                  that are out of order, but within jitter
	                  for the audio channel"
	::= { ptH323MUXAudioStat 6 }


ptH323MUXAudioPacketsLate           OBJECT-TYPE
	SYNTAX Gauge32
	MAX-ACCESS	read-only
	STATUS          current
	DESCRIPTION     "Total number of packets received by MUX 
	                  that are outside of the jitter window
	                  for the audio channel"
	::= { ptH323MUXAudioStat 7 }


ptH323MUXAudioPacketsDiscarded      OBJECT-TYPE
	SYNTAX Gauge32
	MAX-ACCESS	read-only
	STATUS          current
	DESCRIPTION     "Total number of packets discarded due 
	                  to a bad RTP header for the audio channel"
	::= { ptH323MUXAudioStat 8 }


ptH323MUXAudioPacketJitter          OBJECT-TYPE
	SYNTAX Gauge32
	MAX-ACCESS	read-only
	STATUS          current
	DESCRIPTION     "Average audio packet jitter (msec)"
	::= { ptH323MUXAudioStat 9 }


ptH323MUXAudioMinRoundTripLatency   OBJECT-TYPE
	SYNTAX Gauge32
	MAX-ACCESS	read-only
	STATUS          current
	DESCRIPTION      "Minimum round-trip latency
	                  for the audio channel"
	::= { ptH323MUXAudioStat 10 }


ptH323MUXAudioMaxRoundTripLatency   OBJECT-TYPE
	SYNTAX Gauge32
	MAX-ACCESS	read-only
	STATUS          current
	DESCRIPTION      "Maximum round-trip latency
	                  for the audio channel"
	::= { ptH323MUXAudioStat 11 }


ptH323MUXAudioAvgRoundTripLatency   OBJECT-TYPE
	SYNTAX Gauge32
	MAX-ACCESS	read-only
	STATUS          current
	DESCRIPTION      "Average round-trip latency
	                  for the audio channel"
	::= { ptH323MUXAudioStat 12 }


--
-- MUX Video channel Statistic
--


ptH323MUXVideoStatTable         OBJECT-TYPE
	SYNTAX SEQUENCE OF PtH323MUXVideoStatEntry
	MAX-ACCESS	not-accessible
	STATUS          current
	DESCRIPTION      "H.323 MUX video channel statistics table"
	::= { ptH323MUXVideoStat 1 }


ptH323MUXVideoStatEntry         OBJECT-TYPE
	SYNTAX PtH323MUXVideoStatEntry
	MAX-ACCESS	not-accessible
	STATUS          current
	DESCRIPTION      "Logical row describing an entry in the
	                  H.323 MUX video channel statistics table"
	INDEX	{ ptH323MUXVideoStatIndex }
	::= { ptH323MUXVideoStatTable 1 }


PtH323MUXVideoStatEntry ::= SEQUENCE {
	ptH323MUXVideoStatIndex              Integer32,
	ptH323MUXVideoPacketsSent            Gauge32,
	ptH323MUXVideoBytesSent              Gauge32,
	ptH323MUXVideoPacketsReceived        Gauge32,
	ptH323MUXVideoBytesReceived          Gauge32,
	ptH323MUXVideoPacketsLost            Gauge32,
	ptH323MUXVideoPacketsOutOfOrder      Gauge32,
	ptH323MUXVideoPacketsLate            Gauge32,
	ptH323MUXVideoPacketsDiscarded       Gauge32,
	ptH323MUXVideoPacketJitter           Gauge32,
	ptH323MUXVideoMinRoundTripLatency    Gauge32,
	ptH323MUXVideoMaxRoundTripLatency    Gauge32,
	ptH323MUXVideoAvgRoundTripLatency    Gauge32
	}



ptH323MUXVideoStatIndex   OBJECT-TYPE
	SYNTAX Integer32
	MAX-ACCESS	read-only
	STATUS          current
	DESCRIPTION      "The index of the H.323 MUX video channel
	                  statistics in the table"
	::= { ptH323MUXVideoStatEntry 1 }


ptH323MUXVideoPacketsSent           OBJECT-TYPE
	SYNTAX Gauge32
	MAX-ACCESS	read-only
	STATUS          current
	DESCRIPTION      "Total number of packets sent by MUX
	                  for the video channel"
	::= { ptH323MUXVideoStatEntry 2 }


ptH323MUXVideoBytesSent             OBJECT-TYPE
	SYNTAX Gauge32
	MAX-ACCESS	read-only
	STATUS          current
	DESCRIPTION      "Total number of bytes sent by MUX
	                  for the video channel"
	::= { ptH323MUXVideoStatEntry 3 }


ptH323MUXVideoPacketsReceived        OBJECT-TYPE
	SYNTAX Gauge32
	MAX-ACCESS	read-only
	STATUS          current
	DESCRIPTION      "Total number of packets received by MUX
	                  for the video channel"
	::= { ptH323MUXVideoStatEntry 4 }


ptH323MUXVideoBytesReceived          OBJECT-TYPE
	SYNTAX Gauge32
	MAX-ACCESS	read-only
	STATUS          current
	DESCRIPTION      "Total number of bytes received by MUX
	                  for the video channel"
	::= { ptH323MUXVideoStatEntry 5 }


ptH323MUXVideoPacketsLost           OBJECT-TYPE
	SYNTAX Gauge32
	MAX-ACCESS	read-only
	STATUS          current
	DESCRIPTION      "Total number of packets lost in network
	                  (never received by MUX) for the video channel"
	::= { ptH323MUXVideoStatEntry 6 }


ptH323MUXVideoPacketsOutOfOrder     OBJECT-TYPE
	SYNTAX Gauge32
	MAX-ACCESS	read-only
	STATUS          current
	DESCRIPTION      "Total number of packets received by MUX 
	                  that are out of order, but within jitter
	                  for the video channel"
	::= { ptH323MUXVideoStatEntry 7 }


ptH323MUXVideoPacketsLate           OBJECT-TYPE
	SYNTAX Gauge32
	MAX-ACCESS	read-only
	STATUS          current
	DESCRIPTION      "Total number of packets received by MUX 
	                  that are outside of the jitter window
	                  for the video channel"
	::= { ptH323MUXVideoStatEntry 8 }


ptH323MUXVideoPacketsDiscarded      OBJECT-TYPE
	SYNTAX Gauge32
	MAX-ACCESS	read-only
	STATUS          current
	DESCRIPTION      "Total number of packets discarded due 
	                  to a bad RTP header for the video channel"
	::= { ptH323MUXVideoStatEntry 9 }


ptH323MUXVideoPacketJitter          OBJECT-TYPE
	SYNTAX Gauge32
	MAX-ACCESS	read-only
	STATUS          current
	DESCRIPTION      "Average video packet jitter (msec)"
	::= { ptH323MUXVideoStatEntry 10 }


ptH323MUXVideoMinRoundTripLatency   OBJECT-TYPE
	SYNTAX Gauge32
	MAX-ACCESS	read-only
	STATUS          current
	DESCRIPTION      "Minimum round-trip latency
	                  for the video channel"
	::= { ptH323MUXVideoStatEntry 11 }


ptH323MUXVideoMaxRoundTripLatency   OBJECT-TYPE
	SYNTAX Gauge32
	MAX-ACCESS	read-only
	STATUS          current
	DESCRIPTION      "Maximum round-trip latency
	                  for the video channel"
	::= { ptH323MUXVideoStatEntry 12 }


ptH323MUXVideoAvgRoundTripLatency   OBJECT-TYPE
	SYNTAX Gauge32
	MAX-ACCESS	read-only
	STATUS          current
	DESCRIPTION      "Average round-trip latency
	                  for the video channel"
	::= { ptH323MUXVideoStatEntry 13 }


--
-- MUX H.245 control channel Statistic
--


ptH323MUXH245PacketsSent            OBJECT-TYPE
	SYNTAX Gauge32
	MAX-ACCESS	read-only
	STATUS          current
	DESCRIPTION      "Total number of packets sent by MUX"
	::= { ptH323MUXH245Stat  1 }


ptH323MUXH245BytesSent             OBJECT-TYPE
	SYNTAX Gauge32
	MAX-ACCESS	read-only
	STATUS          current
	DESCRIPTION      "Total number of bytes sent by MUX"
	::= { ptH323MUXH245Stat 2 }


ptH323MUXH245PacketsReceived        OBJECT-TYPE
	SYNTAX Gauge32
	MAX-ACCESS	read-only
	STATUS          current
	DESCRIPTION      "Total number of packets received by MUX"
	::= { ptH323MUXH245Stat 3 }


ptH323MUXH245BytesReceived          OBJECT-TYPE
	SYNTAX Gauge32
	MAX-ACCESS	read-only
	STATUS          current
	DESCRIPTION      "Total number of bytes received by MUX"
	::= { ptH323MUXH245Stat 4 }


ptH323MUXH245PacketsDiscarded      OBJECT-TYPE
	SYNTAX Gauge32
	MAX-ACCESS	read-only
	STATUS          current
	DESCRIPTION      "Total number of packets discarded due 
	                  to a bad RTP header"
	::= { ptH323MUXH245Stat 5 }





END
