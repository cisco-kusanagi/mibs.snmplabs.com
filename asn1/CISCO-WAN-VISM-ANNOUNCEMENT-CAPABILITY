-- *****************************************************************
-- CISCO-WAN-VISM-ANNOUNCEMENT-CAPABILITY.my   MIB
--
-- AGENT-CAPABILITIES MIB for CISCO-WAN-ANNOUNCEMENT-MIB.my in the VISM product
--
-- Copyright(c) 2000, 2001 by Cisco Systems,Inc.
--
-- Author: Mike Manley
--
-- 2001/09/28 Results from initial internal MIB externalinterfaces review. 
--
-- *****************************************************************

CISCO-WAN-VISM-ANNOUNCEMENT-CAPABILITY DEFINITIONS ::= BEGIN

IMPORTS
        MODULE-IDENTITY,
        Integer32
                FROM SNMPv2-SMI
        DisplayString       
                FROM SNMPv2-TC                        
        AGENT-CAPABILITIES
                FROM SNMPv2-CONF
        ciscoWanAgentCapability
                FROM CISCOWAN-SMI;

cwAnnouncementCapability MODULE-IDENTITY
        LAST-UPDATED    "200112260000Z"
        ORGANIZATION    "Cisco Systems, Inc."
        CONTACT-INFO
                "       Cisco Systems
                        Customer Service

                Postal: 170 W Tasman Drive
                        San Jose, CA  95134
                        USA

                        Tel: +1 800 553-NETS

                E-mail: cs-vism@cisco.com"
        DESCRIPTION
                "The Agent Capabilities for CISCO-WAN-ANNOUNCEMENT-MIB."

        REVISION        "200110110000Z"
        DESCRIPTION
                "Initial version of this MIB module"
        ::= { ciscoWanAgentCapability 354 }




cwAnnouncementCapabilityV3R00 AGENT-CAPABILITIES
    PRODUCT-RELEASE      "VISM Release3.0"
    STATUS               current
    DESCRIPTION          "CISCO-WAN-ANNOUNCEMENT-MIB Capabilities"

    SUPPORTS CISCO-WAN-ANNOUNCEMENT-MIB
    INCLUDES { cwAnnounceControlGroup,
               cwAnnounceTableGroup }


        VARIATION   cwAnnFileServerName
        SYNTAX      DisplayString(SIZE (1..64))
        DESCRIPTION "Supports a minimum of 1 character length File Server
                     Name to a maximum of 64 character length File Server
                     Name"


        VARIATION   cwAnnAgeTime
        SYNTAX      Integer32 (0..65535)
        DESCRIPTION "Valid range is 0 - 65535."


        VARIATION   cwAnnPrefixPath
        SYNTAX      DisplayString(SIZE (1..64))
        DESCRIPTION "Supports a minimum of 1 character length Prefix Path
                     Name to a maximum of 64 character length Prefix Path
                     Name"


        VARIATION   cwAnnReqTimeout
        SYNTAX      Integer32 (0..15)
        DESCRIPTION "Valid range is 0 - 15."


        VARIATION   cwAnnFileName
        SYNTAX      DisplayString(SIZE (1..64))
        DESCRIPTION "Supports a minimum of 1 character length File
                     Name to a maximum of 64 character length File
                     Name"



    ::= { cwAnnouncementCapability 1 }




END
