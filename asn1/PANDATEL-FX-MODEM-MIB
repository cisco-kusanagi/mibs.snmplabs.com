PANDATEL-FX-MODEM-MIB DEFINITIONS ::= BEGIN

 -- This is the private mib group section for the FX modems.
 -- Because these modems must be installed in the PANDATEL modem rack
 -- the PANDATEL-MODEM-MIB also applies.

 -- Ver.1.06    Sep.13.1999

        IMPORTS
                enterprises
                        FROM RFC1155-SMI
                DisplayString
                        FROM RFC1213-MIB
                OBJECT-TYPE
                        FROM RFC-1212
                mdmSpecifics, device-id
                        FROM PANDATEL-MODEM-MIB;

-- ********************** THE MDM-FX SUBTREE ******************************

-- the specific identifier is identical to the modem type integer
-- of the FX modem entries in the PANDATEL-MODEM-MIB mdmModemTable.

fx-modem      OBJECT IDENTIFIER ::= { device-id 502 }     -- chassis-mib

fx            OBJECT IDENTIFIER ::= { mdmSpecifics 502 }  -- this subtree

fxModemTable OBJECT-TYPE
        SYNTAX  SEQUENCE OF FxTableEntry
        ACCESS  not-accessible
        STATUS  mandatory
        DESCRIPTION
                "The table of all FX modems in this housing."
        ::= { fx 1 }

fxTableEntry OBJECT-TYPE
        SYNTAX  FxTableEntry
        ACCESS  not-accessible
        STATUS  mandatory
        DESCRIPTION
                "The index of the table."
        INDEX   { mdmRack, mdmModem, mdmPosition }
        ::= { fxModemTable 1 }

FxTableEntry ::= SEQUENCE {
        mdmRack
                INTEGER,
        mdmModem
                INTEGER,
        mdmPosition
                INTEGER,
        mdmModemName
                DisplayString,
        mdmRemoteAccessMode
                INTEGER,
        mdmForcedRemoteAccess
                INTEGER,
        mdmClockRecovery
                INTEGER,
        mdmInterfaceAlarmCondition
                INTEGER,
        mdmLineAlarmCondition
                INTEGER
        }

mdmRack OBJECT-TYPE
        SYNTAX  INTEGER
        ACCESS  read-only
        STATUS  mandatory
        DESCRIPTION
                "The index of the rack where the modem is installed."
        ::= { fxTableEntry 1 }

mdmModem OBJECT-TYPE
        SYNTAX  INTEGER
        ACCESS  read-only
        STATUS  mandatory
        DESCRIPTION
                "This variable displays the slot number where the
                 corresponding modem is installed in the rack."
        ::= { fxTableEntry 2 }

mdmPosition OBJECT-TYPE
        SYNTAX  INTEGER {
                local       (1),
                remote      (2)
                }
        ACCESS  read-only
        STATUS  mandatory
        DESCRIPTION
                "This variable displays the location of the corresponding
                 modem: 'local' or 'remote'.
                 The modem which is plugged into a managed rack is 'local',
                 the counterpart is 'remote'."
        ::= { fxTableEntry 3 }

mdmModemName OBJECT-TYPE
        SYNTAX  DisplayString
        ACCESS  read-only
        STATUS  mandatory
        DESCRIPTION
                "A verbal name of this modem."
        ::= { fxTableEntry 5 }

mdmRemoteAccessMode OBJECT-TYPE
        SYNTAX  INTEGER {
                other       (1),
                disable     (2),
                enable      (5)
        }
        ACCESS  read-write
        STATUS  mandatory
        DESCRIPTION
                "The possibility of remote management: 'enabled' or 'disabled'.
                 Once disabled remote management, it is not possible to enable
                 it at the remote unit."
        ::= { fxTableEntry 64 }

mdmForcedRemoteAccess OBJECT-TYPE
        SYNTAX  INTEGER {
                off         (1),
                on          (2)
        }
        ACCESS  read-write
        STATUS  mandatory
        DESCRIPTION
                "Activation of remote management: 'on' or 'off'.
                 Status 'on' enables management of remote unit. During this
                 process the link is restricted to management data. The
                 transmission of user data is interrupted.
                 Status 'off' disables management of remote unit. The link
                 transmits user data."
        ::= { fxTableEntry 65 }

mdmClockRecovery OBJECT-TYPE
        SYNTAX  INTEGER {
                other               (1),
                disable             (2),
                stm1-oc3-155mbps    (3),
                stm4-oc12-622mbps   (4),
                not-available       (100)
        }
        ACCESS  read-write
        STATUS  mandatory
        DESCRIPTION
                "The clock recovery and data retiming at interface and line port.
                 The remote unit's configuration changes simultaneously."
        ::= { fxTableEntry 70 }

mdmInterfaceAlarmCondition OBJECT-TYPE
        SYNTAX  INTEGER {
                other                        (1),
                disable                      (2),
                no-link-signal               (3),
                laser-fail                   (4),
                no-link-signal-or-laser-fail (5),
                not-available                (100)
        }
        ACCESS  read-write
        STATUS  mandatory
        DESCRIPTION
                "The alarm trigger mode at interface port: 'disable', i.e. no alarm
                 is triggered, 'no-link-signal', i.e. an alarm is triggered if
                 the link is down, 'laser-fail', i.e. an alarm is triggered
                 if the laser diode is defective, or 'no-link-signal-or-laser-fail',
                 i.e. the link is down or the laser diode is defective."
        ::= { fxTableEntry 98 }

mdmLineAlarmCondition OBJECT-TYPE
        SYNTAX  INTEGER {
                other                        (1),
                disable                      (2),
                no-link-signal               (3),
                laser-fail                   (4),
                no-link-signal-or-laser-fail (5),
                not-available                (100)
        }
        ACCESS  read-write
        STATUS  mandatory
        DESCRIPTION
                "The alarm trigger mode at line port: 'disable', i.e. no alarm
                 is triggered, 'link-signal', i.e. an alarm is triggered if
                 the link is down, 'laser-fail', i.e. an alarm is triggered
                 if the laser diode is defective, or 'link-signal-or-laser-fail',
                 i.e. the link is down or the laser diode is defective."
        ::= { fxTableEntry 99 }

END
