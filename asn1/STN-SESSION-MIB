-- *****************************************************************
--
-- stn-session.mib:  
--              Spring Tide Networks Session MIB file.
--
--
--      Copyright (c) 1999, 2000 by Spring Tide Networks, Inc.
--                      ALL RIGHTS RESERVED       
--
-- *****************************************************************

-- MIB Object definitions for Spring Tide Network sessions


STN-SESSION-MIB DEFINITIONS ::= BEGIN

    IMPORTS
        MODULE-IDENTITY,
        OBJECT-TYPE,
        NOTIFICATION-TYPE, 
        Unsigned32,
        TimeTicks
                FROM SNMPv2-SMI

        TEXTUAL-CONVENTION,
        DisplayString
                FROM SNMPv2-TC

        MODULE-COMPLIANCE 
                FROM SNMPv2-CONF

        stnSystems,
        stnNotification
                FROM SPRING-TIDE-NETWORKS-SMI

        StnUserFailureType,
        StnConfigFailureType
                FROM SPRING-TIDE-NETWORKS-TC

        stnEngineIndex, 
        stnEngineSlot,
        stnEngineCpu
                FROM STN-CHASSIS-MIB

        stnRouterIndex
                FROM STN-ROUTER-MIB;


    stnSessions     MODULE-IDENTITY
        LAST-UPDATED    "0002160000Z"
        ORGANIZATION    "Spring Tide Networks, Inc."
        CONTACT-INFO
                "
                Spring Tide Networks, Inc.
                Customer Service
                Postal: 3 Clock Tower Place
                        Maynard, MA 01754
                Tel:    1 888-786-4357
                Email:  stncs@springtidenet.com
                "
        DESCRIPTION     "This MIB module describes Spring Tide Networks
                         session objects."
        ::= { stnSystems 5 }


    --
    -- Top Level STN Session MIB Objects
    --
    stnSessionObjects           OBJECT IDENTIFIER ::= { stnSessions 1 }
    stnSessionMibConformance    OBJECT IDENTIFIER ::= { stnSessions 2 }
    stnSessionTrapVars          OBJECT IDENTIFIER ::= { stnSessions 3 }

    stnSession           OBJECT IDENTIFIER ::= { stnSessionObjects 1 }
    stnGlobalSession     OBJECT IDENTIFIER ::= { stnSessionObjects 2 }

    stnSessionsPpp       OBJECT IDENTIFIER ::= { stnSession 2 }
    stnSessionsL2tp      OBJECT IDENTIFIER ::= { stnSession 3 }
    stnSessionsPptp      OBJECT IDENTIFIER ::= { stnSession 4 }
    stnSessionsIpsec     OBJECT IDENTIFIER ::= { stnSession 5 }
    stnSessionsIke       OBJECT IDENTIFIER ::= { stnSession 6 }
    stnSessionsTelnet    OBJECT IDENTIFIER ::= { stnSession 7 }
    stnSessionsFtp       OBJECT IDENTIFIER ::= { stnSession 8 }
    stnSessionsFtpAlg    OBJECT IDENTIFIER ::= { stnSession 9 }
    stnSessionsConsole   OBJECT IDENTIFIER ::= { stnSession 10 }
    stnSessionsAggregate OBJECT IDENTIFIER ::= { stnSession 11 }
    stnSessionsEncaps    OBJECT IDENTIFIER ::= { stnSession 12 }
    stnSessionsSecureUser OBJECT IDENTIFIER ::= { stnSession 13 }
    stnSessionsRemoteConfig  OBJECT IDENTIFIER ::= { stnSession 14 }


    SessionOperStatus ::= TEXTUAL-CONVENTION
        STATUS    current
        DESCRIPTION
        "Operational status of a session."
        SYNTAX     INTEGER {    unknown(1),  
                                inactive(2),     
                                pend-active(3),
                                active(4),
                                pend-inactive(5)      
                                }

    --
    -- STN Session Table
    --

    stnSessionTable OBJECT-TYPE
        SYNTAX        SEQUENCE OF StnSessionEntry
        MAX-ACCESS    not-accessible
        STATUS        current
        DESCRIPTION   "A list of session entries."
        ::= { stnSession 1 }
 
    stnSessionEntry OBJECT-TYPE
        SYNTAX          StnSessionEntry
        MAX-ACCESS      not-accessible
        STATUS          current
        DESCRIPTION     "Entry contains information about a particular 
                        session."
        INDEX           { stnSessionIndex }
        ::= { stnSessionTable 1 }
 
    StnSessionEntry ::= SEQUENCE {
                stnSessionIndex       Unsigned32,
                stnSessionType        INTEGER,
                stnSessionContext     OCTET STRING,
                stnSessionOperStatus  SessionOperStatus,
                stnSessionLastChange  TimeTicks
                }

    stnSessionIndex OBJECT-TYPE
        SYNTAX          Unsigned32
        MAX-ACCESS      read-only
        STATUS          current
        DESCRIPTION     "A sequence number that identifies a session
                        entry in the table."
        ::= { stnSessionEntry 1 }

    stnSessionType OBJECT-TYPE     
        SYNTAX          INTEGER { 
                                unknown(1),       -- not applicable or other
                                ppp(2),         
                                l2tp-tunnel(3),     
                                pptp-tunnel(4),     
                                ipsec(5),
                                ike(6),
                                telnet(7),
                                ftp(8),
                                ftp-alg(9),
                                console(10),
                                encaps(11),
                                secure-user(12),
                                remote-config(13)
                                }
        MAX-ACCESS      read-only
        STATUS          current
        DESCRIPTION     "Indicates the session type."
        ::= { stnSessionEntry  2 }

    stnSessionContext OBJECT-TYPE
        SYNTAX          OCTET STRING (SIZE(0..256))
        MAX-ACCESS      read-only
        STATUS          current
        DESCRIPTION     "A unique context identifier associated with the
                        session."
        ::= { stnSessionEntry  3 }

    stnSessionOperStatus OBJECT-TYPE
        SYNTAX          SessionOperStatus
        MAX-ACCESS      read-only
        STATUS          current
        DESCRIPTION     "The operational status of the session."
        ::= { stnSessionEntry  4 }

    stnSessionLastChange OBJECT-TYPE
    SYNTAX      TimeTicks
       MAX-ACCESS  read-only
       STATUS      current
       DESCRIPTION
               "The value of sysUpTime at the time the session
                entered its current operational state."
       ::= { stnSessionEntry  5 }


    --
    -- PPP session counters
    --

    stnSessionPppTotalCount OBJECT-TYPE
        SYNTAX          Unsigned32
        MAX-ACCESS      read-only
        STATUS          current
        DESCRIPTION     "The total number of PPP sessions since system start."
        ::= { stnSessionsPpp 1 }

    stnSessionPppFailedCount OBJECT-TYPE
        SYNTAX          Unsigned32
        MAX-ACCESS      read-only
        STATUS          current
        DESCRIPTION     "The total number of failed sessions since system 
                         start."
        ::= { stnSessionsPpp 2 }

    stnSessionPppCurrentCount OBJECT-TYPE
        SYNTAX          Unsigned32
        MAX-ACCESS      read-only
        STATUS          current
        DESCRIPTION     "The total number of current PPP sessions."
        ::= { stnSessionsPpp 3 }

    stnSessionPppCurrentActiveCount OBJECT-TYPE
        SYNTAX          Unsigned32
        MAX-ACCESS      read-only
        STATUS          current
        DESCRIPTION     "The total number of current active PPP sessions."
        ::= { stnSessionsPpp 4 }


    --
    -- L2TP session counters
    --

    stnSessionL2tpTunnelTotalCount OBJECT-TYPE
        SYNTAX          Unsigned32
        MAX-ACCESS      read-only
        STATUS          current
        DESCRIPTION     "The total number of L2TP tunnel sessions
                         since system start."
        ::= { stnSessionsL2tp 1 }

    stnSessionL2tpTunnelFailedCount OBJECT-TYPE
        SYNTAX          Unsigned32
        MAX-ACCESS      read-only
        STATUS          current
        DESCRIPTION     "The total number of failed L2TP tunnel sessions 
                         since system start."
        ::= { stnSessionsL2tp 2 }

    stnSessionL2tpTunnelCurrentCount OBJECT-TYPE
        SYNTAX          Unsigned32
        MAX-ACCESS      read-only
        STATUS          current
        DESCRIPTION     "The total number of current L2TP tunnel sessions."
        ::= { stnSessionsL2tp 3 }

    stnSessionL2tpTunnelCurrentActiveCount OBJECT-TYPE
        SYNTAX          Unsigned32
        MAX-ACCESS      read-only
        STATUS          current
        DESCRIPTION     "The total number of current active L2TP 
                         tunnel sessions."
        ::= { stnSessionsL2tp 4 }


    --
    -- PPTP session counters
    --

    stnSessionPptpTunnelTotalCount OBJECT-TYPE
        SYNTAX          Unsigned32
        MAX-ACCESS      read-only
        STATUS          current
        DESCRIPTION     "The total number of PPTP tunnel sessions 
                         since system start."
        ::= { stnSessionsPptp 1 }

    stnSessionPptpTunnelFailedCount OBJECT-TYPE
        SYNTAX          Unsigned32
        MAX-ACCESS      read-only
        STATUS          current
        DESCRIPTION     "The total number of failed PPTP tunnel sessions 
                         since system start."
        ::= { stnSessionsPptp 2 }

    stnSessionPptpTunnelCurrentCount OBJECT-TYPE
        SYNTAX          Unsigned32
        MAX-ACCESS      read-only
        STATUS          current
        DESCRIPTION     "The total number of current PPTP tunnel sessions."
        ::= { stnSessionsPptp 3 }


    stnSessionPptpTunnelCurrentActiveCount OBJECT-TYPE
        SYNTAX          Unsigned32
        MAX-ACCESS      read-only
        STATUS          current
        DESCRIPTION     "The total number of current active PPTP 
                         tunnel sessions."
        ::= { stnSessionsPptp 4 }


    --
    -- IPSec session counters
    --

    stnSessionIpsecTotalCount OBJECT-TYPE
        SYNTAX          Unsigned32
        MAX-ACCESS      read-only
        STATUS          current
        DESCRIPTION     "The total number of IPSEC sessions
                         since system start."
        ::= { stnSessionsIpsec 1 }

    stnSessionIpsecFailedCount OBJECT-TYPE
        SYNTAX          Unsigned32
        MAX-ACCESS      read-only
        STATUS          current
        DESCRIPTION     "The total number of failed IPSEC sessions
                         since system start."
        ::= { stnSessionsIpsec 2 }

    stnSessionIpsecCurrentCount OBJECT-TYPE
        SYNTAX          Unsigned32
        MAX-ACCESS      read-only
        STATUS          current
        DESCRIPTION     "The total number of current IPSEC sessions."
        ::= { stnSessionsIpsec 3 }

    stnSessionIpsecCurrentActiveCount OBJECT-TYPE
        SYNTAX          Unsigned32
        MAX-ACCESS      read-only
        STATUS          current
        DESCRIPTION     "The total number of current active 
                         IPSEC sessions."
        ::= { stnSessionsIpsec 4 }


    --
    -- IKE session counters
    --

    stnSessionIkeTotalCount OBJECT-TYPE
        SYNTAX          Unsigned32
        MAX-ACCESS      read-only
        STATUS          current
        DESCRIPTION     "The total number of IKE sessions
                         since system start."
        ::= { stnSessionsIke 1 }

    stnSessionIkeFailedCount OBJECT-TYPE
        SYNTAX          Unsigned32
        MAX-ACCESS      read-only
        STATUS          current
        DESCRIPTION     "The total number of failed IKE sessions
                         since system start."
        ::= { stnSessionsIke 2 }

    stnSessionIkeCurrentCount OBJECT-TYPE
        SYNTAX          Unsigned32
        MAX-ACCESS      read-only
        STATUS          current
        DESCRIPTION     "The total number of current IKE sessions."
        ::= { stnSessionsIke 3 }

    stnSessionIkeCurrentActiveCount OBJECT-TYPE
        SYNTAX          Unsigned32
        MAX-ACCESS      read-only
        STATUS          current
        DESCRIPTION     "The total number of current active 
                         IKE sessions."
        ::= { stnSessionsIke 4 }


    --
    -- Telnet session counters
    --

    stnSessionTelnetTotalCount OBJECT-TYPE
        SYNTAX          Unsigned32
        MAX-ACCESS      read-only
        STATUS          current
        DESCRIPTION     "The total number of Telnet sessions
                         since system start."
        ::= { stnSessionsTelnet 1 }

    stnSessionTelnetFailedCount OBJECT-TYPE
        SYNTAX          Unsigned32
        MAX-ACCESS      read-only
        STATUS          current
        DESCRIPTION     "The total number of failed Telnet sessions
                         since system start."
        ::= { stnSessionsTelnet 2 }

    stnSessionTelnetCurrentCount OBJECT-TYPE
        SYNTAX          Unsigned32
        MAX-ACCESS      read-only
        STATUS          current
        DESCRIPTION     "The total number of current Telnet sessions."
        ::= { stnSessionsTelnet 3 }

    stnSessionTelnetCurrentActiveCount OBJECT-TYPE
        SYNTAX          Unsigned32
        MAX-ACCESS      read-only
        STATUS          current
        DESCRIPTION     "The total number of current active 
                         Telnet sessions."
        ::= { stnSessionsTelnet 4 }


    --
    -- FTP session counters
    --

    stnSessionFtpTotalCount OBJECT-TYPE
        SYNTAX          Unsigned32
        MAX-ACCESS      read-only
        STATUS          current
        DESCRIPTION     "The total number of FTP sessions
                         since system start."
        ::= { stnSessionsFtp 1 }

    stnSessionFtpFailedCount OBJECT-TYPE
        SYNTAX          Unsigned32
        MAX-ACCESS      read-only
        STATUS          current
        DESCRIPTION     "The total number of failed FTP sessions
                         since system start."
        ::= { stnSessionsFtp 2 }

    stnSessionFtpCurrentCount OBJECT-TYPE
        SYNTAX          Unsigned32
        MAX-ACCESS      read-only
        STATUS          current
        DESCRIPTION     "The total number of current FTP sessions."
        ::= { stnSessionsFtp 3 }

    stnSessionFtpCurrentActiveCount OBJECT-TYPE
        SYNTAX          Unsigned32
        MAX-ACCESS      read-only
        STATUS          current
        DESCRIPTION     "The total number of current active 
                         FTP sessions."
        ::= { stnSessionsFtp 4 }


    --
    -- FTP-ALG session counters
    --

    stnSessionFtpAlgTotalCount OBJECT-TYPE
        SYNTAX          Unsigned32
        MAX-ACCESS      read-only
        STATUS          current
        DESCRIPTION     "The total number of FTP-ALG sessions
                         since system start."
        ::= { stnSessionsFtpAlg 1 }

    stnSessionFtpAlgFailedCount OBJECT-TYPE
        SYNTAX          Unsigned32
        MAX-ACCESS      read-only
        STATUS          current
        DESCRIPTION     "The total number of failed FTP-ALG sessions
                         since system start."
        ::= { stnSessionsFtpAlg 2 }

    stnSessionFtpAlgCurrentCount OBJECT-TYPE
        SYNTAX          Unsigned32
        MAX-ACCESS      read-only
        STATUS          current
        DESCRIPTION     "The total number of current FTP-ALG sessions."
        ::= { stnSessionsFtpAlg 3 }

    stnSessionFtpAlgCurrentActiveCount OBJECT-TYPE
        SYNTAX          Unsigned32
        MAX-ACCESS      read-only
        STATUS          current
        DESCRIPTION     "The total number of current active 
                         FTP-ALG sessions."
        ::= { stnSessionsFtpAlg 4 }


    --
    -- Console session counters
    --

    stnSessionConsoleTotalCount OBJECT-TYPE
        SYNTAX          Unsigned32
        MAX-ACCESS      read-only
        STATUS          current
        DESCRIPTION     "The total number of console sessions
                         since system start."
        ::= { stnSessionsConsole 1 }

    stnSessionConsoleFailedCount OBJECT-TYPE
        SYNTAX          Unsigned32
        MAX-ACCESS      read-only
        STATUS          current
        DESCRIPTION     "The total number of failed console sessions
                         since system start."
        ::= { stnSessionsConsole 2 }

    stnSessionConsoleCurrentCount OBJECT-TYPE
        SYNTAX          Unsigned32
        MAX-ACCESS      read-only
        STATUS          current
        DESCRIPTION     "The total number of current console sessions."
        ::= { stnSessionsConsole 3 }

    stnSessionConsoleCurrentActiveCount OBJECT-TYPE
        SYNTAX          Unsigned32
        MAX-ACCESS      read-only
        STATUS          current
        DESCRIPTION     "The total number of current active 
                         console sessions."
        ::= { stnSessionsConsole 4 }


    --
    -- Aggregate session counters
    --

    stnSessionAggregateTotalCount OBJECT-TYPE
        SYNTAX          Unsigned32
        MAX-ACCESS      read-only
        STATUS          current
        DESCRIPTION     "The total number of sessions since system start."
        ::= { stnSessionsAggregate 1 }

    stnSessionAggregateFailedCount OBJECT-TYPE
        SYNTAX          Unsigned32
        MAX-ACCESS      read-only
        STATUS          current
        DESCRIPTION     "The total number of failed sessions since system 
                         start."
        ::= { stnSessionsAggregate 2 }

    stnSessionAggregateCurrentCount OBJECT-TYPE
        SYNTAX          Unsigned32
        MAX-ACCESS      read-only
        STATUS          current
        DESCRIPTION     "The total number of current sessions."
        ::= { stnSessionsAggregate 3 }

    stnSessionAggregateCurrentActiveCount OBJECT-TYPE
        SYNTAX          Unsigned32
        MAX-ACCESS      read-only
        STATUS          current
        DESCRIPTION     "The total number of current active sessions."
        ::= { stnSessionsAggregate 4 }


    --
    -- Encaps session counters
    --

    stnSessionEncapsTotalCount OBJECT-TYPE
        SYNTAX          Unsigned32
        MAX-ACCESS      read-only
        STATUS          current
        DESCRIPTION     "The total number of encaps sessions
                         since system start."
        ::= { stnSessionsEncaps 1 }

    stnSessionEncapsFailedCount OBJECT-TYPE
        SYNTAX          Unsigned32
        MAX-ACCESS      read-only
        STATUS          current
        DESCRIPTION     "The total number of failed encaps sessions
                         since system start."
        ::= { stnSessionsEncaps 2 }

    stnSessionEncapsCurrentCount OBJECT-TYPE
        SYNTAX          Unsigned32
        MAX-ACCESS      read-only
        STATUS          current
        DESCRIPTION     "The total number of current encaps sessions."
        ::= { stnSessionsEncaps 3 }

    stnSessionEncapsCurrentActiveCount OBJECT-TYPE
        SYNTAX          Unsigned32
        MAX-ACCESS      read-only
        STATUS          current
        DESCRIPTION     "The total number of current active 
                         encaps sessions."
        ::= { stnSessionsEncaps 4 }


    --
    -- Secure user session counters
    --

    stnSessionSecureUserTotalCount OBJECT-TYPE
        SYNTAX          Unsigned32
        MAX-ACCESS      read-only
        STATUS          current
        DESCRIPTION     "The total number of secure user sessions
                         since system start."
        ::= { stnSessionsSecureUser 1 }

    stnSessionSecureUserFailedCount OBJECT-TYPE
        SYNTAX          Unsigned32
        MAX-ACCESS      read-only
        STATUS          current
        DESCRIPTION     "The total number of failed secure user sessions
                         since system start."
        ::= { stnSessionsSecureUser 2 }

    stnSessionSecureUserCurrentCount OBJECT-TYPE
        SYNTAX          Unsigned32
        MAX-ACCESS      read-only
        STATUS          current
        DESCRIPTION     "The total number of current secure user sessions."
        ::= { stnSessionsSecureUser 3 }

    stnSessionSecureUserCurrentActiveCount OBJECT-TYPE
        SYNTAX          Unsigned32
        MAX-ACCESS      read-only
        STATUS          current
        DESCRIPTION     "The total number of current active 
                         secure user sessions."
        ::= { stnSessionsSecureUser 4 }


    --
    -- Remote config session counters
    --

    stnSessionRemoteConfigTotalCount OBJECT-TYPE
        SYNTAX          Unsigned32
        MAX-ACCESS      read-only
        STATUS          current
        DESCRIPTION     "The total number of remote config sessions
                         since system start."
        ::= { stnSessionsRemoteConfig 1 }

    stnSessionRemoteConfigFailedCount OBJECT-TYPE
        SYNTAX          Unsigned32
        MAX-ACCESS      read-only
        STATUS          current
        DESCRIPTION     "The total number of failed remote config sessions
                         since system start."
        ::= { stnSessionsRemoteConfig 2 }

    stnSessionRemoteConfigCurrentCount OBJECT-TYPE
        SYNTAX          Unsigned32
        MAX-ACCESS      read-only
        STATUS          current
        DESCRIPTION     "The total number of current remote config sessions."
        ::= { stnSessionsRemoteConfig 3 }

    stnSessionRemoteConfigCurrentActiveCount OBJECT-TYPE
        SYNTAX          Unsigned32
        MAX-ACCESS      read-only
        STATUS          current
        DESCRIPTION     "The total number of current active 
                         remote config sessions."
        ::= { stnSessionsRemoteConfig 4 }


    --
    -- STN Global Session Table
    --

    stnGlobalSessionTable OBJECT-TYPE
        SYNTAX        SEQUENCE OF StnGlobalSessionEntry
        MAX-ACCESS    not-accessible
        STATUS        current
        DESCRIPTION   "A list of session entries with the box."
        ::= { stnGlobalSession 1 }
 
    stnGlobalSessionEntry OBJECT-TYPE
        SYNTAX          StnGlobalSessionEntry
        MAX-ACCESS      not-accessible
        STATUS          current
        DESCRIPTION     "Entry contains information about a particular 
                        session."
        INDEX           { stnGlobalSessionIndex }
        ::= { stnGlobalSessionTable 1 }
 
    StnGlobalSessionEntry ::= SEQUENCE {
                stnGlobalSessionIndex       Unsigned32,
                stnGlobalSessionOperStatus  INTEGER
                }

    stnGlobalSessionIndex OBJECT-TYPE
        SYNTAX          Unsigned32
        MAX-ACCESS      not-accessible
        STATUS          current
        DESCRIPTION     "A sequence number that identifies a session
                        entry in the table."
        ::= { stnGlobalSessionEntry 1 }

    stnGlobalSessionOperStatus OBJECT-TYPE
        SYNTAX          INTEGER { 
                                inactive(1),     
                                active(2)
                        }
        MAX-ACCESS      read-write
        STATUS          current
        DESCRIPTION     "The operational status of the session."
        ::= { stnGlobalSessionEntry  2 }


    --
    -- STN Session Notification support objects.
    --
    stnNotificationUsername OBJECT-TYPE
        SYNTAX          DisplayString
        MAX-ACCESS      read-only
        STATUS          current
        DESCRIPTION     "The user's name associated with the trap."
        ::= { stnSessionTrapVars 1 }

    stnNotificationUserFailureType OBJECT-TYPE
        SYNTAX          StnUserFailureType
        MAX-ACCESS      read-only
        STATUS          current
        DESCRIPTION     "The type of user failure."
        ::= { stnSessionTrapVars 2 }

    stnNotificationConfigType OBJECT-TYPE
        SYNTAX          StnConfigFailureType
        MAX-ACCESS      read-only
        STATUS          current
        DESCRIPTION     "The type of configuration failure."
        ::= { stnSessionTrapVars 3 }


    --
    -- STN Traps & Notifications 
    --
    stnUserFailure NOTIFICATION-TYPE
        OBJECTS         { stnRouterIndex,           
                          stnNotificationUsername, 
                          stnNotificationUserFailureType,   
                          stnSessionType }
        STATUS          current
        DESCRIPTION     "A stnUserFailure trap signifies that the 
                        agent entity has detected that a configuration
                        failure has occurred.
                        The generation of this trap can be controlled by the
                        CommandLineIfaceTraps configuration object."
        ::= { stnNotification 17 }

    stnConfigFailure NOTIFICATION-TYPE
        OBJECTS         { stnRouterIndex, 
                          stnNotificationUsername, 
                          stnNotificationConfigType }
        STATUS          current
        DESCRIPTION     "A stnConfigFailure trap signifies that the 
                        agent entity has detected that a configuration
                        failure has occurred.
                        The generation of this trap can be controlled by the
                        CommandLineIfaceTraps configuration object."
        ::= { stnNotification 18 }

    stnNoFlowEntriesAvailable NOTIFICATION-TYPE
        OBJECTS         { stnEngineIndex, stnEngineSlot, stnEngineCpu }
        STATUS          current
        DESCRIPTION     "A stnNoFlowEntriesAvailable trap signifies that the 
                        agent entity has detected that the there are
                        no more flow entries available on the indicated
                        slot/cpu. This can occur if too many interfaces
                        are assigned to an engine.
                        The generation of this trap can be controlled by the
                        SessionTraps configuration object."
        ::= { stnNotification 57 }

    stnNoLayerIfsAvailable NOTIFICATION-TYPE
        OBJECTS         { stnEngineIndex, stnEngineSlot, stnEngineCpu }
        STATUS          current
        DESCRIPTION     "A stnNoLayerIfsAvailable trap signifies that the 
                        agent entity has detected that the there are
                        no more layer interfaces available on the indicated
                        slot/cpu. This can occur if too many VCs
                        are assigned to an engine.
                        The generation of this trap can be controlled by the
                        SessionTraps configuration object."
        ::= { stnNotification 58 }

    stnMaxSessionLimitExceeded NOTIFICATION-TYPE
        OBJECTS         { stnEngineIndex, stnEngineSlot, stnEngineCpu }
        STATUS          current
        DESCRIPTION     "A stnMaxSessionLimitExceeded trap signifies that the 
                        agent entity has detected that the maximum session 
                        limit has occurred on the indicated slot/cpu. 
                        The generation of this trap can be controlled by the
                        SessionTraps configuration object."
        ::= { stnNotification 59 }

    stnTunnelEngineLimitExceeded NOTIFICATION-TYPE
        OBJECTS         { stnEngineIndex, stnEngineSlot, stnEngineCpu }
        STATUS          current
        DESCRIPTION     "A stnTunnelEngineLimitExceeded trap signifies that 
                        the agent entity has detected that the maximum tunnel 
                        limit has occurred on the indicated slot/cpu. 
                        The generation of this trap can be controlled by the
                        SessionTraps configuration object."
        ::= { stnNotification 60 }

    stnCallEngineLimitExceeded NOTIFICATION-TYPE
        OBJECTS         { stnEngineIndex, stnEngineSlot, stnEngineCpu }
        STATUS          current
        DESCRIPTION     "A stnCallEngineLimitExceeded trap signifies that 
                        the agent entity has detected that the maximum call 
                        limit has occurred on the indicated slot/cpu. 
                        The generation of this trap can be controlled by the
                        SessionTraps configuration object."
        ::= { stnNotification 61 }

END
