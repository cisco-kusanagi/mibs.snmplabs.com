FLOWMGREXT-MIB

   --FORCE-INCLUDE <mib.h>
   --FORCE-INCLUDE <snmpdefs.h>
   --FORCE-INCLUDE <snmpstat.h>
   --FORCE-INCLUDE "mibproto.h"
 
	DEFINITIONS ::= BEGIN

	IMPORTS
	MODULE-IDENTITY, OBJECT-TYPE, Integer32, Counter64, IpAddress
			FROM SNMPv2-SMI
		DisplayString
			FROM SNMPv2-TC
		TRAP-TYPE
			FROM RFC-1215
		flowMgrExt
			FROM APENT-MIB;

--  flowMgrExt MIB

flowMgrExtMib MODULE-IDENTITY
	LAST-UPDATED "9707202000Z" -- Wed July 20 20:00:00 EST 1997
	ORGANIZATION "ArrowPoint Communications Inc."
	CONTACT-INFO
	"                       Ken Siegel
	Postal:               ArrowPoint Communications Inc.
				                 50 Nagog Park
				                 Acton, Massachusetts 01720
	   Tel:                   +1 978-206-3000  option 1
	   E-Mail:                support@arrowpoint.com"
	DESCRIPTION
		"This MIB module describes the ArrowPoint Communications
		enterprise MIB for the flow manager module."
	::= { flowMgrExt 1 }


-- apFlowMgrExt Scalars

apFlowMgrExtFlowTraceOptions OBJECT-TYPE
	SYNTAX DisplayString(SIZE( 1..10))
	MAX-ACCESS read-write
	STATUS current
	DESCRIPTION
		"This object specifies a bitmask of the current flow 
		trace settings."
	::= { flowMgrExt 2 }

apFlowMgrExtFlowTraceState OBJECT-TYPE
	SYNTAX INTEGER {
			enabled(1)                             ,
			disabled(2)                              
	}
	MAX-ACCESS read-write
	STATUS current
	DESCRIPTION
		"This object specifies the current state of flow tracing."
	::= { flowMgrExt 3 }

apFlowMgrExtFlowTraceFilename OBJECT-TYPE
	SYNTAX DisplayString( SIZE( 0..16 ) )
	MAX-ACCESS read-write
	STATUS current
	DESCRIPTION
		"This object specifies the file name of the log file on disk."
	::= { flowMgrExt 4 }

apFlowMgrExtFlowTraceMaxFileSize OBJECT-TYPE
	SYNTAX INTEGER( 1..100 )
	MAX-ACCESS read-write
	STATUS current
	DESCRIPTION
		"This object specifies the maximum file length allowed to be
		saved to the disk."
	DEFVAL { 100 }
	::= { flowMgrExt 5 }

apFlowMgrExtFlowTraceDuration OBJECT-TYPE
	SYNTAX INTEGER( 1..60 )
	MAX-ACCESS read-write
	STATUS current
	DESCRIPTION
		"This object specifies the duration of the Flow Tracing logging
		session in seconds."
	DEFVAL { 30 }
	::= { flowMgrExt 6 }

apFlowMgrExtPermanentPort1 OBJECT-TYPE
	SYNTAX INTEGER( 0..65535 )
	MAX-ACCESS read-write
	STATUS current
	DESCRIPTION
		"This object specifies the first destination tcp port number
		for flows that the flow manager will not reclaim."
	DEFVAL { 0 }
	::= { flowMgrExt 7 }

apFlowMgrExtPermanentPort2 OBJECT-TYPE
	SYNTAX INTEGER( 0..65535 )
	MAX-ACCESS read-write
	STATUS current
	DESCRIPTION
		"This object specifies the second destination tcp port number
		for flows that the flow manager will not reclaim."
	DEFVAL { 0 }
	::= { flowMgrExt 8 }

apFlowMgrExtPermanentPort3 OBJECT-TYPE
	SYNTAX INTEGER( 0..65535 )
	MAX-ACCESS read-write
	STATUS current
	DESCRIPTION
		"This object specifies the third destination tcp port number
		for flows that the flow manager will not reclaim."
	DEFVAL { 0 }
	::= { flowMgrExt 9 }

apFlowMgrExtPermanentPort4 OBJECT-TYPE
	SYNTAX INTEGER( 0..65535 )
	MAX-ACCESS read-write
	STATUS current
	DESCRIPTION
		"This object specifies the forth destination tcp port number
		for flows that the flow manager will not reclaim."
	DEFVAL { 0 }
	::= { flowMgrExt 10 }

apFlowMgrExtReserveCleanTimer OBJECT-TYPE
	SYNTAX INTEGER( 0..100 )
	MAX-ACCESS read-write
	STATUS current
	DESCRIPTION
		"This object specifies the time (in seconds) at which the 
         flow manager scans flows with a source or destination port
         of less than 25 and may attempt to clean up that flow."
	DEFVAL { 10 }
	::= { flowMgrExt 11 }

apFlowMgrExtPortIdleTable OBJECT-TYPE
	SYNTAX SEQUENCE OF APFlowMgrExtPortIdleEntry
	MAX-ACCESS  not-accessible
	STATUS	current
	DESCRIPTION
		"This is the table of port idle timer values."
	::= { flowMgrExt 12 }

apFlowMgrExtPortIdleEntry OBJECT-TYPE
    SYNTAX  APFlowMgrExtPortIdleEntry
    MAX-ACCESS  not-accessible
    STATUS  current
    DESCRIPTION
            "A table containing the port number and associated
             idle timer."
    INDEX  { apFlowMgrExtPortIdle }
    ::= { apFlowMgrExtPortIdleTable 1 } 

APFlowMgrExtPortIdleEntry ::=
    SEQUENCE {
		apFlowMgrExtPortIdle
			INTEGER,
		apFlowMgrExtPortIdleValue
			INTEGER,
		apFlowMgrExtPortLowWaterFCB
			INTEGER
		}

apFlowMgrExtPortIdle OBJECT-TYPE
	SYNTAX  INTEGER
	MAX-ACCESS  read-only
	STATUS  current
	DESCRIPTION
		"This is the port number of the port for which this entry
         contains the flow manager port configuration."
    ::= { apFlowMgrExtPortIdleEntry 2 } 

apFlowMgrExtPortIdleValue OBJECT-TYPE
	SYNTAX INTEGER ( 0..65535 )
	MAX-ACCESS  read-write
	STATUS  current
	DESCRIPTION
		"This is the flow manager reset idle value for this port."
    DEFVAL { 0 } 
    ::= { apFlowMgrExtPortIdleEntry 3 } 

apFlowMgrExtPortLowWaterFCB OBJECT-TYPE
	SYNTAX INTEGER ( 1..100 )
	MAX-ACCESS  read-write
	STATUS  current
	DESCRIPTION
		"This is the configured flow manager FCB low water mark 
		 for this port.  When free FCBs constitute this percentage
         of total FCBs, expedited flow recovery procedures are invoked."
    DEFVAL { 25 } 
    ::= { apFlowMgrExtPortIdleEntry 4 } 

apFlowMgrExtIdleTimer OBJECT-TYPE
	SYNTAX INTEGER( 0..600 )
	MAX-ACCESS read-write
	STATUS current
	DESCRIPTION
		"This object specifies the time (in seconds) which the 
         flow manager will use to time out flows. A value of 0
         indicates that internal values will be used."
	DEFVAL { 1 }
	::= { flowMgrExt 13 }


-- ********************** apFlowMgrStatIfTable BEGIN ************************

apFlowMgrStatIfTable OBJECT-TYPE
	SYNTAX  SEQUENCE OF ApFlowMgrStatIfEntry
	MAX-ACCESS  not-accessible
	STATUS  current
	DESCRIPTION
		"The FlowMgr Statistics Table"
	::= { flowMgrExt 14 }

apFlowMgrStatIfEntry OBJECT-TYPE
	SYNTAX  ApFlowMgrStatIfEntry
    MAX-ACCESS  not-accessible
	STATUS  current
    DESCRIPTION
		"An entry in the Flow Manager statistics Table referenced via an 
         IFINDEX (apFlowMgrStatIfIndex).  An entry is available for each interface"

	INDEX { apFlowMgrStatIfIndex, apFlowMgrStatIfVlanID }
	::= { apFlowMgrStatIfTable 1 }

	ApFlowMgrStatIfEntry ::=
		SEQUENCE {
			apFlowMgrStatIfIndex                Integer32,
			apFlowMgrStatIfVlanID				Integer32,
			apFlowMgrStatIfUDPTotal             Integer32,
			apFlowMgrStatIfUDPCur               Integer32,
			apFlowMgrStatIfUDPHigh              Integer32,
			apFlowMgrStatIfUDPAvg               Integer32,
			apFlowMgrStatIfTCPTotal             Integer32,
			apFlowMgrStatIfTCPCur               Integer32,
			apFlowMgrStatIfTCPHigh              Integer32,
			apFlowMgrStatIfTCPAvg               Integer32,
			apFlowMgrStatIfCurrentActiveTCP		Integer32,
			apFlowMgrStatIfCurrentActiveUDP		Integer32,
			apFlowMgrStatIfAccountingReportsRx	Integer32,
			apFlowMgrStatIfResets				Integer32,
			apFlowMgrStatIfFcbCount				Integer32
		}

apFlowMgrStatIfIndex OBJECT-TYPE
	SYNTAX          Integer32
	MAX-ACCESS      read-only
	STATUS  		current
	DESCRIPTION     
		"IF Index of interface"
	::= {apFlowMgrStatIfEntry 1}

apFlowMgrStatIfVlanID OBJECT-TYPE
	SYNTAX          Integer32
	MAX-ACCESS      read-only
	STATUS  		current
	DESCRIPTION     
		"IF Index of interface"
	::= {apFlowMgrStatIfEntry 2}

apFlowMgrStatIfUDPTotal OBJECT-TYPE
	SYNTAX          Integer32
	MAX-ACCESS      read-only
	STATUS  		current
	DESCRIPTION     
		"Total UDP flows on interface"
	::= {apFlowMgrStatIfEntry 3}

apFlowMgrStatIfUDPCur OBJECT-TYPE
	SYNTAX          Integer32
	MAX-ACCESS      read-only
	STATUS  		current
	DESCRIPTION     
		"Number of new UDP flows within last second on interface"
	::= {apFlowMgrStatIfEntry 4}

apFlowMgrStatIfUDPHigh OBJECT-TYPE
	SYNTAX          Integer32
	MAX-ACCESS      read-only
	STATUS  		current
	DESCRIPTION     
		"Maximum number of UDP flows in any one second interval on interface"
	::= {apFlowMgrStatIfEntry 5}

apFlowMgrStatIfUDPAvg OBJECT-TYPE
	SYNTAX          Integer32
	MAX-ACCESS      read-only
	STATUS  		current
	DESCRIPTION     
		"Five second moving average of UDP flows per second on interface"
	::= {apFlowMgrStatIfEntry 6}

apFlowMgrStatIfTCPTotal OBJECT-TYPE
	SYNTAX          Integer32
	MAX-ACCESS      read-only
	STATUS  		current
	DESCRIPTION     
		"Total TCP flows on interface"
	::= {apFlowMgrStatIfEntry 7}

apFlowMgrStatIfTCPCur OBJECT-TYPE
	SYNTAX          Integer32
	MAX-ACCESS      read-only
	STATUS  		current
	DESCRIPTION     
		"Number of new TCP flows within last second on interface"
	::= {apFlowMgrStatIfEntry 8}

apFlowMgrStatIfTCPHigh OBJECT-TYPE
	SYNTAX          Integer32
	MAX-ACCESS      read-only
	STATUS  		current
	DESCRIPTION     
		"Maximum number of TCP flows in any one second interval on interface"
	::= {apFlowMgrStatIfEntry 9}

apFlowMgrStatIfTCPAvg OBJECT-TYPE
	SYNTAX          Integer32
	MAX-ACCESS      read-only
	STATUS  		current
	DESCRIPTION     
		"Five second moving average of TCP flows per second on interface"
	::= {apFlowMgrStatIfEntry 10}

apFlowMgrStatIfCurrentActiveTCP OBJECT-TYPE
	SYNTAX          Integer32
	MAX-ACCESS      read-only
	STATUS  		current
	DESCRIPTION     
		"Current number of active TCP flows on interface"
	::= {apFlowMgrStatIfEntry 11}

apFlowMgrStatIfCurrentActiveUDP OBJECT-TYPE
	SYNTAX          Integer32
	MAX-ACCESS      read-only
	STATUS  		current
	DESCRIPTION     
		"Current number of active UDP flows on interface"
	::= {apFlowMgrStatIfEntry 12}


apFlowMgrStatIfAccountingReportsRx OBJECT-TYPE
	SYNTAX          Integer32
	MAX-ACCESS      read-only
	STATUS  		current
	DESCRIPTION     
		"Number of accounting reports received for interface"
	::= {apFlowMgrStatIfEntry 13}

apFlowMgrStatIfResets OBJECT-TYPE
	SYNTAX          Integer32
	MAX-ACCESS      read-only
	STATUS  		current
	DESCRIPTION     
		"Number of times interface has been reset"
	::= {apFlowMgrStatIfEntry 14}


apFlowMgrStatIfFcbCount OBJECT-TYPE
	SYNTAX          Integer32
	MAX-ACCESS      read-only
	STATUS  		current
	DESCRIPTION     
		"Number of unused fastpath flow control blocks for interface"
	::= {apFlowMgrStatIfEntry 15}


-- ********************** apFlowMgrStatIfTable END ***************************

-- ********************** apFlowMgrStatSSTable BEGIN ************************

apFlowMgrStatSSTable OBJECT-TYPE
	SYNTAX  SEQUENCE OF ApFlowMgrStatSSEntry
	MAX-ACCESS  not-accessible
	STATUS  current
	DESCRIPTION
		"The FlowMgr Statistics Table"
	::= { flowMgrExt 15 }

apFlowMgrStatSSEntry OBJECT-TYPE
	SYNTAX  ApFlowMgrStatSSEntry
    MAX-ACCESS  not-accessible
	STATUS  current
    DESCRIPTION
		"An entry in the Flow Manager statistics Table referenced via an 
		chassis manager slot/subslot pair...."

	INDEX { apFlowMgrStatSSSlot, apFlowMgrStatSSSubSlot }
	::= { apFlowMgrStatSSTable 1 }

	ApFlowMgrStatSSEntry ::=
		SEQUENCE {
			apFlowMgrStatSSSlot                 Integer32,
			apFlowMgrStatSSSubSlot              Integer32,
			apFlowMgrStatSSUDPTotal             Integer32,
			apFlowMgrStatSSUDPCur               Integer32,
			apFlowMgrStatSSUDPHigh              Integer32,
			apFlowMgrStatSSUDPAvg               Integer32,
			apFlowMgrStatSSTCPTotal             Integer32,
			apFlowMgrStatSSTCPCur               Integer32,
			apFlowMgrStatSSTCPHigh              Integer32,
			apFlowMgrStatSSTCPAvg               Integer32,
			apFlowMgrStatSSCurrentActiveTCP		Integer32,
			apFlowMgrStatSSCurrentActiveUDP		Integer32,
			apFlowMgrStatSSAccountingReportsRx	Integer32,
			apFlowMgrStatSSResets				Integer32,
			apFlowMgrStatSSFcbCount				Integer32
		}

apFlowMgrStatSSSlot OBJECT-TYPE
	SYNTAX          Integer32
	MAX-ACCESS      read-only
	STATUS  		current
	DESCRIPTION     
		"Physical slot of interface"
	::= {apFlowMgrStatSSEntry 1}

apFlowMgrStatSSSubSlot OBJECT-TYPE
	SYNTAX          Integer32
	MAX-ACCESS      read-only
	STATUS  		current
	DESCRIPTION     
		"Physical sub-slot of interface"
	::= {apFlowMgrStatSSEntry 2}

apFlowMgrStatSSUDPTotal OBJECT-TYPE
	SYNTAX          Integer32
	MAX-ACCESS      read-only
	STATUS  		current
	DESCRIPTION     
		"Total UDP flows on interface"
	::= {apFlowMgrStatSSEntry 3}

apFlowMgrStatSSUDPCur OBJECT-TYPE
	SYNTAX          Integer32
	MAX-ACCESS      read-only
	STATUS  		current
	DESCRIPTION     
		"Number of new UDP flows within last second on interface"
	::= {apFlowMgrStatSSEntry 4}

apFlowMgrStatSSUDPHigh OBJECT-TYPE
	SYNTAX          Integer32
	MAX-ACCESS      read-only
	STATUS  		current
	DESCRIPTION     
		"Maximum number of UDP flows in any one second interval on interface"
	::= {apFlowMgrStatSSEntry 5}

apFlowMgrStatSSUDPAvg OBJECT-TYPE
	SYNTAX          Integer32
	MAX-ACCESS      read-only
	STATUS  		current
	DESCRIPTION     
		"Five second moving average of UDP flows per second on interface"
	::= {apFlowMgrStatSSEntry 6}

apFlowMgrStatSSTCPTotal OBJECT-TYPE
	SYNTAX          Integer32
	MAX-ACCESS      read-only
	STATUS  		current
	DESCRIPTION     
		"Total TCP flows on interface"
	::= {apFlowMgrStatSSEntry 7}

apFlowMgrStatSSTCPCur OBJECT-TYPE
	SYNTAX          Integer32
	MAX-ACCESS      read-only
	STATUS  		current
	DESCRIPTION     
		"Number of new TCP flows within last second on interface"
	::= {apFlowMgrStatSSEntry 8}

apFlowMgrStatSSTCPHigh OBJECT-TYPE
	SYNTAX          Integer32
	MAX-ACCESS      read-only
	STATUS  		current
	DESCRIPTION     
		"Maximum number of TCP flows in any one second interval on interface"
	::= {apFlowMgrStatSSEntry 9}

apFlowMgrStatSSTCPAvg OBJECT-TYPE
	SYNTAX          Integer32
	MAX-ACCESS      read-only
	STATUS  		current
	DESCRIPTION     
		"Five second moving average of TCP flows per second on interface"
	::= {apFlowMgrStatSSEntry 10}

apFlowMgrStatSSCurrentActiveTCP OBJECT-TYPE
	SYNTAX          Integer32
	MAX-ACCESS      read-only
	STATUS  		current
	DESCRIPTION     
		"Current number of active TCP flows on interface"
	::= {apFlowMgrStatSSEntry 11}

apFlowMgrStatSSCurrentActiveUDP OBJECT-TYPE
	SYNTAX          Integer32
	MAX-ACCESS      read-only
	STATUS  		current
	DESCRIPTION     
		"Current number of active UDP flows on interface"
	::= {apFlowMgrStatSSEntry 12}

apFlowMgrStatSSAccountingReportsRx OBJECT-TYPE
	SYNTAX          Integer32
	MAX-ACCESS      read-only
	STATUS  		current
	DESCRIPTION     
		""
	::= {apFlowMgrStatSSEntry 13}

apFlowMgrStatSSResets OBJECT-TYPE
	SYNTAX          Integer32
	MAX-ACCESS      read-only
	STATUS  		current
	DESCRIPTION     
		"Number of times interface has been reset"
	::= {apFlowMgrStatSSEntry 14}


apFlowMgrStatSSFcbCount OBJECT-TYPE
	SYNTAX          Integer32
	MAX-ACCESS      read-only
	STATUS  		current
	DESCRIPTION     
		"Number of unused fastpath flow control blocks for interface"
	::= {apFlowMgrStatSSEntry 15}


-- ********************** apFlowMgrStatSSTable END ***************************

-- ********************** apFlowMgrPortTable BEGIN ***************************

apFlowMgrPortTable OBJECT-TYPE
	SYNTAX  SEQUENCE OF ApFlowMgrPortEntry
	MAX-ACCESS  not-accessible
	STATUS  current
	DESCRIPTION
		"The FlowMgr Port Table for a given slot/subslot in the chassis."
	::= { flowMgrExt 16 }

apFlowMgrPortEntry OBJECT-TYPE
	SYNTAX  ApFlowMgrPortEntry
    MAX-ACCESS  not-accessible
	STATUS  current
    DESCRIPTION
		"An entry in the Flow Manager port Table."
	INDEX { apFlowMgrPortIfIndex }
	::= { apFlowMgrPortTable 1 }

	ApFlowMgrPortEntry ::=
		SEQUENCE {
			apFlowMgrPortIfIndex                Integer32,
			apFlowMgrPortSeqBytes               Counter64,
			apFlowMgrPortInBytes                Counter64,
			apFlowMgrPortOutBytes               Counter64, 
			apFlowMgrPortInFrames               Counter64,
			apFlowMgrPortOutFrames              Counter64,
			apFlowMgrPortTotalInFlows           Counter64,
			apFlowMgrPortTotalOutFlows          Counter64,
			apFlowMgrPortTotalAcctFlows         Counter64,
			apFlowMgrPortCurrTCPFlows           Integer32,  
			apFlowMgrPortCurrUDPFlows           Integer32,
			apFlowMgrPortCurrInFlows            Integer32,
			apFlowMgrPortCurrOutFlows           Integer32,
			apFlowMgrPortResetCount             Integer32, 
			apFlowMgrPortMTU                    Integer32,
			apFlowMgrPortWccAccepted            Integer32, 
			apFlowMgrPortWccAcceptedSticky      Integer32,
			apFlowMgrPortWccAcceptedBridge      Integer32,
			apFlowMgrPortWccAcceptedSfpFwd      Integer32,
			apFlowMgrPortWccAcceptedSfp         Integer32,
			apFlowMgrPortWccForwardSfp          Integer32, 
			apFlowMgrPortWccForward             Integer32, 
			apFlowMgrPortWccLocal               Integer32,
			apFlowMgrPortWccTCPSpoof            Integer32, 
			apFlowMgrPortWccArpPending          Integer32, 
			apFlowMgrPortWccRedirect            Integer32,
			apFlowMgrPortWccRedirectSticky      Integer32, 
			apFlowMgrPortWccNoChange            Integer32, 
			apFlowMgrPortWccRouteNotFound       Integer32,
			apFlowMgrPortWccRtLookupError       Integer32,
			apFlowMgrPortWccDiscard             Integer32,
			apFlowMgrPortWccRejected            Integer32,
			apFlowMgrPortWccRejectedSfp         Integer32,
			apFlowMgrPortTotalAckDelete         Integer32,
			apFlowMgrPortPortAckDelete          Integer32,
			apFlowMgrPortMidSpoofRejects        Integer32,
 			apFlowMgrPortMidNATReject           Integer32,
			apFlowMgrPortMidStickyReject        Integer32,
			apFlowMgrPortSynExceedDelete        Integer32,
			apFlowMgrPortInvalidIP              Integer32,
			apFlowMgrPortBufferShortage         Integer32,
			apFlowMgrPortMovedAcctReports       Integer32,
			apFlowMgrPortUknownQueries          Integer32,
			apFlowMgrPortMappedLeftovers        Integer32,
			apFlowMgrPortUnmappedLeftovers      Integer32,
			apFlowMgrPortRemappedIngress        Integer32,
			apFlowMgrPortFlowsUnavailable       Integer32,
			apFlowMgrPortTCPCsumErrors          Integer32,
			apFlowMgrPortOverflowMaps           Integer32, 
			apFlowMgrPortRouteChangeEvents      Integer32, 
			apFlowMgrPortRouteChangeFlows       Integer32,
			apFlowMgrPortRouteChangeRemaps      Integer32,
			apFlowMgrPortOrphanMappings         Integer32
}


apFlowMgrPortIfIndex OBJECT-TYPE
	SYNTAX          Integer32
	MAX-ACCESS      read-only
	STATUS  		current
	DESCRIPTION     
		"IF index for this interface"
	::= {apFlowMgrPortEntry 1}

apFlowMgrPortSeqBytes OBJECT-TYPE
	SYNTAX          Counter64
	MAX-ACCESS      read-only
	STATUS  		current
	DESCRIPTION     
		"Total TCP sequence space bytes received on interface by flow manager"
	::= {apFlowMgrPortEntry 2}

apFlowMgrPortInBytes OBJECT-TYPE
	SYNTAX          Counter64
	MAX-ACCESS      read-only
	STATUS  		current
	DESCRIPTION     
		"Total IP bytes received by flow manager on interface"
	::= {apFlowMgrPortEntry 3}

apFlowMgrPortOutBytes OBJECT-TYPE
	SYNTAX          Counter64
	MAX-ACCESS      read-only
	STATUS  		current
	DESCRIPTION     
		"Total IP bytes out of flow manager out interface"
	::= {apFlowMgrPortEntry 4}

apFlowMgrPortInFrames OBJECT-TYPE
	SYNTAX          Counter64
	MAX-ACCESS      read-only
	STATUS  		current
	DESCRIPTION     
		"Total IP frames into flow manager on interface"
	::= {apFlowMgrPortEntry 5}

apFlowMgrPortOutFrames OBJECT-TYPE
	SYNTAX          Counter64
	MAX-ACCESS      read-only
	STATUS  		current
	DESCRIPTION     
		"Total IP frames from flow manager out interface"
	::= {apFlowMgrPortEntry 6}


apFlowMgrPortTotalInFlows OBJECT-TYPE
	SYNTAX          Counter64
	MAX-ACCESS      read-only
	STATUS  		current
	DESCRIPTION     
		"Total flows inbound on interface started by flow manager"
	::= {apFlowMgrPortEntry 7}


apFlowMgrPortTotalOutFlows OBJECT-TYPE
	SYNTAX          Counter64
	MAX-ACCESS      read-only
	STATUS  		current
	DESCRIPTION     
		"Total flows outbound on interface started by flow manager"
	::= {apFlowMgrPortEntry 8}


apFlowMgrPortTotalAcctFlows OBJECT-TYPE
	SYNTAX          Counter64
	MAX-ACCESS      read-only
	STATUS  		current
	DESCRIPTION     
		"Total accounting reports for flows received on interface"
	::= {apFlowMgrPortEntry 9}

apFlowMgrPortCurrTCPFlows OBJECT-TYPE
	SYNTAX          Integer32
	MAX-ACCESS      read-only
	STATUS  		current
	DESCRIPTION     
		"Current number of active TCP flows on interface"
	::= {apFlowMgrPortEntry 10}


apFlowMgrPortCurrUDPFlows OBJECT-TYPE
	SYNTAX          Integer32
	MAX-ACCESS      read-only
	STATUS  		current
	DESCRIPTION     
		"Current number of active UDP flows on interface"
	::= {apFlowMgrPortEntry 11}

apFlowMgrPortCurrInFlows OBJECT-TYPE
	SYNTAX          Integer32
	MAX-ACCESS      read-only
	STATUS  		current
	DESCRIPTION     
		"Total current flows inbound on interface"
	::= {apFlowMgrPortEntry 12}

apFlowMgrPortCurrOutFlows OBJECT-TYPE
	SYNTAX          Integer32
	MAX-ACCESS      read-only
	STATUS  		current
	DESCRIPTION     
		"Total current flows outbound on interface"
	::= {apFlowMgrPortEntry 13}


apFlowMgrPortResetCount OBJECT-TYPE
	SYNTAX          Integer32
	MAX-ACCESS      read-only
	STATUS  		current
	DESCRIPTION     
		"Total times flow manager has reset interface"
	::= {apFlowMgrPortEntry 14}

apFlowMgrPortMTU OBJECT-TYPE
	SYNTAX          Integer32
	MAX-ACCESS      read-only
	STATUS  		current
	DESCRIPTION     
		"Maximum transmission unit for TCP flows on interface"
	::= {apFlowMgrPortEntry 15}

apFlowMgrPortWccAccepted OBJECT-TYPE
	SYNTAX          Integer32
	MAX-ACCESS      read-only
	STATUS  		current
	DESCRIPTION     
		"Number of flows accepted by web conversation control"
	::= {apFlowMgrPortEntry 16}

apFlowMgrPortWccAcceptedSticky OBJECT-TYPE
	SYNTAX          Integer32
	MAX-ACCESS      read-only
	STATUS  		current
	DESCRIPTION     
		"Number of sticky accepted flows by web conversation control"
	::= {apFlowMgrPortEntry 17}


apFlowMgrPortWccAcceptedBridge OBJECT-TYPE
	SYNTAX          Integer32
	MAX-ACCESS      read-only
	STATUS  		current
	DESCRIPTION     
		"Number of bridged flows accepted by web conversation control"
	::= {apFlowMgrPortEntry 18}


apFlowMgrPortWccAcceptedSfpFwd OBJECT-TYPE
	SYNTAX          Integer32
	MAX-ACCESS      read-only
	STATUS  		current
	DESCRIPTION     
		"Number of accepted flows that must be forwarded in the mid-path"
	::= {apFlowMgrPortEntry 19}


apFlowMgrPortWccAcceptedSfp OBJECT-TYPE
	SYNTAX          Integer32
	MAX-ACCESS      read-only
	STATUS  		current
	DESCRIPTION     
		"Number of processed content frames for mid-path forwarded flows"
	::= {apFlowMgrPortEntry 20}

apFlowMgrPortWccForwardSfp OBJECT-TYPE
	SYNTAX          Integer32
	MAX-ACCESS      read-only
	STATUS  		current
	DESCRIPTION     
		"Number of frames forwarded unchanged for mid-path forwarded flows"
	::= {apFlowMgrPortEntry 21}

apFlowMgrPortWccForward OBJECT-TYPE
	SYNTAX          Integer32
	MAX-ACCESS      read-only
	STATUS  		current
	DESCRIPTION     
		"Number of frames given to IP module for direct forwarding in mid-path"
	::= {apFlowMgrPortEntry 22}

apFlowMgrPortWccLocal OBJECT-TYPE
	SYNTAX          Integer32
	MAX-ACCESS      read-only
	STATUS  		current
	DESCRIPTION     
		"Number of accepted inbound flows that terminate on chassis"
	::= {apFlowMgrPortEntry 23}

apFlowMgrPortWccTCPSpoof OBJECT-TYPE
	SYNTAX          Integer32
	MAX-ACCESS      read-only
	STATUS  		current
	DESCRIPTION     
		"Number of flows requiring TCP spoofing for content awareness"
	::= {apFlowMgrPortEntry 24}

apFlowMgrPortWccArpPending OBJECT-TYPE
	SYNTAX          Integer32
	MAX-ACCESS      read-only
	STATUS  		current
	DESCRIPTION     
		"Number of flows delayed because ARP entries needed resolution"
	::= {apFlowMgrPortEntry 25}

apFlowMgrPortWccRedirect OBJECT-TYPE
	SYNTAX          Integer32
	MAX-ACCESS      read-only
	STATUS  		current
	DESCRIPTION     
		"Number of flows requiring a redirect after content examination"
	::= {apFlowMgrPortEntry 26}


apFlowMgrPortWccRedirectSticky OBJECT-TYPE
	SYNTAX          Integer32
	MAX-ACCESS      read-only
	STATUS  		current
	DESCRIPTION     
		"Number of sticky flows requiring a redirect after content examination"
	::= {apFlowMgrPortEntry 27}


apFlowMgrPortWccNoChange OBJECT-TYPE
	SYNTAX          Integer32
	MAX-ACCESS      read-only
	STATUS  		current
	DESCRIPTION     
		"Number of content requests on persistent connections that resulted in no flow mapping changes"
	::= {apFlowMgrPortEntry 28}

apFlowMgrPortWccRouteNotFound OBJECT-TYPE
	SYNTAX          Integer32
	MAX-ACCESS      read-only
	STATUS  		current
	DESCRIPTION     
		"Number of times flows attempted without a useable route"
	::= {apFlowMgrPortEntry 29}


apFlowMgrPortWccRtLookupError OBJECT-TYPE
	SYNTAX          Integer32
	MAX-ACCESS      read-only
	STATUS  		current
	DESCRIPTION     
		"Number of times a flow was attempted and a route lookup error occured"
	::= {apFlowMgrPortEntry 30}


apFlowMgrPortWccDiscard OBJECT-TYPE
	SYNTAX          Integer32
	MAX-ACCESS      read-only
	STATUS  		current
	DESCRIPTION     
		"Number of times an unuseable frame came in for a flow expecting content"
	::= {apFlowMgrPortEntry 31}



apFlowMgrPortWccRejected OBJECT-TYPE
	SYNTAX          Integer32
	MAX-ACCESS      read-only
	STATUS  		current
	DESCRIPTION     
		"Number of flows rejected by web conversation control"
	::= {apFlowMgrPortEntry 32}



apFlowMgrPortWccRejectedSfp OBJECT-TYPE
	SYNTAX          Integer32
	MAX-ACCESS      read-only
	STATUS  		current
	DESCRIPTION     
		"Number of mid-path forwarded frames rejected by web conversation control"
	::= {apFlowMgrPortEntry 33}



apFlowMgrPortTotalAckDelete OBJECT-TYPE
	SYNTAX          Integer32
	MAX-ACCESS      read-only
	STATUS  		current
	DESCRIPTION     
		"Total flows deleted because of incomplete TCP flow transactions from client"
	::= {apFlowMgrPortEntry 34}


apFlowMgrPortPortAckDelete OBJECT-TYPE
	SYNTAX          Integer32
	MAX-ACCESS      read-only
	STATUS  		current
	DESCRIPTION     
		"Number of flows deleted on interface because of incomplete TCP flow transactions from client"
	::= {apFlowMgrPortEntry 35}


apFlowMgrPortMidSpoofRejects OBJECT-TYPE
	SYNTAX          Integer32
	MAX-ACCESS      read-only
	STATUS  		current
	DESCRIPTION     
		"Number of flows rejected because spoofing was required and a non-SYN TCP frame started the flow"
	::= {apFlowMgrPortEntry 36}


apFlowMgrPortMidNATReject OBJECT-TYPE
	SYNTAX          Integer32
	MAX-ACCESS      read-only
	STATUS  		current
	DESCRIPTION     
		"Number of flows rejected because NAT was required and a non-SYN TCP frame started the flow"
	::= {apFlowMgrPortEntry 37}



apFlowMgrPortMidStickyReject OBJECT-TYPE
	SYNTAX          Integer32
	MAX-ACCESS      read-only
	STATUS  		current
	DESCRIPTION     
		"Number of sticky flows rejected because a non-SYN TCP frame started the flow"
	::= {apFlowMgrPortEntry 38}



apFlowMgrPortSynExceedDelete OBJECT-TYPE
	SYNTAX          Integer32
	MAX-ACCESS      read-only
	STATUS  		current
	DESCRIPTION     
		"Number of flows deleted because too many SYN frames were sent"
	::= {apFlowMgrPortEntry 39}


apFlowMgrPortInvalidIP OBJECT-TYPE
	SYNTAX          Integer32
	MAX-ACCESS      read-only
	STATUS  		current
	DESCRIPTION     
		"Number of invalid IP frames received"
	::= {apFlowMgrPortEntry 40}



apFlowMgrPortBufferShortage OBJECT-TYPE
	SYNTAX          Integer32
	MAX-ACCESS      read-only
	STATUS  		current
	DESCRIPTION     
		"Number of flows that could not be started due to buffer shortages"
	::= {apFlowMgrPortEntry 41}



apFlowMgrPortMovedAcctReports OBJECT-TYPE
	SYNTAX          Integer32
	MAX-ACCESS      read-only
	STATUS  		current
	DESCRIPTION     
		"Number of accounting reports for flows received on ports other than current flow ingress"
	::= {apFlowMgrPortEntry 42}


apFlowMgrPortUknownQueries OBJECT-TYPE
	SYNTAX          Integer32
	MAX-ACCESS      read-only
	STATUS  		current
	DESCRIPTION     
		"Number of times a flow was known to flow manager and unknown in the fastpath"
	::= {apFlowMgrPortEntry 43}



apFlowMgrPortMappedLeftovers OBJECT-TYPE
	SYNTAX          Integer32
	MAX-ACCESS      read-only
	STATUS  		current
	DESCRIPTION     
		"Number of times a mapped TCP flow was a partner to a flow being freed"
	::= {apFlowMgrPortEntry 44}


apFlowMgrPortUnmappedLeftovers OBJECT-TYPE
	SYNTAX          Integer32
	MAX-ACCESS      read-only
	STATUS  		current
	DESCRIPTION     
		"Number of times an unmapped TCP flow was a partner to a flow being freed"
	::= {apFlowMgrPortEntry 45}



apFlowMgrPortRemappedIngress OBJECT-TYPE
	SYNTAX          Integer32
	MAX-ACCESS      read-only
	STATUS  		current
	DESCRIPTION     
		"Number of times the ingress port of a flow was remapped"
	::= {apFlowMgrPortEntry 46}



apFlowMgrPortFlowsUnavailable OBJECT-TYPE
	SYNTAX          Integer32
	MAX-ACCESS      read-only
	STATUS  		current
	DESCRIPTION     
		"Number of times now flow structures were available for new flows"
	::= {apFlowMgrPortEntry 47}

apFlowMgrPortTCPCsumErrors OBJECT-TYPE
	SYNTAX          Integer32
	MAX-ACCESS      read-only
	STATUS  		current
	DESCRIPTION     
		"Number of frames received with TCP checksum errors for all interfaces"
	::= {apFlowMgrPortEntry 48}

apFlowMgrPortOverflowMaps OBJECT-TYPE
	SYNTAX          Integer32
	MAX-ACCESS      read-only
	STATUS  		current
	DESCRIPTION     
		"Number of flows mapped in the mid-path because of fastpath FCB shortages"
	::= {apFlowMgrPortEntry 49}


apFlowMgrPortRouteChangeEvents OBJECT-TYPE
	SYNTAX          Integer32
	MAX-ACCESS      read-only
	STATUS  		current
	DESCRIPTION     
		"Number of route change events received by flow manager"
	::= {apFlowMgrPortEntry 50}



apFlowMgrPortRouteChangeFlows OBJECT-TYPE
	SYNTAX          Integer32
	MAX-ACCESS      read-only
	STATUS  		current
	DESCRIPTION     
		"Number of flows examined as a result of route change events"
	::= {apFlowMgrPortEntry 51}


apFlowMgrPortRouteChangeRemaps OBJECT-TYPE
	SYNTAX          Integer32
	MAX-ACCESS      read-only
	STATUS  		current
	DESCRIPTION     
		"Number of flows remapped as a result of route change events"
	::= {apFlowMgrPortEntry 52}

apFlowMgrPortOrphanMappings OBJECT-TYPE
	SYNTAX          Integer32
	MAX-ACCESS      read-only
	STATUS  		current
	DESCRIPTION     
		"Number of flows in free list that had mapped fastpath entries"
	::= {apFlowMgrPortEntry 53}


-- ********************** apFlowMgrPortTable END ****************************


-- ********************** apFlowMgrDetailTable BEGIN ************************

apFlowMgrDetailTable OBJECT-TYPE
	SYNTAX  SEQUENCE OF ApFlowMgrDetailEntry
	MAX-ACCESS  not-accessible
	STATUS  current
	DESCRIPTION
		"The FlowMgr Detail Table for a given slot/subslot in the chassis."
	::= { flowMgrExt 17 }

apFlowMgrDetailEntry OBJECT-TYPE
	SYNTAX  ApFlowMgrDetailEntry
    MAX-ACCESS  not-accessible
	STATUS  current
    DESCRIPTION
		"An entry in the Flow Manager Detail Table."
	INDEX { apFlowMgrDetailIfIndex }
	::= { apFlowMgrDetailTable 1 }

	ApFlowMgrDetailEntry ::=
		SEQUENCE {
			apFlowMgrDetailIfIndex          	Integer32,
			apFlowMgrDetailSeqBytes				Integer32, 
			apFlowMgrDetailFlags				Integer32,
			apFlowMgrDetailPoolFlows			Integer32,
			apFlowMgrDetailInBytes				Integer32,
			apFlowMgrDetailOutBytes				Integer32,
			apFlowMgrDetailInFrames				Integer32,
			apFlowMgrDetailOutFrames			Integer32,
			apFlowMgrDetailTotalInFlows			Integer32,
			apFlowMgrDetailTotalOutFlows		Integer32,
			apFlowMgrDetailTotalAcctFlows		Integer32,
			apFlowMgrDetailResetCount			Integer32,
			apFlowMgrDetailCurTCPFlows			Integer32,
			apFlowMgrDetailCurUDPFlows			Integer32,
			apFlowMgrDetailCurInFlows			Integer32,
			apFlowMgrDetailCurOutFlows			Integer32,
			apFlowMgrDetailFPFlowCount			Integer32,
			apFlowMgrDetailTotalInFlowMap		Integer32,
			apFlowMgrDetailInMappedOnlyPrimary	Integer32,
			apFlowMgrDetailInMappedOnlyPrevious	Integer32,
			apFlowMgrDetailInMappedBothPrimary	Integer32,
			apFlowMgrDetailInMappedBothPrevious	Integer32,
			apFlowMgrDetailInNoFPMappings		Integer32,
			apFlowMgrDetailInIngressQueueLen	Integer32,
			apFlowMgrDetailInOrphanFCBFlows		Integer32,
			apFlowMgrDetailInTotalOrphanFCB		Integer32,
			apFlowMgrDetailInTCPPermPort		Integer32,
			apFlowMgrDetailInUDPPermPort		Integer32,
			apFlowMgrDetailInJoined				Integer32,
			apFlowMgrDetailInContentExpected	Integer32,
			apFlowMgrDetailInJoinPending		Integer32,
			apFlowMgrDetailInContentPending		Integer32,
			apFlowMgrDetailInTCPSYNSent			Integer32,
			apFlowMgrDetailInReversePending		Integer32,
			apFlowMgrDetailInSFPForwarded		Integer32,
			apFlowMgrDetailInInPortInflowCount	Integer32,
			apFlowMgrDetailInDeleted			Integer32,
			apFlowMgrDetailInSpoofed			Integer32,
			apFlowMgrDetailInNATInUse			Integer32,
			apFlowMgrDetailInContentAware		Integer32,
			apFlowMgrDetailInSticky				Integer32,
			apFlowMgrDetailInBridged			Integer32,
			apFlowMgrDetailInBuffersPending		Integer32,
			apFlowMgrDetailInSYNDOSTimerActive	Integer32,
			apFlowMgrDetailInOverflowMapped		Integer32,
			apFlowMgrDetailInRejected			Integer32,
			apFlowMgrDetailInTotalTCPFlows		Integer32,
			apFlowMgrDetailInTotalUDPFlows		Integer32,
			apFlowMgrDetailInHTTPSrcFlows		Integer32,
			apFlowMgrDetailInHTTPDstFlows		Integer32,
			apFlowMgrDetailInFTPDataSrcFlows	Integer32,
			apFlowMgrDetailInFTPDataDestFlows	Integer32,
			apFlowMgrDetailInFTPCtrlSrcFlows	Integer32,
			apFlowMgrDetailInFTPCtrlDestFlows	Integer32,
			apFlowMgrDetailInSSHSrcFlows		Integer32,
			apFlowMgrDetailInSSHDestFlows		Integer32,
			apFlowMgrDetailInTelnetSrcFlows		Integer32,
			apFlowMgrDetailInTelnetDestFlows	Integer32,
			apFlowMgrDetailInRASrcFlows			Integer32,
			apFlowMgrDetailInRADestFlows		Integer32,
			apFlowMgrDetailInBGPSrcFlows		Integer32,
			apFlowMgrDetailInBGPDestFlows		Integer32,
			apFlowMgrDetailInSMTPSrcFlows		Integer32,
			apFlowMgrDetailInSMTPDestFlows		Integer32,
			apFlowMgrDetailInPOP3SrcFlows		Integer32,
			apFlowMgrDetailInPOP3DestFlows		Integer32,
			apFlowMgrDetailInHTTPSSrcFlows		Integer32,
			apFlowMgrDetailInHTTPSDestFlows		Integer32,
			apFlowMgrDetailInNNTPSrcFlows		Integer32,
			apFlowMgrDetailInNNTPDestFlows		Integer32,
			apFlowMgrDetailInSOCKSSrcFlows		Integer32,
			apFlowMgrDetailInSOCKSDestFlows		Integer32,
			apFlowMgrDetailInPortLT23SrcFlows	Integer32,
			apFlowMgrDetailInPortLT23DestFlows	Integer32,
			apFlowMgrDetailInPortGT1024SrcFlows	Integer32,
			apFlowMgrDetailInPortGT1024DestFlows Integer32,
			apFlowMgrDetailInTimeSrcFlows		Integer32,
			apFlowMgrDetailInTimeDestSrcFlows	Integer32,
			apFlowMgrDetailInDNSSrcFlows		Integer32,
			apFlowMgrDetailInDNSDestFlows		Integer32,
			apFlowMgrDetailInSNMPSrcFlows		Integer32,
			apFlowMgrDetailInSNMPDestFlows		Integer32,
			apFlowMgrDetailInSNMPTrapSrcFlows	Integer32,
			apFlowMgrDetailInSNMPTrapDestFlows	Integer32,
			apFlowMgrDetailInNFSSrcFlows		Integer32,
			apFlowMgrDetailInNFSDestFlows		Integer32,
			apFlowMgrDetailInUDPGT1024SrcFlows	Integer32,
			apFlowMgrDetailInUDPGT1024DestFlows	Integer32,
			apFlowMgrDetailInUDPLT1024SrcFlows	Integer32,
			apFlowMgrDetailInUDPLT1024DestFlows	Integer32,
			apFlowMgrDetailInExplicitFlows		Integer32,
			apFlowMgrDetailInAcctSent			Integer32,
			apFlowMgrDetailEgTCPPermPort		Integer32,
			apFlowMgrDetailEgUDPPermPort		Integer32,
			apFlowMgrDetailEgJoined				Integer32,
			apFlowMgrDetailEgContentExpected	Integer32,
			apFlowMgrDetailEgJoinPending		Integer32,
			apFlowMgrDetailEgContentPending		Integer32,
			apFlowMgrDetailEgTCPSYNSent			Integer32,
			apFlowMgrDetailEgReversePending		Integer32,
			apFlowMgrDetailEgSFPFowrarded		Integer32,
			apFlowMgrDetailEgInPortInflowCount	Integer32,
			apFlowMgrDetailEgDeleted			Integer32,
			apFlowMgrDetailEgSpoofed			Integer32,
			apFlowMgrDetailEgNATInUse			Integer32,
			apFlowMgrDetailEgContentAware		Integer32,
			apFlowMgrDetailEgSticky				Integer32,
			apFlowMgrDetailEgBridged			Integer32,
			apFlowMgrDetailEgBuffersPending		Integer32,
			apFlowMgrDetailEgSYNDOSTimerActive	Integer32,
			apFlowMgrDetailEgOverflowMapped		Integer32,
			apFlowMgrDetailEgRejected			Integer32,
			apFlowMgrDetailEgTotalTCPFlows		Integer32,
			apFlowMgrDetailEgTotalUDPFlows		Integer32,
			apFlowMgrDetailEgHTTPSrcFlows		Integer32,
			apFlowMgrDetailEgHTTPDstFlows		Integer32,
			apFlowMgrDetailEgFTPDataSrcFlows	Integer32,
			apFlowMgrDetailEgFTPDataDestFlows	Integer32,
			apFlowMgrDetailEgFTPCtrlSrcFlows	Integer32,
			apFlowMgrDetailEgFTPCtrlDestFlows	Integer32,
			apFlowMgrDetailEgSSHSrcFlows		Integer32,
			apFlowMgrDetailEgSSHDestFlows		Integer32,
			apFlowMgrDetailEgTelnetSrcFlows		Integer32,
			apFlowMgrDetailEgTelnetDestFlows	Integer32,
			apFlowMgrDetailEgRASrcFlows			Integer32,
			apFlowMgrDetailEgRADestFlows		Integer32,
			apFlowMgrDetailEgBGPSrcFlows		Integer32,
			apFlowMgrDetailEgBGPDestFlows		Integer32,
			apFlowMgrDetailEgSMTPSrcFlows		Integer32,
			apFlowMgrDetailEgSMTPDestFlows		Integer32,
			apFlowMgrDetailEgPOP3SrcFlows		Integer32,
			apFlowMgrDetailEgPOP3DestFlows		Integer32,
			apFlowMgrDetailEgHTTPSSrcFlows		Integer32,
			apFlowMgrDetailEgHTTPSDestFlows		Integer32,
			apFlowMgrDetailEgNNTPSrcFlows		Integer32,
			apFlowMgrDetailEgNNTPDestFlows		Integer32,
			apFlowMgrDetailEgSOCKSSrcFlows		Integer32,
			apFlowMgrDetailEgSOCKSDestFlows		Integer32,
			apFlowMgrDetailEgPortLT23SrcFlows	Integer32,
			apFlowMgrDetailEgPortLT23DestFlows	Integer32,
			apFlowMgrDetailEgPortGT1024SrcFlows	Integer32,
			apFlowMgrDetailEgPortGT1024DestFlows Integer32,
			apFlowMgrDetailEgTimeSrcFlows		Integer32,
			apFlowMgrDetailEgTimeDestSrcFlows	Integer32,
			apFlowMgrDetailEgDNSSrcFlows		Integer32,
			apFlowMgrDetailEgDNSDestFlows		Integer32,
			apFlowMgrDetailEgSNMPSrcFlows		Integer32,
			apFlowMgrDetailEgSNMPDestFlows		Integer32,
			apFlowMgrDetailEgSNMPTrapSrcFlows	Integer32,
			apFlowMgrDetailEgSNMPTrapDestFlows	Integer32,
			apFlowMgrDetailEgNFSSrcFlows		Integer32,
			apFlowMgrDetailEgNFSDestFlows		Integer32,
			apFlowMgrDetailEgUDPGT1024SrcFlows	Integer32,
			apFlowMgrDetailEgUDPGT1024DestFlows	Integer32,
			apFlowMgrDetailEgUDPLT1024SrcFlows	Integer32,
			apFlowMgrDetailEgUDPLT1024DestFlows	Integer32
}



apFlowMgrDetailIfIndex OBJECT-TYPE
	SYNTAX			Integer32
	MAX-ACCESS		read-only
	STATUS			current
	DESCRIPTION
		"IF index for interface"
	::= {apFlowMgrDetailEntry 1}

apFlowMgrDetailSeqBytes OBJECT-TYPE
	SYNTAX			Integer32
	MAX-ACCESS		read-only
	STATUS			current
	DESCRIPTION
		"Total TCP sequence space in bytes from flows on interface"
	::= {apFlowMgrDetailEntry 2}

apFlowMgrDetailFlags OBJECT-TYPE
	SYNTAX			Integer32
	MAX-ACCESS		read-only
	STATUS			current
	DESCRIPTION
		"Interface flow manager state flags"
	::= {apFlowMgrDetailEntry 3}

apFlowMgrDetailPoolFlows OBJECT-TYPE
	SYNTAX			Integer32
	MAX-ACCESS		read-only
	STATUS			current
	DESCRIPTION
		"Number of flows in flow manager shared pool for interface"
	::= {apFlowMgrDetailEntry 4}

apFlowMgrDetailInBytes OBJECT-TYPE
	SYNTAX			Integer32
	MAX-ACCESS		read-only
	STATUS			current
	DESCRIPTION
		"Total IP bytes received on this interface"
	::= {apFlowMgrDetailEntry 5}

apFlowMgrDetailOutBytes OBJECT-TYPE
	SYNTAX			Integer32
	MAX-ACCESS		read-only
	STATUS			current
	DESCRIPTION
		"Total IP bytes sent from flow manager on this interface"
	::= {apFlowMgrDetailEntry 6}

apFlowMgrDetailInFrames OBJECT-TYPE
	SYNTAX			Integer32
	MAX-ACCESS		read-only
	STATUS			current
	DESCRIPTION
		"Total IP frames in to flow manager on this interface"
	::= {apFlowMgrDetailEntry 7}

apFlowMgrDetailTotalInFlows OBJECT-TYPE
	SYNTAX			Integer32
	MAX-ACCESS		read-only
	STATUS			current
	DESCRIPTION
		"Total inbound flows started on this interface"
	::= {apFlowMgrDetailEntry 8}

apFlowMgrDetailTotalOutFlows OBJECT-TYPE
	SYNTAX			Integer32
	MAX-ACCESS		read-only
	STATUS			current
	DESCRIPTION
		"Total flows started outbound through this interface"
	::= {apFlowMgrDetailEntry 9}

apFlowMgrDetailTotalAcctFlows OBJECT-TYPE
	SYNTAX			Integer32
	MAX-ACCESS		read-only
	STATUS			current
	DESCRIPTION
		"Total accounting reports received for flows on interface"
	::= {apFlowMgrDetailEntry 10}

apFlowMgrDetailResetCount OBJECT-TYPE
	SYNTAX			Integer32
	MAX-ACCESS		read-only
	STATUS			current
	DESCRIPTION
		"Total times flow manager reset interface"
	::= {apFlowMgrDetailEntry 11}

apFlowMgrDetailCurTCPFlows OBJECT-TYPE
	SYNTAX			Integer32
	MAX-ACCESS		read-only
	STATUS			current
	DESCRIPTION
		"Current number of active TCP flows on interface"
	::= {apFlowMgrDetailEntry 12}

apFlowMgrDetailCurUDPFlows OBJECT-TYPE
	SYNTAX			Integer32
	MAX-ACCESS		read-only
	STATUS			current
	DESCRIPTION
		"Current number of active UDP flows on interface"
	::= {apFlowMgrDetailEntry 13}

apFlowMgrDetailCurInFlows OBJECT-TYPE
	SYNTAX			Integer32
	MAX-ACCESS		read-only
	STATUS			current
	DESCRIPTION
		"Total number of flows on this interface"
	::= {apFlowMgrDetailEntry 14}

apFlowMgrDetailCurOutFlows OBJECT-TYPE
	SYNTAX			Integer32
	MAX-ACCESS		read-only
	STATUS			current
	DESCRIPTION
		"Total number of flows outbound on this interface"
	::= {apFlowMgrDetailEntry 15}

apFlowMgrDetailFPFlowCount OBJECT-TYPE
	SYNTAX			Integer32
	MAX-ACCESS		read-only
	STATUS			current
	DESCRIPTION
		"Total number of free FCBs reported by the fastpath for this port"
	::= {apFlowMgrDetailEntry 16}

apFlowMgrDetailTotalInFlowMap OBJECT-TYPE
	SYNTAX			Integer32
	MAX-ACCESS		read-only
	STATUS			current
	DESCRIPTION
		"Total number of active FCBs in the flow map for this port"
	::= {apFlowMgrDetailEntry 17}

apFlowMgrDetailInMappedOnlyPrimary OBJECT-TYPE
	SYNTAX			Integer32
	MAX-ACCESS		read-only
	STATUS			current
	DESCRIPTION
		"Total number of active FCBs for this port which have only 
         been mapped to one primary port"
	::= {apFlowMgrDetailEntry 18}

apFlowMgrDetailInMappedOnlyPrevious OBJECT-TYPE
	SYNTAX			Integer32
	MAX-ACCESS		read-only
	STATUS			current
	DESCRIPTION
		"Total number of active FCBs for this port which were mapped to a 
         previous port and are now unmapped"
	::= {apFlowMgrDetailEntry 19}

apFlowMgrDetailInMappedBothPrimary OBJECT-TYPE
	SYNTAX			Integer32
	MAX-ACCESS		read-only
	STATUS			current
	DESCRIPTION
		"Total number of active FCBs for this port which have only been 
         mapped to one primary port"
	::= {apFlowMgrDetailEntry 20}

apFlowMgrDetailInMappedBothPrevious OBJECT-TYPE
	SYNTAX			Integer32
	MAX-ACCESS		read-only
	STATUS			current
	DESCRIPTION
		"Total number of active FCBs for this port which have had their 
         primary port remapped to a different port"
	::= {apFlowMgrDetailEntry 21}

apFlowMgrDetailInNoFPMappings OBJECT-TYPE
	SYNTAX			Integer32
	MAX-ACCESS		read-only
	STATUS			current
	DESCRIPTION
		"Total number of active FCBs for this port which are not 
         mapped in the fastpath, though are active on the SFP"
	::= {apFlowMgrDetailEntry 22}

apFlowMgrDetailInIngressQueueLen OBJECT-TYPE
	SYNTAX			Integer32
	MAX-ACCESS		read-only
	STATUS			current
	DESCRIPTION
		"The length of the ingress (input) queue for this port"
	::= {apFlowMgrDetailEntry 23}

apFlowMgrDetailInOrphanFCBFlows OBJECT-TYPE
	SYNTAX			Integer32
	MAX-ACCESS		read-only
	STATUS			current
	DESCRIPTION
		"The number of times a FCB for this port was found to still
         be mapped in the fastpath when it was reallocated"
	::= {apFlowMgrDetailEntry 24}

apFlowMgrDetailInTotalOrphanFCB OBJECT-TYPE
	SYNTAX			Integer32
	MAX-ACCESS		read-only
	STATUS			current
	DESCRIPTION
		"The total number of times a FCB was mapped in the fastpath
         and found to still be mapped when it was reallocated"
	::= {apFlowMgrDetailEntry 25}

apFlowMgrDetailInTCPPermPort OBJECT-TYPE
	SYNTAX			Integer32
	MAX-ACCESS		read-only
	STATUS			current
	DESCRIPTION
		"The total number of active TCP FCBs on this port that are 
         associated with a configured permanent port"
	::= {apFlowMgrDetailEntry 26}

apFlowMgrDetailInUDPPermPort OBJECT-TYPE
	SYNTAX			Integer32
	MAX-ACCESS		read-only
	STATUS			current
	DESCRIPTION
		"The total number of active UDP FCBs on this port that are 
         associated with a configured permanent port"
	::= {apFlowMgrDetailEntry 27}

apFlowMgrDetailInJoined OBJECT-TYPE
	SYNTAX			Integer32
	MAX-ACCESS		read-only
	STATUS			current
	DESCRIPTION
		"The total number of active ingress FCBs on this port which are in 
         the joined state, meaning the backend server has acknowledged"
	::= {apFlowMgrDetailEntry 28}

apFlowMgrDetailInContentExpected OBJECT-TYPE
	SYNTAX			Integer32
	MAX-ACCESS		read-only
	STATUS			current
	DESCRIPTION
		"The total number of active ingress FCBs on this port which are 
         waiting for a content frame from the client"
	::= {apFlowMgrDetailEntry 29}

apFlowMgrDetailInJoinPending OBJECT-TYPE
	SYNTAX			Integer32
	MAX-ACCESS		read-only
	STATUS			current
	DESCRIPTION
		"The total number of active ingress FCBs on this port which are
         pended, waiting for the SYN/ACK from the backend server"
	::= {apFlowMgrDetailEntry 30}

apFlowMgrDetailInContentPending OBJECT-TYPE
	SYNTAX			Integer32
	MAX-ACCESS		read-only
	STATUS			current
	DESCRIPTION
		"The total number of active ingress FCBs on this port which are
         pended, waiting for the content frame from the client"
	::= {apFlowMgrDetailEntry 31}

apFlowMgrDetailInTCPSYNSent OBJECT-TYPE
	SYNTAX			Integer32
	MAX-ACCESS		read-only
	STATUS			current
	DESCRIPTION
		"The total number of active ingress FCBs on this port for which
         a SYN has been sent to the backend server"
	::= {apFlowMgrDetailEntry 32}

apFlowMgrDetailInReversePending OBJECT-TYPE
	SYNTAX			Integer32
	MAX-ACCESS		read-only
	STATUS			current
	DESCRIPTION
		"The total number of active ingress FCBs on this port which are
         waiting for a SYN/ACK from the client"
	::= {apFlowMgrDetailEntry 33}

apFlowMgrDetailInSFPForwarded OBJECT-TYPE
	SYNTAX			Integer32
	MAX-ACCESS		read-only
	STATUS			current
	DESCRIPTION
		"The total number of active ingress FCBs on this port which are being
         forward in the SFP and not mapped in the fastpath"
	::= {apFlowMgrDetailEntry 34}

apFlowMgrDetailInInPortInflowCount OBJECT-TYPE
	SYNTAX			Integer32
	MAX-ACCESS		read-only
	STATUS			current
	DESCRIPTION
		"The total number of ingress flows on this port"
	::= {apFlowMgrDetailEntry 35}

apFlowMgrDetailInDeleted OBJECT-TYPE
	SYNTAX			Integer32
	MAX-ACCESS		read-only
	STATUS			current
	DESCRIPTION
		"The total number of active ingress FCBs on this port which 
         have been deleted"
	::= {apFlowMgrDetailEntry 36}

apFlowMgrDetailInSpoofed OBJECT-TYPE
	SYNTAX			Integer32
	MAX-ACCESS		read-only
	STATUS			current
	DESCRIPTION
       "The total number of active ingress FCBs on this port which have 
        been spoofed"
	::= {apFlowMgrDetailEntry 37}

apFlowMgrDetailInNATInUse OBJECT-TYPE
	SYNTAX			Integer32
	MAX-ACCESS		read-only
	STATUS			current
	DESCRIPTION
       "The total number of active ingress FCBs on this port which have been
        natted"
	::= {apFlowMgrDetailEntry 38}

apFlowMgrDetailInContentAware OBJECT-TYPE
	SYNTAX			Integer32
	MAX-ACCESS		read-only
	STATUS			current
	DESCRIPTION
		"The total number of active ingress FCBs on this port which are 
         Layer 5 flows for which the CSS examines content frames"
	::= {apFlowMgrDetailEntry 39}

apFlowMgrDetailInSticky OBJECT-TYPE
	SYNTAX			Integer32
	MAX-ACCESS		read-only
	STATUS			current
	DESCRIPTION
		"The total number of active ingress FCBs on this port which are 
         using a sticky balance method"
	::= {apFlowMgrDetailEntry 40}

apFlowMgrDetailInBridged OBJECT-TYPE
	SYNTAX			Integer32
	MAX-ACCESS		read-only
	STATUS			current
	DESCRIPTION
		"The total number of active ingress FCBs on this port for which we
         are bridging frames"
	::= {apFlowMgrDetailEntry 41}

apFlowMgrDetailInBuffersPending OBJECT-TYPE
	SYNTAX			Integer32
	MAX-ACCESS		read-only
	STATUS			current
	DESCRIPTION
		"The total number of active ingress FCBs on this port for 
         which we have buffers containing content frames, awaiting the
         backend connection to the server to complete"
	::= {apFlowMgrDetailEntry 42}

apFlowMgrDetailInSYNDOSTimerActive OBJECT-TYPE
	SYNTAX			Integer32
	MAX-ACCESS		read-only
	STATUS			current
	DESCRIPTION
		"The total number of active ingress FCBs on this port for 
         which we are running the SYN/ACK timer, awaiting the SYN/ACK 
         from the backend server"
	::= {apFlowMgrDetailEntry 43}

apFlowMgrDetailInOverflowMapped OBJECT-TYPE
	SYNTAX			Integer32
	MAX-ACCESS		read-only
	STATUS			current
	DESCRIPTION
		"The total number of active ingress FCBs on this port 
         which have been overflow mapped, meaning that there 
         is not FCB available in the fastpath"
	::= {apFlowMgrDetailEntry 44}

apFlowMgrDetailInRejected OBJECT-TYPE
	SYNTAX			Integer32
	MAX-ACCESS		read-only
	STATUS			current
	DESCRIPTION
		"The total number of active ingress FCBs on this port which are
         marked rejected"
	::= {apFlowMgrDetailEntry 45}

apFlowMgrDetailInTotalTCPFlows OBJECT-TYPE
	SYNTAX			Integer32
	MAX-ACCESS		read-only
	STATUS			current
	DESCRIPTION
		"The total number of active ingress FCBs on this port which are
         the TCP protocol"
	::= {apFlowMgrDetailEntry 46}

apFlowMgrDetailInTotalUDPFlows OBJECT-TYPE
	SYNTAX			Integer32
	MAX-ACCESS		read-only
	STATUS			current
	DESCRIPTION
		"The total number of active ingress FCBs on this port which are
         the UDP protocol"
	::= {apFlowMgrDetailEntry 47}

apFlowMgrDetailInHTTPSrcFlows OBJECT-TYPE
	SYNTAX			Integer32
	MAX-ACCESS		read-only
	STATUS			current
	DESCRIPTION
		"The total number of active ingress FCBs on this port which have
         the HTTP port (80) as the source port"
	::= {apFlowMgrDetailEntry 48}

apFlowMgrDetailInHTTPDstFlows OBJECT-TYPE
	SYNTAX			Integer32
	MAX-ACCESS		read-only
	STATUS			current
	DESCRIPTION
		"The total number of active ingress FCBs on this port which have
         the HTTP port (80) as the destination port"
	::= {apFlowMgrDetailEntry 49}

apFlowMgrDetailInFTPDataSrcFlows OBJECT-TYPE
	SYNTAX			Integer32
	MAX-ACCESS		read-only
	STATUS			current
	DESCRIPTION
		"The total number of active ingress FCBs on this port which have
         the FTP Data port (20) as the source port"
	::= {apFlowMgrDetailEntry 50}

apFlowMgrDetailInFTPDataDestFlows OBJECT-TYPE
	SYNTAX			Integer32
	MAX-ACCESS		read-only
	STATUS			current
	DESCRIPTION
		"The total number of active ingress FCBs on this port which have
         the FTP Data port (20) as the destination port"
	::= {apFlowMgrDetailEntry 51}

apFlowMgrDetailInFTPCtrlSrcFlows OBJECT-TYPE
	SYNTAX			Integer32
	MAX-ACCESS		read-only
	STATUS			current
	DESCRIPTION
		"The total number of active ingress FCBs on this port which have
         the FTP Ctrl port (21) as the source port"
	::= {apFlowMgrDetailEntry 52}

apFlowMgrDetailInFTPCtrlDestFlows OBJECT-TYPE
	SYNTAX			Integer32
	MAX-ACCESS		read-only
	STATUS			current
	DESCRIPTION
		"The total number of active ingress FCBs on this port which have
         the FTP Data port (21) as the destination port"
	::= {apFlowMgrDetailEntry 53}

apFlowMgrDetailInSSHSrcFlows OBJECT-TYPE
	SYNTAX			Integer32
	MAX-ACCESS		read-only
	STATUS			current
	DESCRIPTION
		"The total number of active ingress FCBs on this port which have
         the SSH port (22) as the source port"
	::= {apFlowMgrDetailEntry 54}

apFlowMgrDetailInSSHDestFlows OBJECT-TYPE
	SYNTAX			Integer32
	MAX-ACCESS		read-only
	STATUS			current
	DESCRIPTION
		"The total number of active ingress FCBs on this port which have
         the SSH port (22) as the destination port"
	::= {apFlowMgrDetailEntry 55}

apFlowMgrDetailInTelnetSrcFlows OBJECT-TYPE
	SYNTAX			Integer32
	MAX-ACCESS		read-only
	STATUS			current
	DESCRIPTION
		"The total number of active ingress FCBs on this port which have
         the TELNET port (23) as the source port"
	::= {apFlowMgrDetailEntry 56}

apFlowMgrDetailInTelnetDestFlows OBJECT-TYPE
	SYNTAX			Integer32
	MAX-ACCESS		read-only
	STATUS			current
	DESCRIPTION
		"The total number of active ingress FCBs on this port which have
         the TELNET port (23) as the destination port"
	::= {apFlowMgrDetailEntry 57}

apFlowMgrDetailInRASrcFlows OBJECT-TYPE
	SYNTAX			Integer32
	MAX-ACCESS		read-only
	STATUS			current
	DESCRIPTION
		"The total number of active ingress FCBs on this port which have
         the REAL AUDIO port (7070) as the source port"
	::= {apFlowMgrDetailEntry 58}

apFlowMgrDetailInRADestFlows OBJECT-TYPE
	SYNTAX			Integer32
	MAX-ACCESS		read-only
	STATUS			current
	DESCRIPTION
		"The total number of active ingress FCBs on this port which have
         the REAL AUDIO port (7070) as the destination port"
	::= {apFlowMgrDetailEntry 59}

apFlowMgrDetailInBGPSrcFlows OBJECT-TYPE
	SYNTAX			Integer32
	MAX-ACCESS		read-only
	STATUS			current
	DESCRIPTION
		"The total number of active ingress FCBs on this port which have
         the BGP port (179) as the source port"
	::= {apFlowMgrDetailEntry 60}

apFlowMgrDetailInBGPDestFlows OBJECT-TYPE
	SYNTAX			Integer32
	MAX-ACCESS		read-only
	STATUS			current
	DESCRIPTION
		"The total number of active ingress FCBs on this port which have
         the BGP port (179) as the destination port"
	::= {apFlowMgrDetailEntry 61}

apFlowMgrDetailInSMTPSrcFlows OBJECT-TYPE
	SYNTAX			Integer32
	MAX-ACCESS		read-only
	STATUS			current
	DESCRIPTION
		"The total number of active ingress FCBs on this port which have
         the SMTP port (25) as the source port"
	::= {apFlowMgrDetailEntry 62}

apFlowMgrDetailInSMTPDestFlows OBJECT-TYPE
	SYNTAX			Integer32
	MAX-ACCESS		read-only
	STATUS			current
	DESCRIPTION
		"The total number of active ingress FCBs on this port which have
         the SMTP port (25) as the destination port"
	::= {apFlowMgrDetailEntry 63}

apFlowMgrDetailInPOP3SrcFlows OBJECT-TYPE
	SYNTAX			Integer32
	MAX-ACCESS		read-only
	STATUS			current
	DESCRIPTION
		"The total number of active ingress FCBs on this port which have
         the POP3 port (110) as the source port"
	::= {apFlowMgrDetailEntry 64}

apFlowMgrDetailInPOP3DestFlows OBJECT-TYPE
	SYNTAX			Integer32
	MAX-ACCESS		read-only
	STATUS			current
	DESCRIPTION
		"The total number of active ingress FCBs on this port which have
         the POP3 port (110) as the destination port"
	::= {apFlowMgrDetailEntry 65}

apFlowMgrDetailInHTTPSSrcFlows OBJECT-TYPE
	SYNTAX			Integer32
	MAX-ACCESS		read-only
	STATUS			current
	DESCRIPTION
		"The total number of active ingress FCBs on this port which have
         the SSL port (443) as the source port"
	::= {apFlowMgrDetailEntry 66}

apFlowMgrDetailInHTTPSDestFlows OBJECT-TYPE
	SYNTAX			Integer32
	MAX-ACCESS		read-only
	STATUS			current
	DESCRIPTION
		"The total number of active ingress FCBs on this port which have
         the SSL port (443) as the destination port"
	::= {apFlowMgrDetailEntry 67}

apFlowMgrDetailInNNTPSrcFlows OBJECT-TYPE
	SYNTAX			Integer32
	MAX-ACCESS		read-only
	STATUS			current
	DESCRIPTION
		"The total number of active ingress FCBs on this port which have
         the NNTP port (119) as the source port"
	::= {apFlowMgrDetailEntry 68}

apFlowMgrDetailInNNTPDestFlows OBJECT-TYPE
	SYNTAX			Integer32
	MAX-ACCESS		read-only
	STATUS			current
	DESCRIPTION
		"The total number of active ingress FCBs on this port which have
         the NNTP port (119) as the destination port"
	::= {apFlowMgrDetailEntry 69}

apFlowMgrDetailInSOCKSSrcFlows OBJECT-TYPE
	SYNTAX			Integer32
	MAX-ACCESS		read-only
	STATUS			current
	DESCRIPTION
		"The total number of active ingress FCBs on this port which have
         the SOCKS port (1080) as the source port"
	::= {apFlowMgrDetailEntry 70}

apFlowMgrDetailInSOCKSDestFlows OBJECT-TYPE
	SYNTAX			Integer32
	MAX-ACCESS		read-only
	STATUS			current
	DESCRIPTION
		"The total number of active ingress FCBs on this port which have
         the SOCKS port (1080) as the destination port"
	::= {apFlowMgrDetailEntry 71}

apFlowMgrDetailInPortLT23SrcFlows OBJECT-TYPE
	SYNTAX			Integer32
	MAX-ACCESS		read-only
	STATUS			current
	DESCRIPTION
		"The total number of active ingress FCBs on this port which have
         a TCP port number less than 23 as the source port"
	::= {apFlowMgrDetailEntry 72}

apFlowMgrDetailInPortLT23DestFlows OBJECT-TYPE
	SYNTAX			Integer32
	MAX-ACCESS		read-only
	STATUS			current
	DESCRIPTION
		"The total number of active ingress FCBs on this port which have
         a TCP port number less than 23 as the destination port"
	::= {apFlowMgrDetailEntry 73}

apFlowMgrDetailInPortGT1024SrcFlows OBJECT-TYPE
	SYNTAX			Integer32
	MAX-ACCESS		read-only
	STATUS			current
	DESCRIPTION
		"The total number of active ingress FCBs on this port which have
         a TCP port number greater than 1024 as the source port"
	::= {apFlowMgrDetailEntry 74}

apFlowMgrDetailInPortGT1024DestFlows OBJECT-TYPE
	SYNTAX			Integer32
	MAX-ACCESS		read-only
	STATUS			current
	DESCRIPTION
		"The total number of active ingress FCBs on this port which have
         a TCP port number greater than 1024 as the destination port"
	::= {apFlowMgrDetailEntry 75}

apFlowMgrDetailInTimeSrcFlows OBJECT-TYPE
	SYNTAX			Integer32
	MAX-ACCESS		read-only
	STATUS			current
	DESCRIPTION
		"The total number of active ingress FCBs on this port which have
         the TIME port (37) as the source port"
	::= {apFlowMgrDetailEntry 76}

apFlowMgrDetailInTimeDestSrcFlows OBJECT-TYPE
	SYNTAX			Integer32
	MAX-ACCESS		read-only
	STATUS			current
	DESCRIPTION
		"The total number of active ingress FCBs on this port which have
         the TIME port (37) as the destination port"
	::= {apFlowMgrDetailEntry 77}

apFlowMgrDetailInDNSSrcFlows OBJECT-TYPE
	SYNTAX			Integer32
	MAX-ACCESS		read-only
	STATUS			current
	DESCRIPTION
		"The total number of active ingress FCBs on this port which have
         the DNS port (53) as the source port"
	::= {apFlowMgrDetailEntry 78}

apFlowMgrDetailInDNSDestFlows OBJECT-TYPE
	SYNTAX			Integer32
	MAX-ACCESS		read-only
	STATUS			current
	DESCRIPTION
		"The total number of active ingress FCBs on this port which have
         the DNS port (53) as the destination port"
	::= {apFlowMgrDetailEntry 79}

apFlowMgrDetailInSNMPSrcFlows OBJECT-TYPE
	SYNTAX			Integer32
	MAX-ACCESS		read-only
	STATUS			current
	DESCRIPTION
		"The total number of active ingress FCBs on this port which have
         the SNMP port (161) as the source port"
	::= {apFlowMgrDetailEntry 80}

apFlowMgrDetailInSNMPDestFlows OBJECT-TYPE
	SYNTAX			Integer32
	MAX-ACCESS		read-only
	STATUS			current
	DESCRIPTION
		"The total number of active ingress FCBs on this port which have
         the SNMP port (161) as the destination port"
	::= {apFlowMgrDetailEntry 81}

apFlowMgrDetailInSNMPTrapSrcFlows OBJECT-TYPE
	SYNTAX			Integer32
	MAX-ACCESS		read-only
	STATUS			current
	DESCRIPTION
		"The total number of active ingress FCBs on this port which have
         the SNMP Trap port (162) as the source port"
	::= {apFlowMgrDetailEntry 82}

apFlowMgrDetailInSNMPTrapDestFlows OBJECT-TYPE
	SYNTAX			Integer32
	MAX-ACCESS		read-only
	STATUS			current
	DESCRIPTION
		"The total number of active ingress FCBs on this port which have
         the SNMP Trap port (162) as the destination port"
	::= {apFlowMgrDetailEntry 83}

apFlowMgrDetailInNFSSrcFlows OBJECT-TYPE
	SYNTAX			Integer32
	MAX-ACCESS		read-only
	STATUS			current
	DESCRIPTION
		"The total number of active ingress FCBs on this port which have
         the NFS port (2049) as the source port"
	::= {apFlowMgrDetailEntry 84}

apFlowMgrDetailInNFSDestFlows OBJECT-TYPE
	SYNTAX			Integer32
	MAX-ACCESS		read-only
	STATUS			current
	DESCRIPTION
		"The total number of active ingress FCBs on this port which have
         the NFS port (2049) as the destination port"
	::= {apFlowMgrDetailEntry 85}

apFlowMgrDetailInUDPGT1024SrcFlows OBJECT-TYPE
	SYNTAX			Integer32
	MAX-ACCESS		read-only
	STATUS			current
	DESCRIPTION
		"The total number of active ingress FCBs on this port which have
         a UDP port number greater than 1024 as the source port"
	::= {apFlowMgrDetailEntry 86}

apFlowMgrDetailInUDPGT1024DestFlows OBJECT-TYPE
	SYNTAX			Integer32
	MAX-ACCESS		read-only
	STATUS			current
	DESCRIPTION
		"The total number of active ingress FCBs on this port which have
         a UDP port number greater than 1024 as the destination port"
	::= {apFlowMgrDetailEntry 87}

apFlowMgrDetailInUDPLT1024SrcFlows OBJECT-TYPE
	SYNTAX			Integer32
	MAX-ACCESS		read-only
	STATUS			current
	DESCRIPTION
		"The total number of active ingress FCBs on this port which have
         a UDP port number less than 1024 as the source port"
	::= {apFlowMgrDetailEntry 88}

apFlowMgrDetailInUDPLT1024DestFlows OBJECT-TYPE
	SYNTAX			Integer32
	MAX-ACCESS		read-only
	STATUS			current
	DESCRIPTION
		"The total number of active ingress FCBs on this port which have
         a UDP port number less than 1024 as the destination port"
	::= {apFlowMgrDetailEntry 89}

apFlowMgrDetailInExplicitFlows OBJECT-TYPE
	SYNTAX			Integer32
	MAX-ACCESS		read-only
	STATUS			current
	DESCRIPTION
		"The total number of active FCBs on this port which have
         been setup as an explicit flow from another SFP"
	::= {apFlowMgrDetailEntry 90}

apFlowMgrDetailInAcctSent OBJECT-TYPE
	SYNTAX			Integer32
	MAX-ACCESS		read-only
	STATUS			current
	DESCRIPTION
		"The total number of active FCBs on this port for which
         accounting reports have been received"
	::= {apFlowMgrDetailEntry 91}

apFlowMgrDetailEgTCPPermPort OBJECT-TYPE
	SYNTAX			Integer32
	MAX-ACCESS		read-only
	STATUS			current
	DESCRIPTION
		"The total number of active TCP FCBs on this port which have
         a permanent for either the source or destination port"
	::= {apFlowMgrDetailEntry 92}

apFlowMgrDetailEgUDPPermPort OBJECT-TYPE
	SYNTAX			Integer32
	MAX-ACCESS		read-only
	STATUS			current
	DESCRIPTION
		"The total number of active UDP FCBs on this port which have
         a permanent for either the source or destination port"
	::= {apFlowMgrDetailEntry 93}

apFlowMgrDetailEgJoined OBJECT-TYPE
	SYNTAX			Integer32
	MAX-ACCESS		read-only
	STATUS			current
	DESCRIPTION
		"The total number of active egress FCBs on this port which are in 
         the joined state, meaning the backend server has acknowledged"
	::= {apFlowMgrDetailEntry 94}

apFlowMgrDetailEgContentExpected OBJECT-TYPE
	SYNTAX			Integer32
	MAX-ACCESS		read-only
	STATUS			current
	DESCRIPTION
		"The total number of active egress FCBs on this port which are 
         waiting for a content frame from the client"
	::= {apFlowMgrDetailEntry 95}

apFlowMgrDetailEgJoinPending OBJECT-TYPE
	SYNTAX			Integer32
	MAX-ACCESS		read-only
	STATUS			current
	DESCRIPTION
		"The total number of active egress FCBs on this port which are
         pended, waiting for the SYN/ACK from the backend server"
	::= {apFlowMgrDetailEntry 96}

apFlowMgrDetailEgContentPending OBJECT-TYPE
	SYNTAX			Integer32
	MAX-ACCESS		read-only
	STATUS			current
	DESCRIPTION
		"The total number of active egress FCBs on this port which are
         pended, waiting for the content frame from the client"
	::= {apFlowMgrDetailEntry 97}

apFlowMgrDetailEgTCPSYNSent OBJECT-TYPE
	SYNTAX			Integer32
	MAX-ACCESS		read-only
	STATUS			current
	DESCRIPTION
		"The total number of active egress FCBs on this port for which
         a SYN has been sent to the backend server"
	::= {apFlowMgrDetailEntry 98}

apFlowMgrDetailEgReversePending OBJECT-TYPE
	SYNTAX			Integer32
	MAX-ACCESS		read-only
	STATUS			current
	DESCRIPTION
		"The total number of active egress FCBs on this port which are
         waiting for a SYN/ACK from the client"
	::= {apFlowMgrDetailEntry 99}

apFlowMgrDetailEgSFPFowrarded OBJECT-TYPE
	SYNTAX			Integer32
	MAX-ACCESS		read-only
	STATUS			current
	DESCRIPTION
		"The total number of active egress FCBs on this port which are being
         forward in the SFP and not mapped in the fastpath"
	::= {apFlowMgrDetailEntry 100}

apFlowMgrDetailEgInPortInflowCount OBJECT-TYPE
	SYNTAX			Integer32
	MAX-ACCESS		read-only
	STATUS			current
	DESCRIPTION
		"The total number of egress flows on this port"
	::= {apFlowMgrDetailEntry 101}

apFlowMgrDetailEgDeleted OBJECT-TYPE
	SYNTAX			Integer32
	MAX-ACCESS		read-only
	STATUS			current
	DESCRIPTION
		"The total number of active egress FCBs on this port which 
         have been deleted"
	::= {apFlowMgrDetailEntry 102}

apFlowMgrDetailEgSpoofed OBJECT-TYPE
	SYNTAX			Integer32
	MAX-ACCESS		read-only
	STATUS			current
	DESCRIPTION
       "The total number of active egress FCBs on this port which have 
        been spoofed"
	::= {apFlowMgrDetailEntry 103}

apFlowMgrDetailEgNATInUse OBJECT-TYPE
	SYNTAX			Integer32
	MAX-ACCESS		read-only
	STATUS			current
	DESCRIPTION
       "The total number of active egress FCBs on this port which have been
        natted"
	::= {apFlowMgrDetailEntry 104}

apFlowMgrDetailEgContentAware OBJECT-TYPE
	SYNTAX			Integer32
	MAX-ACCESS		read-only
	STATUS			current
	DESCRIPTION
		"The total number of active egress FCBs on this port which are 
         Layer 5 flows for which the CSS examines content frames"
	::= {apFlowMgrDetailEntry 105}

apFlowMgrDetailEgSticky OBJECT-TYPE
	SYNTAX			Integer32
	MAX-ACCESS		read-only
	STATUS			current
	DESCRIPTION
		"The total number of active egress FCBs on this port which are 
         using a sticky balance method"
	::= {apFlowMgrDetailEntry 106}

apFlowMgrDetailEgBridged OBJECT-TYPE
	SYNTAX			Integer32
	MAX-ACCESS		read-only
	STATUS			current
	DESCRIPTION
		"The total number of active egress FCBs on this port for which we
         are bridging frames"
	::= {apFlowMgrDetailEntry 107}

apFlowMgrDetailEgBuffersPending OBJECT-TYPE
	SYNTAX			Integer32
	MAX-ACCESS		read-only
	STATUS			current
	DESCRIPTION
		"The total number of active egress FCBs on this port for 
         which we have buffers containing content frames, awaiting the
         backend connection to the server to complete"
	::= {apFlowMgrDetailEntry 108}

apFlowMgrDetailEgSYNDOSTimerActive OBJECT-TYPE
	SYNTAX			Integer32
	MAX-ACCESS		read-only
	STATUS			current
	DESCRIPTION
		"The total number of active egress FCBs on this port for 
         which we are running the SYN/ACK timer, awaiting the SYN/ACK 
         from the backend server"
	::= {apFlowMgrDetailEntry 109}

apFlowMgrDetailEgOverflowMapped OBJECT-TYPE
	SYNTAX			Integer32
	MAX-ACCESS		read-only
	STATUS			current
	DESCRIPTION
		"The total number of active egress FCBs on this port 
         which have been overflow mapped, meaning that there 
         is not FCB available in the fastpath"
	::= {apFlowMgrDetailEntry 110}

apFlowMgrDetailEgRejected OBJECT-TYPE
	SYNTAX			Integer32
	MAX-ACCESS		read-only
	STATUS			current
	DESCRIPTION
		"The total number of active egress FCBs on this port which are
         marked rejected"
	::= {apFlowMgrDetailEntry 111}

apFlowMgrDetailEgTotalTCPFlows OBJECT-TYPE
	SYNTAX			Integer32
	MAX-ACCESS		read-only
	STATUS			current
	DESCRIPTION
		"The total number of active egress FCBs on this port which are
         the TCP protocol"
	::= {apFlowMgrDetailEntry 112}

apFlowMgrDetailEgTotalUDPFlows OBJECT-TYPE
	SYNTAX			Integer32
	MAX-ACCESS		read-only
	STATUS			current
	DESCRIPTION
		"The total number of active egress FCBs on this port which are
         the UDP protocol"
	::= {apFlowMgrDetailEntry 113}

apFlowMgrDetailEgHTTPSrcFlows OBJECT-TYPE
	SYNTAX			Integer32
	MAX-ACCESS		read-only
	STATUS			current
	DESCRIPTION
		"The total number of active egress FCBs on this port which have
         the HTTP port (80) as the source port"
	::= {apFlowMgrDetailEntry 114}

apFlowMgrDetailEgHTTPDstFlows OBJECT-TYPE
	SYNTAX			Integer32
	MAX-ACCESS		read-only
	STATUS			current
	DESCRIPTION
		"The total number of active egress FCBs on this port which have
         the HTTP port (80) as the destination port"
	::= {apFlowMgrDetailEntry 115}

apFlowMgrDetailEgFTPDataSrcFlows OBJECT-TYPE
	SYNTAX			Integer32
	MAX-ACCESS		read-only
	STATUS			current
	DESCRIPTION
		"The total number of active egress FCBs on this port which have
         the FTP Data port (20) as the source port"
	::= {apFlowMgrDetailEntry 116}

apFlowMgrDetailEgFTPDataDestFlows OBJECT-TYPE
	SYNTAX			Integer32
	MAX-ACCESS		read-only
	STATUS			current
	DESCRIPTION
		"The total number of active egress FCBs on this port which have
         the FTP Data port (20) as the destination port"
	::= {apFlowMgrDetailEntry 117}

apFlowMgrDetailEgFTPCtrlSrcFlows OBJECT-TYPE
	SYNTAX			Integer32
	MAX-ACCESS		read-only
	STATUS			current
	DESCRIPTION
		"The total number of active egress FCBs on this port which have
         the FTP Ctrl port (21) as the source port"
	::= {apFlowMgrDetailEntry 118}

apFlowMgrDetailEgFTPCtrlDestFlows OBJECT-TYPE
	SYNTAX			Integer32
	MAX-ACCESS		read-only
	STATUS			current
	DESCRIPTION
		"The total number of active egress FCBs on this port which have
         the FTP Data port (21) as the destination port"
	::= {apFlowMgrDetailEntry 119}

apFlowMgrDetailEgSSHSrcFlows OBJECT-TYPE
	SYNTAX			Integer32
	MAX-ACCESS		read-only
	STATUS			current
	DESCRIPTION
		"The total number of active egress FCBs on this port which have
         the SSH port (22) as the source port"
	::= {apFlowMgrDetailEntry 120}

apFlowMgrDetailEgSSHDestFlows OBJECT-TYPE
	SYNTAX			Integer32
	MAX-ACCESS		read-only
	STATUS			current
	DESCRIPTION
		"The total number of active egress FCBs on this port which have
         the SSH port (22) as the destination port"
	::= {apFlowMgrDetailEntry 121}

apFlowMgrDetailEgTelnetSrcFlows OBJECT-TYPE
	SYNTAX			Integer32
	MAX-ACCESS		read-only
	STATUS			current
	DESCRIPTION
		"The total number of active egress FCBs on this port which have
         the TELNET port (23) as the source port"
	::= {apFlowMgrDetailEntry 122}

apFlowMgrDetailEgTelnetDestFlows OBJECT-TYPE
	SYNTAX			Integer32
	MAX-ACCESS		read-only
	STATUS			current
	DESCRIPTION
		"The total number of active egress FCBs on this port which have
         the TELNET port (23) as the destination port"
	::= {apFlowMgrDetailEntry 123}

apFlowMgrDetailEgRASrcFlows OBJECT-TYPE
	SYNTAX			Integer32
	MAX-ACCESS		read-only
	STATUS			current
	DESCRIPTION
		"The total number of active egress FCBs on this port which have
         the REAL AUDIO port (7070) as the source port"
	::= {apFlowMgrDetailEntry 124}

apFlowMgrDetailEgRADestFlows OBJECT-TYPE
	SYNTAX			Integer32
	MAX-ACCESS		read-only
	STATUS			current
	DESCRIPTION
		"The total number of active egress FCBs on this port which have
         the REAL AUDIO port (7070) as the destination port"
	::= {apFlowMgrDetailEntry 125}

apFlowMgrDetailEgBGPSrcFlows OBJECT-TYPE
	SYNTAX			Integer32
	MAX-ACCESS		read-only
	STATUS			current
	DESCRIPTION
		"The total number of active egress FCBs on this port which have
         the BGP port (179) as the source port"
	::= {apFlowMgrDetailEntry 126}

apFlowMgrDetailEgBGPDestFlows OBJECT-TYPE
	SYNTAX			Integer32
	MAX-ACCESS		read-only
	STATUS			current
	DESCRIPTION
		"The total number of active egress FCBs on this port which have
         the BGP port (179) as the destination port"
	::= {apFlowMgrDetailEntry 127}

apFlowMgrDetailEgSMTPSrcFlows OBJECT-TYPE
	SYNTAX			Integer32
	MAX-ACCESS		read-only
	STATUS			current
	DESCRIPTION
		"The total number of active egress FCBs on this port which have
         the SMTP port (25) as the source port"
	::= {apFlowMgrDetailEntry 128}

apFlowMgrDetailEgSMTPDestFlows OBJECT-TYPE
	SYNTAX			Integer32
	MAX-ACCESS		read-only
	STATUS			current
	DESCRIPTION
		"The total number of active egress FCBs on this port which have
         the SMTP port (25) as the destination port"
	::= {apFlowMgrDetailEntry 129}

apFlowMgrDetailEgPOP3SrcFlows OBJECT-TYPE
	SYNTAX			Integer32
	MAX-ACCESS		read-only
	STATUS			current
	DESCRIPTION
		"The total number of active egress FCBs on this port which have
         the POP3 port (110) as the source port"
	::= {apFlowMgrDetailEntry 130}

apFlowMgrDetailEgPOP3DestFlows OBJECT-TYPE
	SYNTAX			Integer32
	MAX-ACCESS		read-only
	STATUS			current
	DESCRIPTION
		"The total number of active egress FCBs on this port which have
         the POP3 port (110) as the destination port"
	::= {apFlowMgrDetailEntry 131}

apFlowMgrDetailEgHTTPSSrcFlows OBJECT-TYPE
	SYNTAX			Integer32
	MAX-ACCESS		read-only
	STATUS			current
	DESCRIPTION
		"The total number of active egress FCBs on this port which have
         the SSL port (443) as the source port"
	::= {apFlowMgrDetailEntry 132}

apFlowMgrDetailEgHTTPSDestFlows OBJECT-TYPE
	SYNTAX			Integer32
	MAX-ACCESS		read-only
	STATUS			current
	DESCRIPTION
		"The total number of active egress FCBs on this port which have
         the SSL port (443) as the destination port"
	::= {apFlowMgrDetailEntry 133}

apFlowMgrDetailEgNNTPSrcFlows OBJECT-TYPE
	SYNTAX			Integer32
	MAX-ACCESS		read-only
	STATUS			current
	DESCRIPTION
		"The total number of active egress FCBs on this port which have
         the NNTP port (119) as the source port"
	::= {apFlowMgrDetailEntry 134}

apFlowMgrDetailEgNNTPDestFlows OBJECT-TYPE
	SYNTAX			Integer32
	MAX-ACCESS		read-only
	STATUS			current
	DESCRIPTION
		"The total number of active egress FCBs on this port which have
         the NNTP port (119) as the destination port"
	::= {apFlowMgrDetailEntry 135}

apFlowMgrDetailEgSOCKSSrcFlows OBJECT-TYPE
	SYNTAX			Integer32
	MAX-ACCESS		read-only
	STATUS			current
	DESCRIPTION
		"The total number of active egress FCBs on this port which have
         the SOCKS port (1080) as the source port"
	::= {apFlowMgrDetailEntry 136}

apFlowMgrDetailEgSOCKSDestFlows OBJECT-TYPE
	SYNTAX			Integer32
	MAX-ACCESS		read-only
	STATUS			current
	DESCRIPTION
		"The total number of active egress FCBs on this port which have
         the SOCKS port (1080) as the destination port"
	::= {apFlowMgrDetailEntry 137}

apFlowMgrDetailEgPortLT23SrcFlows OBJECT-TYPE
	SYNTAX			Integer32
	MAX-ACCESS		read-only
	STATUS			current
	DESCRIPTION
		"The total number of active egress FCBs on this port which have
         a TCP port number less than 23 as the source port"
	::= {apFlowMgrDetailEntry 138}

apFlowMgrDetailEgPortLT23DestFlows OBJECT-TYPE
	SYNTAX			Integer32
	MAX-ACCESS		read-only
	STATUS			current
	DESCRIPTION
		"The total number of active egress FCBs on this port which have
         a TCP port number less than 23 as the destination port"
	::= {apFlowMgrDetailEntry 139}

apFlowMgrDetailEgPortGT1024SrcFlows OBJECT-TYPE
	SYNTAX			Integer32
	MAX-ACCESS		read-only
	STATUS			current
	DESCRIPTION
		"The total number of active egress FCBs on this port which have
         a TCP port number greater than 1024 as the source port"
	::= {apFlowMgrDetailEntry 140}

apFlowMgrDetailEgPortGT1024DestFlows OBJECT-TYPE
	SYNTAX			Integer32
	MAX-ACCESS		read-only
	STATUS			current
	DESCRIPTION
		"The total number of active egress FCBs on this port which have
         a TCP port number greater than 1024 as the destination port"
	::= {apFlowMgrDetailEntry 141}

apFlowMgrDetailEgTimeSrcFlows OBJECT-TYPE
	SYNTAX			Integer32
	MAX-ACCESS		read-only
	STATUS			current
	DESCRIPTION
		"The total number of active egress FCBs on this port which have
         the TIME port (37) as the source port"
	::= {apFlowMgrDetailEntry 142}

apFlowMgrDetailEgTimeDestSrcFlows OBJECT-TYPE
	SYNTAX			Integer32
	MAX-ACCESS		read-only
	STATUS			current
	DESCRIPTION
		"The total number of active egress FCBs on this port which have
         the TIME port (37) as the destination port"
	::= {apFlowMgrDetailEntry 143}

apFlowMgrDetailEgDNSSrcFlows OBJECT-TYPE
	SYNTAX			Integer32
	MAX-ACCESS		read-only
	STATUS			current
	DESCRIPTION
		"The total number of active egress FCBs on this port which have
         the DNS port (53) as the source port"
	::= {apFlowMgrDetailEntry 144}

apFlowMgrDetailEgDNSDestFlows OBJECT-TYPE
	SYNTAX			Integer32
	MAX-ACCESS		read-only
	STATUS			current
	DESCRIPTION
		"The total number of active egress FCBs on this port which have
         the DNS port (53) as the destination port"
	::= {apFlowMgrDetailEntry 145}

apFlowMgrDetailEgSNMPSrcFlows OBJECT-TYPE
	SYNTAX			Integer32
	MAX-ACCESS		read-only
	STATUS			current
	DESCRIPTION
		"The total number of active egress FCBs on this port which have
         the SNMP port (161) as the source port"
	::= {apFlowMgrDetailEntry 146}

apFlowMgrDetailEgSNMPDestFlows OBJECT-TYPE
	SYNTAX			Integer32
	MAX-ACCESS		read-only
	STATUS			current
	DESCRIPTION
		"The total number of active egress FCBs on this port which have
         the SNMP port (161) as the destination port"
	::= {apFlowMgrDetailEntry 147}

apFlowMgrDetailEgSNMPTrapSrcFlows OBJECT-TYPE
	SYNTAX			Integer32
	MAX-ACCESS		read-only
	STATUS			current
	DESCRIPTION
		"The total number of active egress FCBs on this port which have
         the SNMP Trap port (162) as the source port"
	::= {apFlowMgrDetailEntry 148}

apFlowMgrDetailEgSNMPTrapDestFlows OBJECT-TYPE
	SYNTAX			Integer32
	MAX-ACCESS		read-only
	STATUS			current
	DESCRIPTION
		"The total number of active egress FCBs on this port which have
         the SNMP Trap port (162) as the destination port"
	::= {apFlowMgrDetailEntry 149}

apFlowMgrDetailEgNFSSrcFlows OBJECT-TYPE
	SYNTAX			Integer32
	MAX-ACCESS		read-only
	STATUS			current
	DESCRIPTION
		"The total number of active egress FCBs on this port which have
         the NFS port (2049) as the source port"
	::= {apFlowMgrDetailEntry 150}

apFlowMgrDetailEgNFSDestFlows OBJECT-TYPE
	SYNTAX			Integer32
	MAX-ACCESS		read-only
	STATUS			current
	DESCRIPTION
		"The total number of active egress FCBs on this port which have
         the NFS port (2049) as the destination port"
	::= {apFlowMgrDetailEntry 151}

apFlowMgrDetailEgUDPGT1024SrcFlows OBJECT-TYPE
	SYNTAX			Integer32
	MAX-ACCESS		read-only
	STATUS			current
	DESCRIPTION
		"The total number of active egress FCBs on this port which have
         a UDP port number greater than 1024 as the source port"
	::= {apFlowMgrDetailEntry 152}

apFlowMgrDetailEgUDPGT1024DestFlows OBJECT-TYPE
	SYNTAX			Integer32
	MAX-ACCESS		read-only
	STATUS			current
	DESCRIPTION
		"The total number of active egress FCBs on this port which have
         a UDP port number greater than 1024 as the destination port"
	::= {apFlowMgrDetailEntry 153}

apFlowMgrDetailEgUDPLT1024SrcFlows OBJECT-TYPE
	SYNTAX			Integer32
	MAX-ACCESS		read-only
	STATUS			current
	DESCRIPTION
		"The total number of active egress FCBs on this port which have
         a UDP port number less than 1024 as the source port"
	::= {apFlowMgrDetailEntry 154}

apFlowMgrDetailEgUDPLT1024DestFlows OBJECT-TYPE
	SYNTAX			Integer32
	MAX-ACCESS		read-only
	STATUS			current
	DESCRIPTION
		"The total number of active egress FCBs on this port which have
         a UDP port number less than 1024 as the destination port"
	::= {apFlowMgrDetailEntry 155}

apFlowMgrDetailOutFrames OBJECT-TYPE
	SYNTAX			Integer32
	MAX-ACCESS		read-only
	STATUS			current
	DESCRIPTION
		"Total IP frames sent by the flow manager on this interface"
	::= {apFlowMgrDetailEntry 156}



-- ********************** apFlowMgrDetailTable END ************************

-- ********************** apFlowMgr DOS Scalars BEGIN *********************

apFlowMgrExtDosTotalAttacks OBJECT-TYPE
	SYNTAX Integer32
	MAX-ACCESS read-only
	STATUS current
	DESCRIPTION
		"This object specifies the total number of 
         Denial Of Service (DOS) attacks detected by 
         the flowmgr."
	::= { flowMgrExt 18 }

apFlowMgrExtDosTotalSynAttacks OBJECT-TYPE
	SYNTAX Integer32
	MAX-ACCESS read-only
	STATUS current
	DESCRIPTION
		"This object specifies the total number of 
         Denial Of Service (DOS) SYN attacks detected by 
         the flowmgr."
	::= { flowMgrExt 19 }

apFlowMgrExtDosTotalLandAttacks OBJECT-TYPE
	SYNTAX Integer32
	MAX-ACCESS read-only
	STATUS current
	DESCRIPTION
		"This object specifies the total number of 
         Denial Of Service (DOS) LAND attacks detected by 
         the flowmgr."
	::= { flowMgrExt 20 }

apFlowMgrExtDosTotalZeroPortAttacks OBJECT-TYPE
	SYNTAX Integer32
	MAX-ACCESS read-only
	STATUS current
	DESCRIPTION
		"This object specifies the total number of 
         Denial Of Service (DOS) attacks to a source or
         destination port of zero detected by the flowmgr."
	::= { flowMgrExt 21 }

apFlowMgrExtDosTotalIllegalSourceAttacks OBJECT-TYPE
	SYNTAX Integer32
	MAX-ACCESS read-only
	STATUS current
	DESCRIPTION
		"This object specifies the total number of 
         Denial Of Service (DOS) attacks to an illegal
         source address detected by the flowmgr."
	::= { flowMgrExt 22 }        
	
apFlowMgrExtDosTotalIllegalDestinationAttacks OBJECT-TYPE
	SYNTAX Integer32
	MAX-ACCESS read-only
	STATUS current
	DESCRIPTION
		"This object specifies the total number of 
		Denial Of Service (DOS) attacks to an illegal 
		destination address detected by the flowmgr."
	::= { flowMgrExt 23 }
	             
apFlowMgrExtDosTotalPingOfDeathAttacks OBJECT-TYPE
	SYNTAX Integer32
	MAX-ACCESS read-only
	STATUS obsolete
	DESCRIPTION
		"This object specifies the total number of 
         Denial Of Service (DOS) Ping of Death attacks 
         detected by the flowmgr."
	::= { flowMgrExt 24 }

apFlowMgrExtDosTotalSmurfAttacks OBJECT-TYPE
	SYNTAX Integer32
	MAX-ACCESS read-only
	STATUS current
	DESCRIPTION
		"This object specifies the total number of 
         Denial Of Service (DOS) Smurf attacks 
         detected by the flowmgr."
	::= { flowMgrExt 25 }

apFlowMgrExtDosLastAttack OBJECT-TYPE
	SYNTAX DisplayString
	MAX-ACCESS read-only
	STATUS current
	DESCRIPTION
		"This object specifies the time of the last
         Denial Of Service (DOS) attack detected by 
         the flowmgr."
	::= { flowMgrExt 26 }

apFlowMgrExtDosFirstAttack OBJECT-TYPE
	SYNTAX DisplayString
	MAX-ACCESS read-only
	STATUS current
	DESCRIPTION
		"This object specifies the time of the first
         Denial Of Service (DOS) attack detected by
         the flowmgr."
	::= { flowMgrExt 27 }

-- ********************** apFlowMgr DOS Scalars END ************************

-- ********************** apFlowMgrExtDOSAttackTable BEGIN *****************

apFlowMgrExtDOSAttackTable OBJECT-TYPE
	SYNTAX	SEQUENCE OF APFlowMgrExtDOSAttackEntry
	MAX-ACCESS  not-accessible
	STATUS	current
	DESCRIPTION
		"This is the table of Denial of Service (DOS) attack
         events."
	::= { flowMgrExt 28 }

apFlowMgrExtDOSAttackEntry OBJECT-TYPE
    SYNTAX  APFlowMgrExtDOSAttackEntry
    MAX-ACCESS  not-accessible
    STATUS  current
    DESCRIPTION
		"This is the table of Denial of Service (DOS) attack
         events."
    INDEX  { apFlowMgrExtDOSAttackIndex }
    ::= { apFlowMgrExtDOSAttackTable 1 } 

APFlowMgrExtDOSAttackEntry ::=
    SEQUENCE {
		apFlowMgrExtDOSAttackIndex
			INTEGER,
        apFlowMgrExtDOSAttackSrcAddress
            IpAddress,
        apFlowMgrExtDOSAttackDestAddress
            IpAddress,
        apFlowMgrExtDOSAttackFirstEvent
            DisplayString,
        apFlowMgrExtDOSAttackLastEvent
            DisplayString,
        apFlowMgrExtDOSAttackEventCount
            Integer32,
        apFlowMgrExtDOSAttackEventType
            INTEGER,
        apFlowMgrExtDOSAttackEventString
            DisplayString
		}
 
apFlowMgrExtDOSAttackIndex OBJECT-TYPE
	SYNTAX  INTEGER
	MAX-ACCESS  read-only
	STATUS  current
	DESCRIPTION
		"This is the index for the DOS event."
    ::= { apFlowMgrExtDOSAttackEntry 1 } 

apFlowMgrExtDOSAttackSrcAddress OBJECT-TYPE
    SYNTAX IpAddress
	MAX-ACCESS  read-only
	STATUS  current
	DESCRIPTION
		"This is the source ip address for this
         DOS attack event."
    ::= { apFlowMgrExtDOSAttackEntry 2 } 

apFlowMgrExtDOSAttackDestAddress OBJECT-TYPE
    SYNTAX IpAddress
	MAX-ACCESS  read-only
	STATUS  current
	DESCRIPTION
		"This is the destination ip address for this
         DOS attack event."
    ::= { apFlowMgrExtDOSAttackEntry 3 } 

apFlowMgrExtDOSAttackFirstEvent OBJECT-TYPE
    SYNTAX DisplayString
	MAX-ACCESS  read-only
	STATUS  current
	DESCRIPTION
		"This is the first time this DOS attack occurred."
    ::= { apFlowMgrExtDOSAttackEntry 4 } 


apFlowMgrExtDOSAttackLastEvent OBJECT-TYPE
    SYNTAX DisplayString
	MAX-ACCESS  read-only
	STATUS  current
	DESCRIPTION
		"This is the last time this DOS attack occurred."
    ::= { apFlowMgrExtDOSAttackEntry 5 } 

apFlowMgrExtDOSAttackEventCount OBJECT-TYPE
    SYNTAX Integer32
	MAX-ACCESS  read-only
	STATUS  current
	DESCRIPTION
		"This is the number of times this DOS attack
         had occurred."
    ::= { apFlowMgrExtDOSAttackEntry 6 } 

apFlowMgrExtDOSAttackEventType OBJECT-TYPE
    SYNTAX INTEGER {
             syn(1),
             land(2),
             zeroport(3),
             illegalsrc(4),
             pingofdeath(5),
             smurf(6),
             illegaldst(7)
           }
	MAX-ACCESS  read-only
	STATUS  current
	DESCRIPTION
		"This is the type of DOS attack which has occurred."
    ::= { apFlowMgrExtDOSAttackEntry 7 } 

apFlowMgrExtDOSAttackEventString  OBJECT-TYPE
    SYNTAX DisplayString( SIZE( 0..16 ) )
	MAX-ACCESS  read-only
	STATUS  current
	DESCRIPTION
		"This is the ascii text for the type of DOS attack 
         which has occurred."
    ::= { apFlowMgrExtDOSAttackEntry 8 } 

-- ********************** apFlowMgrExtDOSAttackEntry END ********************

-- ********************** apFlowMgrDos Traps BEGIN ************************

apFlowMgrExtDosSynTrap TRAP-TYPE
	ENTERPRISE flowMgrExt
	DESCRIPTION
		"A trap is generated with the threshold is exceeded for a
		 SYN Denial of Service (DOS) attack."
	::= 1

apFlowMgrExtDosLandTrap TRAP-TYPE
	ENTERPRISE flowMgrExt
	DESCRIPTION
		"A trap is generated with the threshold is exceeded for a
		 LAND Denial of Service (DOS) attack."
	::= 2

apFlowMgrExtDosIllegalTrap TRAP-TYPE
	ENTERPRISE flowMgrExt
	DESCRIPTION
		"A trap is generated with the threshold is exceeded for a
		 Illegal Packet format Denial of Service (DOS) attack."
	::= 3

apFlowMgrExtDosPingTrap TRAP-TYPE
	ENTERPRISE flowMgrExt
	DESCRIPTION
		"A trap is generated with the threshold is exceeded for a
		 Ping of Death Denial of Service (DOS) attack."
	::= 4

apFlowMgrExtDosSmurfTrap TRAP-TYPE
	ENTERPRISE flowMgrExt
	DESCRIPTION
		"A trap is generated with the threshold is exceeded for a
		 Smurf Denial of Service (DOS) attack."
	::= 5

END
