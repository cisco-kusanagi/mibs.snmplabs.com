-- 
-- Copyright 1999 by Fore Systems, Inc. 
-- Converted to SMIv2 rfc 2578,2579,2580 - STD 58
--
-- Copyright 1999 by Fore Systems, Inc.

Fore-SSM-MIB DEFINITIONS ::= BEGIN

IMPORTS
	OBJECT-TYPE, MODULE-IDENTITY,
	NOTIFICATION-TYPE		FROM SNMPv2-SMI
	DisplayString			FROM SNMPv2-TC
	syncStatusMsgGroup		FROM Fore-Switch-MIB;


sysStatusMsgModule            MODULE-IDENTITY
          LAST-UPDATED         "9912090000Z"
          ORGANIZATION         "FORE"
          CONTACT-INFO         
               "      Postal:   FORE Systems Inc.
                                1000 FORE Drive
                                Warrendale, PA 15086-7502
                       Tel:     +1 724 742 6900
                       Email:   nm_mibs@fore.com
                       Web:     http://www.fore.com"
          DESCRIPTION
	      "Synchronization Status Message Module"
    ::= { syncStatusMsgGroup 4 }	

SyncStatusMsgType ::= INTEGER	
	{  
	   prs(1),
	   prc(2),
	   stu(3),
	   st2(4),
	   tncssua(5),
	   st3e(8),
	   ssub(9),
	   st3(10),
	   sec(11),
	   smc(12),
	   st4(13),
	   res(15),
	   dus(16),
	   invalid(100),
	   none(101)
	}
--
-- Synchronization Status Message(SSM) Interface table definition
--
syncStatusMsgTable OBJECT-TYPE
	SYNTAX	SEQUENCE OF SyncStatusMsgEntry
	MAX-ACCESS	not-accessible
	STATUS	current
	DESCRIPTION
		"A table containing Synchronization Status Message
	         configuration and status."
	::= { syncStatusMsgGroup 1 }

syncStatusMsgEntry OBJECT-TYPE
	SYNTAX	SyncStatusMsgEntry
	MAX-ACCESS	not-accessible
	STATUS	current
	DESCRIPTION
		"A table entry containing Synchronization Status
		 Message configuration and status."
	INDEX	{ IMPLIED syncStatusMsgInterface }
	::= { syncStatusMsgTable 1 }

SyncStatusMsgEntry ::=
	SEQUENCE {
		syncStatusMsgInterface		DisplayString,
		syncStatusMsgRxMessage		SyncStatusMsgType,	
		syncStatusMsgTxMessage		SyncStatusMsgType,
		syncStatusMsgForceRxSsm		SyncStatusMsgType,
		syncStatusMsgForceDus		INTEGER,
		syncStatusMsgPrevRxMessage	SyncStatusMsgType
	}
	
syncStatusMsgInterface OBJECT-TYPE
	SYNTAX	DisplayString (SIZE(1..255))
	MAX-ACCESS	not-accessible
	STATUS	current
	DESCRIPTION
		"Name of this SSM Interface."
	::= { syncStatusMsgEntry 1 }

syncStatusMsgRxMessage OBJECT-TYPE
	SYNTAX	SyncStatusMsgType
	MAX-ACCESS	read-only
	STATUS	current
	DESCRIPTION
		"Synchronization Status Message currently being received 
		 on this interface. If syncStatusMsgForceRxSsm is set to 
		 any value other than SyncStatusMsgType::none, then 
		 syncStatusMsgRxMessage will reflect that forced value."
	::= { syncStatusMsgEntry 2 }

syncStatusMsgTxMessage OBJECT-TYPE
	SYNTAX	SyncStatusMsgType
	MAX-ACCESS	read-only
	STATUS	current
	DESCRIPTION
		"Synchronization Status Message being transmitted on
		 this interface. If syncStatusMsgForceDus is set to 
		 enabled, then syncStatusMsgTxMessage will be Don't
		 Use for Synchronization(DUS)."
	::= { syncStatusMsgEntry 3 }

syncStatusMsgForceRxSsm OBJECT-TYPE
	SYNTAX SyncStatusMsgType
	MAX-ACCESS read-write
	STATUS current
	DESCRIPTION
		"This variable is used to force a particual
		 Synchronization Status Message as the receive
		 SSM on this interface. Forcing a receive SSM will
		 cause the interface to ignore the actual SSM being
		 received (i.e., changes to S1 byte.) Setting this 
		 variable to SyncStatusMsgType::none will clear 
		 any forced SSM."
	::= { syncStatusMsgEntry 4 }
	
syncStatusMsgForceDus OBJECT-TYPE
	SYNTAX	INTEGER {
		  enabled(1),
		  disabled(2)
		}
	MAX-ACCESS	read-write
	STATUS	current
	DESCRIPTION 
		"Indicates if Don't Use for Synchronization (DUS) is
	         being forced on the transmit side of this interface.
		 If this variable is set to enabled, then the switch will 
		 generate DUS message on the transmit side of the
  		 interface. Otherwise, the switch will transmit an
	         appropriate value according to the SSM protocol."
	::= { syncStatusMsgEntry 5 }

syncStatusMsgPrevRxMessage OBJECT-TYPE
	SYNTAX	SyncStatusMsgType
	MAX-ACCESS	accessible-for-notify
	STATUS	current
	DESCRIPTION
		"Synchronization Status Message previously received on
		 this interface. This variable is used by syncStatusMsgChanged
		 trap."
	::= { syncStatusMsgEntry 6 }

---
--- Group Variables
---

syncStatusMsgAutomaticRefSwitching OBJECT-TYPE
	SYNTAX	INTEGER {
		   enabled(1),
		   disabled(2)
		}
	MAX-ACCESS	read-write
	STATUS  current
	DESCRIPTION 
		"Indicates whether or not changes in SSM will cause 
	         automatic reference switching. If the variable is 
		 set to enabled, the switch will process and react to 
		 changes in SSM. If the variable is set to disabled, 
		 changes in SSM will not cause timing reference
	  	 switching. Default value is disabled."
	::= { syncStatusMsgGroup 2 }

syncStatusMsgSdhOption OBJECT-TYPE
	SYNTAX	INTEGER {
		  optionI(1),
		  optionII(2)
		}
	MAX-ACCESS  read-write
	STATUS	current
	DESCRIPTION 
		"Indicates the SSM Option being used on SDH/E1
		 interfaces. Default value is optionII."
	::= { syncStatusMsgGroup 3 }


-- SSM Trap definition

syncStatusMsgChanged NOTIFICATION-TYPE
	OBJECTS { syncStatusMsgPrevRxMessage, syncStatusMsgRxMessage }
	STATUS      current
	DESCRIPTION
		"This trap is generated whenever a configured timing 
		 reference's receive SSM changes. It indicates the 
		 previous SSM received and the new SSM being received."
        ::= { syncStatusMsgGroup 0 1 }

END
