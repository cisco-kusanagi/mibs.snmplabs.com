-- 1994 General DataComm Inc., Inc. All Rights Reserved.
--
-- Reproduction of this document is authorized on condition that the
-- foregoing copyright notice is included. This General DataComm, GDC,
-- SNMP Management Information Base Specification embodies GDC's
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use, operation, condition, or
-- performance of the Specification.

-- Revision History
-- Version   Date	Name		Description
--
-- 1.00      22-May-95  N. Marino	Initial Revision
--
DDS-MIB DEFINITIONS ::= BEGIN

IMPORTS

	OBJECT-TYPE			FROM RFC-1212
	DisplayString			FROM RFC1213-MIB
	SCinstance			FROM GDCMACRO-MIB
        gdc                             FROM GDCCMN-MIB;

dsu		OBJECT IDENTIFIER ::= { gdc 8 }
dds 		OBJECT IDENTIFIER ::= { dsu 1 }

-- This MIB module uses the extended OBJECT-TYPE macro as
-- defined in RFC 1212.

-- The implementation of all groups is mandatory for all DDS products.

-- Note:  All rows in all tables defined within this MIB module are
-- virtual.  They can neither be created or deleted by management
-- operations.

-- The Version Group. This group identifies the version information
-- for the MIB.
--
ddsMIBversion OBJECT-TYPE
    SYNTAX DisplayString (SIZE (5))
    ACCESS read-only
    STATUS mandatory
    DESCRIPTION
    	"Identifies the version of the MIB. The format
	 of the version is x.yzT, where 'x' identifies
	 the major revision number, 'y'identifies the
	 minor revision number, 'z' identifies the
    	 typographical revision, and T identifies the
	 test revision.  Acceptable values for the 
	 individual revision components are
    	 as follows

    		x: 1 - 9
    		y: 0 - 9
    		z: 0 - 9
    		T: A - Z

    	Upon formal release, no designation for the test
	revision will be present."
    ::= { dds 1 }

-- The GDC DDS Group.  This group contains objects that support the
-- specific management requirements for products that support a GDC
-- DDS functionality.  The group contains tables for Line
-- Configuration Management, DTE Configuration Management, DDS Line
-- Diagnostics, and DDS DTE Diagnostics.

-- The DDS Line Configuration Table

ddsLineCfgTable OBJECT-TYPE
    SYNTAX SEQUENCE OF DdsLineCfgEntry
    ACCESS not-accessible
    STATUS mandatory
    DESCRIPTION
    	"The GDC DDS Line Configuration table.  Information
	 in the entries	of this table defines the
	 configuration of DDS Line."
    ::= { dds 2 }

ddsLineCfgEntry OBJECT-TYPE
    SYNTAX DdsLineCfgEntry
    ACCESS not-accessible
    STATUS mandatory
    DESCRIPTION
    	"The GDC DDS Line Configuration Table Entry.
	 The information in  this entry defines the
	 configuration for the Line of the associated
	 DDS equipment."
    INDEX { ddsLineCfgIndex }
    ::= { ddsLineCfgTable 1 }

DdsLineCfgEntry ::=
SEQUENCE {
    	ddsLineCfgIndex SCinstance,
    	ddsLineType INTEGER,
    	ddsAutoDataRateDetect INTEGER,
	ddsDataRate INTEGER,
    	ddsTxClockSource INTEGER,
	ddsZeroEncodingCfg INTEGER,
	ddsDefaultConfig INTEGER
    }

ddsLineCfgIndex OBJECT-TYPE
    SYNTAX SCinstance
    ACCESS read-only
    STATUS mandatory
    DESCRIPTION
    	"The index value that uniquely identifies the
	 line interface to which this entry is applicable.
	 This has the form of a SCinstance that
	 defines the slot, line, drop, and 
	sub-identifier, which in this case is the DDS Line."
    ::= { ddsLineCfgEntry 1 }

ddsLineType OBJECT-TYPE
    SYNTAX INTEGER {
    	dds1(1),			-- Standard DDS line
    	ddsSc(2),			-- DDS/SC line
    	clearChannel(3),		-- 64K Clear Channel line
    	auto(4)				-- automatic mode determination
    }
    ACCESS read-write
    STATUS mandatory
    DESCRIPTION
    	"Identifies the type of line.
    	The value dds1(1) defines the line type
	as a conventional DDS. The value ddsSc(2)
	defines the line type as a DDS line with
	secondary channel. The value clearChannel(3)
	indicates that the line type is 64K Clear
	Channel. The value auto(4) indicates that
	automatic line detection is in progress.
	Once the line type has been detected,
	 the object reports enumeration (1),(2), or (3)."
    ::= { ddsLineCfgEntry 2 }

ddsAutoDataRateDetect OBJECT-TYPE
    SYNTAX INTEGER {
    	async2400(1),	-- Standard DDS and DDS/SC Rate of 2400 Asynchronous 
    	sync2400(2),	-- Standard DDS and DDS/SC Rate of 2400 Synchronous 
    	async4800(3),	-- Standard DDS and DDS/SC Rate of 4800 Asynchronous
    	sync4800(4),	-- Standard DDS and DDS/SC Rate of 4800 Synchronous
    	async9600(5),	-- Standard DDS and DDS/SC Rate of 9600 Asynchronous
    	sync9600(6),	-- Standard DDS and DDS/SC Rate of 9600 Synchronous
    	async19200(7),	-- Standard DDS and DDS/SC Rate of 19200 Asynchronous
    	sync19200(8),	-- Standard DDS and DDS/SC Rate of 19200 Synchronous
    	sync56000(9),	-- Standard DDS and DDS/SC Rate of 56000 Synchronous
	sync64000(10),	-- Clear Channel Rate of 64000 Synchronous
	autoAsync(11),  -- Automatic Synchronous rate determination
	autoSync(12)    -- Automatic Asynchronous rate determination
    }
    ACCESS read-only
    STATUS mandatory	
    DESCRIPTION
	"The value autoAsync(11) and autoSync(12)
	 indicates that automatic data rate
	 detection for async or sync communications
         is in progress.  Once the data rate has
	 been detected, this object reports the
	 circuit data rate."
   ::= { ddsLineCfgEntry 3 }

ddsDataRate OBJECT-TYPE
    SYNTAX INTEGER {
    	async2400(1),	-- Standard DDS and DDS/SC Rate of 2400 Asynchronous 
    	sync2400(2),	-- Standard DDS and DDS/SC Rate of 2400 Synchronous 
    	async4800(3),	-- Standard DDS and DDS/SC Rate of 4800 Asynchronous
    	sync4800(4),	-- Standard DDS and DDS/SC Rate of 4800 Synchronous
    	async9600(5),	-- Standard DDS and DDS/SC Rate of 9600 Asynchronous
    	sync9600(6),	-- Standard DDS and DDS/SC Rate of 9600 Synchronous
    	async19200(7),	-- Standard DDS and DDS/SC Rate of 19200 Asynchronous
    	sync19200(8),	-- Standard DDS and DDS/SC Rate of 19200 Synchronous
    	sync56000(9),	-- Standard DDS and DDS/SC Rate of 56000 Synchronous
	sync64000(10),	-- Clear Channel Rate of 64000 Synchronous
	autoAsync(11),  -- Automatic Synchronous rate determination
	autoSync(12)    -- Automatic Asynchronous rate determination
    }
    ACCESS read-write
    STATUS mandatory
    DESCRIPTION
        "The DSU data rate option. 
	This object is used to choose the
	operational data rate of the DSU.  The
	two choices autoAsync(11) and autoSync(12)
	allow the DSU to automatically determine
	the circuit speed and set the data rate
	accordingly. 
	
	Similarities in DDS line coding of 56k
	DDS/SC and 64k Clear Channel require the
	user to select sync64000(10) implicitly if 64kbps
	data rate is required."
    ::= { ddsLineCfgEntry 4 }

ddsTxClockSource OBJECT-TYPE
    SYNTAX INTEGER {
    	receive(1),	-- Receive Clock, is derived from the Line
    	internal(2),	-- Internal Clock, generated interally in the Data Set
    	external(3)	-- External Clock, is derived from the DTE
    }
    ACCESS read-write
    STATUS mandatory
    DESCRIPTION
    	"The DSU transmit clock source option.
	 This is the selection for the transmitter
	 timing clock source.  If connecting to
	 a DDS circuit the value of receive(1)
	 must be selected."
    ::= { ddsLineCfgEntry 5 }

ddsZeroEncodingCfg OBJECT-TYPE
    SYNTAX INTEGER {
       	enable(1),
       	disable(2)
    }
    ACCESS read-write
    STATUS mandatory
    DESCRIPTION
        "The DSU zero encoding option.
	This option, for point to point 56k
	DDS secondary channel circuits, allows
	the DTE equipment to transmit all '0'
	octets without violating the ones density
	requirements of DDS.  This option is a GDC
	only feature and must be set to disable
	when coexisting with DSU equipment from
	other providers.  Both local and remote DSU's
	must be set to the same value.  The zero
	encoding feature is not applicable for
	any of the other data rates or line types."
    ::= { ddsLineCfgEntry 6 }

ddsDefaultConfig OBJECT-TYPE
    SYNTAX INTEGER {
	noChange(1),
	defaultCfg(2)
    }
    ACCESS read-write
    STATUS mandatory
    DESCRIPTION
	"The DSU default config option.
	 When the value defaultCfg(2), is selected,
	 the memory of the dataset will be erased,
	 and the DSU configuration will be returned
	 to factory defaults."
    ::= { ddsLineCfgEntry 7 }

--
-- DTE Port Configuration Table.
--

ddsDteCfgTable OBJECT-TYPE
    SYNTAX SEQUENCE OF DdsDteCfgEntry
    ACCESS not-accessible
    STATUS mandatory
    DESCRIPTION
    	"The DDS DTE Configuration Table.
	 Entries in this table pertain to the DTE
	 interface, regardless of the operating
	 mode (sync/async)."
    ::= { dds 3 }

ddsDteCfgEntry OBJECT-TYPE
    SYNTAX DdsDteCfgEntry
    ACCESS not-accessible
    STATUS mandatory
    DESCRIPTION
    	"The GDC DTE Configuration Table Entry.
	 The information in this entry defines
	 the configuration for the associated DTE."
    INDEX { ddsDteCfgIndex }
    ::= { ddsDteCfgTable 1 }

DdsDteCfgEntry ::=
SEQUENCE {
    	ddsDteCfgIndex SCinstance,
	ddsDteExtBuffClk INTEGER,
    	ddsDteCfgTxCarrier INTEGER,
    	ddsDteCfgRxCarrier INTEGER,
    	ddsDteCfgCtsDelay INTEGER,
    	ddsDteCfgLocalDSR INTEGER,
    	ddsDteCfgAnaloopDSR INTEGER,
    	ddsDteCfgAasStatus INTEGER,
    	ddsDteCfgAasTimer INTEGER,
    	ddsDteCfgCircuitAssurance INTEGER,
    	ddsDteCfgSystemStatus INTEGER,
    	ddsDteCfgTermaloop INTEGER
    }

ddsDteCfgIndex OBJECT-TYPE
    SYNTAX SCinstance
    ACCESS read-only
    STATUS mandatory
    DESCRIPTION
    	"An entry in the GDC DDS DTE Configuration
	 Table."
    ::= { ddsDteCfgEntry 1 }

ddsDteExtBuffClk OBJECT-TYPE
    SYNTAX INTEGER {
    	internal(1),	
    	external(2)
    }
    ACCESS read-write
    STATUS mandatory
    DESCRIPTION
    	"The DSU transmit buffer option.
	 An optional elastic transmit buffer is
	 inserted into the data path when a value
	 of external(2) is selected. This elastic
	 buffer maintains network synchronization
	 when an external frequency locked clock
	 source is driven into the external
	 transmit clock input on the DTE interface.
	 Opposing phase relationships between the
	 external transmit clock and network
	 clock are compensated for by this buffer.
	 No buffering is performed when this object
	 is internal(1).  If the transmitter
	 timing is set to external, this object
	 must be set to external(2)."
    ::= { ddsDteCfgEntry 2 }

ddsDteCfgTxCarrier OBJECT-TYPE
    SYNTAX INTEGER {
    	constant(1),
    	switched(2)
    }
    ACCESS read-write
    STATUS mandatory
    DESCRIPTION
    	"The Transmit Carrier option.
	This is feature allows the DTE equipment
	to directly control the transmitter carrier
	via signals on the RTS circuit.  Typically,
	it is set to switched(2) in remote DSU
	multidrop applications. The Transmit Carrier
	constant(1) is used in point-to-point applications
	and also in master multipoint applications.
	When the value of the ddsDataRate is sync64000(10),
	the value of this object is constant(1).
	When this object is constant(1), RTS and CTS
	are forced on internally."
    ::= { ddsDteCfgEntry 3 }

ddsDteCfgRxCarrier OBJECT-TYPE
    SYNTAX INTEGER {
    	constant(1),
    	switched(2)
    }
    ACCESS read-write
    STATUS mandatory
    DESCRIPTION
    	"The Receive Carrier option.
	This option controls the operation of DCD.
	It is set to constant for multipoint remote
	and point to point applications.  Switched(2) is
	used for master multipoint configurations.
	When the value of the ddsDataRate is sync64000(10),
	the receive carrier option is forced
	to constant(1) with DCD forced On."
    ::= { ddsDteCfgEntry 4 }

ddsDteCfgCtsDelay OBJECT-TYPE
    SYNTAX INTEGER {
    	ctsOn(1),
    	ctsFixed3Char(2),
    	cts0mSec(3),
    	cts30mSec(4),
    	cts60mSec(5),
    	cts90mSec(6)
    }
    ACCESS read-write
    STATUS mandatory
    DESCRIPTION
    	"The CTS delay option.
	Cts delay option of ctsOn(1) forces both
	RTS and CTS On regardless of the state of the
	attached business equipment.  The CTS delay
	option provides a variable delay between
	RTS and CTS on transitions. The delays of 
	0msec, 3 character, 30msec, 60msec, and 90msec
	are selectable."
    ::= { ddsDteCfgEntry 5 }
    
ddsDteCfgLocalDSR OBJECT-TYPE
    SYNTAX INTEGER {
        followsDTR(1),
	forcedOn(2)
    }
    ACCESS read-write
    STATUS mandatory
    DESCRIPTION
    	"The DSR option.
	This option controls the operation of DSR.
	When forceOn(2) is selected, DSR is normally on,
	if set for followsDTR(1) then DSR is on only
	when DTR is on."
    ::= { ddsDteCfgEntry 6 }
    	
ddsDteCfgAnaloopDSR OBJECT-TYPE
    SYNTAX INTEGER {
    	off(1),
    	normal(2)
    }
    ACCESS read-write
    STATUS mandatory
    DESCRIPTION
    	"The DSR in Line Loopback (Analoop) option.
	This option controls DSR during a Line
	Loopback test. When Line Loopback is active
	and the ddsDteCfgAnaloopDSR object is off(1),
	a DSR off indication is output to the DTE interface.
	When normal(2), the state of DSR responds in
	accodance with the ddsDteCfgLocalDSR object."
    ::= { ddsDteCfgEntry 7 }

ddsDteCfgAasStatus OBJECT-TYPE
    SYNTAX INTEGER {
        disable(1),
	enable(2)
    }
    ACCESS read-write
    STATUS mandatory
    DESCRIPTION
    	"The Auto-anti Streaming option.
	A value of enable(1) means that the primary channel
	DSU transmitter is forced OFF (idle) if the business
	equipment's (DTE) RTS lead remains on for more than 
	the value of the ddsDteCfgAasTimer. Streaming is
	cleared when the DTE's RTS interface lead turns OFF
	and remains OFF for at least 500msec. "
    ::= { ddsDteCfgEntry 8 }

ddsDteCfgAasTimer OBJECT-TYPE
    SYNTAX INTEGER {
    	sec5(1),
    	sec10(2),
    	sec30(3),
    	sec45(4)
    }
    ACCESS read-write
    STATUS mandatory
    DESCRIPTION
    	"The Auto Anti-Streaming Timer monitor RTS.
	If RTS remains On for more then the selected
	time and ddsDteCfgAasStatus is selected for 
	enable(1), the DSU forces Off its primary channel
	transmitter and turns off CTS."
    ::= { ddsDteCfgEntry 9 }

ddsDteCfgCircuitAssurance OBJECT-TYPE
    SYNTAX INTEGER {
    	disable(1),
        enable(2)
    }
    ACCESS read-write
    STATUS mandatory
    DESCRIPTION
    	"The Circuit Assurance option.
	 The enable(2) configures the DSU to clamp
	 CTS upon receiving the following Network codes:

	 1. IDLE(no DCD)
         2. Out of Service Code (OOS)
	 3. Abnormal Station Code (ASC)
	 4. No Signal(not a network code)
	 5. other inactive channel codes (ICC)

	When the value of this object is disable(1)
	no action occurs for any of the above
	network	conditions."
    ::= { ddsDteCfgEntry 10 }

ddsDteCfgSystemStatus OBJECT-TYPE
    SYNTAX INTEGER {
       	disable(1),
        enable(2)
    }
    ACCESS read-write
    STATUS mandatory
    DESCRIPTION
    	"The System Status option enable(2)
	configures the DSU to clamp DSR upon
	receiving the following Network codes:

         1. Out of Service Code (OOS)
	 2. Abnormal Station Code (ASC)
	 3. No Signal(not a network code)
	 4. other inactive channel codes (ICC)

	When the value of this object is disable(1)
	no action occurs for any of the above
	network conditions." 
    ::= { ddsDteCfgEntry 11 }

ddsDteCfgTermaloop OBJECT-TYPE
    SYNTAX INTEGER {
    	enable(1),
    	disable(2)
    }
    ACCESS read-write
    STATUS mandatory
    DESCRIPTION
	"The Loopback Termination Mode.
	 The enable(1) object stops the DSU from
	 looping the DDS network interface while a
	 local loopback is in progress.
	 When the value of this object is disable(2)
	 the DDS network service is looped back to
	 itself during a local loopback test."
    ::= { ddsDteCfgEntry 12 }

--
-- Async DTE Port Configuration
--

ddsDteAsyncCfgTable OBJECT-TYPE
    SYNTAX SEQUENCE OF DdsDteAsyncCfgEntry
    ACCESS not-accessible
    STATUS mandatory
    DESCRIPTION
    	"The Asynchronous Configuration table.
	 Information in the entries of this table
	 define the configuration of the DTE
	 interface associated with the DDS device.
	 The entries in this table are applicable only
	 if the ddsDataRate object maintains
	 an asynchronous configuration. "
    ::= { dds 4 }

ddsDteAsyncCfgEntry OBJECT-TYPE
    SYNTAX DdsDteAsyncCfgEntry
    ACCESS not-accessible
    STATUS mandatory
    DESCRIPTION
    	"The Asynchronous Configuration Table Entry.
	 The information in this entry defines
	 the configuration of the DTE interface."
    INDEX { ddsDteAsyncCfgIndex }
    ::= { ddsDteAsyncCfgTable 1 }

DdsDteAsyncCfgEntry ::=
SEQUENCE {
    	ddsDteAsyncCfgIndex SCinstance,
    	ddsDteAsyncRateAdapt INTEGER,
    	ddsDteAsyncRxDelay INTEGER,
    	ddsDteAsyncTxEOTcfg INTEGER,
    	ddsDteAsyncRxEOTcfg INTEGER,
    	ddsDteAsyncOverSpeed INTEGER,
    	ddsDteAsyncCharacterSize INTEGER
    }

ddsDteAsyncCfgIndex OBJECT-TYPE
    SYNTAX SCinstance
    ACCESS read-only
    STATUS mandatory
    DESCRIPTION
    	"The index value which uniquely
	identifies the DTE interface to which
	this entry is applicable. Values for
	this object have the form of an SCinstance
	which defines the slot, line, drop, and
	sub-identifier, which in this case is the
	DTE interface."
    ::= { ddsDteAsyncCfgEntry 1 }

ddsDteAsyncRateAdapt OBJECT-TYPE
    SYNTAX INTEGER {
    	none(1),
    	halfLineRate(2),		-- 1200 bps
	quarterLineRate(3),		-- 600 bps
    	from1800to2400LineRate(4)	-- rates between and including 
					-- 1800 to 2400 bps 
    }
    ACCESS read-write
    STATUS mandatory
    DESCRIPTION
    	"The Async rate adaption object.
	 The speed relationship between DDS circuit 
	 and DTE interface when configured for async
	 communication is defined here. The none(1)
	 value maintains a one to one speed relationship
	 between the DDS circuit and DTE interface.  A
	 value of halfLineRate(2) means that the DTE
	 speed is equal to one half the DDS circuit
	 rate.  A value of quarterLineRate(3) means
	 that only one fourth the DDS circuit rate
	 will be available at the DTE interface.
	 If the DTE speed required is 1800 bps,
	 then the provisioned DDS circuit must be
	 2400 DDS or DDS with secondary channel
	 and the enumeration (4) object specified."
    ::= { ddsDteAsyncCfgEntry 2 }

ddsDteAsyncRxDelay OBJECT-TYPE
    SYNTAX INTEGER {
    	short(1),
    	long(2)
    }
    ACCESS read-write
    STATUS mandatory
    DESCRIPTION
    	"When long(2) is selected, a 40 bit
	 buffer in the receive data path is inserted.
         This buffer is used to filter out EOT.
	 If ddsDteAsyncTxEOTcfg, and 
	 ddsDteAsyncRxEOTcfg are enabled,
	 the object long(2) is required.  The short(1)
	 enumeration may be used only if the EOT signal
	 scheme is not in use."
    ::= { ddsDteAsyncCfgEntry 3 }

ddsDteAsyncTxEOTcfg OBJECT-TYPE
    SYNTAX INTEGER {
    	enable(1),
    	disable(2)
    }
    ACCESS read-write
    STATUS mandatory
    DESCRIPTION
    	"The configuration of the Transmit End-of-Text.
	 The value enable(1) means that End-of-Text
	 (EOT) will be transmitted. The value disable(2)
	 inhibits EOT transmission. If enable(1),
	 the unit will insert EOT into the data stream
	 when it is finished."
    ::= { ddsDteAsyncCfgEntry 4 }
    
ddsDteAsyncRxEOTcfg OBJECT-TYPE
    SYNTAX INTEGER {
    	enable(1),
    	disable(2)
    }
    ACCESS read-write
    STATUS mandatory
    DESCRIPTION
    	"The configuration of the Receive End-of-Text.
	 The value enable(1) means that the unit will
	 expect End-of-Text (EOT) and remove it  from
	 the data stream. The value disable(2) means
	 that the unit should not monitor the data 
	 stream for EOT."
    ::= { ddsDteAsyncCfgEntry 5 }

ddsDteAsyncOverSpeed OBJECT-TYPE
    SYNTAX INTEGER {
    	overSpeed1(1),
    	overSpeed2point3(2)
    }
    ACCESS read-write
    STATUS mandatory
    DESCRIPTION
    	"This option is used to determine the amount
	 of asynchronous overspeed the DSU tolerates.
	 The overSpeed1 indicates that the DSU will
	 accept incomming async data that is up to
	 1% faster than the configured data rate. The
	 overSpeed2point3 will allow up to 2.3% of
	 DTE overspeed."
    ::= { ddsDteAsyncCfgEntry 6 }

ddsDteAsyncCharacterSize OBJECT-TYPE
    SYNTAX INTEGER {
    	bits11(1),
    	bits10(2),
    	bits9(3),
    	bits8(4)
    }
    ACCESS read-write
    STATUS mandatory
    DESCRIPTION
    	"This option selects the Asynchronous word size.
	The available settings are:

	1)  8 bits/character.
	2)  9 bits/character.
	3) 10 bits/character.
	4) 11 bits/character.

	The character includes start and stop bits."
    ::= { ddsDteAsyncCfgEntry 7 }


ddsDteStatusTable OBJECT-TYPE
    SYNTAX SEQUENCE OF DdsDteStatusEntry
    ACCESS not-accessible
    STATUS mandatory
    DESCRIPTION
    	"The DDS DTE Configuration Table.
	 This entry pertains to the DTE interface."
    ::= { dds 6 }

ddsDteStatusEntry OBJECT-TYPE
    SYNTAX DdsDteStatusEntry
    ACCESS not-accessible
    STATUS mandatory
    DESCRIPTION
    	"The GDC DTE Configuration Table Entry. This entry
	defines the configuration for the associated DTE."
    INDEX { ddsDteStatusIndex }
    ::= { ddsDteStatusTable 1 }

DdsDteStatusEntry ::=
SEQUENCE {
    	ddsDteStatusIndex SCinstance,
	ddsDteStatus OCTET STRING
    }

ddsDteStatusIndex OBJECT-TYPE
    SYNTAX SCinstance
    ACCESS read-only
    STATUS mandatory
    DESCRIPTION
    	"An entry in the GDC DDS DTE Configuration Table."
    ::= { ddsDteStatusEntry 1 }

ddsDteStatus OBJECT-TYPE
        SYNTAX  OCTET STRING (SIZE(4))
        ACCESS  read-only
        STATUS  mandatory
	DESCRIPTION
        "Returns a bitwise snapshot of the DTE signals.
        Octet 1 bit 7 - not used
                bit 6 - CTS	(1:ON; 0:OFF)
		bit 5 - RTS	(1:ON; 0:OFF)
                bit 4 - DTR 	(1:ON; 0:OFF)
                bit 3 - DSR	(1:ON; 0:OFF)
                bit 2 - NO SIGNAL(NS)	(1:ON; 0:OFF)
                bit 1 - DCD	(1:ON; 0:OFF)
                bit 0 - DTP	(1:ON; 0:OFF)

        Octet 2 bit 7 - not used
                bit 6 - DSP	(1:ON; 0:OFF)
		bit 5 - DCD	(1:Transitions 0:OFF)
                bit 4 - RTS	(1:Transitions 0:OFF)
                bit 3 - CTS	(1:Transitions 0:OFF)
                bit 2 - RXD	(1:Transitions 0:OFF)
                bit 1 - TXC External (1:Trans  0:OFF)
                bit 0 - TXD	(1:Transitions 0:OFF)

        Octet 3 bit 7 - not used
                bit 6 - Internal Test Pattern	(1:ON; 0:OFF)
		bit 5 - \			(100:STC loop)
                bit 4 -  > Test Modes		(010:DataLoop)
                bit 3 - /			(001:Analoop)
                bit 2 - Dataset Inhibit 	(1:active)
                bit 1 - Dataset Streaming Inhibit (1:active)
                bit 0 - Auto Anti-Streaming 	(1:Enabled)
	
        Octet 4 bit 7 - not used
                bit 6 - Diagnostic RTS		(1:ON; 0:OFF)
		bit 5 - Test Inhibit		(1:active )
                bit 4 - Inactive Channel Code 	(1:ON; 0:OFF)
                bit 3 - LPDA Active		(1:ON; 0:OFF)
                bit 2 - DBU Active		(1:ON; 0:OFF)
                bit 1 - Front Panel Test Switch (1:Enabled )
                bit 0 - Front Panel Test Switch Active (1:ON ) "	
    ::= { ddsDteStatusEntry 2 }

END
