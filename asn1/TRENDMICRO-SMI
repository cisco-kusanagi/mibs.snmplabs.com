--
-- Trend Micro Inc. root SMI
--
-- Copyright (C) 1995, 2003 by Trend Micro Inc.
-- All rights reserved.
--
-- Comments to: <webmaster@trendmicro.com>
-- Web URL: http://www.trendmicro.com/
--

     TRENDMICRO-SMI DEFINITIONS ::= BEGIN

     IMPORTS
        enterprises, MODULE-IDENTITY
        	FROM SNMPv2-SMI;

     trendmicro MODULE-IDENTITY
         LAST-UPDATED "0310101040Z"
         ORGANIZATION "Trend Micro Inc."
         CONTACT-INFO
              "Trend Micro Inc.
               10101 N. De Anza Blvd,
               Cupertino, CA - 95014, USA.

               Phone:  + 1 (800) 228 - 5651
               Web:    http://www.trendmicro.com/
               E-Mail: webmaster@trendmicro.com"

         DESCRIPTION
               "Trend Micro Inc.  root MIB module."

       ::= { enterprises 6101 }

     tmNVW OBJECT IDENTIFIER ::= { trendmicro 2500 }

END
