--******************************************************************
--*
--*         Copyright (c) 1993, 1999 by 3Com Corporation
--*                    All Rights Reserved
--*
--*    $Revision:   7.1  $
--*    $Date:   Aug 06 1999 17:30:04  $
--*
--*    3COM IDT1 MIB
--*
--******************************************************************


IDT1-MIB DEFINITIONS ::= BEGIN

IMPORTS
   enterprises,
   experimental,
   IpAddress,
   TimeTicks,
   Gauge,
   Counter
      FROM RFC1155-SMI
   DisplayString
      FROM RFC1213-MIB
   OBJECT-TYPE
      FROM RFC-1212;


usr OBJECT IDENTIFIER ::= { enterprises 429 }

nas OBJECT IDENTIFIER ::= { usr 1 }

idt1 OBJECT IDENTIFIER ::= { nas 15 }

-- The T1-PRI ISDN Card Configuration Group.

idt1Cfg OBJECT IDENTIFIER ::= { idt1 1 }

idt1CfgTable OBJECT-TYPE
SYNTAX SEQUENCE OF Idt1CfgEntry
ACCESS not-accessible
STATUS mandatory
DESCRIPTION
"This table contains an entry for each of the manageable 
T1-PRI ISDN Cards in the chassis.  It contains objects that 
reflect the current configuration of parameters that affect 
the operation of all the entities that reside on the given 
card."
::= { idt1Cfg 1 }

idt1CfgEntry OBJECT-TYPE
SYNTAX Idt1CfgEntry
ACCESS not-accessible
STATUS mandatory
DESCRIPTION
"There is one Configuration table entry per T1-PRI ISDN Card 
in the chassis."
INDEX { idt1CfgIndex }
::= { idt1CfgTable 1 }

Idt1CfgEntry ::=
SEQUENCE {
idt1CfgIndex
    INTEGER,
idt1CfgAssgndISDNGateway
    INTEGER,
idt1CfgMdmCallsAllowedEna
    INTEGER,
idt1CfgMdmRoutingMethod
    INTEGER,
idt1CfgProjectSelectionR2
    INTEGER,
idt1CfgInfoMsgTimeOut
    INTEGER,
idt1CfgInbDNISLength
    INTEGER,
idt1CfgSelectCompanding
    INTEGER,
idt1CfgAniNumberEnable
    INTEGER,
idt1CfgNoBptyMethod
    INTEGER,
idt1CfgMaxISDNGwyCalls
    INTEGER
}

idt1CfgIndex OBJECT-TYPE
SYNTAX INTEGER
ACCESS read-only
STATUS mandatory
DESCRIPTION
"A unique value for each card in the chassis.  The value of 
idt1CfgIndex matches the value of the index for the 
corresponding card entity in the entity table of the 
chassis MIB."
::= { idt1CfgEntry 1 }

idt1CfgAssgndISDNGateway OBJECT-TYPE
SYNTAX INTEGER (0..16)
ACCESS read-write
STATUS mandatory
DESCRIPTION
"Identifies the NAS chassis slot of the Gateway Card 
assigned to this T1-PRI ISDN card. Range 0-16. 
Default=0(none)."
::= { idt1CfgEntry 2 }

idt1CfgMdmCallsAllowedEna OBJECT-TYPE
SYNTAX INTEGER{
  enable(1),
  disable(2)
}
ACCESS read-write
STATUS mandatory
DESCRIPTION
"Indicates if modem calls are disabled/enabled for this 
T1-PRI ISDN Card. Default = enable(1)."
::= { idt1CfgEntry 3 }

idt1CfgMdmRoutingMethod OBJECT-TYPE
SYNTAX INTEGER{
  notSupported(1),
  roundRobin(2),
  firstAvailable(3),
  fixedAssignment(4)
}
ACCESS read-write
STATUS mandatory
DESCRIPTION
"Defines the mechanism used for modem call routing for this 
T1-PRI ISDN Card.
Default = roundRobin(2)."
::= { idt1CfgEntry 4 }

idt1CfgProjectSelectionR2 OBJECT-TYPE
SYNTAX INTEGER{
  q421(1),
  r2(2),
  r2Korea(3),
  p7(4),
  r2Malaysia(5),
  r2Brazil(6),
  r2Mexico(7),
  r2China(8),
  r2LME(9),
  r2Venezuela(10),
  notApplicable(255)
}
ACCESS read-write
STATUS mandatory
DESCRIPTION
"This object lets user select E1 CAS project options. 
Default = mfcBkR2(3)."
::= { idt1CfgEntry 5 }

idt1CfgInfoMsgTimeOut OBJECT-TYPE
SYNTAX INTEGER (0..255)
ACCESS read-write
STATUS mandatory
DESCRIPTION
"This object sets the time out delay in seconds between INFO 
messages. This parameter is effective if overlap rx mode is 
enabled. Default = 12 "
::= { idt1CfgEntry 6 }

idt1CfgInbDNISLength OBJECT-TYPE
SYNTAX INTEGER (1..15)
ACCESS read-write
STATUS mandatory
DESCRIPTION
"This objects sets the total number of digits expected in 
the inbound phone number. In the E1-PRI this only is 
effective when overlap rx mode is enabled. Default = 15"
::= { idt1CfgEntry 7 }

idt1CfgSelectCompanding OBJECT-TYPE
SYNTAX INTEGER{
  alaw(1),
  ulaw(2),
  useCountryCode(3)
}
ACCESS read-write
STATUS mandatory
DESCRIPTION
"Select companding (alaw or ulaw) for use with PCM encoded 
data. Default = alaw(1)."
::= { idt1CfgEntry 8 }

idt1CfgAniNumberEnable OBJECT-TYPE
SYNTAX INTEGER{
  enable(1),
  disable(2)
}
ACCESS read-write
STATUS mandatory
DESCRIPTION
"Allow the collection of A calling party phone number. This 
takes additional time, and is not allowed for all switches. 
Default = disable(2)."
::= { idt1CfgEntry 9 }

idt1CfgNoBptyMethod OBJECT-TYPE
SYNTAX INTEGER{
  analog(1),
  digital(2),
  unAllocatedNum(3)
}
ACCESS read-write
STATUS mandatory
DESCRIPTION
"This object sets the method for handling an incoming call 
when the B-party (Called Number) is not found within the 
<inPhoneNum> table."
::= { idt1CfgEntry 10 }

idt1CfgMaxISDNGwyCalls OBJECT-TYPE
SYNTAX INTEGER (0..255)
ACCESS read-write
STATUS mandatory
DESCRIPTION
"This object sets the maximum number of ISDN calls that can 
be terminated by the Gateway card.  Default = 0."
::= { idt1CfgEntry 11 }

-- The T1-PRI ISDN Card Call Routing Group.

idt1Cr OBJECT IDENTIFIER ::= { idt1 2 }

idt1CrTable OBJECT-TYPE
SYNTAX SEQUENCE OF Idt1CrEntry
ACCESS not-accessible
STATUS mandatory
DESCRIPTION
"This table contains an entry for each of the manageable 
T1-PRI ISDN Cards in the chassis.  It contains objects that 
reflect the current call routing configuration of the card."
::= { idt1Cr 1 }

idt1CrEntry OBJECT-TYPE
SYNTAX Idt1CrEntry
ACCESS not-accessible
STATUS mandatory
DESCRIPTION
"There is one Call Routing Table entry per T1-PRI ISDN Card 
in the chassis."
INDEX { idt1CrIndex, idt1CrPhNumIndex }
::= { idt1CrTable 1 }

Idt1CrEntry ::=
SEQUENCE {
idt1CrIndex
    INTEGER,
idt1CrPhNumIndex
    INTEGER,
idt1CrInboundPhNum
    DisplayString,
idt1CrInboundCallType
    INTEGER
}

idt1CrIndex OBJECT-TYPE
SYNTAX INTEGER
ACCESS read-only
STATUS mandatory
DESCRIPTION
"A unique value for each card in the chassis.  The value of 
idt1CrIndex matches the value of the index for the 
corresponding card's entry in the entity table of the 
chassis MIB."
::= { idt1CrEntry 1 }

idt1CrPhNumIndex OBJECT-TYPE
SYNTAX INTEGER
ACCESS read-only
STATUS mandatory
DESCRIPTION
"This object is the index for one of the 48 inbound call 
routing objects for this card."
::= { idt1CrEntry 2 }

idt1CrInboundPhNum OBJECT-TYPE
SYNTAX DisplayString (SIZE(0..36))
ACCESS read-write
STATUS mandatory
DESCRIPTION
"This is one of the 48 inbound call routing phone numbers."
::= { idt1CrEntry 3 }

idt1CrInboundCallType OBJECT-TYPE
SYNTAX INTEGER{
  analog(1),
  digital(2)
}
ACCESS read-write
STATUS mandatory
DESCRIPTION
"This is one of the 48 inbound call routing call types. 
Default = analog(1)."
::= { idt1CrEntry 4 }

-- The T1-PRI ISDN Reserved Resource Pool to DNIS Mapping table.

idt1Pl OBJECT IDENTIFIER ::= { idt1 3 }

idt1PlTable OBJECT-TYPE
SYNTAX SEQUENCE OF Idt1PlEntry
ACCESS not-accessible
STATUS mandatory
DESCRIPTION
"This table contains an entry for each of the manageable 
T1-PRI ISDN Cards in the chassis.  It contains objects that 
reflect the current reserved resource pool to DNIS mapping."
::= { idt1Pl 1 }

idt1PlEntry OBJECT-TYPE
SYNTAX Idt1PlEntry
ACCESS not-accessible
STATUS mandatory
DESCRIPTION
"There is one Reserved Resuorce Pool ID to DNIS Mapping 
Table entry per T1-PRI ISDN Card in the chassis."
INDEX { idt1PlIndex, idt1PlIDIndex }
::= { idt1PlTable 1 }

Idt1PlEntry ::=
SEQUENCE {
idt1PlIndex
    INTEGER,
idt1PlIDIndex
    INTEGER,
idt1PlDNIS
    DisplayString,
idt1PlType
    INTEGER
}

idt1PlIndex OBJECT-TYPE
SYNTAX INTEGER
ACCESS read-only
STATUS mandatory
DESCRIPTION
"A unique value for each card in the chassis.  The value of 
idt1PlIndex matches the value of the index for the 
corresponding card's entry in the entity table of the 
chassis MIB."
::= { idt1PlEntry 1 }

idt1PlIDIndex OBJECT-TYPE
SYNTAX INTEGER
ACCESS read-only
STATUS mandatory
DESCRIPTION
"This object is the index for one of the 12 pool IDs for 
this card."
::= { idt1PlEntry 2 }

idt1PlDNIS OBJECT-TYPE
SYNTAX DisplayString (SIZE(0..36))
ACCESS read-write
STATUS mandatory
DESCRIPTION
"This is the DNIS number associated with the POOL ID."
::= { idt1PlEntry 3 }

idt1PlType OBJECT-TYPE
SYNTAX INTEGER{
  none(1),
  analog(2),
  digital(3),
  both(4)
}
ACCESS read-write
STATUS mandatory
DESCRIPTION
"This object is the pool type associated with the pool ID."
::= { idt1PlEntry 4 }

-- The T1-PRI ISDN Reserved Resource Pool Assignment table.

idt1MdmRPA OBJECT IDENTIFIER ::= { idt1 4 }

idt1MdmRPATable OBJECT-TYPE
SYNTAX SEQUENCE OF Idt1MdmRPAEntry
ACCESS not-accessible
STATUS mandatory
DESCRIPTION
"This table contains an entry for each of the manageable 
T1-PRI ISDN Cards in the chassis.  It contains objects that 
reflect the current Pool Assignment of the Pool Id to the 
modem device."
::= { idt1MdmRPA 1 }

idt1MdmRPAEntry OBJECT-TYPE
SYNTAX Idt1MdmRPAEntry
ACCESS not-accessible
STATUS mandatory
DESCRIPTION
"There is one Reserved Pool Assignment to modem device Table 
entry per T1-PRI ISDN Card in the chassis."
INDEX { idt1MdmRPAIndex, idt1MdmRPAIDIndex }
::= { idt1MdmRPATable 1 }

Idt1MdmRPAEntry ::=
SEQUENCE {
idt1MdmRPAIndex
    INTEGER,
idt1MdmRPAIDIndex
    INTEGER,
idt1MdmRPASlot
    INTEGER,
idt1MdmRPAChan
    INTEGER,
idt1MdmRPAPoolID
    INTEGER
}

idt1MdmRPAIndex OBJECT-TYPE
SYNTAX INTEGER
ACCESS read-only
STATUS mandatory
DESCRIPTION
"A unique value for each card in the chassis.  The value of 
idt1MdmRPA Index matches the value of the index for the 
corresponding card's entry in the entity table of the 
chassis MIB."
::= { idt1MdmRPAEntry 1 }

idt1MdmRPAIDIndex OBJECT-TYPE
SYNTAX INTEGER
ACCESS read-only
STATUS mandatory
DESCRIPTION
"This object is the index for one of the 64 channel IDs for 
this card."
::= { idt1MdmRPAEntry 2 }

idt1MdmRPASlot OBJECT-TYPE
SYNTAX INTEGER (1..16)
ACCESS read-only
STATUS mandatory
DESCRIPTION
"The channel associated with the Id of Modem device Reserved 
resource Pool Assignment table."
::= { idt1MdmRPAEntry 3 }

idt1MdmRPAChan OBJECT-TYPE
SYNTAX INTEGER (1..4)
ACCESS read-only
STATUS mandatory
DESCRIPTION
"The slot associated with the Id of Modem device Reserved 
resource Pool Assignment table."
::= { idt1MdmRPAEntry 4 }

idt1MdmRPAPoolID OBJECT-TYPE
SYNTAX INTEGER (0..12)
ACCESS read-write
STATUS mandatory
DESCRIPTION
"The Pool Id assigned in the Modem device Reserved resource 
Pool Assignment table (1/2/3/4 <-> none/A/B/C/D)."
::= { idt1MdmRPAEntry 5 }

-- The T1-PRI ISDN-Gateway to Reserved Resource Pool Assignment table.

idt1GwyRPA OBJECT IDENTIFIER ::= { idt1 5 }

idt1GwyRPATable OBJECT-TYPE
SYNTAX SEQUENCE OF Idt1GwyRPAEntry
ACCESS not-accessible
STATUS mandatory
DESCRIPTION
"This table contains an entry for each of the manageable 
T1-PRI ISDN Cards in the chassis.  It contains objects that 
reflect the current Pool Assignment of the Pool Id to the 
ISDN-Gateway(s)."
::= { idt1GwyRPA 1 }

idt1GwyRPAEntry OBJECT-TYPE
SYNTAX Idt1GwyRPAEntry
ACCESS not-accessible
STATUS mandatory
DESCRIPTION
"There is one Reserved Pool Assignment to slot device Table 
entry per T1-PRI ISDN Card in the chassis."
INDEX { idt1GwyRPAIndex, idt1GwyRPASlotIndex }
::= { idt1GwyRPATable 1 }

Idt1GwyRPAEntry ::=
SEQUENCE {
idt1GwyRPAIndex
    INTEGER,
idt1GwyRPASlotIndex
    INTEGER,
idt1GwyRPAPoolID
    INTEGER
}

idt1GwyRPAIndex OBJECT-TYPE
SYNTAX INTEGER
ACCESS read-only
STATUS mandatory
DESCRIPTION
"A unique value for each card in the chassis.  The value of 
idt1GwyRPA Index matches the value of the index for the 
corresponding card's entry in the entity table of the 
chassis MIB."
::= { idt1GwyRPAEntry 1 }

idt1GwyRPASlotIndex OBJECT-TYPE
SYNTAX INTEGER
ACCESS read-only
STATUS mandatory
DESCRIPTION
"This object is the index for one of the 16 Slots in the 
chassis."
::= { idt1GwyRPAEntry 2 }

idt1GwyRPAPoolID OBJECT-TYPE
SYNTAX INTEGER (0..12)
ACCESS read-write
STATUS mandatory
DESCRIPTION
"The Pool Id assigned in the ISDN-Gateway device Reserved 
resource Pool Assignment table (1/2/3/4 <-> none/A/B/C/D)."
::= { idt1GwyRPAEntry 3 }

END
