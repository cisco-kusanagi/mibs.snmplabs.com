-- Retix Proprietry Local Bridge family MIB
-- Version 2.0 - Concise Mib form
-- Copyright Retix 1993. 
-- Retix. 2644 30th Street, Santa Monica. CA 90025.

-- Retix: The Open Networking Company.
--
-- This MIB covers the following Retix Products :-
--
--		2265
--		4660 Local Bridges
-- 
-- It includes the entire MIB as implemented on these devices, i.e. it
-- includes the pieces of MIB-I that the device supports.
--

	RETIX-LOCAL-BRIDGE-MIB { iso org(3) dod(6) internet(1) mgmt(2) 1 }

	DEFINITIONS ::= BEGIN

	IMPORTS
	mgmt, OBJECT-TYPE, NetworkAddress, IpAddress,
	Counter, Gauge, TimeTicks
	FROM RFC1065-SMI;
	mib     OBJECT IDENTIFIER ::= { mgmt 1 }

	-- Retix Specific Groups
	
	retix              OBJECT IDENTIFIER ::= {enterprises 72 } 

	product            OBJECT IDENTIFIER ::= {retix 8 } 
	rtxlocal           OBJECT IDENTIFIER ::= {retix 9 } 


	s3agentSW          OBJECT IDENTIFIER ::= {rtxlocal 1} 
	s3agentHW          OBJECT IDENTIFIER ::= {rtxlocal 2}
	s3agentIpProtocol  OBJECT IDENTIFIER ::= {rtxlocal 3}
	s3snmpAgent        OBJECT IDENTIFIER ::= {rtxlocal 4}
	brdgcommon         OBJECT IDENTIFIER ::= {rtxlocal 5}
	locbrdg            OBJECT IDENTIFIER ::= {rtxlocal 6}
	ieee8023           OBJECT IDENTIFIER ::= {rtxlocal 7}

	p2265m             OBJECT IDENTIFIER ::= {product 3 } 
	p4660              OBJECT IDENTIFIER ::= {product 4 } 



	-- the System group

	sysDescr OBJECT-TYPE
		SYNTAX  OCTET STRING
		ACCESS  read-only
		STATUS  mandatory
		DESCRIPTION "A textual description of the entity.  This value  
		includes the full name and version identification of the system's 
		hardware type, software operating-system, and networking software."
		::= { system 1 }

	sysObjectID OBJECT-TYPE
		SYNTAX  OBJECT IDENTIFIER
		ACCESS  read-only
		STATUS  mandatory
		DESCRIPTION "The unique product id of the bridge."
		::= { system 2 }

	sysUpTime OBJECT-TYPE
		SYNTAX  TimeTicks
		ACCESS  read-only
		STATUS  mandatory
		DESCRIPTION "The time (in hundredths of a second) since the network 
		management portion of the system was las re-initialised."
		::= { system 3 }

	sysLocation OBJECT-TYPE
		SYNTAX  OCTET STRING
		ACCESS  read-write
		STATUS  mandatory
		DESCRIPTION "This is an informational string that could be used to 
		show the physical location of (i.e. area) of the bridge. This element
		will be initialised to a null string by the bridge, but can be modified
		by the manager.  This element will survive a reset, but not necessary 
		a restart.  This field can be used as a simple bridge name."
		::= { system 6 }

--
--	Interfaces group elements
--

	ifNumber OBJECT-TYPE
		SYNTAX  INTEGER
		ACCESS  read-only
		STATUS  mandatory
		DESCRIPTION "The number of network interfaces (regardless of their 
		current state) on which this system can send/receive IP datagrams."
		::= { interfaces 1 }

	-- the Interfaces table

	ifTable OBJECT-TYPE
		SYNTAX  SEQUENCE OF IfEntry
		ACCESS  not-accessible
		STATUS  mandatory
		DESCRIPTION "A list of interface entries.  The number of entries is
		given by the value of ifNumber."
		::= { interfaces 2 }

	ifEntry OBJECT-TYPE
		SYNTAX  IfEntry
		ACCESS  not-accessible
		STATUS  mandatory
		DESCRIPTION "An interface entry containing objects at the subnetwork
		layer and below for a particular interface."
		INDEX { ifIndex }
		::= { ifTable 1 }

	IfEntry ::= SEQUENCE {
		ifIndex
			INTEGER,
		ifDescr
			OCTET STRING,
		ifType
			INTEGER,
		ifMtu
			INTEGER,
		ifSpeed
			Gauge,
		ifPhysAddress
			OCTET STRING,
		ifAdminStatus
			INTEGER,
		ifOperStatus
			INTEGER,
		ifLastChange
			TimeTicks,
		ifInOctets
			Counter,
		ifInUcastPkts
			Counter,
		ifInNUcastPkts
			Counter,
		ifInDiscards
			Counter,
		ifInErrors
			Counter,
		ifInUnknownProtos
			Counter,
		ifOutOctets
			Counter,
		ifOutUcastPkts
			Counter,
		ifOutNUcastPkts
			Counter,
		ifOutDiscards
			Counter,
		ifOutErrors
			Counter,
		ifOutQLen
			Gauge
		}

	ifIndex OBJECT-TYPE
		SYNTAX  INTEGER
		ACCESS  read-only
		STATUS  mandatory
		DESCRIPTION "A unique value for each interface.  Its value ranges
		between 1 and the value of ifNumber.  The value for each interface 
		must remain constant at least from one reinitialization of the
		entity's network management system to the next re-initialisation."
		::= { ifEntry 1 }

	ifDescr OBJECT-TYPE
		SYNTAX  OCTET STRING
		ACCESS  read-only
		STATUS  mandatory
		DESCRIPTION "A text string containing information about the interface. 
		This string should the name of the manufacturer, the product name and
		the version of the hardware interface."
		::= { ifEntry 2 }

	ifType OBJECT-TYPE
		SYNTAX  INTEGER {
			other(1),     -- none of the following
			regular1822(2),
			hdh1822(3),
			ddn-x25(4),
			rfc877-x25(5),
			ethernet-csmacd(6),
			iso88023-csmacd(7),
			iso88024-tokenBus(8),
			iso88025-tokenRing(9),
			iso88026-man(10),
			starLan(11),
			proteon-10MBit(12),
			proteon-80MBit(13),
			hyperchannel(14),
			fddi(15),
			lapb(16),
			sdlc(17),
			t1-carrier(18),
			cept(19),
			basicIsdn(20),
			primaryIsdn(21),
			propPointToPointSerial(22)
			}
		ACCESS  read-only
		STATUS  mandatory
		DESCRIPTION "The type of interface, distinguished according to the 
		physical/link/network protocol (s) immediately 'below' IP in the 
		protocol stack."
		::= { ifEntry 3 }

	ifMtu OBJECT-TYPE
		SYNTAX  INTEGER
		ACCESS  read-only
		STATUS  mandatory
		DESCRIPTION "The size of the largest IP datagram which can be 
		sent/received on the interface, specified in octets."
		::= { ifEntry 4 }

	ifSpeed OBJECT-TYPE
		SYNTAX  Gauge
		ACCESS  read-only
		STATUS  mandatory
		DESCRIPTION "An estimate of the interfaces current bandwidth in bits 
		per second.  For interfaces which do not vary in bandwidth or for 
		those where no accurate estimation can be made, this object should
		contain the nominal bandwidth.
		We return a fixed value equivalent to 10 Megabits per second for this
		element."
		::= { ifEntry 5 }

	ifPhysAddress OBJECT-TYPE
		SYNTAX  OCTET STRING
		ACCESS  read-only
		STATUS  mandatory
		DESCRIPTION "The interfaces address at the protocol layer immediately 
		'below' IP in the protocol stack.  We return the ethernet address of
		the bridge in this element, for both channels of the bridge."
		::= { ifEntry 6 }

	ifAdminStatus OBJECT-TYPE
		SYNTAX  INTEGER {
			up(1),        -- ready to pass packets
			down(2),
			testing(3)    -- in some test mode
			}
		ACCESS  read-write
		STATUS  mandatory
		DESCRIPTION "The desired state of the interface.  The testing(3)
		state indicates that no operational packets can be passed.  We will
		only support the up(1) state for the interfaces of the bridge. 
		Writing any other value to this element will perform no action, and
		will always be read as a 1."
		::= { ifEntry 7 }

	ifOperStatus OBJECT-TYPE
		SYNTAX  INTEGER {
			up(1),	-- ready to pass packets
			down(2),
			testing(3)    -- in some test mode
			}
		ACCESS  read-only
		STATUS  mandatory
		DESCRIPTION "The current operational state of the interface.  The 
		interfaces of the bridge will only ever exist in the up(1) state."
		::= { ifEntry 8 }

	ifLastChange OBJECT-TYPE
		SYNTAX  TimeTicks
		ACCESS  read-only
		STATUS  mandatory
		DESCRIPTION "The value of sysUpTime when the interface entered its 
		current operational state.  If the current state was entered prior to
		the last re-initialisation of the local network management subsystem,
		then this object contains a zero value.
		For the local bridge this parameter will always return a zero value."
		::= { ifEntry 9 }

	ifInOctets OBJECT-TYPE
		SYNTAX  Counter
		ACCESS  read-only
		STATUS  mandatory
		DESCRIPTION "The total number of octets received on the interface,
		including framing characters."
		::= { ifEntry 10 }

	ifInUcastPkts OBJECT-TYPE
		SYNTAX  Counter
		ACCESS  read-only
		STATUS  mandatory
		DESCRIPTION "The number of (subnet)unicast packets delivered to a
		higher-layer protocol. For the local bridge this parameter will 
		always return a zero value."
		::=  { ifEntry 11 }

	ifInNUcastPkts OBJECT-TYPE
		SYNTAX  Counter
		ACCESS  read-only
		STATUS  mandatory
		DESCRIPTION "The number of non-unicast (i.e. subnet broadcast of 
		subnet multicast) packets delivered to a higher-layer protocol.For
		the local bridge this parameter will always return a zero value."
		::= { ifEntry 12 }

	ifInDiscards OBJECT-TYPE
		SYNTAX  Counter
		ACCESS  read-only
		STATUS  mandatory
		DESCRIPTION "The number inbound packets which were chosen to be
		discarded even though no errors had been detected to prevent their
		being delivered to a higher-layer protocol.  One possible reason for
		discarding such a packet could be to free up buffer space.For the 
		local bridge this parameter will always return a zero value."
		::= { ifEntry 13 }

	ifInErrors OBJECT-TYPE
		SYNTAX  Counter
		ACCESS  read-only
		STATUS  mandatory
		DESCRIPTION "The number of inbound packets that contained errors
		preventing them from being deliverable to a higher-layer protocol.For 
		the local bridge this parameter will always return a zero value."
		::= { ifEntry 14 }

	ifInUnknownProtos OBJECT-TYPE
		SYNTAX  Counter
		ACCESS  read-only
		STATUS  mandatory
		DESCRIPTION "The number of packets received via the interface which 
		were discarded because of an unknown or unsupported protocol.For the
		local bridge this parameter will always return a zero value."
		::= { ifEntry 15 }

	ifOutOctets OBJECT-TYPE
		SYNTAX  Counter
		ACCESS  read-only
		STATUS  mandatory
		DESCRIPTION "The total number of octets transmitted out of the 
		interface, including framing characters.  Always returns to zero."
		::= { ifEntry 16 }

	ifOutUcastPkts OBJECT-TYPE
		SYNTAX  Counter
		ACCESS  read-only
		STATUS  mandatory
		DESCRIPTION "The total number of packets that higher-level protocols 
		requested be transmitted to a subnet-unicast address, including those
		that were discarded or not sent.For the local bridge this parameter 
		will always return a zero value."
		::= { ifEntry 17 }

	ifOutNUcastPkts OBJECT-TYPE
		SYNTAX  Counter
		ACCESS  read-only
		STATUS  mandatory
		DESCRIPTION "The total number of packets that higher-level protocols
		requested be transmitted to a non-unicast (i.e., a subnet broadcast or
		subnet multicast) address, incuding those that were discarded or not 
		sent.For the local bridge this parameter will always return a zero
		value."
		::= { ifEntry 18 }

	ifOutDiscards OBJECT-TYPE
		SYNTAX  Counter
		ACCESS  read-only
		STATUS  mandatory
		DESCRIPTION "The number of outband packets which were chosen to be 
		discarded even though no errors had been detected to prevent their
		being transmitted.  One possible reason for discarding such a packet 
		could be to free up buffer space.For the local bridge this parameter 
		will always return a zero value."
		::= { ifEntry 19 }

	ifOutErrors OBJECT-TYPE
		SYNTAX  Counter
		ACCESS  read-only
		STATUS  mandatory
		DESCRIPTION "The total number of outbound packets that could not be 
		transmitted because of errors.For the local bridge this parameter 
		will always return a zero value."
		::= { ifEntry 20 }

	ifOutQLen OBJECT-TYPE
		SYNTAX  Gauge
		ACCESS  read-only
		STATUS  mandatory
		DESCRIPTION "The length of the output packet queue (in packets).
		For the local bridge this parameter will always return a zero value."
		::= { ifEntry 21 }

-- 
--	s3agentSW group elements
--

	s3agentType OBJECT-TYPE
		SYNTAX INTEGER 
		ACCESS read-only
		STATUS mandatory
		DESCRIPTION "The agents module type."
		::= { s3agentSW 1}

	s3agentFwVer OBJECT-TYPE
		SYNTAX INTEGER 
		ACCESS read-only
		STATUS mandatory
		DESCRIPTION "The agents firmware version, 0=A, 1=B, etc."
		::= { s3agentSW 2}

	s3agentSwMajorVer OBJECT-TYPE
		SYNTAX INTEGER 
		ACCESS read-only
		STATUS mandatory
		DESCRIPTION "The major software version number.  e.g. where
		major.minor = 3.0."
		::= { s3agentSW 3}

	s3agentSwMinorVer OBJECT-TYPE
		SYNTAX INTEGER 
		ACCESS read-only
		STATUS mandatory
		DESCRIPTION "The minor software version number.  e.g. where
		major.minor = 3.0."
		::= { s3agentSW 4}

	s3agentBootProtocol OBJECT-TYPE
		SYNTAX INTEGER {
			bootp-tftp(2)
			}
		ACCESS read-only
		STATUS mandatory
		DESCRIPTION "Bootp protocol used to load the module with its software."
		::= { s3agentSW 5}

	s3agentBootFile OBJECT-TYPE
		SYNTAX OCTET STRING (SIZE(64))
		ACCESS read-write
		STATUS mandatory
		DESCRIPTION "The name of the boot file that is sent to the boot
		server during boot time.  The boot protocol is determined by 
		s3agentBootProtocol."
		::= { s3agentSW 6}


	s3agentAuthTrap OBJECT-TYPE
		SYNTAX INTEGER {
			disable(1),	-- disable authentication traps
			enable(2)	-- enable authentication traps
			}
		ACCESS read-write
		STATUS mandatory
		DESCRIPTION "Enable or disable the use of authentication error trap 
		generation."
		::= { s3agentSW 7}

	s3agentLocation OBJECT-TYPE
		SYNTAX DisplayString(SIZE(0..64))
		ACCESS read-write
		STATUS mandatory
		DESCRIPTION "This is an informational string that could be used to
		show the physical location of (i.e. area) of the bridge. This 
		element will share its data with 'sysLocation'.  This will be 
		initialised to a null string by the bridge, but can be modified by 
		the manager.  This element will survive a reset, but not necessary a
		restart.  This field can be used as a simple bridge name."
		::= { s3agentSW 8}

	s3agentMIBlevel OBJECT-TYPE
		SYNTAX INTEGER
		ACCESS read-only
		STATUS mandatory
		DESCRIPTION "Used to determine current MIB release supported by agent.
		The encoding of this object is of the following form:  xyy, where x 
		is the major version number and yy is ther minor version number. 
		Thus, version 3.0 would be represented as 300, version 3.01 would 
		be 301 and 3.1 would be 310."
		::= { s3agentSW 9}

	s3agentfeatureLevel OBJECT-TYPE
		SYNTAX INTEGER
		ACCESS read-only
		STATUS mandatory
		DESCRIPTION "Used to determine feature level of the agent.  The
		encoding of this object is of teh following form:  xyy, where x is
		the major version number and yy is ther minor version number.  Thus,
		version 3.0 would be represented as 300, version 3.01 would be 301
		and 3.1 would be 310."
		::= { s3agentSW 10}

	s3agentMySlotID OBJECT-TYPE
		SYNTAX INTEGER
		ACCESS read-only
		STATUS mandatory
		DESCRIPTION "Slot in which this bridge currently resides."
		::= { s3agentSW 11}

-- 
--	s3agentIpProtocol group elements
-- 

	s3agentIpAddr OBJECT-TYPE
		SYNTAX IpAddress
		ACCESS read-write
		STATUS mandatory
		DESCRIPTION "The IP address of the  bridge."
		::= { s3agentIpProtocol 1}

	s3agentIpNetmask OBJECT-TYPE
		SYNTAX IpAddress
		ACCESS read-write
		STATUS mandatory
		DESCRIPTION "The bridge's subnet mask."
		::= { s3agentIpProtocol 2}

	s3agentDefaultGateway OBJECT-TYPE
		SYNTAX IpAddress
		ACCESS read-write
		STATUS mandatory
		DESCRIPTION "The default gateway IP address."
		::= { s3agentIpProtocol 3}

	s3agentBootServerAddr OBJECT-TYPE
		SYNTAX IpAddress
		ACCESS read-write
		STATUS mandatory
		DESCRIPTION "The IP address to which the requests for boot files
		are sent.  The protocol used to retreive the boot files is 
		determined by object s3agent BootProtocol."
		::= { s3agentIpProtocol 4}


-- 
--	trap receiver objects
--


    trapRcvrTable OBJECT-TYPE
        SYNTAX  SEQUENCE OF TrapRcvrEntry
        ACCESS  not-accessible
        STATUS  mandatory
        DESCRIPTION  "This entities trap server table"
        ::=  { s3snmpAgent 3 }


	trapRcvrEntry OBJECT-TYPE
		SYNTAX  TrapRcvrEntry
		ACCESS  not-accessible
		STATUS  mandatory
		DESCRIPTION "A destination address and community string to a 
		particular trap server, along with a trap filter and entry aging
		capability. All these objects should be supplied in a single PDU,
		when attempting to set an entry in this table."
		INDEX { s3agentTrapRcvrNetAddr }
		::=  { trapRcvrTable 1 }

	TrapRcvrEntry ::= SEQUENCE {
				s3agentTrapRcvrStatus
					INTEGER,
				s3agentTrapRcvrNetAddr
					IpAddress,
				s3agentTrapRcvrComm
					DisplayString,
				s3agentTrapRcvrAgeTime
					TimeTicks

				}

	s3agentTrapRcvrStatus OBJECT-TYPE
		SYNTAX  INTEGER {
				valid (1),
				invalid (2),
				other (3)
				}
		ACCESS  read-write
		STATUS  mandatory
		DESCRIPTION "Setting this object to the value invalid(2) has the 
		effect of invalidating the corresponding entry in the 
		s3agentTrapReceiverTable.  That is, it effectively disassociates
		the address identified with the entry by removing the entry from
		the table."
		::=  { trapRcvrEntry 1 }

	s3agentTrapRcvrNetAddr OBJECT-TYPE
		SYNTAX  IpAddress
		ACCESS  read-write
		STATUS  mandatory
		DESCRIPTION "IP address for trap server that is to receive the trap."
		::=  { trapRcvrEntry 2 }

	s3agentTrapRcvrComm OBJECT-TYPE
		SYNTAX  DisplayString (SIZE(1..20))
		ACCESS  read-write
		STATUS  mandatory
		DESCRIPTION "Community string used for traps."
		::=  { trapRcvrEntry 3 }

	s3agentTrapRcvrAgeTime OBJECT-TYPE
		SYNTAX  TimeTicks
		ACCESS  read-write
		STATUS  mandatory
		DESCRIPTION "Life span of this entry of the trap receiver table in
		1/100 seconds.  Following this time interval the entry will be
		deleted from the table."
		::=  { trapRcvrEntry 4 }

-- 
-- Bridge Common group
-- 

	bcomBpduTimer OBJECT-TYPE
		SYNTAX  INTEGER
		ACCESS  read-write
		STATUS  mandatory
		DESCRIPTION "This parameter is always zero for a local bridge."
		::= { brdgcommon 1 }

	bcomDefaultBpduTimer OBJECT-TYPE
		SYNTAX  INTEGER
		ACCESS  read-write
		STATUS  mandatory
		DESCRIPTION "This parameter will always return a zero value for a 
		local bridge."
		::=  { brdgcommon 2 }


	snmpAccessPolicyObject        	OBJECT IDENTIFIER ::= {brdgcommon 3 } 

	snmpAccessPolicyTable OBJECT-TYPE
		SYNTAX  SEQUENCE OF SnmpAccessPolicyEntry
		ACCESS  not-accessible
		STATUS  mandatory
		DESCRIPTION "This table is a list of entries which are used to 
		authenticate PDUs received by the station.  This table contains a
		maximum of 8 entries."
		::=  { snmpAccessPolicyObject 1 }

	snmpAccessPolicyEntry OBJECT-TYPE
		SYNTAX  SnmpAccessPolicyEntry
		ACCESS  not-accessible
		STATUS  mandatory
		DESCRIPTION "This is an entry in the snmpAccessPolicyTable. To set
		an entry in this table, all the objects should be supplied in a 
		single PDU. All the entries of this table exist at all times. 
		Unused entries are marked as invalid."
		INDEX { accessPolicyIndex }
		::=  { snmpAccessPolicyTable 1 }

	 SnmpAccessPolicyEntry ::= SEQUENCE {
		accessPolicyIndex
			INTEGER,
		communityName
			DisplayString (SIZE(0..10)),
		accessMode
			INTEGER,
		snmpAccessPolicyType
			INTEGER
		}

	accessPolicyIndex OBJECT-TYPE
		SYNTAX  INTEGER
		ACCESS  read-write
		STATUS  mandatory
		DESCRIPTION "This index is used as the instance for a Get or Set
		operation on the table."
		::=  { snmpAccessPolicyEntry 1 }

	communityName OBJECT-TYPE
		SYNTAX  DisplayString ( SIZE (1..10))
		ACCESS  read-write
		STATUS  mandatory
		DESCRIPTION "This object is a string, against which the community
		field in a recieved PDU is compared.  If there are no community names
		in the table, with which the received community field forms a match,
		authentication of the PDU fails."
		::=  { snmpAccessPolicyEntry 2 }

	accessMode OBJECT-TYPE
		SYNTAX  INTEGER{
			 	readonly (1),
				writeonly (2),
				readwrite (3)
				}
		ACCESS  read-write
		STATUS  mandatory
		DESCRIPTION "This sets the access mode allowed from the 
		corresponding community"
		::=  { snmpAccessPolicyEntry 3 }

	snmpAccessPolicyType OBJECT-TYPE
		SYNTAX  INTEGER {
				valid (1),
				invalid (2)
				}
		ACCESS  read-write
		STATUS  mandatory
		DESCRIPTION "This object determines what action is to be performed 
		on a particular entry.  A value causes the entry to be added to the
		table, while a value of invalid causes the entry to be deleted."
		::=  { snmpAccessPolicyEntry 4 }

	snmpAccessPolicyAction OBJECT-TYPE
		SYNTAX  INTEGER {
				clearTable(1)
				}
		ACCESS  write-only
		STATUS  mandatory
		DESCRIPTION "Setting this object to 'clearTable' deletes all the
		entries in the table."
		::=  { snmpAccessPolicyObject 2 }

	snmpAccessPolicyPage OBJECT-TYPE
		SYNTAX  OCTET STRING (SIZE(256))
		ACCESS  read-only
		STATUS  mandatory
		DESCRIPTION "This octetstring contains the entire contents of the
		table in a single, unformatted string. Each entry is 16 bytes long
		and contains all the objects as explained above."
		::=  { snmpAccessPolicyObject 3 }

-- 
--	hardware mib objects
-- 

	s3agentStatus OBJECT-TYPE
		SYNTAX INTEGER {
			offline(1),
			online(2)
			}
		ACCESS read-only
		STATUS mandatory
		DESCRIPTION "Indicates the bridge is online and operating."
		::= { s3agentHW 1 }

	s3agentMdaHwVer OBJECT-TYPE
		SYNTAX INTEGER
		ACCESS read-only
		STATUS mandatory
		DESCRIPTION "The bridges hardware rev.  0=Rev. A, 1=Rev. B etc."
		::= { s3agentHW 2 }

	s3agentMode OBJECT-TYPE
		SYNTAX INTEGER {
			primary(1),
			secondary(2),
			notSupported(3)
			}
		ACCESS read-only
		STATUS mandatory
		DESCRIPTION "This object is not supported by the bridge which will
		always return 3 as its value."
		::= { s3agentHW 3 }

	s3agentReset OBJECT-TYPE
		SYNTAX INTEGER {
			noReset(1),
			reset(2)
			}
		ACCESS read-write
		STATUS mandatory
		DESCRIPTION "Writing a 2 to this object will cause the bridge to
		perform a reset, and if supported to perform a software download.
		Reading this object will always return 1."
		::= { s3agentHW 4 }

	s3agentRestart OBJECT-TYPE
		SYNTAX INTEGER {
			noRestart(1),
			restart(2)
			}
		ACCESS read-write
		STATUS mandatory
		DESCRIPTION "Will cause the bridge to perform a reset, no download 
		of software is performed.  Reading this object will always return 1."
		::= { s3agentHW 5 }

	s3agentBootMode OBJECT-TYPE
		SYNTAX INTEGER {
			eeprom(1),
			other(2)
			}
		ACCESS read-write
		STATUS mandatory
		DESCRIPTION "The method of obtaining boot parameter information.  
		ie. if eeprom(1), and if bootp/tftp is the boot mechanism, then
		obtain server ip address and filename from EEPROM.  If other(2) then
		obtain server ip address and fielname via bootp.  In both cases the
		data is downloaded via tftp."
		::= { s3agentHW 6 }

	s3agentWriteEeprom OBJECT-TYPE
		SYNTAX INTEGER {
			noWriteEeprom(1),
			writeEeprom(2)
			}
		ACCESS read-write
		STATUS mandatory
		DESCRIPTION "Writing a(2) to this object will cause the contents of 
		the current EEPROM data structure to be written to the EEPROM. 
		Reading this value will always return 1."
		::= { s3agentHW 7 }

	s3agentBaudRate OBJECT-TYPE
		SYNTAX Gauge
		ACCESS read-write
		STATUS mandatory
		DESCRIPTION "This object is not supported by the bridge which will
		always return zero as the value of this object.  Any value 
		supplied with a write will be discarded."
		::= { s3agentHW 8 }

	s3agentInitString OBJECT-TYPE
		SYNTAX  OCTET STRING (SIZE (64))
		ACCESS  read-write
		STATUS  mandatory
		DESCRIPTION "This object is not supported by the bridge which will
		always return blank as the value of this object.  Any value supplied
		with a write will be discarded."
		::= { s3agentHW 9 }

	--  IEEE8023 Group

	ieee8023Table OBJECT-TYPE
		SYNTAX  SEQUENCE OF Ieee8023Entry
		ACCESS  not-accessible
		STATUS  mandatory
		DESCRIPTION "A list of IEEE 802.3 Interface entries."
		::= { ieee8023 1 }

	ieee8023Entry OBJECT-TYPE
		SYNTAX  Ieee8023Entry
		ACCESS  not-accessible
		STATUS  mandatory
		DESCRIPTION "The statistics table.  An entry in this table is 
		uniquely identified by the value of the ieee8023Index variable
		associated with the interface to which the statistics refer."
		INDEX { ieee8023Index }
		::= { ieee8023Table 1 }

	Ieee8023Entry ::= SEQUENCE {
		ieee8023Index
			INTEGER,
		ieee8023FramesTransmittedOks
			Counter,
		ieee8023SingleCollisionFrames
			Counter,
		ieee8023MultipleCollisionFrames
			Counter,
		ieee8023OctetsTransmittedOks
			Counter,
		ieee8023DeferredTransmissions
			Counter,
		ieee8023MulticastFramesTransmittedOks
			Counter,
		ieee8023BroadcastFramesTransmittedOks
			Counter,
		ieee8023LateCollisions
			Counter,
		ieee8023ExcessiveCollisions
			Counter,
		ieee8023InternalMACTransmitErrors
			Counter,
		ieee8023CarrierSenseErrors
			Counter,
		ieee8023ExcessiveDeferrals
			Counter,
		ieee8023FramesReceivedOks
			Counter,
		ieee8023OctetsReceivedOks
			Counter,
		ieee8023MulticastFramesReceivedOks
			Counter,
		ieee8023BroadcastFramesReceivedOks
			Counter,
		ieee8023FrameTooLongs
			Counter,
		ieee8023AlignmentErrors
			Counter,
		ieee8023FCSErrors
			Counter,
		ieee8023inRangeLengthErrors
			Counter,
		ieee8023outOfRangeLengthFields
			Counter,
		ieee8023InternalMACReceiveErrors
			Counter,
		ieee8023InitializeMAC
			INTEGER,
		ieee8023PromiscuousReceiveStatus
			INTEGER,
		ieee8023MACSubLayerStatus
			INTEGER,
		ieee8023TransmitStatus
			INTEGER,
		ieee8023MulticastReceiveStatus
			INTEGER,
		ieee8023MACAddress
			OCTET STRING,
		ieee8023SQETestErrors
			Counter
		}

	ieee8023Index   OBJECT-TYPE
		SYNTAX  INTEGER
		ACCESS  read-only
		STATUS  mandatory
		DESCRIPTION "This value uniquely identifies the interface."
		::= { ieee8023Entry 1 }
	
	ieee8023FramesTransmittedOks OBJECT-TYPE
		SYNTAX  Counter
		ACCESS  read-only
		STATUS  mandatory
		DESCRIPTION "This contains a count of frames that are successfully
		transmitted.  This counter is incremented when a frame successfully
		transmitted, even if one of the collision Counters (following two 
		objects) are also counted.  In otherwords, this count includes
		transmissions that succeeded after some number of collisions. 
		This count includes multicast and broadcast frames."
		::= { ieee8023Entry 2 }
	
	ieee8023SingleCollisionFrames OBJECT-TYPE
		SYNTAX  Counter
		ACCESS  read-only
		STATUS  mandatory
		DESCRIPTION "This contains a count of frames that are involved in
		a single collision, and are subsequently transmitted successfully. 
		If this counter is incremented then the ieee8023FramesTransmittedODs 
		count will also be incremented AND ieee8023MultipleCollisionFrames
		will NOT be incremented."
		::= { ieee8023Entry 3 }
	
	ieee8023MultipleCollisionFrames OBJECT-TYPE
		SYNTAX  Counter
		ACCESS  read-only
		STATUS  mandatory
		DESCRIPTION "This contains a count of frames that are involved in 
		more than one collision and are subsequently transmitted successfully.
		If this counter is incremented then the ieee8023FramesTransmittedOKs
		count will also be incremented AND ieee8023SingleCollisionFrames
		will NOT be incremented."
		::= { ieee8023Entry 4 }
	
	ieee8023OctetsTransmittedOks OBJECT-TYPE
		SYNTAX  Counter
		ACCESS  read-only
		STATUS  mandatory
		DESCRIPTION "This contains a count of data and padding octets of
		frames that are successfully transmitted.  This counter includes
		octets in broadcast and multicast frames that are transmitted.  
		This count does not include the address fields, length/type field
		and CRC field of the frame.  In Ethernet-Speak, it is JUST the data
		field (IP header, etc)."
		::= { ieee8023Entry 5 }
	
	ieee8023DeferredTransmissions OBJECT-TYPE
		SYNTAX  Counter
		ACCESS  read-only
		STATUS  mandatory
		DESCRIPTION "This contains a count of frames whose transmission was
		delayed on its first attempt because the medium was busy.  Frames
		involved in collisions are NOT included in this count."
		::= { ieee8023Entry 6 }
	
	ieee8023MulticastFramesTransmittedOks OBJECT-TYPE
		SYNTAX  Counter
		ACCESS  read-only
		STATUS  optional
		DESCRIPTION "This contains a count of frames successfully 
		transmitted to a group destination (multicast) address other 
		than broadcast."
		::= { ieee8023Entry 7 }
	
	ieee8023BroadcastFramesTransmittedOks OBJECT-TYPE
		SYNTAX  Counter
		ACCESS  read-only
		STATUS  optional
		DESCRIPTION "This contains a count of frames successfully 
		transmitted to the broadcast address.  This does not include 
		frames sent to a multicast address."
		::= { ieee8023Entry 8 }
	
	ieee8023LateCollisions OBJECT-TYPE
		SYNTAX  Counter
		ACCESS  read-only
		STATUS  mandatory
		DESCRIPTION "This contains a count of times that a collision has
		been detected later than 512 bit-times into the transmission of
		a packet.  512 bit-times is 51.2 micro-seconds.  This type of
		collision is counted twice:  both as a late collision and as a
		regular, run of the mill collision."
		::= { ieee8023Entry 9 }
	
	ieee8023ExcessiveCollisions OBJECT-TYPE
		SYNTAX  Counter
		ACCESS  read-only
		STATUS  mandatory
		DESCRIPTION "This contains a count of frames that due to excessive
		collisions are not transmitted successfully."
		::= { ieee8023Entry 10 }
	ieee8023InternalMACTransmitErrors OBJECT-TYPE
		SYNTAX  Counter
		ACCESS  read-only
		STATUS  mandatory
		DESCRIPTION "This is the count of transmit errors for which there
		are no specific counters.We will always return zero for this value."
		::= { ieee8023Entry 11 }
	
	ieee8023CarrierSenseErrors OBJECT-TYPE
		SYNTAX  Counter
		ACCESS  read-only
		STATUS  mandatory
		DESCRIPTION "This contains a count of times that carier sense was 
		lost or never appeared when attempting to transmit a packet."
		::= { ieee8023Entry 12 }

	ieee8023ExcessiveDeferrals OBJECT-TYPE
		SYNTAX  Counter
		ACCESS  read-only
		STATUS  optional
		DESCRIPTION "This contains a count of frames which deferred for an
		excessive period of time."
		::= { ieee8023Entry 13 }

	ieee8023FramesReceivedOks OBJECT-TYPE
		SYNTAX  Counter
		ACCESS  read-only
		STATUS  mandatory
		DESCRIPTION "This contains a count of frames that are successfully 
		received.  This does not include frames received with a 
		frame-too-long, FCS, length, or alignment errors or frames lost
		due to internal MAC sublayer error.  This counter includes broadcast
		and multicast frames that are received."
		::= { ieee8023Entry 14 }
	
	ieee8023OctetsReceivedOks OBJECT-TYPE
		SYNTAX  Counter
		ACCESS  read-only
		STATUS  mandatory
		DESCRIPTION "This contains a count of data and padding octets in
		frames that are successfully received.  This does not include frames
		received with a frame-too-long, FCS, length, or alignment errors or 
		frames lost due to internal MAC sublayer error.  This counter includes
		octets in broadcast and multicast frames that are recieved.  This 
		counter does not include the octets in the address, length/type and
		CRC fields."
		::= { ieee8023Entry 15 }
	
	ieee8023MulticastFramesReceivedOks OBJECT-TYPE
		SYNTAX  Counter
		ACCESS  read-only
		STATUS  optional
		DESCRIPTION "This contains a count of frames that are successfully
		recieved and are directed to an active non-broadcast group address.
		This does not include frames received with a frame-too-long, FCD,
		length, or alignment errors or frames lost due to internal MAC
		sublayer error.  Broadcast packets are not included."
		::= { ieee8023Entry 16 }
	
	ieee8023BroadcastFramesReceivedOks OBJECT-TYPE
		SYNTAX  Counter
		ACCESS  read-only
		STATUS  optional
		DESCRIPTION "This contains a count of frames that are successfully
		received and are directed to the broadcast group address.  This does
		not include frames received with a frame-too-long, FCS, length, or
		alighment errors or frames lost due to internal MAC sublayer error.
		Multicast packets are not included."
		::= { ieee8023Entry 17 }
	
	ieee8023FrameTooLongs OBJECT-TYPE
		SYNTAX  Counter
		ACCESS  read-only
		STATUS  optional
		DESCRIPTION "This contains a count of frames that are received and
		exceed the maximum permitted frame size."
		::= { ieee8023Entry 18 }
	
	ieee8023AlignmentErrors OBJECT-TYPE
		SYNTAX  Counter
		ACCESS  read-only
		STATUS  mandatory
		DESCRIPTION "This contains a count of frames that are not an integral
		number of octets in length and do not pass the FCS check."
		::= { ieee8023Entry 19 }
	
	ieee8023FCSErrors OBJECT-TYPE
		SYNTAX  Counter
		ACCESS  read-only
		STATUS  mandatory
		DESCRIPTION "This contains a count of frames that are an integral 
		number of octets in length that do not pass the FCS check."
		::= { ieee8023Entry 20 }

	ieee8023inRangeLengthErrors OBJECT-TYPE
		SYNTAX  Counter
		ACCESS  read-only
		STATUS  optional
		DESCRIPTION "This contains a count of frames with a length field
		value between the minimum unpadded LLC data size and the maximum
		allowed LLC data size inclusive, and does not match the number of 
		LLC data octets received.  The counter also contains frames with a
		length field value less than the minimum unpadded LLC data size. 
		This parameter is currently not supported, and a zero will always 
		be returned."
		::= { ieee8023Entry 21 }
	
	ieee8023outOfRangeLengthFields OBJECT-TYPE
		SYNTAX  Counter
		ACCESS  read-only
		STATUS  optional
		DESCRIPTION "This contains a count of frames with a length field 
		value greater than the maximum allowed LLC data size.
		This parameter is currently not supported, and a zero will always
		be returned."
		::= { ieee8023Entry 22 }

	ieee8023InternalMACReceiveErrors OBJECT-TYPE
		SYNTAX  Counter
		ACCESS  read-only
		STATUS  mandatory
		DESCRIPTION "This contains a count of frames which would otherwise
		be received by the station, but could not be accepted due to an
		internal MAC sublayer receive error.  If this counter is incremented
		then none of the other Counters in this section are incremented. 
		The exact meaning and mechanisim for incrementing this counter is
		implementation dependent.  In short, this is the count of errors 
		for which there are no specific Counters."
		::= { ieee8023Entry 23 }
	
	ieee8023InitializeMAC OBJECT-TYPE
		SYNTAX  INTEGER {
			initialize (1)
			}
		ACCESS  read-write
		STATUS  mandatory
		DESCRIPTION "Resets the MAC layer counters.  When set, only the
		value initialize may be used.  When read, this variable always 
		returns the most recent value to which ieee8023InitializeMAC was 
		set to.  At the moment, this function solely serves to zero the
		MAC counters."
		::= { ieee8023Entry 24 }

	ieee8023PromiscuousReceiveStatus OBJECT-TYPE
		SYNTAX  INTEGER {
			enabled (1)
			}
		ACCESS  read-only
		STATUS  mandatory
		DESCRIPTION "This variable causes the MAC sublayer to enter 
		promiscuous receive state.  Currently the bridge only ever
		operates in promiscuous mode, so this parameter performs no function."
		::= { ieee8023Entry 25 }
	
	ieee8023MACSubLayerStatus OBJECT-TYPE
		SYNTAX  INTEGER {
			enabled (1)
			}
		ACCESS  read-only
		STATUS  optional
		DESCRIPTION "Causes the MAC sublayer to enter the normal 
		operational state at idle."
		::= { ieee8023Entry 26 }

	ieee8023TransmitStatus OBJECT-TYPE
		SYNTAX  INTEGER {
			enabled (1),
			disabled (2)
			}
		ACCESS  read-only
		STATUS  optional
		DESCRIPTION "Transmission is always enabled."
		::= { ieee8023Entry 27 }
	
	ieee8023MulticastReceiveStatus OBJECT-TYPE
		SYNTAX  INTEGER {
			enabled (1)
			}
		ACCESS  read-only
		STATUS  optional
		DESCRIPTION "Reception of multicast frames is always enabled."
		::= { ieee8023Entry 28 }

	ieee8023MACAddress OBJECT-TYPE
		SYNTAX  OCTET STRING (SIZE (6))
		ACCESS  read-only
		STATUS  optional
		DESCRIPTION "This object contains the MAC station address (i.e.
		the Ethernet address).  Reading this element will return the same
		value as locbrdgId."
		::= { ieee8023Entry 29 }

	ieee8023SQETestErrors OBJECT-TYPE
		SYNTAX  Counter
		ACCESS  read-only
		STATUS  mandatory
		DESCRIPTION "This contains a count of times that the SQE TEST
		ERROR status was received."
		::= { ieee8023Entry 30 }


	-- in locbrdg group

	locbrdgNumber OBJECT-TYPE
		SYNTAX INTEGER
		ACCESS read-only
		STATUS mandatory
		DESCRIPTION "The number of bridge instances present in this station."
		::= { locbrdg 1 }

	 locbrdgTable OBJECT-TYPE
		SYNTAX SEQUENCE OF LocbrdgEntry
		ACCESS not-accessible
		STATUS mandatory
		DESCRIPTION "A list of bridge halfs.  The number of entries is
		given by the value of bridgeNumber.  For the Br12 there will be
		two of these."
		::= { locbrdg 2 }

	 locbrdgEntry OBJECT-TYPE
		SYNTAX LocbrdgEntry
		ACCESS not-accessible
		STATUS mandatory
		DESCRIPTION "A bridge entry containing objects relevant to the
		bridging function."
		INDEX { locbrdgIndex }
		::= { locbrdgTable 1 }



	 LocbrdgEntry ::= SEQUENCE {
     		locbrdgIndex          		INTEGER,
     		locbrdgTransmitOnCrs		INTEGER,
     		locbrdgBroadcastRX		INTEGER,
     		locbrdgLanPathCost		INTEGER,
     		locbrdgLanDefaultPathCost      	INTEGER,
     		locbrdgLanPortSpatState		INTEGER,
    		locbrdgPortPriority		INTEGER,
     		locbrdgDefaultPortPriority     	INTEGER,
     		locbrdgDesignatedRoot		OCTET STRING (SIZE(6)),
     		locbrdgDesignatedCost		INTEGER,
     		locbrdgDesignatedPort		INTEGER,
     		locbrdgDesignatedBridge		OCTET STRING (SIZE(6)),
     		locbrdgTopologyChangeAck       	INTEGER
		}

	 locbrdgIndex OBJECT-TYPE
		SYNTAX INTEGER 
		ACCESS read-only
		STATUS mandatory
		DESCRIPTION "A unique value for each bridge instance.  Its 
		value ranges between 1 and the value of locbrdgNumber."
		::= { locbrdgEntry 1 }


	 locbrdgTransmitOnCrs OBJECT-TYPE
		SYNTAX INTEGER {
			txOnNoCRS (1),
			txOnCRS (2)
			}
		ACCESS read-write
		STATUS mandatory
		DESCRIPTION "This object controls whether a transmit is carried
		out with or without a Carrier Sense detection. Setting this object
		only takes effect after a warm-start."
		::= { locbrdgEntry 2 }


	 locbrdgBroadcastRX OBJECT-TYPE
		SYNTAX INTEGER {
			bcastRx (1),
			noBcastRx (2)
			}
		ACCESS read-write
		STATUS mandatory
		DESCRIPTION "This object controls whether broadcast messages are
		received or ignored."
		::= { locbrdgEntry 3 }


	 locbrdgLanPathCost OBJECT-TYPE
		SYNTAX INTEGER
		ACCESS read-only
		STATUS mandatory
		DESCRIPTION "This is the value of path cost assigned to this port
		automatically by the station, and represents the actual current
		operational value."
		::= { locbrdgEntry 4 }


	 locbrdgLanDefaultPathCost OBJECT-TYPE
		SYNTAX INTEGER
		ACCESS read-write
		STATUS mandatory
		DESCRIPTION "This is the value of path cost assigned to the port
		by the manager, which is stored in the non-volatile storage of the
		bridge."
		::= { locbrdgEntry 5 }


	 locbrdgLanPortSpatState OBJECT-TYPE
		SYNTAX INTEGER {
			disabled (1),
			blocking (2),
			learning (3),
			forwarding (4),
			listening (5)
			}
		ACCESS read-only
		STATUS mandatory
		DESCRIPTION "This object indicates the state of the Spanning
		tree port."
		::= { locbrdgEntry 6 }


	 locbrdgPortPriority OBJECT-TYPE
		SYNTAX INTEGER
		ACCESS read-only
		STATUS mandatory
		DESCRIPTION "The current STAP priority of the port in question."
		::= { locbrdgEntry 7 }


	 locbrdgDefaultPortPriority OBJECT-TYPE
		SYNTAX INTEGER
		ACCESS read-write
		STATUS mandatory
		DESCRIPTION "This is the default or power up STAP priority of
		the port in question."
		::= { locbrdgEntry 8 }


	 locbrdgDesignatedRoot OBJECT-TYPE
		SYNTAX OCTET STRING (SIZE(6))
		ACCESS read-only
		STATUS mandatory
		DESCRIPTION "The LAN address of the bridge recorded as the root 
		in the Root Identifier parameter of STP configuration messages
		transmitted by the Designated Bridge for the LAN on this port."
		::= { locbrdgEntry 9 }

	 locbrdgDesignatedCost OBJECT-TYPE
		SYNTAX INTEGER
		ACCESS read-only
		STATUS mandatory
		DESCRIPTION "The cost of the path to the root offered by the
		Designated Port on the LAN associated with the port."
		::= { locbrdgEntry 10 }

	 locbrdgDesignatedPort OBJECT-TYPE
		SYNTAX INTEGER
		ACCESS read-only
		STATUS mandatory
		DESCRIPTION "The port priority for the port of the bridge 
		believed to be the Designated Bridge for the LAN associated
		with each local port."
		::= { locbrdgEntry 11 }


	 locbrdgDesignatedBridge OBJECT-TYPE
		SYNTAX OCTET STRING (SIZE(6))
		ACCESS read-only
		STATUS mandatory
		DESCRIPTION "The LAN address of the bridge believed to be the
		Designated Bridge for teh LAN connected to this port."
		::= { locbrdgEntry 12 }


	 locbrdgTopologyChangeAck OBJECT-TYPE
		SYNTAX INTEGER
		ACCESS read-only
		STATUS mandatory
		DESCRIPTION "The count of the acknowledgements transmitted to
		confirm the network topology changes instituted by the STP."
		::= { locbrdgEntry 13 }

	 locbrdgBridgeMode OBJECT-TYPE
		SYNTAX INTEGER {
			forward (1),
			relay (2),
			security (3),
			listen (4)
			}
		ACCESS read-write
		STATUS mandatory
		DESCRIPTION "This object describes the operational mode of
		the bridge."
		::= { locbrdg 3 }

	 locbrdgDefaultBridgeMode OBJECT-TYPE
		SYNTAX INTEGER {
			forward (1),
			relay (2),
			security (3),
			listen (4)
			}

		ACCESS read-write
		STATUS mandatory
		DESCRIPTION "This object describes the default operational
		mode of the bridge"
		::= { locbrdg 4 }



	 locbrdgFilterMatches OBJECT-TYPE
		SYNTAX INTEGER{
 			pass (1),
			discard (2),
			disable (3)
			}
		ACCESS read-write
		STATUS mandatory
		DESCRIPTION "This object determines the action of the device
		when filtering on the bridge range filters"
		::= { locbrdg 5 }


	 locbrdgSpanningTreeMode OBJECT-TYPE
		SYNTAX INTEGER {
			enabled (1),
			disabled (2)
			}
		ACCESS read-write
		STATUS mandatory
		DESCRIPTION "This gives the current state of  Spanning tree on
		the device."
		::= { locbrdg 6 }


	 locbrdgDefaultSpanTreeMode OBJECT-TYPE
		SYNTAX INTEGER{
			enabled (1),
			disabled (2)
			}
		ACCESS read-write
		STATUS mandatory
		DESCRIPTION "This is the default configuration of spanning
		tree and is saved across a warm start."
		::= { locbrdg 7 }



	 locbrdgSpatHelloTimer OBJECT-TYPE
		SYNTAX INTEGER (1..10)
		ACCESS read-write
		STATUS optional
		DESCRIPTION "This is the period of time, in seconds, between
		the transmission of subsequent configuration BPDUs, used by the
		spanning tree algorithm.  If this bridge is the root then this
		value is used by all bridges of the network"
		::= { locbrdg 8 }


	 locbrdgDefaultSpatHelloTimer OBJECT-TYPE
		SYNTAX INTEGER (1..10)
		ACCESS read-write
		STATUS mandatory
		DESCRIPTION "This is the period of time, in seconds between the
		transmission of subsequent configuration BPDUs, used by the spanning
		tree algorithm.  This is the default value stored in the bridges
		non-volatile storage, and is used while the network is configuring,
		the active value will then be replaced with the root bridge's hello
		timer."
		::= { locbrdg 9 }

	 locbrdgHoldTime OBJECT-TYPE
		SYNTAX INTEGER 
		ACCESS read-only
		STATUS optional
		DESCRIPTION "After this time, in seconds unacknowledged bpdus
		will be resent."
		::= { locbrdg 10 }


	 locbrdgId OBJECT-TYPE
		SYNTAX OCTET STRING (SIZE(6)) 
		ACCESS read-only
		STATUS optional
		DESCRIPTION
		"For 2265's and 4660's, the Mac address of both ports is the same,
		thus rather than use the Mac address field of the ieee8023 group we
		will define a single element in the bridge group.  Should a future
		bridge  have different mac addresses for each port then we can make
		use of the ieee8023 defined element."
		::= { locbrdg 11 }



	 locbrdgSpatVersion OBJECT-TYPE
		SYNTAX INTEGER {
			revisionC(3),	-- ready to pass packets
			revision8(8)
		}
		ACCESS read-only
		STATUS optional
		DESCRIPTION "This variable determines the version of the spanning 
		tree algorithm implemented in the station, this is the current value
		and which can only be altered following a bridge reset."
		::= { locbrdg 12 }

	 locbrdgDefaultSpatVersion OBJECT-TYPE
		SYNTAX INTEGER {
			revisionC(3),	-- ready to pass packets
			revision8(8)
		}
		ACCESS read-write
		STATUS mandatory
		DESCRIPTION "This variable determines the version of the spanning
		tree algorithm supported in the bridge, this is the default value
		stored in non-volatile storage in the bridge, the bridge must be
		reset for the bridge change operational version."
		::= { locbrdg 13 }


	 locbrdgMaxAge OBJECT-TYPE
		SYNTAX INTEGER (6..40)
		ACCESS read-write
		STATUS optional
		DESCRIPTION "The maximum elapsed time, in seconds, that a received
		STP protocol message can exist before it is discarded by the bridge.
		If this bridge is the root bridge then this value is used by all
		bridges in the network."
		::= { locbrdg 14 }



	 locbrdgDefaultBridgeMaxAge OBJECT-TYPE
		SYNTAX INTEGER (6..40)
		ACCESS read-write
		STATUS mandatory
		DESCRIPTION "The maximum elapsed time, in seconds, that a received
		STP protocol message can exist before it is discarded by the bridge.
		This is the default value stored in nvram, if this bridge is the root,
		then this value will be used throughout the bridges of the network.
		Note:  locbrdgDefaultBridgeMaxAge must be <= 
		2*(locbrdgDefaultForwardDelay -1)"
		::= { locbrdg 15 }


	 locbrdgLiveBridgeForwardDelay OBJECT-TYPE
		SYNTAX INTEGER (4..30)
		ACCESS read-only
		STATUS mandatory
		DESCRIPTION "The time spent, in seconds, in the STP listening and
		learning states by the bridge.  This is the current operation value, 
		and is assigned to this bridge by the root bridge if this bridge is
		not the root."
		::= { locbrdg 16 }


	 locbrdgBridgeForwardDelay OBJECT-TYPE
		SYNTAX INTEGER (4..30)
		ACCESS read-write
		STATUS optional
		DESCRIPTION "The time spent in seconds in STP listening and learning
		states by the ports of the bridge.  If this bridge is the root bridge
		then this value is used by all bridges in the network."
		::= { locbrdg 17 }


	 locbrdgDefaultBridgeForwardDelay OBJECT-TYPE
		SYNTAX INTEGER (4..30)
		ACCESS read-write
		STATUS mandatory
		DESCRIPTION "The default value of the forward delay which is stored
		in the non-volatile storage of the bridge.  If this bridge becomes
		the root bridge this will become the forward delay of all bridges 
		in the network."
		::= { locbrdg 18 }


	 locbrdgTopologyChangeCount OBJECT-TYPE
		SYNTAX INTEGER 
		ACCESS read-only
		STATUS mandatory
		DESCRIPTION "The count of the number of STP network topology changes
		since the last bridge reset."
		::= { locbrdg 19 }




locbrdgRangeDataBaseTable   OBJECT IDENTIFIER ::= {locbrdg 20}


--
--  Note that this table is badly defined, i.e. it does not have an index
--  within the table entry itself. However, it may be instanced by row Number,
--  a simple integer, range 1..16
--  
	 locbrdgRangeTable OBJECT-TYPE
		SYNTAX SEQUENCE OF LocbrdgRangeEntry
		ACCESS not-accessible
		STATUS mandatory
		DESCRIPTION "A list of range table entries."
		::= { locbrdgRangeDataBaseTable 1 }


	 locbrdgRangeEntry OBJECT-TYPE
		SYNTAX LocbrdgRangeEntry 
		ACCESS not-accessible
		STATUS mandatory
		DESCRIPTION "Each table entry defines an additional constriction, or
		requisite on frames which are to be forwarded by the bridge.  Whether
		entries in the range table are cause frames to be forwarded or 
		discarded by the bridge depends on the sense of the 'filterMatches'
		variable.
		For a frame to be selected by a range table entry, the source
		address of the frame must have a value between 'sourceLower' and
		'sourceUpper', and its destination address must have a value between
		'destLower' and 'destUpper', and its type field must have a value
		between 'typeLower and 'typeUpper'.
		There are a maximum of 16 range table entries. To set an entry in 
		the table you must supply all the objects in an entry in a Single
		PDU. When a get is performed, only valid entries are returned."
		::= { locbrdgRangeTable  1 }


	 LocbrdgRangeEntry ::= SEQUENCE {
    	    locbrdgSourceLower 	OCTET STRING,
	    	locbrdgSourceUpper 	OCTET STRING,
	    	locbrdgDestLower 	OCTET STRING,
	    	locbrdgDestUpper 	OCTET STRING,
	    	locbrdgTypeLower 	INTEGER,
	        locbrdgTypeUpper 	INTEGER,
			locbrdgRangeType	INTEGER
          }

	 locbrdgSourceLower OBJECT-TYPE
		SYNTAX OCTET STRING ( SIZE (6)) 
		ACCESS read-write
		STATUS mandatory
		DESCRIPTION "The lower bound of source mac addresses which will 
		be passed or filtered by the bridge depending on the sense of 
		filterMatches."
		::= { locbrdgRangeEntry 1 }


	 locbrdgSourceUpper OBJECT-TYPE
		SYNTAX OCTET STRING ( SIZE (6)) 
		ACCESS read-write
		STATUS mandatory
		DESCRIPTION "The upper bound of source mac addresses which will
		be passed or filtered by the bridge depending on the sense of
		filterMarches."
		::= { locbrdgRangeEntry 2 }



	 locbrdgDestLower OBJECT-TYPE
		SYNTAX OCTET STRING ( SIZE (6)) 
		ACCESS read-write
		STATUS mandatory
		DESCRIPTION "The lower bound of destination mac addresses which
		will be passed or filtered by the bridge depending on the sense
		of filterMatches."
		::= { locbrdgRangeEntry 3 }


	 locbrdgDestUpper OBJECT-TYPE
		SYNTAX OCTET STRING ( SIZE (6)) 
		ACCESS read-write
		STATUS mandatory
		DESCRIPTION "The upper bound of destination mac addresses which
		will be passed or filtered by the bridge depending on the sense
		of filterMatches."
		::= { locbrdgRangeEntry 4 }


	 locbrdgTypeLower OBJECT-TYPE
		SYNTAX INTEGER 
		ACCESS read-write
		STATUS mandatory
		DESCRIPTION "The lower bound of type field of mac frames which
		will be passed or filtered by the bridge depending on the sense
		of filterMatches."
		::= { locbrdgRangeEntry 5 }


	 locbrdgTypeUpper OBJECT-TYPE
		SYNTAX INTEGER 
		ACCESS read-write
		STATUS mandatory
		DESCRIPTION "The upper bound of type field of mac frames which
		will be passed or filtered by the bridge depending on the sense
		of filterMatches."
		::= { locbrdgRangeEntry 6 } 
		
	locbrdgRangeType OBJECT-TYPE
		SYNTAX INTEGER {
				valid (1),
				invalid (2)
				}
		ACCESS read-write
		STATUS mandatory
		DESCRIPTION "This defines whether you are adding or deleting an
		entry to/from this table. A value of invalid deletes the existing
		entry."
		::= { locbrdgRangeEntry 7 }


	 locbrdgRangeTablePage OBJECT-TYPE
		SYNTAX OCTET STRING (SIZE (480))
		ACCESS read-only
		STATUS mandatory
		DESCRIPTION "This allows the table to be returned in block form,
		an octet string containing a max. of 16 entries. Each entry
		consists of 28 bytes and contains the following:-
		Bytes 0-5 destLower, 6-11 destUpper, 12-17 sourceLower,
		Bytes 18-23 sourceUpper, 24-25 typeLower, 26-27 typeUpper.
		The MacAddresses are in hexadecimal form, in network byte order.
		Only complete entries are returned"
		::= { locbrdgRangeDataBaseTable 2 }

	 locbrdgRangeTableAction OBJECT-TYPE
		SYNTAX INTEGER {
				clear (1)
				}
		ACCESS write-only
		STATUS mandatory
		DESCRIPTION "Writing a 1 to this variable will cause the
		clearing of the range table."
		::= { locbrdgRangeDataBaseTable 3 }

	locbrdgFilterDataBaseTable   OBJECT IDENTIFIER ::= {locbrdg 21}


	 locbrdgFilterTable OBJECT-TYPE
		SYNTAX SEQUENCE OF LocbrdgFilterEntry
		ACCESS not-accessible
		STATUS mandatory
		DESCRIPTION "A list of filtering data base entries."
		::= { locbrdgFilterDataBaseTable 1 }


	 locbrdgFilterEntry OBJECT-TYPE
		SYNTAX LocbrdgFilterEntry
		ACCESS not-accessible
		STATUS mandatory
		DESCRIPTION "This OCTET STRING contains on entry from the table. 
		Each entry consists of a MAC address, filter disposition, filter
		status and type. All of these objects must be supplied in a single
		PDU when setting an entry. Only valid entries are returned on a
		GetRequest."
		INDEX { locbrdgFilterEntryMacAddress }
		::= { locbrdgFilterTable 1 }

	-- filter data base table

     	LocbrdgFilterEntry ::= SEQUENCE {
          	locbrdgFilterEntryMacAddress OCTET STRING,
          	locbrdgFilterEntryDisposition INTEGER,
          	locbrdgFilterEntryStatus INTEGER,
          	locbrdgFilterEntryType INTEGER
          	}

	 locbrdgFilterEntryMacAddress OBJECT-TYPE
		SYNTAX OCTET STRING ( SIZE (6))
		ACCESS read-write
		STATUS mandatory
		DESCRIPTION "This OCTET STRING contains the MAC address in
		hexadecimal form, in network byte order."
		::= { locbrdgFilterEntry 1 }



	 locbrdgFilterEntryDisposition OBJECT-TYPE
		SYNTAX INTEGER {
				flood (1),
				discard(2),
				forwardToA (3),
				forwardToB (4)
				}
		ACCESS read-write
		STATUS mandatory
		DESCRIPTION "This is the action taken as aresult of a MacAddress
		match. A and B refer to Channel A and Channel B."
		::= { locbrdgFilterEntry 2 }

	 locbrdgFilterEntryStatus OBJECT-TYPE
		SYNTAX INTEGER {
			dynamicActive (1),
			dynamicInactive (2),
			staticActive (3),
			staticInactive (4)
			}
		ACCESS read-only
		STATUS mandatory
		DESCRIPTION
			"This is the status type of the entry. "
		::= { locbrdgFilterEntry 3 }

	 locbrdgFilterEntryType OBJECT-TYPE
		SYNTAX INTEGER{
			valid (1),
			invalid (2)
			}
		ACCESS read-write
		STATUS mandatory
		DESCRIPTION "This object is used to add and delete entries
		to/from the table. A value of 'invalid(2)' deletes the entry."
		::= { locbrdgFilterEntry 4 }

	 locbrdgFilterAction OBJECT-TYPE
		SYNTAX INTEGER{
				clearTable(1)
				}
		ACCESS write-only
		STATUS mandatory
		DESCRIPTION "This object when set, results in a reinitialisation
		of the table, it clears all the entries out."
		::= { locbrdgFilterDataBaseTable 2 }

--
-- Another dodgy bit of SNMP! This should also have an index within the 
-- SEQUENCE struct. It can be indexed by a simple integer, the page No.
-- The No. of pages depends on the Number of entries in the table.
-- Each Page can hold up to 80 entries.
--
	 locbrdgFilterPage OBJECT-TYPE
		SYNTAX SEQUENCE OF LocbrdgFilterPageValue
		ACCESS not-accessible
		STATUS mandatory
		DESCRIPTION "A list of 'paged' entries from the filtering data
		base table."
		::= { locbrdgFilterDataBaseTable 3 }

     	LocbrdgFilterPageValue ::= SEQUENCE {
          	locbrdgFilterPage OCTET STRING ( SIZE (0..640))
          	}

	 locbrdgFilterPageValue OBJECT-TYPE
		SYNTAX OCTET STRING ( SIZE (0..640))
		ACCESS read-only
		STATUS mandatory
		DESCRIPTION "This is the bulk representation of the table.
		Each Page contains 80 table entries, each entry is 8 bytes
		long and is in the form :-
		Bytes  0-5 - MAC address, 6 - Disposition, 7 - Status."
		::= { locbrdgFilterPage 1 }

	 locbrdgLiveSpatHelloTimer OBJECT-TYPE
		SYNTAX INTEGER
		ACCESS read-only
		STATUS mandatory
		DESCRIPTION "The spanning tree hello time, in seconds.  This the
		current operational value and will be the same as the initial 
		hello time of the root bridge of the network."
		::= { locbrdg 24 }

	 locbrdgLiveMaxAge OBJECT-TYPE
		SYNTAX INTEGER
		ACCESS read-only
		STATUS mandatory
		DESCRIPTION "The maximum elapsed time, in seconds, that a received
		STP protocol message can exist before it is discarded by the bridge. 
		If this is the root bridge this value is used as the operational 
		value by all bridges.  This is the current operational value and 
		will be the same as the initial Max Age of the root bridge of the 
		network."
		::= { locbrdg 25 }

	 locbrdgDefaultHoldTime OBJECT-TYPE
		SYNTAX INTEGER
		ACCESS read-write
		STATUS mandatory
		DESCRIPTION "After this time in seconds unacknowledged bpdus will
		be resent.This is the value stored in non volatile storage of the
		bridge, ans will used to initialise the locbrdgHoldTime after the 
		next power up."
		::= { locbrdg 26 }

	 locbrdgPriority OBJECT-TYPE
		SYNTAX INTEGER
		ACCESS read-write
		STATUS mandatory
		DESCRIPTION "The spanning tree priority of the bridge.  This value
		is the current operating value.  The value has been set by the
		manager, or was copied from the default value in EEPROM the last
		time the bridge powered up - see 'locbrdgDefaultPriority'."
		::= { locbrdg 27 }

	 locbrdgDefaultPriority OBJECT-TYPE
		SYNTAX INTEGER
		ACCESS read-write
		STATUS mandatory
		DESCRIPTION "The default spanning tree priority of the bridge. 
		This is the value stored in the EEPROM of the system, and will
		be copied into RAM, and be the operational value of the system
		the next time the system is reset."
		::= { locbrdg 28 }

		  END
