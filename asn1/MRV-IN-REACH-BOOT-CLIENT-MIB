-- $Id: ir-boot-client-mib.mib,v 1.1 2002/06/27 15:40:14 sse Exp $
MRV-IN-REACH-BOOT-CLIENT-MIB DEFINITIONS ::= BEGIN

                    IMPORTS
                            DisplayString
                                    FROM RFC1213-MIB
                            OBJECT-TYPE
                                    FROM RFC-1212
	                    mrvInReachProductDivision
                               FROM MRV-IN-REACH-PRODUCT-DIVISION-MIB;

            xBootClient     OBJECT IDENTIFIER ::= { mrvInReachProductDivision 12 }

            --  This is the MIB module for clients of MRV In-Reach bootstrap
            --  service.

            -- Copyright 2002 MRV Communications, Inc. All Rights Reserved.
            -- Reproduction of this document is authorized on
            -- condition that this copyright notice is included.
            -- This MIB document embodies MRV Communications, Inc.'s 
            -- proprietary intellectual property.  MRV Communications, Inc.
            -- retains all title and ownership in this MIB, including any
            -- revisions.
            --
            -- It is MRV Communications, Inc.'s intent to encourage the
            -- widespread use of this MIB in connection with the management of
            -- MRV Communications, Inc. products. MRV Communications,
            -- Inc. grants vendors,end-users, and other interested parties a
            -- non-exclusive license to use this MIB in connection with the
            -- management of MRV Communications, Inc. products.
            --
            -- This MIB document is supplied "AS IS," and MRV 
            -- Communications, Inc. makes no warranty, either express or
            -- implied, as to the use operation, condition, or performance of
            -- the MIB.


            -- the Bootstrap Client group

            -- Implementation of this group is mandatory for all MRV In-Reach
            -- systems that use the MRV In-Reach bootstrap service

            bootClientStatus OBJECT-TYPE
                SYNTAX DisplayString (SIZE (0..1400))
                ACCESS read-only
                STATUS mandatory
                DESCRIPTION
                    "The overall status of the bootstrapping operation, 
                    including, for example, what is presently happening 
                    and error information."
                ::= { xBootClient 1 }

END
