CXLapBConv-MIB DEFINITIONS ::= BEGIN


IMPORTS
   Counter         FROM RFC1155-SMI
   OBJECT-TYPE     FROM RFC-1212
   cxLapBConv,SapIndex,Alias
            FROM CXProduct-SMI;

-- Proprietary Data Types
PSapIndex       ::=     INTEGER (0..255)
SubRef  ::=     INTEGER (0..255)



lapbcnvSysRouteConnectInterval OBJECT-TYPE
   SYNTAX  INTEGER (10..900)
   ACCESS  read-write
   STATUS  mandatory
   DESCRIPTION
"Determines the number of seconds between attempts to establish a 
connection for a LAPB system route. A connection is attempted only for 
defined non-connected routes.

Range of Values: 10 - 900 seconds

Default Value: 30 seconds

Configuration Changed: administrative and operative"
   DEFVAL {30 }
   ::= { cxLapBConv 1 }

-- gap (9) for future global parameters



--  Service Access Point Configuration Table

--  The table describing:
--      parameters required to configure a LAPB convergence service access 
--      point
--
--      controls available to manipulate a LAPB convergence service access 
--      point
--
--      status available for monitoring the LAPB convergence service access 
--      point
--      statistics available for monitoring any LAPB convergence service 
--      access point

--  Service access points of this type exist at the upper interface of the 
--  LAPB
--  Convergence layer, and are used to communicate with the LAPBD or 
--  IAM layers.


lapbcnvSapTable OBJECT-TYPE
   SYNTAX  SEQUENCE OF LapbcnvSapEntry
   ACCESS  not-accessible
   STATUS  mandatory
   DESCRIPTION
"A table containing configuration information about each LAPB convergence 
service access point. Service access points of this type exist at the 
upper interface of the LAPB Convergence layer, and are used to communicate 
with the LAPBD or IAM layers."
   ::= { cxLapBConv 10 }


   lapbcnvSapEntry OBJECT-TYPE
      SYNTAX  LapbcnvSapEntry
      ACCESS  not-accessible
      STATUS  mandatory
      DESCRIPTION
"Defines a row in the Service Access Point Configuration table. Each row 
contains the objects which are used to define a service access point upper 
interface of the LAPB Convergence layer."
      INDEX { lapbcnvSapNumber }
      ::= { lapbcnvSapTable 1 }


   LapbcnvSapEntry ::=
      SEQUENCE {
-- Parameters
         lapbcnvSapNumber                      PSapIndex,
         lapbcnvSapRowStatus                     INTEGER,
         lapbcnvSapAlias                         Alias,
-- Control
         lapbcnvSapControl                      INTEGER,
-- Status
         lapbcnvSapState                        INTEGER,
-- Statistics
         lapbcnvSapTxFrames                     Counter,
         lapbcnvSapRxFrames                     Counter,
         lapbcnvSapTxOctets                     Counter,
         lapbcnvSapRxOctets                     Counter,
         lapbcnvSapOutSuccessfullConnects       Counter,
         lapbcnvSapOutUnsuccessfullConnects      Counter,
         lapbcnvSapInSuccessfullConnects         Counter,
         lapbcnvSapInUnsuccessfullConnects       Counter,
         lapbcnvSapUnopenedServiceDiscards       Counter,
         lapbcnvSapTxResets                              Counter,
         lapbcnvSapRxResets                              Counter
         }


   lapbcnvSapNumber OBJECT-TYPE
      SYNTAX  PSapIndex
      ACCESS  read-only
      STATUS  mandatory
      DESCRIPTION
"Identifies this SAP (service access point) with a numerical value. Values 
are unique for each service access point."
      ::= { lapbcnvSapEntry 1 }


   lapbcnvSapRowStatus OBJECT-TYPE
      SYNTAX  INTEGER {
               invalid         (1),
               valid           (2)
               }
      ACCESS  read-write
      STATUS  mandatory
      DESCRIPTION
"Determines the status of the objects in a table row.

Options:
invalid (1): Row is deleted from the table immediately, however values are 
still in effect until the next reset. 

valid (2): Use this value to add a new row to the table, or modify an 
existing row.

Default Value: valid (2)

Configuration Changed: administrative"
      ::= { lapbcnvSapEntry 2 }


   lapbcnvSapAlias OBJECT-TYPE
      SYNTAX  Alias
      ACCESS  read-write
      STATUS  mandatory
      DESCRIPTION
"Identifies this service access point by a textual name. Names must be 
unique across all service access points at all layers. 

Range of Values: 1 -16 alphanumeric characters (first character must be a 
letter)

Default Value: none

Configuration Changed: administrative"
      ::= { lapbcnvSapEntry 3 }

   lapbcnvSapControl OBJECT-TYPE
      SYNTAX  INTEGER {
               clearStats              (1)
               }
      ACCESS  write-only
      STATUS  mandatory
      DESCRIPTION
"Permits control of a specific SAP (service access point).

Options:
clearStats (1): Clear all statistics stored by statistics objects.

Configuration Changed: operative"
      ::= { lapbcnvSapEntry 5 }


   lapbcnvSapState OBJECT-TYPE
      SYNTAX  INTEGER {
               offLine         (1),
               unbound         (2),
               notConnected            (3),
               inProgress              (4),
               connected               (5)
               }
      ACCESS  read-only
      STATUS  mandatory
      DESCRIPTION
"Indicates the current state of this SAP (service access point).

Options:
offLine (1): Indicates a newly created service access point whose 
configuration has not yet been sent to the LAPB Convergence layer.

unbound (2): SAP is not yet bound to its companion SAP at an upper layer.

notConnected (3): The associated route with this SAP is not connected, or 
there is no route associated with this SAP.

inProgress (4): The associated route is in the process of connecting. 

connected (5): The associated route is connected."
      DEFVAL { unbound }
      ::= { lapbcnvSapEntry 6 }


   lapbcnvSapTxFrames OBJECT-TYPE
      SYNTAX  Counter
      ACCESS  read-only
      STATUS  mandatory
      DESCRIPTION
"Indicates the number of frames transmitted by this service access point."
      ::= { lapbcnvSapEntry 7 }


   lapbcnvSapRxFrames OBJECT-TYPE
      SYNTAX  Counter
      ACCESS  read-only
      STATUS  mandatory
      DESCRIPTION
"Indicates the number of frames received by this service access point."
      ::= { lapbcnvSapEntry 8 }


   lapbcnvSapTxOctets OBJECT-TYPE
      SYNTAX  Counter
      ACCESS  read-only
      STATUS  mandatory
      DESCRIPTION
"Indicates the number of octets transmitted by this service access point."
      ::= { lapbcnvSapEntry 9 }


   lapbcnvSapRxOctets OBJECT-TYPE
      SYNTAX  Counter
      ACCESS  read-only
      STATUS  mandatory
      DESCRIPTION
"Indicates the number of octets received by this service access point."
      ::= { lapbcnvSapEntry 10 }


   lapbcnvSapOutSuccessfullConnects OBJECT-TYPE
      SYNTAX  Counter
      ACCESS  read-only
      STATUS  mandatory
      DESCRIPTION
"Indicates the number of successful outgoing connections established by 
this SAP (service access point). An outgoing connection is always 
attempted from LAPB convergence to the Inter-Application Module (IAM).

At the PSAP, this object represents the total number of outgoing 
connections established by all SAPs. At each individual SAP, this object 
represents the number of outgoing connections established by only that 
SAP."
      ::= { lapbcnvSapEntry 11 }


   lapbcnvSapOutUnsuccessfullConnects OBJECT-TYPE
      SYNTAX  Counter
      ACCESS  read-only
      STATUS  mandatory
      DESCRIPTION
"Indicates the number of unsuccessful outgoing connections attempted by 
this SAP (service access point). An outgoing connection is always 
attempted from LAPB convergence to the Inter-Application Module (IAM).

At the PSAP, this object represents the total number of unsuccessful 
outgoing connections attempted by all SAPs. At each individual SAP, this 
object represents the number of unsuccessful outgoing connections 
attempted by only that SAP."
      ::= { lapbcnvSapEntry 12 }


   lapbcnvSapInSuccessfullConnects OBJECT-TYPE
      SYNTAX  Counter
      ACCESS  read-only
      STATUS  mandatory
      DESCRIPTION
"Indicates the number of successful incoming connections established at 
this SAP (service access point). An incoming connection is always 
attempted from the Inter-Application Module (IAM) to LAPB convergence.

At the PSAP, this object represents the total number of successful 
incoming connections for all SAPs. At each individual SAP, this object 
represents the number of successful incoming connections for only that 
SAP."
      ::= { lapbcnvSapEntry 13 }


   lapbcnvSapInUnsuccessfullConnects OBJECT-TYPE
      SYNTAX  Counter
      ACCESS  read-only
      STATUS  mandatory
      DESCRIPTION
"Indicates the number of unsuccessful incoming connections attempted at 
this SAP (service access point). An incoming connection is always 
attempted from the Inter-Application Module (IAM) to LAPB convergence.

At the PSAP, this object represents the total number of unsuccessful 
incoming connections for all SAPs. At each individual SAP, this object 
represents the number of unsuccessful incoming connections for only that 
SAP."
      ::= { lapbcnvSapEntry 14 }


   lapbcnvSapUnopenedServiceDiscards OBJECT-TYPE
      SYNTAX  Counter
      ACCESS  read-only
      STATUS  mandatory
      DESCRIPTION
"This object applies only to the PSAP (public service access point).

Indicates the number of frames received and discarded by the PSAP because:

- no route was associated with the frame

- the frame was destined for a route that is not connected"
      ::= { lapbcnvSapEntry 15 }


   lapbcnvSapTxResets OBJECT-TYPE
      SYNTAX  Counter
      ACCESS  read-only
      STATUS  mandatory
      DESCRIPTION
"This object applies only to the PSAP (public service access point).

Indicates the number of Inter- Application Module (IAM) reset frames sent 
by the PSAP."
      ::= { lapbcnvSapEntry 16 }


   lapbcnvSapRxResets OBJECT-TYPE
      SYNTAX  Counter
      ACCESS  read-only
      STATUS  mandatory
      DESCRIPTION
"This object applies only to the PSAP.

Indicates the number of Inter- Application Module (IAM) reset frames 
received by the PSAP."
      ::= { lapbcnvSapEntry 17 }


--  LAPB System Route Table

--  The table containing routes permitting LAPB logical links to be 
--   established between:
--
--    The LAPB layer on this card and the LAPB layer on another similar card
--    within the same chassis (future use within CX1000).
--
--    The LAPBD layer on this card and a LAPB DTE/DCE across the frame
--    relay network.


lapbcnvSysRouteTable OBJECT-TYPE
   SYNTAX  SEQUENCE OF LapbcnvSysRouteEntry
   ACCESS  not-accessible
   STATUS  mandatory
   DESCRIPTION
"A table containing information about each LAPB system route. Routes allow 
this LAPB/D layer to link with another LAPB/D layer across a frame relay 
network, or with the LAPB layer on another similar card in the same 
chassis (for future use with the CX1000)."
   ::= { cxLapBConv 11 }


   lapbcnvSysRouteEntry OBJECT-TYPE
      SYNTAX  LapbcnvSysRouteEntry
      ACCESS  not-accessible
      STATUS  mandatory
      DESCRIPTION
"Defines a row in the lapbcnvSysRouteTable. Each row contains the objects 
which define a system route."
      INDEX { lapbcnvSRSapNumber }
      ::= { lapbcnvSysRouteTable 1 }


   LapbcnvSysRouteEntry ::=
      SEQUENCE {
         lapbcnvSRSapNumber                SapIndex,
         lapbcnvSRRowStatus                INTEGER,
         lapbcnvSRDestAlias                Alias,
         lapbcnvSRSubRef                   SubRef,
-- Status
         lapbcnvSRRouteStatus             INTEGER,
         lapbcnvSRClearStatus             INTEGER
         }

   lapbcnvSRSapNumber OBJECT-TYPE
      SYNTAX  SapIndex
      ACCESS  read-only
      STATUS  mandatory
      DESCRIPTION
"Identifies the service access point this route entry is associated with."
      ::= { lapbcnvSysRouteEntry 1 }


   lapbcnvSRRowStatus OBJECT-TYPE
      SYNTAX  INTEGER {
               invalid         (1),
               valid           (2)
               }
      ACCESS  read-write
      STATUS  mandatory
      DESCRIPTION
"Determines the status of the objects in a table row. 

Options:
invalid (1): Row is deleted from the table immediately, however values are 
still in effect until the next reset. 

valid (2): Use this value to add a new row to the table, or modify an 
existing row.

Default Value: none

Configuration Changed: administrative and operative"
      ::= { lapbcnvSysRouteEntry 2 }


   lapbcnvSRDestAlias OBJECT-TYPE
      SYNTAX  Alias
      ACCESS  read-write
      STATUS  mandatory
      DESCRIPTION
"Determines the textual name of the destination service this route 
connects to. When attempting a LAPB connection across Frame Relay, this 
object specifies the name of the outgoing circuit at the Frame Relay 
layer. 

When attempting a LAPB connection between cards within the same chassis 
(future use within CX1000), this object specifies the name of the LAPB 
Convergence SAP on the remote card.

Range of Values: 1 -16 characters (first character must be a letter)

Default Value: none

Configuration Changed: administrative and operative"
      ::= { lapbcnvSysRouteEntry 3 }


   lapbcnvSRSubRef OBJECT-TYPE
      SYNTAX  SubRef
      ACCESS  read-write
      STATUS  mandatory
      DESCRIPTION
"Specifies a reference number that uniquely identifies this route. This 
number is used by the FRIM (Frame Relay Interface Module) to identify 
routes using the same DLCI (enables PVC consolidation). This number must 
be unique for all routes sharing the same DLCI.

Range of Values: 1 - 255 (when using PVC consolidation)

0 (when not using PVC consolidation)

Default Value: 0

Configuration Changed: administrative and operative"
      ::= { lapbcnvSysRouteEntry 4 }


-- gap (5) for future configuration parameters  


   lapbcnvSRRouteStatus OBJECT-TYPE
      SYNTAX  INTEGER {
               offLine         (1),
               notConnected            (2),
               inProgress              (3),
               connected               (4)
               }
      ACCESS  read-only
      STATUS  mandatory
      DESCRIPTION
"Indicates the connection status of this LAPB route.

Options:
offLine (1): Indicates that the LAPB Convergence SAP this route is 
associated with does not exist or is offline.

notConnected (2): Indicates that the remote destination does not exist, or 
has refused the connection.

inProgress (3): Indicates that the connection is in the process of being 
established. This is a transient state.

connected (4): Indicates that the connection is established and is ready 
for data transfer."
      ::= { lapbcnvSysRouteEntry 10 }


   lapbcnvSRClearStatus OBJECT-TYPE
      SYNTAX  INTEGER {
               noFailure                       (1),
               internalError                   (2),
               localAllocFailure               (3),
               remoteAllocFailure              (4),
               localNoAccess                   (5),
               remoteNoAccess          (6),
               localPvcDown                    (7),
               remotePvcDown           (8),
               localPvcBusy                    (9),
               remotePvcBusy           (10),
               localFcnFailure         (11),
               remoteFcnFailure                (12),
               localDsnFailure         (13),
               localRefInUse                   (14),
               remoteAliasNotFound             (15),
               remoteNoPvcService              (16),
               mpeInvalidSubref                (17)

               }
      ACCESS  read-only
      STATUS  mandatory
      DESCRIPTION
"Indicates the status of a failed connection. The value of this object is 
only valid only between attempts to establish the route connection 
(lapbcnvSRRouteStatus = notConnected), and may or may not change after 
successive failed attempts.

Options:
noFailure (1): Once a system route has been successfully connected, this 
value is maintained for the duration of the connection.

internalError (2): An internal error has occurred.

localAllocFailure (3): There is insufficient memory available for LAPB 
Convergence to establish this connection.

remoteAllocFailure (4): There is insufficient memory available for the 
destination protocol layer to establish this connection.

localNoAccess (5): This route is associated with a SAP that does not 
exist.

remoteNoAccess (6): This route is associated with a SAP that does not 
exist at the destination layer.

localPvcDown (7): For future use.

remotePvcDown (8): The PVC at the destination protocol layer is down.

localPvcBusy (9): The SAP associated with this route is already connected.

remotePvcBusy (10): The destination associated with this route is already 
connected. This typically occurs when the route is a non-MPE (PVC 
consolidating) circuit.

localFcnFailure (11): Flow control negotiation failed.

remoteFcnFailure (12): Flow control negotiation failed at the destination 
protocol layer.

localDsnFailure (13): Data size negotiation failed.

localRefInUse (14): Data size negotiation failed at the destination 
protocol layer.

remoteAliasNotFound (15): The destination alias (lapbcnvSRDestAlias) does 
not exist.

remoteNoPvcService (16): The destination protocol layer does not support 
PVC service.

mpeInvalidSubref (17): The value of lapbcnvSRSubRef is invalid at the 
destination protocol layer. (i.e., lapcnvSRSubRef is set to '0' and the 
destination frame relay circuit is configured for PVC consolidation)."
      ::= { lapbcnvSysRouteEntry 11 }


END
