CXFrameRelayATMIWF-MIB DEFINITIONS ::= BEGIN

--#CURRENT_VERSION 0  

IMPORTS
--   Counter, TimeTicks      FROM RFC1155-SMI
   OBJECT-TYPE     FROM RFC-1212
--   TRAP-TYPE       FROM RFC-1215
   cxFrameRelay,SapIndex
          FROM CXProduct-SMI;

-- This MIB file contains the following:
--
-- (1)  Mib Level Object on behalf of GUI version control
--
-- (2)  Global Timer used to specifiy the interval betweem attempts
--      to establish a connection.
--
-- (3) Frame Relay/ATM PVC Network Interworking Table
-- The table is used to
-- 
--      configure mapping modes between Frame Relay Discard Eligibility(DE Bit)
--      and ATM Cell Loss Priority ( CLP Bit ) 
--
--      configure CLP field to be passed to the ATM cell level. 
--
--      monitor the state of FR/ATM connection.

frpAtmIWFMibLevel OBJECT-TYPE
   SYNTAX  INTEGER
   ACCESS  read-only
   STATUS  mandatory
   DESCRIPTION
"Used to determine current MIB module release supported
by the agent. Object is in decimal."
   DEFVAL { 0 }
   --#STARTING_VERSION 0
   ::= { cxFrameRelay 50 }

frpAtmConnectTimer OBJECT-TYPE
      SYNTAX  INTEGER (3..600)
      ACCESS  read-write
      STATUS  mandatory
      DESCRIPTION
"Determines the number of seconds between attempts to establish
a connection for a Frame Relay to ATM circuit mapping.

Configuration Changed: operative"                    
      DEFVAL { 10 }
      ::= { cxFrameRelay 51 }

frpAtmNISapTable OBJECT-TYPE
   SYNTAX  SEQUENCE OF FrpAtmNISapEntry
   ACCESS  not-accessible
   STATUS  mandatory
   DESCRIPTION
"A table containing configuration and state information about
each FR /ATM Network Interworking service access point." 
   REFERENCE
     "The Frame Relay Forum: Document Number FRF.5 "
   ::= { cxFrameRelay 52 }


   frpAtmNISapEntry OBJECT-TYPE
     SYNTAX  FrpAtmNISapEntry
     ACCESS  not-accessible
     STATUS  mandatory
     DESCRIPTION
"The parameters for a particular frame relay/ATM Network Interworking service access point."
     INDEX { frpAtmNISapNumber }
     ::= { frpAtmNISapTable 1 }

     FrpAtmNISapEntry ::=
     SEQUENCE {
        frpAtmNISapNumber              SapIndex,
-- Status
        frpAtmNISapState               INTEGER,
        frpAtmNIFailureReason          INTEGER,   
-- Parameters
        frpAtmNISapDEtoCLPMapping      INTEGER,
        frpAtmNISapCLPtoDEMapping      INTEGER,
        frpAtmNISapCLPBit              INTEGER
      }

 
   frpAtmNISapNumber OBJECT-TYPE
      SYNTAX  SapIndex
      ACCESS  read-only
      STATUS  mandatory
      DESCRIPTION
"Indicates the row containing objects for configuring and monitoring
a FR/ATM connection. The value of the object is the same as the 
SAP in frpSapTable. The row is automatically created when
the object frpSapMode in frpSapTable has the value of 3.
If the value of object frpSapMode is changed to a value 
different than 3, the row will also be deleted automatically. 

Default Value: none"

      ::= { frpAtmNISapEntry 1 }


   frpAtmNISapState OBJECT-TYPE
      SYNTAX  INTEGER
         {
            offLine        (1),
            notConnected   (2),
            inProgress     (3),
            connected      (4),
            connectFlowOff (5)
         }
      ACCESS  read-only
      STATUS  mandatory
      DESCRIPTION
"Identifies the current status of the connection between the FR sap
and the ATM sap.

Options:

offLine (1):  Indicates that the SAP is offline.

notConnected (2): Indicates that the remote destination does not exist, or
                  has refused the connection.

inProgress (3): Indicates that the connection is in the process of being
                established. This is a transient state.

connected (4): Indicates that the connection is established and is ready
               for data transfer.

connectionFlowOff (5): Indicates that the connection is established but
                       data flow has been stopped."
      ::= { frpAtmNISapEntry 2 }

   frpAtmNIFailureReason  OBJECT-TYPE
      SYNTAX  INTEGER
         {
            noFailure			   (1),
            internalError		   (2),
            localAllocFailure		(3),
            remoteAllocFailure	(4),
            localNoAccess		   (5),
            remoteNoAccess		   (6),
            remotePvcDown		   (8),
            remotePvcBusy		   (10),
            localFcnFailure		(11),
            remoteFcnFailure		(12),
            localDsnFailure		(13),
            remoteAliasNotFound	(15),
            remoteNoPvcService	(16),

            routeStalled		   (18)
         }
      ACCESS  read-only
      STATUS  mandatory
      DESCRIPTION
"Indicates the status of a failed connection. The value of this object is 
only valid only between attempts to establish the  connection,
and may or may not change after successive failed attempts.


Options:
noFailure (1): Once a system route has been successfully connected,
               this value is maintained for the duration of the connection.

internalError (2): An internal error has occurred.

localAllocFailure (3): There is insufficient memory available for ATM DXI
                       to establish this connection.

remoteAllocFailure (4): There is insufficient memory available for the destination 
                        protocol layer to establish this connection.

localNoAccess (5): This route is associated with a SAP that does not exist.

remoteNoAccess (6): This route is associated with a SAP that does not exist 
                    at the destination layer.

remotePvcDown (8): The PVC at the destination protocol layer is down.

remotePvcBusy (10): The destination associated with this route is already connected. 
                    This typically occurs when the route is a non-MPE (PVC consolidating)
                    circuit.

localFcnFailure (11): Flow control negotiation failed.

remoteFcnFailure (12): Flow control negotiation failed at the destination protocol layer.

localDsnFailure (13): Data size negotiation failed.

remoteAliasNotFound (15): The destination alias (atmDxiSRDestAlias) does not exist.

remoteNoPvcService (16): The destination protocol layer does not support PVC service.

routeStalled (18): An invalid control packet exchange has occurred during the route 
                   setup procedure.  The route is temporarily stalled but will recover 
                   within 5 seconds."

      ::= { frpAtmNISapEntry 3 }

   frpAtmNISapDEtoCLPMapping OBJECT-TYPE
      SYNTAX  INTEGER {
             mode1   (1),
             mode2   (2)
          }
      ACCESS  read-write
      STATUS  mandatory
      DESCRIPTION
"Determines which mode will be selected for loss priority mapping in
the FR to ATM direction.

Options:
mode1 (1): The Discard Eligibility ( DE ) field in the Q.922 core frame
           shall be copied unchanged into DE field in the FR-SSCS PDU 
           header and mapped to the ATM Cell Loss Priority( CLP ) of 
           every ATM cell generated by the segmentation process of that
           frame.

mode2 (2): The DE field in the Q.922 core frame shall be copied unchanged
           into the DE field in the FR-SSCS PDU header and the ATM Cell
           Loss Priority of every ATM cell generated by the segmentation
           process of that fame shall be set to a constant value( either 0
           or 1 ). The value is decided when the connection is set up, and is used
           for all cell generated from the segmentation process of every frame, 
           until the ATM connect characteristics are changed. 

Default Value: mode1

Configuration Changed: operative"                    
      DEFVAL { mode1 }
      ::= { frpAtmNISapEntry 4 }

   frpAtmNISapCLPtoDEMapping OBJECT-TYPE
      SYNTAX  INTEGER {
             mode1   (1),
             mode2   (2)
          }
      ACCESS  read-write
      STATUS  mandatory
      DESCRIPTION
"Determines which mode will be selected for loss priority mapping in
the ATM to FR direction.

Options:
mode1 (1): If one or more ATM cells belonging to a frame has it's CLP field
           set to one or if the DE field of the FR-SSCS PDU is set to one, 
           the DE field of the Q.922 core frame should be set.

mode2 (2): No mapping is performed from the ATM layer to Q.922 core layer. The
           FR-SSCS PDU DE field is copied unchanged to the Q.922 core frame DE
           field, independent of CLP indications received at the ATM layer.

Default Value: mode1

Configuration Changed: operative"                    
      DEFVAL { mode1 }
      ::= { frpAtmNISapEntry 5 }

   frpAtmNISapCLPBit OBJECT-TYPE
      SYNTAX  INTEGER {
             zero             (1),
             one              (2)
          }
      ACCESS  read-write
      STATUS  mandatory
      DESCRIPTION
"Determines which value of Cell Loss Priority (CLP) will pass 
to the ATM cell level if the mode2 of frpAtmNISapDEtoCLPMapping is
selected. The object is not valid if the mode1 of 
frpAtmNISapDEtoCLPMappingmode is selected.

Options:
zero (1): The CLP bit will be set to 0 at the ATM cell level.

one (2): The CLP bit will be set to 1 at the ATM cell level.

Default Value: zero

Configuration Changed: operative"                    
      DEFVAL { zero }
      ::= { frpAtmNISapEntry 6 }

END
