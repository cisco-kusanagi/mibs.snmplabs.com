--
-- 	Copyright 1996 Shiva Corporation
--

SHIVA-PBURST-MIB DEFINITIONS ::= BEGIN

IMPORTS
	Counter
		FROM RFC1155-SMI
    	OBJECT-TYPE
    		FROM RFC-1212		-- Concise MIB Definitions
	pburst
    		FROM SHIVA-MIB;

-- MIB for the Powerburst accelerator Agent.  Statistics
-- to show how effective the Powerburst caching has been
-- for all sessions since the box was powered-up.

    pBurstIpxNcpAccelReq OBJECT-TYPE
	SYNTAX	Counter
	ACCESS	read-only
	STATUS	mandatory
	DESCRIPTION
		"Total number of IPX NCP requests received by the
		Powerburst accelerator Agent"
	::= { pburst 1 }

    pBurstIpxNcpBytesReq OBJECT-TYPE
	SYNTAX	Counter
	ACCESS	read-only
	STATUS	mandatory
	DESCRIPTION
		"Total number of bytes requested in all IPX NCP
		 requests processed by the Powerburst accelerator Agent"
	::= { pburst 2 }

    pBurstIpxNcpAccel OBJECT-TYPE
	SYNTAX	Counter
	ACCESS	read-only
	STATUS	mandatory
	DESCRIPTION
		"Total number of IPX NCP requests that did not require
		 data transfer due to usage of the Powerburst accelerator"
	::= { pburst 3 }

    pBurstIpxNcpBytes OBJECT-TYPE
	SYNTAX	Counter
	ACCESS	read-only
	STATUS	mandatory
	DESCRIPTION
		"Total number of bytes that did not have to be transmitted
		 due to usage of the Powerburst accelerator"
	::= { pburst 4 }

    pBurstLicenseStatus OBJECT-TYPE
	SYNTAX	INTEGER {
		license-valid(1),
		license-invalid(2),
		unlicensed(3)
	}
	ACCESS	read-only
	STATUS	mandatory
	DESCRIPTION
		"The Powerburst license status"
	::= { pburst 5 }

END
