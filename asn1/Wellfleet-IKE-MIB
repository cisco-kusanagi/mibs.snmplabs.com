Wellfleet-IKE-MIB DEFINITIONS ::= BEGIN


    IMPORTS

      IpAddress, Opaque, Counter
        FROM RFC1155-SMI
      OBJECT-TYPE
        FROM RFC-1212
      DisplayString
        FROM RFC1213-MIB
      wfIKEGroup
        FROM Wellfleet-COMMON-MIB;

    wfIkeDescriptorTable OBJECT-TYPE
        SYNTAX SEQUENCE OF WfIkeDescriptorEntry
        ACCESS not-accessible
        STATUS mandatory
        DESCRIPTION
                "Table of Internet Key Exchange descriptors.
                 The descriptors correspond to IKE Proposals
                 in the IKE RFC."
        ::= { wfIKEGroup 1 }

    wfIkeDescriptorEntry OBJECT-TYPE
        SYNTAX WfIkeDescriptorEntry
        ACCESS not-accessible
        STATUS mandatory
        DESCRIPTION
                "An Internet Key Exchange Descriptor"
        INDEX  { wfIkeDescriptorLocalIpAddr,
                 wfIkeDescriptorPeerIpAddr,
                 wfIkeDescriptorIndex }
        ::= { wfIkeDescriptorTable 1 }

    WfIkeDescriptorEntry ::= SEQUENCE {
       wfIkeDescriptorCreate
         INTEGER,
       wfIkeDescriptorStatus
         INTEGER,
       wfIkeDescriptorLocalIpAddr
         IpAddress,
       wfIkeDescriptorPeerIpAddr
         IpAddress,
       wfIkeDescriptorIndex
         INTEGER,
       wfIkeDescriptorExchange
         INTEGER,
       wfIkeDescriptorProposals
         Opaque,
       wfIkeDescriptorName
         DisplayString,
       wfIkeDescriptorPreSharedSecret
         OCTET STRING,
       wfIkeDescriptorExpiryMinutes
         INTEGER,
       wfIkeDescriptorExpiryKBytes
         INTEGER,
       wfIkeDescriptorExpiryPref
         INTEGER,
       wfIkeDescriptorIdType
         INTEGER
        }

    wfIkeDescriptorCreate OBJECT-TYPE
        SYNTAX INTEGER {
             created(1),
             deleted(2)
        }
        ACCESS read-write
        STATUS mandatory
        DESCRIPTION
                "Create/Delete parameter. Default is created."
        DEFVAL { created }
        ::= { wfIkeDescriptorEntry 1 }

    wfIkeDescriptorStatus OBJECT-TYPE
        SYNTAX INTEGER {
             up(1),
             down(2),
             notpresent(3)
        }
        ACCESS read-only
        STATUS mandatory
        DESCRIPTION
                ""
        DEFVAL { notpresent }
        ::= { wfIkeDescriptorEntry 2 }

    wfIkeDescriptorLocalIpAddr OBJECT-TYPE
        SYNTAX IpAddress
        ACCESS read-only
        STATUS mandatory
        DESCRIPTION
                "The address of the local IP interface to which this
                 instance applies."
        ::= { wfIkeDescriptorEntry 3 }

    wfIkeDescriptorPeerIpAddr OBJECT-TYPE
        SYNTAX IpAddress
        ACCESS read-only
        STATUS mandatory
        DESCRIPTION
                "The address of the remote IP interface to which this
                 instance applies."
        ::= { wfIkeDescriptorEntry 4 }

    wfIkeDescriptorIndex OBJECT-TYPE
        SYNTAX INTEGER
        ACCESS read-only
        STATUS mandatory
        DESCRIPTION
                "Differentiates instances with same peer IP addr"
        ::= { wfIkeDescriptorEntry 5 }

    wfIkeDescriptorExchange OBJECT-TYPE
        SYNTAX INTEGER {
             main(1),
             aggressive(2)
        }
        ACCESS read-write
        STATUS mandatory
        DESCRIPTION
                ""
        DEFVAL { main }
        ::= { wfIkeDescriptorEntry 6 }

    wfIkeDescriptorProposals OBJECT-TYPE
        SYNTAX Opaque
        ACCESS read-write
        STATUS mandatory
        DESCRIPTION
                "an ordered, logically OR'ed list of IKE proposals"
        ::= { wfIkeDescriptorEntry 7 }

      wfIkeDescriptorName OBJECT-TYPE
        SYNTAX DisplayString
        ACCESS read-write
        STATUS mandatory
        DESCRIPTION
                "Name of Ike Descriptor Entry"
        ::= { wfIkeDescriptorEntry 8 }

       wfIkeDescriptorPreSharedSecret OBJECT-TYPE
	SYNTAX  OCTET STRING
        ACCESS  read-write
        STATUS  mandatory
        DESCRIPTION
		"IKE Pre shared secret"
	::= { wfIkeDescriptorEntry 9 }

    wfIkeDescriptorExpiryMinutes OBJECT-TYPE
        SYNTAX INTEGER
        ACCESS read-write
        STATUS mandatory
        DESCRIPTION
                "The value used to determine when the keys for this SA
                 expire due to the passage of time."
        DEFVAL { 480 }
        ::= { wfIkeDescriptorEntry 10 }

    wfIkeDescriptorExpiryKBytes OBJECT-TYPE
        SYNTAX INTEGER
        ACCESS read-write
        STATUS mandatory
        DESCRIPTION
                "The value used to determine when the keys for this SA
                 expire due to the number of bytes processed. The units are
                 kilobytes."
        DEFVAL { 1024 }
        ::= { wfIkeDescriptorEntry 11 }

    wfIkeDescriptorExpiryPref OBJECT-TYPE
        SYNTAX INTEGER {
             minutes(1),
             kbytes(2)
        }
        ACCESS read-write
        STATUS mandatory
        DESCRIPTION
                ""
        DEFVAL { minutes }
        ::= { wfIkeDescriptorEntry 12 }

    wfIkeDescriptorIdType OBJECT-TYPE
        SYNTAX INTEGER {
             range(1),
             subnet(2),
             host(3)
        }
        ACCESS read-write
        STATUS mandatory
        DESCRIPTION
                "Controls the ID type sent in the ID payload. Use subnet if
                 the peer cannot interpret the range type"
        DEFVAL { range }
        ::= { wfIkeDescriptorEntry 13 }

-----------------------
--
-- end of IkeDescriptor
--
-----------------------

    wfIkeTransformTable OBJECT-TYPE
        SYNTAX SEQUENCE OF WfIkeTransformEntry
        ACCESS not-accessible
        STATUS mandatory
        DESCRIPTION
                "Table of Internet Key Exchange Transforms"
        ::= { wfIKEGroup 2 }

    wfIkeTransformEntry OBJECT-TYPE
        SYNTAX WfIkeTransformEntry
        ACCESS not-accessible
        STATUS mandatory
        DESCRIPTION
                "An Internet Key Exchange Transform"
        INDEX  { wfIkeTransformNumber }
        ::= { wfIkeTransformTable 1 }

    WfIkeTransformEntry ::= SEQUENCE {
       wfIkeTransformCreate
         INTEGER,
       wfIkeTransformStatus
         INTEGER,
       wfIkeTransformNumber
         INTEGER,
       wfIkeTransformCipherAlg
         INTEGER,
       wfIkeTransformDesKeyStrength
         INTEGER,
       wfIkeTransformIntegrityAlg
         INTEGER
        }

    wfIkeTransformCreate OBJECT-TYPE
        SYNTAX INTEGER {
             created(1),
             deleted(2)
        }
        ACCESS read-write
        STATUS mandatory
        DESCRIPTION
                "Create/Delete parameter. Default is created."
        DEFVAL { created }
        ::= { wfIkeTransformEntry 1 }

    wfIkeTransformStatus OBJECT-TYPE
        SYNTAX INTEGER {
             up(1),
             down(2),
             notpresent(3)
        }
        ACCESS read-only
        STATUS mandatory
        DESCRIPTION
                ""
        DEFVAL { notpresent }
        ::= { wfIkeTransformEntry 2 }

    wfIkeTransformNumber OBJECT-TYPE
        SYNTAX INTEGER
        ACCESS read-only
        STATUS mandatory
        DESCRIPTION
                ""
        ::= { wfIkeTransformEntry 3 }

    wfIkeTransformCipherAlg OBJECT-TYPE
        SYNTAX INTEGER {
             des(1),
             desede(5)
        }
        ACCESS read-write
        STATUS mandatory
        DESCRIPTION
                ""
        DEFVAL { desede }
        ::= { wfIkeTransformEntry 4 }

    wfIkeTransformDesKeyStrength OBJECT-TYPE
        SYNTAX INTEGER {
             fortybit(1),
             fiftysixbit(2)
        }
        ACCESS read-write
        STATUS mandatory
        DESCRIPTION
                ""
        DEFVAL { fiftysixbit }
        ::= { wfIkeTransformEntry 5 }

    wfIkeTransformIntegrityAlg OBJECT-TYPE
        SYNTAX INTEGER {
             md5(1),
             sha1(2)
        }
        ACCESS read-write
        STATUS mandatory
        DESCRIPTION
                ""
        DEFVAL { sha1 }
        ::= { wfIkeTransformEntry 6 }

-----------------------
--
-- end of IkeTransform
--
-----------------------

    wfIkeSlotTable OBJECT-TYPE
	SYNTAX SEQUENCE OF WfIkeSlotEntry
	ACCESS	not-accessible
	STATUS	mandatory
	DESCRIPTION
	    "Per slot IKE configuration information"
	::= { wfIKEGroup 3 }

    wfIkeSlotEntry OBJECT-TYPE
	SYNTAX WfIkeSlotEntry
	ACCESS	not-accessible
        STATUS	mandatory
        DESCRIPTION
		"Defines per slot cfg info such as log level"
	INDEX { wfIkeSlotNum }
	::= { wfIkeSlotTable 1 }

    WfIkeSlotEntry ::= SEQUENCE {
	wfIkeSlotCreate
		INTEGER,
	wfIkeSlotNum
	 	INTEGER,
	wfIkeSlotLogLevel
		INTEGER
	}

   wfIkeSlotCreate OBJECT-TYPE
        SYNTAX	INTEGER {
    		    created(1),
    		    deleted(2)
    		}
        ACCESS	read-write
        STATUS	mandatory
        DESCRIPTION 
		"Specifies wfIkeEntry instantiation status"
	DEFVAL	{ created }
        ::= { wfIkeSlotEntry 1 }

   wfIkeSlotNum OBJECT-TYPE
	SYNTAX	INTEGER
        ACCESS	read-only
        STATUS	mandatory
        DESCRIPTION
		"The slot number"
	::= { wfIkeSlotEntry 2 }

   wfIkeSlotLogLevel OBJECT-TYPE
	SYNTAX	INTEGER
	ACCESS  read-write
	STATUS	mandatory
	DESCRIPTION
		"Specifies the level(s) of log messages specified"

	DEFVAL  { 0 }
	::= { wfIkeSlotEntry 3 }

-----------------------
--
-- end of IkeSlot
--
-----------------------

    wfIkeSaTable OBJECT-TYPE
        SYNTAX  SEQUENCE OF WfIkeSaEntry
        ACCESS  not-accessible
        STATUS  mandatory
        DESCRIPTION
                "The IKE security association table"
        ::= { wfIKEGroup 4 }

    wfIkeSaEntry OBJECT-TYPE
        SYNTAX  WfIkeSaEntry
        ACCESS  not-accessible
        STATUS  mandatory
        DESCRIPTION
                "Entry in IKE security association table"
        INDEX   { wfIkeSaSrc,
                  wfIkeSaDest,
                  wfIkeSaIndex }
        ::= { wfIkeSaTable 1 }

    WfIkeSaEntry ::= SEQUENCE {
      wfIkeSaCreate
        INTEGER,
      wfIkeSaSrc
        IpAddress,
      wfIkeSaDest
        IpAddress,
      wfIkeSaIndex
        INTEGER,
      wfIkeSaCipherAlg
        INTEGER,
      wfIkeSaIntegrityAlg
        INTEGER,
      wfIkeSaExpiryUnits
        INTEGER,
      wfIkeSaExpiryValue
        INTEGER,
      wfIkeSaBadDecrypt
        Counter,
      wfIkeSaBadPad
        Counter,
      wfIkeSaTxPkts
        Counter,
      wfIkeSaRxPkts
        Counter,
      wfIkeSaTxOctets
        Counter,
      wfIkeSaRxOctets
        Counter
      }

    wfIkeSaCreate OBJECT-TYPE
        SYNTAX  INTEGER {
                created(1),
                deleted(2)
        }
        ACCESS  read-only
        STATUS  mandatory
        DESCRIPTION
                "Create/Delete parameter."
        ::= { wfIkeSaEntry 1 }

    wfIkeSaSrc OBJECT-TYPE
        SYNTAX  IpAddress
        ACCESS  read-only
        STATUS  mandatory
        DESCRIPTION
                "The IP address of the SA's source."
        ::= { wfIkeSaEntry 2 }

    wfIkeSaDest OBJECT-TYPE
        SYNTAX  IpAddress
        ACCESS  read-only
        STATUS  mandatory
        DESCRIPTION
                "The IP address of the SA's destination."
        ::= { wfIkeSaEntry 3 }

    wfIkeSaIndex OBJECT-TYPE
        SYNTAX  INTEGER
        ACCESS  read-only
        STATUS  mandatory
        DESCRIPTION
                "The index that differentiates IKE SAs"
        ::= { wfIkeSaEntry 4 }

    wfIkeSaCipherAlg OBJECT-TYPE
        SYNTAX  INTEGER {
                des(2),
                des3(3)
        }
        ACCESS  read-only
        STATUS  mandatory
        DESCRIPTION
                "Identifies cipher algorithm for this SA."
        ::= { wfIkeSaEntry 5 }

    wfIkeSaIntegrityAlg OBJECT-TYPE
        SYNTAX  INTEGER {
                md5(2),
                sha1(3)
        }
        ACCESS  read-only
        STATUS  mandatory
        DESCRIPTION
                "The algorithm for ESP Auth."
        ::= { wfIkeSaEntry 6 }

    wfIkeSaExpiryUnits OBJECT-TYPE
        SYNTAX  INTEGER {
                minutes(1),
                kilobytes(2)
                }
        ACCESS  read-only
        STATUS  mandatory
        DESCRIPTION
                "The units used to interpret the expiry value."
        ::= { wfIkeSaEntry 7 }

    wfIkeSaExpiryValue OBJECT-TYPE
        SYNTAX  INTEGER
        ACCESS  read-only
        STATUS  mandatory
        DESCRIPTION
                "The value used to determine when the keys for this SA
                 expire."
        ::= { wfIkeSaEntry 8 }

    wfIkeSaBadDecrypt OBJECT-TYPE
        SYNTAX  Counter
        ACCESS  read-only
        STATUS  mandatory
        DESCRIPTION
                "The number of received packets that could 
                not be properly decrypted."
        ::= { wfIkeSaEntry 9 }

    wfIkeSaBadPad OBJECT-TYPE
        SYNTAX  Counter
        ACCESS  read-only
        STATUS  mandatory
        DESCRIPTION
                "The number of received packets that contained
                bad padding information."
        ::= { wfIkeSaEntry 10 }

    wfIkeSaTxPkts OBJECT-TYPE
        SYNTAX  Counter
        ACCESS  read-only
        STATUS  mandatory
        DESCRIPTION
                "The number of packets sent."
        ::= { wfIkeSaEntry 11 }

    wfIkeSaRxPkts OBJECT-TYPE
        SYNTAX  Counter
        ACCESS  read-only
        STATUS  mandatory
        DESCRIPTION
                "The number of packets received." 
        ::= { wfIkeSaEntry 12 }

    wfIkeSaTxOctets OBJECT-TYPE
        SYNTAX  Counter
        ACCESS  read-only
        STATUS  mandatory
        DESCRIPTION
                "The number of octets transmitted."
        ::= { wfIkeSaEntry 13 }

    wfIkeSaRxOctets OBJECT-TYPE
        SYNTAX  Counter
        ACCESS  read-only
        STATUS  mandatory
        DESCRIPTION
                "The number of octets received."
        ::= { wfIkeSaEntry 14 }

-----------------------
--
-- end of IpsecSaTable
--
-----------------------


 END  -- Wellfleet-IKE-MIB
