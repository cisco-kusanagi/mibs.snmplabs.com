H3530-MIB DEFINITIONS ::= BEGIN


IMPORTS
	enterprises
		FROM RFC1155-SMI
	OBJECT-TYPE
		FROM RFC-1212;
  
  DisplayString ::= OCTET STRING


comet         OBJECT IDENTIFIER ::= { enterprises 22626 }
products      OBJECT IDENTIFIER ::= { comet 1 }
h3530         OBJECT IDENTIFIER ::= { products 2 }
readings      OBJECT IDENTIFIER ::= { h3530 1 }
settings      OBJECT IDENTIFIER ::= { h3530 2 }
readingsint   OBJECT IDENTIFIER ::= { h3530 3 }
settingsint   OBJECT IDENTIFIER ::= { h3530 4 }
traps         OBJECT IDENTIFIER ::= { h3530 5 }
tables	      OBJECT IDENTIFIER ::= { h3530 6 }


-----------------------------------------------------------------------
-- readings
-----------------------------------------------------------------------
temperature OBJECT-TYPE
	SYNTAX  	DisplayString (SIZE (0..8))
	ACCESS		read-only
	STATUS		mandatory
	DESCRIPTION	"Temperature"
::= { readings 1 }

humidity OBJECT-TYPE
	SYNTAX  	DisplayString (SIZE (0..8))
	ACCESS		read-only
	STATUS		mandatory
	DESCRIPTION	"Humidity"
::= { readings 2 }

computedValue OBJECT-TYPE
	SYNTAX  	DisplayString (SIZE (0..8))
	ACCESS		read-only
	STATUS		mandatory
	DESCRIPTION	"Computed value"
::= { readings 3 }

relay1 OBJECT-TYPE
	SYNTAX  	INTEGER (0..65535)
	ACCESS		read-only
	STATUS		mandatory
	DESCRIPTION	"Relay 1 status"
::= { readings 5 }

relay2 OBJECT-TYPE
	SYNTAX  	INTEGER (0..65535)
	ACCESS		read-only
	STATUS		mandatory
	DESCRIPTION	"Relay 2 status"
::= { readings 6 }

input1 OBJECT-TYPE
	SYNTAX  	INTEGER (0..65535)
	ACCESS		read-only
	STATUS		mandatory
	DESCRIPTION	"Binary Input 1"
::= { readings 7 }

input2 OBJECT-TYPE
	SYNTAX  	INTEGER (0..65535)
	ACCESS		read-only
	STATUS		mandatory
	DESCRIPTION	"Binary Input 2"
::= { readings 8 }

input3 OBJECT-TYPE
	SYNTAX  	INTEGER (0..65535)
	ACCESS		read-only
	STATUS		mandatory
	DESCRIPTION	"Binary Input 3"
::= { readings 9 }


-----------------------------------------------------------------------
-- settings
-----------------------------------------------------------------------
tempLow OBJECT-TYPE
	SYNTAX  	DisplayString (SIZE (0..8))
	ACCESS		read-only
	STATUS		mandatory
	DESCRIPTION	"Temperature Limit Low"
::= { settings 1 }

tempHigh OBJECT-TYPE
	SYNTAX  	DisplayString (SIZE (0..8))
	ACCESS		read-only
	STATUS		mandatory
	DESCRIPTION	"Temperature Limit High"
::= { settings 2 }

humidityLow OBJECT-TYPE
	SYNTAX  	DisplayString (SIZE (0..8))
	ACCESS		read-only
	STATUS		mandatory
	DESCRIPTION	"Humidity Limit Low"
::= { settings 3 }

humidityHigh OBJECT-TYPE
	SYNTAX  	DisplayString (SIZE (0..8))
	ACCESS		read-only
	STATUS		mandatory
	DESCRIPTION	"Humidity Limit High"
::= { settings 4 }

cvLow OBJECT-TYPE
	SYNTAX  	DisplayString (SIZE (0..8))
	ACCESS		read-only
	STATUS		mandatory
	DESCRIPTION	"Computed Value Limit Low"
::= { settings 5 }

cvHigh OBJECT-TYPE
	SYNTAX  	DisplayString (SIZE (0..8))
	ACCESS		read-only
	STATUS		mandatory
	DESCRIPTION	"Computed Value Limit High"
::= { settings 6 }

tempTime OBJECT-TYPE
	SYNTAX		INTEGER (0..65535)
	ACCESS		read-only
	STATUS		mandatory
	DESCRIPTION	"Temperature alaram delay"
::= { settings 7 }

humidityTime OBJECT-TYPE
	SYNTAX		INTEGER (0..65535)
	ACCESS		read-only
	STATUS		mandatory
	DESCRIPTION	"Humidity alaram delay"
::= { settings 8 }

cvTime OBJECT-TYPE
	SYNTAX		INTEGER (0..65535)
	ACCESS		read-only
	STATUS		mandatory
	DESCRIPTION	"Computed value alaram delay"
::= { settings 9 }

tempHyst OBJECT-TYPE
	SYNTAX  	DisplayString (SIZE (0..8))
	ACCESS		read-only
	STATUS		mandatory
	DESCRIPTION	"Temperature hysteresis"
::= { settings 10 }

humidityHyst OBJECT-TYPE
	SYNTAX  	DisplayString (SIZE (0..8))
	ACCESS		read-only
	STATUS		mandatory
	DESCRIPTION	"Humidity hysteresis"
::= { settings 11 }

cvHyst OBJECT-TYPE
	SYNTAX  	DisplayString (SIZE (0..8))
	ACCESS		read-only
	STATUS		mandatory
	DESCRIPTION	"Computed value hysteresis"
::= { settings 12 }

relay1Alarm OBJECT-TYPE
	SYNTAX  	DisplayString (SIZE (0..8))
	ACCESS		read-only
	STATUS		mandatory
	DESCRIPTION	"Rrelay 1 alarm"
::= { settings 17 }

relay2Alarm OBJECT-TYPE
	SYNTAX  	DisplayString (SIZE (0..8))
	ACCESS		read-only
	STATUS		mandatory
	DESCRIPTION	"Rrelay 2 alarm"
::= { settings 18 }

relay1Hyst OBJECT-TYPE
	SYNTAX  	DisplayString (SIZE (0..8))
	ACCESS		read-only
	STATUS		mandatory
	DESCRIPTION	"Relay 1 hysteresis"
::= { settings 19 }

relay2Hyst OBJECT-TYPE
	SYNTAX  	DisplayString (SIZE (0..8))
	ACCESS		read-only
	STATUS		mandatory
	DESCRIPTION	"Relay 2 hysteresis"
::= { settings 20 }

relay1Time OBJECT-TYPE
	SYNTAX		INTEGER (0..65535)
	ACCESS		read-only
	STATUS		mandatory
	DESCRIPTION	"Relay 1 alaram delay"
::= { settings 21 }

relay2Time OBJECT-TYPE
	SYNTAX		INTEGER (0..65535)
	ACCESS		read-only
	STATUS		mandatory
	DESCRIPTION	"Relay 2 alaram delay"
::= { settings 22 }

input1Time OBJECT-TYPE
	SYNTAX		INTEGER (0..65535)
	ACCESS		read-only
	STATUS		mandatory
	DESCRIPTION	"Binary Input 1 alaram delay"
::= { settings 23 }

input2Time OBJECT-TYPE
	SYNTAX		INTEGER (0..65535)
	ACCESS		read-only
	STATUS		mandatory
	DESCRIPTION	"Binary Input 2 alaram delay"
::= { settings 24 }

input3Time OBJECT-TYPE
	SYNTAX		INTEGER (0..65535)
	ACCESS		read-only
	STATUS		mandatory
	DESCRIPTION	"Binary Input 3 alaram delay"
::= { settings 25 }


-----------------------------------------------------------------------
-- readingsint
-----------------------------------------------------------------------
temperaturei OBJECT-TYPE
	SYNTAX  	INTEGER(-2000..6000)
	ACCESS		read-only
	STATUS		mandatory
	DESCRIPTION	"Temperature *10"
::= { readingsint 1 }

humidityi OBJECT-TYPE
	SYNTAX  	INTEGER(0..1000)
	ACCESS		read-only
	STATUS		mandatory
	DESCRIPTION	"Humidity *10"
::= { readingsint 2 }

cvi OBJECT-TYPE
	SYNTAX  	INTEGER(-2000..6000)
	ACCESS		read-only
	STATUS		mandatory
	DESCRIPTION	"Computed Value *10"
::= { readingsint 3 }


-----------------------------------------------------------------------
-- settingsint
-----------------------------------------------------------------------
tempLowi OBJECT-TYPE
	SYNTAX  	INTEGER(0..65535)
	ACCESS		read-write
	STATUS		mandatory
	DESCRIPTION	"Temperature Limit Low *10"
::= { settingsint 1 }

tempHighi OBJECT-TYPE
	SYNTAX  	INTEGER(-2000..6000)
	ACCESS		read-write
	STATUS		mandatory
	DESCRIPTION	"Temperature Limit High *10"
::= { settingsint 2 }

humidityLowi OBJECT-TYPE
	SYNTAX  	INTEGER(-2000..6000)
	ACCESS		read-write
	STATUS		mandatory
	DESCRIPTION	"Humidity Limit Low *10"
::= { settingsint 3 }

humidityHighi OBJECT-TYPE
	SYNTAX  	INTEGER(-2000..6000)
	ACCESS		read-write
	STATUS		mandatory
	DESCRIPTION	"Humidity Limit High *10"
::= { settingsint 4 }

cvLowi OBJECT-TYPE
	SYNTAX  	INTEGER(-2000..6000)
	ACCESS		read-write
	STATUS		mandatory
	DESCRIPTION	"Computed value Limit Low *10"
::= { settingsint 5 }

cvHighi OBJECT-TYPE
	SYNTAX  	INTEGER(-2000..6000)
	ACCESS		read-write
	STATUS		mandatory
	DESCRIPTION	"Computed value Limit High *10"
::= { settingsint 6 }

tempTimei OBJECT-TYPE
	SYNTAX		INTEGER (0..65535)
	ACCESS		read-write
	STATUS		mandatory
	DESCRIPTION	"Temperature alaram delay"
::= { settingsint 7 }

humidityTimei OBJECT-TYPE
	SYNTAX		INTEGER (0..65535)
	ACCESS		read-write
	STATUS		mandatory
	DESCRIPTION	"Humidity alaram delay"
::= { settingsint 8 }

cvTimei OBJECT-TYPE
	SYNTAX		INTEGER (0..65535)
	ACCESS		read-write
	STATUS		mandatory
	DESCRIPTION	"Computed value alaram delay"
::= { settingsint 9 }

tempHysti OBJECT-TYPE
	SYNTAX  	INTEGER(-2000..6000)
	ACCESS		read-write
	STATUS		mandatory
	DESCRIPTION	"Temperature hysteresis *10"
::= { settingsint 10 }

humidityHysti OBJECT-TYPE
	SYNTAX  	INTEGER(-2000..6000)
	ACCESS		read-write
	STATUS		mandatory
	DESCRIPTION	"Humidity hysteresis *10"
::= { settingsint 11 }

cvHysti OBJECT-TYPE
	SYNTAX  	INTEGER(-2000..6000)
	ACCESS		read-write
	STATUS		mandatory
	DESCRIPTION	"Computed value hysteresis *10"
::= { settingsint 12 }

input1Timei OBJECT-TYPE
	SYNTAX		INTEGER (0..65535)
	ACCESS		read-write
	STATUS		mandatory
	DESCRIPTION	"Binary Input 1 alaram delay"
::= { settingsint 17 }

input2Timei OBJECT-TYPE
	SYNTAX		INTEGER (0..65535)
	ACCESS		read-write
	STATUS		mandatory
	DESCRIPTION	"Binary Input 2 alaram delay"
::= { settingsint 18 }

input3Timei OBJECT-TYPE
	SYNTAX		INTEGER (0..65535)
	ACCESS		read-write
	STATUS		mandatory
	DESCRIPTION	"Binary Input 3 alaram delay"
::= { settingsint 19 }


-----------------------------------------------------------------------
-- settings
-----------------------------------------------------------------------
messageString OBJECT-TYPE
	SYNTAX		DisplayString (SIZE (0..30))
	ACCESS		read-only
	STATUS		mandatory
	DESCRIPTION	"Message giving more detailed information on alarms."
::= { traps 1 }

alarmTemperature OBJECT-TYPE
	SYNTAX  	INTEGER(0..2)
	ACCESS		read-only
	STATUS		mandatory
	DESCRIPTION	"Temperature alarm
0 = Temperature OK
1 = Temperature too high
2 = Temperature too low"
::= { traps 2 }


alarmHumidity OBJECT-TYPE
	SYNTAX  	INTEGER(0..2)
	ACCESS		read-only
	STATUS		mandatory
	DESCRIPTION	"Humidity alarm
0 = Humidity OK
1 = Humidity too high
2 = Humidity too low"
::= { traps 3 }

alarmCv OBJECT-TYPE
	SYNTAX  	INTEGER(0..2)
	ACCESS		read-only
	STATUS		mandatory
	DESCRIPTION	"Computed value alarm
0 = Computed value OK
1 = Computed value too high
2 = Computed value too low"
	::= { traps 4 }


-----------------------------------------------------------------------
-- history
-----------------------------------------------------------------------
historyTable OBJECT-TYPE
	SYNTAX  SEQUENCE OF HistoryEntry
	ACCESS  not-accessible
	STATUS  mandatory
	DESCRIPTION	"Table of the history values."
::= { tables 1 }

historyEntry OBJECT-TYPE
	SYNTAX  HistoryEntry
	ACCESS  not-accessible
	STATUS  optional
	DESCRIPTION	"History values entries."
	INDEX   { histTemperature }
::= { historyTable 1 }

historyEntry ::=
	SEQUENCE {
		histTemperature
			INTEGER,
		histHumidity
			INTEGER,
		histComputedValue
			INTEGER,
		histRelay1
			INTEGER
		histRelay2
			INTEGER
		histInput1
			INTEGER
		histInput2
			INTEGER
		histInput3
			INTEGER
		}

histTemperature OBJECT-TYPE
	SYNTAX  INTEGER (-2000..6000)
	ACCESS  read-only
	STATUS  mandatory
	DESCRIPTION	"Temperature reading."
::= { historyEntry 1 }

histHumidity OBJECT-TYPE
	SYNTAX  INTEGER (-2000..6000)
	ACCESS  read-only
	STATUS  mandatory
	DESCRIPTION	"Humidity reading."
::= { historyEntry 2 }

histComputedValue OBJECT-TYPE
	SYNTAX  INTEGER (-2000..6000)
	ACCESS  read-only
	STATUS  mandatory
	DESCRIPTION	"Computed value reading."
::= { historyEntry 3 }

histRelay1 OBJECT-TYPE
	SYNTAX  INTEGER (-2000..6000)
	ACCESS  read-only
	STATUS  mandatory
	DESCRIPTION	"Relay 1 reading."
::= { historyEntry 5 }

histRelay2 OBJECT-TYPE
	SYNTAX  INTEGER (-2000..6000)
	ACCESS  read-only
	STATUS  mandatory
	DESCRIPTION	"Relay 2 reading."
::= { historyEntry 6 }

histInput1 OBJECT-TYPE
	SYNTAX  INTEGER (-2000..6000)
	ACCESS  read-only
	STATUS  mandatory
	DESCRIPTION	"Binary Input 1 reading."
::= { historyEntry 7 }

histInput2 OBJECT-TYPE
	SYNTAX  INTEGER (-2000..6000)
	ACCESS  read-only
	STATUS  mandatory
	DESCRIPTION	"Binary Input 2 reading."
::= { historyEntry 8 }

histInput3 OBJECT-TYPE
	SYNTAX  INTEGER (-2000..6000)
	ACCESS  read-only
	STATUS  mandatory
	DESCRIPTION	"Binary Input 3 reading."
::= { historyEntry 9 }

END
