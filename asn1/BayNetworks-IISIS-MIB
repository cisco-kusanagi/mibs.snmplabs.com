BayNetworks-IISIS-MIB DEFINITIONS ::= BEGIN


    IMPORTS

      Counter, IpAddress, Gauge
        FROM RFC1155-SMI
      OBJECT-TYPE
        FROM RFC-1212
      DisplayString
        FROM RFC1213-MIB
      wfIisisGroup
        FROM Wellfleet-COMMON-MIB;

     
    wfIisisGeneralGroup OBJECT IDENTIFIER ::= { wfIisisGroup 1 }

    wfIisisGeneralDelete OBJECT-TYPE
        SYNTAX  INTEGER {
                    created(1),
                    deleted(2)
                }
        ACCESS  read-write
        STATUS  mandatory
        DESCRIPTION
                "'This value determines whether I-ISIS is configured'"
        DEFVAL  { created }
        ::= { wfIisisGeneralGroup 1 }

    wfIisisGeneralDisable OBJECT-TYPE
        SYNTAX  INTEGER {
                    enabled(1),
                    disabled(2)
                }
        ACCESS  read-write
        STATUS  mandatory
        DESCRIPTION

                "'The administrative status of I-ISIS in the router.  The
                value 'enabled' denotes that the I-ISIS Process is active
                on at least one interface; 'disabled' disables it on
                all interfaces.'"
        DEFVAL  { enabled }
        ::= { wfIisisGeneralGroup 2 }

    wfIisisGeneralState OBJECT-TYPE
        SYNTAX  INTEGER {
                    up(1),
                    down(2),
                    invalid(3),
                    notpresent(4)
                }
        ACCESS  read-only
        STATUS  mandatory
        DESCRIPTION
                "'The state of I-ISIS'"
        DEFVAL  { down }
        ::= { wfIisisGeneralGroup 3 }

    wfIisisRouterId OBJECT-TYPE
        SYNTAX OCTET STRING 
        ACCESS  read-write
        STATUS  mandatory
        DESCRIPTION
                "This value contains the system ID of this Intermediate System."
        ::= { wfIisisGeneralGroup 4 }

    wfIisisVersion OBJECT-TYPE
        SYNTAX  DisplayString
        ACCESS  read-only
        STATUS  mandatory
        DESCRIPTION
                "This read-only parameter identifies the version number of the
                IS-IS protocol to which this node conforms to."
        ::= { wfIisisGeneralGroup 5 }


    wfIisisRouterType OBJECT-TYPE
        SYNTAX	INTEGER {
                    l1only(1),
		    l2only(2),
                    l1l2(3)
    		}
        ACCESS	read-write
        STATUS	mandatory
        DESCRIPTION
               "This value determines whether this system is L1 only router
                L2 only router or L1-L2 IS."
        DEFVAL	{  l1l2 }
        ::= { wfIisisGeneralGroup 6 }

    wfIisisSpfHoldDown OBJECT-TYPE
        SYNTAX	INTEGER(0..60)
        ACCESS	read-write
        STATUS	mandatory
        DESCRIPTION
                "Hold Down Timer for the SPF (in seconds).  The SPF will 
                run at most once per hold down timer value.  A value of 0 
                means no hold down."
        DEFVAL	{ 10 }
        ::= { wfIisisGeneralGroup 7 }

    wfIisisPrimaryLogMask OBJECT-TYPE
        SYNTAX	Gauge
        ACCESS	read-write
        STATUS	mandatory
        DESCRIPTION
                "A parameter to specify which I-ISIS log messages should be logged.
                This will only effect the Primary I-ISIS gate.
                Each bit represents a message as defined below.  A 1 in that
                bit location means to log it and a 0 means not to put that
                log message in the log.  Changing this value will NOT restart
                I-ISIS, but will take effct immediately(if there are any messages
                to be logged.

                bit 31                                bit 0
                +---------------------------------------+
                |                                       |
                +---------------------------------------+

                bit0  Trace Messages
                bit1  INFO Level messages
                bit2  debug level messages
                bit3  I-ISIS interface state change messages
                bit4  Nbr state changes
                bit5  self-origination of LSA's
                bit6  receipt of new LSA's
                bit7  changes to I-ISIS`s Routing Table
                bit8  Bad LS requests, Ack's, or updates
                bit9  receipt of less recent LSA's
                bit10 receipt of more recent self-originated LSA's
                bit11 receipt of MAxAge LSA's (i.e. LSA's being flushed)
                bit12 - 31 reserved
                "
        DEFVAL	{ 287 }
        ::= { wfIisisGeneralGroup 8 }

    wfIisisMaximumPath OBJECT-TYPE
        SYNTAX  INTEGER(1..12)
        ACCESS  read-write
        STATUS  mandatory
        DESCRIPTION
              "Maximum number of equal cost paths allowed for a network installed 
               by OSPF."
        DEFVAL { 1 }
        ::= { wfIisisGeneralGroup 9 }

    wfIisisMaxAreas OBJECT-TYPE
        SYNTAX  INTEGER(1..3)
        ACCESS  read-write
        STATUS  mandatory
        DESCRIPTION
             "This value defines the maximum allowable number of areas addresses
              for the domain that this router exists in."
        DEFVAL  { 1 }
        ::= { wfIisisGeneralGroup 10 }

    wfIisisNumL1Lsps OBJECT-TYPE
        SYNTAX  Gauge
        ACCESS  read-only
        STATUS  mandatory
        DESCRIPTION
                "Number of L2 LSPS stored in the database"
        ::= { wfIisisGeneralGroup 11 }

    wfIisisNumL2Lsps OBJECT-TYPE
        SYNTAX  Gauge
        ACCESS  read-only
        STATUS  mandatory
        DESCRIPTION
                "Number of L2 LSPS stored in the database"
        ::= { wfIisisGeneralGroup 12 }

    wfIisisCksumIsPdus OBJECT-TYPE
        SYNTAX  INTEGER {
                    enabled(1),
                    disabled(2)
                }
        ACCESS  read-write
        STATUS  mandatory
        DESCRIPTION
                "This value indicates whether ISIS PDUs will carry a checksum."
        DEFVAL  { enabled }
        ::= { wfIisisGeneralGroup 13 }

    wfIisisL1LspPassword OBJECT-TYPE
        SYNTAX  DisplayString
        ACCESS  read-write
        STATUS  mandatory
        DESCRIPTION
                "This assigns a password such that only L1 Lsps with the matching
                 password will be accepted.  All L1 Lsps generated
                 by this system will contain this string in the password option."
        ::= { wfIisisGeneralGroup 14 }

    wfIisisL2LspPassword OBJECT-TYPE
        SYNTAX  DisplayString
        ACCESS  read-write
        STATUS  mandatory
        DESCRIPTION
                "This assigns a password such that only L2 Lsps with the matching
                 password will be accepted.  All L2 Lsps generated
                 by this system will contain this string in the password option."
        ::= { wfIisisGeneralGroup 15 }

    wfIisisAreaAddr OBJECT-TYPE
        SYNTAX  OCTET STRING
        ACCESS  read-write
        STATUS  mandatory
        DESCRIPTION
                "This Assigns the area address for this router.
                 This field must be filled in.
                 If the user doesn't enter a value, then assign 0x470005.
                 Site Manager must force the user to enter at least a 3-byte
                 value for this field."
        ::= { wfIisisGeneralGroup 16 }

    wfIisisAreaAddrAlias1 OBJECT-TYPE
        SYNTAX  OCTET STRING
        ACCESS  read-write
        STATUS  mandatory
        DESCRIPTION
                "This Assigns the first area address alias for this router.
                This field does no have to be filled in, but if the user
                tries to enter a value, Site Manager must make sure that
                it is at least 3-bytes in length."
        ::= { wfIisisGeneralGroup 17 }

    wfIisisAreaAddrAlias2 OBJECT-TYPE
        SYNTAX  OCTET STRING
        ACCESS  read-write
        STATUS  mandatory
        DESCRIPTION
                "This Assigns the second area address alias for this router.
                This field does no have to be filled in, but if the user
                tries to enter a value, Site Manager must make sure that
                it is at least 3-bytes in length."
        ::= { wfIisisGeneralGroup 18 }

    wfIisisL1CorruptedLsps OBJECT-TYPE
        SYNTAX  Counter
        ACCESS  read-only
        STATUS  mandatory
        DESCRIPTION
                "Number of Corrupted L1-Lsps Detected."
        ::= { wfIisisGeneralGroup 19 }

    wfIisisL2CorruptedLsps OBJECT-TYPE
        SYNTAX  Counter
        ACCESS  read-only
        STATUS  mandatory
        DESCRIPTION
                "Number of Corrupted L2-Lsps Detected."
        ::= { wfIisisGeneralGroup 20 }

   wfIisisL1LspDbOverLoads OBJECT-TYPE
        SYNTAX  Counter
        ACCESS  read-only
        STATUS  mandatory
        DESCRIPTION
               "Number of times the L1 Lsp Database Overload event has been
                generated."
        ::= { wfIisisGeneralGroup 21 }

   wfIisisL2LspDbOverLoads OBJECT-TYPE
        SYNTAX  Counter
        ACCESS  read-only
        STATUS  mandatory
        DESCRIPTION
               "Number of times the L2Lsp Database Overload event has been
                generated."
        ::= { wfIisisGeneralGroup 22 }

   wfIisisNearestL2Is OBJECT-TYPE
        SYNTAX  OCTET STRING
        ACCESS  read-only
        STATUS  mandatory
        DESCRIPTION
               "This is the ID of the nearest L2 system in this area."
        ::= { wfIisisGeneralGroup 23 }

   wfIisisNumL1Routes OBJECT-TYPE
        SYNTAX  Gauge
        ACCESS  read-only
        STATUS  mandatory
        DESCRIPTION
               "Number of L1 Routes."
        ::= { wfIisisGeneralGroup 24 }

   wfIisisNumL2Routes OBJECT-TYPE
        SYNTAX  Gauge
        ACCESS  read-only
        STATUS  mandatory
        DESCRIPTION
               "Number of L2  Routes."
        ::= { wfIisisGeneralGroup 25 }

   wfIisisMinLSPGenerationInterval OBJECT-TYPE
        SYNTAX  INTEGER(5..900)
        ACCESS  read-write
        STATUS  mandatory
        DESCRIPTION
                "Min time interval(in secs) before LSP generation"
        DEFVAL  { 30 } 
        ::= { wfIisisGeneralGroup 26 }

   wfIisisMaxLSPGenerationInterval OBJECT-TYPE
        SYNTAX  INTEGER(150..27000)
        ACCESS  read-write
        STATUS  mandatory
        DESCRIPTION
                "Max time interval(in secs) before LSP generation"
        DEFVAL  { 900 }
        ::= { wfIisisGeneralGroup 27 }

   wfIisisMaxAge OBJECT-TYPE
        SYNTAX  INTEGER(300..7200)
        ACCESS  read-write
        STATUS  mandatory
        DESCRIPTION
                "The lifetime of the lsp after which it will be considered expired"
        DEFVAL  { 1200 }
        ::= { wfIisisGeneralGroup 28 }

    wfIisisMinLSPXmtInterval OBJECT-TYPE
        SYNTAX  INTEGER(0..100)
        ACCESS  read-write
        STATUS  mandatory
        DESCRIPTION
                ""
        DEFVAL  { 5 }
        ::= { wfIisisGeneralGroup 29 }

    wfIisisPartialSNPInterval OBJECT-TYPE 
        SYNTAX  INTEGER(1..30)
        ACCESS  read-write
        STATUS  mandatory
        DESCRIPTION
                ""
        DEFVAL  { 2 }
        ::= { wfIisisGeneralGroup 30 }

    wfIisisZeroAgeLifetime OBJECT-TYPE 
        SYNTAX  INTEGER(0..120)
        ACCESS  read-write
        STATUS  mandatory
        DESCRIPTION
                "If the remaining lifetime of an LSP reaches zero, the 
                 expired LSP will be kept in the database for this time (in
                 seconds)"
        DEFVAL  { 60 }
        ::= { wfIisisGeneralGroup 31 }

    wfIisisAgePend OBJECT-TYPE 
        SYNTAX  INTEGER(10..100)
        ACCESS  read-write
        STATUS  mandatory
        DESCRIPTION
                "The number of entries processed before this gate pends"
        DEFVAL  { 50 }
        ::= { wfIisisGeneralGroup 32 }

    wfIisisCsnpBuildInterval OBJECT-TYPE 
        SYNTAX  INTEGER(10..1200)
        ACCESS  read-write
        STATUS  mandatory
        DESCRIPTION
                "The interval at which CSNPs are generated by the Designated IS"
        DEFVAL  { 10 }
        ::= { wfIisisGeneralGroup 33 }

     wfIisisL2LspBufferSize OBJECT-TYPE
         SYNTAX  INTEGER(256..16384)
         ACCESS  read-write
         STATUS  mandatory
         DESCRIPTION
                "The max size of the LSP generated by system"
         DEFVAL { 1497 }
         ::= { wfIisisGeneralGroup 34 } 

    wfIisisL1SpfCnt OBJECT-TYPE
        SYNTAX  Counter
        ACCESS  read-only
        STATUS  mandatory
        DESCRIPTION
                "The number of times the L1 I-ISIS SPF algorithm
                has been run for this area."
        ::= { wfIisisGeneralGroup 35 }

    wfIisisL2SpfCnt OBJECT-TYPE
        SYNTAX  Counter
        ACCESS  read-only
        STATUS  mandatory
        DESCRIPTION
                "The number of times the L2 I-ISIS SPF algorithm
                has been run for this area."
        ::= { wfIisisGeneralGroup 36 }

    wfIisisAreaTable OBJECT-TYPE
        SYNTAX	SEQUENCE OF WfIisisAreaEntry
        ACCESS	not-accessible
        STATUS	mandatory
        DESCRIPTION
                "--      The I-ISIS Area Data Structure contains information
                 --      regarding the various areas. The interfaces and
                 --      links are configured as part of these areas.
                 --      Area 0.0.0.0, by definition, is the Backbone Area
                       'Information describing the configured parameters and
                       cumulative statistics of the router's attached areas.'
                    REFERENCE
                       'I-ISIS Version 2, Section 6  The Area Data Structure'"
        ::= { wfIisisGroup 2 }

    wfIisisAreaEntry OBJECT-TYPE
        SYNTAX	WfIisisAreaEntry
        ACCESS	not-accessible
        STATUS	mandatory
        DESCRIPTION
                "'Information describing the configured parameters and
                cumulative statistics of one of the router's attached
                areas.'"
        INDEX	{ wfIisisAreaId }
        ::= { wfIisisAreaTable 1 }

    WfIisisAreaEntry ::= SEQUENCE {
    	    wfIisisAreaDelete
    		INTEGER,
    	    wfIisisAreaDisable
    		INTEGER,
    	    wfIisisAreaState
    		INTEGER,
    	    wfIisisAreaId
    		IpAddress,
    	    wfIisisSpfCnt
    		Counter
        }

    wfIisisAreaDelete OBJECT-TYPE
        SYNTAX	INTEGER {
    		    created(1),
    		    deleted(2)
    		}
        ACCESS	read-write
        STATUS	mandatory
        DESCRIPTION
                "This value determines if the I-ISIS router is configured with
                 this area."
        DEFVAL	{ created }
        ::= { wfIisisAreaEntry 1 }

    wfIisisAreaDisable OBJECT-TYPE
        SYNTAX	INTEGER {
    		    enabled(1),
    		    disabled(2)
    		}
        ACCESS	read-write
        STATUS	mandatory
        DESCRIPTION
                "This value indicates the state of this area on the I-ISIS
                 router."
        DEFVAL	{ enabled }
        ::= { wfIisisAreaEntry 2 }

    wfIisisAreaState OBJECT-TYPE
        SYNTAX	INTEGER {
    		    up(1),
    		    down(2)
    		}
        ACCESS	read-only
        STATUS	mandatory
        DESCRIPTION
                "This value indicates the state of the I-ISIS Area."
        DEFVAL	{ down }
        ::= { wfIisisAreaEntry 3 }

    wfIisisAreaId OBJECT-TYPE
        SYNTAX	IpAddress
        ACCESS	read-only
        STATUS	mandatory
        DESCRIPTION
                "A 32-bit integer uniquely identifying an area.  Area
                 ID 0.0.0.0 is used for the I-ISIS backbone."
        ::= { wfIisisAreaEntry 4 }

    wfIisisSpfCnt OBJECT-TYPE
        SYNTAX	Counter
        ACCESS	read-only
        STATUS	mandatory
        DESCRIPTION
                "The number of times the I-ISIS SPF algorithm
                has been run for this area."
        ::= { wfIisisAreaEntry 5 }

    wfIisisL1LspHdrTable OBJECT-TYPE
        SYNTAX  SEQUENCE OF WfIisisL1LspHdrEntry
        ACCESS  not-accessible
        STATUS  mandatory
        DESCRIPTION
                "2 u_int32's so the inst_id len is 2."
        ::= { wfIisisGroup 3 }

    wfIisisL1LspHdrEntry OBJECT-TYPE
        SYNTAX  WfIisisL1LspHdrEntry
        ACCESS  not-accessible
        STATUS  mandatory
        DESCRIPTION
                "A Record in the Level 1 Lsp Header Table"
        INDEX   { wfIisisL1LspHdrLspId }
        ::= { wfIisisL1LspHdrTable 1 }

    WfIisisL1LspHdrEntry ::= SEQUENCE {
          wfIisisL1LspHdrLspId
                OCTET STRING,
          wfIisisL1LspHdrLifetime
                INTEGER,
          wfIisisL1LspHdrSeqnum
                INTEGER,
          wfIisisL1LspHdrFlags
                INTEGER,
          wfIisisL1LspHdrCksum
                OCTET STRING
      }

    wfIisisL1LspHdrLspId OBJECT-TYPE
        SYNTAX  OCTET STRING (SIZE (8))
        ACCESS  read-only
        STATUS  mandatory
        DESCRIPTION
                "LSPID = Source ID + Pseudo-node ID + LSP number"
        ::= { wfIisisL1LspHdrEntry 1 }

    wfIisisL1LspHdrLifetime OBJECT-TYPE
        SYNTAX  INTEGER
        ACCESS  read-only
        STATUS  mandatory
        DESCRIPTION
                "Lsp Lifetime"
        ::= { wfIisisL1LspHdrEntry 2 }

     wfIisisL1LspHdrSeqnum OBJECT-TYPE
        SYNTAX  INTEGER
        ACCESS  read-only
        STATUS  mandatory
        DESCRIPTION
                "Lsp sequence number"
        ::= { wfIisisL1LspHdrEntry 3 }

    wfIisisL1LspHdrFlags OBJECT-TYPE
        SYNTAX  INTEGER
        ACCESS  read-only
        STATUS  mandatory
        DESCRIPTION
                "Flags: P/ATT/LSPDBOL/IS type"
        ::= { wfIisisL1LspHdrEntry 4 }

   wfIisisL1LspHdrCksum OBJECT-TYPE
        SYNTAX  OCTET STRING
        ACCESS  read-only
        STATUS  mandatory
        DESCRIPTION
                "Checksum"
        ::= { wfIisisL1LspHdrEntry 5 }


   wfIisisL2LspHdrTable OBJECT-TYPE
        SYNTAX  SEQUENCE OF WfIisisL2LspHdrEntry
        ACCESS  not-accessible
        STATUS  mandatory
        DESCRIPTION
                "2 u_int32's so the inst_id len is 2."
        ::= { wfIisisGroup 4 }

   wfIisisL2LspHdrEntry OBJECT-TYPE
        SYNTAX  WfIisisL2LspHdrEntry
        ACCESS  not-accessible
        STATUS  mandatory
        DESCRIPTION
                "A Record in the Lsp Header Table"
        INDEX   { wfIisisL2LspHdrLspId }
        ::= { wfIisisL2LspHdrTable 1 }

   WfIisisL2LspHdrEntry ::= SEQUENCE {
          wfIisisL2LspHdrLspId
                OCTET STRING,
          wfIisisL2LspHdrLifetime
                INTEGER,
          wfIisisL2LspHdrSeqnum
                INTEGER,
          wfIisisL2LspHdrFlags
                INTEGER,
          wfIisisL2LspHdrCksum
                OCTET STRING
      }

    wfIisisL2LspHdrLspId OBJECT-TYPE
        SYNTAX  OCTET STRING (SIZE (8))
        ACCESS  read-only
        STATUS  mandatory
        DESCRIPTION
                "LSPID = Source ID + Pseudo-node ID + LSP number"
        ::= { wfIisisL2LspHdrEntry 1 }

    wfIisisL2LspHdrLifetime OBJECT-TYPE
        SYNTAX  INTEGER
        ACCESS  read-only
        STATUS  mandatory
        DESCRIPTION
                "Lsp Lifetime"
        ::= { wfIisisL2LspHdrEntry 2 }

     wfIisisL2LspHdrSeqnum OBJECT-TYPE
        SYNTAX  INTEGER
        ACCESS  read-only
        STATUS  mandatory
        DESCRIPTION
                "Lsp sequence number"
        ::= { wfIisisL2LspHdrEntry 3 }

    wfIisisL2LspHdrFlags OBJECT-TYPE
        SYNTAX  INTEGER
        ACCESS  read-only
        STATUS  mandatory
        DESCRIPTION
                "Flags: P/ATT/LSPDBOL/IS type"
        ::= { wfIisisL2LspHdrEntry 4 }

   wfIisisL2LspHdrCksum OBJECT-TYPE
        SYNTAX  OCTET STRING
        ACCESS  read-only
        STATUS  mandatory
        DESCRIPTION
                "Checksum"
        ::= { wfIisisL2LspHdrEntry 5 }


    wfIisisIfTable OBJECT-TYPE
        SYNTAX  SEQUENCE OF WfIisisIfEntry
        ACCESS  not-accessible
        STATUS  mandatory
        DESCRIPTION
                "--  I-ISIS Interface Table

                --      The I-ISIS Interface Table augments the ifTable with I-ISIS
                --      specific information.

                       'The I-ISIS Interface Table describes the interfaces from
                       the viewpoint of I-ISIS.'"
        ::= { wfIisisGroup 5 }

    wfIisisIfEntry OBJECT-TYPE
        SYNTAX	WfIisisIfEntry
        ACCESS	not-accessible
        STATUS	mandatory
        DESCRIPTION
                "'The I-ISIS Interface Entry describes one interface from
                the viewpoint of I-ISIS.'"
        INDEX	{ wfIisisIfIpAddress,
    		  wfIisisAddressLessIf }
        ::= { wfIisisIfTable 1 }

    WfIisisIfEntry ::= SEQUENCE {
            wfIisisIfDelete
                INTEGER,
            wfIisisIfDisable
                INTEGER,
            wfIisisIfIpAddress
                IpAddress,
            wfIisisAddressLessIf
                INTEGER,
            wfIisisIfRouterLevel
                INTEGER,
            wfIisisIfL1DefaultMetric
                INTEGER,
            wfIisisIfL2DefaultMetric
                INTEGER,
            wfIisisIfL1DrPriority
                INTEGER,
            wfIisisIfL2DrPriority
                INTEGER,
            wfIisisIfHelloTimer
                INTEGER,
            wfIisisIfPassword
                DisplayString,
            wfIisisIfHelloMtuSize
                INTEGER,
            wfIisisIfIihHoldMultiplier
                INTEGER,
            wfIisisIfIshHoldMultiplier
                INTEGER,
            wfIisisIfType
                INTEGER,
            wfIisisIfCsnpTimer
                INTEGER
             
        }
    wfIisisIfDelete OBJECT-TYPE
        SYNTAX	INTEGER {
    		    created(1),
    		    deleted(2)
    		}
        ACCESS	read-write
        STATUS	mandatory
        DESCRIPTION
                "This variable determines in an I-ISIS Interface has been
                configured on the router."
        DEFVAL	{ created }
        ::= { wfIisisIfEntry 1 }

    wfIisisIfDisable OBJECT-TYPE
        SYNTAX	INTEGER {
    		    enabled(1),
    		    disabled(2)
    		}
        ACCESS	read-write
        STATUS	mandatory
        DESCRIPTION
                "'The I-ISIS interface's administrative status.  The value
                'enabled' denotes that neighbor relationships may be
                formed on the interface, and the interface will be
                advertised as an internal route to some area.  The
                value 'disabled' denotes that the interface is external
                to I-ISIS.'"
        DEFVAL	{ enabled }
        ::= { wfIisisIfEntry 2 }

    wfIisisIfIpAddress OBJECT-TYPE
        SYNTAX	IpAddress
        ACCESS	read-only
        STATUS	mandatory
        DESCRIPTION
                "'The IP address of this I-ISIS interface.'"
        ::= { wfIisisIfEntry 3 }

    wfIisisAddressLessIf OBJECT-TYPE
        SYNTAX	INTEGER
        ACCESS	read-only
        STATUS	mandatory
        DESCRIPTION
                "'For the purpose of easing the instancing of addressed
                and addressless interfaces; This variable takes the
                value 0 on interfaces with IP Addresses, and the
                corresponding value of ifIndex for interfaces having no
                IP Address.'"
        ::= { wfIisisIfEntry 4 }

    wfIisisIfRouterLevel OBJECT-TYPE
        SYNTAX  INTEGER {
                    l1(1),
                    l2(2),
                    l1l2(3),
                    ext(4),
                    l2ext(6),
                    l1l2ext(7),
                    esisonly(8)
                }
        ACCESS  read-write
        STATUS  mandatory
        DESCRIPTION
                "This is the level protocol that the circuit runs.
                Its a bit mask to allow for some combination of
                L1, L2, External, ES-IS-only."
        DEFVAL  { l2 }
        ::= { wfIisisIfEntry 5 }

    wfIisisIfL1DefaultMetric OBJECT-TYPE
        SYNTAX  INTEGER(1..63)
        ACCESS  read-write
        STATUS  mandatory
        DESCRIPTION
                "This is the default cost of using this circuit for L1 traffic."
        DEFVAL  { 10 }
        ::= { wfIisisIfEntry 6 }

    wfIisisIfL2DefaultMetric OBJECT-TYPE
        SYNTAX  INTEGER(1..63)
        ACCESS  read-write
        STATUS  mandatory
        DESCRIPTION
                "This is the default cost of using this circuit for L2 traffic."
        DEFVAL  { 10 }
        ::= { wfIisisIfEntry 7 }

    wfIisisIfL1DrPriority OBJECT-TYPE
        SYNTAX  INTEGER(1..127)
        ACCESS  read-write
        STATUS  mandatory
        DESCRIPTION
                "This is the priority for this system to become L1 designated
                router on this LAN circuit."
        DEFVAL  { 64 }
        ::= { wfIisisIfEntry 8 }

    wfIisisIfL2DrPriority OBJECT-TYPE
        SYNTAX  INTEGER(1..127)
        ACCESS  read-write
        STATUS  mandatory
        DESCRIPTION
                "This is the priority for this system to become L2 designated
                router on this LAN circuit."
        DEFVAL  { 64 }
        ::= { wfIisisIfEntry 9 }

    wfIisisIfHelloTimer OBJECT-TYPE
        SYNTAX  INTEGER(1..21845)
        ACCESS  read-write
        STATUS  mandatory
        DESCRIPTION
                "This is the period (secs) between IIH hello transmissions."
        DEFVAL  { 10 }
        ::= { wfIisisIfEntry 10 }

    wfIisisIfPassword OBJECT-TYPE
        SYNTAX  DisplayString
        ACCESS  read-write
        STATUS  mandatory
        DESCRIPTION
                "This is Circuit Password for this circuit. Used to filter
                out Hellos from systems without the correct password."
        ::= { wfIisisIfEntry 11 } 

    wfIisisIfHelloMtuSize OBJECT-TYPE
        SYNTAX	INTEGER(1..10000)
        ACCESS	read-write
        STATUS	mandatory
        DESCRIPTION
                 "Configure Hello MTU size per I-ISIS interface
                     This parameter has the following values/meanings:

                  1 - Use the MTU specified by IP
                  2 - Use the MTU of ethernet, regardless of what IP
                      says
                  > 2 - Use this value as the actual MTU.
                        If the value is smaller than what I-ISIS needs as
                        a minimum then the mtu specified by IP is used.
                        For example, 3 would never be used as an MTU."
        DEFVAL	{ 1 }
        ::= { wfIisisIfEntry 12 }

   wfIisisIfIihHoldMultiplier OBJECT-TYPE
        SYNTAX  INTEGER(1..5)
        ACCESS  read-write
        STATUS  mandatory
        DESCRIPTION
                "This is the multiplier value used to compute the hold time
                set in the IIH PDUs transmitted from this router. Hold time
                equals IIH Timer times IIH Hold Multiplier."
        DEFVAL  { 3 }
        ::= { wfIisisIfEntry 13 }

   wfIisisIfIshHoldMultiplier OBJECT-TYPE
        SYNTAX  INTEGER(1..5)
        ACCESS  read-write
        STATUS  mandatory
        DESCRIPTION
                "This is the multiplier value used to compute the hold time
                set in the ISH PDUs transmitted from this router. Hold time
                equals IIH Timer times IIH Hold Multiplier."
        DEFVAL  { 3 }
        ::= { wfIisisIfEntry 14 }

  wfIisisIfType OBJECT-TYPE
       SYNTAX  INTEGER {
                    broadcast(1),
                    pointtopoint(2)
                 }
       ACCESS  read-write
       STATUS  mandatory
       DESCRIPTION
                "The IISIS interface type."
       DEFVAL  { broadcast }
       ::= { wfIisisIfEntry 15 }

   wfIisisIfCsnpTimer OBJECT-TYPE
        SYNTAX  INTEGER(10..600)
        ACCESS  read-write
        STATUS  mandatory
        DESCRIPTION
                "This is the period (in seconds) between CSNP transmissions."
        DEFVAL  { 10 }
        ::= { wfIisisIfEntry 16 }

    wfIisisIfStatsTable OBJECT-TYPE
        SYNTAX  SEQUENCE OF WfIisisIfStatsEntry
        ACCESS  not-accessible
        STATUS  mandatory
        DESCRIPTION
                "--  I-ISIS Interface Stats Table. "
        ::= { wfIisisGroup 6 }

    wfIisisIfStatsEntry OBJECT-TYPE
        SYNTAX  WfIisisIfStatsEntry
        ACCESS  not-accessible
        STATUS  mandatory
        DESCRIPTION
                "'The information regarding a interface'."
        INDEX   { wfIisisIfStatsIpAddress,
                  wfIisisStatsAddressLessIf }
        ::= { wfIisisIfStatsTable 1 }

    WfIisisIfStatsEntry ::= SEQUENCE {
           wfIisisIfStatsIpAddress
              IpAddress,
           wfIisisStatsAddressLessIf
              INTEGER,
           wfIisisIfStatsState
                INTEGER,
           wfIisisIfStatsCct
                INTEGER,
           wfIisisIfStatsL1TxHellos
                Counter,
           wfIisisIfStatsL2TxHellos
                Counter,
           wfIisisIfStatsL1RxHellos
                Counter,
           wfIisisIfStatsL2RxHellos
                Counter,
           wfIisisIfStatsL1Drops
                Counter,
           wfIisisIfStatsL2Drops
                Counter,
           wfIisisIfStatsL1DesignatedRouter
                OCTET STRING,
           wfIisisIfStatsL2DesignatedRouter
                OCTET STRING,
           wfIisisIfStatsTxL1Lsp
                Counter,
           wfIisisIfStatsTxL2Lsp
                Counter,
           wfIisisIfStatsTxL1Csnp
                Counter,
           wfIisisIfStatsTxL2Csnp
                Counter,
           wfIisisIfStatsTxL1Psnp
                Counter,
           wfIisisIfStatsTxL2Psnp
                Counter,
           wfIisisIfStatsRxL1Lsp
                Counter,
           wfIisisIfStatsRxL2Lsp
                Counter,
           wfIisisIfStatsRxL1Csnp
                Counter,
           wfIisisIfStatsRxL2Csnp
                Counter,
           wfIisisIfStatsRxL1Psnp
                Counter,
           wfIisisIfStatsRxL2Psnp
                Counter,
           wfIisisIfStatsL1NbrCount
                Gauge,
           wfIisisIfStatsL2NbrCount
                Gauge,
           wfIisisIfStatsL1AdjCount
                Gauge,
           wfIisisIfStatsL2AdjCount
                Gauge
           }
    wfIisisIfStatsIpAddress OBJECT-TYPE
        SYNTAX  IpAddress
        ACCESS  read-only
        STATUS  mandatory
        DESCRIPTION
                "'The IP address of this I-ISIS interface.'"
        ::= { wfIisisIfStatsEntry 1 }

    wfIisisStatsAddressLessIf OBJECT-TYPE
        SYNTAX  INTEGER
        ACCESS  read-only
        STATUS  mandatory
        DESCRIPTION
                "'For the purpose of easing the instancing of addressed
                and addressless interfaces; This variable takes the
                value 0 on interfaces with IP Addresses, and the
                corresponding value of ifIndex for interfaces having no
                IP Address.'"
        ::= { wfIisisIfStatsEntry 2 }

     wfIisisIfStatsState OBJECT-TYPE
        SYNTAX  INTEGER {
                    up(1),
                    down(2)
                }
        ACCESS  read-only
        STATUS  mandatory
        DESCRIPTION
                "This indicates whether the circuit state is up or down."
        DEFVAL  { down }
        ::= { wfIisisIfStatsEntry 3 }

     wfIisisIfStatsCct OBJECT-TYPE
        SYNTAX  INTEGER
        ACCESS  read-only
        STATUS  mandatory
        DESCRIPTION
                "A unique value for each known circuit."
        ::= { wfIisisIfStatsEntry 4 }

    wfIisisIfStatsL1TxHellos OBJECT-TYPE
        SYNTAX  Counter
        ACCESS  read-only
        STATUS  mandatory
        DESCRIPTION
                "Number of I-ISIS Hello packets transmitted."
        ::= { wfIisisIfStatsEntry 5 }

    wfIisisIfStatsL2TxHellos OBJECT-TYPE
        SYNTAX  Counter
        ACCESS  read-only
        STATUS  mandatory
        DESCRIPTION
                "Number of I-ISIS Hello packets transmitted."
        ::= { wfIisisIfStatsEntry 6 }

    wfIisisIfStatsL1RxHellos OBJECT-TYPE
        SYNTAX  Counter
        ACCESS  read-only
        STATUS  mandatory
        DESCRIPTION
                "Number of I-ISIS Hello packets received."
        ::= { wfIisisIfStatsEntry 7 }

    wfIisisIfStatsL2RxHellos OBJECT-TYPE
        SYNTAX  Counter
        ACCESS  read-only
        STATUS  mandatory
        DESCRIPTION
                "Number of I-ISIS Hello packets received."
        ::= { wfIisisIfStatsEntry 8 }

    wfIisisIfStatsL1Drops OBJECT-TYPE
        SYNTAX  Counter
        ACCESS  read-only
        STATUS  mandatory
        DESCRIPTION
                "Number of I-ISIS packets dropped because of invalid information
                in the packet."
        ::= { wfIisisIfStatsEntry 9 }

    wfIisisIfStatsL2Drops OBJECT-TYPE
        SYNTAX  Counter
        ACCESS  read-only
        STATUS  mandatory
        DESCRIPTION
                "Number of I-ISIS packets dropped because of invalid information
                in the packet."
        ::= { wfIisisIfStatsEntry 10 }

    wfIisisIfStatsL1DesignatedRouter OBJECT-TYPE
        SYNTAX  OCTET STRING
        ACCESS  read-only
        STATUS  mandatory
        DESCRIPTION
                "This is the ID of the L1 Designated Router on this
                circuit."
        ::= { wfIisisIfStatsEntry 11 }

    wfIisisIfStatsL2DesignatedRouter OBJECT-TYPE
        SYNTAX  OCTET STRING
        ACCESS  read-only
        STATUS  mandatory
        DESCRIPTION
                "This is the ID of the L2 Designated Router on this
                circuit."
        ::= { wfIisisIfStatsEntry 12 }

     wfIisisIfStatsTxL1Lsp OBJECT-TYPE
        SYNTAX  Counter
        ACCESS  read-only
        STATUS  mandatory
        DESCRIPTION
                "Number of L1 LSPs(Link State Packet) transmitted."
        ::= { wfIisisIfStatsEntry 13 }

   wfIisisIfStatsTxL2Lsp OBJECT-TYPE
        SYNTAX  Counter
        ACCESS  read-only
        STATUS  mandatory
        DESCRIPTION
                "Number of L2 LSPs(Link State Packet) transmitted."
        ::= { wfIisisIfStatsEntry 14 }

   wfIisisIfStatsTxL1Csnp OBJECT-TYPE
        SYNTAX  Counter
        ACCESS  read-only
        STATUS  mandatory
        DESCRIPTION
                "Number of L1 CSNPs(Complete sequence no. packet) transmitted."
        ::= { wfIisisIfStatsEntry 15 }

   wfIisisIfStatsTxL2Csnp OBJECT-TYPE
        SYNTAX  Counter
        ACCESS  read-only
        STATUS  mandatory
        DESCRIPTION
                "Number of L2 CSNPs(Complete sequence no. packet) transmitted."
        ::= { wfIisisIfStatsEntry 16 }

   wfIisisIfStatsTxL1Psnp OBJECT-TYPE
        SYNTAX  Counter
        ACCESS  read-only
        STATUS  mandatory
        DESCRIPTION
                "Number of L1 PSNPs(Partial sequence no. packet) transmitted."
        ::= { wfIisisIfStatsEntry 17 }

   wfIisisIfStatsTxL2Psnp OBJECT-TYPE
        SYNTAX  Counter
        ACCESS  read-only
        STATUS  mandatory
        DESCRIPTION
                "Number of L2 PSNPs(Partial sequence no. packet) transmitted."
        ::= { wfIisisIfStatsEntry 18 }

   wfIisisIfStatsRxL1Lsp OBJECT-TYPE
        SYNTAX  Counter
        ACCESS  read-only
        STATUS  mandatory
        DESCRIPTION
                "Number of L1 LSPs(Link State Packet) received."
        ::= { wfIisisIfStatsEntry 19 }

   wfIisisIfStatsRxL2Lsp OBJECT-TYPE
        SYNTAX  Counter
        ACCESS  read-only
        STATUS  mandatory
        DESCRIPTION
                "Number of L2 LSPs(Link State Packet) received."
        ::= { wfIisisIfStatsEntry 20 }

   wfIisisIfStatsRxL1Csnp OBJECT-TYPE
        SYNTAX  Counter
        ACCESS  read-only
        STATUS  mandatory
        DESCRIPTION
                "Number of L1 CSNPs(Complete sequence no. packet) received."
        ::= { wfIisisIfStatsEntry 21 }

   wfIisisIfStatsRxL2Csnp OBJECT-TYPE
        SYNTAX  Counter
        ACCESS  read-only
        STATUS  mandatory
        DESCRIPTION
                "Number of L2 CSNPs(Complete sequence no. packet) received."
        ::= { wfIisisIfStatsEntry 22 }

   wfIisisIfStatsRxL1Psnp OBJECT-TYPE
        SYNTAX  Counter
        ACCESS  read-only
        STATUS  mandatory
        DESCRIPTION
                "Number of L1 PSNPs(Partial sequence no. packet) received."
        ::= { wfIisisIfStatsEntry 23 }

   wfIisisIfStatsRxL2Psnp OBJECT-TYPE
        SYNTAX  Counter
        ACCESS  read-only
        STATUS  mandatory
        DESCRIPTION
                "Number of L2 PSNPs(Partial sequence no. packet) received."
        ::= { wfIisisIfStatsEntry 24 }

   wfIisisIfStatsL1NbrCount OBJECT-TYPE
        SYNTAX  Gauge
        ACCESS  read-only
        STATUS  mandatory
        DESCRIPTION
                "Count of neighbors with any state."
        ::= { wfIisisIfStatsEntry 25 }

   wfIisisIfStatsL2NbrCount OBJECT-TYPE
        SYNTAX  Gauge
        ACCESS  read-only
        STATUS  mandatory
        DESCRIPTION
                "Count of neighbors with any state."
        ::= { wfIisisIfStatsEntry 26 }

   wfIisisIfStatsL1AdjCount OBJECT-TYPE
        SYNTAX  Gauge
        ACCESS  read-only
        STATUS  mandatory
        DESCRIPTION
                "Count of neighbors with state UP."
        ::= { wfIisisIfStatsEntry 27 }

   wfIisisIfStatsL2AdjCount OBJECT-TYPE
        SYNTAX  Gauge
        ACCESS  read-only
        STATUS  mandatory
        DESCRIPTION
                "Count of neighbors with state UP."
        ::= { wfIisisIfStatsEntry 28 }

 
    wfIisisDynNbrTable OBJECT-TYPE
        SYNTAX	SEQUENCE OF WfIisisDynNbrEntry
        ACCESS	not-accessible
        STATUS	mandatory
        DESCRIPTION
                "--  I-ISIS Dynamic Neighbor Table

                     The I-ISIS Dynamic Neighbor Table describes all neighbors 
                     in the locality of the subject router learned during 
                     operation."
        ::= { wfIisisGroup 7 }

    wfIisisDynNbrEntry OBJECT-TYPE
        SYNTAX	WfIisisDynNbrEntry
        ACCESS	not-accessible
        STATUS	mandatory
        DESCRIPTION
                "'The information regarding a single neighbor.'
                         REFERENCE
                'I-ISIS Version 2, Section 10 The Neighbor Data
                Structure'"
        INDEX	{ wfIisisDynNbrIpAddr,
    		  wfIisisDynNbrAddressLessIndex }
        ::= { wfIisisDynNbrTable 1 }

    WfIisisDynNbrEntry ::= SEQUENCE {
    	    wfIisisDynNbrState
    		INTEGER,
    	    wfIisisDynNbrIpAddr
    		IpAddress,
    	    wfIisisDynNbrIfAddr
    		IpAddress,
    	    wfIisisDynNbrAddressLessIndex
    		INTEGER,
    	    wfIisisDynNbrRtrId
    		OCTET STRING,
            wfIisisDynNbrDatabase
                INTEGER,
            wfIisisDynNbrType
                INTEGER,
            wfIisisDynNbrPseudonodeId
                INTEGER,
            wfIisisDynNbrHoldTime
                INTEGER,
            wfIisisDynNbrPriority
                INTEGER,
            wfIisisDynNbrSnpaAddr
                OCTET STRING,
            wfIisisDynNbrLanId
                OCTET STRING
        }

    wfIisisDynNbrState OBJECT-TYPE
        SYNTAX	INTEGER {
    		    down(1),
    		    init(2),
                    up(3)
    		}
        ACCESS	read-only
        STATUS	mandatory
        DESCRIPTION
                "'The State of the relationship with this Neighbor.'"
        DEFVAL	{ down }
        ::= { wfIisisDynNbrEntry 1 }

    wfIisisDynNbrIpAddr OBJECT-TYPE
        SYNTAX	IpAddress
        ACCESS	read-only
        STATUS	mandatory
        DESCRIPTION
                "'The IP address of this neighbor.'"
        ::= { wfIisisDynNbrEntry 2 }

    wfIisisDynNbrIfAddr OBJECT-TYPE
        SYNTAX	IpAddress
        ACCESS	read-only
        STATUS	mandatory
        DESCRIPTION
                "'Our Interface IP address for this neighbor.'"
        ::= { wfIisisDynNbrEntry 3 }

    wfIisisDynNbrAddressLessIndex OBJECT-TYPE
        SYNTAX	INTEGER
        ACCESS	read-only
        STATUS	mandatory
        DESCRIPTION
                "'The circuit over which this neighbor is learnt.'"
        ::= { wfIisisDynNbrEntry 4 }

    wfIisisDynNbrRtrId OBJECT-TYPE
        SYNTAX	OCTET STRING
        ACCESS	read-only
        STATUS	mandatory
        DESCRIPTION
                "'A 6 byte field representing the Intermediate
                  system Id.'"
        ::= { wfIisisDynNbrEntry 5 }

    wfIisisDynNbrDatabase OBJECT-TYPE
        SYNTAX  INTEGER
        ACCESS  read-only
        STATUS  mandatory
        DESCRIPTION
                "Database into which the Adjacency is stored,
                1=ES, 2=Level 1 IS, 3=Level 2 IS."
        DEFVAL {3}
        ::= { wfIisisDynNbrEntry 6 }

    wfIisisDynNbrType OBJECT-TYPE
        SYNTAX  INTEGER {
                         broadcast(1),
                         pointtopoint(2)
                        }
        ACCESS  read-only
        STATUS  mandatory
        DESCRIPTION
                "The type of adjacency."
        DEFVAL {broadcast}
        ::= { wfIisisDynNbrEntry 7 }

    wfIisisDynNbrPseudonodeId OBJECT-TYPE
        SYNTAX  INTEGER
        ACCESS  read-only
        STATUS  mandatory
        DESCRIPTION
                "A unique value for each known circuit."
        ::= { wfIisisDynNbrEntry 8 }

    wfIisisDynNbrHoldTime OBJECT-TYPE
        SYNTAX  INTEGER
        ACCESS  read-only
        STATUS  mandatory
        DESCRIPTION
                "Hold Time received from neighbor."
        ::= { wfIisisDynNbrEntry 9 }

    wfIisisDynNbrPriority OBJECT-TYPE
        SYNTAX  INTEGER
        ACCESS  read-only
        STATUS  mandatory
        DESCRIPTION
                "Priority to become designated router. IS only."
        ::= { wfIisisDynNbrEntry 10 }

    wfIisisDynNbrSnpaAddr OBJECT-TYPE
        SYNTAX  OCTET STRING
        ACCESS  read-only
        STATUS  mandatory
        DESCRIPTION
                "SNPA address for neighbor."
        ::= { wfIisisDynNbrEntry 11 }

    wfIisisDynNbrLanId OBJECT-TYPE
        SYNTAX  OCTET STRING
        ACCESS  read-only
        STATUS  mandatory
        DESCRIPTION
                "LAN ID of Designated IS of this interface."
        ::= { wfIisisDynNbrEntry 12 }

    END  -- BayNetworks-IISIS-MIB
