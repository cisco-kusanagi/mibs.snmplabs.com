--
-- Copyright 1997 ADC Telecommunications, Inc.  All rights reserved.
--
-- ADC Telecommunications, Inc. Confidential and Proprietary
-- This work contains valuable confidential and proprietary information.
-- Disclosure, use or reproduction without the written authorization of ADC
-- Telecommunications, Inc. is prohibited.  This unpublished work by ADC
-- Telecommunications, Inc. is protected by the laws of the United States and
-- other countries.
--

FRAMEVISIONSTD-MIB DEFINITIONS ::= BEGIN

IMPORTS
    enterprises, Counter, TimeTicks
        FROM RFC1155-SMI
    OBJECT-TYPE
        FROM RFC-1212;


-- Local Datatypes
	-- Valid DLCIs are 0-1023 and OTHER (2^31-1 is "other" VC)
	FribDLCI ::= INTEGER (0..2147483646)

	-- From SNMPv2-SMI (SimpleTest can't compile if mix v1 & v2)
	Counter32 ::= Counter
 

--------------------------------------------------------------------------
--  The ADC Kentrox FrameVision Standard Enterprise MIB Module.
--------------------------------------------------------------------------
--  internet(1).private(4).enterprises(1).adcKentrox(181).miblets(100).1
--
framevisionstd   OBJECT IDENTIFIER
        -- Following lines set defaults for this node and all nodes below it.
    ::= { enterprises adcKentrox(181) miblets(100) 1 }

--------------------------------------------------------------------------
--  Groups in the ADC Kentrox FrameVision Enterprise MIB Module.
--------------------------------------------------------------------------

fribStd		OBJECT IDENTIFIER ::= { framevisionstd 1 }
fribCfg		OBJECT IDENTIFIER ::= { framevisionstd 2 }
fribPortMon	OBJECT IDENTIFIER ::= { framevisionstd 3 }
fribVcMon	OBJECT IDENTIFIER ::= { framevisionstd 4 }
fribFrlm	OBJECT IDENTIFIER ::= { framevisionstd 5 }

--------------------------------------------------------------------
--  BEGIN -  framevision standard ??? MIB variables
--------------------------------------------------------------------
fribMibVersion	OBJECT-TYPE
				SYNTAX	INTEGER {
				version1		(1)
				}
				ACCESS	read-only
				STATUS	mandatory
				DESCRIPTION
						"."
				::= { fribStd 1}

fribMibLastChange	OBJECT-TYPE
				SYNTAX	TimeTicks
				ACCESS	read-only
				STATUS	mandatory
				DESCRIPTION
						"."
				::= { fribStd 2 }

--------------------------------------------------------------------
--  BEGIN -  framevision standard frib config MIB variables
--------------------------------------------------------------------
fribCfgTable	OBJECT-TYPE
				SYNTAX	SEQUENCE OF FribCfgEntry
				ACCESS	not-accessible
				STATUS	mandatory
				DESCRIPTION
				"."
				::= { fribCfg 1 }
 
fribCfgEntry	OBJECT-TYPE
				SYNTAX	FribCfgEntry
				ACCESS	not-accessible
				STATUS	mandatory
				DESCRIPTION
						"."
				INDEX	{ fribCfgIfIndex }
				::=	{ fribCfgTable 1 }

FribCfgEntry	::= SEQUENCE {
				fribCfgIfIndex		INTEGER,
				fribCfgLastChange	TimeTicks,
				fribCfgFrameType	INTEGER,
				fribCfgAddrOctets	INTEGER,
				fribCfgFcsBitLength	INTEGER,
				fribCfgTimeInterval	INTEGER,
				fribCfgMaxVCs		INTEGER,
				fribCfgNumberVCs	INTEGER,
				fribCfgVcAddDLCI	FribDLCI,
				fribCfgVcDelDLCI	FribDLCI
				}

fribCfgIfIndex	OBJECT-TYPE
				SYNTAX	INTEGER
				ACCESS	read-only
				STATUS	mandatory
				DESCRIPTION
						"."
				::= { fribCfgEntry 1 }

fribCfgLastChange	OBJECT-TYPE
				SYNTAX	TimeTicks
				ACCESS	read-only
				STATUS	mandatory
				DESCRIPTION
						"."
				::= { fribCfgEntry 2 }

fribCfgFrameType	OBJECT-TYPE
				SYNTAX	INTEGER {
				frameTypeNlpid (1),
				frameTypeEther (2)
				}
				ACCESS	read-write
				STATUS	mandatory
				DESCRIPTION
						"."
				::= { fribCfgEntry 3 }

fribCfgAddrOctets	OBJECT-TYPE
				SYNTAX	INTEGER {
				twoOctets (1),
				fourOctets (2)
				}
				ACCESS	read-write
				STATUS	mandatory
				DESCRIPTION
						"."
				::= { fribCfgEntry 4 }

fribCfgFcsBitLength	OBJECT-TYPE
				SYNTAX	INTEGER {
				frib16BitFcs (1),
				frib32BitFcs (2)
				}
				ACCESS	read-write
				STATUS	mandatory
				DESCRIPTION
						"."
				::= { fribCfgEntry 5 }

fribCfgTimeInterval	OBJECT-TYPE
				SYNTAX	INTEGER
				ACCESS	read-write
				STATUS	mandatory
				DESCRIPTION
						"."
				::= { fribCfgEntry 6 }

fribCfgMaxVCs	OBJECT-TYPE
				SYNTAX	INTEGER
				ACCESS	read-only
				STATUS	mandatory
				DESCRIPTION
						"."
				::= { fribCfgEntry 7 }

fribCfgNumberVCs	OBJECT-TYPE
				SYNTAX	INTEGER
				ACCESS	read-only
				STATUS	mandatory
				DESCRIPTION
						"."
				::= { fribCfgEntry 8 }

fribCfgVcAddDLCI	OBJECT-TYPE
				SYNTAX	FribDLCI
				ACCESS	read-write
				STATUS	mandatory
				DESCRIPTION
						"."
				::= { fribCfgEntry 9 }

fribCfgVcDelDLCI	OBJECT-TYPE
				SYNTAX	FribDLCI
				ACCESS	read-write
				STATUS	mandatory
				DESCRIPTION
						"."
				::= { fribCfgEntry 10 }

fribCfgVcListTable	OBJECT-TYPE
				SYNTAX	SEQUENCE OF FribCfgVcListEntry
				ACCESS	not-accessible
				STATUS	mandatory
				DESCRIPTION
						"."
				::= { fribCfg 2 }

fribCfgVcListEntry	OBJECT-TYPE
				SYNTAX	FribCfgVcListEntry
				ACCESS	not-accessible
				STATUS	mandatory
				DESCRIPTION
						"."
				INDEX { fribCfgVcListIfIndex, fribCfgVcListDLCI }
				::= { fribCfgVcListTable  1 }

FribCfgVcListEntry	::= SEQUENCE {
				fribCfgVcListIfIndex		INTEGER,
				fribCfgVcListDLCI			FribDLCI,
				fribCfgVcListCIR			INTEGER,
				fribCfgVcListEIR			INTEGER,
				fribCfgVcListCreationTime	TimeTicks
				}

fribCfgVcListIfIndex	OBJECT-TYPE
				SYNTAX	INTEGER
				ACCESS	read-only
				STATUS	mandatory
				DESCRIPTION
						"."
				::= { fribCfgVcListEntry 1 }

fribCfgVcListDLCI	OBJECT-TYPE
				SYNTAX	FribDLCI
				ACCESS	read-only
				STATUS	mandatory
				DESCRIPTION
						"."
				::= { fribCfgVcListEntry 2 }

fribCfgVcListCIR	OBJECT-TYPE
				SYNTAX	INTEGER
				ACCESS	read-write
				STATUS	mandatory
				DESCRIPTION
						"."
				::= { fribCfgVcListEntry 3 }

fribCfgVcListEIR	OBJECT-TYPE
				SYNTAX	INTEGER
				ACCESS	read-write
				STATUS	mandatory
				DESCRIPTION
						"."
				::= { fribCfgVcListEntry 4 }

fribCfgVcListCreationTime	OBJECT-TYPE
				SYNTAX	TimeTicks
				ACCESS	read-only
				STATUS	mandatory
				DESCRIPTION
						"."
				::= { fribCfgVcListEntry 5 }



--------------------------------------------------------------------
--  BEGIN -  framevision standard frib port monitoring MIB variables
--------------------------------------------------------------------

fribPortMonDuration		OBJECT-TYPE
				SYNTAX	TimeTicks
				ACCESS	read-only
				STATUS	mandatory
				DESCRIPTION
						"."
				::= { fribPortMon 1 }

fribPortMonClearData	OBJECT-TYPE
				SYNTAX	INTEGER {
				clearDataIdle (1),
				clearDataStart (2)
				}
				ACCESS	read-write
				STATUS	mandatory
				DESCRIPTION
						"."
				::= { fribPortMon 2 }

fribPortMonTable	OBJECT-TYPE
				SYNTAX	SEQUENCE OF FribPortMonEntry
				ACCESS	not-accessible
				STATUS	mandatory
				DESCRIPTION
						"."
				::= { fribPortMon 3 }

fribPortMonEntry	OBJECT-TYPE
				SYNTAX	FribPortMonEntry
				ACCESS	not-accessible
				STATUS	mandatory
				DESCRIPTION
						"."
				INDEX { fribPortMonIfIndex }
				::= { fribPortMonTable 1 }

FribPortMonEntry	::= SEQUENCE {
				fribPortMonIfIndex			INTEGER,
				fribPortMonAvailTime		TimeTicks,
				fribPortMonTxFrames			Counter32,
				fribPortMonRxFrames			Counter32,
				fribPortMonTxOctets			Counter32,
				fribPortMonRxOctets			Counter32,
				fribPortMonIpMgmtTxFrames	Counter32,
				fribPortMonIpMgmtRxFrames	Counter32,
				fribPortMonIpMgmtTxOctets	Counter32,
				fribPortMonIpMgmtRxOctets	Counter32,
				fribPortMonRxInvalidHdrs	Counter32,
				fribPortMonRxHdlcErrors		Counter32
				}


fribPortMonIfIndex		OBJECT-TYPE
				SYNTAX	INTEGER
				ACCESS	read-only
				STATUS	mandatory
				DESCRIPTION
						"."
				::= { fribPortMonEntry 1 }

fribPortMonAvailTime	OBJECT-TYPE
				SYNTAX	TimeTicks
				ACCESS	read-only
				STATUS	mandatory
				DESCRIPTION
						"."
				::= { fribPortMonEntry 2 }

fribPortMonTxFrames		OBJECT-TYPE
				SYNTAX	Counter32
				ACCESS	read-only
				STATUS	mandatory
				DESCRIPTION
						"."
				::= { fribPortMonEntry 3 }

fribPortMonRxFrames		OBJECT-TYPE
				SYNTAX	Counter32
				ACCESS	read-only
				STATUS	mandatory
				DESCRIPTION
						"."
				::= { fribPortMonEntry 4 }

fribPortMonTxOctets		OBJECT-TYPE
				SYNTAX	Counter32
				ACCESS	read-only
				STATUS	mandatory
				DESCRIPTION
						"."
				::= { fribPortMonEntry 5 }

fribPortMonRxOctets		OBJECT-TYPE
				SYNTAX	Counter32
				ACCESS	read-only
				STATUS	mandatory
				DESCRIPTION
						"."
				::= { fribPortMonEntry 6 }

fribPortMonIpMgmtTxFrames	OBJECT-TYPE
				SYNTAX	Counter32
				ACCESS	read-only
				STATUS	mandatory
				DESCRIPTION
						"."
				::= { fribPortMonEntry 7 }

fribPortMonIpMgmtRxFrames	OBJECT-TYPE
				SYNTAX	Counter32
				ACCESS	read-only
				STATUS	mandatory
				DESCRIPTION
						"."
				::= { fribPortMonEntry 8 }

fribPortMonIpMgmtTxOctets	OBJECT-TYPE
				SYNTAX	Counter32
				ACCESS	read-only
				STATUS	mandatory
				DESCRIPTION
						"."
				::= { fribPortMonEntry 9 }

fribPortMonIpMgmtRxOctets	OBJECT-TYPE
				SYNTAX	Counter32
				ACCESS	read-only
				STATUS	mandatory
				DESCRIPTION
						"."
				::= { fribPortMonEntry 10 }

fribPortMonRxInvalidHdrs	OBJECT-TYPE
				SYNTAX	Counter32
				ACCESS	read-only
				STATUS	mandatory
				DESCRIPTION
						"."
				::= { fribPortMonEntry 11 }

fribPortMonRxHdlcErrors		OBJECT-TYPE
				SYNTAX	Counter32
				ACCESS	read-only
				STATUS	mandatory
				DESCRIPTION
						"."
				::= { fribPortMonEntry 12 }


--------------------------------------------------------------------
--  BEGIN -  framevision standard frib vc monitoring MIB variables
--------------------------------------------------------------------

fribVcStatDuration		OBJECT-TYPE
				SYNTAX	TimeTicks
				ACCESS	read-only
				STATUS	mandatory
				DESCRIPTION
						"."
				::= { fribVcMon 1 }
					
fribVcStatClearData		OBJECT-TYPE
				SYNTAX	INTEGER {
				clearDataIdle  (1),
				clearDataStart (2)
				}
				ACCESS	read-write
				STATUS	mandatory
				DESCRIPTION
						"."
				::= { fribVcMon 2 }


fribVcStatTable	OBJECT-TYPE
				SYNTAX	SEQUENCE OF FribVcStatEntry
				ACCESS	not-accessible
				STATUS	mandatory
				DESCRIPTION
						"."
				::= { fribVcMon 3 }

fribVcStatEntry	OBJECT-TYPE
				SYNTAX	FribVcStatEntry
				ACCESS	not-accessible
				STATUS	mandatory
				DESCRIPTION
						"."
				INDEX	{ fribVcStatIfIndex, fribVcStatDLCI }
				::= { fribVcStatTable 1 }
				
FribVcStatEntry	::= SEQUENCE {
				fribVcStatIfIndex	INTEGER,
				fribVcStatDLCI		INTEGER,
				fribVcStatTxFrames	Counter32,
				fribVcStatRxFrames	Counter32,
				fribVcStatTxOctets	Counter32,
				fribVcStatRxOctets	Counter32,
				fribVcStatTxDEs		Counter32,
				fribVcStatRxDEs		Counter32,
				fribVcStatTxFECNs	Counter32,
				fribVcStatRxFECNs	Counter32,
				fribVcStatTxBECNs	Counter32,
				fribVcStatRxBECNs	Counter32
				}

fribVcStatIfIndex	OBJECT-TYPE
				SYNTAX	INTEGER
				ACCESS	read-only
				STATUS	mandatory
				DESCRIPTION
						"."
				::= { fribVcStatEntry 1 }

fribVcStatDLCI	OBJECT-TYPE
				SYNTAX	INTEGER
				ACCESS	read-only
				STATUS	mandatory
				DESCRIPTION
						"."
				::= { fribVcStatEntry 2 }

fribVcStatTxFrames	OBJECT-TYPE
				SYNTAX	Counter32
				ACCESS	read-only
				STATUS	mandatory
				DESCRIPTION
						"."
				::= { fribVcStatEntry 3 }

fribVcStatRxFrames	OBJECT-TYPE
				SYNTAX	Counter32
				ACCESS	read-only
				STATUS	mandatory
				DESCRIPTION
						"."
				::= { fribVcStatEntry 4 }

fribVcStatTxOctets	OBJECT-TYPE
				SYNTAX	Counter32
				ACCESS	read-only
				STATUS	mandatory
				DESCRIPTION
						"."
				::= { fribVcStatEntry 5 }

fribVcStatRxOctets	OBJECT-TYPE
				SYNTAX	Counter32
				ACCESS	read-only
				STATUS	mandatory
				DESCRIPTION
						"."
				::= { fribVcStatEntry 6 }

fribVcStatTxDEs	OBJECT-TYPE
				SYNTAX	Counter32
				ACCESS	read-only
				STATUS	mandatory
				DESCRIPTION
						"."
				::= { fribVcStatEntry 7 }

fribVcStatRxDEs	OBJECT-TYPE
				SYNTAX	Counter32
				ACCESS	read-only
				STATUS	mandatory
				DESCRIPTION
						"."
				::= { fribVcStatEntry 8 }

fribVcStatTxFECNs	OBJECT-TYPE
				SYNTAX	Counter32
				ACCESS	read-only
				STATUS	mandatory
				DESCRIPTION
						"."
				::= { fribVcStatEntry 9 }

fribVcStatRxFECNs	OBJECT-TYPE
				SYNTAX	Counter32
				ACCESS	read-only
				STATUS	mandatory
				DESCRIPTION
						"."
				::= { fribVcStatEntry 10 }

fribVcStatTxBECNs	OBJECT-TYPE
				SYNTAX	Counter32
				ACCESS	read-only
				STATUS	mandatory
				DESCRIPTION
						"."
				::= { fribVcStatEntry 11 }

fribVcStatRxBECNs	OBJECT-TYPE
				SYNTAX	Counter32
				ACCESS	read-only
				STATUS	mandatory
				DESCRIPTION
						"."
				::= { fribVcStatEntry 12 }


fribVcUtilDuration	OBJECT-TYPE
				SYNTAX	TimeTicks
				ACCESS	read-only
				STATUS	mandatory
				DESCRIPTION
						"."
				::= { fribVcMon 4 }

fribVcUtilClearData	OBJECT-TYPE
				SYNTAX	INTEGER {
				clearDataIdle  (1),
				clearDataStart (2)
				}
				ACCESS	read-write
				STATUS	mandatory
				DESCRIPTION
						"."
				::= { fribVcMon 5 }

fribVcUtilTable	OBJECT-TYPE
				SYNTAX SEQUENCE OF FribVcUtilEntry
				ACCESS	not-accessible
				STATUS	mandatory
				DESCRIPTION
						"."
				::= { fribVcMon 6 }

fribVcUtilEntry	OBJECT-TYPE
				SYNTAX	FribVcUtilEntry
				ACCESS	not-accessible
				STATUS	mandatory
				DESCRIPTION
						"."
				INDEX { fribVcUtilIfIndex, fribVcUtilDLCI }
				::= { fribVcUtilTable 1 }

FribVcUtilEntry	::= SEQUENCE {
				fribVcUtilIfIndex				INTEGER,
				fribVcUtilDLCI					FribDLCI,
				fribVcUtilCirExceededTx			Counter32,
				fribVcUtilCirOctetsExceededTx	Counter32,
				fribVcUtilEirExceededTx			Counter32,
				fribVcUtilEirOctetsExceededTx	Counter32
				}

fribVcUtilIfIndex	OBJECT-TYPE
				SYNTAX	INTEGER
				ACCESS	read-only
				STATUS	mandatory
				DESCRIPTION
						"."
				::= { fribVcUtilEntry 1 }

fribVcUtilDLCI		OBJECT-TYPE
				SYNTAX	FribDLCI
				ACCESS	read-only
				STATUS	mandatory
				DESCRIPTION
						"."
				::= { fribVcUtilEntry 2 }

fribVcUtilCirExceededTx		OBJECT-TYPE
				SYNTAX	Counter32
				ACCESS	read-only
				STATUS	mandatory
				DESCRIPTION
						"."
				::= { fribVcUtilEntry 3 }

fribVcUtilCirOctetsExceededTx	OBJECT-TYPE
				SYNTAX	Counter32
				ACCESS	read-only
				STATUS	mandatory
				DESCRIPTION
						"."
				::= { fribVcUtilEntry 4 }

fribVcUtilEirExceededTx			OBJECT-TYPE
				SYNTAX	Counter32
				ACCESS	read-only
				STATUS	mandatory
				DESCRIPTION
						"."
				::= { fribVcUtilEntry 5 }

fribVcUtilEirOctetsExceededTx	OBJECT-TYPE
				SYNTAX	Counter32
				ACCESS	read-only
				STATUS	mandatory
				DESCRIPTION
						"."
				::= { fribVcUtilEntry 6 }


--------------------------------------------------------------------
--  BEGIN -  framevision standard frib frame-relay link management MIB variables
--------------------------------------------------------------------

fribFrlmCfgTable	OBJECT-TYPE
				SYNTAX	SEQUENCE OF FribFrlmCfgEntry
				ACCESS	not-accessible
				STATUS	mandatory
				DESCRIPTION
						"."
				::= { fribFrlm 1 }

fribFrlmCfgEntry	OBJECT-TYPE
				SYNTAX	FribFrlmCfgEntry
				ACCESS	not-accessible
				STATUS	mandatory
				DESCRIPTION
						"."
				INDEX { fribFrlmCfgIfIndex }
				::= { fribFrlmCfgTable 1 }

FribFrlmCfgEntry	::= SEQUENCE {
				fribFrlmCfgIfIndex			INTEGER,
				fribFrlmCfgLastChange		TimeTicks,
				fribFrlmCfgProtocol			INTEGER,
				fribFrlmCfgSpoofing			INTEGER,
				fribFrlmCfgT391				INTEGER,
				fribFrlmCfgN392				INTEGER,
				fribFrlmCfgN393				INTEGER,
				fribFrlmCfgSpoofingStatus	INTEGER
				}



fribFrlmCfgIfIndex		OBJECT-TYPE
				SYNTAX	INTEGER
				ACCESS	read-only
				STATUS	mandatory
				DESCRIPTION
						"."
				::= { fribFrlmCfgEntry 1 }

fribFrlmCfgLastChange	OBJECT-TYPE
				SYNTAX	TimeTicks
				ACCESS	read-only
				STATUS	mandatory
				DESCRIPTION
						"."
				::= { fribFrlmCfgEntry 2 }

fribFrlmCfgProtocol		OBJECT-TYPE
				SYNTAX	INTEGER {
				none		(1),
				lmi			(2),
				ansiT1617D	(3),
				ccittQ933A	(4)
				}
				ACCESS	read-write
				STATUS	mandatory
				DESCRIPTION
						"."
				::= { fribFrlmCfgEntry 3 }

fribFrlmCfgSpoofing		OBJECT-TYPE
				SYNTAX	INTEGER {
				spoofingEnabled  (1),
				spoofingDisabled (2)
				}
				ACCESS	read-write
				STATUS	mandatory
				DESCRIPTION
						"."
				::= { fribFrlmCfgEntry 4 }

fribFrlmCfgT391			OBJECT-TYPE
				SYNTAX	INTEGER (5..30)
				ACCESS	read-write
				STATUS	mandatory
				DESCRIPTION
						"."
				::= { fribFrlmCfgEntry 5 }

fribFrlmCfgN392			OBJECT-TYPE
				SYNTAX	INTEGER (1..10)
				ACCESS	read-write
				STATUS	mandatory
				DESCRIPTION
						"."
				::= { fribFrlmCfgEntry 6 }

fribFrlmCfgN393			OBJECT-TYPE
				SYNTAX	INTEGER (1..10)
				ACCESS	read-write
				STATUS	mandatory
				DESCRIPTION
						"."
				::= { fribFrlmCfgEntry 7 }

fribFrlmCfgSpoofingStatus	OBJECT-TYPE
				SYNTAX	INTEGER {
				spoofingInactive (1),
				spoofingActive   (2)
				}
				ACCESS	read-only
				STATUS	mandatory
				DESCRIPTION
						"."
				::= { fribFrlmCfgEntry 8 }

fribFrlmPortDuration	OBJECT-TYPE
				SYNTAX	TimeTicks
				ACCESS	read-only
				STATUS	mandatory
				DESCRIPTION
						"."
				::= { fribFrlm 2 }

fribFrlmPortClearData	OBJECT-TYPE
				SYNTAX	INTEGER {
				clearDataIdle	(1),
				clearDataStart	(2)
				}
				ACCESS	read-write
				STATUS	mandatory
				DESCRIPTION
						"."
				::= { fribFrlm 3 }

fribFrlmPortTable	OBJECT-TYPE
				SYNTAX	SEQUENCE OF FribFrlmPortEntry
				ACCESS	not-accessible
				STATUS	mandatory
				DESCRIPTION
						"."
				::= { fribFrlm 4 }

fribFrlmPortEntry	OBJECT-TYPE
				SYNTAX	FribFrlmPortEntry
				ACCESS	not-accessible
				STATUS	mandatory
				DESCRIPTION
						"."
				INDEX { fribFrlmPortIfIndex }
				::= { fribFrlmPortTable 1 }

FribFrlmPortEntry	::= SEQUENCE {
				fribFrlmPortIfIndex					INTEGER,
				fribFrlmPortSendSeqNumTx			Counter32,
				fribFrlmPortSendSeqNumRx			Counter32,
				fribFrlmPortReceiveSeqNumTx			Counter32,
				fribFrlmPortReceiveSeqNumRx			Counter32,
				fribFrlmPortStatusRsp				Counter32,
				fribFrlmPortStatusRspMissed			Counter32,
				fribFrlmPortStatusRspSpoofed		Counter32,
				fribFrlmPortStatusFullRsp			Counter32,
				fribFrlmPortStatusFullRspMissed		Counter32,
				fribFrlmPortStatusFullRspSpoofed	Counter32
				}


fribFrlmPortIfIndex		OBJECT-TYPE
				SYNTAX	INTEGER
				ACCESS	read-only
				STATUS	mandatory
				DESCRIPTION
						"."
				::= { fribFrlmPortEntry 1 }

fribFrlmPortSendSeqNumTx	OBJECT-TYPE
				SYNTAX	Counter32
				ACCESS	read-only
				STATUS	mandatory
				DESCRIPTION
						"."
				::= { fribFrlmPortEntry 2 }

fribFrlmPortSendSeqNumRx	OBJECT-TYPE
				SYNTAX	Counter32
				ACCESS	read-only
				STATUS	mandatory
				DESCRIPTION
						"."
				::= { fribFrlmPortEntry 3 }

fribFrlmPortReceiveSeqNumTx		OBJECT-TYPE
				SYNTAX	Counter32
				ACCESS	read-only
				STATUS	mandatory
				DESCRIPTION
						"."
				::= { fribFrlmPortEntry 4 }

fribFrlmPortReceiveSeqNumRx		OBJECT-TYPE
				SYNTAX	Counter32
				ACCESS	read-only
				STATUS	mandatory
				DESCRIPTION
						"."
				::= { fribFrlmPortEntry 5 }

fribFrlmPortStatusRsp		OBJECT-TYPE
				SYNTAX	Counter32
				ACCESS	read-only
				STATUS	mandatory
				DESCRIPTION
						"."
				::= { fribFrlmPortEntry 6 }

fribFrlmPortStatusRspMissed		OBJECT-TYPE
				SYNTAX	Counter32
				ACCESS	read-only
				STATUS	mandatory
				DESCRIPTION
						"."
				::= { fribFrlmPortEntry 7 }

fribFrlmPortStatusRspSpoofed	OBJECT-TYPE
				SYNTAX	Counter32
				ACCESS	read-only
				STATUS	mandatory
				DESCRIPTION
						"."
				::= { fribFrlmPortEntry 8 }

fribFrlmPortStatusFullRsp	OBJECT-TYPE
				SYNTAX	Counter32
				ACCESS	read-only
				STATUS	mandatory
				DESCRIPTION
						"."
				::= { fribFrlmPortEntry 9 }

fribFrlmPortStatusFullRspMissed		OBJECT-TYPE
				SYNTAX	Counter32
				ACCESS	read-only
				STATUS	mandatory
				DESCRIPTION
						"."
				::= { fribFrlmPortEntry 10 }

fribFrlmPortStatusFullRspSpoofed	OBJECT-TYPE
				SYNTAX	Counter32
				ACCESS	read-only
				STATUS	mandatory
				DESCRIPTION
						"."
				::= { fribFrlmPortEntry 11 }

fribFrlmStatusDuration	OBJECT-TYPE
				SYNTAX	TimeTicks
				ACCESS	read-only
				STATUS	mandatory
				DESCRIPTION
						"."
				::= { fribFrlm 5 }

fribFrlmStatusClearData	OBJECT-TYPE
				SYNTAX	INTEGER {
				clearDataIdle  (1),
				clearDataStart (2)
				}
				ACCESS	read-write
				STATUS	mandatory
				DESCRIPTION
						"."
				::= { fribFrlm 6 }

fribFrlmStatusTable	OBJECT-TYPE
				SYNTAX	SEQUENCE OF FribFrlmStatusEntry
				ACCESS	not-accessible
				STATUS	mandatory
				DESCRIPTION
						"."
				::= { fribFrlm 7 }

fribFrlmStatusEntry	OBJECT-TYPE
				SYNTAX	FribFrlmStatusEntry
				ACCESS	not-accessible
				STATUS	mandatory
				DESCRIPTION
						"."
				INDEX { fribVcUtilIfIndex, fribVcUtilDLCI }
				::= { fribFrlmStatusTable 1 }

FribFrlmStatusEntry	::= SEQUENCE {
				fribFrlmStatusIfIndex		INTEGER,
				fribFrlmStatusDLCI			FribDLCI,
				fribFrlmStatusStatus		INTEGER,
				fribFrlmStatusDownEvents	Counter32,
				fribFrlmStatusActiveSecs	Counter32,
				fribFrlmStatusTotalSecs		Counter32
				}

fribFrlmStatusIfIndex		OBJECT-TYPE
				SYNTAX	INTEGER
				ACCESS	read-only
				STATUS	mandatory
				DESCRIPTION
						"."
				::= { fribFrlmStatusEntry 1 }

fribFrlmStatusDLCI			OBJECT-TYPE
				SYNTAX	FribDLCI
				ACCESS	read-only
				STATUS	mandatory
				DESCRIPTION
						"."
				::= { fribFrlmStatusEntry 2 }

fribFrlmStatusStatus		OBJECT-TYPE
				SYNTAX	INTEGER {
				frlmStatusNew		(1),
				frlmStatusDelete	(2),
				frlmStatusActive	(3),
				frlmStatusInactive	(4),
				frlmStatusSpoofed	(5)
				}
				ACCESS	read-only
				STATUS	mandatory
				DESCRIPTION
						"."
				::= { fribFrlmStatusEntry 3 }

fribFrlmStatusDownEvents	OBJECT-TYPE
				SYNTAX	Counter32
				ACCESS	read-only
				STATUS	mandatory
				DESCRIPTION
						"."
				::= { fribFrlmStatusEntry 4 }

fribFrlmStatusActiveSecs	OBJECT-TYPE
				SYNTAX	Counter32
				ACCESS	read-only
				STATUS	mandatory
				DESCRIPTION
						"."
				::= { fribFrlmStatusEntry 5 }

fribFrlmStatusTotalSecs		OBJECT-TYPE
				SYNTAX	Counter32
				ACCESS	read-only
				STATUS	mandatory
				DESCRIPTION
						"."
				::= { fribFrlmStatusEntry 6 }




END
