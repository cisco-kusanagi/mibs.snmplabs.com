-- efdata.mib 
-- For use with DTMX5000 release: 4.2
--
--
--

EFDATA-MIB DEFINITIONS ::= BEGIN
IMPORTS
    DisplayString , PhysAddress
        FROM RFC1213-MIB
    enterprises, Counter, IpAddress
        FROM RFC1155-SMI
    OBJECT-TYPE
        FROM RFC-1212;


efdata OBJECT IDENTIFIER ::= { enterprises 6247 }

spectracast OBJECT IDENTIFIER ::= { efdata 3 }

dtmx5000 OBJECT IDENTIFIER ::= { spectracast 1 }


cbGateway OBJECT IDENTIFIER ::= { dtmx5000 1 }

cbStatistics OBJECT IDENTIFIER ::= { cbGateway 1 }

    cbStatGeneral OBJECT IDENTIFIER ::= { cbStatistics 1 }

        cbStatNumBytesTXed OBJECT-TYPE 
            SYNTAX  Counter 
            ACCESS  read-only
            STATUS  mandatory
            DESCRIPTION
"Number of bytes transmitted since last statistics reset."
			--DEFAULT test-function    it_exists
			--DEFAULT    set-function    set_%n
			--DEFAULT    get-function    get_%n
			--DEFAULT    next-function    std_next
			--DEFAULT cookie        (char *) 0
            ::= { cbStatGeneral 1 }

        cbStatNumOfPackets OBJECT-TYPE 
            SYNTAX  Counter 
            ACCESS  read-only
            STATUS  mandatory
            DESCRIPTION
"Number of data packets transmitted since last statistics reset."
			--DEFAULT test-function    it_exists
			--DEFAULT    set-function    set_%n
			--DEFAULT    get-function    get_%n
			--DEFAULT    next-function    std_next
			--DEFAULT cookie        (char *) 0
            ::= { cbStatGeneral 2 }

        cbStatAvrPktSize OBJECT-TYPE 
            SYNTAX  Counter 
            ACCESS  read-only
            STATUS  mandatory
            DESCRIPTION
"Average packet size since last statistics reset."
			--DEFAULT test-function    it_exists
			--DEFAULT    set-function    set_%n
			--DEFAULT    get-function    get_%n
			--DEFAULT    next-function    std_next
			--DEFAULT cookie        (char *) 0
            ::= { cbStatGeneral 3 }

        cbStatAvrBytesPerSec OBJECT-TYPE 
            SYNTAX  Counter 
            ACCESS  read-only
            STATUS  mandatory
            DESCRIPTION
"Average speed in bytes per second since last statistics reset."
			--DEFAULT test-function    it_exists
			--DEFAULT    set-function    set_%n
			--DEFAULT    get-function    get_%n
			--DEFAULT    next-function    std_next
			--DEFAULT cookie        (char *) 0
            ::= { cbStatGeneral 4 }

        cbStatNumPacketDiscarded OBJECT-TYPE 
            SYNTAX  Counter 
            ACCESS  read-only
            STATUS  mandatory
            DESCRIPTION
"Number of data packets that were discarded since last statistics reset."
			--DEFAULT test-function    it_exists
			--DEFAULT    set-function    set_%n
			--DEFAULT    get-function    get_%n
			--DEFAULT    next-function    std_next
			--DEFAULT cookie        (char *) 0
            ::= { cbStatGeneral 5 }

        cbStatNumNMSFrames OBJECT-TYPE 
            SYNTAX  Counter 
            ACCESS  read-only
            STATUS  mandatory
            DESCRIPTION
"Number of NMS packets received since last statistics reset."
			--DEFAULT test-function    it_exists
			--DEFAULT    set-function    set_%n
			--DEFAULT    get-function    get_%n
			--DEFAULT    next-function    std_next
			--DEFAULT cookie        (char *) 0
            ::= { cbStatGeneral 6 }

        cbCPULoad OBJECT-TYPE 
            SYNTAX  Counter 
            ACCESS  read-only
            STATUS  mandatory
            DESCRIPTION
"Current CPU Load in percents (0-100)."
			--DEFAULT test-function    it_exists
			--DEFAULT    set-function    set_%n
			--DEFAULT    get-function    get_%n
			--DEFAULT    next-function    std_next
			--DEFAULT cookie        (char *) 0
            ::= { cbStatGeneral 7 }

        cbMemoryUsage OBJECT-TYPE 
            SYNTAX  Counter 
            ACCESS  read-only
            STATUS  mandatory
            DESCRIPTION
"Current Memory Usage in percents (0-100)."
			--DEFAULT test-function    it_exists
			--DEFAULT    set-function    set_%n
			--DEFAULT    get-function    get_%n
			--DEFAULT    next-function    std_next
			--DEFAULT cookie        (char *) 0
            ::= { cbStatGeneral 8 }

        cbStatReset OBJECT-TYPE 
            SYNTAX  INTEGER 
				{
				cbTrue (1),
				cbFalse (0)
				}
            ACCESS  write-only
            STATUS  mandatory
            DESCRIPTION
"Set to cbTrue in order to reset the general statistics values
(either in active or non-active mode)."
			--DEFAULT test-function    it_exists
			--DEFAULT    set-function    set_%n
			--DEFAULT    get-function    get_%n
			--DEFAULT    next-function    std_next
			--DEFAULT cookie        (char *) 0
            ::= { cbStatGeneral 9 }

	    cbStatNumClients OBJECT-TYPE 
	         SYNTAX  Counter 
	         ACCESS  read-only
	         STATUS  mandatory
	         DESCRIPTION
"Number of clients currently connected to the Gateway.
It is not part of the General Statistics since the 
cbStatReset does not change its value."
			--DEFAULT test-function    it_exists
			--DEFAULT    set-function    set_%n
			--DEFAULT    get-function    get_%n
			--DEFAULT    next-function    std_next
			--DEFAULT cookie        (char *) 0
	        ::= { cbStatGeneral 10 }

    cbStatClient OBJECT IDENTIFIER ::= { cbStatistics 2 }

        cbClientIP OBJECT-TYPE 
            SYNTAX  IpAddress 
            ACCESS  read-write
            STATUS  mandatory
            DESCRIPTION
"The IP address of the client. The rest of the params in
cbStatClient reffers to this IP.
In order to get a statistics on a single clients,
set cbClientIP to the IP of the desired client and
get the results under cbClientStatistics. 
Continuously get operations of the rest of the params
will give the updated statistics values without a need
to set cbClientIP again and again."
			--DEFAULT test-function    it_exists
			--DEFAULT    set-function    set_%n
			--DEFAULT    get-function    get_%n
			--DEFAULT    next-function    std_next
			--DEFAULT cookie        (char *) 0
            ::= { cbStatClient 1 }

		cbClientStatistics OBJECT IDENTIFIER ::= { cbStatClient 2 }

			cbClNumSeconds OBJECT-TYPE 
				SYNTAX  Counter 
				ACCESS  read-only
				STATUS  mandatory
				DESCRIPTION
"The number of seconds since the client statistics are
active.
The statistics values are reset automaticaly by
the gateway (as well as by setting cbClReset) according
to the value of cbFreqClientsInfoReset."
				--DEFAULT test-function    it_exists
				--DEFAULT    set-function    set_%n
				--DEFAULT    get-function    get_%n
				--DEFAULT    next-function    std_next
				--DEFAULT cookie        (char *) 0
				::= { cbClientStatistics 1 }

			cbClNumKBytes OBJECT-TYPE 
				SYNTAX  Counter
				ACCESS  read-only
				STATUS  mandatory
				DESCRIPTION
"Number of bytes transmitted to IP==cbClientIP 
in the last cbClNumSeconds seconds."
				--DEFAULT test-function    it_exists
				--DEFAULT    set-function    set_%n
				--DEFAULT    get-function    get_%n
				--DEFAULT    next-function    std_next
				--DEFAULT cookie        (char *) 0
				::= { cbClientStatistics 2 }

			cbClNumPackets OBJECT-TYPE 
				SYNTAX  Counter 
				ACCESS  read-only
				STATUS  mandatory
				DESCRIPTION
"Number of packets transmitted to IP==cbClientIP 
in the last cbClNumSeconds seconds."
				--DEFAULT test-function    it_exists
				--DEFAULT    set-function    set_%n
				--DEFAULT    get-function    get_%n
				--DEFAULT    next-function    std_next
				--DEFAULT cookie        (char *) 0
				::= { cbClientStatistics 3 }


			cbClAvrBytesPerSecond OBJECT-TYPE 
				SYNTAX  Counter 
				ACCESS  read-only
				STATUS  mandatory
				DESCRIPTION
"Average transfer rate in bytes per second for this client."
				--DEFAULT test-function    it_exists
				--DEFAULT    set-function    set_%n
				--DEFAULT    get-function    get_%n
				--DEFAULT    next-function    std_next
				--DEFAULT cookie        (char *) 0
				::= { cbClientStatistics 4 }


			cbClNumPacketsDiscarded OBJECT-TYPE 
				SYNTAX  Counter 
				ACCESS  read-only
				STATUS  mandatory
				DESCRIPTION
"Number of packets discarded to IP==cbClientIP 
in the last cbClNumSeconds seconds."
				--DEFAULT test-function    it_exists
				--DEFAULT    set-function    set_%n
				--DEFAULT    get-function    get_%n
				--DEFAULT    next-function    std_next
				--DEFAULT cookie        (char *) 0
				::= { cbClientStatistics 5 }


			cbClStatReset OBJECT-TYPE 
				SYNTAX  INTEGER 
					{
					cbTrue (1),
					cbFalse (0)
					}
				ACCESS  write-only
				STATUS  mandatory
				DESCRIPTION
"Set ot non-zero - Reset the statistics values for the client cbClientIP."
				--DEFAULT test-function    it_exists
				--DEFAULT    set-function    set_%n
				--DEFAULT    get-function    get_%n
				--DEFAULT    next-function    std_next
				--DEFAULT cookie        (char *) 0
				::= { cbClientStatistics 6 }

			cbClEncrEnbled OBJECT-TYPE 
				SYNTAX  INTEGER 
					{
					cbTrue (1),
					cbFalse (0)
					}
				ACCESS  read-only
				STATUS  mandatory
				DESCRIPTION
"If this variable is True then the user desire encryption.
This value may not changed and it is NOT changed by setting cbClStatReset."
				--DEFAULT test-function    it_exists
				--DEFAULT    set-function    set_%n
				--DEFAULT    get-function    get_%n
				--DEFAULT    next-function    std_next
				--DEFAULT cookie        (char *) 0
				::= { cbClientStatistics 7 }

    cbStatClTable OBJECT IDENTIFIER ::= { cbStatistics 3 }

        cbClTable OBJECT-TYPE
            SYNTAX  SEQUENCE OF CbClTableNode
            ACCESS  not-accessible
            STATUS  mandatory
            DESCRIPTION 
"This table contains updated statistics of all clients known to the gateway."
            --DEFAULT test-function-async test_%p
            --DEFAULT next-function-async next_%p
            --DEFAULT get-function-async get_%p
            --DEFAULT set-function-async set_%p
            --DEFAULT cookie (char*) 0
            ::= { cbStatClTable 1 }

            cbClTableNode OBJECT-TYPE
                SYNTAX  CbClTableNode
                ACCESS  not-accessible
                STATUS  mandatory
                         DESCRIPTION "Information about a particular client."
                         INDEX   {cbClTableIP}
            ::= { cbClTable 1 }

            CbClTableNode ::=
            SEQUENCE {
                cbClTableIP
                    IpAddress,
                cbClTableStampTime
                    INTEGER,
				cbClTableStartTime
					INTEGER,
				cbClTableTotalPackets
					INTEGER,
				cbClTableBytesInSec
					INTEGER,
				cbClTablePacketsDiscr
					INTEGER,
				cbClTableKBytesTxed
					INTEGER,
				cbClTableReset
					INTEGER
                }

            cbClTableIP OBJECT-TYPE
                SYNTAX  IpAddress
                ACCESS  read-only
                STATUS  mandatory
                DESCRIPTION	"The clients IP."
                ::= { cbClTableNode 1 }

            cbClTableStampTime OBJECT-TYPE
                SYNTAX  INTEGER
                ACCESS  read-only
                STATUS  mandatory
                DESCRIPTION	"The clients Stamp Time."
                ::= { cbClTableNode 2 }

            cbClTableStartTime OBJECT-TYPE
                SYNTAX  INTEGER
                ACCESS  read-only
                STATUS  mandatory
                DESCRIPTION	"The clients Start Time."
                ::= { cbClTableNode 3 }

            cbClTableTotalPackets OBJECT-TYPE
                SYNTAX  INTEGER
                ACCESS  read-only
                STATUS  mandatory
                DESCRIPTION	"Total Packets transmitted to this client."
                ::= { cbClTableNode 4 }

            cbClTableBytesInSec OBJECT-TYPE
                SYNTAX  INTEGER
                ACCESS  read-only
                STATUS  mandatory
                DESCRIPTION	"The clients Rate in Bytes/Sec."
                ::= { cbClTableNode 5 }

            cbClTablePacketsDiscr OBJECT-TYPE
                SYNTAX  INTEGER
                ACCESS  read-only
                STATUS  mandatory
                DESCRIPTION	"The Total Packets which were discarded to this client"
                ::= { cbClTableNode 6 }

            cbClTableKBytesTxed OBJECT-TYPE
                SYNTAX  INTEGER
                ACCESS  read-only
                STATUS  mandatory
                DESCRIPTION	"The Total KBytes transmitted to this client."
                ::= { cbClTableNode 7 }

            cbClTableReset OBJECT-TYPE
                SYNTAX  INTEGER
					{
					cbNo (0),
					cbYes (1)
					}
                ACCESS  read-write
                STATUS  mandatory
                DESCRIPTION	"Reset the client statistics."
                ::= { cbClTableNode 8 }

cbConfig OBJECT IDENTIFIER ::= { cbGateway 2 } 

    cbNetworkParam OBJECT IDENTIFIER ::= { cbConfig 1 } 

        cbNetGatewayMngIP OBJECT-TYPE 
             SYNTAX  IpAddress 
             ACCESS  read-only
             STATUS  mandatory
             DESCRIPTION
"C&M IP Address.
Changing this parameter will affect after system reset."
			--DEFAULT test-function    it_exists
			--DEFAULT    set-function    set_%n
			--DEFAULT    get-function    get_%n
			--DEFAULT    next-function    std_next
			--DEFAULT cookie        (char *) 0
            ::= { cbNetworkParam 1 }

        cbNetGatewayMngSubnetMask OBJECT-TYPE 
             SYNTAX  IpAddress 
             ACCESS  read-only
             STATUS  mandatory
             DESCRIPTION
"C&M subnet mask.
Changing this parameter will affect after system reset."
			--DEFAULT test-function    it_exists
			--DEFAULT    set-function    set_%n
			--DEFAULT    get-function    get_%n
			--DEFAULT    next-function    std_next
			--DEFAULT cookie        (char *) 0
            ::= { cbNetworkParam 2 }

        cbNetDefaultGateway OBJECT-TYPE 
             SYNTAX  IpAddress 
             ACCESS  read-write
             STATUS  mandatory
             DESCRIPTION
"The default gateway IP Address. The term gateway here, is reffering to another
station in the same LAN of the CATV-Gateway. All IP packets that the CATV-Gateway
is sending to the LAN (and not over the viedo) and their IP Address do not belong
to the CATV-Gateway local ring will be sent to this gateway station unless
cbNetDefaultGateway is 0.0.0.0
Changing this parameter will affect after system reset."
			--DEFAULT test-function    it_exists
			--DEFAULT    set-function    set_%n
			--DEFAULT    get-function    get_%n
			--DEFAULT    next-function    std_next
			--DEFAULT cookie        (char *) 0
            ::= { cbNetworkParam 3 }

        cbNetPromiscuous OBJECT-TYPE 
            SYNTAX  INTEGER 
                {
                cbEnabled (1),
                cbDisabled (0)
                }
            ACCESS  read-write
            STATUS  mandatory
            DESCRIPTION
"Enables/Disables Promiscuous Mode. 
Changing this parameter will affect after system reset."
				--DEFAULT test-function    it_exists
				--DEFAULT    set-function    set_%n
				--DEFAULT    get-function    get_%n
				--DEFAULT    next-function    std_next
				--DEFAULT cookie        (char *) 0
            ::= { cbNetworkParam 4 }

        cbNetUnregisteredUsers OBJECT-TYPE 
            SYNTAX  INTEGER 
                {
                cbEnabled (1),
                cbDisabled (0)
                }
            ACCESS  read-write
            STATUS  mandatory
            DESCRIPTION
"Enables/Disables Unregistered Users."
				--DEFAULT test-function    it_exists
				--DEFAULT    set-function    set_%n
				--DEFAULT    get-function    get_%n
				--DEFAULT    next-function    std_next
				--DEFAULT cookie        (char *) 0
            ::= { cbNetworkParam 5 }

        cbNetMulticast OBJECT-TYPE 
            SYNTAX  INTEGER 
                {
                cbEnabled (1),
                cbDisabled (0)
                }
            ACCESS  read-write
            STATUS  mandatory
            DESCRIPTION
"Enables/Disables receive Multicast Packets."
				--DEFAULT test-function    it_exists
				--DEFAULT    set-function    set_%n
				--DEFAULT    get-function    get_%n
				--DEFAULT    next-function    std_next
				--DEFAULT cookie        (char *) 0
            ::= { cbNetworkParam 6 }

        cbNetDualNIC OBJECT-TYPE 
            SYNTAX  INTEGER 
                {
                cbEnabled (1),
                cbDisabled (0)
                }
            ACCESS  read-write
            STATUS  mandatory
            DESCRIPTION
"Enables/Disables Transportation NIC
Changing this parameter will affect after system reset."
				--DEFAULT test-function    it_exists
				--DEFAULT    set-function    set_%n
				--DEFAULT    get-function    get_%n
				--DEFAULT    next-function    std_next
				--DEFAULT cookie        (char *) 0
            ::= { cbNetworkParam 7 }

        cbNetGatewayDataIP OBJECT-TYPE 
             SYNTAX  IpAddress 
             ACCESS  read-write
             STATUS  mandatory
             DESCRIPTION
"Transportation IP Address.
Changing this parameter will affect after system reset."
			--DEFAULT test-function    it_exists
			--DEFAULT    set-function    set_%n
			--DEFAULT    get-function    get_%n
			--DEFAULT    next-function    std_next
			--DEFAULT cookie        (char *) 0
            ::= { cbNetworkParam 8 }

        cbNetGatewayDataSubnetMask OBJECT-TYPE 
             SYNTAX  IpAddress 
             ACCESS  read-write
             STATUS  mandatory
             DESCRIPTION
"Transportation subnet mask.
Changing this parameter will affect after system reset."
			--DEFAULT test-function    it_exists
			--DEFAULT    set-function    set_%n
			--DEFAULT    get-function    get_%n
			--DEFAULT    next-function    std_next
			--DEFAULT cookie        (char *) 0
            ::= { cbNetworkParam 9 }

        cbNetTelnet OBJECT-TYPE 
            SYNTAX  INTEGER 
                {
                cbEnabled (1),
                cbDisabled (0)
                }
            ACCESS  read-write
            STATUS  mandatory
            DESCRIPTION
"Enables/Disables the Telnet Server"
				--DEFAULT test-function    it_exists
				--DEFAULT    set-function    set_%n
				--DEFAULT    get-function    get_%n
				--DEFAULT    next-function    std_next
				--DEFAULT cookie        (char *) 0
            ::= { cbNetworkParam 10 }

        cbNetFTP OBJECT-TYPE 
            SYNTAX  INTEGER 
                {
                cbEnabled (1),
                cbDisabled (0)
                }
            ACCESS  read-write
            STATUS  mandatory
            DESCRIPTION
"Enables/Disables the FTP Server"
				--DEFAULT test-function    it_exists
				--DEFAULT    set-function    set_%n
				--DEFAULT    get-function    get_%n
				--DEFAULT    next-function    std_next
				--DEFAULT cookie        (char *) 0
            ::= { cbNetworkParam 11 }

    cbDVBOutputParam OBJECT IDENTIFIER ::= { cbConfig 2 } 



			cbDVBOutputBitRate OBJECT-TYPE 
				 SYNTAX  INTEGER 
				 ACCESS  read-write
				 STATUS  mandatory
				 DESCRIPTION "PLL Frequency"
				--DEFAULT test-function    it_exists
				--DEFAULT    set-function    set_%n
				--DEFAULT    get-function    get_%n
				--DEFAULT    next-function    std_next
				--DEFAULT cookie        (char *) 0
				::= { cbDVBOutputParam 1 }

            cbDVBPAT OBJECT-TYPE 
				 SYNTAX  INTEGER 
				 ACCESS  read-write
				 STATUS  mandatory
				 DESCRIPTION "PAT Rate"
				--DEFAULT test-function    it_exists
				--DEFAULT    set-function    set_%n
				--DEFAULT    get-function    get_%n
				--DEFAULT    next-function    std_next
				--DEFAULT cookie        (char *) 0
				::= { cbDVBOutputParam 2 }

            cbDVBPMT OBJECT-TYPE 
				 SYNTAX  INTEGER 
				 ACCESS  read-write
				 STATUS  mandatory
				 DESCRIPTION "PMT Rate"
				--DEFAULT test-function    it_exists
				--DEFAULT    set-function    set_%n
				--DEFAULT    get-function    get_%n
				--DEFAULT    next-function    std_next
				--DEFAULT cookie        (char *) 0
				::= { cbDVBOutputParam 3 }


            cbDVBFraming OBJECT-TYPE 
				 SYNTAX  INTEGER 
				     {
					 cbFraming188  (1),
					 cbFraming204  (2)
					 }
				 ACCESS  read-write
				 STATUS  mandatory
				 DESCRIPTION "188/204 Framing."
				--DEFAULT test-function    it_exists
				--DEFAULT    set-function    set_%n
				--DEFAULT    get-function    get_%n
				--DEFAULT    next-function    std_next
				--DEFAULT cookie        (char *) 0
				::= { cbDVBOutputParam 4 }

	        cbStuffingMode OBJECT-TYPE 
				 SYNTAX  INTEGER 
				     {
					 cbFFStuffing  (0),
					 cbAdaptationField (1)
					 }
				 ACCESS  read-write
				 STATUS  mandatory
				 DESCRIPTION 
"Stuffing mode: either FF stuffing or Adaptation field stuffing"
				--DEFAULT test-function    it_exists
				--DEFAULT    set-function    set_%n
				--DEFAULT    get-function    get_%n
				--DEFAULT    next-function    std_next
				--DEFAULT cookie        (char *) 0
				::= { cbDVBOutputParam 5 }

	        cbMpeMode OBJECT-TYPE 
				 SYNTAX  INTEGER 
				     {
					 cbPacked  (0),
					 cbNotPacked (1)
					 }
				 ACCESS  read-write
				 STATUS  mandatory
				 DESCRIPTION 
"MPE mode: Packed MPE mode or Not packed MPE mode."
				--DEFAULT test-function    it_exists
				--DEFAULT    set-function    set_%n
				--DEFAULT    get-function    get_%n
				--DEFAULT    next-function    std_next
				--DEFAULT cookie        (char *) 0
				::= { cbDVBOutputParam 6 }

	        cbCRCMode OBJECT-TYPE 
				 SYNTAX  INTEGER 
				     {
					 cbZero  (0),
					 cbCheckSum (1),
					 cbCRC		(2)
					 }
				 ACCESS  read-write
				 STATUS  mandatory
				 DESCRIPTION "CRC type"
				--DEFAULT test-function    it_exists
				--DEFAULT    set-function    set_%n
				--DEFAULT    get-function    get_%n
				--DEFAULT    next-function    std_next
				--DEFAULT cookie        (char *) 0
				::= { cbDVBOutputParam 7 }

            cbDVBClockPolarity OBJECT-TYPE 
				 SYNTAX  INTEGER 
				     {
					 cbNotInverted   (0),
					 cbInverted    (1)
					 }
				 ACCESS  read-only
				 STATUS  mandatory
				 DESCRIPTION "DVB Clock Polarity.
(read only value - may be changed in CFG.INI only)."
				--DEFAULT test-function    it_exists
				--DEFAULT    set-function    set_%n
				--DEFAULT    get-function    get_%n
				--DEFAULT    next-function    std_next
				--DEFAULT cookie        (char *) 0
				::= { cbDVBOutputParam 8 }

            cbDVBAuxInput OBJECT-TYPE 
				 SYNTAX  INTEGER 
				     {
					 cbEnabled   (1),
					 cbDisabled    (0)
					 }
				 ACCESS  read-write
				 STATUS  mandatory
				 DESCRIPTION "Aux Input Enable"
				--DEFAULT test-function    it_exists
				--DEFAULT    set-function    set_%n
				--DEFAULT    get-function    get_%n
				--DEFAULT    next-function    std_next
				--DEFAULT cookie        (char *) 0
				::= { cbDVBOutputParam 9 }

            cbDVBAuxNullPackets OBJECT-TYPE 
				 SYNTAX  INTEGER 
				     {
					 cbEnabled   (1),
					 cbDisabled    (0)
					 }
				 ACCESS  read-write
				 STATUS  mandatory
				 DESCRIPTION "Aux Null Packets"
				--DEFAULT test-function    it_exists
				--DEFAULT    set-function    set_%n
				--DEFAULT    get-function    get_%n
				--DEFAULT    next-function    std_next
				--DEFAULT cookie        (char *) 0
				::= { cbDVBOutputParam 10 }

            cbDVBAuxInputType OBJECT-TYPE 
				 SYNTAX  INTEGER 
				     {
					 cbASI   (1),
					 cbLVDS    (0)
					 }
				 ACCESS  read-write
				 STATUS  mandatory
				 DESCRIPTION "Aux Input Type"
				--DEFAULT test-function    it_exists
				--DEFAULT    set-function    set_%n
				--DEFAULT    get-function    get_%n
				--DEFAULT    next-function    std_next
				--DEFAULT cookie        (char *) 0
				::= { cbDVBOutputParam 11 }

            cbDVBLlcSnap OBJECT-TYPE 
				 SYNTAX  INTEGER 
				     {
					 cbEnabled   (1),
					 cbDisabled    (0)
					 }
				 ACCESS  read-write
				 STATUS  mandatory
				 DESCRIPTION "Enable LLC-SNAP in MPE"
				--DEFAULT test-function    it_exists
				--DEFAULT    set-function    set_%n
				--DEFAULT    get-function    get_%n
				--DEFAULT    next-function    std_next
				--DEFAULT cookie        (char *) 0
				::= { cbDVBOutputParam 12 }


    cbGeneralParam OBJECT IDENTIFIER ::= { cbConfig 3 } 

        cbGatewayEnabled OBJECT-TYPE 
            SYNTAX  INTEGER 
                {
                cbTrue (1),
                cbFalse (0)
                }
            ACCESS  read-write
            STATUS  mandatory
            DESCRIPTION
"Enables/Disables all the Gateway operations."
				--DEFAULT test-function    it_exists
				--DEFAULT    set-function    set_%n
				--DEFAULT    get-function    get_%n
				--DEFAULT    next-function    std_next
				--DEFAULT cookie        (char *) 0
            ::= { cbGeneralParam 1 }

        cbGatewaySWReset OBJECT-TYPE 
            SYNTAX  INTEGER 
                {
                cbTrue (1),
                cbFalse (0)
                }
            ACCESS  write-only
            STATUS  mandatory
            DESCRIPTION
"CAUTION: Setting this param to cbTrue cause a S/W reset of the gateway."
				--DEFAULT test-function    it_exists
				--DEFAULT    set-function    set_%n
				--DEFAULT    get-function    get_%n
				--DEFAULT    next-function    std_next
				--DEFAULT cookie        (char *) 0
            ::= { cbGeneralParam 2 }

        cbTraceInfo OBJECT IDENTIFIER ::= { cbGeneralParam 3 } 

            cbTraceMask OBJECT-TYPE 
                 SYNTAX  INTEGER 
                 ACCESS  read-write
                 STATUS  mandatory
                 DESCRIPTION
"Mask to select elements for trace."
				--DEFAULT test-function    it_exists
				--DEFAULT    set-function    set_%n
				--DEFAULT    get-function    get_%n
				--DEFAULT    next-function    std_next
				--DEFAULT cookie        (char *) 0
            ::= { cbTraceInfo 1 }

            cbTraceLevel OBJECT-TYPE 
                 SYNTAX  INTEGER 
                 ACCESS  read-write
                 STATUS  mandatory
                 DESCRIPTION
"Trace level for elements specified by cbTraceMask"
				--DEFAULT test-function    it_exists
				--DEFAULT    set-function    set_%n
				--DEFAULT    get-function    get_%n
				--DEFAULT    next-function    std_next
				--DEFAULT cookie        (char *) 0
            ::= { cbTraceInfo 2 }

            cbTraceOutputChannel OBJECT-TYPE 
                 SYNTAX  INTEGER
					{
					cbTraceToVGA (1),
					cbTraceToCOM1 (2),
					cbTraceToCOM2 (3)
					}

                 ACCESS  read-write
                 STATUS  mandatory
                 DESCRIPTION
"Trace output channel."
				--DEFAULT test-function    it_exists
				--DEFAULT    set-function    set_%n
				--DEFAULT    get-function    get_%n
				--DEFAULT    next-function    std_next
				--DEFAULT cookie        (char *) 0
            ::= { cbTraceInfo 3 }


        cbPktEncrypt OBJECT-TYPE 
             SYNTAX  INTEGER 
                {
                cbTrue (1),
                cbFalse (0)
                }
             ACCESS  read-write
             STATUS  mandatory
             DESCRIPTION
"Enable/Disable encryption of the the transmitted packets.
If cbPktEncrypt==cbTrue, packets will be encrypted only if 
cbClEncrEnable==cbTrue for that client."
			--DEFAULT test-function    it_exists
			--DEFAULT    set-function    set_%n
			--DEFAULT    get-function    get_%n
			--DEFAULT    next-function    std_next
			--DEFAULT cookie        (char *) 0
           ::= { cbGeneralParam 4 }

        cbGatewayDescription OBJECT-TYPE
             SYNTAX  DisplayString 
             ACCESS  read-write
             STATUS  mandatory
             DESCRIPTION
"A general description of this gateway. The description may
be changed as needed."
--DEFAULT get-function    get_string
--DEFAULT cookie        (char *) cbsnmp_%n
				--DEFAULT test-function    it_exists
				--DEFAULT    set-function    set_%n
				--DEFAULT    next-function    std_next
            ::= { cbGeneralParam 5 }

        cbSWVersion OBJECT-TYPE
                 SYNTAX  DisplayString 
                 ACCESS  read-only
                 STATUS  mandatory
                 DESCRIPTION
"TV Gateway Software Version."
--DEFAULT get-function    get_string
--DEFAULT cookie        (char *) cbsnmp_%n
				--DEFAULT test-function    it_exists
				--DEFAULT    set-function    set_%n
				--DEFAULT    next-function    std_next
            ::= { cbGeneralParam 6 }

        cbApplicationFileName OBJECT-TYPE
                 SYNTAX  DisplayString 
                 ACCESS  read-write
                 STATUS  mandatory
                 DESCRIPTION
"TV Gateway Application Software File Name.
Changing this parameter will affect after system reset."
                 --DEFAULT get-function    get_string
                 --DEFAULT cookie        (char *) cbsnmp_%n
				 --DEFAULT test-function    it_exists
				 --DEFAULT    set-function    set_%n
				 --DEFAULT    next-function    std_next
             ::= { cbGeneralParam 7 }

        cbDataMappingMode OBJECT-TYPE 
             SYNTAX  INTEGER 
                {
                cbDataStreaming (2),
                cbProtocolEncapsulation (3)
                }
             ACCESS  read-write
             STATUS  mandatory
             DESCRIPTION
"Data Boradcast Mode - Encodding mode of data from network."
			--DEFAULT test-function    it_exists
			--DEFAULT    set-function    set_%n
			--DEFAULT    get-function    get_%n
			--DEFAULT    next-function    std_next
			--DEFAULT cookie        (char *) 0
           ::= { cbGeneralParam 8 }

	        cbMaxAllowableDelay OBJECT-TYPE 
	             SYNTAX  INTEGER
	             ACCESS  read-write
	             STATUS  mandatory
	             DESCRIPTION
"The Maximum allowable time (in mSec) which a packet can be 
delayed in the gateway. "
				--DEFAULT test-function    it_exists
				--DEFAULT    set-function    set_%n
				--DEFAULT    get-function    get_%n
				--DEFAULT    next-function    std_next
				--DEFAULT cookie        (char *) 0
	           ::= { cbGeneralParam 9 }

        cbQualityOfService OBJECT IDENTIFIER ::= { cbGeneralParam 10 } 

	        cbQOSMode OBJECT-TYPE 
	             SYNTAX  INTEGER 
	                {
					cbPermissive (1),
					cbRestrictive (2)
	                }
	             ACCESS  read-write
	             STATUS  mandatory
	             DESCRIPTION
"Permissive mode will allow transmit to users obove their maximum rate when when
band-width is available.
Restrictive mode will not transmit any data to users above their maximum rate even
if band-width is available."
				--DEFAULT test-function    it_exists
				--DEFAULT    set-function    set_%n
				--DEFAULT    get-function    get_%n
				--DEFAULT    next-function    std_next
				--DEFAULT cookie        (char *) 0
	           ::= { cbQualityOfService 1 }

	        cbQOSActive OBJECT-TYPE 
	             SYNTAX  INTEGER 
	                {
					cbFalse (0),
					cbTrue (1)
	                }
	             ACCESS  read-write
	             STATUS  mandatory
	             DESCRIPTION
"Turn on (cbTrue) or off (cbFalse) the Quality of Service mechanism.
When Quality of Service is turned off, the minimum CIR promised to 
users is ignored and data is transffered to users in the order it
is received from the Ethernet by the gateway."
				--DEFAULT test-function    it_exists
				--DEFAULT    set-function    set_%n
				--DEFAULT    get-function    get_%n
				--DEFAULT    next-function    std_next
				--DEFAULT cookie        (char *) 0
	           ::= { cbQualityOfService 2 }

        cbFlushing OBJECT-TYPE 
			 SYNTAX  INTEGER 
			     {
				 cbNo  (0),
				 cbYes (1)
				 }
			 ACCESS  read-write
			 STATUS  mandatory
			 DESCRIPTION "Flushing packets on IDLE"
			--DEFAULT test-function    it_exists
			--DEFAULT    set-function    set_%n
			--DEFAULT    get-function    get_%n
			--DEFAULT    next-function    std_next
			--DEFAULT cookie        (char *) 0
			::= { cbGeneralParam 11 }

        cbFPGAFileName OBJECT-TYPE 
             SYNTAX  DisplayString 
             ACCESS  read-write
             STATUS  mandatory
             DESCRIPTION
"A string that holds the MCS file name loaded to the Gateway's Encoder.
Changing this parameter will affect after system reset."
			--DEFAULT test-function    it_exists
			--DEFAULT    set-function    set_%n
			--DEFAULT    next-function    std_next
            --DEFAULT get-function    get_string
            --DEFAULT cookie        (char *) cbsnmp_%n
            ::= { cbGeneralParam 13 }


    cbGroupsTable OBJECT IDENTIFIER ::= { cbConfig 4 }

        cbGrTable OBJECT-TYPE
            SYNTAX  SEQUENCE OF CbGroupsTableNode
            ACCESS  not-accessible
            STATUS  mandatory
            DESCRIPTION "This table contains the Groups definitions."
            --DEFAULT test-function-async test_%p
            --DEFAULT next-function-async next_%p
            --DEFAULT get-function-async get_%p
            --DEFAULT set-function-async set_%p
            --DEFAULT cookie (char*) 0
            ::= { cbGroupsTable 1 }

            cbGroupsTableNode OBJECT-TYPE
                SYNTAX  CbGroupsTableNode
                ACCESS  not-accessible
                STATUS  mandatory
                DESCRIPTION "Information about a particular group."
                INDEX   {cbGrTableIndex}
            ::= { cbGrTable 1 }

            CbGroupsTableNode ::=
            SEQUENCE {
                cbGrTableIndex
                    INTEGER,
                cbGrTablePID
                    INTEGER,
                cbGrTableQosMode
                    INTEGER,
				cbGrTableMinRate
					INTEGER,
				cbGrTableMaxRate
					INTEGER
                }

            cbGrTableIndex OBJECT-TYPE
                SYNTAX  INTEGER
                ACCESS  read-write
                STATUS  mandatory
                DESCRIPTION	"Group Index."
                ::= { cbGroupsTableNode 1 }

            cbGrTablePID OBJECT-TYPE
                SYNTAX  INTEGER
                ACCESS  read-write
                STATUS  mandatory
                DESCRIPTION	"The Group PID."
                ::= { cbGroupsTableNode 2 }

            cbGrTableQosMode OBJECT-TYPE
			 	SYNTAX  INTEGER 
			     	{
				 	cbIndividual (0),
				 	cbGlobal (1)
				 	}
                ACCESS  read-write
                STATUS  mandatory
                DESCRIPTION	"The Group Qos Mode."
                ::= { cbGroupsTableNode 3 }

            cbGrTableMinRate OBJECT-TYPE
                SYNTAX  INTEGER
                ACCESS  read-write
                STATUS  mandatory
                DESCRIPTION	"The Group Minimum rate. This parameter affects only if QosMode=Global"
                ::= { cbGroupsTableNode 4 }

            cbGrTableMaxRate OBJECT-TYPE
                SYNTAX  INTEGER
                ACCESS  read-write
                STATUS  mandatory
                DESCRIPTION	"The Group Maximum rate. This parameter affects only if QosMode=Global"
                ::= { cbGroupsTableNode 5 }


    cbConfigSTUTable OBJECT IDENTIFIER ::= { cbConfig 5 }

        cbStaticUserTable OBJECT-TYPE
            SYNTAX  SEQUENCE OF CbStaticUserEntry
            ACCESS  not-accessible
            STATUS  mandatory
            DESCRIPTION 
"This table contains the all the static users."
            --DEFAULT test-function-async test_%p
            --DEFAULT next-function-async next_%p
            --DEFAULT get-function-async get_%p
            --DEFAULT set-function-async set_%p
            --DEFAULT cookie (char*) 0
            ::= { cbConfigSTUTable 1 }

            cbStaticUserEntry OBJECT-TYPE
                SYNTAX  CbStaticUserEntry
                ACCESS  not-accessible
                STATUS  mandatory
                         DESCRIPTION "Information about a particular static user."
                         INDEX   {cbStaticUserIP}
            ::= { cbStaticUserTable 1 }

            CbStaticUserEntry ::=
            SEQUENCE {
                cbStaticUserIP
                    IpAddress,
                cbStaticUserMask
                    IpAddress,
				cbStaticUserGroup
					INTEGER,
				cbStaticUserMAC
					PhysAddress,
				cbStaticUserMinRate
					INTEGER,
				cbStaticUserMaxRate
					INTEGER
                }

            cbStaticUserIP OBJECT-TYPE
                SYNTAX  IpAddress
                ACCESS  read-write
                STATUS  mandatory
                DESCRIPTION	"IP of static user."
                ::= { cbStaticUserEntry 1 }

            cbStaticUserMask OBJECT-TYPE
                SYNTAX  IpAddress
                ACCESS  read-write
                STATUS  mandatory
                DESCRIPTION	"The static user mask."
                ::= { cbStaticUserEntry 2 }

            cbStaticUserGroup OBJECT-TYPE
                SYNTAX  INTEGER
                ACCESS  read-write
                STATUS  mandatory
                DESCRIPTION	"The static user's Group."
                ::= { cbStaticUserEntry 3 }

            cbStaticUserMAC OBJECT-TYPE
                SYNTAX  PhysAddress
                ACCESS  read-write
                STATUS  mandatory
                DESCRIPTION	"The group in which the static user resides."
                ::= { cbStaticUserEntry 4 }


            cbStaticUserMinRate OBJECT-TYPE
                SYNTAX  INTEGER
                ACCESS  read-write
                STATUS  mandatory
                DESCRIPTION	"The static user Minimum rate (CIR)."
                ::= { cbStaticUserEntry 5 }

            cbStaticUserMaxRate OBJECT-TYPE
                SYNTAX  INTEGER
                ACCESS  read-write
                STATUS  mandatory
                DESCRIPTION	"The static user Maximum rate."
                ::= { cbStaticUserEntry 6 }


    cbConfigMulticastTable OBJECT IDENTIFIER ::= { cbConfig 6 }

        cbMulticastTable OBJECT-TYPE
            SYNTAX  SEQUENCE OF CbMulticastEntry
            ACCESS  not-accessible
            STATUS  mandatory
            DESCRIPTION 
"This table contains the all the multicasts."
            --DEFAULT test-function-async test_%p
            --DEFAULT next-function-async next_%p
            --DEFAULT get-function-async get_%p
            --DEFAULT set-function-async set_%p
            --DEFAULT cookie (char*) 0
            ::= { cbConfigMulticastTable 1 }

            cbMulticastEntry OBJECT-TYPE
                SYNTAX  CbMulticastEntry
                ACCESS  not-accessible
                STATUS  mandatory
                DESCRIPTION "Information about a particular multicast."
                INDEX   { cbMulticastIP }
            ::= { cbMulticastTable 1 }

            CbMulticastEntry ::=
            SEQUENCE {
                cbMulticastIP
                    IpAddress,
				cbMulticastGroup
					INTEGER,
				cbMulticastSID
					INTEGER,
				cbMulticastMinRate
					INTEGER,
				cbMulticastMaxRate
					INTEGER
                }

            cbMulticastIP OBJECT-TYPE
                SYNTAX  IpAddress
                ACCESS  read-write
                STATUS  mandatory
                DESCRIPTION	"IP of multicast."
                ::= { cbMulticastEntry 1 }

            cbMulticastGroup OBJECT-TYPE
                SYNTAX  INTEGER
                ACCESS  read-write
                STATUS  mandatory
                DESCRIPTION	"The multicast's Group."
                ::= { cbMulticastEntry 2 }

            cbMulticastSID OBJECT-TYPE
                SYNTAX  INTEGER
                ACCESS  read-write
                STATUS  mandatory
                DESCRIPTION	"The group in which the multicast resides."
                ::= { cbMulticastEntry 3 }


            cbMulticastMinRate OBJECT-TYPE
                SYNTAX  INTEGER
                ACCESS  read-write
                STATUS  mandatory
                DESCRIPTION	"The multicast Minimum rate (CIR)."
                ::= { cbMulticastEntry 4 }

            cbMulticastMaxRate OBJECT-TYPE
                SYNTAX  INTEGER
                ACCESS  read-write
                STATUS  mandatory
                DESCRIPTION	"The multicast Maximum rate."
                ::= { cbMulticastEntry 5 }

    cbConfigClTable OBJECT IDENTIFIER ::= { cbConfig 7 }

        cbCfgClTable OBJECT-TYPE
            SYNTAX  SEQUENCE OF CbCfgClTableNode
            ACCESS  not-accessible
            STATUS  mandatory
            DESCRIPTION 
"This table contains updated configuration of all clients known to the gateway."
            --DEFAULT test-function-async test_%p
            --DEFAULT next-function-async next_%p
            --DEFAULT get-function-async get_%p
            --DEFAULT set-function-async set_%p
            --DEFAULT cookie (char*) 0
            ::= { cbConfigClTable 1 }

            cbCfgClTableNode OBJECT-TYPE
                SYNTAX  CbCfgClTableNode
                ACCESS  not-accessible
                STATUS  mandatory
                DESCRIPTION "Information about a particular client configuration."
                INDEX   {cbCfgClTableIP}
            ::= { cbCfgClTable 1 }

            CbCfgClTableNode ::=
            SEQUENCE {
                cbCfgClTableIP
                    IpAddress,
                cbCfgClTableMask
                    IpAddress,
				cbCfgClTableMAC
					PhysAddress,
				cbCfgClTableGroup
					INTEGER,
				cbCfgClTableBy
					DisplayString,
				cbCfgClTableMinRate
					INTEGER,
				cbCfgClTableMaxRate
					INTEGER,
				cbCfgClTableEncrypt
					INTEGER
                }

            cbCfgClTableIP OBJECT-TYPE
                SYNTAX  IpAddress
                ACCESS  read-only
                STATUS  mandatory
                DESCRIPTION	"The clients IP."
                ::= { cbCfgClTableNode 1 }

            cbCfgClTableMask OBJECT-TYPE
                SYNTAX  IpAddress
                ACCESS  read-only
                STATUS  mandatory
                DESCRIPTION	"The clients IP Mask."
                ::= { cbCfgClTableNode 2 }

            cbCfgClTableMAC OBJECT-TYPE
                SYNTAX  PhysAddress
                ACCESS  read-only
                STATUS  mandatory
                DESCRIPTION	"The clients MAC Address."
                ::= { cbCfgClTableNode 3 }

            cbCfgClTableGroup OBJECT-TYPE
                SYNTAX  INTEGER
                ACCESS  read-only
                STATUS  mandatory
                DESCRIPTION	"The clients Group."
                ::= { cbCfgClTableNode 4 }

            cbCfgClTableBy OBJECT-TYPE
                SYNTAX  DisplayString
                ACCESS  read-only
                STATUS  mandatory
                DESCRIPTION	"By whom the client was added."
                ::= { cbCfgClTableNode 5 }

            cbCfgClTableMinRate OBJECT-TYPE
                SYNTAX  INTEGER
                ACCESS  read-only
                STATUS  mandatory
                DESCRIPTION	"The clients Minimum rate (CIR)."
                ::= { cbCfgClTableNode 6 }

            cbCfgClTableMaxRate OBJECT-TYPE
                SYNTAX  INTEGER
                ACCESS  read-only
                STATUS  mandatory
                DESCRIPTION	"The clients Maximum rate."
                ::= { cbCfgClTableNode 7 }

            cbCfgClTableEncrypt OBJECT-TYPE
                SYNTAX  INTEGER
					{
					cbFalse (0),
					cbTrue	(1)
					}
                ACCESS  read-only
                STATUS  mandatory
                DESCRIPTION	"The clients Encryption parameter True/False."
                ::= { cbCfgClTableNode 8 }

    cbTimeDate OBJECT IDENTIFIER ::= { cbConfig 8 } 

        cbTime OBJECT-TYPE 
             SYNTAX  DisplayString 
             ACCESS  read-write
             STATUS  mandatory
             DESCRIPTION
"A string in the form HH:MM:SS that represents
the gateway idea of the current time.
Single digits should be preceeded by 0.
Examples: 12:35:27 01:50:00 09:01:59"
				--DEFAULT    set-function    set_%n
				--DEFAULT    next-function    std_next
--DEFAULT test-function   it_exists
--DEFAULT get-function    get_%n
--DEFAULT cookie        (char *) 0
            ::= { cbTimeDate 1 }

        cbDate OBJECT-TYPE 
             SYNTAX  DisplayString 
             ACCESS  read-write
             STATUS  mandatory
             DESCRIPTION
"A string representing the gateway idea of the current date.
In order to set a different date, use the following format:
<Full Month Name> <1 or 2 Digits of Day of Month>,<4 Digits of Year>
Examples: September 1,1998 
Januray 12, 2002"
				--DEFAULT    set-function    set_%n
				--DEFAULT    next-function    std_next
--DEFAULT test-function   it_exists
--DEFAULT get-function    get_%n
--DEFAULT cookie        (char *) 0
            ::= { cbTimeDate 2 }


	    cbClientsInfoReset OBJECT-TYPE 
	         SYNTAX  INTEGER 
	         ACCESS  read-write
	         STATUS  mandatory
	         DESCRIPTION
"This parameter is applicable only for clients that were NOT
added by the CCU.
The gateway will delete from its lists
clients information (statistics and encryption
parameters) for each client registered
in the system for more then cbTClientsInfoReset seconds.
cbTClientsInfoReset must be greater then 0."
				--DEFAULT test-function    it_exists
				--DEFAULT    set-function    set_%n
				--DEFAULT    get-function    get_%n
				--DEFAULT    next-function    std_next
				--DEFAULT cookie        (char *) 0
            ::= { cbConfig 9 }

    cbCCUParam OBJECT IDENTIFIER ::= { cbConfig 10 } 

	    cbCCU1 OBJECT-TYPE 
	         SYNTAX  IpAddress
	         ACCESS  read-write
	         STATUS  mandatory
	         DESCRIPTION
             "IP of CCU Server #1 (set to 0.0.0.0 to disable CCU #1)"
				--DEFAULT test-function    it_exists
				--DEFAULT    set-function    set_%n
				--DEFAULT    get-function    get_%n
				--DEFAULT    next-function    std_next
				--DEFAULT cookie        (char *) 0
            ::= { cbCCUParam 1 }

	    cbCCU2 OBJECT-TYPE 
	         SYNTAX  IpAddress
	         ACCESS  read-write
	         STATUS  mandatory
	         DESCRIPTION
             "IP of CCU Server #2 (set to 0.0.0.0 to disable CCU #2)"
				--DEFAULT test-function    it_exists
				--DEFAULT    set-function    set_%n
				--DEFAULT    get-function    get_%n
				--DEFAULT    next-function    std_next
				--DEFAULT cookie        (char *) 0
            ::= { cbCCUParam 2 }

	    cbCCU3 OBJECT-TYPE 
	         SYNTAX  IpAddress
	         ACCESS  read-write
	         STATUS  mandatory
	         DESCRIPTION
             "IP of CCU Server #3 (set to 0.0.0.0 to disable CCU #3)"
				--DEFAULT test-function    it_exists
				--DEFAULT    set-function    set_%n
				--DEFAULT    get-function    get_%n
				--DEFAULT    next-function    std_next
				--DEFAULT cookie        (char *) 0
            ::= { cbCCUParam 3 }

	    cbCCU4 OBJECT-TYPE 
	         SYNTAX  IpAddress
	         ACCESS  read-write
	         STATUS  mandatory
	         DESCRIPTION
             "IP of CCU Server #4 (set to 0.0.0.0 to disable CCU #4)"
				--DEFAULT test-function    it_exists
				--DEFAULT    set-function    set_%n
				--DEFAULT    get-function    get_%n
				--DEFAULT    next-function    std_next
				--DEFAULT cookie        (char *) 0
            ::= { cbCCUParam 4 }

	    cbCCU5 OBJECT-TYPE 
	         SYNTAX  IpAddress
	         ACCESS  read-write
	         STATUS  mandatory
	         DESCRIPTION
             "IP of CCU Server #5 (set to 0.0.0.0 to disable CCU #5)"
				--DEFAULT test-function    it_exists
				--DEFAULT    set-function    set_%n
				--DEFAULT    get-function    get_%n
				--DEFAULT    next-function    std_next
				--DEFAULT cookie        (char *) 0
            ::= { cbCCUParam 5 }

	    cbCCU6 OBJECT-TYPE 
	         SYNTAX  IpAddress
	         ACCESS  read-write
	         STATUS  mandatory
	         DESCRIPTION
             "IP of CCU Server #6 (set to 0.0.0.0 to disable CCU #6)"
				--DEFAULT test-function    it_exists
				--DEFAULT    set-function    set_%n
				--DEFAULT    get-function    get_%n
				--DEFAULT    next-function    std_next
				--DEFAULT cookie        (char *) 0
            ::= { cbCCUParam 6 }

	    cbCCU7 OBJECT-TYPE 
	         SYNTAX  IpAddress
	         ACCESS  read-write
	         STATUS  mandatory
	         DESCRIPTION
             "IP of CCU Server #7 (set to 0.0.0.0 to disable CCU #7)"
				--DEFAULT test-function    it_exists
				--DEFAULT    set-function    set_%n
				--DEFAULT    get-function    get_%n
				--DEFAULT    next-function    std_next
				--DEFAULT cookie        (char *) 0
            ::= { cbCCUParam 7 }

	    cbCCU8 OBJECT-TYPE 
	         SYNTAX  IpAddress
	         ACCESS  read-write
	         STATUS  mandatory
	         DESCRIPTION
             "IP of CCU Server #8 (set to 0.0.0.0 to disable CCU #8)"
				--DEFAULT test-function    it_exists
				--DEFAULT    set-function    set_%n
				--DEFAULT    get-function    get_%n
				--DEFAULT    next-function    std_next
				--DEFAULT cookie        (char *) 0
            ::= { cbCCUParam 8 }

	    cbCCU9 OBJECT-TYPE 
	         SYNTAX  IpAddress
	         ACCESS  read-write
	         STATUS  mandatory
	         DESCRIPTION
             "IP of CCU Server #9 (set to 0.0.0.0 to disable CCU #9)"
				--DEFAULT test-function    it_exists
				--DEFAULT    set-function    set_%n
				--DEFAULT    get-function    get_%n
				--DEFAULT    next-function    std_next
				--DEFAULT cookie        (char *) 0
            ::= { cbCCUParam 9 }

	    cbCCU10 OBJECT-TYPE 
	         SYNTAX  IpAddress
	         ACCESS  read-write
	         STATUS  mandatory
	         DESCRIPTION
             "IP of CCU Server #10 (set to 0.0.0.0 to disable CCU #10)"
				--DEFAULT test-function    it_exists
				--DEFAULT    set-function    set_%n
				--DEFAULT    get-function    get_%n
				--DEFAULT    next-function    std_next
				--DEFAULT cookie        (char *) 0
            ::= { cbCCUParam 10 }


    cbHASParam OBJECT IDENTIFIER ::= { cbConfig 11 } 

            cbHasEnable OBJECT-TYPE 
               SYNTAX  INTEGER 
                   {
                   cbEnabled (1),
                   cbDisabled (0)
                   }
               ACCESS  read-write
               STATUS  mandatory
               DESCRIPTION
"Enables/Disables High Availability Mode."
				--DEFAULT test-function    it_exists
				--DEFAULT    set-function    set_%n
				--DEFAULT    get-function    get_%n
				--DEFAULT    next-function    std_next
				--DEFAULT cookie        (char *) 0
            ::= { cbHASParam 1 }

            cbHasCpu OBJECT-TYPE
                SYNTAX  INTEGER
                ACCESS  read-write
                STATUS  mandatory
                DESCRIPTION	"Maximum CPU"
				--DEFAULT test-function    it_exists
				--DEFAULT    set-function    set_%n
				--DEFAULT    get-function    get_%n
				--DEFAULT    next-function    std_next
				--DEFAULT cookie        (char *) 0
                ::= { cbHASParam 2 }

            cbHasMemory OBJECT-TYPE
                SYNTAX  INTEGER
                ACCESS  read-write
                STATUS  mandatory
                DESCRIPTION	"Maximum Memory Usage"
				--DEFAULT test-function    it_exists
				--DEFAULT    set-function    set_%n
				--DEFAULT    get-function    get_%n
				--DEFAULT    next-function    std_next
				--DEFAULT cookie        (char *) 0
                ::= { cbHASParam 3 }

cbDiagnostics OBJECT IDENTIFIER ::= { cbGateway 3 } 

    cbDiagTestTx OBJECT IDENTIFIER ::= { cbDiagnostics 1 } 

        cbDiagTestTxParam OBJECT IDENTIFIER ::= { cbDiagTestTx 1 } 

            cbTestTxDestIP OBJECT-TYPE 
                 SYNTAX  IpAddress 
                 ACCESS  read-write
                 STATUS  mandatory
                 DESCRIPTION
"Test Transfer Packet ID"
				--DEFAULT test-function    it_exists
				--DEFAULT    set-function    set_%n
				--DEFAULT    get-function    get_%n
				--DEFAULT    next-function    std_next
				--DEFAULT cookie        (char *) 0
            ::= { cbDiagTestTxParam 1 }

            cbTestTxType OBJECT-TYPE 
                 SYNTAX  INTEGER
					{
					cbTestTypeOnePacket (1),
					cbTestTypeLowSpeedCont (2),
					cbTestTypeHighSpeedCont (3)
					}

                 ACCESS  read-write
                 STATUS  mandatory
                 DESCRIPTION
"READ/WRITE
Test Transfer Type:
cbTestTypeOnePacket - one packet,
cbTestTypeLowSpeedCont - Low Speed Continuous.
cbTestTypeHighSpeedCont - High Speed Continuous."
				--DEFAULT test-function    it_exists
				--DEFAULT    set-function    set_%n
				--DEFAULT    get-function    get_%n
				--DEFAULT    next-function    std_next
				--DEFAULT cookie        (char *) 0
            ::= { cbDiagTestTxParam 2 }

        cbDiagTestTxActive OBJECT-TYPE 
             SYNTAX  INTEGER 
                    {
                    cbTrue (1),
                    cbFalse (0)
                    }
             ACCESS  read-write
             STATUS  mandatory
             DESCRIPTION
"Set to 0 in order to stop Test Transfer.
Set to non-0 in order to activate it.
(in case cbTestTxType = 1, set to 0 and to non-zero
in order to re-send the single test packet)"
				--DEFAULT test-function    it_exists
				--DEFAULT    set-function    set_%n
				--DEFAULT    get-function    get_%n
				--DEFAULT    next-function    std_next
				--DEFAULT cookie        (char *) 0
        ::= { cbDiagTestTx 2 }



cbSWDownload OBJECT IDENTIFIER ::= { cbGateway 4 } 

        cbSWServerIP OBJECT-TYPE 
             SYNTAX  IpAddress 
             ACCESS  read-write
             STATUS  mandatory
             DESCRIPTION
"The TFTP server IP address.
The S/W file will be TFTPed from this station.
Use 0.0.0.0 to load a different local file (without TFTP)."
				--DEFAULT test-function    it_exists
				--DEFAULT    set-function    set_%n
				--DEFAULT    get-function    get_%n
				--DEFAULT    next-function    std_next
				--DEFAULT cookie        (char *) 0
            ::= { cbSWDownload 1 }

    cbAppDownload OBJECT IDENTIFIER ::= { cbSWDownload 2 } 

        cbSWSourceFileName OBJECT-TYPE 
             SYNTAX  DisplayString 
             ACCESS  read-write
             STATUS  mandatory
             DESCRIPTION
"The software file name and its optional path (relative to the TFTP server 
root definition) to be downloaded from the server.
Example: catvgw.dat"
				--DEFAULT test-function    it_exists
				--DEFAULT    set-function    set_%n
				--DEFAULT    next-function    std_next
            --DEFAULT get-function    get_string
            --DEFAULT cookie        (char *) cbsnmp_%n
            ::= { cbAppDownload 1 }

        cbSWTargetFileName OBJECT-TYPE 
             SYNTAX  DisplayString 
             ACCESS  read-write
             STATUS  mandatory
             DESCRIPTION
"The S/W file name (without path) on the Gateway.
Example: ram.abs
WARNING: cbApplicationFileName (under cbGeneralParam) is the name of
the running S/W. If cbSWTargetFileName is different from 
cbApplicationFileName, it will be just downloaded to the Gateway and
not used until cbApplicationFileName will be changed (in CFG.INI) to 
be equal to cbSWTargetFileName."
				--DEFAULT test-function    it_exists
				--DEFAULT    set-function    set_%n
				--DEFAULT    next-function    std_next
            --DEFAULT get-function    get_string
            --DEFAULT cookie        (char *) cbsnmp_%n
            ::= { cbAppDownload 2 }

        cbSWDownloadStart OBJECT-TYPE 
             SYNTAX  INTEGER 
					{
					cbTrue (1),
					cbFalse (0)
					}
             ACCESS  write-only
             STATUS  mandatory
             DESCRIPTION
"Set cbSWDownloadStart to cbTrue in order to start the S/W download process.
Set cbSWDownloadStart to cbFalse to interrupt (and stop) S/W download 
in progress (when cbSWDownloadStatus = cbDownloadInProgress)."
				--DEFAULT test-function    it_exists
				--DEFAULT    set-function    set_%n
				--DEFAULT    get-function    get_%n
				--DEFAULT    next-function    std_next
				--DEFAULT cookie        (char *) 0
            ::= { cbAppDownload 3 }

        cbSWDownloadStatus OBJECT-TYPE 
             SYNTAX  INTEGER
				{ 
				cbIdle (0),
				cbDownloadInProgress (1),
				cbERRORTFTPServernotFound (2),
				cbERRORFileNotFound (3),
				cbERRORNotASWFile (4),
				cbERRORBadChecksum (5),
				cbERRORCommunicationFailed (6),
				cbDownloadAborted (7)
				}
             ACCESS  read-only
             STATUS  mandatory
             DESCRIPTION
"Status of SW Download:
cbIdle - Download has not started yet or has comleted and gateway already restarted with new version (not an error).
cbDownloadInProgress - Download is currently in progrees (not an error).
cbERRORTFTPServernotFound - Cannot find a TFTP server in the specified IP address - check and correct cbSWServerIP.
cbERRORFileNotFound - Cannot find the specified file - check and correct cbSWFileName.
cbERRORNotaSWFile - The specified file is not a SW file - check and correct cbSWFileName.
cbERRORBadChecksum - Bad checksum - try to download again.
cbERRORCommunicationFailed - Communication with server failed - try to download again.
cbDownloadAborted - Download aborted by SNMP manager (cbSWDownloadStart was set to cbFalse during download)."
				--DEFAULT test-function    it_exists
				--DEFAULT    set-function    set_%n
				--DEFAULT    get-function    get_%n
				--DEFAULT    next-function    std_next
				--DEFAULT cookie        (char *) 0
            ::= { cbAppDownload 4 }

    cbFPGADownload OBJECT IDENTIFIER ::= { cbSWDownload 3 } 

        cbFPGASourceFileName OBJECT-TYPE 
             SYNTAX  DisplayString 
             ACCESS  read-write
             STATUS  mandatory
             DESCRIPTION
"The FPGA file name and its optional path (relative to the TFTP server 
root definition) to be downloaded from the server.
Example: FPGA.DAT"
				--DEFAULT test-function    it_exists
				--DEFAULT    set-function    set_%n
				--DEFAULT    next-function    std_next
            --DEFAULT get-function    get_string
            --DEFAULT cookie        (char *) cbsnmp_%n
            ::= { cbFPGADownload 1 }

        cbFPGATargetFileName OBJECT-TYPE 
             SYNTAX  DisplayString 
             ACCESS  read-write
             STATUS  mandatory
             DESCRIPTION
"The FPGA file name (without path) on the Gateway.
Example: FPGA.DAT"
				--DEFAULT test-function    it_exists
				--DEFAULT    set-function    set_%n
				--DEFAULT    next-function    std_next
            --DEFAULT get-function    get_string
            --DEFAULT cookie        (char *) cbsnmp_%n
            ::= { cbFPGADownload 2 }

        cbFPGADownloadStart OBJECT-TYPE 
             SYNTAX  INTEGER 
					{
					cbTrue (1),
					cbFalse (0)
					}
             ACCESS  write-only
             STATUS  mandatory
             DESCRIPTION
"Set cbFPGADownloadStart to cbTrue in order to start the FPGA download process.
Set cbFPGADownloadStart to cbFalse to interrupt (and stop) FPGA download 
in progress (when cbFPGADownloadStatus = cbDownloadInProgress)."
				--DEFAULT test-function    it_exists
				--DEFAULT    set-function    set_%n
				--DEFAULT    get-function    get_%n
				--DEFAULT    next-function    std_next
				--DEFAULT cookie        (char *) 0
            ::= { cbFPGADownload 3 }

        cbFPGADownloadStatus OBJECT-TYPE 
             SYNTAX  INTEGER
				{ 
				cbIdle (0),
				cbDownloadInProgress (1),
				cbERRORTFTPServernotFound (2),
				cbERRORFileNotFound (3),
				cbERRORNotASWFile (4),
				cbERRORBadChecksum (5),
				cbERRORCommunicationFailed (6),
				cbDownloadAborted (7)
				}
             ACCESS  read-only
             STATUS  mandatory
             DESCRIPTION
"Status of FPGA Download:
cbIdle - Download has not started yet or has comleted and gateway already restarted with new version (not an error).
cbDownloadInProgress - Download is currently in progrees (not an error).
cbERRORTFTPServernotFound - Cannot find a TFTP server in the specified IP address - check and correct cbSWServerIP.
cbERRORFileNotFound - Cannot find the specified file - check and correct cbFPGAFileName.
cbERRORNotaSWFile - The specified file is not a SW file - check and correct cbFPGAFileName.
cbERRORBadChecksum - Bad checksum - try to download again.
cbERRORCommunicationFailed - Communication with server failed - try to download again.
cbDownloadAborted - Download aborted by SNMP manager (cbFPGADownloadStart was set to cbFalse during download)."
				--DEFAULT test-function    it_exists
				--DEFAULT    set-function    set_%n
				--DEFAULT    get-function    get_%n
				--DEFAULT    next-function    std_next
				--DEFAULT cookie        (char *) 0
            ::= { cbFPGADownload 4 }

     END
