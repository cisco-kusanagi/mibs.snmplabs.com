-- zyxel Communications Corporation
 -- Private Enterprise MIB definition - Calvin Chai
 -- 04/30/96

 -- This file describes the zyxel Communications Corporation Enterprise MIB.
 -- It includes object identifiers and object definitions for the zyxel
 -- Enterprise MIB only, and should be used for compilation by a management
 -- tool in order to extend the tool to support the zyxel MIB.

    ZYXEL-MIB DEFINITIONS ::= BEGIN

    IMPORTS
	enterprises, NetworkAddress, IpAddress, Counter
		FROM RFC1155-SMI
	OBJECT-TYPE
		FROM RFC-1212
	TRAP-TYPE
	        FROM RFC-1215;

	DisplayString	::=	OCTET STRING

 -- tree structure

	zyxel			OBJECT IDENTIFIER ::= { enterprises 890 }

	products		OBJECT IDENTIFIER ::= { zyxel 1 }

	prestige		OBJECT IDENTIFIER ::= { products 2 }

	pSysVariables		OBJECT IDENTIFIER ::= { prestige 1 }
	pBRIVariables		OBJECT IDENTIFIER ::= { prestige 2 }
	pIPXVariables		OBJECT IDENTIFIER ::= { prestige 3 }
	pAPTVariables		OBJECT IDENTIFIER ::= { prestige 4 }
	pBRGVariables		OBJECT IDENTIFIER ::= { prestige 5 }
	pDialInVariables	OBJECT IDENTIFIER ::= { prestige 6 }
	pRemoteNodeVariables	OBJECT IDENTIFIER ::= { prestige 7 }
	pRemoteUserVariables	OBJECT IDENTIFIER ::= { prestige 8 }
	zyxelTraps		OBJECT IDENTIFIER ::= { prestige 9 }

 -- Node: zyxel
 -- Node: products
 -- Node: prestige
 -- Node: pSysVariables		This group contains information dealing
 --				wish the overall prestige system, such as
 --				software versions, feature bits...etc.
 
        whyReboot       OBJECT-TYPE
                        SYNTAX	DisplayString 
                        ACCESS  read-only
                        STATUS  mandatory
                        DESCRIPTION
                           "Send a message to the manager that the system is going to reboot.
	                 The variable is the reason of rebooting."
                        ::= { zyxelTraps 1 }

	pSysRasSWVersion OBJECT-TYPE
		SYNTAX	DisplayString (SIZE (0..255))
		ACCESS	read-only
		STATUS	mandatory
		DESCRIPTION
			"The current RAS software version."
	::= { pSysVariables 1 }

	pSysIsdnFWVersion OBJECT-TYPE
		SYNTAX	DisplayString (SIZE (0..255))
		ACCESS	read-only
		STATUS	mandatory
		DESCRIPTION
			"The current ISDN firmware version."
	::= { pSysVariables 2 }

	pSysRouteIP OBJECT-TYPE
		SYNTAX	INTEGER {
			no(1),
			yes(2)
		}
		ACCESS	read-only
		STATUS	mandatory
		DESCRIPTION
			"Determines if TCP/IP is enabled."
	::= { pSysVariables 3 }

	pSysRouteIPX OBJECT-TYPE
		SYNTAX	INTEGER {
			no(1),
			yes(2),
			na(3)
		}
		ACCESS	read-only
		STATUS	mandatory
		DESCRIPTION
			"Determines if IPX is enabled."
	::= { pSysVariables 4 }

	pSysRouteAPT OBJECT-TYPE
		SYNTAX	INTEGER {
			no(1),
			yes(2),
			na(3)
		}
		ACCESS	read-only
		STATUS	mandatory
		DESCRIPTION
			"Determines if AppleTalk is enabled."
	::= { pSysVariables 5 }

	pSysBridge OBJECT-TYPE
		SYNTAX	INTEGER {
			no(1),
			yes(2)
		}
		ACCESS	read-only
		STATUS	mandatory
		DESCRIPTION
			"Determines if Bridging is enabled."
	::= { pSysVariables 6 }

 -- Node: pBRIVariables		This group defines the ISDN variables.

	pBRISwitchType OBJECT-TYPE
		SYNTAX	INTEGER {
			nortelcustom(1),
			at-tni-1(2),
			dss1(3),
			ltr6(4),
			at-tp2p(5),
			at-tp2m(6),
			nortelni-1(7),
			at-tni-1(8),
			at-tp2m(9),
			nortelni-1(10)
		}
		ACCESS	read-only
		STATUS	mandatory
		DESCRIPTION
			"Identifies the ISDN switch type."
	::= { pBRIVariables 1 }

	pBChannelUsage OBJECT-TYPE
		SYNTAX	INTEGER {
			switch-unused(1),
			switch-switch(2)
		}
		ACCESS	read-only
		STATUS	mandatory
		DESCRIPTION
			"Idenitifes how the B channels are used."
	::= { pBRIVariables 2 }

	p1stPhoneNumber OBJECT-TYPE
		SYNTAX	DisplayString (SIZE (0..255))
		ACCESS	read-only
		STATUS	mandatory
		DESCRIPTION
			"First telephone number."
	::= { pBRIVariables 3 }

	p1stSpidNumber OBJECT-TYPE
		SYNTAX	DisplayString (SIZE (0..255))
		ACCESS	read-only
		STATUS	mandatory
		DESCRIPTION
			"First SPID number."
	::= { pBRIVariables 4 }

	p1stAnalogCall OBJECT-TYPE
		SYNTAX	INTEGER {
			none(1),
			modem(2),
			voice(3),
			data(4)
		}
		ACCESS	read-only
		STATUS	mandatory
		DESCRIPTION
			"How the 1st channel will handle an analog call."
	::= { pBRIVariables 5 }

	p2ndPhoneNumber OBJECT-TYPE
		SYNTAX	DisplayString (SIZE (0..255))
		ACCESS	read-only
		STATUS	mandatory
		DESCRIPTION
			"Second telephone number."
	::= { pBRIVariables 6 }

	p2ndSpidNumber OBJECT-TYPE
		SYNTAX	DisplayString (SIZE (0..255))
		ACCESS	read-only
		STATUS	mandatory
		DESCRIPTION
			"Second SPID number."
	::= { pBRIVariables 7 }

	p2ndAnalogCall OBJECT-TYPE
		SYNTAX	INTEGER {
			none(1),
			modem(2),
			voice(3),
			data(4),
			na(5)
		}
		ACCESS	read-only
		STATUS	mandatory
		DESCRIPTION
			"How the 2nd channel will handle an analog call."
	::= { pBRIVariables 8 }

 -- Node: pIPXVariables		Defines the IPX variables for the prestige

	pFrameType8022 OBJECT-TYPE
		SYNTAX	INTEGER {
			no(1),
			yes(2)
		}
		ACCESS	read-only
		STATUS	mandatory
		DESCRIPTION
			"Frame type 802.2 is enabled."
	::= { pIPXVariables 1 }

	pSeedRouter8022 OBJECT-TYPE
		SYNTAX	INTEGER {
			no(1),
			yes(2),
			na(3)
		}
		ACCESS	read-only
		STATUS	mandatory
		DESCRIPTION
			"Defines if this is a seed router."
	::= { pIPXVariables 2 }

	pNetworkNumber8022 OBJECT-TYPE
		SYNTAX	DisplayString (SIZE (0..255))
		ACCESS	read-only
		STATUS	mandatory
		DESCRIPTION
			"Defines the network address for this frame type."
	::= { pIPXVariables 3 }

	pFrameType8023 OBJECT-TYPE
		SYNTAX	INTEGER {
			no(1),
			yes(2)
		}
		ACCESS	read-only
		STATUS	mandatory
		DESCRIPTION
			"Frame type 802.3 is enabled."
	::= { pIPXVariables 4 }

	pSeedRouter8023 OBJECT-TYPE
		SYNTAX	INTEGER {
			no(1),
			yes(2),
			na(3)
		}
		ACCESS	read-only
		STATUS	mandatory
		DESCRIPTION
			"Defines if this is a seed router."
	::= { pIPXVariables 5 }

	pNetworkNumber8023 OBJECT-TYPE
		SYNTAX	DisplayString (SIZE (0..255))
		ACCESS	read-only
		STATUS	mandatory
		DESCRIPTION
			"Defines the network address for this frame type."
	::= { pIPXVariables 6 }

	pFrameTypeEthernetII OBJECT-TYPE
		SYNTAX	INTEGER {
			no(1),
			yes(2)
		}
		ACCESS	read-only
		STATUS	mandatory
		DESCRIPTION
			"Frame type Ethernet II is enabled."
	::= { pIPXVariables 7 }

	pSeedRouterEthernetII OBJECT-TYPE
		SYNTAX	INTEGER {
			no(1),
			yes(2),
			na(3)
		}
		ACCESS	read-only
		STATUS	mandatory
		DESCRIPTION
			"Defines if this is a seed router."
	::= { pIPXVariables 8 }

	pNetworkNumberEthernetII OBJECT-TYPE
		SYNTAX	DisplayString (SIZE (0..255))
		ACCESS	read-only
		STATUS	mandatory
		DESCRIPTION
			"Defines the network address for this frame type."
	::= { pIPXVariables 9 }

	pFrameTypeSnap OBJECT-TYPE
		SYNTAX	INTEGER {
			no(1),
			yes(2)
		}
		ACCESS	read-only
		STATUS	mandatory
		DESCRIPTION
			"Frame type SNAP is enabled."
	::= { pIPXVariables 10 }

	pSeedRouterSnap OBJECT-TYPE
		SYNTAX	INTEGER {
			no(1),
			yes(2),
			na(3)
		}
		ACCESS	read-only
		STATUS	mandatory
		DESCRIPTION
			"Defines if this is a seed router."
	::= { pIPXVariables 11 }

	pNetworkNumberSnap OBJECT-TYPE
		SYNTAX	DisplayString (SIZE (0..255))
		ACCESS	read-only
		STATUS	mandatory
		DESCRIPTION
			"Defines the network address for this frame type."
	::= { pIPXVariables 12 }

	pIPXRouteTable OBJECT-TYPE
		SYNTAX	SEQUENCE OF PIPXRouteEntry
		ACCESS	not-accessible
		STATUS	mandatory
		DESCRIPTION
			"Each row of the table provides the information for
			 an IPX static route."
	::= { pIPXVariables 13 }

	pipxRouteEntry OBJECT-TYPE
		SYNTAX	PIPXRouteEntry
		ACCESS	not-accessible
		STATUS	mandatory
		DESCRIPTION
			"The object type of the rows in pIPXRouteTable."
		INDEX	{ pIpxRtIndex } 
	::= { pIPXRouteTable 1 }

	PIPXRouteEntry ::= SEQUENCE {
		pIpxRtIndex		INTEGER,
		pIpxRtServerName	DisplayString,
		pIpxRtActive		INTEGER,
		pIpxRtNetworkNumber	DisplayString,
		pIpxRtNodeNumber	DisplayString,
		pIpxRtSocketNumber	DisplayString,
		pIpxRtTypeNumber	DisplayString,
		pIpxRtHopCount		INTEGER,
		pIpxRtTickCount		INTEGER,
		pIpxRtGatewayNode	INTEGER
	}

	pIpxRtIndex OBJECT-TYPE
		SYNTAX	INTEGER
		ACCESS	read-only
		STATUS	mandatory
		DESCRIPTION
			"The index of the route entry."
	::= { pipxRouteEntry 1 }	

	pIpxRtServerName OBJECT-TYPE
		SYNTAX	DisplayString (SIZE (0..255))
		ACCESS	read-only
		STATUS	mandatory
		DESCRIPTION
			"The name of the IPX route."
	::= { pipxRouteEntry 2 }

	pIpxRtActive OBJECT-TYPE
		SYNTAX	INTEGER {
			no(1),
			yes(2)
		}
		ACCESS	read-only
		STATUS	mandatory
		DESCRIPTION
			"Determines if the route is active or not."
	::= { pipxRouteEntry 3 }

	pIpxRtNetworkNumber OBJECT-TYPE
		SYNTAX	DisplayString (SIZE (0..255))
		ACCESS	read-only
		STATUS	mandatory
		DESCRIPTION
			"The network number for this IPX route."
	::= { pipxRouteEntry 4 }

	pIpxRtNodeNumber OBJECT-TYPE
		SYNTAX	DisplayString (SIZE (0..255))
		ACCESS	read-only
		STATUS	mandatory
		DESCRIPTION
			"The node number for this IPX route."
	::= { pipxRouteEntry 5 }

	pIpxRtSocketNumber OBJECT-TYPE
		SYNTAX	DisplayString (SIZE (0..255))
		ACCESS	read-only
		STATUS	mandatory
		DESCRIPTION
			"The socket number for this IPX route."
	::= { pipxRouteEntry 6 }

	pIpxRtTypeNumber OBJECT-TYPE
		SYNTAX	DisplayString (SIZE (0..255))
		ACCESS	read-only
		STATUS	mandatory
		DESCRIPTION
			"The type number for this IPX route."
	::= { pipxRouteEntry 7 }

	pIpxRtHopCount OBJECT-TYPE
		SYNTAX	INTEGER
		ACCESS	read-only
		STATUS	mandatory
		DESCRIPTION
			"The hop count for this IPX route."
	::= { pipxRouteEntry 8 }

	pIpxRtTickCount OBJECT-TYPE
		SYNTAX	INTEGER
		ACCESS	read-only
		STATUS	mandatory
		DESCRIPTION
			"The tick count for this IPX route."
	::= { pipxRouteEntry 9 }

	pIpxRtGatewayNode OBJECT-TYPE
		SYNTAX	INTEGER
		ACCESS	read-only
		STATUS	mandatory
		DESCRIPTION
			"The remote node number that serves as the gateway
			 for this IPX route."
	::= { pipxRouteEntry 10 }

 -- Node: pAPTVariables

	pAPTSeedRouter OBJECT-TYPE
		SYNTAX	INTEGER {
			no(1),
			yes(2)
		}
		ACCESS	read-only
		STATUS	mandatory
		DESCRIPTION
			"Determines if this is a seed router."
	::= { pAPTVariables 1 }

	pAPTNetworkMin OBJECT-TYPE
		SYNTAX	INTEGER {
			na(65536)
		}
		ACCESS	read-only
		STATUS	mandatory
		DESCRIPTION
			"The network minimum number for the range."
	::= { pAPTVariables 2 }

	pAPTNetworkMax OBJECT-TYPE
		SYNTAX	INTEGER {
			na(65536)
		}
		ACCESS	read-only
		STATUS	mandatory
		DESCRIPTION
			"The network maximum number for the range."
	::= { pAPTVariables 3 }

	pAPT1stZoneName OBJECT-TYPE
		SYNTAX	DisplayString (SIZE (0..255))
		ACCESS	read-only
		STATUS	mandatory
		DESCRIPTION
			"1st AppleTalk zone name."
	::= { pAPTVariables 4 }

	pAPT2ndZoneName OBJECT-TYPE
		SYNTAX	DisplayString (SIZE (0..255))
		ACCESS	read-only
		STATUS	mandatory
		DESCRIPTION
			"2nd AppleTalk zone name."
	::= { pAPTVariables 5 }

	pAPTZipTimeout OBJECT-TYPE
		SYNTAX	INTEGER
		ACCESS	read-only
		STATUS	mandatory
		DESCRIPTION
			"Zip Timeout."
	::= { pAPTVariables 6 }

	pAPTRouteTable OBJECT-TYPE
		SYNTAX	SEQUENCE OF PAPTRouteEntry
		ACCESS	not-accessible
		STATUS	mandatory
		DESCRIPTION
			"Each row of this table provides the information for
			 an AppleTalk static route."
	::= { pAPTVariables 7 }

	paptRouteEntry OBJECT-TYPE
		SYNTAX	PAPTRouteEntry
		ACCESS	not-accessible
		STATUS	mandatory
		DESCRIPTION
			"The object type of the rows in pAPTRouteTable."
		INDEX	{ pAptRtIndex }
	::= { pAPTRouteTable 1 }

	PAPTRouteEntry ::= SEQUENCE {
		pAptRtIndex		INTEGER,
		pAptRt1stZoneName	DisplayString,
		pAptRt2ndZoneName	DisplayString,
		pAptRtNetworkMin	INTEGER,
		pAptRtNetworkMax	INTEGER,
		pAptRtActive		INTEGER,
		pAptRtMetric		INTEGER,
		pAptRtGatewayNode	INTEGER
	}

	pAptRtIndex OBJECT-TYPE
		SYNTAX	INTEGER
		ACCESS	read-only
		STATUS	mandatory
		DESCRIPTION
			"The row index for the static route."
	::= { paptRouteEntry 1 }

	pAptRt1stZoneName OBJECT-TYPE
		SYNTAX	DisplayString (SIZE (0..255))
		ACCESS	read-only
		STATUS	mandatory
		DESCRIPTION
			"1st zone name for this static route."
	::= { paptRouteEntry 2 }

	pAptRt2ndZoneName OBJECT-TYPE
		SYNTAX	DisplayString (SIZE (0..255))
		ACCESS	read-only
		STATUS	mandatory
		DESCRIPTION
			"2nd zone name for this static route."
	::= { paptRouteEntry 3 }

	pAptRtNetworkMin OBJECT-TYPE
		SYNTAX	INTEGER
		ACCESS	read-only		
		STATUS	mandatory
		DESCRIPTION
			"Network min number for this static route."
	::= { paptRouteEntry 4 }

	pAptRtNetworkMax OBJECT-TYPE
		SYNTAX	INTEGER
		ACCESS	read-only		
		STATUS	mandatory
		DESCRIPTION
			"Network max number for this static route."
	::= { paptRouteEntry 5 }

	pAptRtActive OBJECT-TYPE
		SYNTAX	INTEGER {
			no(1),
			yes(2)
		}
		ACCESS	read-only		
		STATUS	mandatory
		DESCRIPTION
			"Determines if this static route is active."
	::= { paptRouteEntry 6 }

	pAptRtMetric OBJECT-TYPE
		SYNTAX	INTEGER
		ACCESS	read-only		
		STATUS	mandatory
		DESCRIPTION
			"Metric for this static route."
	::= { paptRouteEntry 7 }

	pAptRtGatewayNode OBJECT-TYPE
		SYNTAX	INTEGER
		ACCESS	read-only		
		STATUS	mandatory
		DESCRIPTION
			"Gateway remote node for this static route."
	::= { paptRouteEntry 8 }

-- Node: pBRGVariables

	pBRGHandleIpx OBJECT-TYPE
		SYNTAX	INTEGER {
			none(1),
			client(2),
			server(3)
		}
		ACCESS	read-only
		STATUS	mandatory
		DESCRIPTION
			"Determines how prestige should handle IPX."
	::= { pBRGVariables 1 }

	pBRGRouteTable OBJECT-TYPE
		SYNTAX	SEQUENCE OF PBRGRouteEntry
		ACCESS	not-accessible
		STATUS	mandatory
		DESCRIPTION
			"Each row of this table provides the information for
			 a Bridge static route."
	::= { pBRGVariables 2 }

	pbrgRouteEntry OBJECT-TYPE
		SYNTAX	PBRGRouteEntry
		ACCESS	not-accessible
		STATUS	mandatory
		DESCRIPTION
			"The object type of the rows in pBRGRouteTable."
		INDEX	{ pBrgRtIndex }
	::= { pBRGRouteTable 1 }

	PBRGRouteEntry ::= SEQUENCE {
		pBrgRtIndex		INTEGER,
		pBrgRtRouteName		DisplayString,
		pBrgRtActive		INTEGER,
		pBrgRtEtherAddress	DisplayString,
		pBrgRtIpAddress		IpAddress,
		pBrgRtGatewayNode	INTEGER
	}

	pBrgRtIndex OBJECT-TYPE
		SYNTAX	INTEGER
		ACCESS	read-only
		STATUS	mandatory
		DESCRIPTION
			"The row index for the static route."
	::= { pbrgRouteEntry 1 }

	pBrgRtRouteName OBJECT-TYPE
		SYNTAX	DisplayString (SIZE (0..255))
		ACCESS	read-only
		STATUS	mandatory
		DESCRIPTION
			"Route name for this static route."
	::= { pbrgRouteEntry 2 }

	pBrgRtActive OBJECT-TYPE
		SYNTAX	INTEGER {
			no(1),
			yes(2)
		}
		ACCESS	read-only		
		STATUS	mandatory
		DESCRIPTION
			"Determines if this static route is active."
	::= { pbrgRouteEntry 3 }

	pBrgRtEtherAddress OBJECT-TYPE
		SYNTAX	DisplayString (SIZE (0..255))
		ACCESS	read-only
		STATUS	mandatory
		DESCRIPTION
			"The ethernet address for this static route."
	::= { pbrgRouteEntry 4 }

	pBrgRtIpAddress OBJECT-TYPE
		SYNTAX	IpAddress
		ACCESS	read-only
		STATUS	mandatory
		DESCRIPTION
			"The ip dress for this static route."
	::= { pbrgRouteEntry 5}

	pBrgRtGatewayNode OBJECT-TYPE
		SYNTAX	INTEGER
		ACCESS	read-only		
		STATUS	mandatory
		DESCRIPTION
			"Gateway remote node for this static route."
	::= { pbrgRouteEntry 6 }

 -- Node: pDialInVariables		This group contains information for
 --					the default dial-in parameters.

	pDIClidAuthen OBJECT-TYPE
		SYNTAX	INTEGER {
			none(1),
			required(2),
			preferred(3)
		}
		ACCESS	read-only
		STATUS	mandatory
		DESCRIPTION
			"CLID authentication status for incoming calls."
	::= { pDialInVariables 1 }

	pDIRecvAuthen OBJECT-TYPE
		SYNTAX	INTEGER {
			chap-pap(1),
			chap(2),
			pap(3),
			none(4)
		}
		ACCESS	read-only
		STATUS	mandatory
		DESCRIPTION
			"Determines the type of authentication for incoming
			 calls."
	::= { pDialInVariables 2 }

	pDILinkCompression OBJECT-TYPE
		SYNTAX	INTEGER {
			none(1),
			stac(2),
			v42bis(3)
		}
		ACCESS	read-only
		STATUS	mandatory
		DESCRIPTION
			"Determines the type of compression algorithm used."
	::= { pDialInVariables 3 }

	pDIMaxTransferRate OBJECT-TYPE
		SYNTAX	INTEGER {
			speed-128k(1),
			speed-64k(2)
		}
		ACCESS	read-only
		STATUS	mandatory
		DESCRIPTION
			"Maximum transfer rate allowed."
	::= { pDialInVariables 4 }

	pDIIdleTimeout OBJECT-TYPE
		SYNTAX	INTEGER
		ACCESS	read-only
		STATUS	mandatory
		DESCRIPTION
			"The default idle timeout value."
	::= { pDialInVariables 5 }

	pDIIpAddressSupply OBJECT-TYPE
		SYNTAX	INTEGER {
			user(1),
			pool(2)
		}
		ACCESS	read-only
		STATUS	mandatory
		DESCRIPTION
			"How the IP address is supplied."
	::= { pDialInVariables 6 }

	pDIIpPoolStartAddress OBJECT-TYPE
		SYNTAX	IpAddress
		ACCESS	read-only
		STATUS	mandatory
		DESCRIPTION
			"The IP pool start address."
	::= { pDialInVariables 7 }

	pDIIpPoolCount OBJECT-TYPE
		SYNTAX	INTEGER {
			na(1000)
		}
		ACCESS	read-only
		STATUS	mandatory
		DESCRIPTION
			"Number of IP pool address to use."
	::= { pDialInVariables 8 }

	pDIIpxPool OBJECT-TYPE
		SYNTAX	INTEGER {
			no(1),
			yes(2)
		}
		ACCESS	read-only
		STATUS	mandatory
		DESCRIPTION
			"Use IPX pool to assign IPX network number."
	::= { pDialInVariables 9 }

	pDIIpxPoolStartNetNumber OBJECT-TYPE
		SYNTAX	DisplayString (SIZE (0..255))
		ACCESS	read-only
		STATUS	mandatory
		DESCRIPTION
			"Starting IPX net number in the pool."
	::= { pDialInVariables 10 }

	pDIIpxPoolCount OBJECT-TYPE
		SYNTAX	INTEGER {
			na(1000)
		}
		ACCESS	read-only
		STATUS	mandatory
		DESCRIPTION
			"IPX pool count number."
	::= { pDialInVariables 11 }

 -- Node: pRemoteNodeVariables

	pRemoteNodeTable OBJECT-TYPE
		SYNTAX	SEQUENCE OF PRemoteNodeEntry
		ACCESS	not-accessible
		STATUS	mandatory
		DESCRIPTION
			"Each row of this table provides the information for
			 one remote node."
	::= { pRemoteNodeVariables 1 }

	premoteNodeEntry OBJECT-TYPE
		SYNTAX	PRemoteNodeEntry
		ACCESS	not-accessible
		STATUS	mandatory
		DESCRIPTION
			"The object type of the rows in pRemoteNodeTable."
		INDEX	{ pRNIndex }
	::= { pRemoteNodeTable 1 }

	PRemoteNodeEntry ::= SEQUENCE {
		pRNIndex		INTEGER,
		pRNName			DisplayString,
		pRNActive		INTEGER,
		pRNCallDirection	INTEGER,
		pRNRemLogin		DisplayString,
		pRNRemClid		DisplayString,
		pRNCallBack		INTEGER,
		pRNMyLogin		DisplayString,
		pRN1stPhoneNumber	DisplayString,
		pRN2ndPhoneNumber	DisplayString,
		pRNRouteType		INTEGER,
		pRNBridgeEnabled	INTEGER,
		pRNEncapsulation	INTEGER,
		pRNIpAddress		IpAddress,
		pRNTransferRate		INTEGER,
		pRNIdleTimeout		INTEGER
	}

	pRNIndex OBJECT-TYPE
		SYNTAX	INTEGER
		ACCESS	read-only
		STATUS	mandatory
		DESCRIPTION
			"Row number for this node in the remote node table."
	::= { premoteNodeEntry 1 }

	pRNName OBJECT-TYPE
		SYNTAX	DisplayString (SIZE (0..255))
		ACCESS	read-only
		STATUS	mandatory
		DESCRIPTION
			"Descriptive name to identify the remote node."
	::= { premoteNodeEntry 2 }

	pRNActive OBJECT-TYPE
		SYNTAX	INTEGER {
			no(1),
			yes(2)
		}
		ACCESS	read-only
		STATUS	mandatory
		DESCRIPTION
			"To set the remote node active or inactive."
	::= { premoteNodeEntry 3 }

	pRNCallDirection OBJECT-TYPE
		SYNTAX	INTEGER {
			both(1),
			incoming(2),
			outgoing(3)
		}
		ACCESS	read-only
		STATUS	mandatory
		DESCRIPTION
			"Call direction for the remote node."
	::= { premoteNodeEntry 4 }

	pRNRemLogin OBJECT-TYPE
		SYNTAX	DisplayString (SIZE (0..255))
		ACCESS	read-only
		STATUS	mandatory
		DESCRIPTION
			"Remote node login name."
	::= { premoteNodeEntry 5 }

	pRNRemClid OBJECT-TYPE
		SYNTAX	DisplayString (SIZE (0..255))
		ACCESS	read-only
		STATUS	mandatory
		DESCRIPTION
			"Remote node CLID number."
	::= { premoteNodeEntry 6 }

	pRNCallBack OBJECT-TYPE
		SYNTAX	INTEGER {
			no(1),
			yes(2),
			na(3)
		}
		ACCESS	read-only
		STATUS	mandatory
		DESCRIPTION
			"Remote node callback enabled or not."
	::= { premoteNodeEntry 7 }

	pRNMyLogin OBJECT-TYPE
		SYNTAX	DisplayString (SIZE (0..255))
		ACCESS	read-only
		STATUS	mandatory
		DESCRIPTION
			"Your login name for a call to a remote node."
	::= { premoteNodeEntry 8 }

	pRN1stPhoneNumber OBJECT-TYPE
		SYNTAX	DisplayString (SIZE (0..255))
		ACCESS	read-only
		STATUS	mandatory
		DESCRIPTION
			"Primary phone number for the remote node."
	::= { premoteNodeEntry 9 }

	pRN2ndPhoneNumber OBJECT-TYPE
		SYNTAX	DisplayString (SIZE (0..255))
		ACCESS	read-only
		STATUS	mandatory
		DESCRIPTION
			"Secondary phone number for the remote node."
	::= { premoteNodeEntry 10 }

	pRNRouteType OBJECT-TYPE
		SYNTAX	INTEGER {
			none(1),
			ip(2),
			ipx(3),
			appletalk(4),
			ip-ipx(5),
			ip-appletalk(6),
			ipx-appletalk(7),
			ip-ipx-appletalk(8)
		}
		ACCESS	read-only
		STATUS	mandatory
		DESCRIPTION
			"Route capabilities for this remote node."
	::= { premoteNodeEntry 11 }

	pRNBridgeEnabled OBJECT-TYPE
		SYNTAX	INTEGER {
			no(1),
			yes(2)
		}
		ACCESS	read-only
		STATUS	mandatory
		DESCRIPTION
			"Bridging enabled or disabled."
	::= { premoteNodeEntry 12 }

	pRNEncapsulation OBJECT-TYPE
		SYNTAX	INTEGER {
			ppp(1),
			ascend(2),
			microsoft(3)
		}
		ACCESS	read-only
		STATUS	mandatory
		DESCRIPTION
			"Encapsualtion for the packets."
	::= { premoteNodeEntry 13 }

	pRNIpAddress OBJECT-TYPE
		SYNTAX	IpAddress
		ACCESS	read-only
		STATUS	mandatory
		DESCRIPTION
			"LAN IP address of remote node."
	::= { premoteNodeEntry 14 }
	
	pRNTransferRate OBJECT-TYPE
		SYNTAX	INTEGER {
			speed-2-2M(1),
			speed-56k-only(2),
			speed-Modem(3),
			speed-64k(4),
			speed-128k(5)
		}		
                                 ACCESS	read-only
		STATUS	mandatory
		DESCRIPTION
			"Transfer rate for the call to this remote node."
	::= { premoteNodeEntry 15 }

	pRNIdleTimeout OBJECT-TYPE
		SYNTAX	INTEGER
		ACCESS	read-only
		STATUS	mandatory
		DESCRIPTION
			"Idle timeout for this remote node."
	::= { premoteNodeEntry 16 }

 -- Node: pRemoteUserVariables

	pRemoteUserTable OBJECT-TYPE
		SYNTAX	SEQUENCE OF PRemoteUserEntry
		ACCESS	not-accessible
		STATUS	mandatory
		DESCRIPTION
			"Each row of this table provides a remote user entry."
	::= { pRemoteUserVariables 1 }

	premoteUserEntry OBJECT-TYPE
		SYNTAX	PRemoteUserEntry
		ACCESS	not-accessible
		STATUS	mandatory
		DESCRIPTION
			"The object type of the rows in pRemoteUserTable."
		INDEX	{ pRUIndex }
	::= { pRemoteUserTable 1 }

	PRemoteUserEntry ::= SEQUENCE {
		pRUIndex		INTEGER,
		pRUName			DisplayString,
		pRUActive		INTEGER,
		pRUCallBack		INTEGER,
		pRUCallBackNumber	DisplayString,
		pRUCallBackOverride	INTEGER,
		pRUClid			DisplayString,
		pRUIdleTimeout		INTEGER
	}

	pRUIndex OBJECT-TYPE
		SYNTAX	INTEGER
		ACCESS	read-only
		STATUS	mandatory
		DESCRIPTION
			"The row number of this remote user."
	::= { premoteUserEntry 1 }

	pRUName OBJECT-TYPE
		SYNTAX	DisplayString (SIZE (0..255))
		ACCESS	read-only
		STATUS	mandatory
		DESCRIPTION
			"The name of this remote user."
	::= { premoteUserEntry 2 }

	pRUActive OBJECT-TYPE
		SYNTAX	INTEGER {
			no(1),
			yes(2)
		}
		ACCESS	read-only
		STATUS	mandatory
		DESCRIPTION
			"Determines if remote user is active or inactive"
	::= { premoteUserEntry 3 }

	pRUCallBack OBJECT-TYPE
		SYNTAX	INTEGER {
			no(1),
			yes(2)
		}
		ACCESS	read-only
		STATUS	mandatory
		DESCRIPTION
			"Determines if callback is enabled for this remote user."
	::= { premoteUserEntry 4 }

	pRUCallBackNumber OBJECT-TYPE
		SYNTAX	DisplayString (SIZE (0..255))
		ACCESS	read-only
		STATUS	mandatory
		DESCRIPTION
			"The callback phone number of this remote user."
	::= { premoteUserEntry 5 }

	pRUCallBackOverride OBJECT-TYPE
		SYNTAX	INTEGER {
			no(1),
			yes(2)
		}
		ACCESS	read-only
		STATUS	mandatory
		DESCRIPTION
			"Determines if the callback override is enabled for this remote user."
	::= { premoteUserEntry 6 }

	pRUClid OBJECT-TYPE
		SYNTAX	DisplayString (SIZE (0..255))
		ACCESS	read-only
		STATUS	mandatory
		DESCRIPTION
			"The CLID number for this remote user."
	::= { premoteUserEntry 7 }

	pRUIdleTimeout OBJECT-TYPE
		SYNTAX	INTEGER
		ACCESS	read-only
		STATUS	mandatory
		DESCRIPTION
			"The idle timeout for this remote user."
	::= { premoteUserEntry 8 }
	
	
-- Define enterprise specific traps
-- 1. reboot
        reboot	TRAP-TYPE
	ENTERPRISE	zyxel
        VARIABLES       { 
                        whyReboot 
                        }
	DESCRIPTION	"Send a message to the manager that the system is going to reboot.
	                 The variable is the reason of rebooting."
	::= 1	

END
