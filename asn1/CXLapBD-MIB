CXLapBD-MIB DEFINITIONS ::= BEGIN


IMPORTS
   Counter         FROM RFC1155-SMI
   OBJECT-TYPE     FROM RFC-1212
   TRAP-TYPE               FROM RFC-1215
   DisplayString           FROM RFC1213-MIB
   cxLapBD,SapIndex,Alias
            FROM CXProduct-SMI;

-- Proprietary Data Types
Sapi            ::=     INTEGER {
            q930-q931       (0),
            x25             (16),
            mngmt           (63)
            }

Tei             ::=     INTEGER (0..127)



lapbdLowerPoolThreshold OBJECT-TYPE
   SYNTAX  INTEGER (1..99)
   ACCESS  read-write
   STATUS  mandatory
   DESCRIPTION
"Determines the lower global resource threshold (available buffer space), 
that when reached, causes the LAPB/D layer to initiate flow control 
(transmission of RNRs). This is a global value that applies across all 
lower SAPs (service access points). Thus if resources are low, all links 
are affected.

The value set for this object must not exceed the value set for the object 
lapbdUpperPoolThreshold. 

Range of Values: 1 - 99

Related Objects:
lapbdUpperPoolThreshold
lapbdMacSapFlowControlState

Default Value: 10 (10 percent)

Configuration Changed: administrative"
   DEFVAL { 10 }
   ::= { cxLapBD 1 }


lapbdUpperPoolThreshold OBJECT-TYPE
   SYNTAX  INTEGER (1..99)
   ACCESS  read-write
   STATUS  mandatory
   DESCRIPTION
"Determines the upper global resource threshold (available buffer space), 
that when reached, causes the LAPB/D layer to cancel flow control. This is 
a global value that applies across all lower SAPs (service access points). 


The value set for this object must not be less than the value set for the 
object lapbdLowerPoolThreshold. 

Range of Values: 1 - 99

Default Value: 20 (20 percent)

Related Objects:
lapbdUpperPoolThreshold
lapbdMacSapFlowControlState

Configuration Changed: administrative"
   DEFVAL { 20 }
   ::= { cxLapBD 2 }


lapbdTraceSize OBJECT-TYPE
   SYNTAX  INTEGER (0..30)
   ACCESS  read-write
   STATUS  mandatory
   DESCRIPTION
"Defines the number of bytes that are traced in each data buffer that is 
transmitted or received.

Range of Values: 0 - 30

Default Value: 15

Related Objects:
lapbdTraceFlags
lapbdMacSapControl

Configuration Changed: administrative and operative"
   DEFVAL { 15 }
   ::= { cxLapBD 3 }


lapbdTraceFlags OBJECT-TYPE
   SYNTAX  INTEGER (0..255)
   ACCESS  read-write
   STATUS  mandatory
   DESCRIPTION
"Specifies which events are traced. Each bit in this object is mapped to a 
specific event. Turning the bit on causes the event to be traced.

- bit 1:  trace all receive data events
- bit 2:  trace all transmit data events
- bit 3:  trace all timer events
- bit 4:  reserved for future use
- bit 5:  reserved for future use
- bit 6:  reserved for future use
- bit 7:  reserved for future use
- bit 8:  reserved for future use

Range of Values: 0 - 255

Default Value: 7

Related Objects:
lapbdTraceSize
lapbdMacSapControl

Configuration Changed: administrative and operative"
   DEFVAL { 7 }
   ::= { cxLapBD 4 }


lapbdTraps OBJECT-TYPE
   SYNTAX  INTEGER {
            disabled        (1),
            enabled (2)
            }
   ACCESS  read-write
   STATUS  mandatory
   DESCRIPTION
"Determines if this layer generates the lapbdStatusIndication trap.

Options:
disabled (1): This layer does not generate the lapbdStatusIndication trap.

enabled (2): This layer generates the lapbdStatusIndication trap.

Default Value: disabled (1)

Related Objects:
lapbdStatusEvent
lapbdStatusIndication

Configuration Changed: administrative and operative"
   DEFVAL { disabled }
   ::= { cxLapBD 7 }


lapbdStatusEvent OBJECT-TYPE
   SYNTAX  INTEGER {
            noEvent                 (1),
            enteringCongestion              (2),
            exitingCongestion               (3),
            linkUp                          (4),
            linkDown                        (5),
            protocolError                   (6),
            invTeiRemovalAttempt    (7)
            }
   ACCESS  read-only
   STATUS  mandatory
   DESCRIPTION
"Indicates the status reported by a lapbdStatusIndication trap when it 
occurs. This object always returns the value 'noEvent' when read.

Options:
noEvent (1): There is no status to report.

enteringCongestion (2): The data link connection is congested 
(lapbdMacSapTxQUpperThreshold has been exceeded). If this persists, the 
connection is terminated.

exitingCongestion (3): The data link connection has recovered from 
congestion and is operating normally.

linkUp (4): The LAPB/D link is active.

linkDown (5): The LAB/D link is inactive.

protocolError (6): A protocol error has occurred (FRMR for example).

invTeiRemovalAttempt (7): The local or remote attempted to remove a static 
TEI (terminal endpoint identifier)."
   ::= { cxLapBD 8 }


lapbdSoftwareVersions OBJECT-TYPE
   SYNTAX  DisplayString
   ACCESS  read-only
   STATUS  mandatory
   DESCRIPTION
"Identifies the LAPB/D software revision number, which is displayed as a 
string of five numbers each separated by a period (1.2.3.4.5). The five 
numbers represent:

- 1  main version number
- 2  main revision number
- 3  branch version number
- 4  branch revision number
- 5  part number"
   ::= { cxLapBD 10 }

-- gap (10) for future global parameters



--  MAC Service Access Point Configuration Table

--  The table describing:
--      parameters required to configure a mac service access point
--      controls available to manipulate a mac service access point
--      status available for monitoring the current state of the mac service 
--      access point
--      statistics available for monitoring any mac service access point

--    Service access points of this type exist at the lower interface of the 
--    Data Link layer, and are typically used to communicate with the 
--    Media Access Control (MAC) layer.


lapbdMacSapTable OBJECT-TYPE
   SYNTAX  SEQUENCE OF LapbdMacSapEntry
   ACCESS  not-accessible
   STATUS  mandatory
   DESCRIPTION
"A table containing configuration information about each LAPB/D lower 
service access point."
   ::= { cxLapBD 20 }


   lapbdMacSapEntry OBJECT-TYPE
      SYNTAX  LapbdMacSapEntry
      ACCESS  not-accessible
      STATUS  mandatory
      DESCRIPTION
"The parameters for a specific LAPB/D lower (MAC) service access point."
      INDEX { lapbdMacSapNumber }
      ::= { lapbdMacSapTable 1 }


   LapbdMacSapEntry ::=
      SEQUENCE {
-- Parameters
         lapbdMacSapNumber                               SapIndex,    -- 1--
         lapbdMacSapRowStatus                    INTEGER,             -- 2--
         lapbdMacSapAlias                                Alias,       -- 3--
         lapbdMacSapCompanionAlias               Alias,               -- 4--
         lapbdMacSapLapType                      INTEGER,             -- 5--
         lapbdMacSapLogicalInterfaceType         INTEGER,             -- 6--
         lapbdMacSapArbitrationLogic             INTEGER,             -- 7--
         lapbdMacSapLapDProtocolFlavor           INTEGER,             -- 8--
         lapbdMacSapLapBProtocolFlavor           INTEGER,             -- 9--
         lapbdMacSapWindow                               INTEGER,     --10--
         lapbdMacSapTxQUpperThreshold            INTEGER,             --11--
         lapbdMacSapTxQLowerThreshold            INTEGER,             --12--
         lapbdMacSapConnectionTimer              INTEGER,             --13--
         lapbdMacSapT202Timer                    INTEGER,             --14--
         lapbdMacSapN202Counter                  INTEGER,             --15--
         lapbdMacSapTeiCheckTimer                        INTEGER,     --16--
         lapbdMacSapT201Timer                    INTEGER,             --17--
         lapbdMacSapLowTei                               INTEGER,     --18--
         lapbdMacSapKeepL1Up                     INTEGER,             --19--
-- Control
         lapbdMacSapControl                              INTEGER,    --30--
-- Status
         lapbdMacSapHighLevelState                       INTEGER,    --35--
         lapbdMacSapFlowControlState             INTEGER,            --36--
         lapbdMacSapOutstandingFrames            Counter,            --37--
         lapbdMacSapTotalFramesDropped           Counter,            --38--
         lapbdMacSapActiveSaps                   Counter,            --39--
-- Statistics
         lapbdMacSapTxIFrames                    Counter,            --50--
         lapbdMacSapRxIFrames                    Counter,            --51--
         lapbdMacSapTxRrFrames                   Counter,            --52--
         lapbdMacSapRxRrFrames                   Counter,            --53--
         lapbdMacSapTxRnrFrames                  Counter,            --54--
         lapbdMacSapRxRnrFrames                  Counter,            --55--
         lapbdMacSapTxRejFrames                  Counter,            --56--
         lapbdMacSapRxRejFrames                  Counter,            --57--
         lapbdMacSapTxSabmFrames                 Counter,            --58--
         lapbdMacSapRxSabmFrames                 Counter,            --59--
         lapbdMacSapTxDiscFrames                 Counter,            --60--
         lapbdMacSapRxDiscFrames                 Counter,            --61--
         lapbdMacSapTxUaFrames                   Counter,            --62--
         lapbdMacSapRxUaFrames                   Counter,            --63--
         lapbdMacSapTxDmFrames                   Counter,            --64--
         lapbdMacSapRxDmFrames                   Counter,            --65--
         lapbdMacSapTxFrmrFrames                 Counter,            --66--
         lapbdMacSapRxFrmrFrames                 Counter,            --67--
         lapbdMacSapTxUiFrames                   Counter,            --68--
         lapbdMacSapRxUiFrames                   Counter,            --69--
         lapbdMacSapTxXidFrames                  Counter,            --70--
         lapbdMacSapRxXidFrames                  Counter,            --71--
         lapbdMacSapRxInvalidFrames              Counter,            --72--
         lapbdMacSapRxInvalidDiscards            Counter,            --73--
         lapbdMacSapSabmErrors                   Counter,            --74--
         lapbdMacSapFrmrErrors                   Counter         --75--
         }


   lapbdMacSapNumber OBJECT-TYPE
      SYNTAX  SapIndex
      ACCESS  read-only
      STATUS  mandatory
      DESCRIPTION
"Identifies the service access point by a unique numerical value."
      ::= { lapbdMacSapEntry 1 }


   lapbdMacSapRowStatus OBJECT-TYPE
      SYNTAX  INTEGER {
               invalid         (1),
               valid           (2)
               }
      ACCESS  read-write
      STATUS  mandatory
      DESCRIPTION
"Determines the status of the objects in a table row.

Options:
invalid (1): Row is deleted from the table immediately, however values are 
still in effect until the next reset. 

valid (2): Use this value to add a new row to the table, or modify an 
existing row.

Configuration Changed: administrative"
      ::= { lapbdMacSapEntry 2 }


   lapbdMacSapAlias OBJECT-TYPE
      SYNTAX  Alias
      ACCESS  read-write
      STATUS  mandatory
      DESCRIPTION
"Identifies the service access point by a textual name. Service access 
point names must be unique across all layers.

Range of Values: 1 -16 alphanumeric characters (first character must be a 
letter)

Default Value: none

Configuration Changed: administrative"
      ::= { lapbdMacSapEntry 3 }


   lapbdMacSapCompanionAlias OBJECT-TYPE
      SYNTAX  Alias
      ACCESS  read-write
      STATUS  mandatory
      DESCRIPTION
"Identifies by a textual name, the remote service access point with which 
this service access point will communicate with. Service access point 
names must be unique across all layers.

Range of Values: 1 -16 alphanumeric characters (first character must be a 
letter)

Default Value: none

Configuration Changed: administrative"
      ::= { lapbdMacSapEntry 4 }


   lapbdMacSapLapType OBJECT-TYPE
      SYNTAX  INTEGER {
               lapb            (1),
               lapd            (2)
               }
      ACCESS  read-write
      STATUS  mandatory
      DESCRIPTION
"Determines the type of link access procedure provided by this MAC SAP 
(service access point): LAPB or LAPD. It also determines the number of 
data link SAPs that are automatically created and associated with this 
SAP.

If the value of lapbdMacSapLapBProtocolFlavor is set to 'v8022', then the 
value for this object is forced to 'lapb', regardless of its setting. This 
object returns to its original value only when 
lapbdMacSapLapBProtocolFlavor is set to 'standard'.

Options:
lapb (1): Defines a LAPB service access point and creates one associated 
data link SAP.

lapd (2): Defines a LAPD service access point and creates three associated 
data link SAPs.

Default Value: lapb (1)

Related Objects:
lapbdMacSapLapBProtocolFlavor

Configuration Changed: administrative"
      DEFVAL { lapb }
      ::= { lapbdMacSapEntry 5 }


   lapbdMacSapLogicalInterfaceType OBJECT-TYPE
      SYNTAX  INTEGER {
               dte             (1),
               dce             (2)
               }
      ACCESS  read-write
      STATUS  mandatory
      DESCRIPTION
"Determines the logical interface type of the SAP (service access point): 
DTE or DCE. This is true only when the object lapbdMacSapLapType is set to 
'lapb'. When the object lapbdMacSapLapType set to 'lapd', 'dte' maps to 
user side and 'dce' maps to network side automatically. 

The network side is also known as the Assignment Source Point (ASP) of all 
TEIs (terminal endpoint identifiers). 

If the value of lapbdMacSapLapBProtocolFlavor is set to 'v8022', then the 
value for this object is forced to 'dte', regardless of its setting. This 
object returns to its original value only when 
lapbdMacSapLapBProtocolFlavor is set to 'standard'.

Options:
dte (1): The SAP functions as a DTE when object lapbdMacSapLapType is set 
to value 'lapb' and User when it is set to 'lapd'.

dce (2): The SAP functions as a DCE when object lapbdMacSapLapType is set 
to value 'lapb' and Network when it is set to 'lapd'.

Default Value: dte (1)

Related Objects:
lapbdMacSapLapType

Configuration Changed: administrative and operative"
      DEFVAL { dte }
      ::= { lapbdMacSapEntry 6 }


   lapbdMacSapArbitrationLogic OBJECT-TYPE
      SYNTAX  INTEGER {
               passive         (1),
               active          (2)
               }
      ACCESS  read-write
      STATUS  mandatory
      DESCRIPTION
"Determines if the SAP initiates the link (active) by sending a SABM 
(LAPB) or a SABME (LAPD) to the other side. Both sides can be active. 
However, typically the DCE side is active and the DTE side is passive.

Note: A link will never be established if both sides of the link are set 
to 'passive'.

Options:
passive (1): The SAP waits for the other side to initiate the link.

active (2): The SAP initiates the link.

Default Value: active (2)

Related Objects:
lapbdMacSapLapType
lapbdMacSapLogicalInterfaceType

Configuration Changed: administrative and operative"
      DEFVAL { active }
      ::= { lapbdMacSapEntry 7 }


   lapbdMacSapLapDProtocolFlavor OBJECT-TYPE
      SYNTAX  INTEGER {
               ccitt           (1),
               vn3             (2),
               etsi            (3)
               }
      ACCESS  read-write
      STATUS  mandatory
      DESCRIPTION
"This object applies only to LAPD (object lapbdMacSapLapType set to 
'lapd'). 

Determines how TEI (terminal endpoint identifier) assignments are handled.

Options:
ccitt (1): Supports CCITT standards (forces TEI assignment on power up).

vn3 (2): Supports VN3 standards (forces TEI assignment only when the layer 
above LAPB/D requests a connection).

etsi (3): Supports ETSI standards.

Default Value: ccitt (1)

Related Objects:
lapbdMacSapLapType

Configuration Changed: administrative and operative"
      DEFVAL { ccitt }
      ::= { lapbdMacSapEntry 8 }


   lapbdMacSapLapBProtocolFlavor OBJECT-TYPE
      SYNTAX  INTEGER {
               standard        (1),
               v8022           (2)
               }
      ACCESS  read-write
      STATUS  mandatory
      DESCRIPTION
"This object applies only to LAPB (object lapbdMacSapLapType set to 
'lapb'). 

Determines the LAPB protocol variant used by this SAP (service access 
point).

Setting this object to 'v8022' forces the following:

- object lapbdMacSapLogicalInterfaceType is set to 'dte'
- object lapbdDlSapModulo (lapbdDlSapTable) is set to 'modulo 128' 
- object lapbdDlSapMaxFrameSize (lapbdDlSapTable) is set to '265'

Once set, these settings are locked. Only the restoration of object 
lapbdMacSapLapBProtocolFlavor to 'standard' unlocks these objects.

Options:
standard (1): The standard LAPB protocol is used by this SAP.

v8022 (2): The 802.2 variant of the LAPB protocol is used by this SAP.

Default Value: standard (1)

Configuration Changed: administrative"
      DEFVAL { standard }
      ::= { lapbdMacSapEntry 9 }


   lapbdMacSapWindow OBJECT-TYPE
      SYNTAX  INTEGER (1..127)
      ACCESS  read-write
      STATUS  mandatory
      DESCRIPTION
"Determines the maximum number of frames that can be outstanding at any 
given time to a sub-layer. A frame is considered to be outstanding until 
its receipt is acknowledged. This object controls the setting of internal 
communications between layers. To control the actual window size of the 
data link connection see lapbdDlSapWindowSize.

Range of Values: 1 - 127

Default Value: 2

Configuration Changed: administrative and operative"
      DEFVAL { 2 }
      ::= { lapbdMacSapEntry 10 }


   lapbdMacSapTxQUpperThreshold OBJECT-TYPE
      SYNTAX  INTEGER (1..255)
      ACCESS  read-write
      STATUS  mandatory
      DESCRIPTION
"Defines the threshold which declares a data link connection on this MAC 
SAP (service access point) to be congested. When the number of frames in 
the queue for this data link connection exceeds this value, the congestion 
timer is started and link status is set to congested. If congestion has 
not cleared before this timer expires, the link is dropped.

Each data link connection through this MAC SAP (service access point) 
maintains its own queue.

Range of Values: 1 - 255

Default Value: 16

Related Objects:
lapbdMacSapTxQLowerThreshold
lapbdDlSapCongestionTimer
lapbdStatusEvent
lapbdDlcTxFlowControlState

Configuration Changed: administrative and operative"
      DEFVAL { 16 }
      ::= { lapbdMacSapEntry 11 }


   lapbdMacSapTxQLowerThreshold OBJECT-TYPE
      SYNTAX  INTEGER (1..255)
      ACCESS  read-write
      STATUS  mandatory
      DESCRIPTION
"Defines the threshold which declares a data link connection on this MAC 
SAP (service access point) to no longer be congested. When the number of 
frames in the queue for this data link connection reaches this value, the 
congestion timer is stopped and link status is set to not congested. 

Each data link connection through this MAC SAP (service access point) 
maintains its own queue.

Range of Values: 1 - 255

Default Value: 8

Related Objects:
lapbdMacSapTxQLowerThreshold
lapbdDlSapCongestionTimer
lapbdStatusEvent
lapbdDlcTxFlowControlState

Configuration Changed: administrative and operative"
      DEFVAL { 8 }
      ::= { lapbdMacSapEntry 12 }


   lapbdMacSapConnectionTimer OBJECT-TYPE
      SYNTAX  INTEGER (1..2047)
      ACCESS  read-write
      STATUS  mandatory
      DESCRIPTION
"Determines the maximum amount of time that the LAPB/D layer waits for a 
sub- layer to respond to a connection request. If this timer expires 
before a response is received, the connection is retried.

A positive response (connection confirmed) is only issued by the sub- 
layer when the physical/logical line is active, otherwise a negative 
response (disconnect indication) is issued.

Range of Values: 1 - 2047 (in tenths of a second)

Default Value: 30 (3 seconds)

Configuration Changed: administrative and operative"
      DEFVAL { 30 }
      ::= { lapbdMacSapEntry 13 }


   lapbdMacSapT202Timer OBJECT-TYPE
      SYNTAX  INTEGER (1..2047)
      ACCESS  read-write
      STATUS  mandatory
      DESCRIPTION
"This object applies only when: object lapbdMacSapLapType is set to 'lapd' 
object lapbdMacSapLogicalInterfaceType is set to 'dte' (user side) object 
lapbdDlSapTeiAssignmentMode is set to 'automatic' (automatically assign 
TEIs)

Determines the minimum amount of time between retransmission of TEI 
Identity-Request messages.

Default Value: 20 (2 seconds)

Range of Values: 1 - 2047 (in tenths of a second)

Configuration Changed: administrative and operative"
      REFERENCE       "(T202-LAPD)"
      DEFVAL { 20 }
      ::= { lapbdMacSapEntry 14 }


   lapbdMacSapN202Counter OBJECT-TYPE
      SYNTAX  INTEGER (1..1023)
      ACCESS  read-write
      STATUS  mandatory
      DESCRIPTION
"This object applies only when: object lapbdMacSapLapType is set to 'lapd' 
object lapbdMacSapLogicalInterfaceType is set to 'dte' (user side) object 
lapbdDlSapTeiAssignmentMode is set to 'automatic' (automatically assign 
TEIs)

Determines the maximum number of retransmission of TEI Identity-Request 
messages.

Default Value: 3

Range of Values: 1 - 1023

Related Object:
lapbdMacSapT202Timer

Configuration Changed: administrative and operative"
      REFERENCE       "(N202-LAPD)"
      DEFVAL { 3 }
      ::= { lapbdMacSapEntry 15 }


   lapbdMacSapTeiCheckTimer OBJECT-TYPE
      SYNTAX  INTEGER (0..2047)
      ACCESS  read-write
      STATUS  mandatory
      DESCRIPTION
"This object applies only when: object lapbdMacSapLapType is set to 'lapd' 
object lapbdMacSapLogicalInterfaceType is set to 'dce' (network side/ASP) 
object lapbdDlSapTeiAssignmentMode is set to 'automatic' (automatically 
assign TEIs)

Determines how long the ASP (assignment source point) waits between 
initiating TEI check procedures. 

The value for this object must be greater than two times the value of 
object lapbdMacSapT201Timer. Default Value: 0 (disabled)

Range of Values: 1 - 2047 (in tenths of a second), a value of 0 disables 
the timer

Related Object:
lapbdMacSapT202Timer

Configuration Changed: administrative and operative"
      DEFVAL { 0 }
      ::= { lapbdMacSapEntry 16 }


   lapbdMacSapT201Timer OBJECT-TYPE
      SYNTAX  INTEGER (1..2047)
      ACCESS  read-write
      STATUS  mandatory
      DESCRIPTION
"This object applies only when: object lapbdMacSapLapType is set to 'lapd' 
object lapbdMacSapLogicalInterfaceType is set to 'dce' (network side/ASP) 
object lapbdDlSapTeiAssignmentMode is set to 'automatic' (automatically 
assign TEIs)

Determines the delay between retransmission of TEI Identity-Check messages 
by the ASP (assignment source point).

The value for this object must be less than half the value of object 
lapbdMacSapTeiCheckTimer.

Default Value: 20 (2 seconds)

Range of Values: 1 - 2047 (in tenths of a second)

Related Object:
lapbdMacSapTeiCheckTimer

Configuration Changed: administrative and operative"
      REFERENCE       "(T201-LAPD)"
      DEFVAL { 20 }
      ::= { lapbdMacSapEntry 17 }


   lapbdMacSapLowTei OBJECT-TYPE
      SYNTAX  INTEGER (0..127)
      ACCESS  read-write
      STATUS  mandatory
      DESCRIPTION
"This object applies only to LAPD (object lapbdMacSapLapType set to 
'lapd')

Determines lower boundary for automatic TEI assignments. This defines the 
ranges for automatic and non-automatic (static) TEIs assignments as 
follows:

TEI numbers from 0 to lapbdMacSapLowTei -1 are available for non-automatic 
(static) assignment. TEI numbers from lapbdMacSapLowTei to 127 are 
available for automatic assignment

Range of Values: 0 - 127 

Default Value: 64 (recommended by the ITU-T)

Related Objects:
lapbdMacSapLapType 
lapbdMacSapLowTei

Configuration Changed: administrative and operative"
      DEFVAL { 64 }
      ::= { lapbdMacSapEntry 18 }


   lapbdMacSapKeepL1Up OBJECT-TYPE
      SYNTAX  INTEGER {
               disabled        (1),
               enabled (2)
               }
      ACCESS  read-write
      STATUS  mandatory
      DESCRIPTION
"This object applies only to LAPD (object lapbdMacSapLapType set to 
'lapd').

Determines how this SAP (service access point) handles connections with 
the sub-layer.

Options:
disabled (1): This SAP attempts to connect with the sub-layer only when 
the layer above LAPB/D connects to this SAP.

enabled (2): This SAP always attempts to connect with the sub-layer.

Default Value: enabled (2)

Configuration Changed: administrative and operative"
      DEFVAL { enabled }
      ::= { lapbdMacSapEntry 19 }


   lapbdMacSapControl OBJECT-TYPE
      SYNTAX  INTEGER {
               clearStats              (1),
               enableTrace             (2),
               disableTrace            (3),
               enableMacSap            (4),
               disableMacSap   (5)
               }
      ACCESS  write-only
      STATUS  mandatory
      DESCRIPTION
"Permits control of a specific MAC SAP (service access point).

Options:
clearStats (1): Clear all statistics stored by lapbdMacSap statistics 
objects.

enableTrace (2): Display LAPB/D protocol data on the console. 

disableTrace (3):Do not display LAPB/D protocol data on the console.

enableMacSap (4): Forces the LAPB link to issue a SABM frame.

disableMacSap (5): Forces the LAPB link to issue a DISC frame.

Default Value: none

Configuration Changed: administrative and operative"
      ::= { lapbdMacSapEntry 30 }


   lapbdMacSapHighLevelState OBJECT-TYPE
      SYNTAX  INTEGER {
               unbound (1),
               configured      (2),
               bound           (3)
               }
      ACCESS  read-only
      STATUS  mandatory
      DESCRIPTION
"Indicates the current state of this MAC SAP (service access point).

Options:
unbound (1): Initial state when the SAP is added.

configured (2): The layer manager has configured the SAP.

bound (3):Fully-functional MAC SAP."
      ::= { lapbdMacSapEntry 35 }


   lapbdMacSapFlowControlState OBJECT-TYPE
      SYNTAX  INTEGER {
               flowNormal      (1),
               flowStopped     (2),
               noFlow  (3)
               }
      ACCESS  read-only
      STATUS  mandatory
      DESCRIPTION
"Indicates the status of flow control on this MAC SAP (service access 
point).

Flow control is initiated by this MAC SAP when overall system resources 
drop lower than the percentage specified by the global object 
lapbdLowerPoolThreshold, and is terminated when the overall system 
resources exceed the percentage specified by the global object 
lapbdUpperPoolThreshold.

Options:
flowNormal (1): Data flow is normal. No flow control procedures are 
active.

flowStopped (2): Flow control procedures are active, since overall system 
resources have dropped lower than the percentage specified by global 
object lapbdLowerPoolThreshold.

noFlow (3): Indicates this SAP is configured incorrectly.

Related Objects:
lapbdLowerPoolThreshold
lapbdUpperPoolThreshold"
      ::= { lapbdMacSapEntry 36 }


   lapbdMacSapOutstandingFrames OBJECT-TYPE
      SYNTAX  Counter
      ACCESS  read-only
      STATUS  mandatory
      DESCRIPTION
"Indicates the current number of outstanding frames to the sub-layer. The 
object lapbdMacSapWindow defines the maximum number of frames that can be 
outstanding."
      ::= { lapbdMacSapEntry 37 }


   lapbdMacSapTotalFramesDropped OBJECT-TYPE
      SYNTAX  Counter
      ACCESS  read-only
      STATUS  mandatory
      DESCRIPTION
"Indicates the number of frames dropped by this MAC service access point, 
which may be due to an internal problem between the MAC layer and the 
sub-layer it is communicating with. This does not indicate a problem with 
the data link connection."
      ::= { lapbdMacSapEntry 38 }


   lapbdMacSapActiveSaps OBJECT-TYPE
      SYNTAX  Counter
      ACCESS  read-only
      STATUS  mandatory
      DESCRIPTION
"This object applies only to LAPD (object lapbdMacSapLapType set to 
'lapd').

Indicates the number of active data link SAPs (service access points) 
associated with this MAC SAP. Currently this is always set to three.

Related Object:
lapbdDlSapNumber"
      ::= { lapbdMacSapEntry 39 }


   lapbdMacSapTxIFrames OBJECT-TYPE
      SYNTAX  Counter
      ACCESS  read-only
      STATUS  mandatory
      DESCRIPTION
"Indicates the number of information frames sent from this service access 
point."
      ::= { lapbdMacSapEntry  50 }


   lapbdMacSapRxIFrames OBJECT-TYPE
      SYNTAX  Counter
      ACCESS  read-only
      STATUS  mandatory
      DESCRIPTION
"Indicates the number of information frames received at this service 
access point."
      ::= { lapbdMacSapEntry  51 }


   lapbdMacSapTxRrFrames OBJECT-TYPE
      SYNTAX  Counter
      ACCESS  read-only
      STATUS  mandatory
      DESCRIPTION
"Indicates the number of receive ready (RR) frames sent from this service 
access point."
      ::= { lapbdMacSapEntry  52 }


   lapbdMacSapRxRrFrames OBJECT-TYPE
      SYNTAX  Counter
      ACCESS  read-only
      STATUS  mandatory
      DESCRIPTION
"Indicates the number of receive ready (RR) frames received by this 
service access point."
      ::= { lapbdMacSapEntry  53 }


   lapbdMacSapTxRnrFrames OBJECT-TYPE
      SYNTAX  Counter
      ACCESS  read-only
      STATUS  mandatory
      DESCRIPTION
"Indicates the number of receive not ready (RNR) frames transmitted by 
this service access point."
      ::= { lapbdMacSapEntry  54 }


   lapbdMacSapRxRnrFrames OBJECT-TYPE
      SYNTAX  Counter
      ACCESS  read-only
      STATUS  mandatory
      DESCRIPTION
"Indicates the number of receive not ready (RNR) frames received by this 
service access point."
      ::= { lapbdMacSapEntry  55 }


   lapbdMacSapTxRejFrames OBJECT-TYPE
      SYNTAX  Counter
      ACCESS  read-only
      STATUS  mandatory
      DESCRIPTION
"Indicates the number of reject (REJ) frames transmitted by this service 
access point."
      ::= { lapbdMacSapEntry  56 }


   lapbdMacSapRxRejFrames OBJECT-TYPE
      SYNTAX  Counter
      ACCESS  read-only
      STATUS  mandatory
      DESCRIPTION
"Indicates the number of reject (REJ) frames received by this service 
access point."
      ::= { lapbdMacSapEntry  57 }


   lapbdMacSapTxSabmFrames OBJECT-TYPE
      SYNTAX  Counter
      ACCESS  read-only
      STATUS  mandatory
      DESCRIPTION
"Indicates the number of set asynchronous balanced mode (SABM) frames 
transmitted by this service access point."
      ::= { lapbdMacSapEntry  58 }


   lapbdMacSapRxSabmFrames OBJECT-TYPE
      SYNTAX  Counter
      ACCESS  read-only
      STATUS  mandatory
      DESCRIPTION
"Indicates the number of set asynchronous balanced mode (SABM) frames 
received by this service access point."
      ::= { lapbdMacSapEntry  59 }


   lapbdMacSapTxDiscFrames OBJECT-TYPE
      SYNTAX  Counter
      ACCESS  read-only
      STATUS  mandatory
      DESCRIPTION
"Indicates the number of disconnect (DISC) frames sent from this service 
access point."
      ::= { lapbdMacSapEntry  60 }


   lapbdMacSapRxDiscFrames OBJECT-TYPE
      SYNTAX  Counter
      ACCESS  read-only
      STATUS  mandatory
      DESCRIPTION
"Indicates the number of disconnect (DISC) frames transmitted by this 
service access point."
      ::= { lapbdMacSapEntry  61 }


   lapbdMacSapTxUaFrames OBJECT-TYPE
      SYNTAX  Counter
      ACCESS  read-only
      STATUS  mandatory
      DESCRIPTION
"Indicates the number of unnumbered acknowledgment (UA) frames sent from 
this service access point."
      ::= { lapbdMacSapEntry  62 }


   lapbdMacSapRxUaFrames OBJECT-TYPE
      SYNTAX  Counter
      ACCESS  read-only
      STATUS  mandatory
      DESCRIPTION
"Indicates the number of unnumbered acknowledgment (UA) frames received by 
this service access point."
      ::= { lapbdMacSapEntry  63 }


   lapbdMacSapTxDmFrames OBJECT-TYPE
      SYNTAX  Counter
      ACCESS  read-only
      STATUS  mandatory
      DESCRIPTION
"Indicates the number of disconnected mode (DM) frames transmitted by this 
service access point."
      ::= { lapbdMacSapEntry  64 }


   lapbdMacSapRxDmFrames OBJECT-TYPE
      SYNTAX  Counter
      ACCESS  read-only
      STATUS  mandatory
      DESCRIPTION
"Indicates the number of disconnected mode (DM) frames received by this 
service access point."
      ::= { lapbdMacSapEntry  65 }


   lapbdMacSapTxFrmrFrames OBJECT-TYPE
      SYNTAX  Counter
      ACCESS  read-only
      STATUS  mandatory
      DESCRIPTION
"Indicates the number of frame reject (FRMR) frames transmitted by this 
service access point."
      ::= { lapbdMacSapEntry  66 }


   lapbdMacSapRxFrmrFrames OBJECT-TYPE
      SYNTAX  Counter
      ACCESS  read-only
      STATUS  mandatory
      DESCRIPTION
"Indicates the number of frame reject (FRMR) frames received by this 
service access point."
      ::= { lapbdMacSapEntry  67 }


   lapbdMacSapTxUiFrames OBJECT-TYPE
      SYNTAX  Counter
      ACCESS  read-only
      STATUS  mandatory
      DESCRIPTION
"This object applies only to LAPD (object lapbdMacSapLapType set to 
'lapd').

Indicates the number of unnumbered information (UI) frames transmitted by 
this service access point."
      ::= { lapbdMacSapEntry  68 }


   lapbdMacSapRxUiFrames OBJECT-TYPE
      SYNTAX  Counter
      ACCESS  read-only
      STATUS  mandatory
      DESCRIPTION
"This object applies only to LAPD (object lapbdMacSapLapType set to 
'lapd').

Indicates the number of unnumbered information (UI) frames received by 
this service access point."
      ::= { lapbdMacSapEntry  69 }


   lapbdMacSapTxXidFrames OBJECT-TYPE
      SYNTAX  Counter
      ACCESS  read-only
      STATUS  mandatory
      DESCRIPTION
"Indicates the number of XID frames transmitted by this service access 
point."
      ::= { lapbdMacSapEntry  70 }


   lapbdMacSapRxXidFrames OBJECT-TYPE
      SYNTAX  Counter
      ACCESS  read-only
      STATUS  mandatory
      DESCRIPTION
"Indicates the number of XID frames received by this service access 
point."
      ::= { lapbdMacSapEntry  71 }


   lapbdMacSapRxInvalidFrames OBJECT-TYPE
      SYNTAX  Counter
      ACCESS  read-only
      STATUS  mandatory
      DESCRIPTION
"Indicates the number of invalid frames received by this service access 
point."
      ::= { lapbdMacSapEntry  72 }


   lapbdMacSapRxInvalidDiscards OBJECT-TYPE
      SYNTAX  Counter
      ACCESS  read-only
      STATUS  mandatory
      DESCRIPTION
"Indicates the number of frames received at this service access point 
which were marked as being received in error, and subsequently dropped. 
The errors covered by this statistic are line reception errors such as:

- aborted frames
- frames received with a bad CRC
- frames that were overrun
- frames with non-integral number of bits
- frames that are too long"
      ::= { lapbdMacSapEntry  73 }


   lapbdMacSapSabmErrors OBJECT-TYPE
      SYNTAX  Counter
      ACCESS  read-only
      STATUS  mandatory
      DESCRIPTION
"Indicates the number of set asynchronous balanced mode errors that 
occurred at this service access point."
      ::= { lapbdMacSapEntry  74 }


   lapbdMacSapFrmrErrors OBJECT-TYPE
      SYNTAX  Counter
      ACCESS  read-only
      STATUS  mandatory
      DESCRIPTION
"Indicates the number of frame reject errors that occurred at this service 
access point."
      ::= { lapbdMacSapEntry  75 }


--  Data Link Service Access Point Configuration Table

--  The table describing:
--      parameters required to modify parameters at a data link service 
--      access point
--      controls available to manipulate a data link service access point
--      status available for monitoring the current state of the data link 
--      service access point
--      statistics available for monitoring any data link service access 
--      point

--    Service access points of this type exist at the upper interface of the 
--    Data Link layer, and are automatically created for every mac service 
--    access point created.

--    One data link service access point will be automatically created for a 
--  LAPB configured mac service access point, and three data link service 
--  access points will be automatically created for a LAPD configured mac 
--  service access point .


lapbdDlSapTable OBJECT-TYPE
   SYNTAX  SEQUENCE OF LapbdDlSapEntry
   ACCESS  not-accessible
   STATUS  mandatory
   DESCRIPTION
"A table containing configuration information about each data link SAP 
(service access point). Data link SAPs exist at the upper layer of the 
LAPB/D interface and are automatically created when a lower SAP is 
created.

For lower SAPs of type LAPB, one upper SAP is created. For lowers SAPs of 
type LAPD, three upper SAPs are created (see object lapbdDlSapNumber)"
   ::= { cxLapBD 21 }


   lapbdDlSapEntry OBJECT-TYPE
      SYNTAX  LapbdDlSapEntry
      ACCESS  not-accessible
      STATUS  mandatory
      DESCRIPTION
"The parameters for a specific data link service access point."
      INDEX { lapbdDlSapMacSapNumber,
            lapbdDlSapNumber }
      ::= { lapbdDlSapTable 1 }


   LapbdDlSapEntry ::=
      SEQUENCE {
-- Parameters
         lapbdDlSapMacSapNumber                  SapIndex,
         lapbdDlSapNumber                                Sapi,
--                      lapbdDlSapRowStatus                     INTEGER,
         lapbdDlSapAlias                         Alias,
         lapbdDlSapMaxFrameSize                  INTEGER,
         lapbdDlSapWindowSize                    INTEGER,
         lapbdDlSapMaxRetransmissions            INTEGER,
         lapbdDlSapCongestionTimer                       INTEGER,
         lapbdDlSapT1T200Timer                   INTEGER,
         lapbdDlSapT2Timer                               INTEGER,
         lapbdDlSapT3T203Timer                   INTEGER,
         lapbdDlSapModulo                                INTEGER,
         lapbdDlSapMaxDlcs                               INTEGER,
         lapbdDlSapTeiAssignmentMode             INTEGER,
-- Control
-- Status
         lapbdDlSapHighLevelState                        INTEGER,
         lapbdDlSapActiveDlcs                    Counter
-- Statistics
         }


   lapbdDlSapMacSapNumber OBJECT-TYPE
      SYNTAX  SapIndex
      ACCESS  read-only
      STATUS  mandatory
      DESCRIPTION
"Identifies the MAC (lower) service access point this entry is associated 
with."
      ::= { lapbdDlSapEntry 1 }


   lapbdDlSapNumber OBJECT-TYPE
      SYNTAX  Sapi
      ACCESS  read-only
      STATUS  mandatory
      DESCRIPTION
"Identifies the data link service access point by a unique numerical 
value, commonly referred to as the SAPI (service access point identifier). 
The SAPI identifies the type of protocol that is supported by this SAP. It 
is a LAPD concept which permits the multiplexing of different types of 
traffic on the same TEI.

When LAPD service is selected (object lapbdMacSapLapType set to value 
'lapd'), and a row is added to the lapbdSapTable, three data link SAPs are 
automatically created with following SAPI values: 0, 16, 63

SAPI is not used within LAPB, and as a result when LAPB service is 
selected (object lapbdMacSapLapType value 'lapb'), and a row is added to 
the lapbdSapTable, only one data link SAP with the value 16 (X.25) is 
automatically created.

Options:
0: This SAP is associated with ISDN B- channel call control procedures.

16: This SAP is associated with X.25 over ISDN.

63: This SAP is associated with ISDN management procedures.

Related Objects:
lapbdMacSapLapType"
      ::= { lapbdDlSapEntry 2 }


-- gap (1) for future use


   lapbdDlSapAlias OBJECT-TYPE
      SYNTAX  Alias
      ACCESS  read-write
      STATUS  mandatory
      DESCRIPTION
"The textual name that identifies this SAP (service access point). A name 
is not required.

Range of Values: 1 -16 alphanumeric characters (first character must be a 
letter)

Default Value: none

Configuration Changed: administrative"
      ::= { lapbdDlSapEntry 4 }


   lapbdDlSapMaxFrameSize OBJECT-TYPE
      SYNTAX  INTEGER (1..4095)
      ACCESS  read-write
      STATUS  mandatory
      DESCRIPTION
"Determines the maximum size of the LAPB/D information field supported by 
this SAP. In other words, it is the maximum number of bytes that can be 
passed through this SAP in either direction (to upper or lower layers).

Setting lapbdMacSapLapbProtocolFlavour to 'v8022' forces this object to 
'265'.

Range of Values: 0 - 4095

Default Value: LAPB = 1380, LAPD = 260

Related Objects:
lapbdMacSapLapbProtocolFlavor

Configuration Changed: administrative and operative"
      REFERENCE       "(N1-LAPB)/ (N201-LAPD)"
      DEFVAL { 1380 }
      ::= { lapbdDlSapEntry 5 }


   lapbdDlSapWindowSize OBJECT-TYPE
      SYNTAX  INTEGER (1..127)
      ACCESS  read-write
      STATUS  mandatory
      DESCRIPTION
"Determines the maximum number of information frames that can be 
outstanding at any given time (window size). A frame is considered to be 
outstanding until the other side acknowledges its receipt. This object 
supports modulo 8 and modulo 128 service. 

Setting lapbdMacSapLapbProtocolFlavour to 'v8022' forces lapbdDlSapModulo 
to 'modulo 128', which affects the maximum setting that can be made to 
this object.

Range of Values:

1 - 7 if object lapbdDlSapModulo is set to modulo8

1 - 127 if object lapbdDlSapModulo is set to modulo128

Default Value: LAPB = 7, LAPD = 7

Related Objects:
lapbdDlSapModulo
lapbdMacSapLapbProtocolFlavour

Configuration Changed: administrative and operative"
      REFERENCE       "(K)"
      DEFVAL { 7 }
      ::= { lapbdDlSapEntry 6 }


   lapbdDlSapMaxRetransmissions OBJECT-TYPE
      SYNTAX  INTEGER (1..127)
      ACCESS  read-write
      STATUS  mandatory
      DESCRIPTION
"Determines the maximum number of attempts made to successfully transfer a 
command frame (error recovery) after the acknowledgment timer 
(lapbdDlSapT1T200Timer) expires. Known as N2. 

Default Value: LAPB = 5, LAPD = 3

Default Value: 5

Related Objects:
lapbdDlSapT1T200Timer

Configuration Changed: administrative and operative"
      REFERENCE       "(N2-LAPB)/ (N200-LAPD)"
      DEFVAL { 5 }
      ::= { lapbdDlSapEntry 7 }


   lapbdDlSapCongestionTimer OBJECT-TYPE
      SYNTAX  INTEGER (0..2047)
      ACCESS  read-write
      STATUS  mandatory
      DESCRIPTION
"Determines the maximum amount of time LAPB/D waits for the link to become 
uncongested before it terminates the link.

This timer is started when the number of frames queued for a data link 
connection associated with this service access point (lapbdDlcTxQSize) 
reaches the congestion threshold (lapbdMacSapTxQUpperThreshold).

This timer is stopped when the number of frames queued for a data link 
connection (lapbdDlcTxQSize) reaches the congestion minimum 
(lapbdMacSapTxQLowerThreshold).

If this timer expires, the data link connection is terminated.

Range of Values: 0 - 2047 (in tenths of a second)

Default Value: LAPB = 1000 (100 seconds)

LAPD = 1000 (100 seconds)

Related Objects:
lapbdDlcTxQSize
lapbdMacSapTxQUpperThreshold
lapbdMacSapTxQLowerThreshold

Configuration Changed: administrative and operative"
      DEFVAL { 1000 }
      ::= { lapbdDlSapEntry 8 }


   lapbdDlSapT1T200Timer OBJECT-TYPE
      SYNTAX  INTEGER (1..2047)
      ACCESS  read-write
      STATUS  mandatory
      DESCRIPTION
"Determines how long this SAP waits for a response to a command frame 
before initiating error recovery. Known as the checkpoint timer (T1). The 
value set for this object must be smaller than the value set for object 
lapbdDlSapT3T203Timer.

Range of Values: 1 -2047 (in tenths of a second)

Default Value: LAPB = 20 (2 seconds), LAPD = 10 (1 second)

Related Objects:
lapbdDlSapMaxRetransmissions
lapbdDlSapT3T203Timer

Configuration Changed: administrative and operative"
      REFERENCE       "(T1-LAPB)/ (T200-LAPD)"
      DEFVAL { 20 }
      ::= { lapbdDlSapEntry 9 }


   lapbdDlSapT2Timer OBJECT-TYPE
      SYNTAX  INTEGER (1..2047)
      ACCESS  read-write
      STATUS  mandatory
      DESCRIPTION
"This object applies only to LAPB (object lapbdMacSapLapType set to 
'lapb'). 

Determines the period of time (T1)within which this SAP must acknowledge a 
frame it has received. 

This timer must always be less than the setting for T1 timer on the remote 
side. Otherwise, the remote side will time out before this SAP can 
respond.

Range of Values: 1 - 2047 (in tenths of a second)

Default Value: LAPB = 10 (1 second), LAPD = 0 seconds 

Related Objects:
lapbdDlSapT1T200Timer

Configuration Changed: administrative and operative"
      REFERENCE       "(T2-LAPB)"
      DEFVAL { 10 }
      ::= { lapbdDlSapEntry 10 }


   lapbdDlSapT3T203Timer OBJECT-TYPE
      SYNTAX  INTEGER (1..2047)
      ACCESS  read-write
      STATUS  mandatory
      DESCRIPTION
"Determines the maximum time this SAP will allow the link to remain idle 
(no frames exchanged) before sending an RR poll to the other side. Known 
as idle probe timer (T3).

Range of Values: 1 - 2047 (in tenths of a second) 

Default Value: LAPB = 200 (20 seconds), LAPD = 200 (20 seconds)

Configuration Changed: administrative and operative"
      REFERENCE       "(T3-LAPB)/ (T203-LAPD)"
      DEFVAL { 200 }
      ::= { lapbdDlSapEntry 11 }


   lapbdDlSapModulo OBJECT-TYPE
      SYNTAX  INTEGER {
               modulo8 (1),
               modulo128       (2)
               }
      ACCESS  read-write
      STATUS  mandatory
      DESCRIPTION
"Determines the range of sequence numbers available for frame numbering at 
this SAP (service access point). The modulo limits the size of the window 
that can be set (lapbdDlSapWindowSize).

Setting lapbdMacSapLapbProtocolFlavour to 'v8022' forces this object to 
'modulo 128'.

Options:
modulo8 (1): Sequence numbers range from 0 to 7 supporting a maximum 
window size of 7.

modulo128 (2): Sequence numbers range from 0 to 128 supporting a maximum 
window size of 127.

Default Value: LAPB = modulo8 (1), LAPD = modulo128 (2)

Related Objects:
lapbdDlSapWindowSize
lapbdMacSapLapbProtocolFlavour

Configuration Changed: administrative and operative"
      DEFVAL { modulo8 }
      ::= { lapbdDlSapEntry 12 }


   lapbdDlSapMaxDlcs OBJECT-TYPE
      SYNTAX  INTEGER (1..127)
      ACCESS  read-write
      STATUS  mandatory
      DESCRIPTION
"This object applies only to LAPD (object lapbdMacSapLapType set to 
'lapd'). 

Determines the maximum number of data link connections supported at this 
service access point.

Related Object:
lapbdMacSapLapType

Default Value: LAPB = 1, LAPD = 1

Configuration Changed: administrative"
      DEFVAL { 1 }
      ::= { lapbdDlSapEntry 13 }


   lapbdDlSapTeiAssignmentMode OBJECT-TYPE
      SYNTAX  INTEGER {
               nonAutomatic    (1),
               automatic       (2)
               }
      ACCESS  read-write
      STATUS  mandatory
      DESCRIPTION
"This object applies only to LAPD (object lapbdMacSapLapType set to 
'lapd'). 

Determines the TEI assignment mode used by this service access point. Each 
data link service access point can be configured as either 'automatic' or 
'non-Automatic' (static) even if assigned to the same MAC sap. 

Options:
nonAutomatic (1): TEIs are not automatically assigned by the ASP 
(assignment source point).

automatic (2): TEIs are automatically assigned.

Default Value: LAPB = automatic (2), LAPD = automatic (2)

Related Objects:
lapbdMacSapLapType

Configuration Changed: administrative"
      DEFVAL { automatic }
      ::= { lapbdDlSapEntry 14 }


   lapbdDlSapHighLevelState OBJECT-TYPE
      SYNTAX  INTEGER {
               unbound (1),
               configured      (2),
               bound           (3)
               }
      ACCESS  read-only
      STATUS  mandatory
      DESCRIPTION
"Indicates the current state of this SAP (service access point).

Options:
unbound (1): Initial state when the SAP is added.

configured (2): The layer manager has configured the SAP.

bound (3):Fully-functional data link SAP."
      ::= { lapbdDlSapEntry 15 }


   lapbdDlSapActiveDlcs OBJECT-TYPE
      SYNTAX  Counter
      ACCESS  read-only
      STATUS  mandatory
      DESCRIPTION
"This object applies only to LAPD (object lapbdMacSapLapType set to 
'lapd'). 

Indicates the current number of active data link connections at this SAP 
(service access point)."
      ::= { lapbdDlSapEntry 16 }



-- Tei Table (LAPD-only)

--    The table used to define the Terminal Endpoint Identifiers (TEIs).
--
--    A TEI is are used to identify a specific connection endpoint within 
--    a data link service access point (identified by its SAPI), at a 
--    specific mac sap.
--
--  TEIs are assigned by the network equipment if the user equipment is 
--  configured for automatic TEI assignment, or it is entered into the user 
--  equipment if the user equipment is configured for non-automatic (static) 
--  TEI assignment.


lapbdTeiTable OBJECT-TYPE
   SYNTAX  SEQUENCE OF LapbdTeiEntry
   ACCESS  not-accessible
   STATUS  mandatory
   DESCRIPTION
"A table containing Terminal Endpoint Identifiers (TEIs) which are to be 
assigned to identify data link connections.

A TEI is used to identify a specific connection endpoint within a data 
link service access point (identified by its SAPI), at a specific MAC 
(lower) sap.

TEIs are assigned by the network equipment if the user equipment is 
configured for automatic TEI assignment, or are entered into the user 
equipment if the user equipment is configured for non-automatic (static) 
TEI assignment."
   ::= { cxLapBD 22 }


   lapbdTeiEntry OBJECT-TYPE
      SYNTAX  LapbdTeiEntry
      ACCESS  not-accessible
      STATUS  mandatory
      DESCRIPTION
"Determines the settings for a single TEI to be assigned to a data link 
connected at a specific data link service access point, which exists at a 
specific MAC (lower) SAP."
      INDEX { lapbdTeiMacSapNumber,
            lapbdTeiSapi,
            lapbdTeiNumber }
      ::= { lapbdTeiTable 1 }



   LapbdTeiEntry ::=
      SEQUENCE {
         lapbdTeiMacSapNumber                    SapIndex,
         lapbdTeiSapi                                    Sapi,
         lapbdTeiNumber                          Tei,
         lapbdTeiRowStatus                               INTEGER
         }



   lapbdTeiMacSapNumber OBJECT-TYPE
      SYNTAX  SapIndex
      ACCESS  read-only
      STATUS  mandatory
      DESCRIPTION
"This object applies only to LAPD (object lapbdMacSapLapType set to 
'lapd'). 

Identifies the MAC service access point (lapbdMacSapNumber ) this entry is 
associated with."
      ::= { lapbdTeiEntry 1 }


   lapbdTeiSapi OBJECT-TYPE
      SYNTAX  Sapi
      ACCESS  read-only
      STATUS  mandatory
      DESCRIPTION
"This object applies only to LAPD (object lapbdMacSapLapType set to 
'lapd'). 

Identifies the data link service access point (lapbdDlSapNumber ) this 
entry is associated with."
      ::= { lapbdTeiEntry 2 }


   lapbdTeiNumber OBJECT-TYPE
      SYNTAX  Tei
      ACCESS  read-only
      STATUS  mandatory
      DESCRIPTION
"This object applies only to LAPD (object lapbdMacSapLapType set to 
'lapd'). 

Identifies the TEI value assigned for use at the data link service access 
point identified by object lapbdTeiSapi, which exists at the MAC service 
access point identified by object lapbdTeiMacSapNumber."
      ::= { lapbdTeiEntry 3 }


   lapbdTeiRowStatus OBJECT-TYPE
      SYNTAX  INTEGER {
               invalid         (1),
               valid           (2)
               }
      ACCESS  read-write
      STATUS  mandatory
      DESCRIPTION
"Determines the status of the objects in a table row. 

Options:
invalid (1): Row is deleted from the table immediately, however values are 
still in effect until the next reset. 

valid (2): Use this value to add a new row to the table, or modify an 
existing row.

Default: valid (2)

Configuration Changed: administrative and operative"
      ::= { lapbdTeiEntry 4 }



-- Data Link Connection Status Table

--    The table containing the status of all data link connections which 
--   currently exist throughout the data link layer.



lapbdDlcStatusTable OBJECT-TYPE
   SYNTAX  SEQUENCE OF LapbdDlcStatusEntry
   ACCESS  not-accessible
   STATUS  mandatory
   DESCRIPTION
"A table containing status information for each existing data link 
connection."
   ::= { cxLapBD 23 }


   lapbdDlcStatusEntry OBJECT-TYPE
      SYNTAX  LapbdDlcStatusEntry
      ACCESS  not-accessible
      STATUS  mandatory
      DESCRIPTION
"The status of a specific data link connection at a specific data link 
service access point, which exists at a specific MAC service access 
point."
      INDEX {         lapbdDlcMacSapNumber,
            lapbdDlcSapi,
            lapbdDlcTei }
      ::= { lapbdDlcStatusTable 1 }



   LapbdDlcStatusEntry ::=
      SEQUENCE {
         lapbdDlcMacSapNumber                    SapIndex,
         lapbdDlcSapi                                    Sapi,
         lapbdDlcTei                                     Tei,
         lapbdDlcLinkLevelState                  INTEGER,
         lapbdDlcNextTxNs                                INTEGER,
         lapbdDlcNextRxNs                                INTEGER,
         lapbdDlcRetransmissionCount             INTEGER,
         lapbdDlcLocalFlowControlState           INTEGER,
         lapbdDlcRemoteFlowControlState          INTEGER,
         lapbdDlcMacTxFlowControlState           INTEGER,
         lapbdDlcTxQSize                         INTEGER
         }



   lapbdDlcMacSapNumber OBJECT-TYPE
      SYNTAX  SapIndex
      ACCESS  read-only
      STATUS  mandatory
      DESCRIPTION
"Identifies the MAC service access point (lower SAP) this entry is 
associated with."
      ::= { lapbdDlcStatusEntry 1 }


   lapbdDlcSapi OBJECT-TYPE
      SYNTAX  Sapi
      ACCESS  read-only
      STATUS  mandatory
      DESCRIPTION
"Identifies the data link service access point (upper SAP) this entry is 
associated with."
      ::= { lapbdDlcStatusEntry 2 }


   lapbdDlcTei OBJECT-TYPE
      SYNTAX  Tei
      ACCESS  read-only
      STATUS  mandatory
      DESCRIPTION
"This object applies only to LAPD (object lapbdMacSapLapType set to 
'lapd'). 

Identifies the TEI value (lapbdTeiNumber) this entry is associated with. "
      ::= { lapbdDlcStatusEntry 3 }


   lapbdDlcLinkLevelState OBJECT-TYPE
      SYNTAX  INTEGER {
               disconnectedDisabled            (1),
               connectingLinkLevel             (2),
               dataTransfer                    (3),
               disconnectingLinkLevel  (4),
               connectingAwaitingTei   (5),
               resettingLinkLevelEnabled       (6),
               resettingLinkLevelDisabled      (7),
               frameRejection          (8),
               disconnectedEnabled             (9),
               assignAwaitingTei               (10)
               }
      ACCESS  read-only
      STATUS  mandatory
      DESCRIPTION
"Indicates the current link level state at this data link connection.

Options:
disconnectedDisabled (1): LAPB/D is disconnected and has not yet received 
a connection request for this link from an upper layer.

connectingLinkLevel (2): Attempting to establish the link layer.

dataTransfer (3): In data transfer mode (LAPD only).

disconnectingLinkLevel (4): The link is being disconnected.

connectingAwaitingTei (5): Waiting for TEI assignments to be completed. 
(LAPD)

resettingLinkLevelEnabled (6): Resetting the link for an active 
connection.

resettingLinkLevelDisabled (7): Resetting the link for which no connection 
request was received. 

frameRejection (8): A frame was rejected.

disconnectedEnabled (9): Applies only if the link is configured as passive 
(lapbdMacSapAbritrationLogic). Indicates that a connection request was 
received from an upper layer, but the remote side has not yet initiated 
the link.

assignAwaitingTei (10): Waiting for TEI assignments to be completed. 
(LAPD)"
      ::= { lapbdDlcStatusEntry 4 }


   lapbdDlcNextTxNs OBJECT-TYPE
      SYNTAX  INTEGER
      ACCESS  read-only
      STATUS  mandatory
      DESCRIPTION
"Indicates the value of the next N(s) to send on this data link 
connection."
      ::= { lapbdDlcStatusEntry 5 }


   lapbdDlcNextRxNs OBJECT-TYPE
      SYNTAX  INTEGER
      ACCESS  read-only
      STATUS  mandatory
      DESCRIPTION
"Indicates the value of the next N(s) expected by this data link 
connection."
      ::= { lapbdDlcStatusEntry 6 }


   lapbdDlcRetransmissionCount OBJECT-TYPE
      SYNTAX  INTEGER
      ACCESS  read-only
      STATUS  mandatory
      DESCRIPTION
"Indicates the number of times the current command frame has been 
transmitted. The value for this object will be greater than 1 when 
retransmission of a frame is in progress (i.e., the lapbdDlSapT1T200Timer 
has expired).

Related Objects:
lapbdDlSapMaxRetransmissions
lapbdDlSapT1T200Timer"
      ::= { lapbdDlcStatusEntry 7 }


   lapbdDlcLocalFlowControlState OBJECT-TYPE
      SYNTAX  INTEGER {
               localFlowNormal (1),
               localFlowStopped        (2)
               }
      ACCESS  read-only
      STATUS  mandatory
      DESCRIPTION
"Indicates the status of flow control on this MAC SAP (service access 
point). Same as lapbMacSapFlowControlState.

Flow control is initiated by this MAC SAP when overall system resources 
drop lower than the percentage specified by the global object 
lapbdLowerPoolThreshold, and is terminated when the overall system 
resources exceed the percentage specified by the global object 
lapbdUpperPoolThreshold.

Options:
localflowNormal (1): Data flow is normal. No flow control procedures are 
active.

localflowStopped (2): Flow control procedures are active, since overall 
system resources have dropped lower than the percentage specified by 
global object lapbdLowerPoolThreshold.

noFlow (3): Indicates this SAP is configured incorrectly.

Related Objects:
lapbdLowerPoolThreshold
lapbdUpperPoolThreshold
lapbMacSapFlowControlState"
      ::= { lapbdDlcStatusEntry 8 }


   lapbdDlcRemoteFlowControlState OBJECT-TYPE
      SYNTAX  INTEGER {
               remoteFlowNormal        (1),
               remoteFlowStopped       (2)
               }
      ACCESS  read-only
      STATUS  mandatory
      DESCRIPTION
"Indicates the status of flow control on the remote side of the link.

Options:
remoteFlowNormal (1): Data flow is normal. No flow control procedures are 
active.

remoteFlowStopped (2): Flow control procedures are active."
      ::= { lapbdDlcStatusEntry 9 }


   lapbdDlcMacTxFlowControlState OBJECT-TYPE
      SYNTAX  INTEGER {
               flowNormal      (1),
               flowStopped     (2)
               }
      ACCESS  read-only
      STATUS  mandatory
      DESCRIPTION
"Indicates the status of data flow on the link.

Options:
flowNormal(1): The data link connection is operating normally.

FlowStopped(2): The data link connection is congested (frames queued for 
this SAP exceed the value of object lapbdMacSapTxQUpperThreshold), and the 
data link has initiated flow control procedures (RNRs). If this persists 
longer than the value of lapbdDlSapCongestionTime, the link is terminated. 
Flow is terminated when the number of queued frames is less than the value 
of object lapbdMacSapTxQLowerThreshold.

Related Objects:
lapbdMacSapTxQLowerThreshold
lapbdDlSapCongestionTimer
lapbdStatusEvent
lapbdDlcTxQueueSize"
      ::= { lapbdDlcStatusEntry 10 }


   lapbdDlcTxQSize OBJECT-TYPE
      SYNTAX  INTEGER
      ACCESS  read-only
      STATUS  mandatory
      DESCRIPTION
"Indicates the number of frames currently in the transmit queue for this 
data link connection. If the number of frames exceeds 
lapbdMacSapTxQUpperThreshold, the link is congested and flow control 
procedures are initiated. If this persists longer than the value of 
lapbdDlSapCongestionTime, the link is terminated. Flow is terminated when 
the number of queued frames exceeds the value of object 
lapbdMacSapTxQUpperThreshold.

Related Objects:
lapbdMacSapTxQLowerThreshold
lapbdDlSapCongestionTimer
lapbdStatusEvent
lapbdDlcTxFlowControlState"
      ::= { lapbdDlcStatusEntry 11 }



-- Traps


lapbdStatusIndication TRAP-TYPE
   ENTERPRISE      cxLapBD
   VARIABLES               {       lapbdTeiMacSapNumber,
               lapbdTeiSapi,
               lapbdTeiNumber,
               lapbdStatusEvent
            }
   DESCRIPTION
"Identifies the lapbdStatusEvent trap which has occurred. This trap is 
only generated when global object lapbdTraps is set to value 'enabled'.

Options:
lapbdTeiMacSapNumber: The MAC service access point this trap applies to.

lapbdTeiSapi: TheSAPI number this trap applies to.

lapbdTeiNumber: The TEI number this trap applies to.

lapbdStatusEvent: The event which triggered the trap (lapbdStatusEvent)."
   ::= 1


END
