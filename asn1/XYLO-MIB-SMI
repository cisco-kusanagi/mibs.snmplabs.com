-- File: xylo.smi
--	Bay Networks Private Enterprise Remote Annex MIB
--
--  Copyright 1991, 1993, 1994, 1995, 1996, 1997 Bay Networks, Inc. 
--  ALL RIGHTS RESERVED.
--
--  ALL RIGHTS RESERVED. Licensed Material - Property of Bay Networks, Inc.
--  This software is made available solely pursuant to the terms of a
--  software license agreement which governs its use.
--  Unauthorized duplication, distribution or sale are strictly prohibited.
--
--  This information is subject to change without notice, and should
--  not be construed as a commitment by Bay Networks, Inc.  Bay Networks, Inc.,
--  assumes no responsibility for any errors that may appear in this
--  document.
--
--  $Id: 
--
-- overview

-- This is the base MIB for the Bay Networks Remote Annex product line.
-- This module defines Bay Networks Remote Annex Enterprise MIB.

  XYLO-MIB-SMI DEFINITIONS ::= BEGIN

  IMPORTS
		enterprises
			FROM RFC1155-SMI
		DisplayString
			FROM RFC1213-MIB
		OBJECT-TYPE
			FROM RFC-1212;

  xylogics	OBJECT IDENTIFIER ::= { enterprises 15 } 

  prod		OBJECT IDENTIFIER ::= { xylogics 1 } 

  prodannex	OBJECT-TYPE
		SYNTAX DisplayString (SIZE (0..128))
		ACCESS read-only 
		STATUS mandatory
		DESCRIPTION
			"Product name."
		::= { prod 1 }

  mibversion    OBJECT-TYPE
	        SYNTAX DisplayString (SIZE (0..16))
		ACCESS read-only
		STATUS mandatory
		DESCRIPTION
			"The current version of this private MIB. 
			Currently, the returned value is the same as
			the software revision of the executing image."
		::= { prod 2 }

  prodoid       OBJECT IDENTIFIER ::= { prod 3 }
  
  unknown       OBJECT IDENTIFIER ::= { prodoid 1 }
  annexII       OBJECT IDENTIFIER ::= { prodoid 2 }
  annex3        OBJECT IDENTIFIER ::= { prodoid 3 }
  microanx      OBJECT IDENTIFIER ::= { prodoid 4 }
  microels      OBJECT IDENTIFIER ::= { prodoid 5 }
  csmim1        OBJECT IDENTIFIER ::= { prodoid 6 }
  ods           OBJECT IDENTIFIER ::= { prodoid 7 }
  bay5390	OBJECT IDENTIFIER ::= { prodoid 8 }
  csmim2        OBJECT IDENTIFIER ::= { prodoid 9 }
  annex2000     OBJECT IDENTIFIER ::= { prodoid 10 }
  microcs       OBJECT IDENTIFIER ::= { prodoid 11 }
  annex4000     OBJECT IDENTIFIER ::= { prodoid 12 }
  a3Com         OBJECT IDENTIFIER ::= { prodoid 13 }
  csmim-t1      OBJECT IDENTIFIER ::= { prodoid 14 }
  ra6100     	OBJECT IDENTIFIER ::= { prodoid 15 }
  ra6300     	OBJECT IDENTIFIER ::= { prodoid 16 }
  bay5391	OBJECT IDENTIFIER ::= { prodoid 17 }
  bay5393	OBJECT IDENTIFIER ::= { prodoid 18 }
  bay5399	OBJECT IDENTIFIER ::= { prodoid 19 }

  annex		OBJECT IDENTIFIER ::= { xylogics 2 }
 
--  Since we cannot release (or claim to support) any MIBs defined
--  in Internet-drafts or MIBs defined in RFCs as being attached to
--  the "experimental" node of the MIB-II, the following node is
--  defined so that these types of MIBs can be attached to our
--  private enterprise MIB.  That way, the interim MIB definitions
--  may be released as part of our private MIB.

  anxexperimental       OBJECT IDENTIFIER ::= { xylogics 3 }

-- Remote Access Concentrator related traps.

  racTraps		OBJECT IDENTIFIER ::= { xylogics 100 }



  hw		  OBJECT IDENTIFIER ::= { annex 1 }
-- Descr
-- 	Annex hardware group 
-- Module
--	xylo-anx.mib

  sw		  OBJECT IDENTIFIER ::= { annex 2 }
-- Descr
-- 	Annex software group 
-- Module
--	xylo-anx.mib

  ports		  OBJECT IDENTIFIER ::= { annex 3 }
-- Descr
-- 	Annex serial ports group. 
-- Module
--	xylo-ports.mib

  parallelport	  OBJECT IDENTIFIER ::= { annex 4 }
-- Descr
-- 	Annex parallel ports group 
-- Module
--	xylo-ports.mib

  annexconfig	  OBJECT IDENTIFIER ::= { annex 5 }
  anxigmpconfig	OBJECT IDENTIFIER ::= { annexconfig 105 }
-- Descr
-- 	Annex configuration group 
-- Module
--	xylo-anx.mib

  annexcmds	  OBJECT IDENTIFIER ::= { annex 6 }
-- Descr
-- 	Annex commands group 
-- Module
--	xylo-anx.mib

  annexlatstats   OBJECT IDENTIFIER ::= { annex 7 }
-- Descr
-- 	Annex LAT group 
-- Module
--	xylo-protocol.mib

  interfacerip    OBJECT IDENTIFIER ::= { annex 8 }
-- Descr
-- 	Annex RIP2 group 
-- Module
--	xylo-protocol.mib

  anxsyncports 	  OBJECT IDENTIFIER ::= { annex 9 }
-- Descr
-- 	Annex synchronous ports group 
-- Module
--	xylo-ports.mib

  anxTrapHostInfo OBJECT IDENTIFIER ::= { annex 10 }
-- Descr
-- 	Annex trap host group 
-- Module
--	xylo-trpobj.mib

  anxt1 	  OBJECT IDENTIFIER ::= { annex 11 }
-- Descr
-- 	Annex DS1/T1 group 
-- Module
--	xylo-wan.mib

  anxpri	  OBJECT IDENTIFIER ::= { annex 12 }
-- Descr
-- 	Annex PRI/ISDN group 
-- Module
--	xylo-wan.mib

  anxinterface	  OBJECT IDENTIFIER ::= { annex 13 }
-- Descr
--	This group will have proprietary MIB for interfaces
--	implemented on Annex product family.
-- Module
--	xylo-ports.mib

  anxtunnelport	  OBJECT IDENTIFIER ::= { annex 14 }
-- Descr
--	Annex tunnelport/UDAS group
-- Module
--	xylo-wan.mib

  anxgrestats	  OBJECT IDENTIFIER ::= { annex 15 }
-- Descr
--	Annex Generic Routing Encapsulation Stats
-- Module
--	xylo-anx.mib

  callmgmt	  OBJECT IDENTIFIER ::= { annex 16 }
-- Descr
--	Baynetworks proprietary extension for call management MIB.
-- Module
--	xylo-callmgmt.mib


  anxModem	  OBJECT IDENTIFIER ::= { annex 100 }
-- Descr
-- 	Annex modem group 
-- Module
--	xylo-ports.mib

  anxchascommon   OBJECT IDENTIFIER ::= { annex 101 }
-- Descr
-- 	Annex Chassis group 
-- Module
--	xylo-anx.mib

  anxchas	  OBJECT IDENTIFIER ::= { annex 102 }
-- Descr
-- 	Annex Chassis group 
-- Module
--	xylo-anx.mib

  radiusClient 	  OBJECT IDENTIFIER ::= { annex 103 }
  anxgsystats OBJECT IDENTIFIER ::= { annex 104 }  
  anxccpstats	  OBJECT IDENTIFIER ::= { annex 105 }
-- Descr
--      Annex Chassis group
-- Module
--      xylo-anx.mib

  radiusConfig    OBJECT IDENTIFIER ::= { radiusClient 1 }  
  radiusStats     OBJECT IDENTIFIER ::= { radiusClient 2 }
-- Descr 
--       radius CLient group
-- Module
--       xylo-anx.mib

-- Trap related MIB objects.
  racTrapObjects	OBJECT IDENTIFIER ::= { racTraps 1 }
-- Descr
-- 	RAC's trap related MIB objects.
-- Module
--	xylo-anx.mib


  wanTrapObj	OBJECT IDENTIFIER ::= { racTrapObjects 1 }
-- Descr
-- 	WAN trap related MIB objects.
-- Module
--	xylo-trpobj.mib

  modemTrapObj	OBJECT IDENTIFIER ::= { racTrapObjects 2 }
-- Descr
-- 	Modem trap related MIB objects.
-- Module
--	xylo-trpobj.mib

  callmgmtTrapObj	OBJECT IDENTIFIER ::= { racTrapObjects 3 }
-- Descr
-- 	Call management trap related MIB objects.
-- Module
--	xylo-trpobj.mib

  genericTrapObj	OBJECT IDENTIFIER ::= { racTrapObjects 4 }
-- Descr
-- 	generic trap related MIB objects.
-- Module
--	xylo-trpobj.mib


END
