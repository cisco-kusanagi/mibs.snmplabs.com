ROUTING-MIB 

  DEFINITIONS ::= BEGIN

  -- This file contains the definition of the routing mib for Coriolis Networks.

    IMPORTS
    IpAddress
        FROM RFC1155-SMI
    OBJECT-TYPE, MODULE-IDENTITY
        FROM SNMPv2-SMI
	routing
        FROM CORIOLIS-MIB
    ;

    routingMIB MODULE-IDENTITY
    LAST-UPDATED "0007270000Z"
    ORGANIZATION "Coriolis Networks"
    CONTACT-INFO
    "  Shubhra Garg
       Postal: 330 Codman Hill Road,
       Boxboro MA, 01719.

       Tel: +1 978 264 1904
       Fax: +1 978 264 1929

       E-mail: shubhra@coriolisnet.com"
       DESCRIPTION
       "The MIB module for coriolis proprietary routing variables"
     ::= { routing 1 }

     routeAdvPrefixTable OBJECT-TYPE
     SYNTAX SEQUENCE OF RouteAdvPrefixEntry
     MAX-ACCESS not-accessible
     STATUS current
     DESCRIPTION
     "The routing prefix table. For NEs(including the GNE) whose subnet
	  number is included in this table, the subnet route gets added to 
	  the  routing tables and propagated by routing protocols rather than
	  the host route"
     ::= { routing 2 }

     routeAdvPrefixEntry OBJECT-TYPE
     SYNTAX RouteAdvPrefixEntry
     MAX-ACCESS not-accessible
     STATUS current
     DESCRIPTION
     "Entry containing information about subnet numbers and the corresponding masks"
     INDEX { routeAdvSummAddr, routeAdvSummMask }
     ::= { routeAdvPrefixTable 1 }

     RouteAdvPrefixEntry ::= SEQUENCE {
       routeAdvSummAddr
          IpAddress,
       routeAdvSummMask
          IpAddress,
       routeAdvSummRowStatus
	      INTEGER,
       routeAdvSummRipAdminCost
          INTEGER,
       routeAdvSummOspfAdminCost
          INTEGER,
       routeAdvSummNumSuppressedRoutes
	      INTEGER
     }

     routeAdvSummAddr OBJECT-TYPE
     SYNTAX IpAddress
     MAX-ACCESS read-only
     STATUS current
     DESCRIPTION
     " The subnet number, used as an index in the table "
     ::= { routeAdvPrefixEntry 1 }

     routeAdvSummMask OBJECT-TYPE
     SYNTAX IpAddress
     MAX-ACCESS read-only
     STATUS current
     DESCRIPTION
     " The subnet mask, used as an index in the table "
     ::= { routeAdvPrefixEntry 2 }

     routeAdvSummRowStatus OBJECT-TYPE
     SYNTAX INTEGER {
	   active(1),
	   invalid(2)
     }
     MAX-ACCESS read-create
     STATUS current
     DESCRIPTION
     " The row status is used to add entries to the prefix table or delete those entries "
     ::= { routeAdvPrefixEntry 3 }

     routeAdvSummRipAdminCost OBJECT-TYPE
     SYNTAX INTEGER 
     MAX-ACCESS read-write
     STATUS current
     DESCRIPTION
     " This parameter is the RIP metric that is used when the entry is added to the RIP routing table  "
     ::= { routeAdvPrefixEntry 4 }

     routeAdvSummOspfAdminCost OBJECT-TYPE
     SYNTAX INTEGER 
     MAX-ACCESS read-write
     STATUS current
     DESCRIPTION
     " This parameter is the OSPF metric that is used when the entry is added to the RIP routing table  "
     ::= { routeAdvPrefixEntry 5 }

     routeAdvSummNumSuppressedRoutes OBJECT-TYPE
     SYNTAX INTEGER 
     MAX-ACCESS read-write
     STATUS current
     DESCRIPTION
     " This is the number of host routes that have been suppressed by this
	   prefix route if this prefix route has been added to the RIP routing 
	   table.  "
     ::= { routeAdvPrefixEntry 6 }

   END
