-- LLC-2 Interface Module MIB

CXLLCInterfaceModule-MIB DEFINITIONS ::= BEGIN


IMPORTS
OBJECT-TYPE     FROM RFC-1212
cxLlcim,Alias
       FROM CXProduct-SMI;


llcimConnectInterval OBJECT-TYPE
SYNTAX  INTEGER (10..900)
ACCESS  read-write
STATUS  mandatory
DESCRIPTION
"Determines the amount of time between 
LLC-2 XID or TEST retries.

Range of Values: 10 - 900 seconds

Default Value: 30 seconds

Configuration Changed: administrative"
DEFVAL {30 }
::= { cxLlcim 1 }

-- gap (9) for future global parameters



--  Service Access Point Configuration Table

--     The table defining all the parameters, status, control and statistics 
--     required to manipulate a LLC-2 Interface Module Service Access Point
--     (SAP).


llcimSapTable OBJECT-TYPE
SYNTAX  SEQUENCE OF LlcimSapEntry
ACCESS  not-accessible
STATUS  mandatory
DESCRIPTION
"A table containing configuration information about each LLC-2 Interface 
Module service access point."
::= { cxLlcim 10 }


llcimSapEntry OBJECT-TYPE
 SYNTAX  LlcimSapEntry
 ACCESS  not-accessible
 STATUS  mandatory
 DESCRIPTION
"Defines a row in the llcimSapTable. Each row contains the objects which 
define an LLC-2 service access point."
 INDEX { llcimSapNumber }
 ::= { llcimSapTable 1 }


LlcimSapEntry ::=
 SEQUENCE {
-- Parameters
    llcimSapNumber                        INTEGER,
    llcimSapRowStatus                     INTEGER,
    llcimSapAlias                         Alias,
    llcimSapCompanionAlias                Alias,
    llcimSapType                          INTEGER,
    llcimSapConnectMethod                 INTEGER,
-- Status
    llcimSapState                         INTEGER
    }


llcimSapNumber OBJECT-TYPE
SYNTAX  INTEGER (0..255)
 ACCESS  read-only
 STATUS  mandatory
 DESCRIPTION
"Identifies this SAP (service access point) with a numerical value. Values 
for each SAP must be unique. A value of '0' is automatically allocated to 
the first LLCIM upper SAP. This upper SAP row always exists and cannot be 
deleted."
 ::= { llcimSapEntry 1 }


llcimSapRowStatus OBJECT-TYPE
 SYNTAX  INTEGER {
          invalid         (1),
          valid           (2)
          }
 ACCESS  read-write
 STATUS  mandatory
 DESCRIPTION
"Determines the status of the objects in a table row.

Options:
invalid (1): Row is flagged, after next reset the values will be disabled 
and the row is deleted from the table

valid (2): Values are enabled

Default Value: none

Configuration Changed: administrative"
 ::= { llcimSapEntry 2 }


llcimSapAlias OBJECT-TYPE
 SYNTAX  Alias
 ACCESS  read-write
 STATUS  mandatory
 DESCRIPTION
"Identifies this service access point by a textual name. Names must be 
unique across all service access points at all layers. 

Range of Values: 1 -16 alphanumeric characters (first character must be a 
letter)

Default Value: none

Configuration Changed: administrative"
 ::= { llcimSapEntry 3 }


llcimSapCompanionAlias OBJECT-TYPE
 SYNTAX  Alias
 ACCESS  read-write
 STATUS  mandatory
 DESCRIPTION
"Determines the remote SAP this SAP communicates with. This object 
contains the textual name of the remote SAP.

If this object is associated with a lower SAP, this object is set to the 
value of the corresponding LAPB/D MAC SAP Alias (lapbdMacSapAlias). The 
LAPB/D SAP must have the following objects defined as follows: 
labpdMacSapLapType set to 'lapb' lapbdMacSapLapBProtocolFlavor set to 
'v8022'

Range of Values: 1 -16 alphanumeric characters (first character must be a 
letter)

Default Value: none

Configuration Changed: administrative"
::= { llcimSapEntry 4 }


llcimSapType OBJECT-TYPE
 SYNTAX  INTEGER {
              lower           (1),
              upper           (2)
          }
 ACCESS  read-write
 STATUS  mandatory
 DESCRIPTION
"Determines if this SAP (service access point) is an upper or lower SAP.

Options:
lower (1): This is a lower SAP, used to communicate with a LAPB/D MAC SAP.

upper (2): This is an upper SAP, used to communicate with an upper layer 
service.

Default Value: lower (1)

Configuration Changed: administrative"
 DEFVAL { lower }
 ::= { llcimSapEntry 5 }
 
 
llcimSapConnectMethod OBJECT-TYPE
 SYNTAX  INTEGER {
          generateXid  (1),
          waitForXid   (2),
          immediate	   (3)
        }
 ACCESS  read-write
 STATUS  mandatory
 DESCRIPTION
"Determines if the NULL XID exchange used to establish an LLC link is 
initiated by this station or by the remote station.

Options:
generateXid (1): This station initiates the NULL XID exchange.

waitForXid (2): This station waits for the other side to initiate the NULL 
XID exchange.

Default Value: generateXid (1)

Configuration Changed: administrative and operative"
 DEFVAL { generateXid }
 ::= { llcimSapEntry 6 }


llcimSapState OBJECT-TYPE
 SYNTAX  INTEGER {
          offLine           (1),
          unbound           (2),
          notConnected      (3),
          testExchange      (4),
          xidIssued         (5),
          waitXid           (6),
          connected         (7),
          setMode           (8),
          waitSetMode       (9),
          setModeReceived   (10),
          data              (11),
          inLinkDisconnect  (12),
          outLinkDisconnect (13),
          outLineDisconnect (14)
       }
 ACCESS  read-only
 STATUS  mandatory
 DESCRIPTION
"Indicates the state of this service access point.

Options:
offLine (1): Indicates that the SAP is not configured.

unbound (2): Indicates that this SAP is not bound to its companion SAP.

notConnected (3): Indicates that the link is idle.

testExchange (4): Indicates that the TEST exchange is ongoing.

xidIssued (5): Indicates that this SAP has sent a NULL XID.

waitXid (6): Indicates that this SAP is waiting for the remote to send a 
NULL XID.

connected (7): Indicates that the link is established (TEST and XID 
exchanges has been successfully completed).

setMode (8): Indicates that this SAP has sent a Set Mode command to the 
remote.

waitSetMode (9): Indicates that this SAP is waiting for a Set Mode command 
from the remote.

setModeReceived (10): Indicates that this SAP has received a Set Mode 
command from the remote.

data (11): Indicates that data exchange mode has been reached.

inLinkDisconnect (12): Indicates that the link has been disconnected (a 
DISC was received from the remote).

outLinkDisconnect (13): Indicates that the link has been disconnected (a 
DISC was sent to the remote).

outLineDisconnect (14) Indicates that the connection to the remote is 
being terminated."
 ::= { llcimSapEntry 7 }

END
