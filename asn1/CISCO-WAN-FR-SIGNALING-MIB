-- *****************************************************************
-- ciscoWanFrSignalingMIB
--
-- September 2002, Subra.Hegde
--
-- Copyright (c) 2002 by cisco Systems, Inc.
-- All rights reserved.
-- *****************************************************************

CISCO-WAN-FR-SIGNALING-MIB DEFINITIONS ::= BEGIN
IMPORTS
    MODULE-IDENTITY,
    OBJECT-TYPE,
    Integer32,
    Counter32
                               FROM SNMPv2-SMI
    MODULE-COMPLIANCE,
    OBJECT-GROUP                FROM SNMPv2-CONF
    frPortCnfSig,
    frPortCntSig	       FROM BASIS-MIB
    ciscoWan                   FROM CISCOWAN-SMI;

ciscoWanFrSignalingMIB MODULE-IDENTITY
    LAST-UPDATED    "200303240000Z"
    ORGANIZATION    "Cisco Systems, Inc."
    CONTACT-INFO
            "       Cisco Systems
                        Customer Service

                Postal: 170 W Tasman Drive
                        San Jose, CA  95134
                        USA

                        Tel: +1 800 553-NETS

                E-mail: cs-wanatm@cisco.com"
    DESCRIPTION
        "The MIB module to configure LMI and CLLM
        on a frame relay ports. This mib module also
        contains objects to represent LMI and CLLM
        statistics information. The frame relay logical
        port is referred to as 'frame relay port' in this
        mib. The 'logical port' refers to frame relay
        port.

        LMI  : Local Management Interface.
            The Frame Relay LMI is a set of enhancements to
            the basic Frame Relay Specification. The Key
            Frame Relay LMI extensions include global addressing,
            virtual circuit status messages and multicasting.
            The LMI includes support for a keepalive mechanism,
            which verifies that data is flowing, and a status
            mechanism, which provides an on-going status report
            on the DLCIs known to the switch.

            The LMI Global Addressing extension gives Frame Relay
            DLCI values global rather than local significance.
            The global addressing extension adds functionality
            and manageability to Frame Relay internetworks.

            The LMI virtual circuit messages provide communication
            and synchronization between Frame Relay DTE and
            DCE devices. These messages are periodically report
            on the status of PVCs, which prevents data from being
            sent into black holes(that, over PVCs that no longer
            exist).
            LMI UNI signaling enables subscribers to find out
            about the PVC status of the network, thus inhibiting
            the use of an unavailable PVC and supplies procedures
            for detecting and modifying following events:
                * deletion of a PVC
                * addition of a PVC
                * availability of a configured PVC
                * unavailability of a configured PVC
                * error due to LMI message sequencing

        ELMI : Enhanced LMI
               ELMI allows the router to learn QoS(Quality of
               Service) parameters from the switch and use them
               for traffic shaping, configuration or management
               purposes. 

        CLLM : Consolidated Link Layer Management.
            The CLLM is an out-of-band mechanism to transport
            congestion-related information to the far end.
            The CLLM enables the Frame Relay network to more
            efficiently relay congestion notifications to the DTE(router).
            The CLLM congestion notification is sent on the reserved
            data link connection identifier(DLCI) 1023.

        Frame Forwarding Port: Frame Forwarding Ports are identified
        by portType = frame-forward(3). The signaling parameters
        are not applicable to these ports."

    -- REFERENCE
    --   "LMI:   ANSI T1.617 Annex D, ITU Q.933 Annex A."
    --   "CLLM:  ANSI T1.618/ITU Q.922 Annex A."
    REVISION    "200303240000Z"
    DESCRIPTION
	"Added portLmiSigConfMethod mib object to support LMI 
	 Autosense feature"
    REVISION    "200209040000Z"
    DESCRIPTION
        "Initial version of the MIB.

        The content of this MIB was originally available
        in CISCO-WAN-AXIPOP-MIB defined using SMIv1.
        The applicable objects from CISCO-WAN-AXIPOP-MIB
        are defined using SMIv2 in this MIB. Also the
        descriptions of some of the objects have been 
        modified."
    ::= { ciscoWan 46 }


frPortCnfSigLMIGrp   	OBJECT IDENTIFIER ::= { frPortCnfSig 1 }


-- ------------------------------------------------------------------------
--
-- frPortCnfSigLMI group
-- Port configurable signalling parameters  
--
-- ------------------------------------------------------------------------


frPortCnfSigLMIGrpTable	OBJECT-TYPE
    SYNTAX	SEQUENCE OF FrPortCnfSigLMIGrpEntry
    MAX-ACCESS	not-accessible
    STATUS	current
    DESCRIPTION
        "This table is for configuration of
        singaling(LMI) on  frame relay ports."
    ::= { frPortCnfSigLMIGrp 1 }

frPortCnfSigLMIGrpEntry	OBJECT-TYPE
    SYNTAX	FrPortCnfSigLMIGrpEntry
    MAX-ACCESS	not-accessible
    STATUS	current
    DESCRIPTION
        "An entry for each frame relay port. The entries
        are applicable only for following ports:
           portType = frame-relay(1),
           portType = frFUNI(2).
        This table is not applicable for Frame Forwarding
        ports,i.e portType = frame-forward(3)."
    INDEX	{ lmiCnfPortNum }
    ::= { frPortCnfSigLMIGrpTable 1 }

FrPortCnfSigLMIGrpEntry ::=
    SEQUENCE {
        lmiCnfPortNum 	              Integer32,
        signallingProtocolType        INTEGER, 
        asynchronousUpdates           INTEGER, 
        t391LinkIntegrityTimer        Integer32,
        t392PollingVerificationTimer  Integer32,
        n391FullStatusPollingCounter  Integer32,
        n392ErrorThreshold            Integer32,
        n393MonitoredEventCount       Integer32,
        enhancedLmi                   INTEGER,
        portFRF1Dot2Support           INTEGER,
        portLmiSigConfMethod          INTEGER
    }

lmiCnfPortNum OBJECT-TYPE
    SYNTAX	Integer32(1..2147483647)
    MAX-ACCESS	read-only
    STATUS	current
    DESCRIPTION		  
        "The value of this object identifies the frame
        relay port. The value of this object must be 
        same as the value of 'portNum' from frPortCnfPortGrpTable.

        The Frame Forwarding Port value is not valid for 
        this object." 
    REFERENCE
        "portNum object in CISCO-WAN-FR-PORT-MIB.my"
    ::= { frPortCnfSigLMIGrpEntry 1}

signallingProtocolType  OBJECT-TYPE
    SYNTAX     INTEGER {
                  other(1),
                  noSignalling(2),
                  strataLMI(3),
                  annexAUNI(4),
                  annexDUNI(5),
                  annexANNI(6),
                  annexDNNI(7)
              }
    MAX-ACCESS read-write
    STATUS     current
    DESCRIPTION
        "The value of this object is used for configuring
        the LMI signaling protocol type.
                1 - other.  Not a valid value for SET request.
                2 - noSignalling
                3 - strataLMI
                4 - annexAUNI
                5 - annexDUNI
                6 - annexANNI
                7 - annexDNNI

         The ports with portType = frame-forward(3)
         can be set to noSingalling(2) only.

         The value strataLMI(3) is not supported for 
         portHeaderLen =  fourOctets(2)."
    REFERENCE
        "ANSI T1.617 Annex D, ITU Q.933 Annex A."
    DEFVAL { noSignalling }
    ::= { frPortCnfSigLMIGrpEntry 2}

asynchronousUpdates OBJECT-TYPE
    SYNTAX	INTEGER {
                    disable(1),
                    enable(2),
                    fsenable(3),
                    updfsenable(4)
                }
    MAX-ACCESS	read-write
    STATUS	current
    DESCRIPTION		  
        "This object is used for configuring asynchronous
         updates.
        
         The possible values are :

           disable(1)     : disable Asynchronous Status Updates 
                            & Unsolicited Full Status
           enable(2)      :  enable Asynchronous Status Updates
           fsenable(3)    :  enable Unsolicited Full Status
           updfsenable(4) :  enable Asynchronous Status Updates &
                             Unsolicited Full Status."
    DEFVAL { disable }
    ::= { frPortCnfSigLMIGrpEntry 3}

t391LinkIntegrityTimer OBJECT-TYPE
    SYNTAX     Integer32 (5..30)
    UNITS      "seconds"
    MAX-ACCESS read-write
    STATUS     current
    DESCRIPTION		  
        "The value of this object identifies the desired
        User-side T391 link integrity verification polling
        timer value for this UNI/NNI logical port."
    DEFVAL { 10 }
    ::= { frPortCnfSigLMIGrpEntry 4}
		      	   
t392PollingVerificationTimer OBJECT-TYPE
    SYNTAX      Integer32 (5..30)
    UNITS       "seconds"
    MAX-ACCESS	read-write
    STATUS	current
    DESCRIPTION		  
        "The value of this object identifies the desired
        Network-side T392 polling verification timer value
        (nT2 for LMI) for this UNI/NNI logical port.
        This is the length of time the network should 
        wait between Status Inquiry Messages."
    DEFVAL { 15 }
    ::= { frPortCnfSigLMIGrpEntry 5}

n391FullStatusPollingCounter	OBJECT-TYPE
    SYNTAX     Integer32 (1..255)
    UNITS      "Polls"
    MAX-ACCESS read-write
    STATUS     current
    DESCRIPTION
        "The value of this object identifies the
        User-Side 391 full status polling cycle value
        for this UNI/NNI logical port."
    REFERENCE
        "Q.933 Annex A [22],
        T1.617 Annex D [17]"
    DEFVAL { 6 }
    ::= { frPortCnfSigLMIGrpEntry 6}

n392ErrorThreshold	OBJECT-TYPE
    SYNTAX     Integer32 (1..10)
    MAX-ACCESS read-write
    STATUS     current
    DESCRIPTION
        "The value of this object identifies the desired
        User-side/Network-side N392 error threshold value for this
        UNI/NNI logical port."
    REFERENCE
        "Q.933 Annex A [22],
        T1.617 Annex D [17]"
    DEFVAL { 3 }
    ::= { frPortCnfSigLMIGrpEntry 7}

n393MonitoredEventCount	OBJECT-TYPE
    SYNTAX     Integer32 (1..10)
    UNITS      "Events"
    MAX-ACCESS read-write
    STATUS     current
    DESCRIPTION
        "The value of this object identifies the desired
        User-side/Network-side N393 monitored events count 
        value for this UNI/NNI logical port."
    REFERENCE
        "Q.933 Annex A [22],
        T1.617 Annex D [17]"
    DEFVAL { 4 }
    ::= { frPortCnfSigLMIGrpEntry 8}

enhancedLmi OBJECT-TYPE
SYNTAX          INTEGER {
                    disable(1),
                    enable(2)
                }
    MAX-ACCESS  read-write
    STATUS	current
    DESCRIPTION		  
        "This object enables/disables the Enhanced LMI
        (ELMI) on the frame relay port."

    DEFVAL { disable }
    ::= { frPortCnfSigLMIGrpEntry 9}

portFRF1Dot2Support OBJECT-TYPE
    SYNTAX    INTEGER {
                  enable(1),
                  disable(2)
              }
    MAX-ACCESS read-write
    STATUS     current
    DESCRIPTION
        "This object enables/disables the FRF 1.2 feature.
         This object is added for FRSM12.

	 This object is not applicable to MGX Release 1.x	
        "
    REFERENCE 
        "FRF 1.2"
    DEFVAL { disable }
    ::= { frPortCnfSigLMIGrpEntry 10}

portLmiSigConfMethod OBJECT-TYPE
    SYNTAX  INTEGER {
                manual   (1),
                autosense(2)
            }
    MAX-ACCESS  read-write
    STATUS      current
    DESCRIPTION
        " 
         This object enables/disables the port LMI signalling autosense.

         Setting this object to autosense(2) enables the port to
         autodetect and configure port LMI signalling type.

         signallingProtocolType mib should be set to noSignalling 
         while this object is being set to autosense(2). If 
         signallingProtocolType mib is set to a value other than 
         noSignalling while this object is being set to autosense(2), 
         the set request fails.

         When this object is set to manual(1), user needs to manually
         configure the port LMI signalling type using the
         signallingProtocolType mib. signallingProtocolType can be 
         configured to any valid value including noSignalling when 
         this object is set to manual(1).
        "
    DEFVAL { manual }
    ::= { frPortCnfSigLMIGrpEntry 11}


frPortCntSigLMIGrp   	OBJECT IDENTIFIER ::= { frPortCntSig 1 }


-- ------------------------------------------------------------------------
--
-- frPortCntSigLMI group
-- Port counter signalling values
--
-- ------------------------------------------------------------------------


frPortCntSigLMIGrpTable	OBJECT-TYPE
    SYNTAX	SEQUENCE OF FrPortCntSigLMIGrpEntry
    MAX-ACCESS	not-accessible
    STATUS	current
    DESCRIPTION
        "This table contains the LMI statistics 
        of frame relay ports."
    ::= { frPortCntSigLMIGrp 1 }

frPortCntSigLMIGrpEntry	OBJECT-TYPE
    SYNTAX	FrPortCntSigLMIGrpEntry
    MAX-ACCESS	not-accessible
    STATUS	current
    DESCRIPTION
        "An entry for each frame relay port.
        Each entry identifies the LMI statistics supported
        on a frame relay port.
        The entries are applicable only for following ports:
           portType = frame-relay(1),
           portType = frFUNI(2).
        This table is not applicable for Frame Forwarding
        ports,i.e portType = frame-forward(3)."
    INDEX	{ lmiSigPortNum }
    ::= { frPortCntSigLMIGrpTable 1 }

FrPortCntSigLMIGrpEntry ::=
    SEQUENCE {
        lmiSigPortNum        Integer32,
        rcvStatusInquiry     Counter32, 
        rcvInvalidRequest    Counter32, 
        rcvUNISeqMismatch    Counter32, 
        xmtStatus	     Counter32, 
        xmtAsynchUpdate	     Counter32, 
        uniSignalingTimeout  Counter32, 
        xmtStatusInquiry     Counter32, 
        rcvStatus	     Counter32, 
        rcvAsynchUpdate	     Counter32, 
        rcvNNISeqMismatch    Counter32, 
        nniSignalingTimeout  Counter32
    }

lmiSigPortNum OBJECT-TYPE
    SYNTAX	Integer32(1..2147483647)
    MAX-ACCESS	read-only
    STATUS	current
    DESCRIPTION		  
        "The value of this object refers to
        the frame relay port. The value for
        this object must be same as the 'portNum'
        object defined in frPortCnfPortGrpTable.

        The frame forwarding port value is not valid
        for this object."
    REFERENCE
        "portNum object in CISCO-WAN-FR-PORT-MIB.my"
    ::= { frPortCntSigLMIGrpEntry 1}

rcvStatusInquiry OBJECT-TYPE
    SYNTAX	Counter32
    MAX-ACCESS	read-only
    STATUS	current
    DESCRIPTION		  
        "The number of Status Inquiry messages received."
::= { frPortCntSigLMIGrpEntry 2}

rcvInvalidRequest OBJECT-TYPE
    SYNTAX	Counter32
    MAX-ACCESS	read-only
    STATUS	current
    DESCRIPTION		  
        "The number of Invalid Request messages received."
    ::= { frPortCntSigLMIGrpEntry 3}

rcvUNISeqMismatch OBJECT-TYPE
    SYNTAX	Counter32
    MAX-ACCESS	read-only
    STATUS	current
    DESCRIPTION		  
        "The number of times UNI messages 
        with sequence number mismatches were received."
    ::= { frPortCntSigLMIGrpEntry 4}

xmtStatus OBJECT-TYPE
    SYNTAX	Counter32
    MAX-ACCESS	read-only
    STATUS	current
    DESCRIPTION		  
        "The number of times Status response messages 
        transmitted."
    ::= { frPortCntSigLMIGrpEntry 5}

xmtAsynchUpdate OBJECT-TYPE
    SYNTAX	Counter32
    MAX-ACCESS	read-only
    STATUS	current
    DESCRIPTION		  
        "The number of times Asynch Status messages 
        transmitted."
    ::= { frPortCntSigLMIGrpEntry 6}

uniSignalingTimeout OBJECT-TYPE
    SYNTAX	Counter32
    MAX-ACCESS	read-only
    STATUS	current
    DESCRIPTION		  
        "The number of times UNI Status requests 
        were not received."
    ::= { frPortCntSigLMIGrpEntry 7}

xmtStatusInquiry OBJECT-TYPE
    SYNTAX	Counter32
    MAX-ACCESS	read-only
    STATUS	current
    DESCRIPTION		  
        "The number of Status Inquiry messages transmitted."
    ::= { frPortCntSigLMIGrpEntry 8}

rcvStatus OBJECT-TYPE
    SYNTAX	Counter32
    MAX-ACCESS	read-only
    STATUS	current
    DESCRIPTION		  
        "The number of times Status response messages received."
    ::= { frPortCntSigLMIGrpEntry 9}

rcvAsynchUpdate OBJECT-TYPE
    SYNTAX	Counter32
    MAX-ACCESS	read-only
    STATUS	current
    DESCRIPTION		  
        "The number of times Asynch Status messages received
        "
    ::= { frPortCntSigLMIGrpEntry 10}

rcvNNISeqMismatch OBJECT-TYPE
    SYNTAX	Counter32
    MAX-ACCESS	read-only
    STATUS	current
    DESCRIPTION		  
        "The number of times NNI messages 
        with sequence number mismatches were received."
    ::= { frPortCntSigLMIGrpEntry 11}

nniSignalingTimeout OBJECT-TYPE
    SYNTAX	Counter32
    MAX-ACCESS	read-only
    STATUS	current
    DESCRIPTION		  
        "The number of times NNI Status requests were 
        not received."
    ::= { frPortCntSigLMIGrpEntry 12}


frPortCnfSigCLLMGrp   	OBJECT IDENTIFIER ::= { frPortCnfSig 2 }


-- ------------------------------------------------------------------------
--
-- frPortCnfSigCLLM group
-- Port configurable signalling parameters  
--
-- ------------------------------------------------------------------------


frPortCnfSigCLLMGrpTable	OBJECT-TYPE
    SYNTAX	SEQUENCE OF FrPortCnfSigCLLMGrpEntry
    MAX-ACCESS	not-accessible
    STATUS	current
    DESCRIPTION
        "This table is configuring the CLLM on
        frame relay ports. This table is not 
        applicable for Frame Forwarding ports."
    ::= { frPortCnfSigCLLMGrp 1 }

frPortCnfSigCLLMGrpEntry	OBJECT-TYPE
    SYNTAX	FrPortCnfSigCLLMGrpEntry
    MAX-ACCESS	not-accessible
    STATUS	current
    DESCRIPTION
        "An entry for each frame relay port. The entries
        are applicable only for following ports:
           portType = frame-relay(1),
           portType = frFUNI(2).
        This table is not applicable for Frame Forwarding
        ports,i.e portType = frame-forward(3)."
    INDEX	{ cllmCnfPortNum }
    ::= { frPortCnfSigCLLMGrpTable 1 }

FrPortCnfSigCLLMGrpEntry ::=
    SEQUENCE {
        cllmCnfPortNum        Integer32,
        cllmEnable            INTEGER, 
        xmtCLLMStatusTimer    Integer32, 
        rcvCLLMStatusTimer    INTEGER
    }

cllmCnfPortNum OBJECT-TYPE
    SYNTAX	Integer32(1..2147483647)
    MAX-ACCESS	read-only
    STATUS	current
    DESCRIPTION		  
        "The value of this object identifies the frame
        relay port. The value of this object must be
        same as the value of 'portNum' from frPortCnfPortGrpTable.

        The Frame Forwarding Port value is not valid for 
        this object." 
    REFERENCE
        "portNum object in CISCO-WAN-FR-PORT-MIB.my"
    ::= { frPortCnfSigCLLMGrpEntry 1}

cllmEnable OBJECT-TYPE
    SYNTAX	INTEGER {
                    disable(1),
                    enable(2)
                }
    MAX-ACCESS read-write
    STATUS     current
    DESCRIPTION
        "This object is used for enabling/disabling
        CLLM on frame relay port.
        When set to 'disabled', CLLM is disabled.
        When set to 'enabled', CLLM is enabled."
    DEFVAL { disable }
    ::= { frPortCnfSigCLLMGrpEntry 2}

xmtCLLMStatusTimer OBJECT-TYPE
    SYNTAX	Integer32 (40..5000)
    UNITS       "milli-seconds"
    MAX-ACCESS	read-write
    STATUS	current
    DESCRIPTION		  
        "Interval in milliseconds for CLLM to send CLLM updates." 
    DEFVAL { 40 }
    ::= { frPortCnfSigCLLMGrpEntry 3}
		      	   
rcvCLLMStatusTimer OBJECT-TYPE
    SYNTAX	INTEGER { rcvCLLMTimerValue (1000) }
    MAX-ACCESS	read-only
    STATUS	current
    DESCRIPTION		  
        "Timeout value for receiving CLLM updates."
    DEFVAL { rcvCLLMTimerValue }
    ::= { frPortCnfSigCLLMGrpEntry 4}



frPortCntSigCLLMGrp   	OBJECT IDENTIFIER ::= { frPortCntSig 2 }


-- ------------------------------------------------------------------------
--
-- frPortCntSigCLLM group
-- Port counter signalling values
--
-- ------------------------------------------------------------------------


frPortCntSigCLLMGrpTable	OBJECT-TYPE
    SYNTAX	SEQUENCE OF FrPortCntSigCLLMGrpEntry
    MAX-ACCESS	not-accessible
    STATUS	current
    DESCRIPTION
        "This table is for CLLM statistics for
        frame relay ports."
    ::= { frPortCntSigCLLMGrp 1 }

frPortCntSigCLLMGrpEntry	OBJECT-TYPE
    SYNTAX	FrPortCntSigCLLMGrpEntry
    MAX-ACCESS	not-accessible
    STATUS	current
    DESCRIPTION
        " An entry for frame relay port.
        The entries are applicable only for following ports:
           portType = frame-relay(1),
           portType = frFUNI(2).
        This table is not applicable for Frame Forwarding
        ports,i.e portType = frame-forward(3)."
    INDEX	{ cllmSigPortNum }
    ::= { frPortCntSigCLLMGrpTable 1 }

FrPortCntSigCLLMGrpEntry ::=
    SEQUENCE {
        cllmSigPortNum    Integer32,
        rcvFramesCLLM     Counter32, 
        rcvBytesCLLM      Counter32, 
        xmtFramesCLLM     Counter32, 
        xmtBytesCLLM      Counter32, 
        cllmFailures      Counter32
    }

cllmSigPortNum OBJECT-TYPE
    SYNTAX	Integer32(1..2147483647)
    MAX-ACCESS	read-only
    STATUS	current
    DESCRIPTION		  
        "The value of this object identifies the frame
        relay port. The value of this object must be
        same as the value of 'portNum' from frPortCnfPortGrpTable.

        The Frame Forwarding Port value is not valid for 
        this object." 
    REFERENCE
        "portNum object in CISCO-WAN-FR-PORT-MIB.my"
    ::= { frPortCntSigCLLMGrpEntry 1}

rcvFramesCLLM OBJECT-TYPE
    SYNTAX	Counter32
    UNITS       "frames"
    MAX-ACCESS	read-only
    STATUS	current
    DESCRIPTION		  
        "The number of CLLM frames received."
    ::= { frPortCntSigCLLMGrpEntry 2}

rcvBytesCLLM OBJECT-TYPE
    SYNTAX	Counter32
    UNITS       "bytes"
    MAX-ACCESS	read-only
    STATUS	current
    DESCRIPTION		  
        "The number of CLLM bytes received."
::= { frPortCntSigCLLMGrpEntry 3}

xmtFramesCLLM OBJECT-TYPE
    SYNTAX	Counter32
    UNITS       "frames"
    MAX-ACCESS	read-only
    STATUS	current
    DESCRIPTION		  
        "The number of CLLM frames transmitted."
    ::= { frPortCntSigCLLMGrpEntry 4}

xmtBytesCLLM OBJECT-TYPE
    SYNTAX	Counter32
    UNITS       "bytes"
    MAX-ACCESS	read-only
    STATUS	current
    DESCRIPTION		  
        "The number of CLLM bytes transmitted."
    ::= { frPortCntSigCLLMGrpEntry 5}

cllmFailures OBJECT-TYPE
    SYNTAX	Counter32
    MAX-ACCESS	read-only
    STATUS	current
    DESCRIPTION		  
        "The number of times an expected CLLM
        message was not received."
    ::= { frPortCntSigCLLMGrpEntry 6}


-- conformance information

cwfSignalingMIBConformance OBJECT IDENTIFIER ::= { ciscoWanFrSignalingMIB 2 }

cwfSignalingMIBGroups OBJECT IDENTIFIER ::= { cwfSignalingMIBConformance 1 }
cwfSignalingMIBCompliances OBJECT IDENTIFIER ::= { cwfSignalingMIBConformance 2 }


-- compliance statements

cwfSignalingMIBCompliance MODULE-COMPLIANCE
    STATUS  current
    DESCRIPTION
            "The compliance statement for SNMP entities which have
            network interfaces."
    MODULE  -- this module
        MANDATORY-GROUPS {
            ciscoWanFrLmiConfigGroup,
            ciscoWanFrLmiStatsGroup,
            ciscoWanFrCllmGroup,
            ciscoWanFrCllmStatsGroup
        }
    ::= { cwfSignalingMIBCompliances 1 }

ciscoWanFrLmiConfigGroup OBJECT-GROUP
    OBJECTS {
        lmiCnfPortNum,
	signallingProtocolType,
	asynchronousUpdates,
	t391LinkIntegrityTimer,
	t392PollingVerificationTimer,
	n391FullStatusPollingCounter,
	n392ErrorThreshold,
	n393MonitoredEventCount,
	enhancedLmi,
	portFRF1Dot2Support,
	portLmiSigConfMethod
    }
    STATUS current
    DESCRIPTION 
        "A collection of objects providing information
        applicable to Frame Relay Logical Ports
        (Frame Relay Ports)."
    ::= { cwfSignalingMIBGroups 1 }

ciscoWanFrLmiStatsGroup OBJECT-GROUP
    OBJECTS {
        lmiSigPortNum,
	rcvStatusInquiry,
	rcvInvalidRequest,
	rcvUNISeqMismatch,
	xmtStatus,
	xmtAsynchUpdate,
	uniSignalingTimeout,
	xmtStatusInquiry,
	rcvStatus,
	rcvAsynchUpdate,
	rcvNNISeqMismatch,
	nniSignalingTimeout
    }
    STATUS current
    DESCRIPTION 
        "A collection of objects providing information
        applicable to LMI statistics on Frame Relay Ports."
    ::= { cwfSignalingMIBGroups 2 }

ciscoWanFrCllmGroup OBJECT-GROUP
    OBJECTS {
	   	cllmCnfPortNum ,
		cllmEnable,
		xmtCLLMStatusTimer,
		rcvCLLMStatusTimer
    }
    STATUS current
    DESCRIPTION 
        "A collection of objects providing information
         on CLLM applicable to Frame Relay Ports."
    ::= { cwfSignalingMIBGroups 3 }


ciscoWanFrCllmStatsGroup OBJECT-GROUP
    OBJECTS {
        cllmSigPortNum,
        rcvFramesCLLM,
        rcvBytesCLLM,
        xmtFramesCLLM,
        xmtBytesCLLM,
        cllmFailures

    }
    STATUS current
    DESCRIPTION 
        "A collection of objects providing information
        applicable to CLLMI statistics on Frame Relay Ports."
    ::= { cwfSignalingMIBGroups 4 }


END
