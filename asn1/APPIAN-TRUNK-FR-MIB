--
--  Title:  Appian-FR-TRUNKS-MIB
--
--  Date:   11/13/99
--
--  Description:
--
--  This file contains frame relay trunk MIB definitions.
--
--

APPIAN-TRUNK-FR-MIB DEFINITIONS ::= BEGIN

    IMPORTS
        acTrunks                                            FROM APPIAN-SMI-MIB
        MODULE-IDENTITY, OBJECT-TYPE, IpAddress             FROM SNMPv2-SMI
        TruthValue                                          FROM SNMPv2-TC;

--
-- Frame Relay Trunks
--
acFrTrunk   MODULE-IDENTITY
    LAST-UPDATED    "9911100000Z"
    ORGANIZATION    "Appian Communications, Inc."
    CONTACT-INFO    "Douglas Theriault"
    DESCRIPTION
                    "Appian Communications FrameRelay trunking MIB."
    REVISION
                    "9911130000Z"
        DESCRIPTION     "Engineering draft version, not for release."
        ::= { acTrunks 2 }

acFrTrunkTable OBJECT-TYPE
    SYNTAX  SEQUENCE OF AcFrTrunkEntry
    MAX-ACCESS  not-accessible
    STATUS      current
    DESCRIPTION
    "Frame Relay trunk table. This table contains the frame relay specific
     objects of a trunk, if the trunk is a frame relay trunk. A row in this
         table comes to existence as a frame relay trunk is defined in the common
         trunk table and the row disappears as the row is removed from the common
         trunk table. In other words, one doesn't directly create and destroy
         rows in this table."

    ::= { acFrTrunk 1 }

acFrTrunkEntry OBJECT-TYPE
    SYNTAX      AcFrTrunkEntry
    MAX-ACCESS  not-accessible
    STATUS      current
    DESCRIPTION
    "A row within the frame-relay trunk table which the index to this table
    entry using a Trunk index."

    INDEX { acFrTrunkIndex }

    ::= { acFrTrunkTable 1 }

AcFrTrunkEntry ::=
        SEQUENCE {
            acFrTrunkIndex              INTEGER,
            acFrTrunkLmiProtocol        INTEGER,
            acFrTrunkLmiPollingMode     INTEGER,
            acFrTrunkT391               INTEGER,
            acFrTrunkT392               INTEGER,
            acFrTrunkN391               INTEGER,
            acFrTrunkN392               INTEGER,
            acFrTrunkN393               INTEGER,
            acFrTrunkShared             TruthValue
        }

acFrTrunkIndex  OBJECT-TYPE
    SYNTAX      INTEGER
    MAX-ACCESS  accessible-for-notify
    STATUS      current
    DESCRIPTION
    "The trunk number, a number that uniquely identifies a trunk in a ring.
        It is used as the index to this table."
    ::= { acFrTrunkEntry 1 }

acFrTrunkLmiProtocol OBJECT-TYPE
    SYNTAX  INTEGER {
                -- unknown         (0),
				-- noLmiConfigured (1),
                -- lmiRev1         (2),
                -- ansiT1617D      (3),
                -- ansiT1617B      (4),
                -- ituQ933A        (5),
				-- ansiT1617D1994  (6),
                itu             (5),
				ansi            (6),
				auto            (7)
            }
    MAX-ACCESS  read-write
    STATUS      current
    DESCRIPTION
    "The protocol mode of LMI running on this service instance.  Appians
    supports auto, Q933A(5) and ansi(3)."
    DEFVAL  { auto }
    ::= { acFrTrunkEntry 2 }

acFrTrunkLmiPollingMode  OBJECT-TYPE
    SYNTAX  INTEGER {
                polling(1),     -- polling mode only
                polled(2)       -- polled mode only
            }
    MAX-ACCESS  read-write
    STATUS      current
    DESCRIPTION
    "Defines whether this instance of the service will perform LMI polling,
    responds to LMI requests, or both."
    DEFVAL  { polled }
    ::= { acFrTrunkEntry 3 }

acFrTrunkT391   OBJECT-TYPE
    SYNTAX      INTEGER (5..30)
    MAX-ACCESS  read-write
    STATUS      current
    DESCRIPTION
    "The status enquiry polling interval in seconds.  Applicable to polling
    mode only.  Range is valid only from 5 to 30 seconds, default value is 10
    seconds."
    DEFVAL  { 10 }
    ::= { acFrTrunkEntry 4 }

acFrTrunkT392   OBJECT-TYPE
    SYNTAX      INTEGER (5..30)
    MAX-ACCESS  read-write
    STATUS      current
    DESCRIPTION
    "The polling verification timer in seconds.  Applicable to polled mode
    only.  Range valid from 5 to 30 seconds, default value is 15 seconds."
    DEFVAL { 15 }
    ::= { acFrTrunkEntry 5 }

acFrTrunkN391   OBJECT-TYPE
    SYNTAX      INTEGER (1..255)
    MAX-ACCESS  read-write
    STATUS      current
    DESCRIPTION
    "The number of polling intervals to issue full status enquiry measured in
    intervals.  Range valid from 1 to 255, default set to 6 intervals."
    DEFVAL { 6 }
    ::= { acFrTrunkEntry 6 }

acFrTrunkN392   OBJECT-TYPE
    SYNTAX      INTEGER (1..10)
    MAX-ACCESS  read-write
    STATUS      current
    DESCRIPTION
    "The number of errors to occur before declaring the trunk down.  Valid
    range is 1 to 10 LMI intervals with a default set to 3."
    DEFVAL { 3 }
    ::= { acFrTrunkEntry 7 }

acFrTrunkN393   OBJECT-TYPE
    SYNTAX      INTEGER (1..10)
    MAX-ACCESS  read-write
    STATUS      current
    DESCRIPTION
    "The number of monitored events."
    DEFVAL { 4 }
    ::= { acFrTrunkEntry 8 }

acFrTrunkShared   OBJECT-TYPE
    SYNTAX      TruthValue
    MAX-ACCESS  read-write
    STATUS      current
    DESCRIPTION
    "Is this trunk shared by multiple OSAPs?"
    DEFVAL { false }
    ::= { acFrTrunkEntry 9 }
END
