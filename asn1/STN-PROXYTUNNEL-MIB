-- *****************************************************************
--
-- stn-proxy-tun.mib:  
--      Spring Tide Networks Proxy Tunnel
--                          MIB File
--
--
--      Copyright (c) 2000 by Spring Tide Networks, Inc.
--                      ALL RIGHTS RESERVED       
--
-- *****************************************************************

-- MIB Object definitions for Spring Tide ProxyTunnel

STN-PROXYTUNNEL-MIB DEFINITIONS ::= BEGIN

    IMPORTS
        MODULE-IDENTITY,
        OBJECT-TYPE, 
        IpAddress,
		Counter64,
        Integer32
                FROM SNMPv2-SMI

        DisplayString
                FROM SNMPv2-TC

        MODULE-COMPLIANCE
                FROM SNMPv2-CONF

        InterfaceIndex
                FROM IF-MIB

        stnPMProxyTunnel
                FROM STN-POLICY-MIB

        stnNotification
                FROM SPRING-TIDE-NETWORKS-SMI;


    stnProxyTunnel MODULE-IDENTITY
        LAST-UPDATED    "0001160000Z"
        ORGANIZATION    "Spring Tide Networks"
        CONTACT-INFO
                "
                Spring Tide Networks, Inc.
                Customer Service

                Postal: 3 Clock Tower Place
                        Suite 200
                        Maynard, MA 01754 USA
                Tel:    +1 978 298 2000
                Email:  custserv@springtidenet.com
                "
        DESCRIPTION     "This MIB module describes managed objects of
                         Spring Tide Networks Proxy Tunnel."
        ::= { stnPMProxyTunnel 1 }


--
-- Top Level STN PROXYTUNNEL MIB Objects
--

    stnProxyTunnelObjects       OBJECT IDENTIFIER ::= {stnProxyTunnel 1}
    
--
-- STN PROXYTUNNEL Table
--   One entry for each PROXYTUNNEL defined in the system.
--
    stnProxyTunnelTable OBJECT-TYPE
        SYNTAX          SEQUENCE OF StnProxyTunnelEntry
        MAX-ACCESS      not-accessible
        STATUS          current
        DESCRIPTION     "A list of Proxy Tunnel entries."
        ::= { stnProxyTunnelObjects 1 }
 
    stnProxyTunnelEntry OBJECT-TYPE
        SYNTAX          StnProxyTunnelEntry
        MAX-ACCESS      not-accessible
        STATUS          current
        DESCRIPTION     "Entry contains information about a particular Proxy Tunnel."
        INDEX           { stnProxyTunnelSerialNumber,
                          stnProxyTunnelRouterInstance }
        ::= { stnProxyTunnelTable 1 }
 
    StnProxyTunnelEntry ::= SEQUENCE {
        stnProxyTunnelSerialNumber                Integer32,
        stnProxyTunnelRouterInstance              Integer32,
        stnProxyTunnelConnIdleTimeOut             Integer32,
        stnProxyTunnelPolicyInstance              Integer32,
        stnProxyTunnelPolicyName                  DisplayString,
        stnProxyTunnelEncapsType                  INTEGER,
        stnProxyTunnelState                       INTEGER,
        stnProxyTunnelL3IfaceTx                   InterfaceIndex,
        stnProxyTunnelLocalTunnelAddr             IpAddress,
        stnProxyTunnelRemoteTunnelAddr            IpAddress,
        stnProxyTunnelInESPSPIs                   OCTET STRING (SIZE(0..128)),
        stnProxyTunnelOutESPSPIs                  OCTET STRING (SIZE(0..128)),
        stnProxyTunnelInAHSPIs                    OCTET STRING (SIZE(0..128)),
        stnProxyTunnelOutAHSPIs                   OCTET STRING (SIZE(0..128)),
        stnProxyTunnelEncapsIndex                 Integer32,
        stnProxyTunnelInPkts                      Counter64,
        stnProxyTunnelInErrPkts                   Counter64,
        stnProxyTunnelOutPkts                     Counter64,
        stnProxyTunnelOutErrPkts                  Counter64
    }

    stnProxyTunnelSerialNumber OBJECT-TYPE
        SYNTAX          Integer32
        MAX-ACCESS      read-only
        STATUS          current
        DESCRIPTION     "The  serial number of the Proxy Tunnel Interface."
        ::= { stnProxyTunnelEntry 1 }

    stnProxyTunnelRouterInstance OBJECT-TYPE
        SYNTAX          Integer32
        MAX-ACCESS      read-only
        STATUS          current
        DESCRIPTION     "The  instance of the router corresponding to this 
                        proxy tunnel."
        ::= { stnProxyTunnelEntry 2 }

    stnProxyTunnelConnIdleTimeOut OBJECT-TYPE
        SYNTAX          Integer32
        MAX-ACCESS      read-only
        STATUS          current
        DESCRIPTION     "The  timeout in seconds that the tunnel will 
                        stay connected even if no activity takes place."
        ::= { stnProxyTunnelEntry 3 }

    stnProxyTunnelPolicyInstance OBJECT-TYPE
        SYNTAX          Integer32
        MAX-ACCESS      read-only
        STATUS          current
        DESCRIPTION     "The  instance of the policy from which the proxy 
                        tunnel was created."
        ::= { stnProxyTunnelEntry 4 }

    stnProxyTunnelPolicyName OBJECT-TYPE
        SYNTAX          DisplayString
        MAX-ACCESS      read-only
        STATUS          current
        DESCRIPTION     "The  name of the policy associated with this proxy 
                        tunnel interface."
        ::= { stnProxyTunnelEntry 5 }

    stnProxyTunnelEncapsType OBJECT-TYPE
        SYNTAX          INTEGER {
                            stnProxyTunEncapsIpIp(1),
                            stnProxyTunEncapsIpGre(2),
                            stnProxyTunEncapsIpsec(3)
                        }
        MAX-ACCESS      read-only
        STATUS          current
        DESCRIPTION     "The type of encapsulation used on the proxy tunnel.
                        A value of stnProxyTunEncapsIpIp indicates an IP-IP
                        encapsulation on the tunnel. A value of 
                        stnProxyTunEncapsIpGre indicates an IP/GRE
                        encapsulation and a value of stnProxyTunEncapsIpsec 
                        indicates IPSEC encapsulation on the tunnel."
        ::= { stnProxyTunnelEntry 6 }

    stnProxyTunnelState OBJECT-TYPE
        SYNTAX          INTEGER {
                          up(1),
                          down(2)
                        }
        MAX-ACCESS      read-only
        STATUS          current
        DESCRIPTION     "The  state of the proxy tunnel. A value of up 
                        indicates that the proxy tunnel is ready to send 
                        and receive data."
        ::= { stnProxyTunnelEntry 7 }

    stnProxyTunnelL3IfaceTx OBJECT-TYPE
        SYNTAX          InterfaceIndex
        MAX-ACCESS      read-only
        STATUS          current
        DESCRIPTION     "Interface index of the L3 interface over which the 
                        proxy tunnel is established. The interface 
                        corresponding to this index is used by the proxy i
                        tunnel to send out packets."
        ::= { stnProxyTunnelEntry 8 }

    stnProxyTunnelLocalTunnelAddr OBJECT-TYPE
        SYNTAX          IpAddress
        MAX-ACCESS      read-only
        STATUS          current
        DESCRIPTION     "The IP address of the local tunnel end-point."
        ::= { stnProxyTunnelEntry 9 }

    stnProxyTunnelRemoteTunnelAddr OBJECT-TYPE
        SYNTAX          IpAddress
        MAX-ACCESS      read-only
        STATUS          current
        DESCRIPTION     "The IP address of the remote tunnel end-point."
        ::= { stnProxyTunnelEntry 10 }

    stnProxyTunnelInESPSPIs OBJECT-TYPE
        SYNTAX          OCTET STRING (SIZE(0..128))
        MAX-ACCESS      read-only
        STATUS          current
        DESCRIPTION     "Packet array of Security Protocol Indices 
                        corresponding to incoming ESP security assocations 
                        used to encapsulate traffic on the proxy tunnel 
                        when the encapsulation type is set to IPSEC."
        ::= { stnProxyTunnelEntry 11 }

    stnProxyTunnelOutESPSPIs OBJECT-TYPE
        SYNTAX          OCTET STRING (SIZE(0..128))
        MAX-ACCESS      read-only
        STATUS          current
        DESCRIPTION     "Packet array of Security Protocol Indices 
                        corresponding to outgoing ESP security assocations 
                        used to encapsulate traffic on the proxy tunnel 
                        when the encapsulation type is set to IPSEC."
        ::= { stnProxyTunnelEntry 12 }

    stnProxyTunnelInAHSPIs OBJECT-TYPE
        SYNTAX          OCTET STRING (SIZE(0..128))
        MAX-ACCESS      read-only
        STATUS          current
        DESCRIPTION     "Packet array of Security Protocol Indices 
                        corresponding to incoming AH security assocations 
                        used to encapsulate traffic on the proxy tunnel 
                        when the encapsulation type is set to IPSEC."
        ::= { stnProxyTunnelEntry 13 }

    stnProxyTunnelOutAHSPIs OBJECT-TYPE
        SYNTAX          OCTET STRING (SIZE(0..128))
        MAX-ACCESS      read-only
        STATUS          current
        DESCRIPTION     "Packet array of Security Protocol Indices 
                        corresponding to outgoing AH security assocations 
                        used to encapsulate traffic on the proxy tunnel 
                        when the encapsulation type is set to IPSEC."
        ::= { stnProxyTunnelEntry 14 }

    stnProxyTunnelEncapsIndex OBJECT-TYPE
        SYNTAX          Integer32
        MAX-ACCESS      read-only
        STATUS          current
        DESCRIPTION     "Index of the Encapsulation entry in the 
                        stnPmEncapsTable used to encapsulate traffic on the 
                        proxy tunnel when the encapsulation type is set 
                        IP-IP or IP-GRE."
        ::= { stnProxyTunnelEntry 15 }

    stnProxyTunnelInPkts OBJECT-TYPE
        SYNTAX          Counter64
        MAX-ACCESS      read-only
        STATUS          current
        DESCRIPTION     "The total number of packets received across the 
                        proxy tunnel."
        ::= { stnProxyTunnelEntry 16 }

    stnProxyTunnelInErrPkts OBJECT-TYPE
        SYNTAX          Counter64
        MAX-ACCESS      read-only
        STATUS          current
        DESCRIPTION     "The number of packets received across the proxy 
                        tunnel that were determined to be erroneous."
        ::= { stnProxyTunnelEntry 17 }

    stnProxyTunnelOutPkts OBJECT-TYPE
        SYNTAX          Counter64
        MAX-ACCESS      read-only
        STATUS          current
        DESCRIPTION     "The total number of packets sent out the proxy tunnel."
        ::= { stnProxyTunnelEntry 18 }

    stnProxyTunnelOutErrPkts OBJECT-TYPE
        SYNTAX          Counter64
        MAX-ACCESS      read-only
        STATUS          current
        DESCRIPTION     "The number of packets determined to be in error and 
                        discarded before sending over the tunnel."
        ::= { stnProxyTunnelEntry 19 }
END
