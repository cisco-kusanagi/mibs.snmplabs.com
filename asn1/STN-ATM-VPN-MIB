-- *****************************************************************
--
-- stn-atm-vpn.mib:  
--      Spring Tide Networks ATM Virtual Private Network 
--			(ATM-VPN-TRUNK) MIB File
--
--
--      Copyright (c) 2000 by Spring Tide Networks, Inc.
--                      ALL RIGHTS RESERVED       
--
-- *****************************************************************

-- MIB Object definitions for Spring Tide ATM VPN TRUNK

STN-ATM-VPN-MIB DEFINITIONS ::= BEGIN

    IMPORTS
        MODULE-IDENTITY,
        OBJECT-TYPE, 
        IpAddress,
        Integer32,
        Counter64
	        FROM SNMPv2-SMI

        DisplayString
                FROM SNMPv2-TC

        MODULE-COMPLIANCE
                FROM SNMPv2-CONF

        InterfaceIndex
                FROM IF-MIB

        stnRouterAtmVpn
                FROM STN-ROUTER-MIB

        stnNotification
                FROM SPRING-TIDE-NETWORKS-SMI;


    stnAtmVpn MODULE-IDENTITY
        LAST-UPDATED    "0008080000Z"
        ORGANIZATION    "Spring Tide Networks"
        CONTACT-INFO
                "
                Spring Tide Networks, Inc.
                Customer Service

                Postal: 3 Clock Tower Place
                        Suite 200
                        Maynard, MA 01754 USA
                Tel:    +1 978 298 2000
                Email:  custserv@springtidenet.com
                "
        DESCRIPTION     "This MIB module describes managed objects of
                         Spring Tide Networks ATM VPN Interfaces."
        ::= { stnRouterAtmVpn 1 }


    --
    -- Top Level STN ATM VPN MIB Objects
    --
    stnAtmVpnTrunkObjects       OBJECT IDENTIFIER ::= {stnAtmVpn 1}
    stnAtmVpnLinkObjects        OBJECT IDENTIFIER ::= {stnAtmVpn 2}
    
    --
    -- STN ATM VPN Trunk Table  
    --   One entry for each ATM VPN Trunk defined in the system.
    --
    stnAtmVpnTrunkTable OBJECT-TYPE
        SYNTAX		SEQUENCE OF StnAtmVpnTrunkEntry
        MAX-ACCESS	not-accessible
        STATUS		current
        DESCRIPTION	"A list of ATM VPN Trunk entries."
        ::= { stnAtmVpnTrunkObjects 1 }
 
    stnAtmVpnTrunkEntry OBJECT-TYPE
        SYNTAX          StnAtmVpnTrunkEntry
        MAX-ACCESS      not-accessible
        STATUS          current
        DESCRIPTION     "Entry contains information about a particular ATM VPN Trunk."
        INDEX           { stnAtmVpnTrunkIfIndex }
        ::= { stnAtmVpnTrunkTable 1 }
 
    StnAtmVpnTrunkEntry ::= SEQUENCE {
        stnAtmVpnTrunkIfIndex                     InterfaceIndex,
        stnAtmVpnTrunkViId                        Integer32,
        stnAtmVpnTrunkName                        DisplayString,
        stnAtmVpnTrunkState                       INTEGER,              
        stnAtmVpnTrunkLowerIfIndex                InterfaceIndex,
	stnAtmVpnTrunkVpnPaths                    Integer32,
	stnAtmVpnTrunkInUnknownVpnId              Counter64,
	stnAtmVpnTrunkInVpnIdIfaceInvalid         Counter64,
	stnAtmVpnTrunkOutUnknownVpnId             Counter64,
	stnAtmVpnTrunkOutVpnIdIfaceInvalid        Counter64
    }

    stnAtmVpnTrunkIfIndex OBJECT-TYPE
        SYNTAX          InterfaceIndex
        MAX-ACCESS      read-only
        STATUS          current
        DESCRIPTION     "The ifIndex of the ATM VPN Trunk Interface."
        ::= { stnAtmVpnTrunkEntry 1 }

    stnAtmVpnTrunkViId OBJECT-TYPE
        SYNTAX          Integer32
        MAX-ACCESS      read-only
        STATUS          current
        DESCRIPTION     "The instance of the configuration record 
                         corresponding to this ATM VPN Trunk."
        ::= { stnAtmVpnTrunkEntry 2 }

    stnAtmVpnTrunkName OBJECT-TYPE
        SYNTAX          DisplayString (SIZE (1..32))
        MAX-ACCESS      read-only
        STATUS          current
        DESCRIPTION     "The name configured for this ATM VPN Trunk."
        ::= { stnAtmVpnTrunkEntry 3 }

    stnAtmVpnTrunkState OBJECT-TYPE
        SYNTAX          INTEGER {
                          up(1),       -- ready to pass packets
                          down(2),
                          testing(3)   -- in some test mode
                        }
        MAX-ACCESS      read-only
        STATUS          current
        DESCRIPTION     "The current operational state of the ATM VPN Trunk."
        ::= { stnAtmVpnTrunkEntry 4 }

    stnAtmVpnTrunkLowerIfIndex OBJECT-TYPE
        SYNTAX          InterfaceIndex
        MAX-ACCESS      read-only
        STATUS          current
        DESCRIPTION     "The ifIndex of the Interface below the 
                         ATM VPN Trunk Interface."
        ::= { stnAtmVpnTrunkEntry 5 }

    stnAtmVpnTrunkVpnPaths OBJECT-TYPE
        SYNTAX          Integer32
        MAX-ACCESS      read-only
        STATUS          current
        DESCRIPTION     "The number of VPN Paths that this ATM VPN Trunk has 
                         in its forwarding table."
        ::= { stnAtmVpnTrunkEntry 6 }

    stnAtmVpnTrunkInUnknownVpnId OBJECT-TYPE
        SYNTAX          Counter64
        MAX-ACCESS      read-only
        STATUS          current
        DESCRIPTION     "The number packets received with a Vpn-Id that was 
		         not present it the ATM VPN Trunk's forwarding table."
        ::= { stnAtmVpnTrunkEntry 7 }

    stnAtmVpnTrunkInVpnIdIfaceInvalid OBJECT-TYPE
        SYNTAX          Counter64
        MAX-ACCESS      read-only
        STATUS          current
        DESCRIPTION     "The number packets received with a Vpn-Id that was 
		         known, but the entry in the FIB refered to an
                         invalid or non-existant interface. This can indicate
                         an invalid configuration."
        ::= { stnAtmVpnTrunkEntry 8 }

    stnAtmVpnTrunkOutUnknownVpnId OBJECT-TYPE
        SYNTAX          Counter64
        MAX-ACCESS      read-only
        STATUS          current
        DESCRIPTION     "The number packets passed to this trunk from 
                         another ATM VPN Trunk or Link with a Vpn-Id that was 
		         not present it the ATM VPN Trunk's forwarding table."
        ::= { stnAtmVpnTrunkEntry 9 }

    stnAtmVpnTrunkOutVpnIdIfaceInvalid OBJECT-TYPE
        SYNTAX          Counter64
        MAX-ACCESS      read-only
        STATUS          current
        DESCRIPTION     "The number packets passed to this trunk from 
                         another ATM VPN Trunk or Link when there was no
                         suitable interface below the ATM VPN Trunk."
        ::= { stnAtmVpnTrunkEntry 10 }


    --
    -- STN ATM VPN Trunk Path Table  
    --   One entry for each VPN Path learned or configured by a ATM VPN Trunk.
    --
    stnAtmVpnTrunkPathTable OBJECT-TYPE
        SYNTAX		SEQUENCE OF StnAtmVpnTrunkPathEntry
        MAX-ACCESS	not-accessible
        STATUS		current
        DESCRIPTION	"A list of the ATM VPN Paths known to a ATM VPN Trunk."
        ::= { stnAtmVpnTrunkObjects 2 }
 
    stnAtmVpnTrunkPathEntry OBJECT-TYPE
        SYNTAX          StnAtmVpnTrunkPathEntry
        MAX-ACCESS      not-accessible
        STATUS          current
        DESCRIPTION     "Entry contains information about a particular remote 
			 MAC learned on a VEI VcLink."
        INDEX           { stnAtmVpnTrunkPathTrunkIfIndex, 
	                  stnAtmVpnTrunkPathVpnOUI,
	                  stnAtmVpnTrunkPathVpnIndex,
	                  stnAtmVpnTrunkPathVpnSubIndex
			}
        ::= { stnAtmVpnTrunkPathTable 1 }
 
    StnAtmVpnTrunkPathEntry ::= SEQUENCE {
	stnAtmVpnTrunkPathTrunkIfIndex   InterfaceIndex, 
	stnAtmVpnTrunkPathVpnOUI         Integer32,
	stnAtmVpnTrunkPathVpnIndex       Integer32,
	stnAtmVpnTrunkPathVpnSubIndex    Integer32,
        stnAtmVpnTrunkPathType           INTEGER,
        stnAtmVpnTrunkPathNextIfType     INTEGER,
        stnAtmVpnTrunkPathNextIfIndex    InterfaceIndex,
	stnAtmVpnTrunkPathInPackets      Counter64,
	stnAtmVpnTrunkPathInOctets       Counter64,
	stnAtmVpnTrunkPathOutPackets     Counter64,
	stnAtmVpnTrunkPathOutOctets      Counter64
    }

    stnAtmVpnTrunkPathTrunkIfIndex OBJECT-TYPE
        SYNTAX          InterfaceIndex
        MAX-ACCESS      read-only
        STATUS          current
        DESCRIPTION     "The IfIndex of the ATM VPN Trunk Interface which 
			 owns the VPN Path entry."
        ::= { stnAtmVpnTrunkPathEntry 1 }

    stnAtmVpnTrunkPathVpnOUI OBJECT-TYPE
        SYNTAX          Integer32
        MAX-ACCESS      read-only
        STATUS          current
        DESCRIPTION     "The VPN OUI for which packets this VPN Path pertains to."
        ::= { stnAtmVpnTrunkPathEntry 2 }

    stnAtmVpnTrunkPathVpnIndex OBJECT-TYPE
        SYNTAX          Integer32
        MAX-ACCESS      read-only
        STATUS          current
        DESCRIPTION     "The VPN Index for which packets this VPN Path 
                         pertains to."
        ::= { stnAtmVpnTrunkPathEntry 3 }

    stnAtmVpnTrunkPathVpnSubIndex OBJECT-TYPE
        SYNTAX          Integer32
        MAX-ACCESS      read-only
        STATUS          current
        DESCRIPTION     "The VPN SubIndex for which packets this VPN Path 
                         pertains to."
        ::= { stnAtmVpnTrunkPathEntry 4 }

    stnAtmVpnTrunkPathType OBJECT-TYPE
        SYNTAX          INTEGER {
                            vpnLearnedPath(1),
                            vpnStaticPath(2)
                        }
        MAX-ACCESS      read-only
        STATUS          current
        DESCRIPTION     "Indicates the type of the VPN Path database entry. 
			 Learned indicates that the entry was dynamically 
			 learned from link/trunk configuration or other 
			 dynamic means. 
                         Static indicates that the entry was configured 
                         explicitly using a VirtualInterfaceInfo Entry."
        ::= { stnAtmVpnTrunkPathEntry 5 }

    stnAtmVpnTrunkPathNextIfType OBJECT-TYPE
        SYNTAX          INTEGER {
                            atmVpnLink(1),
                            atmVpnTrunk(2)
                        }
        MAX-ACCESS      read-only
        STATUS          current
        DESCRIPTION     "Indicates the type of ATM VPN Interface that this
                         path points to."
        ::= { stnAtmVpnTrunkPathEntry 6 }

    stnAtmVpnTrunkPathNextIfIndex OBJECT-TYPE
        SYNTAX          InterfaceIndex
        MAX-ACCESS      read-only
        STATUS          current
        DESCRIPTION     "The IfIndex of the destination ATM VPN Interface 
                         which this path entry refers to."
        ::= { stnAtmVpnTrunkPathEntry 7 }
	
    stnAtmVpnTrunkPathInPackets OBJECT-TYPE
        SYNTAX          Counter64
        MAX-ACCESS      read-only
        STATUS          current
        DESCRIPTION     "The number of packets that have been received by
                         the ATM VPN Trunk for this VPN path."
        ::= { stnAtmVpnTrunkPathEntry 8 }

    stnAtmVpnTrunkPathInOctets OBJECT-TYPE
        SYNTAX          Counter64
        MAX-ACCESS      read-only
        STATUS          current
        DESCRIPTION     "The number of octets that have been received by
                         the ATM VPN Trunk for this VPN path."
        ::= { stnAtmVpnTrunkPathEntry 9 }

    stnAtmVpnTrunkPathOutPackets OBJECT-TYPE
        SYNTAX          Counter64
        MAX-ACCESS      read-only
        STATUS          current
        DESCRIPTION     "The number of packets that have been transmitted 
                         by the ATM VPN Trunk for this VPN path."
        ::= { stnAtmVpnTrunkPathEntry 10 }

    stnAtmVpnTrunkPathOutOctets OBJECT-TYPE
        SYNTAX          Counter64
        MAX-ACCESS      read-only
        STATUS          current
        DESCRIPTION     "The number of octets that have been transmitted 
                         by the ATM VPN Trunk for this VPN path."
        ::= { stnAtmVpnTrunkPathEntry 11 }


    --
    -- STN ATM VPN Link Table  
    --   One entry for each ATM VPN Link defined in the system.
    --
    stnAtmVpnLinkTable OBJECT-TYPE
        SYNTAX		SEQUENCE OF StnAtmVpnLinkEntry
        MAX-ACCESS	not-accessible
        STATUS		current
        DESCRIPTION	"A list of ATM VPN Link entries."
        ::= { stnAtmVpnLinkObjects 1 }
 
    stnAtmVpnLinkEntry OBJECT-TYPE
        SYNTAX          StnAtmVpnLinkEntry
        MAX-ACCESS      not-accessible
        STATUS          current
        DESCRIPTION     "Entry contains information about a particular 
                         ATM VPN Link."
        INDEX           { stnAtmVpnLinkIfIndex }
        ::= { stnAtmVpnLinkTable 1 }
 
    StnAtmVpnLinkEntry ::= SEQUENCE {
	stnAtmVpnLinkIfIndex			 InterfaceIndex,
	stnAtmVpnLinkViId			 Integer32,
	stnAtmVpnLinkName			 DisplayString,
	stnAtmVpnLinkVpnOUI			 Integer32,
	stnAtmVpnLinkVpnIndex			 Integer32,
	stnAtmVpnLinkVpnSubIndex		 Integer32,
	stnAtmVpnLinkState			 INTEGER,
	stnAtmVpnLinkTrunkViId			 Integer32,
	stnAtmVpnLinkLowerIfIndex		 InterfaceIndex,
	stnAtmVpnLinkOutUnknownVpnId		 Counter64,
	stnAtmVpnLinkOutVpnIdIfaceInvalid	 Counter64,
	stnAtmVpnLinkInVpnIdIfaceInvalid         Counter64
    }

    stnAtmVpnLinkIfIndex OBJECT-TYPE
        SYNTAX          InterfaceIndex
        MAX-ACCESS      read-only
        STATUS          current
        DESCRIPTION     "The ifIndex of the ATM VPN Link Interface."
        ::= { stnAtmVpnLinkEntry 1 }

    stnAtmVpnLinkViId OBJECT-TYPE
        SYNTAX          Integer32
        MAX-ACCESS      read-only
        STATUS          current
        DESCRIPTION     "The instance of the configuration record 
                         corresponding to this ATM VPN Link."
        ::= { stnAtmVpnLinkEntry 2 }

    stnAtmVpnLinkName OBJECT-TYPE
        SYNTAX          DisplayString (SIZE (1..32))
        MAX-ACCESS      read-only
        STATUS          current
        DESCRIPTION     "The name configured for this ATM VPN Link."
        ::= { stnAtmVpnLinkEntry 3 }

    stnAtmVpnLinkVpnOUI OBJECT-TYPE
        SYNTAX          Integer32
        MAX-ACCESS      read-only
        STATUS          current
        DESCRIPTION     "The Vpn OUI that is associated with this 
                         ATM VPN Link."
        ::= { stnAtmVpnLinkEntry 4 }

    stnAtmVpnLinkVpnIndex OBJECT-TYPE
        SYNTAX          Integer32
        MAX-ACCESS      read-only
        STATUS          current
        DESCRIPTION     "The Vpn Index that is associated with this 
                         ATM VPN Link."
        ::= { stnAtmVpnLinkEntry 5 }

    stnAtmVpnLinkVpnSubIndex OBJECT-TYPE
        SYNTAX          Integer32
        MAX-ACCESS      read-only
        STATUS          current
        DESCRIPTION     "The Vpn SubIndex that is associated with this 
                         ATM VPN Link."
        ::= { stnAtmVpnLinkEntry 6 }

    stnAtmVpnLinkState OBJECT-TYPE
        SYNTAX          INTEGER {
                          up(1),       -- ready to pass packets
                          down(2),
                          testing(3)   -- in some test mode
                        }
        MAX-ACCESS      read-only
        STATUS          current
        DESCRIPTION     "The current operational state of the ATM VPN LINK."
        ::= { stnAtmVpnLinkEntry 7 }

    stnAtmVpnLinkTrunkViId OBJECT-TYPE
        SYNTAX          Integer32
        MAX-ACCESS      read-only
        STATUS          current
        DESCRIPTION     "The instance of the configuration record 
                         corresponding to the ATM VPN Trunk associated with
                         this ATM VPN Link. If the value is zero, then 
                         no ATM VPN Trunk is currently associated with this
                         ATM VPN Link."
        ::= { stnAtmVpnLinkEntry 8 }

    stnAtmVpnLinkLowerIfIndex OBJECT-TYPE
        SYNTAX          InterfaceIndex
        MAX-ACCESS      read-only
        STATUS          current
        DESCRIPTION     "The ifIndex of the Interface below the 
                         ATM VPN Link Interface."
        ::= { stnAtmVpnLinkEntry 9 }

    stnAtmVpnLinkOutUnknownVpnId OBJECT-TYPE
        SYNTAX          Counter64
        MAX-ACCESS      read-only
        STATUS          current
        DESCRIPTION     "The number packets passed from an ATM VPN Trunk
                         with a Vpn-Id that was appropriate for the 
                         ATM VPN Link's forwarding table."
        ::= { stnAtmVpnLinkEntry 10 }

    stnAtmVpnLinkOutVpnIdIfaceInvalid OBJECT-TYPE
        SYNTAX          Counter64
        MAX-ACCESS      read-only
        STATUS          current
        DESCRIPTION     "The number packets passed from an ATM VPN Trunk
                         when no appropriate interface exists below this
                         ATM VPN Link."
        ::= { stnAtmVpnLinkEntry 11 }

    stnAtmVpnLinkInVpnIdIfaceInvalid OBJECT-TYPE
        SYNTAX          Counter64
        MAX-ACCESS      read-only
        STATUS          current
        DESCRIPTION     "The number packets received when there was no 
			 appropriate ATM VPN Trunk Interface present."
        ::= { stnAtmVpnLinkEntry 12 }


END
