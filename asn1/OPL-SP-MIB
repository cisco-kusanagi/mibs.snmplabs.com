OPL-SP-MIB DEFINITIONS ::= BEGIN

IMPORTS

	MODULE-IDENTITY, OBJECT-TYPE, Integer32, enterprises,
	IpAddress, NOTIFICATION-TYPE
                FROM SNMPv2-SMI
        DisplayString, TEXTUAL-CONVENTION
                FROM SNMPv2-TC
	MODULE-COMPLIANCE, NOTIFICATION-GROUP, OBJECT-GROUP
                FROM SNMPv2-CONF;

	fujitsu             OBJECT IDENTIFIER ::= { enterprises     211 }
	product             OBJECT IDENTIFIER ::= { fujitsu           1 }
	solaris             OBJECT IDENTIFIER ::= { product          15 }
	sparcEnterprise     OBJECT IDENTIFIER ::= { solaris           3 }

oplSpMIB MODULE-IDENTITY
	LAST-UPDATED "201005240000Z"
        ORGANIZATION "Sun Microsystems, Inc.
		      Fujitsu LIMITED"
        CONTACT-INFO "Sun Microsystems, Inc.
                      4150 Network Circle
                      Santa Clara, CA 95054
                      +1-800-555-9SUN or
                      +1-650-960-1300
                      http://www.sun.com
                      or contact your local support representative

		      Fujitsu LIMITED.
                      http://www.fujitsu.com
                      or contact your local support representative"
        DESCRIPTION
		"Version: 1.5
         	 Copyright 2009, by Sun Microsystems, Inc.
         	 All rights reserved. Use is subject to license terms.

		 All Rights Reserved, Copyright Fujitsu LIMITED 2007-2009.

		 This MIB module provides monitoring capabilities for 
		 OPL Systems."
	REVISION "201005240000Z"
        DESCRIPTION
                "This revision extends ScfBoardSubTypeTC with
		types C, 1 and 2."
	REVISION "200906100000Z"
        DESCRIPTION
                "This revision extends ScfTrapEventTypeTC with new
		ac restore trap types. ScfBoardEntry is also extended
		with scfBoardSubType and ScfBoardSubTypeTC."
	REVISION "200901280000Z"
        DESCRIPTION
                "This revision extends ScfComponentType and ScfTrapEventTypeTC
		and introduces scfModeSwitchEvent to support new traps.
		Support for scfSystemAirFlow is also added."
	REVISION "200811140000Z"
        DESCRIPTION
                "This revision introduces power management extensions
		to scfSystemInfo."
	REVISION "200804010000Z"
        DESCRIPTION
                "This revision extends the ScfTrapEventTypeTC
		 textual convention."
	REVISION "200701070000Z"
        DESCRIPTION
                "Initial version of this MIB."
        ::= { sparcEnterprise 1 }

scfObjects         	OBJECT IDENTIFIER ::= { oplSpMIB 1 }

scfInfo           	OBJECT IDENTIFIER ::= { scfObjects 1 }
scfState		OBJECT IDENTIFIER ::= { scfObjects 2 }
scfMonitorInfo		OBJECT IDENTIFIER ::= { scfObjects 3 }
scfSystemInfo		OBJECT IDENTIFIER ::= { scfObjects 4 }
scfDomainInfo	 	OBJECT IDENTIFIER ::= { scfObjects 5 }
scfXsbInfo	 	OBJECT IDENTIFIER ::= { scfObjects 6 }
scfLsbInfo	 	OBJECT IDENTIFIER ::= { scfObjects 7 }
scfBoardInfo		OBJECT IDENTIFIER ::= { scfObjects 8 }
scfCpuInfo		OBJECT IDENTIFIER ::= { scfObjects 9 }
scfMemoryInfo		OBJECT IDENTIFIER ::= { scfObjects 10 }
scfIoBoxInfo       	OBJECT IDENTIFIER ::= { scfObjects 11 }
scfComponentInfo	OBJECT IDENTIFIER ::= { scfObjects 12 }

scfMIBTraps       	OBJECT IDENTIFIER ::= { oplSpMIB 2 }
scfMIBTrapPrefix      	OBJECT IDENTIFIER ::= { scfMIBTraps 0 }
scfMIBTrapData		OBJECT IDENTIFIER ::= { scfMIBTraps 1 }

scfMIBConformances    	OBJECT IDENTIFIER ::= { oplSpMIB 3 }
scfMIBCompliances   	OBJECT IDENTIFIER ::= { scfMIBConformances 1 }
scfMIBGroups     	OBJECT IDENTIFIER ::= { scfMIBConformances 2 }

scfMIBObjectGroups  	OBJECT IDENTIFIER ::= { scfMIBGroups 1 }
scfMIBNotifGroups   	OBJECT IDENTIFIER ::= { scfMIBGroups 2 }

--
-- This MIB, along with providing information pertaining to the
-- monitoring of OPL systems, details the system hardware hierarchy.  This is
-- accomplished in many of the table indexes through the following objects,
-- BoardType, BoardID, ModuleType, ModuleID, SubType, and SubID.  The actual
-- object name in tables which provide hierarchy will vary, but all contain a
-- substring of those names(i.e. scfComponentBoardType) in their necessary
-- table entry indexes.  Board, Module, and Sub Types, all considered system
-- components, are represented in the MIB by the ScfComponentType textual
-- convention.
--
-- The scfComponentTable is the main table of this MIB and provides information
-- for chassis contained hardware.  Other tables, the scfMonitorTable,
-- scfBoardTable, scfCpuTable, and the scfMemoryTable, have a relationship with
-- the scfComponentTable.  This relationship is detailed through the
-- aforementioned indexes BoardType/ID, Module Type/ID, and SubType/ID.
-- Although not all three levels of that hierarchy are necessary for all
-- tables, the table index values will match for related entries.  For example,
-- the scfComponentTable contains a CPU Memory Unit(CMU) ID 1, which is
-- represented with the following indexes:
--
-- scfComponentBoardType: cmu(1)
-- scfComponentBoardId: 1
-- scfComponentModuleType: notApplicable(254)
-- scfComponentModuleId: 0
-- scfComponentSubType: notApplicable(254)
-- scfComponentSubId: 0
--
-- As shown, it is a single level hierarchy, but the table can contain physical
-- component values for all indexes(i.e. CPU Chip: cmu/1, cpum/0, cpuChip/0).
-- With the above entry in the scfComponentTable, there are also corresponding
-- entries in the scfMonitorTable and scfBoardTable to provide even more
-- information for that component.  The indexes in those tables are similar in
-- value even when different in OID and name.  The following are the indexes
-- for the scfBoardTable which requires only 1 level to the hierarchy as the
-- table shows nothing below the board level:
--
-- scfBoardType: cmu(1)
-- scfBoardId: 1
--
-- The following are the indexes for the CMU ID 1 temperature sensor 0 in the
-- scfMonitorTable:
--
-- scfMonitorBoardType: cmu(1)
-- scfMonitorBoardId: 1
-- scfMonitorModuleType: notApplicable(254)
-- scfMonitorModuleId: 0
-- scfMonitorType: temperature(1)
-- scfMonitorId: 0
--
-- The scfMonitorTable has no component entries with more than a two level
-- hierarchy.
--
-- The relationship may not be 1 to 1 from the scfComponentTable to the
-- scfMonitorTable as can be at least several sensors per component, however
-- as it is with the scfBoardTable, if the CMU ID 1 does not appear in the
-- scfComponentTable, there will be no corresponding entries in the other
-- tables.
--
-- This MIB also provides information pertaining to I/O Box I/O expansion
-- chassis.  All I/O Box information is located within the scfIoBoxInfo
-- object group only.
--

-- ***************************************************************************
-- *                      Textual Conventions                                *
-- ***************************************************************************

ScfMonitorTypeTC ::= TEXTUAL-CONVENTION
	STATUS current
    	DESCRIPTION
        	"An enumerated value which represents the type of data
		that is being monitored."
    	SYNTAX INTEGER {
        	temperature(1),
		voltage(2),
		fanRotational(3),
		humidity(4),
		unknown(255)
   	 }

ScfComponentType ::= TEXTUAL-CONVENTION
	STATUS current
    	DESCRIPTION
        	"An enumerated value which represents components
		which make up an OPL Platform."
    	SYNTAX INTEGER {
		cmu(1),
		ddc(2),
		cpum(3),
		cpuChip(4),
		cpuCore(5),
		cpuStrand(6),
		way(7),
		mem(9),
		sc(10),
		tag(11),
		xsb(12),
		mac(13),
		bank(14),
		block(15),
		xbuA(16),
		half(17),
		xbuB(19),
		iou(21),
		pcir(23),
		ioc(24),
		flp(25),
		iocCh(26),
		iocLeaf(27),
		hdd(28),
		pci(29),
		pcic(30),
		xscfA(31),
		xscfB(32),
		xscfC(33),
		clkuA(34),
		clkuB(36),
		psubpA(38),
		psubpB(39),
		acsA(40),
		acsB(41),
		psu(42),
		bpA(43),
		bpB(44),
		ddcA(45),
		fanbpA(46),
		fanbpB(47),
		fanbpC(48),
		fanA(49),
		fan(50),
		fanB(51),
		opnl(53),
		tape(54),
		dvd(55),
		swbp(56),
		medbp(57),
		mbuA(96),
		riser(97),
		pcmu(98),
		ddcB(100),
		memb(110),
		mbuB(115),
		bpuA(133),
		iob(134),
		pdb(135),
		bpuB(136),
		busbar(137),
		ddcr(141),
		sw(148),
		bridge(149),
		gbe(150),
		sas(151),
		xscfu(155),
		psuFan(157),
		airA(158),
		airB(159),
		airC(160),
		acInlet(161),
		hddbp(169),
		tapebp(171),
		dvdbpA(173),
		dvdbpB(175),
		cable(180),
		ioua(190),
		snsu(192),
		ups(196),
		environment(200),
		firm(201),
		domain(203),
		unspecified(253),
		notApplicable(254),
		unknown(255)
   	 }

ScfValidStatus ::= TEXTUAL-CONVENTION
    	STATUS      current
    	DESCRIPTION
        	"An enumeration representing the validity of a
	 	object."
    	SYNTAX INTEGER { 
		invalid(1), 
		valid(2) 
	}

ScfLEDState ::= TEXTUAL-CONVENTION
    	STATUS      current
    	DESCRIPTION
        	"An enumeration representing the state of an OPL System or
		Component LED."
    	SYNTAX INTEGER { 
		off(1), 
		on(2), 
		blinking(3)
	}

ScfModeSwitchState ::= TEXTUAL-CONVENTION
    	STATUS      current
    	DESCRIPTION
        	"A enumerated value representing the state of the OPL systems
		operator panel mode switch."
    	SYNTAX INTEGER { 
		locked(1), 
		service(2)
	}

ScfStateTC ::= TEXTUAL-CONVENTION
    	STATUS      current
    	DESCRIPTION
        	"An enumeration of possible component or Extended System
		Board(XSB) state values."
    	SYNTAX INTEGER {
		unmounted(1),
    		stop(2),
    		init(3),
    		notConfigured(4),
    		idle(5),
    		run(6),
		deconfigured(7),
    		change(254),
    		unknown(255)
	}

ScfErrorStatus ::= TEXTUAL-CONVENTION
    	STATUS      current
    	DESCRIPTION
        	"An enumeration of possible error status values."
    	SYNTAX INTEGER { 
		normal(1),
		degraded(2),
		faulted(3),
		change(254),
		unknown(255)
	}

ScfDomainStatusTC ::= TEXTUAL-CONVENTION
    	STATUS      current
    	DESCRIPTION
        	"An enumeration of possible domain status values."
    	SYNTAX INTEGER { 
		powerOff(1),
    		panic(2),
    		shutdown(3),
    		initialize(4),
    		boot(5),
    		running(6),
    		prom(7),
    		change(254),
    		unknown(255)
	}

ScfDomainConfigPolicy ::= TEXTUAL-CONVENTION
    	STATUS      current
    	DESCRIPTION
        	"An enumeration of possible Domain Component List(DCL)
		configuration policies."
    	SYNTAX INTEGER { 
		fru(1),
    		xsb(2),
    		system(3)
	}

ScfIoBoxLEDState ::= TEXTUAL-CONVENTION
    	STATUS      current
    	DESCRIPTION
        	"An enumeration representing the possible I/O Box LED states."
    	SYNTAX INTEGER { 
		off(1),
		standbyBlink(2),
		blinkSlow(3),
		blinkFast(4),
		feedbackFlash(5),
		on(6),
		unknown(7) 
	}

ScfIoBoxComponentLocation ::= TEXTUAL-CONVENTION
    	STATUS      current
    	DESCRIPTION
        	"An enumeration representing an I/O Box Component Location."
    	SYNTAX INTEGER { 
		left(1),
         	right(2)
	}

ScfIoBoxComponentType ::= TEXTUAL-CONVENTION
    	STATUS      current
    	DESCRIPTION
        	"An enumeration describing possible I/O Box components."
    	SYNTAX INTEGER { 
		unknown(1),
		cp(2),
		ps(3),
		boat(4),
		ulc(5),
		dlc(6)
	}

ScfIoBoatTypeTC ::= TEXTUAL-CONVENTION
    	STATUS      current
    	DESCRIPTION
        	"An enumeration representing I/O Boat Types."
    	SYNTAX INTEGER { 
		notPresent(1),
		unknown(2),
		pcie(3),
         	pcix(4),
         	max(5)
	}

ScfIoBoxEnabledAlarms ::= TEXTUAL-CONVENTION
    	STATUS      current
    	DESCRIPTION
        	"The possible alarm levels that may be enabled for an I/O
		Box sensor."
    	SYNTAX BITS {
        	min(0),
        	max(1)
    	}

ScfCodState ::= TEXTUAL-CONVENTION
    	STATUS      current
    	DESCRIPTION
        	"An enumeration describing possible Capacity On Demand(COD)
		states."
    	SYNTAX INTEGER { 
		disabled(1),
		enabled(2),
		notApplicable(3)
	}

ScfBoardSubTypeTC ::= TEXTUAL-CONVENTION
    	STATUS      current
    	DESCRIPTION
        	"An enumeration describing board subtype."
    	SYNTAX INTEGER { 
		typeA(1),
		typeB(2),
		typeC(3),
		type1(4),
		type2(5),
		notApplicable(254),
		unknown(255)
	}

ScfTrapEventTypeTC ::= TEXTUAL-CONVENTION
    	STATUS      current
    	DESCRIPTION
        	"An enumeration describing possible reasons that
		a trap event has been generated."
    	SYNTAX INTEGER { 
		other(1),
		add(2),
		remove(3),
		acFail(4),
		acRestore(5),
		changeComplete(6),
		acRestoreStart(7),
		acRestoreFail(8),
		acRestoreComplete(9)
	}

ScfTrapStatusEventTypeTC ::= TEXTUAL-CONVENTION
    	STATUS      current
    	DESCRIPTION
        	"An enumeration describing possible reasons that
		a status trap event has been generated."
    	SYNTAX INTEGER {
		other(1),
		degraded(2),
		faulted(3),
		recover(4),
		information(5)
	}

ScfDomainStatusAlarmType ::= TEXTUAL-CONVENTION
    	STATUS      current
    	DESCRIPTION
        	"An enumeration describing possible reasons that
		a domain status alarm has been generated."
    	SYNTAX INTEGER { 
		other(1),
		status(2),
		panic(3)
	}

ScfTrapIoBoxTempEventTypeTC ::= TEXTUAL-CONVENTION
    	STATUS      current
    	DESCRIPTION
        	"An enumeration of possible reasons that an I/O Boat
		Temperature event has been generated."
    	SYNTAX INTEGER { 
		other(1),
		overTemp(2),
		recover(3)
	}

ScfIoBoxLEDType ::= TEXTUAL-CONVENTION
    	STATUS      current
    	DESCRIPTION
        	"An enumeration of I/O Boat LED types."
    	SYNTAX INTEGER { 
		unknown(1),
		locate(2),
		active(3),
		powerDC(4),
		powerAC(5),
		service(6),
		rtr(7),
		overtemp(8),
		mgmt(9),
		data(10)
	}

ScfTrapModeSwitchEventTypeTC ::= TEXTUAL-CONVENTION
    	STATUS      current
    	DESCRIPTION
        	"An enumeration describing possible reasons that
		a panel switch trap event has been generated."
    	SYNTAX INTEGER { 
		other(1),
		powerShort(2),
		powerLong(3),
		modeToLocked(4),
		modeToService(5)
	}

ScfIndex ::= TEXTUAL-CONVENTION
    STATUS            current
    DESCRIPTION
            "An arbitrary value which uniquely identifies an element.  The 
	     value should be a small positive integer; index
             values for different elements are not necessarily
             contiguous."
    SYNTAX Integer32 (0..2147483647)

ScfIoBoxIndex ::= TEXTUAL-CONVENTION
    STATUS            current
    DESCRIPTION
            "An fixed length string which uniquely identifies an I/O
	     Box chassis.  This corresponds to the Boxes serial number."
    SYNTAX OCTET STRING (SIZE(1..6))

ScfXsbIndex ::= TEXTUAL-CONVENTION
    STATUS            current
    DESCRIPTION
            "An fixed length string which uniquely identifies a system XSB.
	    i.e 00-0, 06-1, 15-3"
    SYNTAX OCTET STRING (SIZE(4))

ScfDRState ::= TEXTUAL-CONVENTION
    	STATUS      current
    	DESCRIPTION
        	"An enumeration describing possible dynamic reconfiguration(DR)
		states."
    	SYNTAX INTEGER {
		unconfigured(1),
		configured(2),
		waiting(3),
		disconnected(4),
		unknown(255)
	}

ScfUsageState ::= TEXTUAL-CONVENTION
    	STATUS      current
    	DESCRIPTION
        	"An enumeration describing general states of use."
    	SYNTAX INTEGER { 
		off(1),
		on(2)
	}

ScfTestState ::= TEXTUAL-CONVENTION
    	STATUS      current
    	DESCRIPTION
        	"An enumeration describing various XSB test states."
    	SYNTAX INTEGER { 
		unmounted(1),
		unknown(2),
		testing(3),
		passed(4),
		failed(5)
	}

ScfAssignmentState ::= TEXTUAL-CONVENTION
    	STATUS      current
    	DESCRIPTION
        	"An enumeration describing XSB assignment states."
    	SYNTAX INTEGER { 
		unavailable(1),
		available(2),
		assigned(3)
	}

ScfConnectivityState ::= TEXTUAL-CONVENTION
    	STATUS      current
    	DESCRIPTION
        	"An enumeration describing XSB connectivity states."
    	SYNTAX INTEGER { 
		disconnected(1),
		connected(2)
	}

ScfConfigurationState ::= TEXTUAL-CONVENTION
    	STATUS      current
    	DESCRIPTION
        	"An enumeration describing XSB configuration states."
    	SYNTAX INTEGER { 
		unconfigured(1),
		configured(2)
	}

-- ***************************************************************************
-- *                           scfObjects               	             *
-- ***************************************************************************

--
-- SCF Information
--
--	This group provides general information pertaining to the System
--   Control Facility(SCF).
--

scfAgentId OBJECT-TYPE
	SYNTAX      Integer32
	MAX-ACCESS  read-only
	STATUS      current
	DESCRIPTION
		"SCF board ID which this SNMP agent is currently running on."
	::= { scfInfo 1 }

scfAgentNumber OBJECT-TYPE
	SYNTAX      Integer32
	MAX-ACCESS  read-only
	STATUS      current
	DESCRIPTION
		"Total count of available SCF boards."
	::= { scfInfo 2 }

--
-- SCF Agent Table
--

scfAgentTable OBJECT-TYPE
	SYNTAX      SEQUENCE OF ScfAgentEntry
	MAX-ACCESS  not-accessible
	STATUS      current
	DESCRIPTION
		"Table of available SCF boards."
	::= { scfInfo 3 }

scfAgentEntry OBJECT-TYPE
	SYNTAX      ScfAgentEntry
	MAX-ACCESS  not-accessible
	STATUS      current
	DESCRIPTION
		"Available SCF board entry."
	INDEX   { scfAgentIndex }
	::= { scfAgentTable 1 }

ScfAgentEntry ::=
	SEQUENCE {
		scfAgentIndex ScfIndex,
		scfXcpVersion DisplayString
	}

scfAgentIndex OBJECT-TYPE
	SYNTAX      ScfIndex
	MAX-ACCESS  read-only
	STATUS      current
	DESCRIPTION
		"SCF board ID."
	::= { scfAgentEntry 1 }

scfXcpVersion OBJECT-TYPE
	SYNTAX      DisplayString
	MAX-ACCESS  read-only
	STATUS      current
	DESCRIPTION
		"SCF board XSCF Control Package(XCP) version."
	::= { scfAgentEntry 2 }

--
-- SCF IP Address Information
--
scfIpAddressPortNumber OBJECT-TYPE
	SYNTAX      Integer32
	MAX-ACCESS  read-only
	STATUS      current
	DESCRIPTION
		"SNMP communication port for all SCF LAN IP Addresses."
	::= { scfInfo 4 }

scfIpAddressNumber OBJECT-TYPE
	SYNTAX      Integer32
	MAX-ACCESS  read-only
	STATUS      current
	DESCRIPTION
		"Total count of IP Address table entries."
	::= { scfInfo 5 }

--
-- SCF IP Address Table
--

scfIpAddressTable OBJECT-TYPE
	SYNTAX      SEQUENCE OF ScfIpAddressEntry
	MAX-ACCESS  not-accessible
	STATUS      current
	DESCRIPTION
		"Table of available management LAN IPs on SCF."
	::= { scfInfo 6 }

scfIpAddressEntry OBJECT-TYPE
	SYNTAX      ScfIpAddressEntry
	MAX-ACCESS  not-accessible
	STATUS      current
	DESCRIPTION
		"SCF LAN IP Address entry."
	INDEX   { scfIpAddressIndex }
	::= { scfIpAddressTable 1 }

ScfIpAddressEntry ::=
	SEQUENCE {
		scfIpAddressIndex ScfIndex,
		scfIpAddress IpAddress
	}

scfIpAddressIndex OBJECT-TYPE
	SYNTAX      ScfIndex
	MAX-ACCESS  read-only
	STATUS      current
	DESCRIPTION
		"SCF IP Address table entry index."
	::= { scfIpAddressEntry 1 }

scfIpAddress OBJECT-TYPE
	SYNTAX      IpAddress
	MAX-ACCESS  read-only
	STATUS      current
	DESCRIPTION
		"IP Address of a management LAN port."
	::= { scfIpAddressEntry 2 }

--
-- SCF State Information
--
--	This group provides overall status information known to the SCF.
--

scfSystemState OBJECT-TYPE
	SYNTAX      ScfErrorStatus
	MAX-ACCESS  read-only
	STATUS      current
	DESCRIPTION
		"Overall system state."
	::= { scfState 1 }

scfFirmwareState OBJECT-TYPE
	SYNTAX       ScfErrorStatus
	MAX-ACCESS   read-only
	STATUS       current
	DESCRIPTION
		"SCF software state."
	::= { scfState 2 }

scfHardwareState OBJECT-TYPE
	SYNTAX      ScfErrorStatus
	MAX-ACCESS  read-only
	STATUS      current
	DESCRIPTION
		"Overall system hardware state."
	::= { scfState 3 }

scfModeSwitch OBJECT-TYPE
	SYNTAX      ScfModeSwitchState
	MAX-ACCESS  read-only
	STATUS      current
	DESCRIPTION
		"Operator panel switch state."
	::= { scfState 4 }

--
-- SCF Monitor Information
--
--	This group provides environmental information for a variety of
--   components within the system.
--

scfMonitorNumber OBJECT-TYPE
	SYNTAX      Integer32
	MAX-ACCESS  read-only
	STATUS      current
	DESCRIPTION
		"Total count of environmental monitor table entries."
	::= { scfMonitorInfo 1 }

--
-- SCF Monitor Table
--

scfMonitorTable OBJECT-TYPE
	SYNTAX      SEQUENCE OF ScfMonitorEntry
	MAX-ACCESS  not-accessible
	STATUS      current
	DESCRIPTION
		"Monitor table.  Contains environmental monitor
		information for system components."
	::= { scfMonitorInfo 2 }

scfMonitorEntry OBJECT-TYPE
	SYNTAX      ScfMonitorEntry
	MAX-ACCESS  not-accessible
	STATUS      current
	DESCRIPTION
		"Environmental monitor table entry."
	INDEX   {
		scfMonitorBoardType,
		scfMonitorBoardId,
		scfMonitorModuleType,
		scfMonitorModuleId,
		scfMonitorType,
		scfMonitorId
	}
	::= { scfMonitorTable 1 }

ScfMonitorEntry ::=
	SEQUENCE {
		scfMonitorBoardType ScfComponentType,
		scfMonitorBoardId ScfIndex,
		scfMonitorModuleType ScfComponentType,
		scfMonitorModuleId ScfIndex,
		scfMonitorType ScfMonitorTypeTC,
		scfMonitorId ScfIndex,
		scfMonitorDescription DisplayString,
		scfMonitorAdditionalInfo DisplayString,
		scfMonitorUnits DisplayString,
		scfMonitorStatus ScfValidStatus,
		scfMonitorValue Integer32,
		scfMonitorValueStatus ScfErrorStatus
	}

scfMonitorBoardType OBJECT-TYPE
	SYNTAX      ScfComponentType
	MAX-ACCESS  read-only
	STATUS      current
	DESCRIPTION
		"Monitor component board type."
	::= { scfMonitorEntry 1 }
	
scfMonitorBoardId OBJECT-TYPE
	SYNTAX      ScfIndex
	MAX-ACCESS  read-only
	STATUS      current
	DESCRIPTION
		"Monitor component board ID."
	::= { scfMonitorEntry 2 }

scfMonitorModuleType OBJECT-TYPE
	SYNTAX      ScfComponentType
	MAX-ACCESS  read-only
	STATUS	    current
	DESCRIPTION
		"Monitor component module type."
	::= { scfMonitorEntry 3 }
   
scfMonitorModuleId OBJECT-TYPE
	SYNTAX	    ScfIndex
	MAX-ACCESS  read-only
	STATUS	    current
	DESCRIPTION
		"Monitor component module ID."
	::= { scfMonitorEntry 4 }

scfMonitorType OBJECT-TYPE
	SYNTAX      ScfMonitorTypeTC
	MAX-ACCESS  read-only
	STATUS      current
	DESCRIPTION
		"Monitor component type."
	::= { scfMonitorEntry 5 }

scfMonitorId OBJECT-TYPE
	SYNTAX      ScfIndex
	MAX-ACCESS  read-only
	STATUS      current
	DESCRIPTION
		"Monitor ID."
	::= { scfMonitorEntry 6 }
		
scfMonitorDescription OBJECT-TYPE
	SYNTAX      DisplayString
	MAX-ACCESS  read-only
	STATUS      current
	DESCRIPTION
		"Text description of a monitor component."
	::= { scfMonitorEntry 7 }
	
scfMonitorAdditionalInfo OBJECT-TYPE
	SYNTAX      DisplayString
	MAX-ACCESS  read-only
	STATUS      current
	DESCRIPTION
		"Additional monitor info."
	::= { scfMonitorEntry 8 }
	
scfMonitorUnits OBJECT-TYPE
	SYNTAX      DisplayString
	MAX-ACCESS  read-only
	STATUS      current
	DESCRIPTION
		"Units of value."
	::= { scfMonitorEntry 9 }
	
scfMonitorStatus OBJECT-TYPE
	SYNTAX      ScfValidStatus
	MAX-ACCESS  read-only
	STATUS      current
	DESCRIPTION
		"Status of monitor component.  Reflects if the sensor
		could be accessed or should not be used based on
		the containing components state."
	::= { scfMonitorEntry 10 }
	
scfMonitorValue OBJECT-TYPE
	SYNTAX      Integer32
	MAX-ACCESS  read-only
	STATUS      current
	DESCRIPTION
		"Monitor value."
	::= { scfMonitorEntry 11 }

scfMonitorValueStatus OBJECT-TYPE
	SYNTAX      ScfErrorStatus
	MAX-ACCESS  read-only
	STATUS      current
	DESCRIPTION
		"Status of the monitor value.  Reflects if valid value
		is within required limits."
	::= { scfMonitorEntry 12 }

--
-- SCF System Information
--
--	This group provides general System information and LED states.
--

scfSystemName OBJECT-TYPE
	SYNTAX      DisplayString
	MAX-ACCESS  read-only
	STATUS      current
	DESCRIPTION
		"System name."
	::= { scfSystemInfo 1 }

scfSystemType OBJECT-TYPE
	SYNTAX 	    DisplayString
	MAX-ACCESS  read-only
	STATUS      current
	DESCRIPTION
		"System type."
	::= { scfSystemInfo 2 }

scfSystemSerialNumber OBJECT-TYPE
	SYNTAX      DisplayString
	MAX-ACCESS  read-only
	STATUS      current
	DESCRIPTION
		"System serial number."
	::= { scfSystemInfo 3 }

scfSystemAdditionalInfo OBJECT-TYPE
	SYNTAX      DisplayString
	MAX-ACCESS  read-only
	STATUS      current
	DESCRIPTION
		"Additional System information."
	::= { scfSystemInfo 4 }

scfSystemCpuNumber OBJECT-TYPE
	SYNTAX      Integer32
	MAX-ACCESS  read-only
	STATUS      current
	DESCRIPTION
		"Total count of CPUs/Chips in this system."
	::= { scfSystemInfo 5 }

scfSystemMemoryCapacity OBJECT-TYPE
	SYNTAX      Integer32
	UNITS       "GB"
	MAX-ACCESS  read-only
	STATUS      current
	DESCRIPTION
		"Total memory capacity of this system."
	::= { scfSystemInfo 6 }

scfSystemReadyLED OBJECT-TYPE
	SYNTAX      ScfLEDState
	MAX-ACCESS  read-only
	STATUS      current
	DESCRIPTION
		"Systems Ready LED state."
	::= { scfSystemInfo 7 }

scfSystemPowerLED OBJECT-TYPE
	SYNTAX      ScfLEDState
	MAX-ACCESS  read-only
	STATUS      current
	DESCRIPTION
		"Systems Power LED state."
	::= { scfSystemInfo 8 }

scfSystemCheckLED OBJECT-TYPE
	SYNTAX      ScfLEDState
	MAX-ACCESS  read-only
	STATUS      current
	DESCRIPTION
		"Systems Check LED state."
	::= { scfSystemInfo 9 }

scfSystemActualPowerConsumption    OBJECT IDENTIFIER ::= { scfSystemInfo 10 }
scfSystemAirFlow                   OBJECT IDENTIFIER ::= { scfSystemInfo 11 }
scfSystemAmbientTemperature        OBJECT IDENTIFIER ::= { scfSystemInfo 12 }
scfSystemPowerSource               OBJECT IDENTIFIER ::= { scfSystemInfo 13 }
scfSystemPermittedPowerConsumption OBJECT IDENTIFIER ::= { scfSystemInfo 14 }
scfSystemAvailablePowerConsumption OBJECT IDENTIFIER ::= { scfSystemInfo 15 }

--
-- SCF System Actual Power Consumption
--
--	This group provides System Actual Power Consumption information
--

scfSystemActualPowerConsumptionValue OBJECT-TYPE
	SYNTAX      Integer32
	MAX-ACCESS  read-only
	STATUS      current
	DESCRIPTION
		"Power consumption of the system. Set to 0 if this feature
		is not supported."
	::= { scfSystemActualPowerConsumption 1 }

scfSystemActualPowerConsumptionUnit OBJECT-TYPE
	SYNTAX      DisplayString
	MAX-ACCESS  read-only
	STATUS      current
	DESCRIPTION
		"Unit of system power consumption."
	::= { scfSystemActualPowerConsumption 2 }

scfSystemActualPowerMinPollingInterval OBJECT-TYPE
	SYNTAX      Integer32
	MAX-ACCESS  read-only
	STATUS      current
	DESCRIPTION
		"Minimum interval time in seconds between updates of
		scfSystemActualPowerConsumptionValue. It is strongly
		recommended to get object scfSystemActualPowerConsumptionValue
		with intervals longer than this value. It is meaningless to
		get value at smaller intervals, because, internally,
		scfSystemActualPowerConsumptionValue will not be updated.
		When this feature is not supported, maximum
		value of INTEGER type is set as interval value."
	::= { scfSystemActualPowerConsumption 3 }

--
-- SCF System Exhaust Air Flow
--
--	This group provides System Exhaust Air Flow information
--

scfSystemExhaustAirFlowValue OBJECT-TYPE
	SYNTAX      Integer32
	MAX-ACCESS  read-only
	STATUS      current
	DESCRIPTION
		"Exhaust air flow of the system. Set to 0 if this feature
		is not supported."
	::= { scfSystemAirFlow 1 }

scfSystemExhaustAirFlowUnit OBJECT-TYPE
	SYNTAX      DisplayString
	MAX-ACCESS  read-only
	STATUS      current
	DESCRIPTION
		"Unit of system exhaust air flow."
	::= { scfSystemAirFlow 2 }

scfSystemExhaustAirFlowMinPollingInterval OBJECT-TYPE
	SYNTAX      Integer32
	MAX-ACCESS  read-only
	STATUS      current
	DESCRIPTION
		"Minimum interval time in seconds between updates of
		scfSystemExhaustAirFlowValue. It is strongly
		recommended to get object scfSystemExhaustAirFlowValue
		with intervals longer than this value. It is meaningless to
		get value at smaller intervals, because, internally,
		scfSystemExhaustAirFlowValue will not be updated.
		When this feature is not supported, maximum
		value of INTEGER type is set as interval value."
	::= { scfSystemAirFlow 3 }

--
-- SCF System Ambient Temperature
--
--	This group provides System AAmbient Temperature information
--

scfSystemAmbientTemperatureValue OBJECT-TYPE
	SYNTAX      DisplayString
	MAX-ACCESS  read-only
	STATUS      current
	DESCRIPTION
		"Ambient temperature of the system. Set to 0 if this feature
		is not supported."
	::= { scfSystemAmbientTemperature 1 }

scfSystemAmbientTemperatureUnit OBJECT-TYPE
	SYNTAX      DisplayString
	MAX-ACCESS  read-only
	STATUS      current
	DESCRIPTION
		"Unit of system ambient temperature."
	::= { scfSystemAmbientTemperature 2 }

scfSystemAmbientTemperatureMinPollingInterval OBJECT-TYPE
	SYNTAX      Integer32
	MAX-ACCESS  read-only
	STATUS      current
	DESCRIPTION
		"Minimum interval time in seconds between updates of
		scfSystemAmbientTemperatureValue. It is strongly
		recommended to get object scfSystemAmbientTemperatureValue
		with intervals longer than this value. It is meaningless to
		get value at smaller intervals, because, internally,
		scfSystemAmbientTemperatureValue will not be updated.
		When this feature is not supported, maximum
		value of INTEGER type is set as interval value."
	::= { scfSystemAmbientTemperature 3 }

--
-- SCF System Permitted Power Consumption
--
--	This group provides System Permitted Power Consumption information
--

scfSystemPermittedPowerConsumptionValue OBJECT-TYPE
	SYNTAX      Integer32
	MAX-ACCESS  read-only
	STATUS      current
	DESCRIPTION
		"Maximum power consumption, that a system 
		will consume over all configurations. When this feature is 
		not supported, 0 is set."
	::= { scfSystemPermittedPowerConsumption 1 }

scfSystemPermittedPowerConsumptionUnit OBJECT-TYPE
	SYNTAX      DisplayString
	MAX-ACCESS  read-only
	STATUS      current
	DESCRIPTION
		"Unit of power consumption."
	::= { scfSystemPermittedPowerConsumption 2 }

--
-- SCF Domain Information
--
--	This group provides information specific to all Domains known to 
--   the SCF.
--

scfDomainNumber OBJECT-TYPE
	SYNTAX      Integer32
	MAX-ACCESS  read-only
	STATUS      current
	DESCRIPTION
		"Total count of Domain Table entries."
	::= { scfDomainInfo 1 }

--
-- SCF Domain Table
--

scfDomainTable OBJECT-TYPE
	SYNTAX      SEQUENCE OF ScfDomainEntry
	MAX-ACCESS  not-accessible
	STATUS      current
	DESCRIPTION
		"Domain table."
	::= { scfDomainInfo 2 }

scfDomainEntry OBJECT-TYPE
	SYNTAX      ScfDomainEntry
	MAX-ACCESS  not-accessible
	STATUS      current
	DESCRIPTION
		"Domain table entry."
	INDEX   { scfDomainId }
	::= { scfDomainTable 1 }

ScfDomainEntry ::=
	SEQUENCE {
		scfDomainId ScfIndex,
		scfDomainCpuNumber Integer32,
		scfDomainMemoryCapacity Integer32,
		scfDomainObpVersion DisplayString,
		scfDomainObpAdditionalInfo DisplayString,
		scfDomainOsMachine DisplayString,
		scfDomainOsRelease DisplayString,
		scfDomainOsSysName DisplayString,
		scfDomainOsNodeName DisplayString,
		scfDomainOsVersion DisplayString,
		scfDomainOsAdditionalInfo DisplayString,
		scfDomainValid ScfValidStatus,
		scfDomainXsbs DisplayString,
		scfDomainStatus ScfDomainStatusTC,
		scfDomainErrorStatus ScfErrorStatus,
		scfDomainConfigurationPolicy ScfDomainConfigPolicy
	}

scfDomainId OBJECT-TYPE
	SYNTAX      ScfIndex
	MAX-ACCESS  read-only
	STATUS      current
	DESCRIPTION
		"Domain ID."
	::= { scfDomainEntry 1 }

scfDomainCpuNumber OBJECT-TYPE
	SYNTAX      Integer32
	MAX-ACCESS  read-only
	STATUS      current
	DESCRIPTION
		"Total number of CPUs/Strands in this domain."
	::= { scfDomainEntry 2 }

scfDomainMemoryCapacity OBJECT-TYPE
	SYNTAX      Integer32
	UNITS       "GB"
	MAX-ACCESS  read-only
	STATUS      current
	DESCRIPTION
		"Memory capacity of this domain."
	::= { scfDomainEntry 3 }

scfDomainObpVersion OBJECT-TYPE
	SYNTAX      DisplayString
	MAX-ACCESS  read-only
	STATUS      current
	DESCRIPTION
		"Version of OBP firmware."
	::= { scfDomainEntry 4 }

scfDomainObpAdditionalInfo OBJECT-TYPE
	SYNTAX      DisplayString
	MAX-ACCESS  read-only
	STATUS      current
	DESCRIPTION
		"Additional OBP information."
	::= { scfDomainEntry 5 }

scfDomainOsMachine OBJECT-TYPE
	SYNTAX      DisplayString
	MAX-ACCESS  read-only
	STATUS      current
	DESCRIPTION
		"Domain machine hardware name."
	::= { scfDomainEntry 6 }

scfDomainOsRelease OBJECT-TYPE
	SYNTAX      DisplayString
	MAX-ACCESS  read-only
	STATUS      current
	DESCRIPTION
		"OS release level."
	::= { scfDomainEntry 7 }

scfDomainOsSysName OBJECT-TYPE
	SYNTAX      DisplayString
	MAX-ACCESS  read-only
	STATUS      current
	DESCRIPTION
		"OS Name."
	::= { scfDomainEntry 8 }

scfDomainOsNodeName OBJECT-TYPE
	SYNTAX      DisplayString
	MAX-ACCESS  read-only
	STATUS      current
	DESCRIPTION
		"OS network node hostname."
	::= { scfDomainEntry 9 }

scfDomainOsVersion OBJECT-TYPE
	SYNTAX      DisplayString
	MAX-ACCESS  read-only
	STATUS      current
	DESCRIPTION
		"Version of the OS."
	::= { scfDomainEntry 10 }

scfDomainOsAdditionalInfo OBJECT-TYPE
	SYNTAX      DisplayString
	MAX-ACCESS  read-only
	STATUS      current
	DESCRIPTION
		"Additional OS information."
	::= { scfDomainEntry 11 }

scfDomainValid OBJECT-TYPE
	SYNTAX      ScfValidStatus
	MAX-ACCESS  read-only
	STATUS      current
	DESCRIPTION
		"Validity of the domain."
	::= { scfDomainEntry 12 }

scfDomainXsbs OBJECT-TYPE
	SYNTAX      DisplayString
	MAX-ACCESS  read-only
	STATUS      current
	DESCRIPTION
		"List of XSBs contained in this domain."
	::= { scfDomainEntry 13 }

scfDomainStatus OBJECT-TYPE
	SYNTAX      ScfDomainStatusTC
	MAX-ACCESS  read-only
	STATUS      current
	DESCRIPTION
		"Domain operational status."
	::= { scfDomainEntry 14 }

scfDomainErrorStatus OBJECT-TYPE
	SYNTAX ScfErrorStatus
	MAX-ACCESS  read-only
	STATUS      current
	DESCRIPTION
		"Domain error status."
	::= { scfDomainEntry 15 }

scfDomainConfigurationPolicy OBJECT-TYPE
	SYNTAX      ScfDomainConfigPolicy
	MAX-ACCESS  read-only
	STATUS      current
	DESCRIPTION
		"The DCL configuration policy of this domain."
	::= { scfDomainEntry 16 }

--
-- SCF XSB Information
--
--	This group provides information specific to all Extended System
--   Boards(XSBs) known to the SCF.
--

scfXsbType OBJECT-TYPE
	SYNTAX      Integer32
	MAX-ACCESS  read-only
	STATUS      current
	DESCRIPTION
		"Type of XSB rule for the system."
	::= { scfXsbInfo 1 }

scfXsbNumber OBJECT-TYPE
	SYNTAX      Integer32
	MAX-ACCESS  read-only
	STATUS      current
	DESCRIPTION
		"Total count of XSB Table entries."
	::= { scfXsbInfo 2 }

--
-- SCF XSB Table
--

scfXsbTable OBJECT-TYPE
	SYNTAX      SEQUENCE OF ScfXsbEntry
	MAX-ACCESS  not-accessible
	STATUS      current
	DESCRIPTION
		"XSB table."
	::= { scfXsbInfo 3 }

scfXsbEntry OBJECT-TYPE
	SYNTAX      ScfXsbEntry
	MAX-ACCESS  not-accessible
	STATUS      current
	DESCRIPTION
		"XSB table entry."
	INDEX   { scfXsbId }
	::= { scfXsbTable 1 }

ScfXsbEntry ::=
	SEQUENCE {
		scfXsbId ScfXsbIndex,
            	scfXsbStatus ScfStateTC,
            	scfXsbErrorStatus ScfErrorStatus,
            	scfXsbDomainId Integer32,
            	scfXsbDrStatus ScfDRState,
            	scfXsbSubStatusPower ScfUsageState,
            	scfXsbSubStatusTest ScfTestState,
            	scfXsbSubStatusAssignment ScfAssignmentState,
            	scfXsbSubStatusConnectivity ScfConnectivityState,
            	scfXsbSubStatusConfiguration ScfConfigurationState,
		scfXsbSetupDID Integer32,
            	scfXsbNextDID Integer32
	}

scfXsbId OBJECT-TYPE
	SYNTAX      ScfXsbIndex
	MAX-ACCESS  read-only
	STATUS      current
	DESCRIPTION
		"XSB ID."
	::= { scfXsbEntry 1 }

scfXsbStatus OBJECT-TYPE
	SYNTAX      ScfStateTC
	MAX-ACCESS  read-only
	STATUS      current
	DESCRIPTION
		"XSB operational state."
	::= { scfXsbEntry 2 }

scfXsbErrorStatus OBJECT-TYPE
	SYNTAX      ScfErrorStatus
	MAX-ACCESS  read-only
	STATUS      current
	DESCRIPTION
		"XSB error status."
	::= { scfXsbEntry 3 }

scfXsbDomainId OBJECT-TYPE
	SYNTAX      Integer32
	MAX-ACCESS  read-only
	STATUS      current
	DESCRIPTION
		"Active domain ID of the XSB."
	::= { scfXsbEntry 4 }

scfXsbDrStatus OBJECT-TYPE
	SYNTAX      ScfDRState
	MAX-ACCESS  read-only
	STATUS      current
	DESCRIPTION
		"Domain reconfiguration status of the XSB."
	::= { scfXsbEntry 5 }

scfXsbSubStatusPower OBJECT-TYPE
	SYNTAX      ScfUsageState
	MAX-ACCESS  read-only
	STATUS      current
	DESCRIPTION
		"XSB detail status power state."
	::= { scfXsbEntry 6 }

scfXsbSubStatusTest OBJECT-TYPE
	SYNTAX      ScfTestState
	MAX-ACCESS  read-only
	STATUS      current
	DESCRIPTION
		"XSB detail status test state."
	::= { scfXsbEntry 7 }

scfXsbSubStatusAssignment OBJECT-TYPE
	SYNTAX      ScfAssignmentState
	MAX-ACCESS  read-only
	STATUS      current
	DESCRIPTION
		"XSB detail status assignment state."
	::= { scfXsbEntry 8 }

scfXsbSubStatusConnectivity OBJECT-TYPE
	SYNTAX      ScfConnectivityState
	MAX-ACCESS  read-only
	STATUS      current
	DESCRIPTION
		"XSB detail status conectivity state."
	::= { scfXsbEntry 9 }

scfXsbSubStatusConfiguration OBJECT-TYPE
	SYNTAX      ScfConfigurationState
	MAX-ACCESS  read-only
	STATUS      current
	DESCRIPTION
		"XSB detail status configuration state."
	::= { scfXsbEntry 10 }

scfXsbSetupDID OBJECT-TYPE
	SYNTAX      Integer32
	MAX-ACCESS  read-only
	STATUS      current
	DESCRIPTION
		"The Setup Domain ID.  Shows the Domain ID where the XSB
		will be added."
	::= { scfXsbEntry 11 }

scfXsbNextDID OBJECT-TYPE
	SYNTAX      Integer32
	MAX-ACCESS  read-only
	STATUS      current
	DESCRIPTION
		"Next Domain ID.  Shows the Domain ID where the XSB is
		preassigned."
	::= { scfXsbEntry 12 }

--
-- SCF LSB Information
--
--	This group provides information specific to all Logical System
--   Boards(LSBs).  
--

scfLsbType OBJECT-TYPE
	SYNTAX      Integer32
	MAX-ACCESS  read-only
	STATUS      current
	DESCRIPTION
		"Type of LSB rule for this system."
	::= { scfLsbInfo 1 }

scfLsbNumber OBJECT-TYPE
	SYNTAX      Integer32
	MAX-ACCESS  read-only
	STATUS      current
	DESCRIPTION
		"Total count of LSB Table entries."
	::= { scfLsbInfo 2 }

--
-- SCF LSB Table
--
--	This table contains Domain Component List(DCL) information
--   for each LSB.
--

scfLsbTable OBJECT-TYPE
	SYNTAX      SEQUENCE OF ScfLsbEntry
	MAX-ACCESS  not-accessible
	STATUS      current
	DESCRIPTION
		"LSB table."
	::= { scfLsbInfo 3 }

scfLsbEntry OBJECT-TYPE
	SYNTAX      ScfLsbEntry
	MAX-ACCESS  not-accessible
	STATUS      current
	DESCRIPTION
		"LSB table entry."
	INDEX   { scfLsbDomainId, scfLsbId }
	::= { scfLsbTable 1 }

ScfLsbEntry ::=
	SEQUENCE {
		scfLsbDomainId ScfIndex,
		scfLsbId ScfIndex,
		scfLsbXsbId DisplayString,
		scfLsbNoMem ScfUsageState,
            	scfLsbNoIo ScfUsageState,
            	scfLsbFloatingBoard ScfUsageState
	}

scfLsbDomainId OBJECT-TYPE
	SYNTAX      ScfIndex
	MAX-ACCESS  read-only
	STATUS      current
	DESCRIPTION
		"LSB Domain ID."
	::= { scfLsbEntry 1 }

scfLsbId OBJECT-TYPE
	SYNTAX      ScfIndex
	MAX-ACCESS  read-only
	STATUS      current
	DESCRIPTION
		"LSB ID."
	::= { scfLsbEntry 2 }

scfLsbXsbId OBJECT-TYPE
	SYNTAX      DisplayString
	MAX-ACCESS  read-only
	STATUS      current
	DESCRIPTION
		"Current XSB ID that is registered to this LSB."
	::= { scfLsbEntry 3 }

scfLsbNoMem OBJECT-TYPE
	SYNTAX      ScfUsageState
	MAX-ACCESS  read-only
	STATUS      current
	DESCRIPTION
		"DCL no-mem use setting.  Reflects if the memory which is
		part of this LSB should not be used in the Domain."
	::= { scfLsbEntry 4 }

scfLsbNoIo OBJECT-TYPE
	SYNTAX      ScfUsageState
	MAX-ACCESS  read-only
	STATUS      current
	DESCRIPTION
		"DCL no-io use setting.  Reflects if the I/O which is
		part of this LSB should not be used in the Domain"
	::= { scfLsbEntry 5 }

scfLsbFloatingBoard OBJECT-TYPE
	SYNTAX      ScfUsageState
	MAX-ACCESS  read-only
	STATUS      current
	DESCRIPTION
		"DCL floating board use setting.  Reflects if the LSB
		is considered a floating board which eases DR operations."
	::= { scfLsbEntry 6 }

--
-- SCF Board Information
--
--	This group provides information pertaining to specific board components
--   within a System.  Currently this is limited to CPU Memory Board Units(CMU)
--   and I/O Units(IOU).
--

scfBoardNumber OBJECT-TYPE
	SYNTAX      Integer32
	MAX-ACCESS  read-only
	STATUS      current
	DESCRIPTION
		"Total count of Board Table entries."
	::= { scfBoardInfo 1 }

--
-- SCF Board Table
--

scfBoardTable OBJECT-TYPE
	SYNTAX      SEQUENCE OF ScfBoardEntry
	MAX-ACCESS  not-accessible
	STATUS      current
	DESCRIPTION
		"Board table."
	::= { scfBoardInfo 2 }

scfBoardEntry OBJECT-TYPE
	SYNTAX      ScfBoardEntry
	MAX-ACCESS  not-accessible
	STATUS      current
	DESCRIPTION
		"Board table entry."
	INDEX   { 
		scfBoardType, 
		scfBoardId 
	}
	::= { scfBoardTable 1 }

ScfBoardEntry ::=
	SEQUENCE {
		scfBoardType ScfComponentType,
		scfBoardId ScfIndex,
		scfBoardName DisplayString,
		scfBoardAdditionalInfo DisplayString,
		scfBoardXsbs Integer32,
		scfBoardState ScfStateTC,
		scfBoardCODEnabled ScfCodState,
		scfBoardSubType ScfBoardSubTypeTC
	}

scfBoardType OBJECT-TYPE
	SYNTAX      ScfComponentType
	MAX-ACCESS  read-only
	STATUS      current
	DESCRIPTION
		"Board type."
	::= { scfBoardEntry 1 }
	
scfBoardId OBJECT-TYPE
	SYNTAX      ScfIndex
	MAX-ACCESS  read-only
	STATUS      current
	DESCRIPTION
		"Board ID."
	::= { scfBoardEntry 2 }
	
scfBoardName OBJECT-TYPE
	SYNTAX      DisplayString
	MAX-ACCESS  read-only
	STATUS      current
	DESCRIPTION
		"Board description."
	::= { scfBoardEntry 3 }
	
scfBoardAdditionalInfo OBJECT-TYPE
	SYNTAX      DisplayString
	MAX-ACCESS  read-only
	STATUS      current
	DESCRIPTION
		"Additional board info."
	::= { scfBoardEntry 4 }
	
scfBoardXsbs OBJECT-TYPE
	SYNTAX      Integer32
	MAX-ACCESS  read-only
	STATUS      current
	DESCRIPTION
		"The total number of XSB partitions for this board."
	::= { scfBoardEntry 5 }

scfBoardState OBJECT-TYPE
	SYNTAX      ScfStateTC
	MAX-ACCESS  read-only
	STATUS      current
	DESCRIPTION
		"Board operating state."
	::= { scfBoardEntry 6 }

scfBoardCODEnabled OBJECT-TYPE
	SYNTAX	    ScfCodState
	MAX-ACCESS  read-only
	STATUS      current
	DESCRIPTION
		"COD State of the board."
	::= { scfBoardEntry 7 }

scfBoardSubType OBJECT-TYPE
	SYNTAX	    ScfBoardSubTypeTC
	MAX-ACCESS  read-only
	STATUS      current
	DESCRIPTION
		"Board subtype."
	::= { scfBoardEntry 8 }

--
-- SCF CPU Information
--
--	This group provides information for all CPU Modules/Chips within the
--   System.
--

scfCpuNumber OBJECT-TYPE
	SYNTAX      Integer32
	MAX-ACCESS  read-only
	STATUS      current
	DESCRIPTION
		"Total count of CPU Table entries."
	::= { scfCpuInfo 1 }

--
-- SCF CPU Table
--

scfCpuTable OBJECT-TYPE
	SYNTAX      SEQUENCE OF ScfCpuEntry
	MAX-ACCESS  not-accessible
	STATUS      current
	DESCRIPTION
		"CPU table."
	::= { scfCpuInfo 2 }

scfCpuEntry OBJECT-TYPE
	SYNTAX      ScfCpuEntry
	MAX-ACCESS  not-accessible
	STATUS      current
	DESCRIPTION
		"CPU table entry."
	INDEX   {
		scfCpuBoardType,
		scfCpuBoardId,
		scfCpuModuleType,
		scfCpuModuleId,
		scfCpuSubType,
		scfCpuSubId
	}
	::= { scfCpuTable 1 }

ScfCpuEntry ::=
	SEQUENCE {
		scfCpuBoardType ScfComponentType,
		scfCpuBoardId ScfIndex,
		scfCpuModuleType ScfComponentType,
		scfCpuModuleId ScfIndex,
		scfCpuSubType ScfComponentType,
		scfCpuSubId ScfIndex,
		scfCpuType DisplayString,
		scfCpuFrequency Integer32,
		scfCpuAdditionalInfo DisplayString,
		scfCpuState ScfStateTC
	}

scfCpuBoardType OBJECT-TYPE
	SYNTAX      ScfComponentType
	MAX-ACCESS  read-only
	STATUS      current
	DESCRIPTION
		"CPU board type."
	::= { scfCpuEntry 1 }
	
scfCpuBoardId OBJECT-TYPE
	SYNTAX      ScfIndex
	MAX-ACCESS  read-only
	STATUS      current
	DESCRIPTION
		"CPU board ID."
	::= { scfCpuEntry 2 }

scfCpuModuleType OBJECT-TYPE
	SYNTAX      ScfComponentType
	MAX-ACCESS  read-only
	STATUS      current
	DESCRIPTION
		"CPU module type."
	::= { scfCpuEntry 3 }
	
scfCpuModuleId OBJECT-TYPE
	SYNTAX      ScfIndex
	MAX-ACCESS  read-only
	STATUS      current
	DESCRIPTION
		"CPU module ID."
	::= { scfCpuEntry 4 }

scfCpuSubType OBJECT-TYPE
	SYNTAX 	    ScfComponentType
	MAX-ACCESS  read-only
	STATUS      current
	DESCRIPTION
		"CPU sub-part type."
	::= { scfCpuEntry 5 }
	
scfCpuSubId OBJECT-TYPE
	SYNTAX      ScfIndex
	MAX-ACCESS  read-only
	STATUS      current
	DESCRIPTION
		"CPU sub-part ID."
	::= { scfCpuEntry 6 }

scfCpuType OBJECT-TYPE
	SYNTAX      DisplayString
	MAX-ACCESS  read-only
	STATUS      current
	DESCRIPTION
		"CPU type."
	::= { scfCpuEntry 7 }
	
scfCpuFrequency OBJECT-TYPE
	SYNTAX      Integer32
	UNITS       "MHz"
	MAX-ACCESS  read-only
	STATUS      current
	DESCRIPTION
		"CPU frequency."
	::= { scfCpuEntry 8 }
	
scfCpuAdditionalInfo OBJECT-TYPE
	SYNTAX      DisplayString
	MAX-ACCESS  read-only
	STATUS      current
	DESCRIPTION
		"Additional CPU info."
	::= { scfCpuEntry 9 }
	
scfCpuState OBJECT-TYPE
	SYNTAX      ScfStateTC
	MAX-ACCESS  read-only
	STATUS      current
	DESCRIPTION
		"CPU operating state."
	::= { scfCpuEntry 10 }

--
-- SCF Memory Information
--

scfMemoryNumber OBJECT-TYPE
	SYNTAX      Integer32
	MAX-ACCESS  read-only
	STATUS      current
	DESCRIPTION
		"Total count of Memory Table entries."
	::= { scfMemoryInfo 1 }

--
-- SCF Memory Table
--
--	This group provides information for all Memory Modules within the
--   System.
--

scfMemoryTable OBJECT-TYPE
	SYNTAX      SEQUENCE OF ScfMemoryEntry
	MAX-ACCESS  not-accessible
	STATUS      current
	DESCRIPTION
		"Memory card table."
	::= { scfMemoryInfo 2 }

scfMemoryEntry OBJECT-TYPE
	SYNTAX      ScfMemoryEntry
	MAX-ACCESS  not-accessible
	STATUS      current
	DESCRIPTION
		"Memory card table entry."
	INDEX   { 
		  scfMemoryBoardType, 
		  scfMemoryBoardId, 
		  scfMemoryModuleType, 
		  scfMemoryModuleId,
		  scfMemorySubType,
		  scfMemorySubId
	}
	::= { scfMemoryTable 1 }

ScfMemoryEntry ::=
	SEQUENCE {
		scfMemoryBoardType ScfComponentType,
		scfMemoryBoardId ScfIndex,
		scfMemoryModuleType ScfComponentType,
		scfMemoryModuleId ScfIndex,
		scfMemorySubType ScfComponentType,
		scfMemorySubId ScfIndex,
		scfMemoryName DisplayString,
		scfMemoryCapacity Integer32,
		scfMemoryAdditionalInfo DisplayString,
		scfMemoryState ScfStateTC
	}

scfMemoryBoardType OBJECT-TYPE
	SYNTAX      ScfComponentType
	MAX-ACCESS  read-only
	STATUS      current
	DESCRIPTION
		"Memory board type."
	::= { scfMemoryEntry 1 }
	
scfMemoryBoardId OBJECT-TYPE
	SYNTAX      ScfIndex
	MAX-ACCESS  read-only
	STATUS      current
	DESCRIPTION
		"Memory board ID."
	::= { scfMemoryEntry 2 }
	
scfMemoryModuleType OBJECT-TYPE
	SYNTAX      ScfComponentType
	MAX-ACCESS  read-only
	STATUS      current
	DESCRIPTION
		"Memory module type."
	::= { scfMemoryEntry 3 }

scfMemoryModuleId OBJECT-TYPE
	SYNTAX      ScfIndex
	MAX-ACCESS  read-only
	STATUS      current
	DESCRIPTION
		"Memory module ID."
	::= { scfMemoryEntry 4 }

scfMemorySubType OBJECT-TYPE
	SYNTAX      ScfComponentType
	MAX-ACCESS  read-only
	STATUS      current
	DESCRIPTION
		"Memory sub-part type."
	::= { scfMemoryEntry 5 }

scfMemorySubId OBJECT-TYPE
	SYNTAX      ScfIndex
	MAX-ACCESS  read-only
	STATUS      current
	DESCRIPTION
		"Memory sub-part ID."
	::= { scfMemoryEntry 6 }

scfMemoryName OBJECT-TYPE
	SYNTAX      DisplayString
	MAX-ACCESS  read-only
	STATUS      current
	DESCRIPTION
		"Memory Name.  This object provides the actual nomenclature
		specific name for this piece of memory. i.e. 02A, 13B"
	::= { scfMemoryEntry 7 }

scfMemoryCapacity OBJECT-TYPE
	SYNTAX	    Integer32
	UNITS       "GB"
	MAX-ACCESS  read-only
	STATUS      current
	DESCRIPTION
		"Memory capacity."
	::= { scfMemoryEntry 8 }

scfMemoryAdditionalInfo OBJECT-TYPE
	SYNTAX      DisplayString
	MAX-ACCESS  read-only
	STATUS      current
	DESCRIPTION
		"Additional Memory info."
	::= { scfMemoryEntry 9 }

scfMemoryState OBJECT-TYPE
	SYNTAX 	    ScfStateTC
	MAX-ACCESS  read-only
	STATUS      current
	DESCRIPTION
		"Operation state of the memory."
	::= { scfMemoryEntry 10 }

--
-- SCF I/O Box Information
--
--	This group provides information for the I/O Box expansion chassis that
--   are attached to the System and the components which make it up.
--   The components include I/O Boats, Link Cards, and Power Supplies/Fans.
--
--	The tables within this object group are all related based on a common
--   index, IoBoxId.  Each table has their own definition of this index,
--   however, each entry in the scfIoBoxTable by using it's scfIoBoxId value
--   can be used in part to find augmenting information pertaining to that
--   I/O Box chassis including Boat, Link Card, Power Supply/Fan, and sensor
--   information for the Box and Box components.
--

scfIoBoxNumber OBJECT-TYPE
	SYNTAX      Integer32
	MAX-ACCESS  read-only
	STATUS      current
	DESCRIPTION
		"Total count of I/O Box Table entries."
	::= { scfIoBoxInfo 1 }

scfIoBoxTable OBJECT-TYPE
	SYNTAX      SEQUENCE OF ScfIoBoxEntry
	MAX-ACCESS  not-accessible
	STATUS      current
	DESCRIPTION 
		"I/O Box table."
	::= { scfIoBoxInfo 2 }

scfIoBoxEntry OBJECT-TYPE
	SYNTAX      ScfIoBoxEntry
	MAX-ACCESS  not-accessible
	STATUS      current
	DESCRIPTION
		"I/O Box entry."
	INDEX   { scfIoBoxId }
	::= { scfIoBoxTable 1 }

ScfIoBoxEntry ::=
	SEQUENCE {
		scfIoBoxId ScfIoBoxIndex,
		scfIoBoxLocationLED ScfIoBoxLEDState,
		scfIoBoxOverTempLED ScfIoBoxLEDState,
		scfIoBoxServiceReqLED ScfIoBoxLEDState,
		scfIoBoxActiveLED ScfIoBoxLEDState,
		scfIoBoxPartNumber DisplayString,
		scfIoBoxSerialNumber DisplayString,
		scfIoBoxDashLevel DisplayString
	}

scfIoBoxId OBJECT-TYPE
	SYNTAX         ScfIoBoxIndex
	MAX-ACCESS     read-only
	STATUS         current
	DESCRIPTION    
		"Unique I/O Box identifier.  The persistent unique identifier
		for an I/O Box is it's serial number."
	::= { scfIoBoxEntry 1 }

scfIoBoxLocationLED OBJECT-TYPE
	SYNTAX      ScfIoBoxLEDState
	MAX-ACCESS  read-only
	STATUS      current
	DESCRIPTION
		"State of the Location LED."
	::= { scfIoBoxEntry 2 }

scfIoBoxOverTempLED OBJECT-TYPE
	SYNTAX      ScfIoBoxLEDState
	MAX-ACCESS  read-only
	STATUS      current
	DESCRIPTION    
		"State of the Over Temperature LED."
	::= { scfIoBoxEntry 3 }

scfIoBoxServiceReqLED OBJECT-TYPE
	SYNTAX      ScfIoBoxLEDState
	MAX-ACCESS  read-only
	STATUS      current
	DESCRIPTION    
		"State of the Service Request LED."
	::= { scfIoBoxEntry 4 }

scfIoBoxActiveLED OBJECT-TYPE
	SYNTAX      ScfIoBoxLEDState
	MAX-ACCESS  read-only
	STATUS      current
	DESCRIPTION    
		"State of the Active LED."
	::= { scfIoBoxEntry 5 }

scfIoBoxPartNumber OBJECT-TYPE
	SYNTAX      DisplayString
	MAX-ACCESS  read-only
	STATUS      current
	DESCRIPTION
		"I/O Box part number."
	::= { scfIoBoxEntry 6 }
	
scfIoBoxSerialNumber OBJECT-TYPE
	SYNTAX      DisplayString
	MAX-ACCESS  read-only
	STATUS      current
	DESCRIPTION
		"I/O Box serial number."
	::= { scfIoBoxEntry 7 }

scfIoBoxDashLevel OBJECT-TYPE
	SYNTAX      DisplayString
	MAX-ACCESS  read-only
	STATUS      current
	DESCRIPTION
		"I/O Box dash level."
	::= { scfIoBoxEntry 8 }

--
-- SCF IOBoat Information
--

scfIoBoatNumber OBJECT-TYPE
	SYNTAX      Integer32
	MAX-ACCESS  read-only
	STATUS      current
	DESCRIPTION
		"Total count of I/O Boat Table entries."
	::= { scfIoBoxInfo 3 }

scfIoBoatTable OBJECT-TYPE
    	SYNTAX      SEQUENCE OF ScfIoBoatEntry
    	MAX-ACCESS  not-accessible
    	STATUS      current
    	DESCRIPTION    
		"I/O Boat table."
    	::= { scfIoBoxInfo 4 }

scfIoBoatEntry OBJECT-TYPE
    	SYNTAX         ScfIoBoatEntry
    	MAX-ACCESS     not-accessible
    	STATUS         current
    	DESCRIPTION    
		"I/O Boat entry.  This entry is indexed by the I/O Box ID
		the Boat is contained in, as well as the Boat identifier."
	INDEX   { scfIoBoatIoBoxId, scfIoBoatId }
    	::= { scfIoBoatTable 1 }

ScfIoBoatEntry ::= 
	SEQUENCE {
		scfIoBoatIoBoxId ScfIoBoxIndex,
    		scfIoBoatId ScfIndex,
		scfIoBoatLocation ScfIoBoxComponentLocation,
		scfIoBoatType ScfIoBoatTypeTC,
		scfIoBoatOKtoRemoveLED ScfIoBoxLEDState,
		scfIoBoatServiceReqLED ScfIoBoxLEDState,
		scfIoBoatActiveLED ScfIoBoxLEDState,
		scfIoBoatPartNumber DisplayString,
		scfIoBoatSerialNumber DisplayString,
		scfIoBoatDashLevel DisplayString
	}

scfIoBoatIoBoxId OBJECT-TYPE
	SYNTAX         ScfIoBoxIndex
	MAX-ACCESS     read-only
	STATUS         current
	DESCRIPTION    
		"Unique I/O Box identifier.  The persistent unique identifier
		for an I/O Box is it's serial number."
	::= { scfIoBoatEntry 1 }

scfIoBoatId OBJECT-TYPE
    	SYNTAX 	    ScfIndex
    	MAX-ACCESS  read-only
    	STATUS      current
    	DESCRIPTION 
		"Unique I/O Boat identifier"
    	::= { scfIoBoatEntry 2 }

scfIoBoatLocation OBJECT-TYPE
    	SYNTAX      ScfIoBoxComponentLocation
    	MAX-ACCESS  read-only
    	STATUS      current
    	DESCRIPTION 
		"Slot location in I/O Box."
    	::= { scfIoBoatEntry 3 }

scfIoBoatType OBJECT-TYPE
	SYNTAX      ScfIoBoatTypeTC
    	MAX-ACCESS  read-only
    	STATUS      current
    	DESCRIPTION 
		"I/O Boat Type."
    	::= { scfIoBoatEntry 4 }

scfIoBoatOKtoRemoveLED OBJECT-TYPE
    	SYNTAX      ScfIoBoxLEDState
    	MAX-ACCESS  read-only
    	STATUS      current
    	DESCRIPTION 
		"State of the I/O Boat Removal LED."
    	::= { scfIoBoatEntry 5 }

scfIoBoatServiceReqLED OBJECT-TYPE
    	SYNTAX      ScfIoBoxLEDState
    	MAX-ACCESS     read-only
    	STATUS         current
    	DESCRIPTION    
		"State of the Service Request LED."
    	::= { scfIoBoatEntry 6 }

scfIoBoatActiveLED OBJECT-TYPE
    	SYNTAX      ScfIoBoxLEDState
    	MAX-ACCESS     read-only
    	STATUS         current
    	DESCRIPTION    
		"State of the Active LED."
    	::= { scfIoBoatEntry 7 }

scfIoBoatPartNumber OBJECT-TYPE
	SYNTAX      DisplayString
	MAX-ACCESS  read-only
	STATUS      current
	DESCRIPTION
		"I/O Boat part number."
	::= { scfIoBoatEntry 8 }
	
scfIoBoatSerialNumber OBJECT-TYPE
	SYNTAX      DisplayString
	MAX-ACCESS  read-only
	STATUS      current
	DESCRIPTION
		"I/O Boat serial number."
	::= { scfIoBoatEntry 9 }

scfIoBoatDashLevel OBJECT-TYPE
	SYNTAX      DisplayString
	MAX-ACCESS  read-only
	STATUS      current
	DESCRIPTION
		"I/O Boat dash level."
	::= { scfIoBoatEntry 10 }

--
-- SCF IOBox Link Card Table
--

scfLinkCardNumber OBJECT-TYPE
	SYNTAX      Integer32
	MAX-ACCESS  read-only
	STATUS      current
	DESCRIPTION
		"Total count of I/O Boat Link Card Table entries."
	::= { scfIoBoxInfo 5 }

scfLinkCardTable OBJECT-TYPE
    	SYNTAX      SEQUENCE OF ScfLinkCardEntry
    	MAX-ACCESS  not-accessible
    	STATUS      current
    	DESCRIPTION    
		"I/O Box Link Card table."
    	::= { scfIoBoxInfo 6 }

scfLinkCardEntry OBJECT-TYPE
    	SYNTAX      ScfLinkCardEntry
    	MAX-ACCESS  not-accessible
    	STATUS      current
    	DESCRIPTION
		"PCI-E Link Card Table Entry.  This entry is indexed by the
		I/O Box container hierarchy, where the link card is
		contained in the boat and the boat is contained in the box."
	INDEX	{ scfLinkCardIoBoxId, scfLinkCardIoBoatId, scfLinkCardId }
    	::= { scfLinkCardTable 1 }

ScfLinkCardEntry ::=
	SEQUENCE {
		scfLinkCardIoBoxId ScfIoBoxIndex,
    		scfLinkCardIoBoatId ScfIndex,
    		scfLinkCardId ScfIndex,
		scfLinkCardDataLED ScfIoBoxLEDState,
		scfLinkCardMgmtLED ScfIoBoxLEDState,
		scfLinkCardDownlinkCardLocation DisplayString,
		scfLinkCardDownlinkCardId Integer32,
		scfLinkCardPartNumber DisplayString,
		scfLinkCardSerialNumber DisplayString,
		scfLinkCardDashLevel DisplayString
	}

scfLinkCardIoBoxId OBJECT-TYPE
	SYNTAX         ScfIoBoxIndex
	MAX-ACCESS     read-only
	STATUS         current
	DESCRIPTION    
		"Unique I/O Box identifier.  The persistent unique identifier
		for an I/O Box is it's serial number."
	::= { scfLinkCardEntry 1 }

scfLinkCardIoBoatId OBJECT-TYPE
    	SYNTAX 	    ScfIndex
    	MAX-ACCESS  read-only
    	STATUS      current
    	DESCRIPTION 
		"Unique I/O Boat identifier"
    	::= { scfLinkCardEntry 2 }

scfLinkCardId OBJECT-TYPE
    	SYNTAX      ScfIndex
    	MAX-ACCESS  read-only
    	STATUS      current
    	DESCRIPTION 
		"Unique Link Card identifier."
    	::= { scfLinkCardEntry 3 }

scfLinkCardDataLED OBJECT-TYPE
    	SYNTAX      ScfIoBoxLEDState
    	MAX-ACCESS  read-only
    	STATUS      current
    	DESCRIPTION 
		"State of the Data LED."
    	::= { scfLinkCardEntry 4 }

scfLinkCardMgmtLED OBJECT-TYPE
    	SYNTAX      ScfIoBoxLEDState
    	MAX-ACCESS  read-only
    	STATUS      current
    	DESCRIPTION 
		"State of the Management LED."
    	::= { scfLinkCardEntry 5 }

scfLinkCardDownlinkCardLocation OBJECT-TYPE
	SYNTAX      DisplayString
	MAX-ACCESS  read-only
	STATUS      current
	DESCRIPTION
		"Link Card counterpart card location on the Host IOU."
	::= { scfLinkCardEntry 6 }

scfLinkCardDownlinkCardId OBJECT-TYPE
	SYNTAX      Integer32
	MAX-ACCESS  read-only
	STATUS      current
	DESCRIPTION
		"Link Card counterpart card ID on the Host IOU."
	::= { scfLinkCardEntry 7 }

scfLinkCardPartNumber OBJECT-TYPE
	SYNTAX      DisplayString
	MAX-ACCESS  read-only
	STATUS      current
	DESCRIPTION
		"Link Card part number."
	::= { scfLinkCardEntry 8 }
	
scfLinkCardSerialNumber OBJECT-TYPE
	SYNTAX      DisplayString
	MAX-ACCESS  read-only
	STATUS      current
	DESCRIPTION
		"Link Card serial number."
	::= { scfLinkCardEntry 9 }

scfLinkCardDashLevel OBJECT-TYPE
	SYNTAX      DisplayString
	MAX-ACCESS  read-only
	STATUS      current
	DESCRIPTION
		"Link Card dash level."
	::= { scfLinkCardEntry 10 }

--
-- SCF IOBox Power Supply/Fan Table
--

scfPowerSupplyFanNumber OBJECT-TYPE
	SYNTAX      Integer32
	MAX-ACCESS  read-only
	STATUS      current
	DESCRIPTION
		"Total count of I/O Box Power Supply/Fan Table entries."
	::= { scfIoBoxInfo 7 }

scfPowerSupplyFanTable OBJECT-TYPE
    	SYNTAX         SEQUENCE OF ScfPowerSupplyFanEntry
    	MAX-ACCESS     not-accessible
    	STATUS         current
    	DESCRIPTION    
		"IOBox Power Supply/Fan Table."
    	::= { scfIoBoxInfo 8 }

scfPowerSupplyFanEntry OBJECT-TYPE
    	SYNTAX         ScfPowerSupplyFanEntry
    	MAX-ACCESS     not-accessible
    	STATUS         current
    	DESCRIPTION    
		"I/O Box Power Supply/Fan Table Entry.  This entry is indexed
		by the I/O Box ID the PS/Fan is contained in, as well as the 
		PS/Fan identifier."
	INDEX	{ scfPowerSupplyFanIoBoxId, scfPowerSupplyFanId }
    	::= { scfPowerSupplyFanTable 1 }

ScfPowerSupplyFanEntry ::= 
	SEQUENCE {
		scfPowerSupplyFanIoBoxId ScfIoBoxIndex,
    		scfPowerSupplyFanId ScfIndex,
		scfPowerSupplyFanLocation ScfIoBoxComponentLocation,
		scfPowerSupplyFanOKtoRemoveLED ScfIoBoxLEDState,
		scfPowerSupplyFanServiceReqLED ScfIoBoxLEDState,
		scfPowerSupplyFanACPowerLED ScfIoBoxLEDState,
		scfPowerSupplyFanDCPowerLED ScfIoBoxLEDState,
		scfPowerSupplyFanPartNumber DisplayString,
		scfPowerSupplyFanSerialNumber DisplayString,
		scfPowerSupplyFanDashLevel DisplayString
	}

scfPowerSupplyFanIoBoxId OBJECT-TYPE
	SYNTAX         ScfIoBoxIndex
	MAX-ACCESS     read-only
	STATUS         current
	DESCRIPTION    
		"Unique I/O Box identifier.  The persistent unique identifier
		for an I/O Box is it's serial number."
	::= { scfPowerSupplyFanEntry 1 }

scfPowerSupplyFanId OBJECT-TYPE
    	SYNTAX         ScfIndex
    	MAX-ACCESS     read-only
    	STATUS         current
    	DESCRIPTION    
		"IOBox Power Supply/Fan identifier."
    	::= { scfPowerSupplyFanEntry 2 }

scfPowerSupplyFanLocation OBJECT-TYPE
    	SYNTAX         ScfIoBoxComponentLocation
    	MAX-ACCESS     read-only
    	STATUS         current
    	DESCRIPTION    
		"Slot location in IOBox."
    	::= { scfPowerSupplyFanEntry 3 }

scfPowerSupplyFanOKtoRemoveLED OBJECT-TYPE
    	SYNTAX      ScfIoBoxLEDState
    	MAX-ACCESS     read-only
    	STATUS         current
    	DESCRIPTION    
		"State of the Power Supply Fan Removal LED."
    	::= { scfPowerSupplyFanEntry 4 }

scfPowerSupplyFanServiceReqLED OBJECT-TYPE
    	SYNTAX      ScfIoBoxLEDState
    	MAX-ACCESS     read-only
    	STATUS         current
    	DESCRIPTION    
		"State of the Service Request LED."
    	::= { scfPowerSupplyFanEntry 5 }

scfPowerSupplyFanACPowerLED OBJECT-TYPE
    	SYNTAX      ScfIoBoxLEDState
    	MAX-ACCESS     read-only
    	STATUS         current
    	DESCRIPTION    
		"State of the A/C Power LED."
    	::= { scfPowerSupplyFanEntry 6 }

scfPowerSupplyFanDCPowerLED OBJECT-TYPE
    	SYNTAX      ScfIoBoxLEDState
    	MAX-ACCESS     read-only
    	STATUS         current
    	DESCRIPTION    
		"State of the D/C Power LED."
    	::= { scfPowerSupplyFanEntry 7 }

scfPowerSupplyFanPartNumber OBJECT-TYPE
	SYNTAX      DisplayString
	MAX-ACCESS  read-only
	STATUS      current
	DESCRIPTION
		"PowerSupply/Fan part number."
	::= { scfPowerSupplyFanEntry 8 }
	
scfPowerSupplyFanSerialNumber OBJECT-TYPE
	SYNTAX      DisplayString
	MAX-ACCESS  read-only
	STATUS      current
	DESCRIPTION
		"PowerSupply/Fan serial number."
	::= { scfPowerSupplyFanEntry 9 }

scfPowerSupplyFanDashLevel OBJECT-TYPE
	SYNTAX      DisplayString
	MAX-ACCESS  read-only
	STATUS      current
	DESCRIPTION
		"PowerSupply/Fan dash level."
	::= { scfPowerSupplyFanEntry 10 }

--
-- SCF IOBox Sensor Table
--

scfIoBoxSensorNumber OBJECT-TYPE
	SYNTAX      Integer32
	MAX-ACCESS  read-only
	STATUS      current
	DESCRIPTION
		"Total count of I/O Box environmental sensor table entries."
	::= { scfIoBoxInfo 9 }

scfIoBoxSensorTable OBJECT-TYPE
	SYNTAX      SEQUENCE OF ScfIoBoxSensorEntry
	MAX-ACCESS  not-accessible
	STATUS      current
	DESCRIPTION
		"I/O Box environmental sensor table."
	::= { scfIoBoxInfo 10 }

scfIoBoxSensorEntry OBJECT-TYPE
	SYNTAX      ScfIoBoxSensorEntry
	MAX-ACCESS  not-accessible
	STATUS      current
	DESCRIPTION
		"I/O Box environmental sensor entry."
	INDEX   {
		scfIoBoxSensorIoBoxId,
		scfIoBoxSensorIoBoxSubType,
		scfIoBoxSensorIoBoxSubId,
		scfIoBoxSensorId
	}
	::= { scfIoBoxSensorTable 1 }

ScfIoBoxSensorEntry ::=
	SEQUENCE {
		scfIoBoxSensorIoBoxId ScfIoBoxIndex,
		scfIoBoxSensorIoBoxSubType ScfIoBoxComponentType,
		scfIoBoxSensorIoBoxSubId ScfIndex,
		scfIoBoxSensorId ScfIndex,
		scfIoBoxSensorDescription DisplayString,
		scfIoBoxSensorUnits DisplayString,
		scfIoBoxSensorValue Integer32,
		scfIoBoxSensorEnabledAlarms ScfIoBoxEnabledAlarms,
		scfIoBoxSensorMinAlarm Integer32,
		scfIoBoxSensorMaxAlarm Integer32
	}

scfIoBoxSensorIoBoxId OBJECT-TYPE
	SYNTAX         ScfIoBoxIndex
	MAX-ACCESS     read-only
	STATUS         current
	DESCRIPTION    
		"Unique I/O Box identifier for a sensor entry.  The 
		persistent unique identifier for an I/O Box is it's serial 
		number."
	::= { scfIoBoxSensorEntry 1 }

scfIoBoxSensorIoBoxSubType OBJECT-TYPE
	SYNTAX         ScfIoBoxComponentType
	MAX-ACCESS     read-only
	STATUS         current
	DESCRIPTION    
		"Type of the I/O Box component that the sensor
		is located."
	::= { scfIoBoxSensorEntry 2 }


scfIoBoxSensorIoBoxSubId OBJECT-TYPE
	SYNTAX         ScfIndex
	MAX-ACCESS     read-only
	STATUS         current
	DESCRIPTION    
		"Identifier for the I/O Box component that the sensor
		is located."
	::= { scfIoBoxSensorEntry 3 }

scfIoBoxSensorId OBJECT-TYPE
	SYNTAX         ScfIndex
	MAX-ACCESS     read-only
	STATUS         current
	DESCRIPTION
		"Identifier of the sensor."
	::= { scfIoBoxSensorEntry 4 }

scfIoBoxSensorDescription OBJECT-TYPE
	SYNTAX         DisplayString
	MAX-ACCESS     read-only
	STATUS         current
	DESCRIPTION
		"A description of the environmental sensor."
	::= { scfIoBoxSensorEntry 5 }

scfIoBoxSensorUnits OBJECT-TYPE
	SYNTAX         DisplayString
	MAX-ACCESS     read-only
	STATUS         current
	DESCRIPTION
		"The units for the environmental sensor value."
	::= { scfIoBoxSensorEntry 6 }

scfIoBoxSensorValue OBJECT-TYPE
	SYNTAX         Integer32
	MAX-ACCESS     read-only
	STATUS         current
	DESCRIPTION    
		"The value read from the environmental sensor.

		This object can be compared with the Sensor Minimum Alarm
		and Maximum Alarm objects in this table to determine the value
		status.  In addition, the Enabled Alarm should be
		used to determine what this value can be compared against,
		MinAlarm, MaxAlarm, or both.

		If a value has exceeded the Minimum or Maximum, then the user
		will be notified through a change in the I/O Box
		component LED or temperature event trap.  Through the
		comparisions described here, further information can be
		gathered as to the cause."
	::= { scfIoBoxSensorEntry 7 }

scfIoBoxSensorEnabledAlarms OBJECT-TYPE
	SYNTAX         ScfIoBoxEnabledAlarms
	MAX-ACCESS     read-only
	STATUS         current
	DESCRIPTION    
		"The environmental alarm threshold values to be utilized
		for this sensor.  The values immediately follow this object."
	::= { scfIoBoxSensorEntry 8 }

scfIoBoxSensorMinAlarm OBJECT-TYPE
	SYNTAX         Integer32
	MAX-ACCESS     read-only
	STATUS         current
	DESCRIPTION    
		"The environmental sensor minimum threshold value before
		an alarm is generated.  Not utilized for all sensors."
	::= { scfIoBoxSensorEntry 9 }

scfIoBoxSensorMaxAlarm OBJECT-TYPE
	SYNTAX         Integer32
	MAX-ACCESS     read-only
	STATUS         current
	DESCRIPTION    
		"The environmental sensor maximum threshold value before
		an alarm is generated.  Not utilized for all sensors."
	::= { scfIoBoxSensorEntry 10 }

--
-- SCF Component Information
--
--	This group provides FRU and Status information for every component 
--   in the system.
--

scfComponentNumber OBJECT-TYPE
	SYNTAX      Integer32
	MAX-ACCESS  read-only
	STATUS      current
	DESCRIPTION
		"Total count of Component Table entries."
	::= { scfComponentInfo 1 }

--
-- SCF Component Table
--

scfComponentTable OBJECT-TYPE
	SYNTAX      SEQUENCE OF ScfComponentEntry
	MAX-ACCESS  not-accessible
	STATUS      current
	DESCRIPTION
		"Hardware Component table."
	::= { scfComponentInfo 2 }

scfComponentEntry OBJECT-TYPE
	SYNTAX      ScfComponentEntry
	MAX-ACCESS  not-accessible
	STATUS      current
	DESCRIPTION
		"Component table entry."
	INDEX   {
		scfComponentBoardType,
		scfComponentBoardId,
		scfComponentModuleType,
		scfComponentModuleId,
		scfComponentSubType,
		scfComponentSubId
	}
	::= { scfComponentTable 1 }

ScfComponentEntry ::=
	SEQUENCE {
		scfComponentBoardType ScfComponentType,
		scfComponentBoardId ScfIndex,
		scfComponentModuleType ScfComponentType,
		scfComponentModuleId ScfIndex,
		scfComponentSubType ScfComponentType,
		scfComponentSubId ScfIndex,
		scfComponentAdditionalInfo DisplayString,
		scfComponentPartNumber DisplayString,
		scfComponentSerialNumber DisplayString,
		scfComponentProductName DisplayString,
		scfComponentManufacturer DisplayString,
		scfComponentManufactureDate DisplayString,
		scfComponentStatus ScfStateTC,
		scfComponentErrorStatus ScfErrorStatus
	}

scfComponentBoardType OBJECT-TYPE
	SYNTAX 	    ScfComponentType
	MAX-ACCESS  read-only
	STATUS      current
	DESCRIPTION
		"Component board type."
	::= { scfComponentEntry 1 }
	
scfComponentBoardId OBJECT-TYPE
	SYNTAX      ScfIndex
	MAX-ACCESS  read-only
	STATUS      current
	DESCRIPTION
		"Component board ID."
	::= { scfComponentEntry 2 }
	
scfComponentModuleType OBJECT-TYPE
	SYNTAX      ScfComponentType
	MAX-ACCESS  read-only
	STATUS      current
	DESCRIPTION
		"Component module type."
	::= { scfComponentEntry 3 }
	
scfComponentModuleId OBJECT-TYPE
	SYNTAX      ScfIndex
	MAX-ACCESS  read-only
	STATUS      current
	DESCRIPTION
		"Component module ID."
	::= { scfComponentEntry 4 }
	
scfComponentSubType OBJECT-TYPE
	SYNTAX 	    ScfComponentType
	MAX-ACCESS  read-only
	STATUS      current
	DESCRIPTION
		"Component sub-part type."
	::= { scfComponentEntry 5 }
	
scfComponentSubId OBJECT-TYPE
	SYNTAX      ScfIndex
	MAX-ACCESS  read-only
	STATUS      current
	DESCRIPTION
		"Component sub-part ID."
	::= { scfComponentEntry 6 }
	
scfComponentAdditionalInfo OBJECT-TYPE
	SYNTAX      DisplayString
	MAX-ACCESS  read-only
	STATUS      current
	DESCRIPTION
		"Additional component info."
	::= { scfComponentEntry 7 }

scfComponentPartNumber OBJECT-TYPE
	SYNTAX      DisplayString
	MAX-ACCESS  read-only
	STATUS      current
	DESCRIPTION
		"Component part number."
	::= { scfComponentEntry 8 }
		
scfComponentSerialNumber OBJECT-TYPE
	SYNTAX      DisplayString
	MAX-ACCESS  read-only
	STATUS      current
	DESCRIPTION
		"Component serial number."
	::= { scfComponentEntry 9 }
	
scfComponentProductName OBJECT-TYPE
	SYNTAX      DisplayString
	MAX-ACCESS  read-only
	STATUS      current
	DESCRIPTION
		"Component product name."
	::= { scfComponentEntry 10 }

scfComponentManufacturer OBJECT-TYPE
	SYNTAX      DisplayString
	MAX-ACCESS  read-only
	STATUS      current
	DESCRIPTION
		"Component manufacturer."
	::= { scfComponentEntry 11 }
	
scfComponentManufactureDate OBJECT-TYPE
	SYNTAX      DisplayString
	MAX-ACCESS  read-only
	STATUS      current
	DESCRIPTION
		"Component manufacture date.

		This date varies for different components.  For many components
		this object will provide IPMI format, which is 3 bytes of the
		number of minutes from 0:00 hrs 1/1/96. In this case the most
		significant byte is first.  In some components, 2 bytes will be
		provided with the first byte year(yy) in binary-coded
		decimal(BCD), and the second byte week(ww) in BCD."
	::= { scfComponentEntry 12 }
				
scfComponentStatus OBJECT-TYPE
	SYNTAX	    ScfStateTC
	MAX-ACCESS  read-only
	STATUS      current
	DESCRIPTION
		"Component operational status."
	::= { scfComponentEntry 13 }
		
scfComponentErrorStatus OBJECT-TYPE
	SYNTAX      ScfErrorStatus
	MAX-ACCESS  read-only
	STATUS      current
	DESCRIPTION
		"Error status of component."
	::= { scfComponentEntry 14 }
	

-- ***************************************************************************
-- *                                scfMIBTraps                              *
-- ***************************************************************************

--
-- MIB Notification data
--
--   The following objects may be optionally appended to any notification.
--

scfTrapEventType OBJECT-TYPE
    	SYNTAX	    ScfTrapEventTypeTC
    	MAX-ACCESS  accessible-for-notify
    	STATUS      current
    	DESCRIPTION 
		"The event type of this notification.  This provides additional
		information on the reason that the notification was sent."
    	::= { scfMIBTrapData 1 }

scfTrapStatusEventType OBJECT-TYPE
    	SYNTAX	    ScfTrapStatusEventTypeTC
    	MAX-ACCESS  accessible-for-notify
    	STATUS      current
    	DESCRIPTION 
		"The status event type of this notification.  This provides
		additional information on the reason that the notification
		was sent."
    	::= { scfMIBTrapData 2 }

scfTrapDomainStatusAlarmType OBJECT-TYPE
    	SYNTAX	    ScfDomainStatusAlarmType
    	MAX-ACCESS  accessible-for-notify
    	STATUS      current
    	DESCRIPTION 
		"The type of this domain alarm that provides additional
		information on the reason that the notification was sent."
    	::= { scfMIBTrapData 3 }

scfTrapIoBoxId OBJECT-TYPE
	SYNTAX         ScfIoBoxIndex
	MAX-ACCESS     accessible-for-notify
	STATUS         current
	DESCRIPTION    
		"Trap unique I/O Box identifier.  The persistent
		unique identifier for an I/O Box is it's serial 
		number."
	::= { scfMIBTrapData 4 }

scfTrapIoBoxSubType OBJECT-TYPE
	SYNTAX         ScfIoBoxComponentType
	MAX-ACCESS     accessible-for-notify
	STATUS         current
	DESCRIPTION    
		"Type of the I/O Box component that a trap
		originated from."
	::= { scfMIBTrapData 5 }

scfTrapIoBoxSubId OBJECT-TYPE
	SYNTAX         ScfIndex
	MAX-ACCESS     accessible-for-notify
	STATUS         current
	DESCRIPTION    
		"Identifier for the I/O Box component that a trap
		originated from."
	::= { scfMIBTrapData 6 }

scfTrapIoBoxTempEventType OBJECT-TYPE
	SYNTAX         ScfTrapIoBoxTempEventTypeTC
	MAX-ACCESS     accessible-for-notify
	STATUS         current
	DESCRIPTION
		"The event type of this notification.  This provides additional
		information on the reason that the notification was sent."
	::= { scfMIBTrapData 7 }

scfTrapIoBoxLedType OBJECT-TYPE
	SYNTAX         ScfIoBoxLEDType
	MAX-ACCESS     accessible-for-notify
	STATUS         current
	DESCRIPTION    
		"LED Type for the I/O Box component that a trap
		originated from."
	::= { scfMIBTrapData 8 }

scfTrapIoBoxLedValue OBJECT-TYPE
	SYNTAX         ScfIoBoxLEDState
	MAX-ACCESS     accessible-for-notify
	STATUS         current
	DESCRIPTION    
		"LED Value for the I/O Box component LED that a trap
		originated from."
	::= { scfMIBTrapData 9 }

scfTrapModeSwitchEventType OBJECT-TYPE
    	SYNTAX	    ScfTrapModeSwitchEventTypeTC
    	MAX-ACCESS  accessible-for-notify
    	STATUS      current
    	DESCRIPTION 
		"The panel switch event type of this notification. This
		provides additional information on the reason that the
		notification was sent."
    	::= { scfMIBTrapData 10 }

--
-- MIB Notifications
--

scfSPFailover NOTIFICATION-TYPE
    	OBJECTS {
		scfAgentIndex
    	}
    	STATUS      current
    	DESCRIPTION
        	"Indicates that a failover from the active SP to the standby 
		SP has occurred.  The Board ID included is the ID of the 
		SP that has been failed over to."
	::= { scfMIBTrapPrefix 1 }

scfComponentEvent NOTIFICATION-TYPE
    	OBJECTS {
		scfComponentSerialNumber,
		scfTrapEventType
    	}
    	STATUS      current
    	DESCRIPTION
        	"Indicates that a component has been added to or removed from
		the system, or that a component-specific event has occurred.
		When indicating that a component has been added to or removed
		from the system, the event will be based on the highest level
		component possible.  For example, if a CMU is removed, then
		only a trap for the CMU is generated and not for the CPU and
		Memory that are on that CMU."
	::= { scfMIBTrapPrefix 2 }

scfComponentStatusEvent NOTIFICATION-TYPE
    	OBJECTS { 
		scfComponentStatus,
		scfTrapStatusEventType
    	}
    	STATUS      current
    	DESCRIPTION
        	"Indicates that a component has changed to a status
		of interest, including fault, degraded, and recovery from
		a previous fault or degraded state condition."
	::= { scfMIBTrapPrefix 3 }

scfXsbModeChangeEvent NOTIFICATION-TYPE
    	OBJECTS {
		scfBoardXsbs
    	}
    	STATUS      current
    	DESCRIPTION
        	"Indicates that an XSB mode has been changed to either
		a divided or non-divided state."
	::= { scfMIBTrapPrefix 4 }

scfDomainStatusAlarm NOTIFICATION-TYPE
    	OBJECTS { 
		scfDomainStatus,
		scfTrapDomainStatusAlarmType
    	}
    	STATUS      current
    	DESCRIPTION
        	"Indicates that a status alarm condition has occurred on a 
		domain.  This includes a status change and a panic."
	::= { scfMIBTrapPrefix 5 }

scfDomainXsbEvent NOTIFICATION-TYPE
    	OBJECTS { 
		scfXsbDomainId,
		scfTrapEventType
    	}
    	STATUS      current
    	DESCRIPTION
        	"Indicates that an XSB has been added to or removed from
		a domain."
	::= { scfMIBTrapPrefix 6 }

scfIoBoxEvent NOTIFICATION-TYPE
    	OBJECTS { 
		scfTrapIoBoxId,
		scfTrapIoBoxSubType,
		scfTrapIoBoxSubId,
		scfTrapEventType
    	}
    	STATUS      current
    	DESCRIPTION
        	"Indicates that an I/O Box component has been added to or
		removed from the system."
	::= { scfMIBTrapPrefix 7 }

scfIoBoxLedEvent NOTIFICATION-TYPE
    	OBJECTS { 
		scfTrapIoBoxId,
		scfTrapIoBoxSubType,
		scfTrapIoBoxSubId,
		scfTrapIoBoxLedType,
		scfTrapIoBoxLedValue
    	}
    	STATUS      current
    	DESCRIPTION
        	"Indicates that an I/O Box component LED changed.  Depending
		on the LED type, this will notify of errors detected in an
		I/O Box component."
	::= { scfMIBTrapPrefix 8 }

scfIoBoxTemperatureEvent NOTIFICATION-TYPE
    	OBJECTS { 
		scfTrapIoBoxId,
		scfTrapIoBoxSubType,
		scfTrapIoBoxSubId,
		scfTrapIoBoxTempEventType
    	}
    	STATUS      current
    	DESCRIPTION
        	"Indicates that an I/O Box temperature sensor has triggered
		an event."
	::= { scfMIBTrapPrefix 9 }

scfModeSwitchEvent NOTIFICATION-TYPE
    	OBJECTS {
		scfTrapModeSwitchEventType,
		scfModeSwitch
    	}
    	STATUS      current
    	DESCRIPTION
        	"Indicates that a panel switch has triggered an event."
	::= { scfMIBTrapPrefix 10 }

-- ***************************************************************************
-- *                         scfCompliance                            	     *
-- ***************************************************************************

scfCompliance MODULE-COMPLIANCE
	STATUS current
    	DESCRIPTION
        	"The compliance statement for SNMP entities which 
		implement this MIB."
    	MODULE -- this MODULE
        	MANDATORY-GROUPS {
            		scfInfoGroup,
	    		scfStateGroup,
	    		scfMonitorInfoGroup,
	    		scfSystemInfoGroup,
	    		scfDomainInfoGroup,
	    		scfXsbInfoGroup,
			scfLsbInfoGroup,
	    		scfBoardInfoGroup,
	    		scfCpuInfoGroup,
	    		scfMemoryInfoGroup,
	    		scfIoBoxInfoGroup,
	    		scfComponentInfoGroup,
			scfNotificationObjectGroup,
            		scfNotificationsGroup,
	    		scfSystemActualPowerConsumptionGroup,
	    		scfSystemAmbientTemperatureGroup,
	    		scfSystemPermittedPowerConsumptionGroup,
	    		scfSystemAirFlowGroup
        	}
	::= { scfMIBCompliances 1 }

-- ***************************************************************************
-- *                            scfMIBObjectGroups                           *
-- ***************************************************************************

scfInfoGroup OBJECT-GROUP
    	OBJECTS { 
              scfAgentId, scfAgentNumber, scfAgentIndex, scfXcpVersion,
	      scfIpAddressPortNumber, scfIpAddressNumber, scfIpAddressIndex,
	      scfIpAddress
	}
	STATUS  current
    	DESCRIPTION
            "A collection of objects providing SCF SNMP Agent information."
    	::= { scfMIBObjectGroups 1 }

scfStateGroup OBJECT-GROUP
    	OBJECTS { 
              scfSystemState, scfFirmwareState, scfHardwareState, 
	      scfModeSwitch
        }
    	STATUS  current
    	DESCRIPTION
            "A collection of objects providing overall SCF state
	    information."
    	::= { scfMIBObjectGroups 2 }

scfMonitorInfoGroup OBJECT-GROUP
    	OBJECTS { 
              scfMonitorNumber, scfMonitorType, scfMonitorBoardType,
	      scfMonitorBoardId, scfMonitorModuleType, scfMonitorModuleId, 
              scfMonitorId, scfMonitorDescription, scfMonitorAdditionalInfo, 
	      scfMonitorUnits, scfMonitorStatus, scfMonitorValue,
	      scfMonitorValueStatus
        }
    	STATUS  current
    	DESCRIPTION
            "A collection of objects providing environmental 
	    (temperature, voltage, rotation) monitoring information
	    for platform components."
    	::= { scfMIBObjectGroups 3 }

scfSystemInfoGroup OBJECT-GROUP
    	OBJECTS { 
              scfSystemName, scfSystemType, scfSystemSerialNumber,
	      scfSystemAdditionalInfo, scfSystemCpuNumber, 
	      scfSystemMemoryCapacity, scfSystemReadyLED, scfSystemPowerLED,
	      scfSystemCheckLED
        }
    	STATUS  current
    	DESCRIPTION
            "A collection of objects providing System information."
    	::= { scfMIBObjectGroups 4 }

scfDomainInfoGroup OBJECT-GROUP
    	OBJECTS { 
		scfDomainNumber, scfDomainId, scfDomainCpuNumber,
		scfDomainMemoryCapacity, scfDomainObpVersion,
		scfDomainObpAdditionalInfo, scfDomainOsMachine,
		scfDomainOsRelease, scfDomainOsSysName, scfDomainOsNodeName,
		scfDomainOsVersion, scfDomainOsAdditionalInfo, scfDomainValid,
		scfDomainXsbs, scfDomainStatus, scfDomainErrorStatus,
		scfDomainConfigurationPolicy
        }
    	STATUS  current
    	DESCRIPTION
            "A collection of objects providing Domain information."
    	::= { scfMIBObjectGroups 5 }

scfXsbInfoGroup OBJECT-GROUP
    	OBJECTS { 
		scfXsbType, scfXsbNumber, scfXsbId, scfXsbStatus,
		scfXsbErrorStatus, scfXsbDomainId, scfXsbDrStatus,
		scfXsbSubStatusPower, scfXsbSubStatusTest,
		scfXsbSubStatusAssignment, scfXsbSubStatusConnectivity,
            	scfXsbSubStatusConfiguration, scfXsbSetupDID,
		scfXsbNextDID
        }
    	STATUS  current
    	DESCRIPTION
            "A collection of objects providing XSB information."
    	::= { scfMIBObjectGroups 6 }

scfLsbInfoGroup OBJECT-GROUP
    	OBJECTS { 
		scfLsbType, scfLsbNumber, scfLsbDomainId, scfLsbId,
		scfLsbXsbId, scfLsbNoMem, scfLsbNoIo, scfLsbFloatingBoard
        }
    	STATUS  current
    	DESCRIPTION
            "A collection of objects providing LSB information."
    	::= { scfMIBObjectGroups 7 }

scfBoardInfoGroup OBJECT-GROUP
    	OBJECTS { 
              	scfBoardNumber, scfBoardType, scfBoardId,
		scfBoardName, scfBoardAdditionalInfo, scfBoardXsbs,
		scfBoardState, scfBoardCODEnabled, scfBoardSubType
        }
    	STATUS  current
    	DESCRIPTION
            "A collection of objects providing Board(CMU/IOU) information."
    	::= { scfMIBObjectGroups 8 }

scfCpuInfoGroup OBJECT-GROUP
    	OBJECTS { 
              	scfCpuNumber, scfCpuBoardType, scfCpuBoardId,
		scfCpuModuleType, scfCpuModuleId, scfCpuSubType, scfCpuSubId,
		scfCpuType, scfCpuFrequency, scfCpuAdditionalInfo,
		scfCpuState
        }
    	STATUS  current
    	DESCRIPTION
            "A collection of objects providing CPU Module information."
    	::= { scfMIBObjectGroups 9 }

scfMemoryInfoGroup OBJECT-GROUP
    	OBJECTS { 
		scfMemoryNumber, scfMemoryBoardType, scfMemoryBoardId,
		scfMemoryModuleType, scfMemoryModuleId, scfMemorySubType,
		scfMemorySubId, scfMemoryName, scfMemoryCapacity,
		scfMemoryAdditionalInfo, scfMemoryState
        }
    	STATUS  current
    	DESCRIPTION
            "A collection of objects providing Memory information."
    	::= { scfMIBObjectGroups 10 }

scfIoBoxInfoGroup OBJECT-GROUP
    	OBJECTS { 
		scfIoBoxNumber, scfIoBoxId, scfIoBoxLocationLED, 
		scfIoBoxOverTempLED, scfIoBoxServiceReqLED, 
		scfIoBoxActiveLED, scfIoBoxPartNumber, 
		scfIoBoxSerialNumber, scfIoBoxDashLevel, scfIoBoatNumber,
		scfIoBoatIoBoxId, scfIoBoatId, scfIoBoatLocation,
		scfIoBoatType,  scfIoBoatOKtoRemoveLED, 
		scfIoBoatServiceReqLED, scfIoBoatActiveLED, 
		scfIoBoatPartNumber,  scfIoBoatSerialNumber, 
		scfIoBoatDashLevel, scfLinkCardNumber, scfLinkCardIoBoxId, 
		scfLinkCardIoBoatId, scfLinkCardId, 
		scfLinkCardDataLED, scfLinkCardMgmtLED,
		scfLinkCardDownlinkCardLocation, 
		scfLinkCardDownlinkCardId, scfLinkCardPartNumber, 
		scfLinkCardSerialNumber, scfLinkCardDashLevel, 
		scfPowerSupplyFanNumber, scfPowerSupplyFanIoBoxId, 
		scfPowerSupplyFanId, scfPowerSupplyFanLocation,
		scfPowerSupplyFanOKtoRemoveLED, 
		scfPowerSupplyFanServiceReqLED, 
		scfPowerSupplyFanACPowerLED, scfPowerSupplyFanDCPowerLED,
		scfPowerSupplyFanPartNumber, scfPowerSupplyFanSerialNumber,
		scfPowerSupplyFanDashLevel, scfIoBoxSensorNumber,
		scfIoBoxSensorIoBoxId, scfIoBoxSensorIoBoxSubType,
		scfIoBoxSensorIoBoxSubId, scfIoBoxSensorId,
		scfIoBoxSensorDescription, scfIoBoxSensorUnits,
		scfIoBoxSensorValue, scfIoBoxSensorEnabledAlarms,
		scfIoBoxSensorMinAlarm, scfIoBoxSensorMaxAlarm
        }
    	STATUS  current
    	DESCRIPTION
            "A collection of objects providing I/O Box information."
    	::= { scfMIBObjectGroups 11 }

scfComponentInfoGroup OBJECT-GROUP
    	OBJECTS { 
              	scfComponentNumber, scfComponentBoardType,
		scfComponentBoardId, scfComponentModuleType,
		scfComponentModuleId, scfComponentSubType,
		scfComponentSubId, scfComponentAdditionalInfo,
		scfComponentPartNumber, scfComponentSerialNumber,
		scfComponentProductName, scfComponentManufacturer,
		scfComponentManufactureDate, scfComponentStatus,
		scfComponentErrorStatus
        }
    	STATUS  current
    	DESCRIPTION
            "A collection of objects providing physical component information."
    	::= { scfMIBObjectGroups 12 }

scfNotificationObjectGroup OBJECT-GROUP
    	OBJECTS { 
		scfTrapEventType, scfTrapStatusEventType,
		scfTrapDomainStatusAlarmType, scfTrapIoBoxId,
		scfTrapIoBoxSubType, scfTrapIoBoxSubId,
		scfTrapIoBoxTempEventType, scfTrapIoBoxLedType,
		scfTrapIoBoxLedValue, scfTrapModeSwitchEventType
        }
    	STATUS  current
    	DESCRIPTION
            "The collection of notification objects used to indicate events,
	     alarms, and state changes that occur in the system."
    	::= { scfMIBObjectGroups 13 }

scfSystemActualPowerConsumptionGroup OBJECT-GROUP
    	OBJECTS { 
              scfSystemActualPowerConsumptionValue,
	      scfSystemActualPowerConsumptionUnit, 
	      scfSystemActualPowerMinPollingInterval
        }
    	STATUS  current
    	DESCRIPTION
            "A collection of objects providing 
		System Actual Power Consumption information."
    	::= { scfMIBObjectGroups 14 }

scfSystemAmbientTemperatureGroup OBJECT-GROUP
    	OBJECTS { 
              scfSystemAmbientTemperatureValue,
	      scfSystemAmbientTemperatureUnit, 
	      scfSystemAmbientTemperatureMinPollingInterval
        }
    	STATUS  current
    	DESCRIPTION
            "A collection of objects providing 
		System Ambient Temperature information."
    	::= { scfMIBObjectGroups 15 }

scfSystemPermittedPowerConsumptionGroup OBJECT-GROUP
    	OBJECTS { 
              scfSystemPermittedPowerConsumptionValue,
	      scfSystemPermittedPowerConsumptionUnit
        }
    	STATUS  current
    	DESCRIPTION
            "A collection of objects providing
		System Permitted Power Consumption information."
    	::= { scfMIBObjectGroups 16 }

scfSystemAirFlowGroup OBJECT-GROUP
    	OBJECTS { 
              scfSystemExhaustAirFlowValue,
	      scfSystemExhaustAirFlowUnit, 
	      scfSystemExhaustAirFlowMinPollingInterval
        }
    	STATUS  current
    	DESCRIPTION
            "A collection of objects providing 
		System Air Flow information."
    	::= { scfMIBObjectGroups 17 }

-- ***************************************************************************
-- *                            scfMIBNotifGroups                            *
-- ***************************************************************************

scfNotificationsGroup NOTIFICATION-GROUP
	NOTIFICATIONS {
		scfSPFailover, scfComponentEvent, scfComponentStatusEvent,
		scfXsbModeChangeEvent, scfDomainStatusAlarm,
		scfDomainXsbEvent, scfIoBoxEvent, scfIoBoxLedEvent,
		scfIoBoxTemperatureEvent, scfModeSwitchEvent
    	}
    	STATUS current
    	DESCRIPTION
        	"The collection of notifications used to indicate events,
		alarms, and state changes that occur in the system."
    	::= { scfMIBNotifGroups 1 }

END
