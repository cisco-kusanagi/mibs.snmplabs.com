-- $Id: srvcmgmt.mib,v 29.2 1999/01/23 01:02:46 mkrasnic Exp $
--
-- May 28, 1998 AKQ initial creation.
 
ASCEND-SRVC-MGMT-MIB DEFINITIONS ::= BEGIN
 
IMPORTS
	Counter,  TimeTicks
		FROM RFC1155-SMI
	OBJECT-TYPE
     		FROM RFC-1212
	DisplayString
		FROM RFC1213-MIB
   	srvcMgmtGroup
		FROM ASCEND-MIB;


dnisMgmt OBJECT IDENTIFIER ::= { srvcMgmtGroup 1 }

--
-- Ascend DNIS (Dialed Number Information Service) Management group
-- 
-- DNIS Management is one of components of the Ascend's Service
-- Management.
--
-- Using DNIS management, ISPs can provide different Class of Services
-- to users such as Guaranteed Connected, Low Latency, Limitted Access,
-- etc...
-- 
-- When the DNIS Management mode is enabled global, the resources
-- (modems, hdlc) in the plant will be managed by the policy setup on the
-- Network Managemnt console such as NavisAccess.
--
-- When the DNIS Management mode is profile, the resources
-- (modems, hdlc) in the specific box will be managed by thresholds
-- setup for each resource.
--
  
dnisMgmtGlobalEnabled OBJECT-TYPE
	SYNTAX INTEGER {
		true(1),
		false(2)
	}	
	ACCESS read-write
	STATUS deprecated
	DESCRIPTION
		"This is to enable the DNIS global management.
		If the 'dnisGlobalEnabled' is set to true
		then the DNIS management is controlled by the 
		policy set up on the Network Management station to
		manage the resource plant as a whole.

		If the 'dnisGlobalEnabled' is set to false,
		then the DNIS limitation is controlled by the 
		policy set up in the local profile under
		Ethernet->Mod Config->DNIS options. 
		Note that this option only exist on the
		MAX 400x/600x Series.  As for TNT all incoming
		calls will be accepted."
	::= { dnisMgmt 1 }

dnisMgmtGlobalNumEntries OBJECT-TYPE
	SYNTAX INTEGER
	ACCESS read-only
	STATUS mandatory
	DESCRIPTION
		"The number of entries present in the dnisGlobalTable."
	::= { dnisMgmt 2 }

dnisMgmtGlobalLastChange OBJECT-TYPE
	SYNTAX TimeTicks
	ACCESS read-only
	STATUS mandatory
	DESCRIPTION
		"The value of sysUpTime at the time of the last creation
		or deletion of an entry in the dnisMgmtGlobalTable.  If 
		the number of entries has been unchanged since the last
		re-initialization of the local network management
		subsystem, then this object contains a zero value."
	::= { dnisMgmt 3 }

dnisMgmtGlobalTable OBJECT-TYPE
    	SYNTAX SEQUENCE OF DnisMgmtGlobalEntry
    	ACCESS not-accessible
     	STATUS mandatory
     	DESCRIPTION
     		"This table contains one entry for each DNIS that has 
		connected with a NAS."
    	::= { dnisMgmt 4 }

dnisMgmtGlobalEntry OBJECT-TYPE
	SYNTAX DnisMgmtGlobalEntry
	ACCESS not-accessible
	STATUS mandatory
	DESCRIPTION
        	"An entry in the DNIS Management global table."
	INDEX  { dnisGlobalPhoneNumber }
	::= {  dnisMgmtGlobalTable 1 }
 
DnisMgmtGlobalEntry ::=
     SEQUENCE {
		dnisGlobalIndex			INTEGER,
		dnisGlobalPhoneNumber		DisplayString,
		dnisGlobalStatus		INTEGER,
		dnisGlobalCallsAccepted		Counter,
		dnisGlobalCallsDropped		Counter,
		dnisGlobalAction		INTEGER,
		dnisGlobalStatusTimeout		TimeTicks
	}

dnisGlobalIndex		OBJECT-TYPE
	SYNTAX	INTEGER
	ACCESS	read-only
	STATUS	deprecated
	DESCRIPTION
		"An unique value, greater than zero, for each
                DNIS phone number.  The value ranges from 1 to
                'dnisMgmtGlobalNumEntries' and identifies which
                DNIS phone number is associated with.

                It is recommended that the value are assigned
                continuously starting from 1.  The value must remain
                constant at least from one re-intialization
                of the entity's network management system to the next
                re-intialization.

		Note:
		This attribute is no longer used as an index
		in this table. It always returns 1."
        ::= {  dnisMgmtGlobalEntry 1 }

dnisGlobalPhoneNumber OBJECT-TYPE
    	SYNTAX DisplayString (SIZE(4..24))
     	ACCESS read-only
     	STATUS mandatory
     	DESCRIPTION
		"4 to 24 digits number.  The DNIS is the phone number dialed
		to access to the hunt group.
		This number is extracted from incoming calls or from
		dnisGlobalActioni. Note that if this number contains
		characters other than digits, the agent returns error. "
     	::= { dnisMgmtGlobalEntry 2 }

dnisGlobalStatus OBJECT-TYPE
     	SYNTAX INTEGER {
		enabled(1),
		disabled(2)
	}
     	ACCESS read-write
     	STATUS mandatory
     	DESCRIPTION
		"The status of this DNIS phone number. When set to enabled, 
		calls on this DNIS will be answered.  When set to disabled,
		calls will be dropped and the fast busy signal will be
		generated.
		Applied only when the dnisMgmtGlobalEnabled is set to true(1)."
     	::= { dnisMgmtGlobalEntry 3 }

dnisGlobalCallsAccepted OBJECT-TYPE
	SYNTAX Counter
   	ACCESS read-only
   	STATUS mandatory
    	DESCRIPTION
		"The number of calls that has been accepted by this DNIS."
     	::= { dnisMgmtGlobalEntry 4 }

dnisGlobalCallsDropped OBJECT-TYPE
	SYNTAX Counter
   	ACCESS read-only
   	STATUS mandatory
    	DESCRIPTION
		"The number of calls that has been dropped by this DNIS."
     	::= { dnisMgmtGlobalEntry 5 }

dnisGlobalAction OBJECT-TYPE
     	SYNTAX INTEGER {
		noAction(1),
		create(2),
		destroy(3)
	}
     	ACCESS read-write
     	STATUS mandatory
     	DESCRIPTION
		"To add/delete an entry (row) in the dnisGlobalTable."
     	::= { dnisMgmtGlobalEntry 6 }

dnisGlobalStatusTimeout OBJECT-TYPE
        SYNTAX  TimeTicks
        ACCESS  read-write
        STATUS  mandatory
        DESCRIPTION
                "This timeout is applied to the dnis if its dnisGlobalStatus
                 is set to disabled(2). After the timeout expires, this
                 dnis changes its dnisGlobalStatus to enabled(1).
                 This timeout may be set at any time, even if the previous
                 one has not yet expired.
                 If this timeout is not set by user at the time
                 dnisGlobalStatus set to disabled(2), it is set
                 to its default value.
		 Note: When being read, this attribute shows the time interval
		       remaining till expiration."
        DEFVAL { 360000 }
        ::= { dnisMgmtGlobalEntry 7 }

END
