Wellfleet-SNMPEXT-MIB DEFINITIONS ::= BEGIN

-- Created by mdl2asn version 3.1
-- Creation date: Wed Aug 30 16:47:43 EDT 1995


    IMPORTS

      IpAddress, Counter, Gauge
        FROM RFC1155-SMI
      OBJECT-TYPE
        FROM RFC-1212
      DisplayString
        FROM RFC1213-MIB
      wfSnmpGroup
        FROM Wellfleet-COMMON-MIB
      AutonomousType
	FROM SNMPv2-TC;


    wfSnmp		OBJECT IDENTIFIER ::= { wfSnmpGroup 1 }

    wfSnmpDisable OBJECT-TYPE
        SYNTAX	INTEGER {
    		    enabled(1),
    		    disabled(2)
    		}
        ACCESS	read-write
        STATUS	mandatory
        DESCRIPTION
                "Enables or disables the SNMP subsystem"
        DEFVAL	{ enabled }
        ::= { wfSnmp 1 }

    wfSnmpUseLock OBJECT-TYPE
        SYNTAX	INTEGER {
    		    enabled(1),
    		    disabled(2)
    		}
        ACCESS	read-write
        STATUS	mandatory	
        DESCRIPTION
                "Flag to indicate whether set locking mechanism is enabled or
                disabled. Set locking permits only one manager to perform
                SNMP sets to the system at any given time.  A genErr will
                be returned to managers that are locked out."
        DEFVAL	{ enabled }
        ::= { wfSnmp 2 }

    wfSnmpLockAddress OBJECT-TYPE
        SYNTAX	IpAddress
        ACCESS	read-write
        STATUS	mandatory	
        DESCRIPTION
                "Address of remote manager that is enforcing the lock. This
                value is set by the SNMP agent.  Remote managers are only
                allowed to clear it."
        ::= { wfSnmp 3 }

    wfSnmpLockTimeOut OBJECT-TYPE
        SYNTAX	INTEGER(1..60)
        ACCESS	read-write
        STATUS	mandatory	
        DESCRIPTION
                "The maximum time (in minutes) a lock can be idle before it is
                cleared.  An idle period is a time interval with no sets from
                the locking manager."
        DEFVAL	{ 2 }
        ::= { wfSnmp 4 }

    wfSnmpAuth OBJECT-TYPE
        SYNTAX	INTEGER {
    		    trivial(1),
    		    party(2),
    		    proprietary(3)
    		}
        ACCESS	read-only
        STATUS	mandatory
        DESCRIPTION
                "The type of authentication used by the agent (set through
                console interface)."
        DEFVAL	{ trivial }
        ::= { wfSnmp 5 }

    wfSnmpInPkts OBJECT-TYPE
        SYNTAX	Counter
        ACCESS	read-only
        STATUS	mandatory
        DESCRIPTION
                "Total number of PDUs received by SNMP from transport entity"
        ::= { wfSnmp 6 }

    wfSnmpOutPkts OBJECT-TYPE
        SYNTAX	Counter
        ACCESS	read-only
        STATUS	mandatory
        DESCRIPTION
                "Total number of PDUs sent by SNMP to transport entity"
        ::= { wfSnmp 7 }

    wfSnmpInBadVersions OBJECT-TYPE
        SYNTAX	Counter
        ACCESS	read-only
        STATUS	mandatory
        DESCRIPTION
                "Total number of PDUs requesting unsupported versions"
        ::= { wfSnmp 8 }

    wfSnmpInBadCommunityNames OBJECT-TYPE
        SYNTAX	Counter
        ACCESS	read-only
        STATUS	mandatory
        DESCRIPTION
                "Total number of PDUs which had an invalid community string"
        ::= { wfSnmp 9 }

    wfSnmpInBadCommunityUses OBJECT-TYPE
        SYNTAX	Counter
        ACCESS	read-only
        STATUS	mandatory
        DESCRIPTION
                "Total number of PDUs requesting an operation unsupported by
                the community"
        ::= { wfSnmp 10 }

    wfSnmpInASNParseErrs OBJECT-TYPE
        SYNTAX	Counter
        ACCESS	read-only
        STATUS	mandatory
        DESCRIPTION
                "Total number of ASN.1 parsing errors during decoding"
        ::= { wfSnmp 11 }

    wfSnmpInBadTypes OBJECT-TYPE
        SYNTAX	Counter
        ACCESS	read-only
        STATUS	mandatory
        DESCRIPTION
                "Total number of PDUs having an unknown PDU type"
        ::= { wfSnmp 12 }

    wfSnmpInTooBigs OBJECT-TYPE
        SYNTAX	Counter
        ACCESS	read-only
        STATUS	mandatory
        DESCRIPTION
                "Total number of PDUs delivered with ErrorStatus='tooBig"
        ::= { wfSnmp 13 }

    wfSnmpInNoSuchNames OBJECT-TYPE
        SYNTAX	Counter
        ACCESS	read-only
        STATUS	mandatory
        DESCRIPTION
                "Total number of PDUs delivered with ErrorStatus='noSuchName"
        ::= { wfSnmp 14 }

    wfSnmpInBadValues OBJECT-TYPE
        SYNTAX	Counter
        ACCESS	read-only
        STATUS	mandatory
        DESCRIPTION
                "Total number of PDUs delivered with ErrorStatus='badValue"
        ::= { wfSnmp 15 }

    wfSnmpInReadOnlys OBJECT-TYPE
        SYNTAX	Counter
        ACCESS	read-only
        STATUS	mandatory
        DESCRIPTION
                "Total number of PDUs delivered with ErrorStatus='readOnly"
        ::= { wfSnmp 16 }

    wfSnmpInGenErrs OBJECT-TYPE
        SYNTAX	Counter
        ACCESS	read-only
        STATUS	mandatory
        DESCRIPTION
                "Total number of PDUs delivered with ErrorStatus='genErr"
        ::= { wfSnmp 17 }

    wfSnmpInTotalReqVars OBJECT-TYPE
        SYNTAX	Counter
        ACCESS	read-only
        STATUS	mandatory
        DESCRIPTION
                "Total number of MIB objects retrieved successfully by the
                agent"
        ::= { wfSnmp 18 }

    wfSnmpInTotalSetVars OBJECT-TYPE
        SYNTAX	Counter
        ACCESS	read-only
        STATUS	mandatory
        DESCRIPTION
                "Total number of MIB objects which have been SET successfully"
        ::= { wfSnmp 19 }

    wfSnmpInGetRequests OBJECT-TYPE
        SYNTAX	Counter
        ACCESS	read-only
        STATUS	mandatory
        DESCRIPTION
                "Total number of Get-Request PDUS accepted and processed"
        ::= { wfSnmp 20 }

    wfSnmpInGetNexts OBJECT-TYPE
        SYNTAX	Counter
        ACCESS	read-only
        STATUS	mandatory
        DESCRIPTION
                "Total number of GetNext-Request PDUS accepted and processed"
        ::= { wfSnmp 21 }

    wfSnmpInSetRequests OBJECT-TYPE
        SYNTAX	Counter
        ACCESS	read-only
        STATUS	mandatory
        DESCRIPTION
                "Total number of Set-Request PDUS accepted and processed"
        ::= { wfSnmp 22 }

    wfSnmpInGetResponses OBJECT-TYPE
        SYNTAX	Counter
        ACCESS	read-only
        STATUS	mandatory
        DESCRIPTION
                "Total number of GetResponse PDUs accepted and processed"
        ::= { wfSnmp 23 }

    wfSnmpInTraps OBJECT-TYPE
        SYNTAX	Counter
        ACCESS	read-only
        STATUS	mandatory
        DESCRIPTION
                "Total number of Trap PDUs accepted and processed"
        ::= { wfSnmp 24 }

    wfSnmpOutTooBigs OBJECT-TYPE
        SYNTAX	Counter
        ACCESS	read-only
        STATUS	mandatory
        DESCRIPTION
                "Total number of PDUs generated by the agent with ErrorStatus=
                'tooBig"
        ::= { wfSnmp 25 }

    wfSnmpOutNoSuchNames OBJECT-TYPE
        SYNTAX	Counter
        ACCESS	read-only
        STATUS	mandatory
        DESCRIPTION
                "Total number of PDUs generated by the agent with ErrorStatus=
                'noSuchName"
        ::= { wfSnmp 26 }

    wfSnmpOutBadValues OBJECT-TYPE
        SYNTAX	Counter
        ACCESS	read-only
        STATUS	mandatory
        DESCRIPTION
                "Total number of PDUs generated by the agent with ErrorStatus=
                'badValue"
        ::= { wfSnmp 27 }

    wfSnmpOutReadOnlys OBJECT-TYPE
        SYNTAX	Counter
        ACCESS	read-only
        STATUS	mandatory
        DESCRIPTION
                "Total number of PDUs generated by the agent with ErrorStatus=
                'readOnly"
        ::= { wfSnmp 28 }

    wfSnmpOutGenErrs OBJECT-TYPE
        SYNTAX	Counter
        ACCESS	read-only
        STATUS	mandatory
        DESCRIPTION
                "Total number of PDUs generated by the agent with ErrorStatus=
                'genErr"
        ::= { wfSnmp 29 }

    wfSnmpOutGetRequests OBJECT-TYPE
        SYNTAX	Counter
        ACCESS	read-only
        STATUS	mandatory
        DESCRIPTION
                "Total number of Get-Request PDUs generated by the agent"
        ::= { wfSnmp 30 }

    wfSnmpOutGetNexts OBJECT-TYPE
        SYNTAX	Counter
        ACCESS	read-only
        STATUS	mandatory
        DESCRIPTION
                "Total number of Get-Next-Request PDUs generated by the agent"
        ::= { wfSnmp 31 }

    wfSnmpOutSetRequests OBJECT-TYPE
        SYNTAX	Counter
        ACCESS	read-only
        STATUS	mandatory
        DESCRIPTION
                "Total number of Set-Request PDUs generated by the agent"
        ::= { wfSnmp 32 }

    wfSnmpOutGetResponses OBJECT-TYPE
        SYNTAX	Counter
        ACCESS	read-only
        STATUS	mandatory
        DESCRIPTION
                "Total number of Get-Response PDUs generated by the agent"
        ::= { wfSnmp 33 }

    wfSnmpOutTraps OBJECT-TYPE
        SYNTAX	Counter
        ACCESS	read-only
        STATUS	mandatory
        DESCRIPTION
                "Total number of Trap PDUs generated by the agent"
        ::= { wfSnmp 34 }

    wfSnmpEnableAuthTraps OBJECT-TYPE
        SYNTAX	INTEGER {
    		    enabled(1),
    		    disabled(2)
    		}
        ACCESS	read-write
        STATUS	mandatory
        DESCRIPTION
                "Idicates whether agent can generate Authentication Failure
                Traps"
        DEFVAL	{ enabled }
        ::= { wfSnmp 35 }

    wfSnmpTrapDebug OBJECT-TYPE
        SYNTAX	INTEGER {
    		    on(1),
    		    off(2)
    		}
        ACCESS	read-write
        STATUS	obsolete
        DESCRIPTION
                "This attribute controls the specific trap filter for debug
                messages"
        DEFVAL	{ on }
        ::= { wfSnmp 36 }

    wfSnmpTrapTrace OBJECT-TYPE
        SYNTAX	INTEGER {
    		    on(1),
    		    off(2)
    		}
        ACCESS	read-write
        STATUS	obsolete
        DESCRIPTION
                "This attribute controls the specific trap filter for trace
                messages"
        DEFVAL	{ on }
        ::= { wfSnmp 37 }

    wfSnmpTrapInfo OBJECT-TYPE
        SYNTAX	INTEGER {
    		    on(1),
    		    off(2)
    		}
        ACCESS	read-write
        STATUS	obsolete
        DESCRIPTION
                "This attribute controls the specific trap filter for
                informational messages"
        DEFVAL	{ off }
        ::= { wfSnmp 38 }

    wfSnmpTrapWarn OBJECT-TYPE
        SYNTAX	INTEGER {
    		    on(1),
    		    off(2)
    		}
        ACCESS	read-write
        STATUS	obsolete
        DESCRIPTION
                "This attribute controls the specific trap filter for warning
                messages"
        DEFVAL	{ off }
        ::= { wfSnmp 39 }

    wfSnmpTrapFault OBJECT-TYPE
        SYNTAX	INTEGER {
    		    on(1),
    		    off(2)
    		}
        ACCESS	read-write
        STATUS	obsolete
        DESCRIPTION
                "This attribute controls the specific trap filter for fault
                messages"
        DEFVAL	{ off }
        ::= { wfSnmp 40 }

    wfSnmpIpTos OBJECT-TYPE
        SYNTAX	INTEGER {
    		    normal(1),
    		    reliability(2)
    		}
        ACCESS	read-write
        STATUS	obsolete
        DESCRIPTION
                "The Type Of Service value set in the IP datagram specifies to
                the Internet transport layer how the datagram should be
                handled. For SNMP high reliability Type Of Service is
                important."
        DEFVAL	{ reliability }
        ::= { wfSnmp 41 }

    wfSnmpPropEncryption OBJECT-TYPE
        SYNTAX	INTEGER {
    		    wflt(1),
    		    others(2)
    		}
        ACCESS	read-only
        STATUS	mandatory
        DESCRIPTION
                "The encryption algorithm to use in proprietary security"
        DEFVAL	{ wflt }
        ::= { wfSnmp 42 }

    wfSnmpPDUThreads OBJECT-TYPE
        SYNTAX INTEGER (3..20)
	ACCESS read-write
        STATUS mandatory
        DESCRIPTION
                "The number of EMANATE Master Agent PDU thread gates"
        DEFVAL { 10 }
        ::= { wfSnmp 43 }

    wfSnmpBusyPDUThreads OBJECT-TYPE
        SYNTAX Gauge
        ACCESS read-only
        STATUS mandatory
        DESCRIPTION
      		"The current number of busy EMANATE Master Agent PDU thread 
                 gates"
	::= { wfSnmp 44 }
     
    wfSnmpLogLevel OBJECT-TYPE
	SYNTAX INTEGER {
		   apall(1),
		   aperror(2),
		   apwarn (3),
		   aptrace (4),
	 	   aptraceerr(5),
		   aptracewarn(6),
		   aperrwarn(7),
		   apnone(8)
		}
        ACCESS read-write
        STATUS mandatory
        DESCRIPTION 
		"The log level enabled for EMANATE log messages"
        DEFVAL { apnone }
        ::= { wfSnmp 45 }

    wfSnmpDelete OBJECT-TYPE
        SYNTAX  INTEGER {
                    created(1),
                    deleted(2)
                }
        ACCESS  read-write
        STATUS  mandatory
        DESCRIPTION
                "Create/Delete parameter. Default is created."
        DEFVAL  { created }
        ::= { wfSnmp 46 }

    wfSnmpScopeDelimiter OBJECT-TYPE
        SYNTAX OCTET STRING(SIZE(1))
        ACCESS read-write
        STATUS mandatory
        DESCRIPTION
                "The character used to separate the naming scope from a
                 scoped community name in the community configuration table.
                 Note that any attempt to configure a community containing
                 this delimiter will be rejected. further, any attempt to
                 change the value of this object to a value which is already
                 used in an existing community string will be rejected."
        DEFVAL {"@"}
        ::= { wfSnmp 47 }

    wfSnmpMaxInPktChain OBJECT-TYPE
        SYNTAX  INTEGER(1..128)
        ACCESS  read-write
        STATUS  mandatory
        DESCRIPTION
                "The maximum number of packets allowed to be processed
                 by snmp gate in a single running state."
        DEFVAL  { 16 }
        ::= { wfSnmp 48 }
 
    wfSnmpCommTable OBJECT-TYPE
        SYNTAX	SEQUENCE OF WfSnmpCommEntry
        ACCESS	not-accessible
        STATUS	mandatory
        DESCRIPTION
                "A table containing valid management communities"
        ::= { wfSnmpGroup 2 }

    wfSnmpCommEntry OBJECT-TYPE
        SYNTAX	WfSnmpCommEntry
        ACCESS	not-accessible
        STATUS	mandatory
        DESCRIPTION
                "Information about a particular community"
        INDEX	{ wfSnmpCommIndex }
        ::= { wfSnmpCommTable 1 }

    WfSnmpCommEntry ::= SEQUENCE {
    	    wfSnmpCommDelete
    		INTEGER,
    	    wfSnmpCommIndex
    		INTEGER,
    	    wfSnmpCommName
    		DisplayString,
    	    wfSnmpCommAccess
    		INTEGER,
	    wfSnmpCommScopeType
		AutonomousType,
	    wfSnmpCommViewIndex
                INTEGER
        }

    wfSnmpCommDelete OBJECT-TYPE
        SYNTAX	INTEGER {
    		    created(1),
    		    deleted(2)
    		}
        ACCESS	read-write
        STATUS	mandatory
        DESCRIPTION
                "A flag to indicate community instance deletion"
        DEFVAL	{ created }
        ::= { wfSnmpCommEntry 1 }

    wfSnmpCommIndex OBJECT-TYPE
        SYNTAX	INTEGER
        ACCESS	read-only
        STATUS	mandatory
        DESCRIPTION
                "A unique numeric value that has a one to one correspondence
                with the community name"
        ::= { wfSnmpCommEntry 2 }

    wfSnmpCommName OBJECT-TYPE
        SYNTAX	DisplayString
        ACCESS	read-write
        STATUS	mandatory
        DESCRIPTION
                "Community name"
        ::= { wfSnmpCommEntry 3 }

    wfSnmpCommAccess OBJECT-TYPE
        SYNTAX	INTEGER {
    		    read-only(1),
    		    read-write(2)
    		}
        ACCESS	read-write
        STATUS	mandatory
        DESCRIPTION
                "Community access mode"
        DEFVAL	{ read-only }
        ::= { wfSnmpCommEntry 4 }

    wfSnmpCommScopeType OBJECT-TYPE
        SYNTAX  AutonomousType
        ACCESS  read-write
        STATUS  mandatory
        DESCRIPTION
                "The type of logical entity with which this community is
                 associated. The naming scope for this type of logical
                 entity is accessed by appending a '@' character followed
                 by the ascii name of the naming scope to the community
                 string, wfsnmpCommName, of this entity. If the scope is
                 unspecified {0 0}, then this community is assumed to be
                 affiliated with the main naming scope."
        ::= { wfSnmpCommEntry 5 }

    wfSnmpCommViewIndex OBJECT-TYPE
        SYNTAX  INTEGER
        ACCESS  read-write
        STATUS  mandatory
        DESCRIPTION
                "Index of the view that is associated to this community."
        ::= { wfSnmpCommEntry 6 }

    wfSnmpMgrTable OBJECT-TYPE
        SYNTAX	SEQUENCE OF WfSnmpMgrEntry
        ACCESS	not-accessible
        STATUS	mandatory
        DESCRIPTION
                "A table containing managers and their respective communities"
        ::= { wfSnmpGroup 3 }

    wfSnmpMgrEntry OBJECT-TYPE
        SYNTAX	WfSnmpMgrEntry
        ACCESS	not-accessible
        STATUS	mandatory
        DESCRIPTION
                "Information about a manager of a community"
        INDEX	{ wfSnmpMgrCommIndex,
    		  wfSnmpMgrAddress }
        ::= { wfSnmpMgrTable 1 }

    WfSnmpMgrEntry ::= SEQUENCE {
    	    wfSnmpMgrDelete
    		INTEGER,
    	    wfSnmpMgrCommIndex
    		INTEGER,
    	    wfSnmpMgrAddress
    		IpAddress,
    	    wfSnmpMgrName
    		DisplayString,
    	    wfSnmpMgrTrapPort
    		INTEGER,
    	    wfSnmpMgrTraps
    		INTEGER,
    	    wfSnmpMgrEncrSeed1
    		INTEGER,
    	    wfSnmpMgrEncrSeed2
    		INTEGER,
    	    wfSnmpMgrEncrSeed3
    		INTEGER,
    	    wfSnmpMgrEncrSeed4
    		INTEGER,
    	    wfSnmpMgrEncrSeed5
    		INTEGER,
	    wfSnmpMgrCircuitlessTrap
		INTEGER
        }

    wfSnmpMgrDelete OBJECT-TYPE
        SYNTAX	INTEGER {
    		    created(1),
    		    deleted(2)
    		}
        ACCESS	read-write
        STATUS	mandatory
        DESCRIPTION
                "A flag to indicate manager instance deletion"
        DEFVAL	{ created }
        ::= { wfSnmpMgrEntry 1 }

    wfSnmpMgrCommIndex OBJECT-TYPE
        SYNTAX	INTEGER
        ACCESS	read-only
        STATUS	mandatory
        DESCRIPTION
                "Associates this manager with a community in the community
                table"
        ::= { wfSnmpMgrEntry 2 }

    wfSnmpMgrAddress OBJECT-TYPE
        SYNTAX	IpAddress
        ACCESS	read-only
        STATUS	mandatory
        DESCRIPTION
                "IP Address of this manager"
        ::= { wfSnmpMgrEntry 3 }

    wfSnmpMgrName OBJECT-TYPE
        SYNTAX	DisplayString
        ACCESS	read-write
        STATUS	mandatory
        DESCRIPTION
                "A name for this manager"
        ::= { wfSnmpMgrEntry 4 }

    wfSnmpMgrTrapPort OBJECT-TYPE
        SYNTAX	INTEGER
        ACCESS	read-write
        STATUS	mandatory
        DESCRIPTION
                "The UDP Port on which this manager is listening for traps"
        DEFVAL	{ 162 }
        ::= { wfSnmpMgrEntry 5 }

    wfSnmpMgrTraps OBJECT-TYPE
        SYNTAX	INTEGER {
    		    none(1),
    		    generic(2),
    		    specific(4),
    		    all(7)
    		}
        ACCESS	read-write
        STATUS	mandatory
        DESCRIPTION
                "Allowable trap types to be sent to Manager"
        DEFVAL	{ generic }
        ::= { wfSnmpMgrEntry 6 }

    wfSnmpMgrEncrSeed1 OBJECT-TYPE
        SYNTAX	INTEGER
        ACCESS	read-only
        STATUS	mandatory
        DESCRIPTION
                "The encrypted value of the seed counter for application 1 of
                this manager"
        ::= { wfSnmpMgrEntry 7 }

    wfSnmpMgrEncrSeed2 OBJECT-TYPE
        SYNTAX	INTEGER
        ACCESS	read-only
        STATUS	mandatory
        DESCRIPTION
                "The encrypted value of the seed counter for application 2 of
                this manager"
        ::= { wfSnmpMgrEntry 8 }

    wfSnmpMgrEncrSeed3 OBJECT-TYPE
        SYNTAX	INTEGER
        ACCESS	read-only
        STATUS	mandatory
        DESCRIPTION
                "The encrypted value of the seed counter for application 3 of
                this manager"
        ::= { wfSnmpMgrEntry 9 }

    wfSnmpMgrEncrSeed4 OBJECT-TYPE
        SYNTAX	INTEGER
        ACCESS	read-only
        STATUS	mandatory
        DESCRIPTION
                "The encrypted value of the seed counter for application 4 of
                this manager"
        ::= { wfSnmpMgrEntry 10 }

    wfSnmpMgrEncrSeed5 OBJECT-TYPE
        SYNTAX	INTEGER
        ACCESS	read-only
        STATUS	mandatory
        DESCRIPTION
                "The encrypted value of the seed counter for application 5 of
                this manager"
        ::= { wfSnmpMgrEntry 11 }

    wfSnmpMgrCircuitlessTrap OBJECT-TYPE
	SYNTAX  INTEGER {
		    enabled(1),
		    disabled(2)
		}
	ACCESS  read-write
	STATUS  mandatory
	DESCRIPTION
		"If enabled use the circuitless interface IP address as
		 SNMP Trap source. If disabled (default), use the outgoing
		 interface IP address as SNMP Trap source address."
	DEFVAL  { disabled }
	::= { wfSnmpMgrEntry 12 }

    wfSnmpTrapEntityTable OBJECT-TYPE
        SYNTAX	SEQUENCE OF WfSnmpTrapEntityEntry
        ACCESS	not-accessible
        STATUS	mandatory
        DESCRIPTION
                "A table of Entity Trap switches ; indexed by entity number
                and slot"
        ::= { wfSnmpGroup 5 }

    wfSnmpTrapEntityEntry OBJECT-TYPE
        SYNTAX	WfSnmpTrapEntityEntry
        ACCESS	not-accessible
        STATUS	mandatory
        DESCRIPTION
                "An Entity Trap Switch Entry"
        INDEX	{ wfSnmpTrapEntityNumber,
    		  wfSnmpTrapEntitySlot }
        ::= { wfSnmpTrapEntityTable 1 }

    WfSnmpTrapEntityEntry ::= SEQUENCE {
    	    wfSnmpTrapEntityDelete
    		INTEGER,
    	    wfSnmpTrapEntityDisable
    		INTEGER,
    	    wfSnmpTrapEntityNumber
    		INTEGER,
    	    wfSnmpTrapEntitySlot
    		INTEGER,
    	    wfSnmpTrapEntityName
    		DisplayString,
    	    wfSnmpTrapEntityFault
    		INTEGER,
    	    wfSnmpTrapEntityWarn
    		INTEGER,
    	    wfSnmpTrapEntityInfo
    		INTEGER,
    	    wfSnmpTrapEntityTrace
    		INTEGER,
    	    wfSnmpTrapEntityDebug
    		INTEGER
        }

    wfSnmpTrapEntityDelete OBJECT-TYPE
        SYNTAX	INTEGER {
    		    created(1),
    		    deleted(2)
    		}
        ACCESS	read-write
        STATUS	mandatory
        DESCRIPTION
                "A flag to indicate entity instance deletion"
        DEFVAL	{ created }
        ::= { wfSnmpTrapEntityEntry 1 }

    wfSnmpTrapEntityDisable OBJECT-TYPE
        SYNTAX	INTEGER {
    		    enabled(1),
    		    disabled(2)
    		}
        ACCESS	read-write
        STATUS	mandatory
        DESCRIPTION
                "Enable/Disable an entity's traps."
        DEFVAL	{ enabled }
        ::= { wfSnmpTrapEntityEntry 2 }

    wfSnmpTrapEntityNumber OBJECT-TYPE
        SYNTAX	INTEGER
        ACCESS	read-only
        STATUS	mandatory
        DESCRIPTION
                "Entity number"
        ::= { wfSnmpTrapEntityEntry 3 }

    wfSnmpTrapEntitySlot OBJECT-TYPE
        SYNTAX	INTEGER
        ACCESS	read-only
        STATUS	mandatory
        DESCRIPTION
                "Slot number"
        ::= { wfSnmpTrapEntityEntry 4 }

    wfSnmpTrapEntityName OBJECT-TYPE
        SYNTAX	DisplayString
        ACCESS	read-only
        STATUS	mandatory
        DESCRIPTION
                "Entity Name"
        ::= { wfSnmpTrapEntityEntry 5 }

    wfSnmpTrapEntityFault OBJECT-TYPE
        SYNTAX	INTEGER {
    		    on(1),
    		    off(2)
    		}
        ACCESS	read-write
        STATUS	mandatory
        DESCRIPTION
                "This attribute controls the entity's fault messages.
                A trap will be generated when this is turned ON."
        DEFVAL	{ off }
        ::= { wfSnmpTrapEntityEntry 6 }

    wfSnmpTrapEntityWarn OBJECT-TYPE
        SYNTAX	INTEGER {
    		    on(1),
    		    off(2)
    		}
        ACCESS	read-write
        STATUS	mandatory
        DESCRIPTION
                "This attribute controls the entity's warning messages.
                A trap will be generated when this is turned ON."
        DEFVAL	{ off }
        ::= { wfSnmpTrapEntityEntry 7 }

    wfSnmpTrapEntityInfo OBJECT-TYPE
        SYNTAX	INTEGER {
    		    on(1),
    		    off(2)
    		}
        ACCESS	read-write
        STATUS	mandatory
        DESCRIPTION
                "This attribute controls the entity's info messages.
                A trap will be generated when this is turned ON."
        DEFVAL	{ off }
        ::= { wfSnmpTrapEntityEntry 8 }

    wfSnmpTrapEntityTrace OBJECT-TYPE
        SYNTAX	INTEGER {
    		    on(1),
    		    off(2)
    		}
        ACCESS	read-write
        STATUS	mandatory
        DESCRIPTION
                "This attribute controls the entity's info messages.
                A trap will be generated when this is turned ON."
        DEFVAL	{ off }
        ::= { wfSnmpTrapEntityEntry 9 }

    wfSnmpTrapEntityDebug OBJECT-TYPE
        SYNTAX	INTEGER {
    		    on(1),
    		    off(2)
    		}
        ACCESS	read-write
        STATUS	mandatory
        DESCRIPTION
                "This attribute controls the entity's debug messages.
                A trap will be generated when this is turned ON. "
        DEFVAL	{ off }
        ::= { wfSnmpTrapEntityEntry 10 }

    wfSnmpTrapEventTable OBJECT-TYPE
        SYNTAX	SEQUENCE OF WfSnmpTrapEventEntry
        ACCESS	not-accessible
        STATUS	mandatory
        DESCRIPTION
                "A table of Event Trap switches ; indexed by entity and event
                number"
        ::= { wfSnmpGroup 6 }

    wfSnmpTrapEventEntry OBJECT-TYPE
        SYNTAX	WfSnmpTrapEventEntry
        ACCESS	not-accessible
        STATUS	mandatory
        DESCRIPTION
                "An Event Trap Switch Entry"
        INDEX	{ wfSnmpTrapEventEntity,
    		  wfSnmpTrapEventNumber }
        ::= { wfSnmpTrapEventTable 1 }

    WfSnmpTrapEventEntry ::= SEQUENCE {
    	    wfSnmpTrapEventDelete
    		INTEGER,
    	    wfSnmpTrapEventDisable
    		INTEGER,
    	    wfSnmpTrapEventEntity
    		INTEGER,
    	    wfSnmpTrapEventNumber
    		INTEGER,
    	    wfSnmpTrapEventName
    		DisplayString
        }

    wfSnmpTrapEventDelete OBJECT-TYPE
        SYNTAX	INTEGER {
    		    created(1),
    		    deleted(2)
    		}
        ACCESS	read-write
        STATUS	mandatory
        DESCRIPTION
                "Create/Delete a trap event switch."
        DEFVAL	{ created }
        ::= { wfSnmpTrapEventEntry 1 }

    wfSnmpTrapEventDisable OBJECT-TYPE
        SYNTAX	INTEGER {
    		    enabled(1),
    		    disabled(2)
    		}
        ACCESS	read-write
        STATUS	mandatory
        DESCRIPTION
                "Enable/Disable trap."
        DEFVAL	{ enabled }
        ::= { wfSnmpTrapEventEntry 2 }

    wfSnmpTrapEventEntity OBJECT-TYPE
        SYNTAX	INTEGER
        ACCESS	read-only
        STATUS	mandatory
        DESCRIPTION
                "Entity number"
        ::= { wfSnmpTrapEventEntry 3 }

    wfSnmpTrapEventNumber OBJECT-TYPE
        SYNTAX	INTEGER
        ACCESS	read-only
        STATUS	mandatory
        DESCRIPTION
                "Event number"
        ::= { wfSnmpTrapEventEntry 4 }

    wfSnmpTrapEventName OBJECT-TYPE
        SYNTAX	DisplayString
        ACCESS	read-only
        STATUS	mandatory
        DESCRIPTION
                "Entity name of event"
        ::= { wfSnmpTrapEventEntry 5 }

    wfSnmpViewTable OBJECT-TYPE
        SYNTAX  SEQUENCE OF WfSnmpViewEntry
        ACCESS  not-accessible
        STATUS  mandatory
        DESCRIPTION
                "Locally held information about the MIB views known to this
                 snmp agent."
        ::= { wfSnmpGroup 7 }

    wfSnmpViewEntry OBJECT-TYPE
        SYNTAX  WfSnmpViewEntry
        ACCESS  not-accessible
        STATUS  mandatory
        DESCRIPTION
                "Information on a particular family of view subtrees included in
                 or excluded from the view of an external management entity"
        INDEX   { wfSnmpViewIndex, wfSnmpViewSubtree }
        ::= { wfSnmpViewTable 1 }

    WfSnmpViewEntry ::= SEQUENCE {
            wfSnmpViewDelete
                INTEGER,
            wfSnmpViewIndex
                INTEGER,
            wfSnmpViewSubtree
                INTEGER,
            wfSnmpViewName
                DisplayString,
            wfSnmpViewTree
                DisplayString,
            wfSnmpViewType
                INTEGER
        }
    wfSnmpViewDelete OBJECT-TYPE
        SYNTAX  INTEGER {
                    created(1),
                    deleted(2)
                }
        ACCESS  read-write
        STATUS  mandatory
        DESCRIPTION
                "Create/Delete parameter for the view."
        DEFVAL  { created }
        ::= { wfSnmpViewEntry 1 }

    wfSnmpViewIndex OBJECT-TYPE
        SYNTAX  INTEGER
        ACCESS  read-only
        STATUS  mandatory
        DESCRIPTION
                "A unique value for each MIB view.  The value for each MIB view
                 must remain constant at least from one re-initialization of the
                 entity's network management system to the next re-initialization."
        ::= { wfSnmpViewEntry 2 }

    wfSnmpViewSubtree OBJECT-TYPE
        SYNTAX  INTEGER
        ACCESS  read-only
        STATUS  mandatory
        DESCRIPTION
                "A sequencial numeric value that makes each snmp view entry and its
                 subtree view unique."
        ::= { wfSnmpViewEntry 3 }

    wfSnmpViewName OBJECT-TYPE
        SYNTAX  DisplayString
        ACCESS  read-write
        STATUS  mandatory
        DESCRIPTION
                "Ascii name of the view"
        ::= { wfSnmpViewEntry 4 }

    wfSnmpViewTree OBJECT-TYPE
        SYNTAX  DisplayString
        ACCESS  read-write
        STATUS  mandatory
        DESCRIPTION
                "The ascii representation of the view tree. The object portion of
                 the view tree may be represented by its character name or its
                 numerical representation. The  attribute and instance portions
                 of the tree must be indentified by their numerical
                 representation."
        ::= { wfSnmpViewEntry 5 }

    wfSnmpViewType OBJECT-TYPE
        SYNTAX  INTEGER {
                    included(1),
                    excluded(2)
                }
        ACCESS  read-write
        STATUS  mandatory
        DESCRIPTION
                "The status of a particular family of view subtrees.  The value
                 `included(1)' indicates that the corresponding instances of
                 the configured mib subtree define a family of view subtrees
                 included in the MIB view.  The value `excluded(2)' indicates that
                 the corresponding instances of the configured mib subtree and
                 wfSnmpViewMask define a family of view subtrees excluded from
                 the MIB view."
	DEFVAL  { included }
        ::= { wfSnmpViewEntry 6 }

    END  -- Wellfleet-SNMP-MIB
