CXDDS-MIB DEFINITIONS ::= BEGIN


IMPORTS
   OBJECT-TYPE             FROM RFC-1212
   TRAP-TYPE               FROM RFC-1215
   DisplayString           FROM RFC1213-MIB
   cxDds,
   SapIndex,
   Alias                   FROM CXProduct-SMI;


--  Configuration Table

--  The table describing:
--      parameters used to configure each DDS slot and its associated 
--      hardware port.


ddsSlotTable OBJECT-TYPE
   SYNTAX  SEQUENCE OF DdsSlotEntry
   ACCESS  not-accessible
   STATUS  mandatory
   DESCRIPTION
"Identifies the configuration information for a specific DDS access point and 
its associated hardware port."  
   ::= { cxDds 1 }


   ddsSlotEntry OBJECT-TYPE
      SYNTAX  DdsSlotEntry
      ACCESS  not-accessible
      STATUS  mandatory
      DESCRIPTION
"Identifies the configuration information for a specific DDS access point and 
its associated hardware port."
      INDEX { ddsSlotNumber }
      ::= { ddsSlotTable 1 }


   DdsSlotEntry ::=
      SEQUENCE {
    ddsSlotNumber                        SapIndex,
    ddsSlotAlias                         Alias,
    ddsSlotRowStatus                     INTEGER,    
    ddsSlotStatus                        INTEGER,
    ddsSlotConfigLineType                INTEGER,
    ddsSlotConfigLineService             INTEGER,
    ddsSlotConfigRemLoop2LocalAddress    INTEGER,
    ddsSlotConfigRemLoop2RemoteAddress   INTEGER,
    ddsSlotConfigLoopback                INTEGER,
    ddsSlotConfigPatternGen              INTEGER,
    ddsSlotDialNumber                    DisplayString,
    ddsSlotSoftwareRevision              INTEGER,
    ddsSlotStuffingOption                INTEGER,
    ddsSlotLineQuality                   INTEGER,
    ddsSlotLineRelativeReceiveLevelMin   INTEGER,
    ddsSlotLineRelativeReceiveLevelMax   INTEGER,
    ddsSlotLineLoopback                  INTEGER,
    ddsSlotResultErtPatternDetect        INTEGER,
    ddsSlotResultPatternGen              INTEGER,
    ddsSlotResultDialing                 INTEGER,
    ddsSlotModel                         INTEGER,
    ddsSlotRevision                      INTEGER,
    ddsSlotEco                           INTEGER,
    ddsSlotLineTrap                    INTEGER,
    ddsSlotLoopTrap        INTEGER
    }


   ddsSlotNumber OBJECT-TYPE
      SYNTAX  SapIndex
      ACCESS  read-only
      STATUS  mandatory
      DESCRIPTION
"Identifies a DDS access point by a numerical value. Each DDS access point 
has a unique value."
      ::= { ddsSlotEntry 1 }

   ddsSlotAlias OBJECT-TYPE
      SYNTAX  Alias
      ACCESS  read-write
      STATUS  mandatory
      DESCRIPTION
"Assigns a textual name to the DDS access point. Each access point requires a 
unique name. You may not assign the same name twice.

Default Value: none

Range of Values: up to 12 alphanumeric characters, the first must be 
a letter.

Configuration Changed: operative"
      ::= { ddsSlotEntry 2 }

   ddsSlotRowStatus OBJECT-TYPE
      SYNTAX  INTEGER {
          invalid         (1),
          valid           (2)
          }
      ACCESS  read-write
      STATUS  mandatory
      DESCRIPTION
"Determines the status of the objects in a row.

Default Value: valid

Options: 

invalid (1): row is flagged, after next reset the values will be disabled and 
the row will be deleted from the table

valid (2): values are enabled

Configuration Changed: administrative"
      ::= { ddsSlotEntry 3 }

   ddsSlotStatus OBJECT-TYPE
      SYNTAX  INTEGER {
    dds-not-present         (1),
    dds-present             (2),
    dds-present-failed      (3)
     }
      ACCESS  read-only
      STATUS  mandatory
      DESCRIPTION
"Identifies the status of the DDS option card as present, not present or 
present but failed.

Default Value: none

Options:
dds-not-present (1)

dds-present (2)

dds-present-failed (3)"

      ::= { ddsSlotEntry 4 }

   ddsSlotConfigLineType OBJECT-TYPE
      SYNTAX  INTEGER {
    telco-point-to-point    (1),
    telco-multipt           (2),
    ldm-timing-slave        (3),
    ldm-timing-master       (4)
     }
      ACCESS  read-write
      STATUS  mandatory
      DESCRIPTION
"Assigns the DDS line configuration.

Default Value:  
telco-point-to-point (1)

Options:
telco-point-to-point (1)

telco-multipoint (2)

idm-timing-slave (3)

idm-timing-master (4)

Configuration Changed: operative"
      
DEFVAL { telco-point-to-point }
      ::= { ddsSlotEntry 5 }


   ddsSlotConfigLineService OBJECT-TYPE
      SYNTAX  INTEGER {
    clear-channel-64K    (1),
    switched-56K         (2),
    dds-56K              (3),
    dds-19200            (4),
    dds-9600             (5),
    dds-4800             (6),
    dds-2400             (7)
       }
      ACCESS  read-write
      STATUS  mandatory
      DESCRIPTION
"Assigns the DDS line service type.

Default Value:  dds-56K (2)

Range of Values: 
clear-channel-64K (1)

switched-56K (2)

dds-56K (3)

dds-19200 (4)

dds-9600 (5)

dds-4800 (6)

dds-2400 (7)

dds-1200 (8)

Configuration Changed: operative"

      DEFVAL { dds-56K }
      ::= { ddsSlotEntry 6 }

   ddsSlotConfigLoopback OBJECT-TYPE
      SYNTAX  INTEGER {
    no-loopback          (1),
    dte-loopback         (2),
    loop2                (3),
    loop3                (4),
    loop4                (5),
    remote-loop2         (6)
     }
      ACCESS  read-write
      STATUS  mandatory
      DESCRIPTION
"Specifies the DDS loopback type.

Default Value: no-loopback (1)

Range of Values: 
no-loopback (1)

dte-loopback (2)

loop2 (3),

loop3 (4),

loop4 (5)

remote-loop2 (6)

Configuration Changed: operative"
      DEFVAL { no-loopback }
      ::= { ddsSlotEntry 7 }

   ddsSlotConfigRemLoop2LocalAddress OBJECT-TYPE
      SYNTAX  INTEGER (0..255)
      ACCESS  read-write
      STATUS  mandatory
      DESCRIPTION
"Specifies the local address for V.54 remote loop2.

Default Value: none

Range of Values:  0 to 255

The 34 valid V.54 hex addresses include:

0x01, 

0x03, 0x05, 0x07, 0x09, 

0x0B,

0x0D, 0x0F, 0x11, 0x13, 0x15, 0x17,

0x19, 0x1B, 0x1D, 0x1F, 0x25, 0x27,

0x2B, 0x2D, 0x2F, 0x33, 0x35, 0x37,

0x3B, 0x3D, 0x3F, 0x55, 0x57, 0x5B,

0x5F, 0x6F, 0x77, 0x7F

Configuration Changed: operative"
      ::= { ddsSlotEntry 8 }

   ddsSlotConfigRemLoop2RemoteAddress OBJECT-TYPE
      SYNTAX  INTEGER (0..255)
      ACCESS  read-write
      STATUS  mandatory
      DESCRIPTION
"Specifies the remote address for V.54 remote loop2.

Range of Values:  0 to 255

Default Value: none

Configuration Changed: operative"
      ::= { ddsSlotEntry 9 }

   ddsSlotConfigPatternGen OBJECT-TYPE
      SYNTAX  INTEGER {
    no-pattern              (1),
    pattern-511             (2),
    pattern-511-with-errors (3)
     }
      ACCESS  read-write
      STATUS  mandatory
      DESCRIPTION
"Specifies the type of pattern generated.

Range of Values: 
no-pattern (1)

pattern-511 (2)

pattern-511-with-errors (3)

Default Value: no-pattern (1)

Configuration Changed: operative"
      DEFVAL { no-pattern }
      ::= { ddsSlotEntry 10 }

   ddsSlotDialNumber OBJECT-TYPE
      SYNTAX  DisplayString (SIZE (0..11))
      ACCESS  read-write
      STATUS  mandatory
      DESCRIPTION
"Assigns the dial number for switched56 applications.

Default Value: none

Range of Values: 12 character octet string

Configuration Changed: operative"
      ::= { ddsSlotEntry 11 }

   ddsSlotSoftwareRevision OBJECT-TYPE
      SYNTAX  INTEGER (0..255)
      ACCESS  read-only
      STATUS  mandatory
      DESCRIPTION
"Indicates the DDS firmware revision as an integer value 
from 0 to 255.

Default Value: none

Range of Values: 0-255"
      ::= { ddsSlotEntry 12 }

   ddsSlotStuffingOption OBJECT-TYPE
      SYNTAX  INTEGER {
    ccc-installed        (1),
    ccc-not-installed    (2)
       }
      ACCESS  read-only
      STATUS  mandatory
      DESCRIPTION
 "Identifies whether the clear channel chip (ccc) option (for 64K clear 
channel) is installed.

Default Value: none

Options:
ccc-installed (1)

ccc-not-installed (2)"

      ::= { ddsSlotEntry 13 }

   ddsSlotLineQuality OBJECT-TYPE
      SYNTAX  INTEGER {
    link                 (1),
    no-link              (2),
    network-error-oos    (3)
       }
      ACCESS  read-only
      STATUS  mandatory
      DESCRIPTION
"Identifies whether the link is up, if no link exists or if a network error 
(OOS - out of service) has occurred.

Default Value: none

Options:
link (1)

no-link (2)

network-error-oos (3)"
      ::= { ddsSlotEntry 14 }

   ddsSlotLineRelativeReceiveLevelMin OBJECT-TYPE
      SYNTAX  INTEGER (0..255)
      ACCESS  read-only
      STATUS  mandatory
      DESCRIPTION
"Indicates the minimum relative receive line level.

Default Value: none

Range of Values: 0-255"
      ::= { ddsSlotEntry 15 }

  
 ddsSlotLineRelativeReceiveLevelMax OBJECT-TYPE
      SYNTAX  INTEGER (0..255)
      ACCESS  read-only
      STATUS  mandatory
      DESCRIPTION
"Indicates the maximum relative receive line level.

Default Value: none

Range of Values: 0-255"

      ::= { ddsSlotEntry 16 }

 
  ddsSlotLineLoopback OBJECT-TYPE
      SYNTAX  INTEGER {
    none              (1),
    csu-loopback      (2),
    dsu-loopback      (3),
    dte-loopback      (4),
    loop2             (5),
    loop3             (6),
    loop4             (7),
    remote-loop2      (8)
       }
      ACCESS  read-only
      STATUS  mandatory
      DESCRIPTION
"Indicates the loopback status of the line.

Options:
none (1)

csu-loopback (2)

dsu-loopback (3)

dte-loopback (4)

loop2 (5)

loop3 (6)

loop4 (7)

remote-loop2 (8) 

Default Value: none (1)
"
      ::= { ddsSlotEntry 17 }

   ddsSlotResultErtPatternDetect OBJECT-TYPE
      SYNTAX  INTEGER {
   not-receiving-pattern (1),
   receiving-pattern (2),
   receiving-patt-with-errors (3)
   }
      ACCESS  read-only
      STATUS  mandatory
      DESCRIPTION
 "Identifies the reception of the 511 bit pattern or not.

Options:
not-receiving-pattern (1)

receiving-pattern (2)

receiving-patt-with-errors (3) 

Default Value: none
"
      
::= { ddsSlotEntry 18 }


   ddsSlotResultPatternGen OBJECT-TYPE
      SYNTAX  INTEGER {
    no-pattern        (1),
    ert-pattern       (2),
    ert-with-errors   (3)
       }
      ACCESS  read-only
      STATUS  mandatory
      DESCRIPTION
"Identifies what type of pattern the DDS is generating on the line.

Options:
no-pattern (1)

ert-pattern (2)

ert-with-errors (3) 

Default: none
"
      ::= { ddsSlotEntry 19 }

   ddsSlotResultDialing OBJECT-TYPE
      SYNTAX  INTEGER {
    dialing-idle             (1),
    dialing-now              (2),
    connection-made          (3),
    err-no-num-from-host    (4),
    err-no-link             (5),
    err-no-rx-idle          (6),
    err-no-wink             (7),
    err-invalid-wink        (8),
    err-no-answer           (9)
       }
      ACCESS  read-only
      STATUS  mandatory
      DESCRIPTION
"Indicates the dialing result codes for switched56 service as: dialing, 
connection made, the connection is not switched56, that a number has not been 
supplied by the host, no link available, no wink available, wink invalid or 
no answer.

Options:
dialing-idle (1)

dialing-now (2)

connection-made (3)

err-no-num-from-host (4)

err-no-link (5)

err-no-rx-idle (6)

err-no-wink (7)

err-invalid-wink (8)

err-no-answer (9)

Default Value: none " 

      ::= { ddsSlotEntry 20 }
      
   ddsSlotModel OBJECT-TYPE
      SYNTAX  INTEGER (0..7)
      ACCESS  read-only
      STATUS  mandatory
      DESCRIPTION
 "Indicates the Printed Circuit Board (PCB) model number .

Range of Values: 0-7

Default: none"
      ::= { ddsSlotEntry 21 }

   
ddsSlotRevision OBJECT-TYPE
      SYNTAX  INTEGER (0..15)
      ACCESS  read-only
      STATUS  mandatory
      DESCRIPTION
"Indicates the PCB revision level.

Range of Values: 0-15 

Default Value: none"
      ::= { ddsSlotEntry 22 }

   ddsSlotEco OBJECT-TYPE
      SYNTAX  INTEGER (0..15)
      ACCESS  read-only
      STATUS  mandatory
      DESCRIPTION
"Indicates the PCB Engineering Change Order (ECO) level.

Range of Values: 0-15

Default Value: none "
      ::= { ddsSlotEntry 23 }

   
ddsSlotLineTrap OBJECT-TYPE
      SYNTAX  INTEGER {
          disabled        (1),
          enabled (2)
          }
      ACCESS  read-write
      STATUS  mandatory
      DESCRIPTION
"Determines the status of the line trap.

Options:
disabled (1)

enabled (2)

Default Value: disabled (1)

Configuration Changed: operative"

      DEFVAL { disabled }
      ::= { ddsSlotEntry 24 }

   ddsSlotLoopTrap OBJECT-TYPE
      SYNTAX  INTEGER {
          disabled        (1),
          enabled (2)
          }
      ACCESS  read-write
      STATUS  mandatory
      DESCRIPTION
"Determines the status of the loopback change trap.

Range of Values:
disabled (1)

enabled (2)

Default Value: disabled (1)

Configuration Changed: operative"
      DEFVAL { disabled }
      ::= { ddsSlotEntry 25 }

-- Service access point related traps

ddsSlotLineStatusChange TRAP-TYPE
   ENTERPRISE      cxDds
   VARIABLES               {       ddsSlotNumber,
          ddsSlotLineQuality
       }
   DESCRIPTION
"Indicates that an alarm has occurred. The line quality currently in use at 
 the DDS access point has changed state to any of the states defined in 
object ddsSlotLineQuality."
   ::= 1

ddsSlotLoopStatusChange TRAP-TYPE
   ENTERPRISE      cxDds
   VARIABLES               {       ddsSlotNumber,
          ddsSlotLineLoopback
       }
   DESCRIPTION
"Indicates an alarm status has occurred. The loopback status currently in use 
at the DDS access point has changed state to any of the states defined in 
object ddsSlotLineLoopback."
   ::= 2

END
