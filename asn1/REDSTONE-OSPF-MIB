-- *****************************************************************
-- REDSTONE-OSPF-MIB
--
-- Redstone Communications Inc. Enterprise MIB
-- Extensions for OSPF Protocol Management
--
-- Copyright 1998 Redstone Communications, Incorporated.
-- All Rights Reserved.
-- *****************************************************************

REDSTONE-OSPF-MIB DEFINITIONS ::= BEGIN

IMPORTS
	MODULE-IDENTITY,
	OBJECT-TYPE,
    Integer32
		FROM SNMPv2-SMI

    MODULE-COMPLIANCE,
    OBJECT-GROUP
        FROM SNMPv2-CONF

    ospfIfEntry
        FROM OSPF-MIB

	rsMgmt
		FROM REDSTONE-SMI;


rsOspfMIB  MODULE-IDENTITY
	LAST-UPDATED "9801010000Z"
	ORGANIZATION "Redstone Communications, Inc."
	CONTACT-INFO
        "
        Redstone Communications, Inc.
		5 Carlisle Road
        Westford MA 01886
        USA

        Tel:    +1-978-692-1999
		Email:  mib@redstonecom.com
        "
	DESCRIPTION
		"The OSPF Protocol MIB for the 
		Redstone Communications Inc. enterprise."
	REVISION      "9801010000Z"
	DESCRIPTION
		"Initial version of this MIB module."
	::= { rsMgmt 14 }



-- ++++++++++++++++++++++++++++++++++++++++++++++++++++++++++++++++++++++
-- Textual conventions
-- ++++++++++++++++++++++++++++++++++++++++++++++++++++++++++++++++++++++

-- No textual conventions are defined in this MIB.



-- ++++++++++++++++++++++++++++++++++++++++++++++++++++++++++++++++++++++
-- Managed objects
-- ++++++++++++++++++++++++++++++++++++++++++++++++++++++++++++++++++++++

rsOspfObjects       OBJECT IDENTIFIER ::= { rsOspfMIB 1 }

-- +++++++++++++++++++++++++++++++++++++++++++++++++++++++++++++++++++++++++++++
-- OSPF General Group attributes (scalars)
-- +++++++++++++++++++++++++++++++++++++++++++++++++++++++++++++++++++++++++++++

rsOspfGeneralGroup  OBJECT IDENTIFIER ::= { rsOspfObjects 1 }

rsOspfProcessId OBJECT-TYPE
    SYNTAX      Integer32 (0..65535)
    MAX-ACCESS  read-write
    STATUS      current
    DESCRIPTION
        "An identifier having special semantics when set.

        When this object's value is zero, OSPF is disabled
        and cannot be configured. Setting this object to a 
        nonzero value enables OSPF operation and permits
        further OSPF configuration to be performed.

        When this object's value is nonzero, setting it to a
        value of zero disables OSPF operation and clears
        all existing OSPF configuration.

        Once set to a nonzero value, this object cannot be
        set to a different nonzero value without first setting
        it to zero.

        (This MIB object mimics the behavior of the OSPF 'process ID' 
        parameter used through the command-line interface.)"
    ::= { rsOspfGeneralGroup 1 }

rsOspfMaxPathSplits OBJECT-TYPE
    SYNTAX      Integer32 (1..16)
    MAX-ACCESS  read-write
    STATUS      current
    DESCRIPTION
        "The maximum number of equal-cost routes that will be maintained
        by the OSPF protocol.

        A change in this value will be taken into account at the
        next shortest-path-first recalculation."
    ::= { rsOspfGeneralGroup 2 }

rsOspfSpfHoldInterval OBJECT-TYPE
    SYNTAX      Integer32 (1..5)
    UNITS       "seconds"
    MAX-ACCESS  read-write
    STATUS      current
    DESCRIPTION
        "The minimum amount of time that must elapse between 
        shortest-path-first recalculations.

        Reducing this value can cause an immediate SPF 
        recalulation if the new value is less than the
        current value of rsOspfSpfHoldTimeRemaining and
        other SPF-inducing protocol events have occurred."
    ::= { rsOspfGeneralGroup 3 }


-- +++++++++++++++++++++++++++++++++++++++++++++++++++++++++++++++++++++++++++++
-- OSPF Interface attributes
-- +++++++++++++++++++++++++++++++++++++++++++++++++++++++++++++++++++++++++++++

--
--  OSPF Interface Table
--

rsOspfIfTable OBJECT-TYPE
    SYNTAX      SEQUENCE OF RsOspfIfEntry
    MAX-ACCESS  not-accessible
    STATUS      current
    DESCRIPTION
        "The Redstone OSPF Interface Table describes the
        OSPF-specific characteristics of interfaces."
    ::= { rsOspfObjects 2 }


rsOspfIfEntry OBJECT-TYPE
    SYNTAX      RsOspfIfEntry
    MAX-ACCESS  not-accessible
    STATUS      current
    DESCRIPTION
        "The OSPF Interface Entry describes OSPF-specific
        characteristics of one interface."
    AUGMENTS { ospfIfEntry }
    ::= { rsOspfIfTable 1 }

RsOspfIfEntry ::= SEQUENCE {
    rsOspfIfCost
        Integer32
    }

rsOspfIfCost OBJECT-TYPE
    SYNTAX      Integer32 (1..65535)
    MAX-ACCESS  read-create
    STATUS      current
    DESCRIPTION
        "The cost value for this interface."
    DEFVAL  { 10 }
    ::= { rsOspfIfEntry 1 }


-- ++++++++++++++++++++++++++++++++++++++++++++++++++++++++++++++++++++++
-- Notification control 
-- ++++++++++++++++++++++++++++++++++++++++++++++++++++++++++++++++++++++

-- No notifications are defined in this MIB. Placeholders follow.

--rsOspfTrapEnables OBJECT IDENTIFIER ::= { rsOspfMIB 2 }


-- ++++++++++++++++++++++++++++++++++++++++++++++++++++++++++++++++++++++
-- Notifications
-- ++++++++++++++++++++++++++++++++++++++++++++++++++++++++++++++++++++++

-- No notifications are defined in this MIB. Placeholders follow.

-- The following two OBJECT IDENTIFIERS are used to define SNMPv2 
-- Notifications that are easily translated into SNMPv1 Traps.

-- rsOspfTraps       OBJECT IDENTIFIER ::= { rsOspfMIB 3 }
-- rsOspfTrapPrefix  OBJECT IDENTIFIER ::= { rsOspfTraps 0 }


-- ++++++++++++++++++++++++++++++++++++++++++++++++++++++++++++++++++++++
-- Conformance information
-- ++++++++++++++++++++++++++++++++++++++++++++++++++++++++++++++++++++++

rsOspfConformance     OBJECT IDENTIFIER ::= { rsOspfMIB 4 }
rsOspfCompliances     OBJECT IDENTIFIER ::= { rsOspfConformance 1 }
rsOspfGroups          OBJECT IDENTIFIER ::= { rsOspfConformance 2 }

-- compliance statements

rsOspfCompliance MODULE-COMPLIANCE
    STATUS      current
    DESCRIPTION
        "The compliance statement for entities which implement
        the Redstone OSPF MIB."
    MODULE  -- this module
        MANDATORY-GROUPS { rsOspfBasicGroup, rsOspfIfGroup }
    ::= { rsOspfCompliances 1 }

-- units of conformance

rsOspfBasicGroup OBJECT-GROUP
    OBJECTS {
        rsOspfProcessId,
        rsOspfMaxPathSplits,
        rsOspfSpfHoldInterval
	}
	STATUS      current
	DESCRIPTION
		"A collection of objects for managing general OSPF
		capabilities in a Redstone product."
    ::= { rsOspfGroups 1 }

rsOspfIfGroup OBJECT-GROUP
    OBJECTS {
        rsOspfIfCost
    }
	STATUS  current
	DESCRIPTION
		"A collection of objects for managing OSPF Interface
		capabilities in a Redstone product."
    ::= { rsOspfGroups 2 }

END
