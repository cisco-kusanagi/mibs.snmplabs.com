-->#
--># Copyright (C) Siemens AG 1998
-->#               All rights reserved
-->#
-->#protocol specification
-->%PROTOCOL SNMP
-->#
-->#configuration
-->%REMCONFIG NO
-->%REMOPERATION NO
-->#
 
UTM-MIB DEFINITIONS ::= BEGIN
--  MIB-Version: 3
 
--
-- Title:   MIB for UTM V3.3 (and above)
--
-- Version: 3
-- Date:    Feb. 1998
-- Author:  Birgit Lamers        BS2000 DC3
-- Reason:  Access of utmMainApplHomeDir is set to 'read-only'
--
-- Version: 2
-- Date:    Dez. 1997
-- Author:  Birgit Lamers        BS2000 DC3
-- Reason:  New values for PtermConnected, TacStatus and  ConConnected
--          due to UTM V4.0
--
-- Date:    since March 1996
-- Author:  Birgit Lamers        BS2000 OS45
--          Manfred Mayr         MR PD 43
--                
 
 IMPORTS
        Gauge, enterprises     FROM RFC1155-SMI
        DisplayString   FROM RFC1213-MIB
        OBJECT-TYPE     FROM RFC-1212
      DateAndTime     FROM SNMPv2-TC
		TRAP-TYPE FROM RFC-1215;
 
--      copied from RFC1514:
--   DateAndTime ::= OCTET STRING (SIZE (8 | 11))
   --        A date-time specification for the local time of day.
   --        This data type is intended to provide a consistent
   --        method of reporting date information.
   --
   --            field  octets  contents                  range
   --            _____  ______  ________                  _____
   --              1      1-2   year                      0..65536
   --                           (in network byte order)
   --              2       3    month                     1..12
   --              3       4    day                       1..31
   --              4       5    hour                      0..23
   --              5       6    minutes                   0..59
   --              6       7    seconds                   0..60
   --                           (use 60 for leap-second)
   --              7       8    deci-seconds              0..9
   --              8       9    direction from UTC        "+" / "-"
   --                           (in ascii notation)
   --              9      10    hours from UTC            0..11
   --             10      11    minutes from UTC          0..59
   --
   --            Note that if only local time is known, then
   --            timezone information (fields 8-10) is not present.
 
 
sni                 OBJECT IDENTIFIER ::= { enterprises 231 }
sniProductMibs      OBJECT IDENTIFIER ::= { sni 2 }
sniUTM              OBJECT IDENTIFIER ::= { sniProductMibs 19 }
 
 
-- UTM  Application Table  ( Names of all applications)
--
 
 
 
-- begin of objects for UNIX
utmApplTabNum                 OBJECT-TYPE
        SYNTAX  INTEGER
        ACCESS  read-only
        STATUS  mandatory
        DESCRIPTION "The number of entries in the table utmApplTable"
        ::= {sniUTM 1}
 
utmApplTable           OBJECT-TYPE
        SYNTAX  SEQUENCE OF UtmApplEntry
        ACCESS  not-accessible
        STATUS  mandatory
        DESCRIPTION "Table of UTM applications"
        ::= {sniUTM 2}
 
utmApplEntry        OBJECT-TYPE
        SYNTAX  UtmApplEntry
        ACCESS  not-accessible
        STATUS  mandatory
        DESCRIPTION "An entry in the table"
	INDEX {utmApplIndex}
	::= {utmApplTable 1}
 
UtmApplEntry ::=
        SEQUENCE 
        {
            utmApplIndex                INTEGER,
            utmApplName                 DisplayString,
            utmApplStatus               INTEGER,
            utmApplSharedMemKey         Gauge,
            utmApplSharedMemSegSize     Gauge,
            utmApplSemId                Gauge,
            utmApplHomeDir              DisplayString
        }
 
utmApplIndex   OBJECT-TYPE
        SYNTAX  INTEGER
        ACCESS  read-only
        STATUS  mandatory
        DESCRIPTION "A unique value for each entry, its value
                     ranges between 1 and the value of utmApplTabNum"
        ::= {utmApplEntry 1}
 
utmApplName      OBJECT-TYPE
        SYNTAX  DisplayString
        ACCESS  read-only
        STATUS  mandatory
        DESCRIPTION "Name of the UTM application"
        ::= {utmApplEntry 2}
 
utmApplStatus    OBJECT-TYPE
        SYNTAX  INTEGER {
                          up   (1),
                          down (2)
                        }
        ACCESS  read-only
        STATUS  mandatory
        DESCRIPTION "Status of the UTM application is either up or down"
        ::= {utmApplEntry 3}
 
utmApplSharedMemKey      OBJECT-TYPE
        SYNTAX  Gauge
        ACCESS  read-only
        STATUS  mandatory
        DESCRIPTION "Shared memory key of the UTM application"
        ::= {utmApplEntry 4}
 
utmApplSharedMemSegSize      OBJECT-TYPE
        SYNTAX  Gauge
        ACCESS  read-only
        STATUS  mandatory
        DESCRIPTION "Size of the shared memory segement of the UTM application"
        ::= {utmApplEntry 5}
 
utmApplSemId      OBJECT-TYPE
        SYNTAX  Gauge
        ACCESS  read-only
        STATUS  mandatory
        DESCRIPTION "Semaphore ID number of the UTM application"
        ::= {utmApplEntry 6}
 
utmApplHomeDir      OBJECT-TYPE
        SYNTAX  DisplayString
        ACCESS  read-only
        STATUS  mandatory
        DESCRIPTION "Home directory of the UTM application"
        ::= {utmApplEntry 7}
-- end of objects for UNIX
 
 
 
 
-- UTM  Application Data
--
 
utmApplicationData            OBJECT IDENTIFIER ::= { sniUTM 3 }
 
utmMainData         OBJECT IDENTIFIER ::= { utmApplicationData  1 }
utmStatData         OBJECT IDENTIFIER ::= { utmApplicationData  2 }
utmSyspData         OBJECT IDENTIFIER ::= { utmApplicationData  3 }
utmPtermData        OBJECT IDENTIFIER ::= { utmApplicationData  4 }
utmLtermData        OBJECT IDENTIFIER ::= { utmApplicationData  5 }
utmTacData          OBJECT IDENTIFIER ::= { utmApplicationData  6 }
utmTacclassData     OBJECT IDENTIFIER ::= { utmApplicationData  7 }
utmUserData         OBJECT IDENTIFIER ::= { utmApplicationData  8 }
utmConData          OBJECT IDENTIFIER ::= { utmApplicationData  9 }
utmLpapData         OBJECT IDENTIFIER ::= { utmApplicationData 10 }
utmPoolData         OBJECT IDENTIFIER ::= { utmApplicationData 11 }
utmLsesData         OBJECT IDENTIFIER ::= { utmApplicationData 12 }
utmLtacData         OBJECT IDENTIFIER ::= { utmApplicationData 13 }
utmOsiAssData       OBJECT IDENTIFIER ::= { utmApplicationData 14 }
utmOsiConData       OBJECT IDENTIFIER ::= { utmApplicationData 15 }
utmOsiLpapData      OBJECT IDENTIFIER ::= { utmApplicationData 16 }
utmMiscData         OBJECT IDENTIFIER ::= { utmApplicationData 17 }
 
 
 
-----------------------------------------------
-- main application data
-----------------------------------------------
 
 
utmMainApplName      OBJECT-TYPE
        SYNTAX  DisplayString
        ACCESS  read-write
        STATUS  mandatory
        DESCRIPTION "Name of the selected UTM application"
	::= {utmMainData 1}
 
utmMainBCAMAppl      OBJECT-TYPE
        SYNTAX  DisplayString
        ACCESS  read-write
        STATUS  mandatory
        DESCRIPTION "BCAM application name of the selected UTM application"
        ::= {utmMainData 2}
 
utmMainUTMversion     OBJECT-TYPE
        SYNTAX  DisplayString
        ACCESS  read-only
        STATUS  mandatory
        DESCRIPTION "UTM version"
        ::= {utmMainData  3}
 
utmMainApplStartStop     OBJECT-TYPE
        SYNTAX  INTEGER {
                          start       (1),
                          stop        (2),
                          undefined (255)
                        }
        ACCESS  read-write
        STATUS  mandatory
        DESCRIPTION "Reading: status of selected UTM application;
                     writing: start (START) or terminate (STOP)
                              selected UTM application"
        ::= {utmMainData  4}
 
-- begin of objects for UNIX
utmMainApplHomeDir    OBJECT-TYPE
        SYNTAX  DisplayString
	ACCESS  read-only
        STATUS  mandatory
        DESCRIPTION "Home directory of the selected application"
        ::= {utmMainData 5}
-- end of objects for UNIX
 
utmMainSubagentVersion    OBJECT-TYPE
        SYNTAX  DisplayString
        ACCESS  read-only
        STATUS  mandatory
        DESCRIPTION "Version number of the SNMP subagent and the
                     type of operating system"
        ::= {utmMainData 6}
 
 
-----------------------------------------------
-- Output of the command KDCINF STATISTICS
-----------------------------------------------
 
utmStatStartDateAndTime OBJECT-TYPE
        SYNTAX  DateAndTime
        ACCESS  read-only
        STATUS  mandatory
        DESCRIPTION "Date and time of the last cold start of the application"
        ::= {utmStatData  1}
 
utmStatStartDateAndTimeString OBJECT-TYPE
        SYNTAX  DisplayString
        ACCESS  read-only
        STATUS  mandatory
        DESCRIPTION "Date and time of the last cold start of the application"
        ::= {utmStatData  2}
 
utmStatTermInMsgs   OBJECT-TYPE
        SYNTAX  INTEGER
        ACCESS  read-only
        STATUS  mandatory
        DESCRIPTION "Number of messages entered on all terminals since the
                     completion of the last hour"
        ::= {utmStatData  3}
 
utmStatTermOutMsgs  OBJECT-TYPE
        SYNTAX  INTEGER
        ACCESS  read-only
        STATUS  mandatory
        DESCRIPTION "Number of messages issued on all terminals since the
                     completion of the last hour"
        ::= {utmStatData  4}
 
utmStatCurrTasks    OBJECT-TYPE
        SYNTAX  INTEGER
        ACCESS  read-only
        STATUS  mandatory
        DESCRIPTION "Number of current tasks in this application"
        ::= {utmStatData  5}
 
utmStatConnUsers    OBJECT-TYPE
        SYNTAX  INTEGER
        ACCESS  read-only
        STATUS  mandatory
        DESCRIPTION "Number of connected users"
        ::= {utmStatData  6}
 
utmStatOpenDialConv  OBJECT-TYPE
        SYNTAX  INTEGER
        ACCESS  read-only
        STATUS  mandatory
        DESCRIPTION "Number of active dialog conversations "
        ::= {utmStatData  7}
 
utmStatOpenAsynConv OBJECT-TYPE
        SYNTAX  INTEGER
        ACCESS  read-only
        STATUS  mandatory
        DESCRIPTION "Number of active asynchronous conversations "
        ::= {utmStatData  8}
 
utmStatDialTAperSec OBJECT-TYPE
        SYNTAX  Gauge
        ACCESS  read-only
        STATUS  mandatory
        DESCRIPTION "Number of dialog transactions per second"
        ::= {utmStatData  9}
 
utmStatAsynTAperSec OBJECT-TYPE
        SYNTAX  Gauge
        ACCESS  read-only
        STATUS  mandatory
        DESCRIPTION "Number of asynchronous transactions per second"
        ::= {utmStatData  10}
 
utmStatDialStepSec  OBJECT-TYPE
        SYNTAX  Gauge
        ACCESS  read-only
        STATUS  mandatory
        DESCRIPTION "Number of dialog steps per second"
        ::= {utmStatData  11}
 
utmStatMaxPoolSize  OBJECT-TYPE
        SYNTAX  Gauge
        ACCESS  read-only
        STATUS  mandatory
        DESCRIPTION "Maximum occupancy of the pagepool in percent"
        ::= {utmStatData  12}
 
utmStatActPoolSize  OBJECT-TYPE
        SYNTAX  Gauge
        ACCESS  read-only
        STATUS  mandatory
        DESCRIPTION "Current occupancy of the pagepool in percent"
        ::= {utmStatData  13}
 
utmStatAvgPoolSize  OBJECT-TYPE
        SYNTAX  Gauge
        ACCESS  read-only
        STATUS  mandatory
        DESCRIPTION "Average occupancy of the pagepool in percent"
        ::= {utmStatData  14}
 
utmStatCacheHitRate OBJECT-TYPE
        SYNTAX  Gauge
        ACCESS  read-only
        STATUS  mandatory
        DESCRIPTION "Hit rate in percent when searching a cache page "
        ::= {utmStatData  15}
 
utmStatCacheWaits   OBJECT-TYPE
        SYNTAX  Gauge
        ACCESS  read-only
        STATUS  mandatory
        DESCRIPTION "Percentage of cache buffer requests leading to a
                     waiting time"
        ::= {utmStatData  16}
 
utmStatUnprocAtacs  OBJECT-TYPE
        SYNTAX  INTEGER
        ACCESS  read-only
        STATUS  mandatory
        DESCRIPTION "Number of asynchronous transaction jobs, which are not
                     yet processed"
        ::= {utmStatData  17}
 
utmStatUnprocPrints OBJECT-TYPE
        SYNTAX  INTEGER
        ACCESS  read-only
        STATUS  mandatory
        DESCRIPTION "Number of waiting print jobs"
        ::= {utmStatData  18}
 
utmStatWaitDPUTs    OBJECT-TYPE
        SYNTAX  INTEGER
        ACCESS  read-only
        STATUS  mandatory
        DESCRIPTION "Number of pending time driven jobs"
        ::= {utmStatData  19}
 
utmStatAbTermConv   OBJECT-TYPE
        SYNTAX  INTEGER
        ACCESS  read-only
        STATUS  mandatory
        DESCRIPTION "Number of abnormally terminated conversations"
        ::= {utmStatData  20}
 
utmStatResourcWaits OBJECT-TYPE
        SYNTAX  Gauge
        ACCESS  read-only
        STATUS  mandatory
        DESCRIPTION "Relation (per mille) between the number of resources
                     requests with waiting and the total number of
                     resources requests"
        ::= {utmStatData  21}
 
utmStatDeadlocks    OBJECT-TYPE
        SYNTAX  INTEGER
        ACCESS  read-only
        STATUS  mandatory
        DESCRIPTION "Number of recognized and removed deadlocks"
        ::= {utmStatData  22}
 
utmStatPeriodWrites OBJECT-TYPE
        SYNTAX  INTEGER
        ACCESS  read-only
        STATUS  mandatory
        DESCRIPTION "Number of periodic writes"
        ::= {utmStatData  23}
 
utmStatPagesPWrite  OBJECT-TYPE
        SYNTAX  INTEGER
        ACCESS  read-only
        STATUS  mandatory
        DESCRIPTION "Number of 2 KB pages being averagely saved by a
                     periodic write"
        ::= {utmStatData  24}
 
utmStatLogWrites    OBJECT-TYPE
        SYNTAX  INTEGER
        ACCESS  read-only
        STATUS  mandatory
        DESCRIPTION "Number of write jobs to the user log file since the
                     completion of the last hour"
        ::= {utmStatData  25}
 
utmStatActJR        OBJECT-TYPE
SYNTAX  INTEGER
        ACCESS  read-only
        STATUS  mandatory
        DESCRIPTION "Current number of job receiving conversations, which
                     are addressed at the same time"
        ::= {utmStatData  26}
 
utmStatMaxJR        OBJECT-TYPE
        SYNTAX  INTEGER
        ACCESS  read-only
        STATUS  mandatory
        DESCRIPTION "Maximum number of job receiving conversations,
                     which have been addressed at the same time since
                     KDCDEF generation"
        ::= {utmStatData  27}
 
-----------------------------------------------
-- Output of the command KDCINF SYSPARM
-----------------------------------------------
 
-- begin of objects for BS2000
 
utmSyspAccount      OBJECT-TYPE
        SYNTAX  INTEGER   {
                            on  (1),
                            off (2)
                           }
        ACCESS  read-write
        STATUS  mandatory
        DESCRIPTION "UTM accounting is either activated (ON) or not
                     activated (OFF)"
        ::= {utmSyspData  1}
 
utmSyspCalcAccount  OBJECT-TYPE
        SYNTAX  INTEGER   {
                            on  (1),
                            off (2)
                           }
        ACCESS  read-write
        STATUS  mandatory
        DESCRIPTION "The calculation phase of UTM accounting is either
                     activated (ON) or not activated (OFF)"
        ::= {utmSyspData  2}
 
utmSyspSM2          OBJECT-TYPE
        SYNTAX  INTEGER   {
                            on  (1),
                            off (2)
                           }
        ACCESS  read-write
        STATUS  mandatory
        DESCRIPTION "The delivery of data to SM2 is either activated (ON)
                     or not activated (OFF)"
        ::= {utmSyspData  3}
 
utmSyspKDCMON       OBJECT-TYPE
        SYNTAX  INTEGER   {
                            on  (1),
                            off (2)
                           }
        ACCESS  read-write
        STATUS  mandatory
        DESCRIPTION "KDCMON is either activated (ON) or not activated (OFF)"
        ::= {utmSyspData  4}
 
-- end of objects for BS2000
 
 
 
 
utmSyspTestmode     OBJECT-TYPE
        SYNTAX  INTEGER   {
                            on  (1),
                            off (2)
                           }
        ACCESS  read-write
        STATUS  mandatory
        DESCRIPTION "Test mode is either activated (ON) or not
                     activated (OFF)"
        ::= {utmSyspData  5}
 
utmSyspMaxPagRate   OBJECT-TYPE
        SYNTAX  Gauge
        ACCESS  read-write
        STATUS  mandatory
        DESCRIPTION "Percentage of cache pages which are to be written
                     to KDCFILE in case of a bottleneck"
        ::= {utmSyspData  6}
 
utmSyspProgFGG      OBJECT-TYPE
        SYNTAX  INTEGER
        ACCESS  read-write
        STATUS  mandatory
        DESCRIPTION "read:  Number of the current file generation of
                            the program
                     write: -1 => old (load lower program generation)
                            +1 => new (load higher program generation)"
        ::= {utmSyspData  7}
 
utmSyspTermWait     OBJECT-TYPE
        SYNTAX  INTEGER
        ACCESS  read-write
        STATUS  mandatory
        DESCRIPTION "Maximum elapse time (seconds) between terminal output
                     and the following input of the terminal user during a
                     multi step conversation"
        ::= {utmSyspData  8}
 
utmSyspUsLogFGG     OBJECT-TYPE
        SYNTAX  INTEGER
        ACCESS  read-write
        STATUS  mandatory
        DESCRIPTION "Number of the current file generation of the user
                     log file"
        ::= {utmSyspData  9}
 
utmSyspResWaitTA    OBJECT-TYPE
        SYNTAX  INTEGER
        ACCESS  read-write
        STATUS  mandatory
        DESCRIPTION "Maximum waiting time in seconds for a resource locked
                     by another transaction"
        ::= {utmSyspData  10}
 
utmSyspMaxTasks     OBJECT-TYPE
        SYNTAX  INTEGER
        ACCESS  read-write
        STATUS  mandatory
        DESCRIPTION "Maximum number of tasks which are allowed in this
                     application"
        ::= {utmSyspData  11}
 
utmSyspResWaitPr    OBJECT-TYPE
        SYNTAX  INTEGER
        ACCESS  read-write
        STATUS  mandatory
        DESCRIPTION "Maximum waiting time in seconds for a resource locked
                     by another process"
        ::= {utmSyspData  12}
 
utmSyspCurrTasks    OBJECT-TYPE
        SYNTAX  INTEGER
        ACCESS  read-only
        STATUS  mandatory
        DESCRIPTION "Number of current work processes of the application"
        ::= {utmSyspData  13}
 
utmSyspConRTime     OBJECT-TYPE
        SYNTAX  INTEGER
        ACCESS  read-write
        STATUS  mandatory
        DESCRIPTION "Cycle in minutes, in which UTM retries to create a
             logical connection"
        ::= {utmSyspData  14}
 
utmSyspMaxAsynTasks OBJECT-TYPE
        SYNTAX  INTEGER
        ACCESS  read-write
        STATUS  mandatory
        DESCRIPTION "Maximum number of tasks for asynchronous programs"
        ::= {utmSyspData  15}
 
 
-- begin of objects for BS2000
utmSyspLogAckwait   OBJECT-TYPE
        SYNTAX  INTEGER
        ACCESS  read-only
        STATUS  mandatory
        DESCRIPTION "Maximum waiting time in seconds for a print or transport
                     acknowledgement"
        ::= {utmSyspData  16}
-- end of objects for BS2000
 
 
utmSyspPTCTime      OBJECT-TYPE
        SYNTAX  INTEGER
        ACCESS  read-write
        STATUS  mandatory
        DESCRIPTION "Maximum waiting time in seconds of a job receiving
                     conversation in PTC for acknowledgement"
        ::= {utmSyspData  17}
 
utmSyspConcTime     OBJECT-TYPE
        SYNTAX  INTEGER
        ACCESS  read-write
        STATUS  mandatory
        DESCRIPTION "Time in seconds permitted for creation of a session or
                     an association"
        ::= {utmSyspData  18}
 
utmSyspPGWTTime     OBJECT-TYPE
        SYNTAX  INTEGER
        ACCESS  read-write
        STATUS  mandatory
        DESCRIPTION "Maximum time in seconds permitted for the
                     KDCS call PGWT"
        ::= {utmSyspData  19}
 
utmSyspTasksWaitPGWT  OBJECT-TYPE
        SYNTAX  INTEGER
        ACCESS  read-only
        STATUS  mandatory
        DESCRIPTION "Current number of tasks being in a wait state by a
                     PGWT call"
        ::= {utmSyspData  20}
 
utmSyspTasksinPGWT  OBJECT-TYPE
        SYNTAX  INTEGER
        ACCESS  read-write
        STATUS  mandatory
        DESCRIPTION "Maximum number of task for PGWT calls"
        ::= {utmSyspData  21}
 
-----------------------------------------------
-- Output of the command KDCINF PTERM
-----------------------------------------------
 
utmPtermTabNum    OBJECT-TYPE
        SYNTAX  INTEGER
        ACCESS  read-only
        STATUS  mandatory
        DESCRIPTION "The number of entries in the table utmPtermTable"
        ::= {utmPtermData  1}
 
utmPtermTable   OBJECT-TYPE
        SYNTAX  SEQUENCE OF UtmPtermEntry
        ACCESS  not-accessible
        STATUS  mandatory
        DESCRIPTION "Table of all physical terminals"
        ::= {utmPtermData  2}
 
utmPtermEntry   OBJECT-TYPE
        SYNTAX  UtmPtermEntry
        ACCESS  not-accessible
        STATUS  mandatory
        DESCRIPTION "An entry in the table"
        INDEX {utmPtermIndex}
        ::= {utmPtermTable 1}
 
UtmPtermEntry ::=
        SEQUENCE
        {
          utmPtermIndex         INTEGER,
          utmPtermName          DisplayString,
          utmPtermProname       DisplayString,
          utmPtermLterm         DisplayString,
          utmPtermBCAMAppl      DisplayString,
          utmPtermPtyp          DisplayString,
          utmPtermStatus        INTEGER, 
          utmPtermConnected     INTEGER,
          utmPtermConnectStatus INTEGER,
 
 
-- begin of objects for BS2000
          utmPtermConnectForced INTEGER,
          utmPtermConnectMultiplexed INTEGER,
-- end of objects for BS2000
 
 
          utmPtermConTime       INTEGER,
          utmPtermLett          INTEGER,
          utmPtermConb          INTEGER
        }
 
utmPtermIndex   OBJECT-TYPE
        SYNTAX  INTEGER
        ACCESS  read-only
        STATUS  mandatory
        DESCRIPTION "A unique value for each entry, its value
                     ranges between 1 and the value of utmPtermTabNum"
        ::= {utmPtermEntry 1}
 
utmPtermName   OBJECT-TYPE
        SYNTAX  DisplayString
        ACCESS  read-only
        STATUS  mandatory
        DESCRIPTION "Name of the chosen physical terminal"
        ::= {utmPtermEntry 2}
 
utmPtermProname   OBJECT-TYPE
        SYNTAX  DisplayString
        ACCESS  read-write
        STATUS  mandatory
        DESCRIPTION "Processor name of the physical terminal (or blank
                     for local devices)"
        ::= {utmPtermEntry 3}
 
utmPtermLterm   OBJECT-TYPE
        SYNTAX  DisplayString
        ACCESS  read-write
        STATUS  mandatory
        DESCRIPTION "Name of the logical UTM terminal that belongs to
                     the physical terminal"
        ::= {utmPtermEntry 4}
 
utmPtermBCAMAppl   OBJECT-TYPE
        SYNTAX  DisplayString
        ACCESS  read-write
        STATUS  mandatory
        DESCRIPTION "BCAM name of the UTM application"
        ::= {utmPtermEntry 5}
 
utmPtermPtyp   OBJECT-TYPE
        SYNTAX  DisplayString
        ACCESS  read-only
        STATUS  mandatory
        DESCRIPTION "Partner type of the UTM terminal"
        ::= {utmPtermEntry 6}
 
utmPtermStatus   OBJECT-TYPE
        SYNTAX  INTEGER   {
                            on  (1),
                            off (2)
                          }
        ACCESS  read-write
        STATUS  mandatory
        DESCRIPTION "The UTM terminal is either locked (off) or unlocked (on)"
        ::= {utmPtermEntry 7}
 
utmPtermConnected   OBJECT-TYPE
        SYNTAX  INTEGER   {
                            yes (1),
			    no (2),
			    waiting (3)
                          }
        ACCESS  read-write
        STATUS  mandatory
	DESCRIPTION "The UTM terminal is either connected (yes) or
		     not connected (no) or waiting for connection"
        ::= {utmPtermEntry 8}
 
utmPtermConnectStatus    OBJECT-TYPE
        SYNTAX  INTEGER  {
                            automaticCon (1),
                            terminalPool (2),
                            na           (3)
                         }
        ACCESS  read-write
        STATUS  mandatory
	DESCRIPTION "Status = 'A' means automatic connection at application start,
		     status = 'P' means a terminalpool connection"
        ::= {utmPtermEntry 9}
 
 
-- begin of objects for BS2000
utmPtermConnectForced    OBJECT-TYPE
        SYNTAX  INTEGER  {
                            yes (1),
                            no  (2)
                         }
        ACCESS  read-only
        STATUS  mandatory
        DESCRIPTION "Like automatic connection but also forces a existing 
                     connection to the terminal to be cut"
        ::= {utmPtermEntry 10}
 
utmPtermConnectMultiplexed    OBJECT-TYPE
        SYNTAX  INTEGER  {
                            yes (1),
                            no  (2)
                         }
        ACCESS  read-only
        STATUS  mandatory
        DESCRIPTION "The terminal uses either a multiplex connection or not"
        ::= {utmPtermEntry 11}
-- end of objects for BS2000
 
 
utmPtermConTime   OBJECT-TYPE
        SYNTAX  INTEGER
        ACCESS  read-only
        STATUS  mandatory
        DESCRIPTION "Duration of existing connection in minutes"
        ::= {utmPtermEntry 12}
 
utmPtermLett   OBJECT-TYPE
        SYNTAX  INTEGER
        ACCESS  read-only
        STATUS  mandatory
        DESCRIPTION "Number of messages input and output at the terminal
                     since the start of the application"
        ::= {utmPtermEntry 13}
 
utmPtermConb   OBJECT-TYPE
        SYNTAX  INTEGER
        ACCESS  read-only
        STATUS  mandatory
        DESCRIPTION "Number of breakdowns of the physical or virtual connection
                     between this terminal and the application since the start of
                     the application"
        ::= {utmPtermEntry 14}
 
 
 
 
-----------------------------------------------
-- Output of the command KDCINF LTERM
-----------------------------------------------
 
utmLtermTabNum    OBJECT-TYPE
        SYNTAX  INTEGER
        ACCESS  read-only
        STATUS  mandatory
        DESCRIPTION "The number of entries in the table utmLtermTable"
        ::= {utmLtermData  1}
 
utmLtermTable   OBJECT-TYPE
        SYNTAX  SEQUENCE OF UtmLtermEntry
        ACCESS  not-accessible
        STATUS  mandatory
        DESCRIPTION "Table of all logical UTM terminals"
        ::= {utmLtermData  2}
 
utmLtermEntry   OBJECT-TYPE
        SYNTAX  UtmLtermEntry
        ACCESS  not-accessible
        STATUS  mandatory
        DESCRIPTION "An entry in the table"
        INDEX {utmLtermIndex}
        ::= {utmLtermTable 1}
 
UtmLtermEntry ::=
        SEQUENCE
        {
          utmLtermIndex            INTEGER,
          utmLtermName             DisplayString,
          utmLtermPterm            DisplayString,
          utmLtermUser             DisplayString,
          utmLtermKset             DisplayString,
          utmLtermLock             INTEGER,
          utmLtermUsageType        INTEGER,
          utmLtermUsageBundle      INTEGER,
          utmLtermUsageTermPool    INTEGER,
          utmLtermStatus           INTEGER,
          utmLtermOutq             INTEGER,
          utmLtermInCnt            INTEGER,
          utmLtermSecCnt           INTEGER
        }
 
utmLtermIndex   OBJECT-TYPE
        SYNTAX  INTEGER
        ACCESS  read-only
        STATUS  mandatory
        DESCRIPTION "A unique value for each entry, its value
                     ranges between 1 and the value of utmLtermTabNum"
        ::= {utmLtermEntry 1}
 
utmLtermName   OBJECT-TYPE
        SYNTAX  DisplayString
        ACCESS  read-only
        STATUS  mandatory
        DESCRIPTION "Name of the chosen logical UTM terminal"
        ::= {utmLtermEntry  2}
 
utmLtermPterm   OBJECT-TYPE
        SYNTAX  DisplayString
        ACCESS  read-write
        STATUS  mandatory
        DESCRIPTION "Name of the physical terminal that belongs
                     to the logical UTM terminal"
        ::= {utmLtermEntry  3}
 
utmLtermUser   OBJECT-TYPE
        SYNTAX  DisplayString
        ACCESS  read-only
        STATUS  mandatory
        DESCRIPTION "Login name of the user currently connected
                     to the logical UTM terminal"
        ::= {utmLtermEntry  4}
 
utmLtermKset   OBJECT-TYPE
        SYNTAX  DisplayString
        ACCESS  read-only
        STATUS  mandatory
        DESCRIPTION "Key set of the UTM terminal"
        ::= {utmLtermEntry  5}
 
utmLtermLock   OBJECT-TYPE
        SYNTAX  INTEGER
        ACCESS  read-only
        STATUS  mandatory
        DESCRIPTION "Lock of the UTM-terminal"
        ::= {utmLtermEntry  6}
 
utmLtermUsageType   OBJECT-TYPE
        SYNTAX  INTEGER  {
                            dialog (1),
                            output (2)
                         }
        ACCESS  read-only
        STATUS  mandatory
        DESCRIPTION "Type is 'D' (dialog terminal) or 'O' (output terminal)"
        ::= {utmLtermEntry  7}
 
utmLtermUsageBundle   OBJECT-TYPE
        SYNTAX  INTEGER  {
                            yes (1),
                            no  (2)
                         }
        ACCESS  read-only
        STATUS  mandatory
        DESCRIPTION "The UTM terminal is a pool ('bundle') if 'B' is set"
        ::= {utmLtermEntry  8}
 
utmLtermUsageTermPool  OBJECT-TYPE
        SYNTAX  INTEGER  {
                            yes (1),
                            no  (2)
                         }
        ACCESS  read-only
        STATUS  mandatory
        DESCRIPTION "The UTM terminal is generated for a terminal pool
                     if 'P' is set"
        ::= {utmLtermEntry  9}
 
utmLtermStatus   OBJECT-TYPE
        SYNTAX  INTEGER  {
                            on  (1),
                            off (2)
                         }
        ACCESS  read-write
        STATUS  mandatory
        DESCRIPTION "The status of the UTM terminal is either 'ON' or 'OFF'"
        ::= {utmLtermEntry  10}
 
 
utmLtermOutq   OBJECT-TYPE
        SYNTAX  INTEGER
        ACCESS  read-only
        STATUS  mandatory
        DESCRIPTION "Number of messages that still have to be output
                     to this terminal"
        ::= {utmLtermEntry  11}
 
utmLtermInCnt   OBJECT-TYPE
        SYNTAX  INTEGER
        ACCESS  read-only
        STATUS  mandatory
        DESCRIPTION "Number of messages input at this terminal since
                     the start of the application; for printers, it's the
                     number of print acknowledgments"
        ::= {utmLtermEntry  12}
 
utmLtermSecCnt   OBJECT-TYPE
        SYNTAX  INTEGER
        ACCESS  read-only
        STATUS  mandatory
        DESCRIPTION "Number of security violations at this logical terminal
                     since the start of the application"
        ::= {utmLtermEntry  13}
 
 
 
-----------------------------------------------
-- Output of the command KDCINF TAC
-----------------------------------------------
 
utmTacTabNum    OBJECT-TYPE
        SYNTAX  INTEGER
        ACCESS  read-only
        STATUS  mandatory
        DESCRIPTION "The number of entries in the table utmTacTable"
        ::= {utmTacData  1}
 
utmTacTable   OBJECT-TYPE
        SYNTAX  SEQUENCE OF UtmTacEntry
        ACCESS  not-accessible
        STATUS  mandatory
        DESCRIPTION "Table including infos about all transaction codes"
        ::= {utmTacData  2}
 
utmTacEntry   OBJECT-TYPE
        SYNTAX  UtmTacEntry
        ACCESS  not-accessible
        STATUS  mandatory
        DESCRIPTION "An entry in the table"
        INDEX {utmTacIndex}
        ::= {utmTacTable 1}
 
UtmTacEntry ::=
        SEQUENCE
        {
          utmTacIndex               INTEGER,
          utmTacName                DisplayString,
          utmTacLock                INTEGER,
          utmTacStatus              INTEGER,
          utmTacTcl                 INTEGER,
          utmTacInq                 INTEGER,
          utmTacUsed                INTEGER,
          utmTacError               INTEGER,
          utmTacDbcnt               INTEGER,
          utmTacElap                INTEGER,
          utmTacDbElap              INTEGER,
          utmTacCpu                 INTEGER
        }
 
utmTacIndex   OBJECT-TYPE
        SYNTAX  INTEGER
        ACCESS  read-only
        STATUS  mandatory
        DESCRIPTION "A unique value for each entry, its value
                     ranges between 1 and the value of utmTacTabNum"
        ::= {utmTacEntry 1}
 
utmTacName   OBJECT-TYPE
        SYNTAX  DisplayString
        ACCESS  read-only
        STATUS  mandatory
        DESCRIPTION "Name of the chosen transaction code"
        ::= {utmTacEntry  2}
 
utmTacLock   OBJECT-TYPE
        SYNTAX  INTEGER
        ACCESS  read-only
        STATUS  mandatory
        DESCRIPTION "Lock of the transaction code (0 through 255)"
        ::= {utmTacEntry  3}
 
utmTacStatus   OBJECT-TYPE
        SYNTAX  INTEGER {
			  on   (1),
			  off  (2),
			  halt (3)
                        }
        ACCESS  read-write
        STATUS  mandatory
	DESCRIPTION "The status of the transaction code is either 'on', 'off'
		     or locked ('halt')"
        ::= {utmTacEntry  4}
 
utmTacTcl   OBJECT-TYPE
        SYNTAX  INTEGER
        ACCESS  read-only
        STATUS  mandatory
        DESCRIPTION "TAC class of this transaction code"
        ::= {utmTacEntry  5}
 
utmTacInq   OBJECT-TYPE
        SYNTAX  INTEGER
        ACCESS  read-only
        STATUS  mandatory
        DESCRIPTION "Number of messages still to be processed by the program
                     unit run designated by transaction code"
        ::= {utmTacEntry  6}
 
utmTacUsed   OBJECT-TYPE
        SYNTAX  INTEGER
        ACCESS  read-only
        STATUS  mandatory
        DESCRIPTION "Number of program unit runs with this transaction code
                     processed since the initial start of the application
                     (only for asynchronous TAC's)"
        ::= {utmTacEntry  7}
 
utmTacError   OBJECT-TYPE
        SYNTAX  INTEGER
        ACCESS  read-only
        STATUS  mandatory
        DESCRIPTION "Number of program unit runs with this transaction code
                     terminated with errors since the initial start of
                     the application"
        ::= {utmTacEntry  8}
 
utmTacDbcnt   OBJECT-TYPE
        SYNTAX  INTEGER
        ACCESS  read-only
        STATUS  mandatory
        DESCRIPTION "Always '0' if XA-interface is used"
        ::= {utmTacEntry  9}
 
utmTacElap   OBJECT-TYPE
        SYNTAX  INTEGER
        ACCESS  read-only
        STATUS  mandatory
        DESCRIPTION "Average runtime in milliseconds of program units
                     with this transaction code"
        ::= {utmTacEntry  10}
 
utmTacDbElap   OBJECT-TYPE
        SYNTAX  INTEGER
        ACCESS  read-only
        STATUS  mandatory
        DESCRIPTION "Average time in milliseconds spent processing the
                     database calls in the program unit runs with this
                     transaction code"
        ::= {utmTacEntry  11}
 
utmTacCpu   OBJECT-TYPE
        SYNTAX  INTEGER
        ACCESS  read-only
        STATUS  mandatory
        DESCRIPTION "Average CPU time in milliseconds spent in the UTM program run for
                     processing this transaction code"
        ::= {utmTacEntry  12}
 
 
-----------------------------------------------
-- Output of the command KDCINF TACCLASS
-----------------------------------------------
 
utmTacclassTable   OBJECT-TYPE
        SYNTAX  SEQUENCE OF UtmTacclassEntry
        ACCESS  not-accessible
        STATUS  mandatory
        DESCRIPTION "Table including infos about all TAC-classes"
        ::= {utmTacclassData  1}
 
utmTacclassEntry   OBJECT-TYPE
        SYNTAX  UtmTacclassEntry
        ACCESS  not-accessible
        STATUS  mandatory
        DESCRIPTION "An entry in the table"
        INDEX {utmTacclassNumber}
        ::= {utmTacclassTable 1}
 
UtmTacclassEntry ::=
        SEQUENCE
        {
          utmTacclassNumber       INTEGER,
          utmTacclassTasks        INTEGER,
          utmTacclassWtMesg       INTEGER,
          utmTacclassAvgWtTime    INTEGER,
          utmTacclassPGWT         INTEGER
        }
 
utmTacclassNumber   OBJECT-TYPE
        SYNTAX  INTEGER
        ACCESS  read-only
        STATUS  mandatory
        DESCRIPTION "TAC class number"
        ::= {utmTacclassEntry 1}
 
utmTacclassTasks   OBJECT-TYPE
        SYNTAX  INTEGER
        ACCESS  read-write
        STATUS  mandatory
        DESCRIPTION "Maximum number of tasks that can currently
                     work for a specific TAC class"
        ::= {utmTacclassEntry 2}
 
utmTacclassWtMesg   OBJECT-TYPE
        SYNTAX  INTEGER
        ACCESS  read-only
        STATUS  mandatory
        DESCRIPTION "Number of messages for a specific TAC class
                     currently buffered and not yet processed"
        ::= {utmTacclassEntry  3}
 
utmTacclassAvgWtTime   OBJECT-TYPE
        SYNTAX  INTEGER
        ACCESS  read-only
        STATUS  mandatory
        DESCRIPTION "Average wait times in milliseconds for all
                     dialog TAC classes (1 through 8)"
        ::= {utmTacclassEntry  4}
 
utmTacclassPGWT   OBJECT-TYPE
        SYNTAX  INTEGER {
                          yes (1),
                          no  (2)
                        }
        ACCESS  read-only
        STATUS  mandatory
        DESCRIPTION "Indicates whether program units containing a
                     PGWT call can run in a specific TAC class"
        ::= {utmTacclassEntry  5}
 
 
 
-----------------------------------------------
-- Output of the command KDCINF USER
-----------------------------------------------
 
utmUserTabNum    OBJECT-TYPE
        SYNTAX  INTEGER
        ACCESS  read-only
        STATUS  mandatory
        DESCRIPTION "The number of entries in the table utmUserTable"
        ::= {utmUserData  1}
 
utmUserTable   OBJECT-TYPE
        SYNTAX  SEQUENCE OF UtmUserEntry
        ACCESS  not-accessible
        STATUS  mandatory
        DESCRIPTION "Table including infos about all users"
        ::= {utmUserData  2}
 
utmUserEntry   OBJECT-TYPE
        SYNTAX  UtmUserEntry
        ACCESS  not-accessible
        STATUS  mandatory
        DESCRIPTION "An entry in the table"
        INDEX {utmUserIndex}
        ::= {utmUserTable 1}
 
UtmUserEntry ::=
        SEQUENCE
        {
          utmUserIndex              INTEGER,
          utmUserName               DisplayString,
          utmUserKset               DisplayString,
          utmUserStatus             INTEGER,
          utmUserInVg               INTEGER,
          utmUserNrTacs             INTEGER,
          utmUserCpuTime            INTEGER,
          utmUserSecCnt             INTEGER,
          utmUserLterm              DisplayString
        }
 
utmUserIndex   OBJECT-TYPE
        SYNTAX  INTEGER
        ACCESS  read-only
        STATUS  mandatory
        DESCRIPTION "A unique value for each entry, its value
                     ranges between 1 and the value of utmUserTabNum"
        ::= {utmUserEntry 1}
 
utmUserName    OBJECT-TYPE
        SYNTAX  DisplayString 
        ACCESS  read-only
        STATUS  mandatory
        DESCRIPTION "Name of the user"
        ::= {utmUserEntry 2}
 
utmUserKset    OBJECT-TYPE
        SYNTAX DisplayString
        ACCESS  read-only
        STATUS  mandatory
        DESCRIPTION "Key set assigned to users login name"
        ::= {utmUserEntry 3}
 
utmUserStatus  OBJECT-TYPE
        SYNTAX  INTEGER { 
                          on  (1), 
                          off (2) 
                        }
        ACCESS  read-write
        STATUS  mandatory
        DESCRIPTION "Login name is either locked (off) or unlocked (on)"
        ::= {utmUserEntry 4}
 
utmUserInVg    OBJECT-TYPE
        SYNTAX  INTEGER {
                          yes (1), 
                          no  (2)
                        }
        ACCESS  read-only
        STATUS  mandatory
        DESCRIPTION "Determines if the user is currently processing a conversation"
        ::= {utmUserEntry 5}
 
utmUserNrTacs  OBJECT-TYPE
        SYNTAX  INTEGER
        ACCESS  read-only
        STATUS  mandatory
        DESCRIPTION "Number of transaction jobs entered by the user since the
                     initial start of the application"
        ::= {utmUserEntry 6}
 
utmUserCpuTime OBJECT-TYPE
        SYNTAX  INTEGER
        ACCESS  read-only
        STATUS  mandatory
        DESCRIPTION "Number of seconds spent in processing transaction jobs for
                     the user (excluding database calls)"
        ::= {utmUserEntry 7}
 
utmUserSecCnt  OBJECT-TYPE
        SYNTAX  INTEGER
        ACCESS  read-only
        STATUS  mandatory
        DESCRIPTION "Number of security violations for the login name since
                     the start of the application"
        ::= {utmUserEntry 8}
 
utmUserLterm   OBJECT-TYPE
        SYNTAX  DisplayString
        ACCESS  read-only
        STATUS  mandatory
        DESCRIPTION "Name of the logical terminal through witch the user of the
                     UTM application logged on"
        ::= {utmUserEntry 9}
 
 
-----------------------------------------------
-- Output of the command KDCINF CON
-----------------------------------------------
 
utmConTabNum    OBJECT-TYPE
        SYNTAX  INTEGER
        ACCESS  read-only
        STATUS  mandatory
        DESCRIPTION "The number of entries in the table utmConTable"
        ::= {utmConData  1}
 
utmConTable   OBJECT-TYPE
        SYNTAX  SEQUENCE OF UtmConEntry
        ACCESS  not-accessible
        STATUS  mandatory
        DESCRIPTION "Table including infos about all connections"
        ::= {utmConData  2}
 
utmConEntry   OBJECT-TYPE
        SYNTAX  UtmConEntry
        ACCESS  not-accessible
        STATUS  mandatory
        DESCRIPTION "An entry in the table"
        INDEX {utmConIndex}
        ::= {utmConTable 1}
 
UtmConEntry ::=
        SEQUENCE
        {
          utmConIndex              INTEGER,
          utmConName               DisplayString,
          utmConProname            DisplayString,
          utmConLpap               DisplayString,
          utmConBcamAppl           DisplayString,
          utmConStatus             INTEGER,
          utmConConnected          INTEGER,
          utmConConnectStatus      INTEGER,
          utmConConTime            INTEGER,
          utmConLett               INTEGER,
          utmConConb               INTEGER
        }
 
utmConIndex   OBJECT-TYPE
        SYNTAX  INTEGER
        ACCESS  read-only
        STATUS  mandatory
        DESCRIPTION "A unique value for each entry, its value
                     ranges between 1 and the value of utmConTabNum"
        ::= {utmConEntry 1}
 
utmConName    OBJECT-TYPE
        SYNTAX  DisplayString
        ACCESS  read-only
        STATUS  mandatory
        DESCRIPTION "Name of the connection"
        ::= {utmConEntry 2}
 
utmConProname OBJECT-TYPE
        SYNTAX  DisplayString
        ACCESS  read-only
        STATUS  mandatory
        DESCRIPTION "Processor name"
        ::= {utmConEntry 3}
 
utmConLpap    OBJECT-TYPE
        SYNTAX  DisplayString
        ACCESS  read-only
        STATUS  mandatory
        DESCRIPTION "Name of the remote application in the local application"
        ::= {utmConEntry 4}
 
utmConBcamAppl OBJECT-TYPE
        SYNTAX  DisplayString
        ACCESS  read-only
        STATUS  mandatory
        DESCRIPTION "BCAM name of the UTM application"
        ::= {utmConEntry 5}
 
utmConStatus   OBJECT-TYPE
        SYNTAX  INTEGER {
                          on  (1), 
                          off (2)
                        }
        ACCESS  read-write
        STATUS  mandatory
        DESCRIPTION "A connection to the remote application exists or can be
                     set up (on), or cannot be set up (off)"
        ::= {utmConEntry 6}
 
utmConConnected OBJECT-TYPE
        SYNTAX  INTEGER {
                          yes (1), 
			  no (2),
			  waiting (3)
			}
        ACCESS  read-write
        STATUS  mandatory
	DESCRIPTION "A connection is either established (yes) or not (no)
		     or UTM is just establishing a connection (waiting)"
        ::= {utmConEntry 7}
 
utmConConnectStatus OBJECT-TYPE
        SYNTAX  INTEGER {
                          automaticCon     (1),
                          noAutomaticCon   (2)
                        }
        ACCESS  read-write
        STATUS  mandatory
        DESCRIPTION "An 'A' means automatic connection setup at start of 
                     application"
        ::= {utmConEntry 8}
 
utmConConTime OBJECT-TYPE
        SYNTAX  INTEGER
        ACCESS  read-only
        STATUS  mandatory
        DESCRIPTION "Duration of connection in minutes"
        ::= {utmConEntry 9}
 
utmConLett    OBJECT-TYPE
        SYNTAX  INTEGER
        ACCESS  read-only
        STATUS  mandatory
        DESCRIPTION "Number of messages input and output through the connection"
        ::= {utmConEntry 10}
 
utmConConb    OBJECT-TYPE
        SYNTAX  INTEGER
        ACCESS  read-only
        STATUS  mandatory
        DESCRIPTION "Number of breakdowns of the connection since the start 
                     of the application"
        ::= {utmConEntry 11}
 
 
-----------------------------------------------
-- Output of the command KDCINF LPAP
-----------------------------------------------
 
utmLpapTabNum    OBJECT-TYPE
        SYNTAX  INTEGER
        ACCESS  read-only
        STATUS  mandatory
        DESCRIPTION "The number of entries in the table utmLpapTable"
        ::= {utmLpapData  1}
 
utmLpapTable   OBJECT-TYPE
        SYNTAX  SEQUENCE OF UtmLpapEntry
        ACCESS  not-accessible
        STATUS  mandatory
        DESCRIPTION "Table including infos about all remote applications
                     communicating with LU6.1"
        ::= {utmLpapData  2}
 
utmLpapEntry   OBJECT-TYPE
        SYNTAX  UtmLpapEntry
        ACCESS  not-accessible
        STATUS  mandatory 
        DESCRIPTION "An entry in the table" 
	INDEX {utmLpapIndex}
	::= {utmLpapTable 1}
 
UtmLpapEntry ::= 
        SEQUENCE 
        { 
          utmLpapIndex              INTEGER, 
          utmLpapName               DisplayString, 
          utmLpapKset               DisplayString, 
          utmLpapStatus             INTEGER,
          utmLpapQuiet              INTEGER,
          utmLpapOutq               INTEGER,
          utmLpapIdleTime           INTEGER
        }
 
utmLpapIndex   OBJECT-TYPE
        SYNTAX  INTEGER
        ACCESS  read-only
        STATUS  mandatory
        DESCRIPTION "A unique value for each entry, its value
                     ranges between 1 and the value of utmLpapTabNum"
        ::= {utmLpapEntry 1}
 
utmLpapName    OBJECT-TYPE
        SYNTAX  DisplayString
        ACCESS  read-only
        STATUS  mandatory
        DESCRIPTION "Name of the LPAP"
        ::= {utmLpapEntry 2}
 
utmLpapKset    OBJECT-TYPE
        SYNTAX  DisplayString
        ACCESS  read-only
        STATUS  mandatory
        DESCRIPTION "Key set of the remote application"
        ::= {utmLpapEntry 3}
 
utmLpapStatus  OBJECT-TYPE
        SYNTAX  INTEGER {
                          on  (1), 
                          off (2)
                        }
        ACCESS  read-write
        STATUS  mandatory
        DESCRIPTION "A connection to the remote application exists or can be
                    set up (on), or cannot be set up (off)"
        ::= {utmLpapEntry 4}
 
utmLpapQuiet OBJECT-TYPE
        SYNTAX  INTEGER {
                          yes (1),
                          no  (2)
                        }
        ACCESS  read-write
        STATUS  mandatory
        DESCRIPTION "A 'Q' means 'quiet', i.e. no more dialog jobs for the 
                     remote application are accepted"
        ::= {utmLpapEntry 5}
 
utmLpapOutq    OBJECT-TYPE
        SYNTAX  INTEGER
        ACCESS  read-only
        STATUS  mandatory
        DESCRIPTION "Number of messages that still have to be sent to this
                     remote application"
        ::= {utmLpapEntry 6}
 
utmLpapIdleTime OBJECT-TYPE
        SYNTAX  INTEGER
        ACCESS  read-write
        STATUS  mandatory
        DESCRIPTION "Time for monitoring the idle state of a session in seconds"
        ::= {utmLpapEntry 7}
 
 
 
-----------------------------------------------
-- Output of the command KDCINF POOL 
-----------------------------------------------
 
utmPoolTabNum    OBJECT-TYPE
        SYNTAX  INTEGER
        ACCESS  read-only
        STATUS  mandatory
        DESCRIPTION "The number of entries in the table utmPoolTable"
        ::= {utmPoolData  1}
 
utmPoolTable   OBJECT-TYPE
        SYNTAX  SEQUENCE OF UtmPoolEntry
        ACCESS  not-accessible
        STATUS  mandatory
        DESCRIPTION "Table including infos about terminal pools"
        ::= {utmPoolData  2}
 
utmPoolEntry   OBJECT-TYPE
        SYNTAX  UtmPoolEntry
        ACCESS  not-accessible
        STATUS  mandatory
        DESCRIPTION "An entry in the table"
	INDEX {utmPoolIndex}
	::= {utmPoolTable 1}

UtmPoolEntry ::=
        SEQUENCE
        {
          utmPoolIndex              INTEGER,
          utmPoolProname            DisplayString,
          utmPoolBcamAppl           DisplayString,
          utmPoolPtype              DisplayString,
          utmPoolStations           INTEGER,
          utmPoolStatusOn           INTEGER,
          utmPoolActCon             INTEGER,
          utmPoolMaxCon             INTEGER,
          utmPoolKset               DisplayString,
          utmPoolLock               INTEGER
        }
 
utmPoolIndex   OBJECT-TYPE
        SYNTAX  INTEGER
        ACCESS  read-only
        STATUS  mandatory
        DESCRIPTION "A unique value for each entry, its value
                     ranges between 1 and the value of utmPoolTabNum"
        ::= {utmPoolEntry 1}
 
utmPoolProname   OBJECT-TYPE
        SYNTAX  DisplayString
        ACCESS  read-only
        STATUS  mandatory
        DESCRIPTION "Processor name of the terminal pool"
        ::= {utmPoolEntry 2}
 
utmPoolBcamAppl   OBJECT-TYPE
        SYNTAX  DisplayString
        ACCESS  read-only
        STATUS  mandatory
        DESCRIPTION "Name of the access point to the transport system which was
                     generated for this terminal pool"
        ::= {utmPoolEntry 3}
 
utmPoolPtype   OBJECT-TYPE
        SYNTAX  DisplayString
        ACCESS  read-only
        STATUS  mandatory
        DESCRIPTION "Physical terminal type of the terminals that can be
                     connected to the application via this pool"
        ::= {utmPoolEntry 4}
 
utmPoolStations   OBJECT-TYPE
        SYNTAX  INTEGER
        ACCESS  read-only
        STATUS  mandatory
        DESCRIPTION "Generated maximum number of terminals that can be 
                     connected to the application via this pool"
        ::= {utmPoolEntry 5}
 
utmPoolStatusOn   OBJECT-TYPE
        SYNTAX  INTEGER
        ACCESS  read-write
        STATUS  mandatory
        DESCRIPTION "Maximum number of terminals with STATUS=ON"
        ::= {utmPoolEntry 6}
 
utmPoolActCon   OBJECT-TYPE
        SYNTAX  INTEGER
        ACCESS  read-only
        STATUS  mandatory
        DESCRIPTION "Number of terminals connected to the application
                     via this pool"
        ::= {utmPoolEntry 7}
 
utmPoolMaxCon   OBJECT-TYPE
        SYNTAX  INTEGER
        ACCESS  read-only
        STATUS  mandatory
        DESCRIPTION "Maximum number of terminals that have been simultaneously
                     connected to the application via this terminal pool
                     during this application run"
        ::= {utmPoolEntry 8}
 
utmPoolKset   OBJECT-TYPE
        SYNTAX  DisplayString
        ACCESS  read-only
        STATUS  mandatory
        DESCRIPTION "Key set of the terminals of this terminal pool"
        ::= {utmPoolEntry 9}
 
utmPoolLock   OBJECT-TYPE
        SYNTAX  INTEGER
        ACCESS  read-only
        STATUS  mandatory
        DESCRIPTION "Lock of the terminals of this terminal pool"
        ::= {utmPoolEntry 10}
 
 
-----------------------------------------------
-- Output of the command KDCINF LSES
-----------------------------------------------
 
utmLsesTabNum    OBJECT-TYPE
        SYNTAX  INTEGER
        ACCESS  read-only
        STATUS  mandatory
        DESCRIPTION "The number of entries in the table utmLsesTable"
        ::= {utmLsesData  1}
 
utmLsesTable   OBJECT-TYPE
        SYNTAX  SEQUENCE OF UtmLsesEntry
        ACCESS  not-accessible
        STATUS  mandatory
        DESCRIPTION "Table including infos about the sessions via LU6.1"
        ::= {utmLsesData  2}
 
utmLsesEntry   OBJECT-TYPE
        SYNTAX  UtmLsesEntry
        ACCESS  not-accessible
        STATUS  mandatory
        DESCRIPTION "An entry in the table"
	INDEX {utmLsesIndex}
	::= {utmLsesTable 1}
 
UtmLsesEntry ::=
        SEQUENCE
        {
          utmLsesIndex              INTEGER,
          utmLsesName               DisplayString,
          utmLsesRses               DisplayString,
          utmLsesLpap               DisplayString,
          utmLsesCon                DisplayString,
          utmLsesProname            DisplayString,
          utmLsesBcamAppl           DisplayString,
          utmLsesAgUser             DisplayString
        }
 
utmLsesIndex   OBJECT-TYPE
        SYNTAX  INTEGER
        ACCESS  read-only
        STATUS  mandatory
        DESCRIPTION "A unique value for each entry, its value
                     ranges between 1 and the value of utmLsesTabNum"
        ::= {utmLsesEntry 1}
 
utmLsesName   OBJECT-TYPE
        SYNTAX  DisplayString
        ACCESS  read-only
        STATUS  mandatory
        DESCRIPTION "Name of the session in the local application"
        ::= {utmLsesEntry 2}
 
utmLsesRses   OBJECT-TYPE
        SYNTAX  DisplayString
        ACCESS  read-only
        STATUS  mandatory
        DESCRIPTION "Name of the session in the remote application"
        ::= {utmLsesEntry 3}
 
utmLsesLpap   OBJECT-TYPE
        SYNTAX  DisplayString
        ACCESS  read-only
        STATUS  mandatory
        DESCRIPTION "Name of the remote application for which the
                     session is generated"
        ::= {utmLsesEntry 4}
 
utmLsesCon   OBJECT-TYPE
        SYNTAX  DisplayString
        ACCESS  read-only
        STATUS  mandatory
        DESCRIPTION "Denotes the transport connection that is set up
                     for the session"
        ::= {utmLsesEntry 5}
 
utmLsesProname   OBJECT-TYPE
        SYNTAX  DisplayString
        ACCESS  read-only
        STATUS  mandatory
        DESCRIPTION "Processor name"
        ::= {utmLsesEntry 6}
 
utmLsesBcamAppl   OBJECT-TYPE
        SYNTAX  DisplayString
        ACCESS  read-only
        STATUS  mandatory
        DESCRIPTION "Denotes the transport connection that is set up
                     for the session"
        ::= {utmLsesEntry 7}
 
utmLsesAgUser  OBJECT-TYPE
        SYNTAX  DisplayString
        ACCESS  read-only
        STATUS  mandatory
        DESCRIPTION "Name of the job-submitting partner for which
                     the session has been reserved"
        ::= {utmLsesEntry 8}
 
 
-----------------------------------------------
-- Output of the command KDCINF LTAC
-----------------------------------------------
 
utmLtacTabNum    OBJECT-TYPE
        SYNTAX  INTEGER
        ACCESS  read-only
        STATUS  mandatory
        DESCRIPTION "The number of entries in the table utmLtacTable"
        ::= {utmLtacData  1}
 
utmLtacTable   OBJECT-TYPE
        SYNTAX  SEQUENCE OF UtmLtacEntry
        ACCESS  not-accessible
        STATUS  mandatory
        DESCRIPTION "Table including infos about LTACs"
        ::= {utmLtacData  2}
 
utmLtacEntry   OBJECT-TYPE
        SYNTAX  UtmLtacEntry
        ACCESS  not-accessible
        STATUS  mandatory
        DESCRIPTION "An entry in the table"
	INDEX {utmLtacIndex}
	::= {utmLtacTable 1}
 
UtmLtacEntry ::=
        SEQUENCE
        {
          utmLtacIndex              INTEGER,
          utmLtacName               DisplayString,
          utmLtacLock               INTEGER,
          utmLtacStatus             INTEGER,
          utmLtacRtac               DisplayString,
          utmLtacLpap               DisplayString,
          utmLtacAccessWait         INTEGER,
          utmLtacReplyWait          INTEGER,
          utmLtacUsed               INTEGER
        }
 
utmLtacIndex   OBJECT-TYPE
        SYNTAX  INTEGER
        ACCESS  read-only
        STATUS  mandatory
        DESCRIPTION "A unique value for each entry, its value
                     ranges between 1 and the value of utmLtacTabNum"
        ::= {utmLtacEntry 1}
 
utmLtacName   OBJECT-TYPE
        SYNTAX  DisplayString
        ACCESS  read-only
        STATUS  mandatory
        DESCRIPTION "Name of the LTAC"
        ::= {utmLtacEntry 2}
 
utmLtacLock   OBJECT-TYPE
        SYNTAX  INTEGER
        ACCESS  read-only
        STATUS  mandatory
        DESCRIPTION "Lock of the remote converstation"
        ::= {utmLtacEntry 3}
 
utmLtacStatus   OBJECT-TYPE
        SYNTAX  INTEGER  {
                           on  (1),
                           off (2)
                         }
        ACCESS  read-write
        STATUS  mandatory
        DESCRIPTION "The LTAC transaction code is either locked (OFF) or 
                     unlocked (ON)"
        ::= {utmLtacEntry 4}
 
utmLtacRtac   OBJECT-TYPE
        SYNTAX  DisplayString
        ACCESS  read-only
        STATUS  mandatory
        DESCRIPTION "Name of the transaction code in a remote application"
        ::= {utmLtacEntry 5}
 
utmLtacLpap   OBJECT-TYPE
        SYNTAX  DisplayString
        ACCESS  read-only
        STATUS  mandatory
        DESCRIPTION "Name of the remote application in the local 
                     application"
        ::= {utmLtacEntry 6}
 
utmLtacAccessWait   OBJECT-TYPE
        SYNTAX  INTEGER
        ACCESS  read-write
        STATUS  mandatory
        DESCRIPTION "Time in seconds spent waiting for a session or 
                     association to be reserved"
        ::= {utmLtacEntry 7}
 
utmLtacReplyWait   OBJECT-TYPE
        SYNTAX  INTEGER
        ACCESS  read-write
        STATUS  mandatory
        DESCRIPTION "Time in seconds spent waiting for response from 
                     receiving partner"
        ::= {utmLtacEntry 8}
 
utmLtacUsed   OBJECT-TYPE
        SYNTAX  INTEGER
        ACCESS  read-only
        STATUS  mandatory
        DESCRIPTION "Number of jobs issued to this LTAC since the start of 
                     the application"
        ::= {utmLtacEntry 9}
 
 
-----------------------------------------------
-- Output of the command KDCINF OSI-ASS
-----------------------------------------------
 
utmOsiAssTabNum    OBJECT-TYPE
        SYNTAX  INTEGER
        ACCESS  read-only
        STATUS  mandatory
        DESCRIPTION "The number of entries in the table utmOsiAssTable"
        ::= {utmOsiAssData  1}
 
utmOsiAssTable   OBJECT-TYPE
        SYNTAX  SEQUENCE OF UtmOsiAssEntry
        ACCESS  not-accessible
        STATUS  mandatory
        DESCRIPTION "Table including infos about OSI-TP associations"
        ::= {utmOsiAssData  2}
 
utmOsiAssEntry   OBJECT-TYPE
        SYNTAX  UtmOsiAssEntry
        ACCESS  not-accessible
        STATUS  mandatory
        DESCRIPTION "An entry in the table"
	INDEX {utmOsiAssIndex}
	::= {utmOsiAssTable 1}

UtmOsiAssEntry ::=
        SEQUENCE
        {
          utmOsiAssIndex              INTEGER,
          utmOsiAssName               DisplayString,
          utmOsiAssOsiLpap            DisplayString,
          utmOsiAssOsiCon             DisplayString,
          utmOsiAssAgUser             DisplayString,
          utmOsiAssConTime            INTEGER,
          utmOsiAssLetters            INTEGER
        }
 
utmOsiAssIndex   OBJECT-TYPE
        SYNTAX  INTEGER
        ACCESS  read-only
        STATUS  mandatory
        DESCRIPTION "A unique value for each entry, its value
                     ranges between 1 and the value of utmOsiAssTabNum"
        ::= {utmOsiAssEntry 1}
 
utmOsiAssName   OBJECT-TYPE
        SYNTAX  DisplayString
        ACCESS  read-only
        STATUS  mandatory
        DESCRIPTION "Name of the OSI association"
        ::= {utmOsiAssEntry 2}
 
utmOsiAssOsiLpap   OBJECT-TYPE
        SYNTAX  DisplayString
        ACCESS  read-only
        STATUS  mandatory
        DESCRIPTION "Name of the remote application in the local 
                     application for which the association is generated"
        ::= {utmOsiAssEntry 3}
 
utmOsiAssOsiCon   OBJECT-TYPE
        SYNTAX  DisplayString
        ACCESS  read-only
        STATUS  mandatory
        DESCRIPTION "Name of the connection set up to the remote application
                     for the association"
        ::= {utmOsiAssEntry 4}
 
utmOsiAssAgUser OBJECT-TYPE
        SYNTAX  DisplayString
        ACCESS  read-only
        STATUS  mandatory
        DESCRIPTION "Name of the job submitter for which the association
                     is reserved"
        ::= {utmOsiAssEntry 5}
 
utmOsiAssConTime   OBJECT-TYPE
        SYNTAX  INTEGER
        ACCESS  read-only
        STATUS  mandatory
        DESCRIPTION "Duration of the connection in minutes"
        ::= {utmOsiAssEntry 6}
 
utmOsiAssLetters   OBJECT-TYPE
        SYNTAX  INTEGER
        ACCESS  read-only
        STATUS  mandatory
        DESCRIPTION "Number of messages input and output since the start of 
                     the application"
        ::= {utmOsiAssEntry 7}
 
 
-----------------------------------------------
-- Output of the command KDCINF OSI-CON
-----------------------------------------------
 
utmOsiConTabNum    OBJECT-TYPE
        SYNTAX  INTEGER
        ACCESS  read-only
        STATUS  mandatory
        DESCRIPTION "The number of entries in the table utmOsiConTable"
        ::= {utmOsiConData  1}
 
utmOsiConTable   OBJECT-TYPE
        SYNTAX  SEQUENCE OF UtmOsiConEntry
        ACCESS  not-accessible
        STATUS  mandatory
        DESCRIPTION "Table including infos about virtual connections for 
                     distributed processing via the OSI-TP protocol"
        ::= {utmOsiConData  2}
 
utmOsiConEntry   OBJECT-TYPE
        SYNTAX  UtmOsiConEntry
        ACCESS  not-accessible
        STATUS  mandatory
        DESCRIPTION "An entry in the table"
	INDEX {utmOsiConIndex}
	::= {utmOsiConTable 1}
 
UtmOsiConEntry ::=
        SEQUENCE
        {
          utmOsiConIndex              INTEGER,
          utmOsiConName               DisplayString,
          utmOsiConOsiLpap            DisplayString,
          utmOsiConTsel               DisplayString,
          utmOsiConNsel               DisplayString,
          utmOsiConAccPnt             DisplayString,
          utmOsiConActive             INTEGER
        }
 
utmOsiConIndex   OBJECT-TYPE
        SYNTAX  INTEGER
        ACCESS  read-only
        STATUS  mandatory
        DESCRIPTION "A unique value for each entry, its value
                     ranges between 1 and the value of utmOsiConTabNum"
        ::= {utmOsiConEntry 1}
 
utmOsiConName   OBJECT-TYPE
        SYNTAX  DisplayString
        ACCESS  read-only
        STATUS  mandatory
        DESCRIPTION "Name of the OSI connection"
        ::= {utmOsiConEntry 2}
 
utmOsiConOsiLpap   OBJECT-TYPE
        SYNTAX  DisplayString
        ACCESS  read-only
        STATUS  mandatory
        DESCRIPTION "Name of the remote application in the local application"
        ::= {utmOsiConEntry 3}
 
utmOsiConTsel   OBJECT-TYPE
        SYNTAX  DisplayString
        ACCESS  read-only
        STATUS  mandatory
        DESCRIPTION "BCAM application name of the remote OSI-TP partner
                     (transport selector)"
        ::= {utmOsiConEntry 4}
 
utmOsiConNsel   OBJECT-TYPE
        SYNTAX  DisplayString
        ACCESS  read-only
        STATUS  mandatory
        DESCRIPTION "Name of the processor on which the OSI-TP partner is 
                     located (network selector)"
        ::= {utmOsiConEntry 5}
 
utmOsiConAccPnt   OBJECT-TYPE
        SYNTAX  DisplayString
        ACCESS  read-only
        STATUS  mandatory
        DESCRIPTION "Local name of an access point through which  
                     communication with OSI-TP partners takes place"
        ::= {utmOsiConEntry 6}
 
utmOsiConActive   OBJECT-TYPE
        SYNTAX  INTEGER  {
                           yes (1),
                           no  (2)
                         }
        ACCESS  read-write
        STATUS  mandatory
        DESCRIPTION "The transport connection can either be used (YES) or
                     is reserved as a substitute connection (NO)" 
        ::= {utmOsiConEntry 7}
 
 
-----------------------------------------------
-- Output of the command KDCINF OSI-LPAP
-----------------------------------------------
 
utmOsiLpapTabNum    OBJECT-TYPE
        SYNTAX  INTEGER
        ACCESS  read-only
        STATUS  mandatory
        DESCRIPTION "The number of entries in the table utmOsiLpapTable"
        ::= {utmOsiLpapData  1}
 
utmOsiLpapTable   OBJECT-TYPE
        SYNTAX  SEQUENCE OF UtmOsiLpapEntry
        ACCESS  not-accessible
        STATUS  mandatory
        DESCRIPTION "Table including infos about remote partner applications
                     that communicate via the OSI-TP protocol"
        ::= {utmOsiLpapData  2}
 
utmOsiLpapEntry   OBJECT-TYPE
        SYNTAX  UtmOsiLpapEntry
        ACCESS  not-accessible
        STATUS  mandatory
        DESCRIPTION "An entry in the table"
	INDEX {utmOsiLpapIndex}
	::= {utmOsiLpapTable 1}

UtmOsiLpapEntry ::=
        SEQUENCE
        {
          utmOsiLpapIndex              INTEGER,
          utmOsiLpapName               DisplayString,
          utmOsiLpapKset               DisplayString,
          utmOsiLpapStatus             INTEGER,
          utmOsiLpapQuiet              INTEGER,
          utmOsiLpapOutq               INTEGER,
          utmOsiLpapIdleTime           INTEGER,
          utmOsiLpapOsiCon             DisplayString,
          utmOsiLpapAssoc              INTEGER,
          utmOsiLpapConnect            INTEGER,
          utmOsiLpapAutoCon            INTEGER
        }
 
utmOsiLpapIndex   OBJECT-TYPE
        SYNTAX  INTEGER
        ACCESS  read-only
        STATUS  mandatory
        DESCRIPTION "A unique value for each entry, its value
                     ranges between 1 and the value of utmOsiLpapTabNum"
        ::= {utmOsiLpapEntry 1}
 
utmOsiLpapName   OBJECT-TYPE
        SYNTAX  DisplayString
        ACCESS  read-only
        STATUS  mandatory
        DESCRIPTION "Name of the OSI LPAP"
        ::= {utmOsiLpapEntry 2}
 
utmOsiLpapKset   OBJECT-TYPE
        SYNTAX  DisplayString
        ACCESS  read-only
        STATUS  mandatory
        DESCRIPTION "Key set of the remote application"
        ::= {utmOsiLpapEntry 3}
 
utmOsiLpapStatus   OBJECT-TYPE
        SYNTAX  INTEGER  {
                           on  (1),
                           off (2)
                         }
	ACCESS  read-write
        STATUS  mandatory
        DESCRIPTION "A connection to the remote application exists or can be
                     set up (ON), or cannot be set up (OFF)"
        ::= {utmOsiLpapEntry 4}
 
utmOsiLpapQuiet   OBJECT-TYPE
        SYNTAX  INTEGER  {
                           yes (1),
                           no  (2)
                         }
        ACCESS  read-write
        STATUS  mandatory
        DESCRIPTION "A 'Q' means 'quiet', i.e. no more dialog jobs for the
                     remote application are accepted"
        ::= {utmOsiLpapEntry 5}
 
utmOsiLpapOutq   OBJECT-TYPE
        SYNTAX  INTEGER
        ACCESS  read-only
        STATUS  mandatory
        DESCRIPTION "Number of messages that still have to be sent to this
                     remote application"
        ::= {utmOsiLpapEntry 6}
 
utmOsiLpapIdleTime   OBJECT-TYPE
        SYNTAX  INTEGER
        ACCESS  read-write
        STATUS  mandatory
        DESCRIPTION "Time for monitoring the idle state of a session"
        ::= {utmOsiLpapEntry 7}
 
utmOsiLpapOsiCon   OBJECT-TYPE
        SYNTAX  DisplayString
        ACCESS  read-only
        STATUS  mandatory
        DESCRIPTION "Name of the transport connection used to communicate
                     with the OSI-TP partner"
        ::= {utmOsiLpapEntry 8}
 
utmOsiLpapAssoc   OBJECT-TYPE
        SYNTAX  INTEGER
        ACCESS  read-only
        STATUS  mandatory
        DESCRIPTION "Number of parallel connections generated for the
                     OSI-TP partner"
        ::= {utmOsiLpapEntry 9}
 
utmOsiLpapConnect   OBJECT-TYPE
        SYNTAX  INTEGER
        ACCESS  read-only
        STATUS  mandatory
        DESCRIPTION "Number of connections set up"
        ::= {utmOsiLpapEntry 10}
 
utmOsiLpapAutoCon   OBJECT-TYPE
        SYNTAX  INTEGER
        ACCESS  read-only
        STATUS  mandatory
        DESCRIPTION "Number of connections to be set up to the partner
                     when the application is started"
        ::= {utmOsiLpapEntry 11}
 
 
 
 
 
-----------------------------------------------
-- Data objects for trap control
-----------------------------------------------
 
 
utmTrapControl                OBJECT IDENTIFIER ::= { sniUTM 4 }
 
 
 
utmTrapCtrlCheckCaseNOW   OBJECT-TYPE
        SYNTAX  INTEGER
        ACCESS  read-write
        STATUS  mandatory
        DESCRIPTION "Any set request for this object will start
                     an immediate trap case detection for all traps
                     (independent from any timer)"
        ::= {utmTrapControl 1}
 
utmTrapCtrlAbortedPeriod   OBJECT-TYPE
        SYNTAX  INTEGER
        ACCESS  read-write
        STATUS  mandatory
        DESCRIPTION "Break time in seconds between two trap checks;
                     '-1' means no trap case detection"
        ::= {utmTrapControl 2}
 
utmTrapCtrlPENDERPeriod   OBJECT-TYPE
        SYNTAX  INTEGER
        ACCESS  read-write
        STATUS  mandatory
        DESCRIPTION "Break time in seconds between two trap checks;
                     '-1' means no trap case detection"
        ::= {utmTrapControl 3}
 
utmTrapCtrlDeadlockPeriod   OBJECT-TYPE
        SYNTAX  INTEGER
        ACCESS  read-write
        STATUS  mandatory
        DESCRIPTION "Break time in seconds between two trap checks;
                     '-1' means no trap case detection"
        ::= {utmTrapControl 4}
 
utmTrapCtrlSecurViolPeriod OBJECT-TYPE
        SYNTAX  INTEGER
        ACCESS  read-write
        STATUS  mandatory
        DESCRIPTION "Break time in seconds between two trap checks;
                     '-1' means no trap case detection"
        ::= {utmTrapControl 5}
 
utmTrapCtrlSecurViolLimit OBJECT-TYPE
        SYNTAX  INTEGER
        ACCESS  read-write
        STATUS  mandatory
        DESCRIPTION "Necessary number of user security violations (since 
                     application start or since last security trap) 
                     before sending a new trap"
        ::= {utmTrapControl 6}
 
utmTrapCtrlConnLossPeriod OBJECT-TYPE
        SYNTAX  INTEGER
        ACCESS  read-write
        STATUS  mandatory
        DESCRIPTION "Break time in seconds between two trap checks;
                     '-1' means no trap case detection"
        ::= {utmTrapControl 7}
 
utmTrapCtrlConnLossLimit OBJECT-TYPE
        SYNTAX  INTEGER
        ACCESS  read-write
        STATUS  mandatory
        DESCRIPTION "Necessary number of unconnected partner 
                     applications before sending a trap; 
                     -1 means maximum (no connected partners)"
        ::= {utmTrapControl 8}
 
utmTrapCtrlConnUsersPeriod   OBJECT-TYPE
        SYNTAX  INTEGER
        ACCESS  read-write
        STATUS  mandatory
        DESCRIPTION "Break time in seconds between two trap checks;
                     '-1' means no trap case detection"
        ::= {utmTrapControl 9}
 
utmTrapCtrlConnUsersLimit   OBJECT-TYPE
        SYNTAX  INTEGER
        ACCESS  read-write
        STATUS  mandatory
        DESCRIPTION "Necessary number of connected users before
                     sending a trap; -1 means the generated maximum 
                     of allowed user connections"
        ::= {utmTrapControl 10}
 
utmTrapCtrlActiveTasksPeriod   OBJECT-TYPE
        SYNTAX  INTEGER
        ACCESS  read-write
        STATUS  mandatory
        DESCRIPTION "Break time in seconds between two trap checks;
                     '-1' means no trap case detection"
        ::= {utmTrapControl 11}
 
utmTrapCtrlActiveTasksLimit   OBJECT-TYPE
        SYNTAX  INTEGER
        ACCESS  read-write
        STATUS  mandatory
        DESCRIPTION "Necessary number of active tasks before 
                     sending a trap; -1 means the actual maximum
                     of allowed tasks"
        ::= {utmTrapControl 12}
 
utmTrapCtrlCacheHitPeriod   OBJECT-TYPE
        SYNTAX  INTEGER
        ACCESS  read-write
        STATUS  mandatory
        DESCRIPTION "Break time in seconds between two trap checks;
                     '-1' means no trap case detection"
        ::= {utmTrapControl 13}
 
utmTrapCtrlCacheHitLimit   OBJECT-TYPE
        SYNTAX  INTEGER
        ACCESS  read-write
        STATUS  mandatory
        DESCRIPTION "Minimum rate (in percent) of cache hits before
                     sending a trap"
        ::= {utmTrapControl 14}
 
utmTrapCtrlPoolSizePeriod   OBJECT-TYPE
        SYNTAX  INTEGER
        ACCESS  read-write
        STATUS  mandatory
        DESCRIPTION "Break time in seconds between two trap checks;
                     '-1' means no trap case detection"
        ::= {utmTrapControl 15}
 
utmTrapCtrlPoolSizeLimit   OBJECT-TYPE
        SYNTAX  INTEGER
        ACCESS  read-write
        STATUS  mandatory
        DESCRIPTION "Maximum pool size (in percent) before sending
                     a trap"
        ::= {utmTrapControl 16}
 
utmTrapCtrlTclWaitMsgsPeriod   OBJECT-TYPE
        SYNTAX  INTEGER
        ACCESS  read-write
        STATUS  mandatory
        DESCRIPTION "Break time in seconds between two trap checks;
                     '-1' means no trap case detection"
        ::= {utmTrapControl 17}
 
utmTrapCtrlTclWaitMsgsLimit   OBJECT-TYPE
        SYNTAX  INTEGER
        ACCESS  read-write
        STATUS  mandatory
        DESCRIPTION "Necessary number of waiting messages for a 
                     TAC class before sending a trap"
        ::= {utmTrapControl 18}
 
utmTrapCtrlLtermWaitOutMsgsPeriod   OBJECT-TYPE
        SYNTAX  INTEGER
        ACCESS  read-write
        STATUS  mandatory
        DESCRIPTION "Break time in seconds between two trap checks;
                     '-1' means no trap case detection"
        ::= {utmTrapControl 19}
 
utmTrapCtrlLtermWaitOutMsgsLimit   OBJECT-TYPE
        SYNTAX  INTEGER
        ACCESS  read-write
        STATUS  mandatory
        DESCRIPTION "Necessary number of messages waiting to be output 
                     on a logical terminal before sending a trap"
        ::= {utmTrapControl 20}
 
 
 
 
 
 
 
 
 
 
 
 
-- UTM  Traps
--
 
utmApplAborted   TRAP-TYPE
              ENTERPRISE utmApplicationData
              DESCRIPTION "Application terminated"
      ::= 1
 
utmApplPENDER   TRAP-TYPE
              ENTERPRISE utmApplicationData
              DESCRIPTION "Termination with PEND ER"
      ::= 2
 
utmApplDeadlock   TRAP-TYPE
              ENTERPRISE utmApplicationData
              DESCRIPTION "Detected and resolved deadlock"
      ::= 3
 
utmApplUserSecurityViolations   TRAP-TYPE
              ENTERPRISE utmApplicationData
              DESCRIPTION "User security violations"
      ::= 4
 
utmApplConnectionLosses   TRAP-TYPE
              ENTERPRISE utmApplicationData
              DESCRIPTION "Connection losses to partner
                           applications"
      ::= 5
 
utmApplConnectedUsers   TRAP-TYPE
              ENTERPRISE utmApplicationData
              DESCRIPTION "Connected users"
      ::= 6
 
utmApplActiveTasks   TRAP-TYPE
              ENTERPRISE utmApplicationData
              DESCRIPTION "Active tasks"
      ::= 7
 
utmApplCacheHits   TRAP-TYPE
              ENTERPRISE utmApplicationData
              DESCRIPTION "Cache hit rate"
      ::= 8
 
utmApplPoolSize   TRAP-TYPE
              ENTERPRISE utmApplicationData
              DESCRIPTION "Page pool size"
      ::= 9
 
utmApplTacclassWaitMsgs   TRAP-TYPE
              ENTERPRISE utmApplicationData
              DESCRIPTION "Unprocessed messages for TAC classes"
      ::= 10
 
utmApplLtermWaitOutpMsgs   TRAP-TYPE
              ENTERPRISE utmApplicationData
              DESCRIPTION "Messages waiting to be output on
                           logical terminals"
      ::= 11
 
 
END
