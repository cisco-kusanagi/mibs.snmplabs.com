--
-- HUAWEI-SEP-MIBv2.my
-- Wednesday, December 02, 2009 at 16:58:09
-- 

HUAWEI-SEP-MIB DEFINITIONS ::= BEGIN

    IMPORTS
        hwDatacomm            
            FROM HUAWEI-MIB            
        EnabledStatus            
            FROM P-BRIDGE-MIB            
        VlanId            
            FROM Q-BRIDGE-MIB            
        OBJECT-GROUP, NOTIFICATION-GROUP            
            FROM SNMPv2-CONF            
        Integer32, Unsigned32, OBJECT-TYPE, MODULE-IDENTITY, OBJECT-IDENTITY, 
        InterfaceIndex, ifName
                       FROM IF-MIB
        NOTIFICATION-TYPE            
            FROM SNMPv2-SMI            
        RowStatus            
            FROM SNMPv2-TC;


    -- 1.3.6.1.4.1.2011.5.25.223
    hwSepMIB MODULE-IDENTITY 
        LAST-UPDATED "200911171530Z"
        ORGANIZATION 
            "Huawei Technologies Co.,Ltd."
        CONTACT-INFO 
            "8090 Team Huawei Technologies Co.,Ltd.
            Huawei Bld.,NO.3 Xinxi Rd., 
            Shang-Di Information Industry Base,
            Hai-Dian District Beijing P.R. China
            http://www.huawei.com
            Zip:100085
            "
        DESCRIPTION 
            "The private mib file includes the general extent 
            information of the device.hwDatacomm(165).hwSepMIB.
            "
        ::= { hwDatacomm 223 }

    


--
-- Node definitions
--

--  Node definitions
-- 
    -- 1.3.6.1.4.1.2011.5.25.223.1
    hwSepObjects OBJECT IDENTIFIER ::= { hwSepMIB 1 }

    
    -- 1.3.6.1.4.1.2011.5.25.223.1.1
    hwSepResetPktCnt OBJECT-TYPE
        SYNTAX INTEGER {
                                clear(1),
                                unused(65535)
                                }
        MAX-ACCESS read-write
        STATUS current
        DESCRIPTION
            "Reset the packet counter of all running SEP ports.
            The value of hwSepResetPktCnt is unused(65535) when it is read.
             The value of hwSepResetPktCnt must be clear(1) when it is set."
        ::= { hwSepObjects 1 }

    
    -- 1.3.6.1.4.1.2011.5.25.223.1.2
    hwSepSegmentTable OBJECT-TYPE
        SYNTAX SEQUENCE OF HwSepSegmentEntry
        MAX-ACCESS not-accessible
        STATUS current
        DESCRIPTION
            "The table includes the information of SEP segments."
        ::= { hwSepObjects 2 }

    
    -- 1.3.6.1.4.1.2011.5.25.223.1.2.1
    hwSepSegmentEntry OBJECT-TYPE
        SYNTAX HwSepSegmentEntry
        MAX-ACCESS not-accessible
        STATUS current
        DESCRIPTION
            "The table includes the information of SEP segments.
            The index of the table is SEP segment id."
        INDEX { hwSepSegmentId }
        ::= { hwSepSegmentTable 1 }

    
    HwSepSegmentEntry ::=
        SEQUENCE { 
            hwSepSegmentId
                Integer32,
            hwSepControlVlanId
                Integer32,
            hwSepPreemptManual
                Integer32,
            hwSepPreemptDelay
                Integer32,
            hwSepBlockPortMode
                INTEGER,
            hwSepBlockPortHop
                Integer32,
            hwSepBlockPortSysname
                OCTET STRING,
            hwSepBlockPortIfname
                OCTET STRING,
            hwSepTcNotifySep
                OCTET STRING,
            hwSepTcNotifyRrpp
                EnabledStatus,
            hwSepTcNotifyStp
                EnabledStatus,
            hwSepTcNotifyVpls
                EnabledStatus,
            hwSepTcNotifyVll
                EnabledStatus,
            hwSepTcNotifySmartLinkCtrlVlan
                Integer32,
            hwSepDealSmartLinkFlush
                EnabledStatus,
            hwSepProtectedInstanceList
                OCTET STRING,
            hwSepTcProtectionInterval
                   Integer32,
            hwSepSegmentRowStatus
                RowStatus
         }

    -- 1.3.6.1.4.1.2011.5.25.223.1.2.1.1
    hwSepSegmentId OBJECT-TYPE
        SYNTAX Integer32 (1..1024)
        MAX-ACCESS not-accessible
        STATUS current
        DESCRIPTION
            "SEP segment Identifier."
        ::= { hwSepSegmentEntry 1 }

    
    -- 1.3.6.1.4.1.2011.5.25.223.1.2.1.2
    hwSepControlVlanId OBJECT-TYPE
        SYNTAX Integer32 (0 | 1..4094)
        MAX-ACCESS read-create
        STATUS current
        DESCRIPTION
            "The control VLAN identifier of the SEP segment.
             If the value of the object is set 0, the operation is delete configuration."
        ::= { hwSepSegmentEntry 2 }

    
    -- 1.3.6.1.4.1.2011.5.25.223.1.2.1.3
    hwSepPreemptManual OBJECT-TYPE
        SYNTAX Integer32 (0..1)
        MAX-ACCESS read-create
        STATUS current
        DESCRIPTION
            "Trigger the manual preemption by setting the object to be 1. 
            When getting the object it will always be 0."
        ::= { hwSepSegmentEntry 3 }

    
    -- 1.3.6.1.4.1.2011.5.25.223.1.2.1.4
    hwSepPreemptDelay OBJECT-TYPE
        SYNTAX Integer32 (0 | 15..600)
        MAX-ACCESS read-create
        STATUS current
        DESCRIPTION
            "The preemption delay timer of the SEP segment.
             If the value of the object is set 0, the operation is delete configuration."
        ::= { hwSepSegmentEntry 4 }

    
    -- 1.3.6.1.4.1.2011.5.25.223.1.2.1.5
    hwSepBlockPortMode OBJECT-TYPE
        SYNTAX INTEGER
            {
            optimal(1),
            middle(2),
            hop(3),
            name(4),
            null(5)
            }
        MAX-ACCESS read-create
        STATUS current
        DESCRIPTION
            "The way to choose the port to be blocked.
            if the value of the object is set 1, the optimal port.
            if the value of the object is set 2, the middle port.
            if the value of the object is set 3, the port with the designated hop(hwSepBlockPortHop).
            if the value of the object is set 4, the port with the designated system name(hwSepBlockPortSysname) and port name(hwSepBlockPortIfname).
            if the value of the object is set 5, the operation is delete configuration of the block port.
            
            BlockPortMode          |                            BlockPortValue
                                   |     active                                                     inactive
            -----------------------|------------------------------------------------------------------------------
            optimal(1)             |     (1)                                                          (2/3/4)
            middle(2)              |     (2)                                                          (1/3/4)
            hop(3)                 |     (3)(hwSepBlockPortHop)                                       (1/2/4)
            name(4)                |     (4)(hwSepBlockPortSysname & hwSepBlockPortIfname)            (1/2/3)
            "
        ::= { hwSepSegmentEntry 5 }

    
    -- 1.3.6.1.4.1.2011.5.25.223.1.2.1.6
    hwSepBlockPortHop OBJECT-TYPE
        SYNTAX Integer32 (0 | 1..512)
        MAX-ACCESS read-create
        STATUS current
        DESCRIPTION
            "The hop count of the preffered blocking port.
             If the value of the object is set 0, the operation is delete configuration.
             If the mode of block port is not hop(3), the value is not have effect."
        ::= { hwSepSegmentEntry 6 }

    
    -- 1.3.6.1.4.1.2011.5.25.223.1.2.1.7
    hwSepBlockPortSysname OBJECT-TYPE
        SYNTAX OCTET STRING (SIZE (0..20))
        MAX-ACCESS read-create
        STATUS current
        DESCRIPTION
            "The system name of the preffered blocking port.
            if not set the value of hwSepBlockPortIfname, this configuration is not take effect.
            if the mode of block port is not name(4), this configuration is not task effect."
        ::= { hwSepSegmentEntry 7 }

    
    -- 1.3.6.1.4.1.2011.5.25.223.1.2.1.8
    hwSepBlockPortIfname OBJECT-TYPE
        SYNTAX OCTET STRING (SIZE (0..63))
        MAX-ACCESS read-create
        STATUS current
        DESCRIPTION
            "The interface name of the preffered blocking port.
            if not set the value of hwSepBlockPortSysname, this configuration is not take effect.
            if the mode of block port is not name(4), this configuration is not take effect."
        ::= { hwSepSegmentEntry 8 }

    
    -- 1.3.6.1.4.1.2011.5.25.223.1.2.1.9
    hwSepTcNotifySep OBJECT-TYPE
        SYNTAX OCTET STRING (SIZE (0..129))
        MAX-ACCESS read-create
        STATUS current
        DESCRIPTION
            "The bitmap of the SEP segments to which the topology change event will be notified "
        ::= { hwSepSegmentEntry 9 }

    
    -- 1.3.6.1.4.1.2011.5.25.223.1.2.1.10
    hwSepTcNotifyRrpp OBJECT-TYPE
        SYNTAX EnabledStatus
        MAX-ACCESS read-create
        STATUS current
        DESCRIPTION
            "If set 1, the topology change event of the SEP segment will be notified to RRPP"
        ::= { hwSepSegmentEntry 10 }

    
    -- 1.3.6.1.4.1.2011.5.25.223.1.2.1.11
    hwSepTcNotifyStp OBJECT-TYPE
        SYNTAX EnabledStatus
        MAX-ACCESS read-create
        STATUS current
        DESCRIPTION
            "If set 1, the topology change event of the SEP segment will be notified to STP"
        ::= { hwSepSegmentEntry 11 }

    
    -- 1.3.6.1.4.1.2011.5.25.223.1.2.1.12
    hwSepTcNotifyVpls OBJECT-TYPE
        SYNTAX EnabledStatus
        MAX-ACCESS read-create
        STATUS current
        DESCRIPTION
            "If set 1, the topology change event of the SEP segment will be notified to VPLS"
        ::= { hwSepSegmentEntry 12 }

    
    -- 1.3.6.1.4.1.2011.5.25.223.1.2.1.13
    hwSepTcNotifyVll OBJECT-TYPE
        SYNTAX EnabledStatus
        MAX-ACCESS read-create
        STATUS current
        DESCRIPTION
            "If set 1, the topology change event of the SEP segment will be notified to VLL"
        ::= { hwSepSegmentEntry 13 }

    
    -- 1.3.6.1.4.1.2011.5.25.223.1.2.1.14
    hwSepTcNotifySmartLinkCtrlVlan OBJECT-TYPE
        SYNTAX Integer32 (0 | 1..4094)
        MAX-ACCESS read-create
        STATUS current
        DESCRIPTION
            "If set control vlan, the topology change event of the SEP segment will be notified to Smart-Link.
             If the value of the object is set 0, the operation is delete configuration."
        ::= { hwSepSegmentEntry 14 }

    
    -- 1.3.6.1.4.1.2011.5.25.223.1.2.1.15
    hwSepDealSmartLinkFlush OBJECT-TYPE
        SYNTAX EnabledStatus
        MAX-ACCESS read-create
        STATUS current
        DESCRIPTION
            "If set 1, the SEP segment will deal the smart link flush-FDB packet"
        ::= { hwSepSegmentEntry 15 }

    
    -- 1.3.6.1.4.1.2011.5.25.223.1.2.1.16
    hwSepProtectedInstanceList OBJECT-TYPE
        SYNTAX OCTET STRING (SIZE (0..512))
        MAX-ACCESS read-create
        STATUS current
        DESCRIPTION
            " The protected instance list of the SEP segment"
        ::= { hwSepSegmentEntry 16 }


       -- 1.3.6.1.4.1.2011.5.25.223.1.2.1.17
       hwSepTcProtectionInterval OBJECT-TYPE
        SYNTAX Integer32 (1..10)
        MAX-ACCESS read-create
        STATUS current
        DESCRIPTION
            "The interval of tc-protection, the default value is 2."
        ::= { hwSepSegmentEntry 17 }
    
    
    -- 1.3.6.1.4.1.2011.5.25.223.1.2.1.128
    hwSepSegmentRowStatus OBJECT-TYPE
        SYNTAX RowStatus
        MAX-ACCESS read-create
        STATUS current
        DESCRIPTION
            "Operation of CreateAndGo can be used to create a new SEP segment, 
            and operation of Destroy be used to destroy an existent SEP segment."
        ::= { hwSepSegmentEntry 128 }

    
    -- 1.3.6.1.4.1.2011.5.25.223.1.3
    hwSepTopologyTable OBJECT-TYPE
        SYNTAX SEQUENCE OF HwSepTopologyEntry
        MAX-ACCESS not-accessible
        STATUS current
        DESCRIPTION
            "The table includes the information of the topology of the SEP segment."
        ::= { hwSepObjects 3 }

    
    -- 1.3.6.1.4.1.2011.5.25.223.1.3.1
    hwSepTopologyEntry OBJECT-TYPE
        SYNTAX HwSepTopologyEntry
        MAX-ACCESS not-accessible
        STATUS current
        DESCRIPTION
            "The table includes the information of the topology of the SEP segment.
            The index of the table is the segment identifier and the hop count of the port."
        INDEX { hwSepSegmentId, hwSepHop }
        ::= { hwSepTopologyTable 1 }

    
    HwSepTopologyEntry ::=
        SEQUENCE { 
            hwSepHop
                Integer32,
            hwSepPortId
                OCTET STRING,
            hwSepTopoSysname
                OCTET STRING,
            hwSepTopoPortname
                OCTET STRING,
            hwSepTopoPortConfigPriority
                Integer32,
            hwSepTopoPortActivePriority
                Integer32,
            hwSepTopoConfigPortRole
                Integer32,
            hwSepTopoActivePortRole
                Integer32,
            hwSepTopoPortNbrState
                INTEGER,
            hwSepTopoBrotherPortId
                OCTET STRING,
            hwSepTopoNbrPortId
                OCTET STRING,
            hwSepTopoPortLinkState
                INTEGER,
            hwSepTopoPortFwdState
                INTEGER
         }

    -- 1.3.6.1.4.1.2011.5.25.223.1.3.1.1
    hwSepHop OBJECT-TYPE
        SYNTAX Integer32 (1..512)
        MAX-ACCESS not-accessible
        STATUS current
        DESCRIPTION
            "The hop count of the port."
        ::= { hwSepTopologyEntry 1 }

    
    -- 1.3.6.1.4.1.2011.5.25.223.1.3.1.2
    hwSepPortId OBJECT-TYPE
        SYNTAX OCTET STRING (SIZE (0..8))
        MAX-ACCESS read-only
        STATUS current
        DESCRIPTION
                "The port identifier. For example: 00.E0.6E.70.23.00.00.00 (hex). The first 6 bytes is the mac address of the device"
        ::= { hwSepTopologyEntry 2 }

    
    -- 1.3.6.1.4.1.2011.5.25.223.1.3.1.3
    hwSepTopoSysname OBJECT-TYPE
        SYNTAX OCTET STRING (SIZE (0..20))
        MAX-ACCESS read-only
        STATUS current
        DESCRIPTION
            "The system name."
        ::= { hwSepTopologyEntry 3 }

    
    -- 1.3.6.1.4.1.2011.5.25.223.1.3.1.4
    hwSepTopoPortname OBJECT-TYPE
        SYNTAX OCTET STRING (SIZE (0..16))
        MAX-ACCESS read-only
        STATUS current
        DESCRIPTION
            "The port name."
        ::= { hwSepTopologyEntry 4 }

    
    -- 1.3.6.1.4.1.2011.5.25.223.1.3.1.5
    hwSepTopoPortConfigPriority OBJECT-TYPE
        SYNTAX Integer32 (1..128)
        MAX-ACCESS read-only
        STATUS current
        DESCRIPTION
                "The configured port priority.The default value is 64."
        ::= { hwSepTopologyEntry 5 }

    
    -- 1.3.6.1.4.1.2011.5.25.223.1.3.1.6
    hwSepTopoPortActivePriority OBJECT-TYPE
        SYNTAX Integer32
        MAX-ACCESS read-only
        STATUS current
        DESCRIPTION
            "The active port priority."
        ::= { hwSepTopologyEntry 6 }

    
    -- 1.3.6.1.4.1.2011.5.25.223.1.3.1.7
    hwSepTopoConfigPortRole OBJECT-TYPE
        SYNTAX Integer32
        MAX-ACCESS read-only
        STATUS current
        DESCRIPTION
            "The configued port role:
            role                       value
            common                      0x10
            edge secondary              0x21
            edge primary                0x22
            no neighbor edge secondary  0x31
            no neighbor edge primary    0x32"
        ::= { hwSepTopologyEntry 7 }

    
    -- 1.3.6.1.4.1.2011.5.25.223.1.3.1.8
    hwSepTopoActivePortRole OBJECT-TYPE
        SYNTAX Integer32
        MAX-ACCESS read-only
        STATUS current
        DESCRIPTION
            "The active port role:
            role                       value
            common                      0x10
            edge secondary              0x21
            edge primary                0x22
            no neighbor edge secondary  0x31
            no neighbor edge primary    0x32"
        ::= { hwSepTopologyEntry 8 }

    
    -- 1.3.6.1.4.1.2011.5.25.223.1.3.1.9
    hwSepTopoPortNbrState OBJECT-TYPE
        SYNTAX INTEGER
            {
            down(1),
            init(2),
            preup(3),
            up(4),
            conflict(5)
            }
        MAX-ACCESS read-only
        STATUS current
        DESCRIPTION
            "The state of the neighbor state machine:
            state      value
            down       1
            init       2
            preup      3
            up         4
            conflict   5"
        ::= { hwSepTopologyEntry 9 }

    
    -- 1.3.6.1.4.1.2011.5.25.223.1.3.1.10
    hwSepTopoBrotherPortId OBJECT-TYPE
        SYNTAX OCTET STRING (SIZE (0..8))
        MAX-ACCESS read-only
        STATUS current
        DESCRIPTION
                "The brother port identifier. For example: 00.E0.6E.70.23.00.00.00 (hex). The first 6 bytes is the mac address of the device"
        ::= { hwSepTopologyEntry 10 }

    
    -- 1.3.6.1.4.1.2011.5.25.223.1.3.1.11
    hwSepTopoNbrPortId OBJECT-TYPE
        SYNTAX OCTET STRING (SIZE (0..8))
        MAX-ACCESS read-only
        STATUS current
        DESCRIPTION
                "The neighbor port identifier. For example: 00.E0.6E.70.23.00.00.00 (hex). The first 6 bytes is the mac address of the device"
        ::= { hwSepTopologyEntry 11 }

    
    -- 1.3.6.1.4.1.2011.5.25.223.1.3.1.12
    hwSepTopoPortLinkState OBJECT-TYPE
        SYNTAX INTEGER
            {
            down(1),
            up(2)
            }
        MAX-ACCESS read-only
        STATUS current
        DESCRIPTION
            "The link state of the port:
            state         value
            link down      1
            link up        2"
        ::= { hwSepTopologyEntry 12 }

    
    -- 1.3.6.1.4.1.2011.5.25.223.1.3.1.13
    hwSepTopoPortFwdState OBJECT-TYPE
        SYNTAX INTEGER
            {
            discarding(1),
            forwarding(2)
            }
        MAX-ACCESS read-only
        STATUS current
        DESCRIPTION
            "The forwarding state of the port:
            state         value
            discarding     1
            forwarding     2"
        ::= { hwSepTopologyEntry 13 }

    
    -- 1.3.6.1.4.1.2011.5.25.223.1.4
    hwSepPortTable OBJECT-TYPE
        SYNTAX SEQUENCE OF HwSepPortEntry
        MAX-ACCESS not-accessible
        STATUS current
        DESCRIPTION
            "The table includes the information of SEP ports"
        ::= { hwSepObjects 4 }

    
    -- 1.3.6.1.4.1.2011.5.25.223.1.4.1
    hwSepPortEntry OBJECT-TYPE
        SYNTAX HwSepPortEntry
        MAX-ACCESS not-accessible
        STATUS current
        DESCRIPTION
            "The table includes the information of SEP ports.
            The index of the table is SEP segment identifier, port type, port identifier1, port identifier2, port identifier3, port identifier4.
            If it is an ethernet port including fast ethernet/gigabit ethernet/eth-trunk, the port type is 1, the port identifier1 is the IfIndex of the ethernet port.
            the other port identifier is for extension and not used currently, should be set 0."
        INDEX { hwSepSegmentId, hwSepPortType, hwSepPortId1, hwSepPortId2, hwSepPortId3, 
            hwSepPortId4 }
        ::= { hwSepPortTable 1 }

    
    HwSepPortEntry ::=
        SEQUENCE { 
            hwSepPortType
                Unsigned32,
            hwSepPortId1
                Unsigned32,
            hwSepPortId2
                Unsigned32,
            hwSepPortId3
                Unsigned32,
            hwSepPortId4
                Unsigned32,
            hwSepSysname
                OCTET STRING,
            hwSepPortname
                OCTET STRING,
            hwSepPortConfigPriority
                Integer32,
            hwSepPortActivePriority
                Integer32,
            hwSepConfigPortRole
                Integer32,
            hwSepActivePortRole
                Integer32,
            hwSepPortNbrState
                INTEGER,
            hwSepNbrPortId
                OCTET STRING,
            hwSepPortFwdState
                INTEGER,
            hwSepRxNbrPktCnt
                Integer32,
            hwSepTxNbrPktCnt
                Integer32,
            hwSepRxLsaInfoPktCnt
                Integer32,
            hwSepTxLsaInfoPktCnt
                Integer32,
            hwSepRxLsaAckPktCnt
                Integer32,
            hwSepTxLsaAckPktCnt
                Integer32,
            hwSepRxPreemptReqPktCnt
                Integer32,
            hwSepTxPreemptReqPktCnt
                Integer32,
            hwSepRxPreemptAckPktCnt
                Integer32,
            hwSepTxPreemptAckPktCnt
                Integer32,
            hwSepRxTcPktCnt
                Integer32,
            hwSepTxTcPktCnt
                Integer32,  
            hwSepRxEpaPktCnt
                Integer32,
            hwSepTxEpaPktCnt
                Integer32,                  
            hwSepResetPortPktCnt
                INTEGER,
            hwSepPortRowStatus
                RowStatus
         }

    -- 1.3.6.1.4.1.2011.5.25.223.1.4.1.1
    hwSepPortType OBJECT-TYPE
        SYNTAX Unsigned32 (1)
        MAX-ACCESS not-accessible
        STATUS current
        DESCRIPTION
            "The port type.Currently SEP just support ethernet port and the value is 1."
        ::= { hwSepPortEntry 1 }

    
    -- 1.3.6.1.4.1.2011.5.25.223.1.4.1.2
    hwSepPortId1 OBJECT-TYPE
        SYNTAX Unsigned32 (0..2147483647)
        MAX-ACCESS not-accessible
        STATUS current
        DESCRIPTION
            "The port identifier1, when the hwSepPortType is 1, the value of the object is the IfIndex of the port."
        ::= { hwSepPortEntry 2 }

    
    -- 1.3.6.1.4.1.2011.5.25.223.1.4.1.3
    hwSepPortId2 OBJECT-TYPE
        SYNTAX Unsigned32 (0..2147483647)
        MAX-ACCESS not-accessible
        STATUS current
        DESCRIPTION
            "The port identifier2, Currently it is not used and only for extension, should be set 0."
        ::= { hwSepPortEntry 3 }

    
    -- 1.3.6.1.4.1.2011.5.25.223.1.4.1.4
    hwSepPortId3 OBJECT-TYPE
        SYNTAX Unsigned32 (0..2147483647)
        MAX-ACCESS not-accessible
        STATUS current
        DESCRIPTION
            "The port identifier3, Currently it is not used and only for extension, should be set 0."
        ::= { hwSepPortEntry 4 }

    
    -- 1.3.6.1.4.1.2011.5.25.223.1.4.1.5
    hwSepPortId4 OBJECT-TYPE
        SYNTAX Unsigned32 (0..2147483647)
        MAX-ACCESS not-accessible
        STATUS current
        DESCRIPTION
            "The port identifier4, Currently it is not used and only for extension, should be set 0."
        ::= { hwSepPortEntry 5 }

    
    -- 1.3.6.1.4.1.2011.5.25.223.1.4.1.6
    hwSepSysname OBJECT-TYPE
        SYNTAX OCTET STRING (SIZE (0..20))
        MAX-ACCESS read-only
        STATUS current
        DESCRIPTION
            "The system name."
        ::= { hwSepPortEntry 6 }

    
    -- 1.3.6.1.4.1.2011.5.25.223.1.4.1.7
    hwSepPortname OBJECT-TYPE
        SYNTAX OCTET STRING (SIZE (0..16))
        MAX-ACCESS read-only
        STATUS current
        DESCRIPTION
            "The port name"
        ::= { hwSepPortEntry 7 }

    
    -- 1.3.6.1.4.1.2011.5.25.223.1.4.1.8
    hwSepPortConfigPriority OBJECT-TYPE
        SYNTAX Integer32 (1..128)
        MAX-ACCESS read-create
        STATUS current
        DESCRIPTION
                "The configured port priority.The default value is 64."
        ::= { hwSepPortEntry 8 }

    
    -- 1.3.6.1.4.1.2011.5.25.223.1.4.1.9
    hwSepPortActivePriority OBJECT-TYPE
        SYNTAX Integer32
        MAX-ACCESS read-only
        STATUS current
        DESCRIPTION
            "The active port priority."
        ::= { hwSepPortEntry 9 }

    
    -- 1.3.6.1.4.1.2011.5.25.223.1.4.1.10
    hwSepConfigPortRole OBJECT-TYPE
        SYNTAX Integer32
        MAX-ACCESS read-create
        STATUS current
        DESCRIPTION
            "The configued port role:
            role                       value
            common                      0x10
            edge secondary              0x21
            edge primary                0x22
            no neighbor edge secondary  0x31
            no neighbor edge primary    0x32"
        ::= { hwSepPortEntry 10 }

    
    -- 1.3.6.1.4.1.2011.5.25.223.1.4.1.11
    hwSepActivePortRole OBJECT-TYPE
        SYNTAX Integer32
        MAX-ACCESS read-only
        STATUS current
        DESCRIPTION
            "The active port role:
            role                       value
            common                      0x10
            edge secondary              0x21
            edge primary                0x22
            no neighbor edge secondary  0x31
            no neighbor edge primary    0x32"
        ::= { hwSepPortEntry 11 }

    
    -- 1.3.6.1.4.1.2011.5.25.223.1.4.1.12
    hwSepPortNbrState OBJECT-TYPE
        SYNTAX INTEGER
            {
            down(1),
            init(2),
            preup(3),
            up(4),
            conflict(5)
            }
        MAX-ACCESS read-only
        STATUS current
        DESCRIPTION
            "The state of the neighbor state machine:
            state      value
            down       1
            init       2
            preup      3
            up         4
            conflict   5"
        ::= { hwSepPortEntry 12 }

    
    -- 1.3.6.1.4.1.2011.5.25.223.1.4.1.13
    hwSepNbrPortId OBJECT-TYPE
        SYNTAX OCTET STRING (SIZE (0..8))
        MAX-ACCESS read-only
        STATUS current
        DESCRIPTION
                "The identifier of the neighbor port. For example: 00.E0.6E.70.23.00.00.00 (hex)
                "
        ::= { hwSepPortEntry 13 }

    
    -- 1.3.6.1.4.1.2011.5.25.223.1.4.1.14
        hwSepPortFwdState OBJECT-TYPE
            SYNTAX INTEGER
                {
                discarding(1),
                forwarding(2)
                }
            MAX-ACCESS read-only
            STATUS current
            DESCRIPTION
                "The forwarding state of the port:
                state         value
                discarding     1
                forwarding     2"
            ::= { hwSepPortEntry 14 }

    
    -- 1.3.6.1.4.1.2011.5.25.223.1.4.1.15
    hwSepRxNbrPktCnt OBJECT-TYPE
        SYNTAX Integer32
        MAX-ACCESS read-only
        STATUS current
        DESCRIPTION
            "The number of received neighbor packets."
        ::= { hwSepPortEntry 15 }

    
    -- 1.3.6.1.4.1.2011.5.25.223.1.4.1.16
    hwSepTxNbrPktCnt OBJECT-TYPE
        SYNTAX Integer32
        MAX-ACCESS read-only
        STATUS current
        DESCRIPTION
            "The number of transmited neighbor packets."
        ::= { hwSepPortEntry 16 }

    
    -- 1.3.6.1.4.1.2011.5.25.223.1.4.1.17
    hwSepRxLsaInfoPktCnt OBJECT-TYPE
        SYNTAX Integer32
        MAX-ACCESS read-only
        STATUS current
        DESCRIPTION
                "The number of received LSA information packets."
        ::= { hwSepPortEntry 17 }

    
    -- 1.3.6.1.4.1.2011.5.25.223.1.4.1.18
    hwSepTxLsaInfoPktCnt OBJECT-TYPE
        SYNTAX Integer32
        MAX-ACCESS read-only
        STATUS current
        DESCRIPTION
                "The number of transmitted LSA information packets."
        ::= { hwSepPortEntry 18 }

    
    -- 1.3.6.1.4.1.2011.5.25.223.1.4.1.19
    hwSepRxLsaAckPktCnt OBJECT-TYPE
        SYNTAX Integer32
        MAX-ACCESS read-only
        STATUS current
        DESCRIPTION
                "The number of received LSA acknowledgement packets."
        ::= { hwSepPortEntry 19 }

    
    -- 1.3.6.1.4.1.2011.5.25.223.1.4.1.20
    hwSepTxLsaAckPktCnt OBJECT-TYPE
        SYNTAX Integer32
        MAX-ACCESS read-only
        STATUS current
        DESCRIPTION
                "The number of transmitted LSA acknowledgement packets."
        ::= { hwSepPortEntry 20 }

    
    -- 1.3.6.1.4.1.2011.5.25.223.1.4.1.21
    hwSepRxPreemptReqPktCnt OBJECT-TYPE
        SYNTAX Integer32
        MAX-ACCESS read-only
        STATUS current
        DESCRIPTION
                "The number of received preemption request packets."
        ::= { hwSepPortEntry 21 }

    
    -- 1.3.6.1.4.1.2011.5.25.223.1.4.1.22
    hwSepTxPreemptReqPktCnt OBJECT-TYPE
        SYNTAX Integer32
        MAX-ACCESS read-only
        STATUS current
        DESCRIPTION
                "The number of transmitted preemption request packets."
        ::= { hwSepPortEntry 22 }

    
    -- 1.3.6.1.4.1.2011.5.25.223.1.4.1.23
    hwSepRxPreemptAckPktCnt OBJECT-TYPE
        SYNTAX Integer32
        MAX-ACCESS read-only
        STATUS current
        DESCRIPTION
                "The number of received preemption acknowledgement packets."
        ::= { hwSepPortEntry 23 }

    
    -- 1.3.6.1.4.1.2011.5.25.223.1.4.1.24
    hwSepTxPreemptAckPktCnt OBJECT-TYPE
        SYNTAX Integer32
        MAX-ACCESS read-only
        STATUS current
        DESCRIPTION
                "The number of transmitted preemption acknowledgement packets."
        ::= { hwSepPortEntry 24 }

    
    -- 1.3.6.1.4.1.2011.5.25.223.1.4.1.25
    hwSepRxTcPktCnt OBJECT-TYPE
        SYNTAX Integer32
        MAX-ACCESS read-only
        STATUS current
        DESCRIPTION
                "The number of received topology change packets."
        ::= { hwSepPortEntry 25 }

    
    -- 1.3.6.1.4.1.2011.5.25.223.1.4.1.26
    hwSepTxTcPktCnt OBJECT-TYPE
        SYNTAX Integer32
        MAX-ACCESS read-only
        STATUS current
        DESCRIPTION
                "The number of transmitted topology change packets."
        ::= { hwSepPortEntry 26 }

    -- 1.3.6.1.4.1.2011.5.25.223.1.4.1.27
    hwSepRxEpaPktCnt OBJECT-TYPE
        SYNTAX Integer32
        MAX-ACCESS read-only
        STATUS current
        DESCRIPTION
                "The number of received topology change packets."
        ::= { hwSepPortEntry 27 }

    
    -- 1.3.6.1.4.1.2011.5.25.223.1.4.1.28
    hwSepTxEpaPktCnt OBJECT-TYPE
        SYNTAX Integer32
        MAX-ACCESS read-only
        STATUS current
        DESCRIPTION
                "The number of transmitted topology change packets."
        ::= { hwSepPortEntry 28 }
    
        -- 1.3.6.1.4.1.2011.5.25.223.1.4.1.29
        hwSepResetPortPktCnt OBJECT-TYPE
            SYNTAX INTEGER
                {
                clear(1),
                unused(65535)
                }
            MAX-ACCESS read-write
            STATUS current
            DESCRIPTION
            "Reset the packet counter of the port in the SEP segment.
            The value of hwSepResetPktCnt is unused(65535) when it is read.
                        The value of hwSepResetPktCnt must be clear(1) when it is set."
            ::= { hwSepPortEntry 29 }
            
    -- 1.3.6.1.4.1.2011.5.25.223.1.4.1.128
    hwSepPortRowStatus OBJECT-TYPE
        SYNTAX RowStatus
        MAX-ACCESS read-create
        STATUS current
        DESCRIPTION
            "Operation of CreateAndGo can be used to have a port join the SEP segment.
            and operation of Destroy be used to have a port leave the SEP segment."
        ::= { hwSepPortEntry 128 }

    
    -- 1.3.6.1.4.1.2011.5.25.223.2
    hwSepGroups OBJECT IDENTIFIER ::= { hwSepMIB 2 }

    
    -- 1.3.6.1.4.1.2011.5.25.223.2.1
    hwSepGlobalInfoGroup OBJECT-GROUP
        OBJECTS { hwSepResetPktCnt }
        STATUS current
        DESCRIPTION 
            "The group of global information."
        ::= { hwSepGroups 1 }

    
    -- 1.3.6.1.4.1.2011.5.25.223.2.2
    hwSepSegmentInfoGroup OBJECT-GROUP
        OBJECTS { hwSepSegmentId, hwSepControlVlanId, hwSepPreemptManual, hwSepPreemptDelay, hwSepBlockPortMode, 
            hwSepBlockPortHop, hwSepBlockPortSysname, hwSepBlockPortIfname, hwSepTcNotifySep, hwSepTcNotifyRrpp, 
            hwSepTcNotifyStp, hwSepTcNotifyVpls, hwSepTcNotifyVll, hwSepTcNotifySmartLinkCtrlVlan, hwSepDealSmartLinkFlush, 
            hwSepProtectedInstanceList, hwSepTcProtectionInterval, hwSepSegmentRowStatus }
        STATUS current
        DESCRIPTION 
            "The group of segment information."
        ::= { hwSepGroups 2 }

    
    -- 1.3.6.1.4.1.2011.5.25.223.2.3
    hwSepPortInfoGroup OBJECT-GROUP
        OBJECTS { hwSepPortType, hwSepPortId1, hwSepPortId2, hwSepPortId3, hwSepPortId4, 
            hwSepSysname, hwSepPortname, hwSepPortConfigPriority, hwSepPortActivePriority, hwSepConfigPortRole, 
            hwSepActivePortRole, hwSepPortNbrState, hwSepNbrPortId, hwSepPortFwdState, hwSepRxNbrPktCnt, 
            hwSepTxNbrPktCnt, hwSepRxLsaInfoPktCnt, hwSepTxLsaInfoPktCnt, hwSepRxLsaAckPktCnt, hwSepTxLsaAckPktCnt, 
            hwSepRxPreemptReqPktCnt, hwSepTxPreemptReqPktCnt, hwSepRxPreemptAckPktCnt, hwSepTxPreemptAckPktCnt, hwSepRxTcPktCnt, 
            hwSepTxTcPktCnt, hwSepRxEpaPktCnt, hwSepTxEpaPktCnt, hwSepResetPortPktCnt, hwSepPortRowStatus }
        STATUS current
        DESCRIPTION 
            "The group of port information."
        ::= { hwSepGroups 3 }

    
    -- 1.3.6.1.4.1.2011.5.25.223.2.4
    hwSepTopologyInfoGroup OBJECT-GROUP
        OBJECTS { hwSepHop, hwSepPortId, hwSepTopoSysname, hwSepTopoPortname, hwSepTopoPortConfigPriority, 
            hwSepTopoPortActivePriority, hwSepTopoConfigPortRole, hwSepTopoActivePortRole, hwSepTopoPortNbrState, hwSepTopoNbrPortId, 
            hwSepTopoPortLinkState, hwSepTopoPortFwdState, hwSepTopoBrotherPortId }
        STATUS current
        DESCRIPTION 
            "The group of topology information."
        ::= { hwSepGroups 4 }
    

END

--
-- HUAWEI-SEP-MIBv2.my
--
