--AHB mib file #2
--BayNetworks-AHB-MIB definitions
 
BayNetworks-AHB-MIB DEFINITIONS ::= BEGIN
 
 
    IMPORTS
 
      IpAddress, Counter, Gauge
        FROM RFC1155-SMI
      OBJECT-TYPE
        FROM RFC-1212
      DisplayString
        FROM RFC1213-MIB
      wfAtmHalfBridgeGroup
        FROM Wellfleet-COMMON-MIB;

    MacAddress ::= OCTET STRING (SIZE (6)) 

    wfAhb  OBJECT IDENTIFIER ::= { wfAtmHalfBridgeGroup 1 }

    wfAhbDelete	OBJECT-TYPE
        SYNTAX  INTEGER {
                created(1),
                deleted(2)
        }
        ACCESS  read-write
        STATUS  mandatory
        DESCRIPTION
                "Create or Delete AHB Function."
	DEFVAL  { created }
        ::= { wfAhb 1 }

    wfAhbDisable OBJECT-TYPE
        SYNTAX	INTEGER {
    		    enabled(1),
    		    disabled(2)
    		}
        ACCESS	read-write
        STATUS	mandatory
        DESCRIPTION
                "Enables or Disables AHB Function."
        DEFVAL	{ enabled }
        ::= {  wfAhb 2 }

    wfAhbAutoLearnMethod OBJECT-TYPE
        SYNTAX	INTEGER {
    		    none(1),
                    unsecure(2),
                    secure(3),
    		    both(4)
    		}
        ACCESS	read-write
        STATUS	mandatory
        DESCRIPTION
                "Method used to dynamically learn new host entries."
        DEFVAL	{ both }
        ::= {  wfAhb 3 }

    wfAhbInitFile OBJECT-TYPE
        SYNTAX  DisplayString (SIZE (0..200))
        ACCESS  read-write
        STATUS  mandatory
        DESCRIPTION
                "Name of local file containing AHB initial host entries."
        DEFVAL  { "" }
        ::= {  wfAhb 4 }

    wfAhbAltInitFile OBJECT-TYPE
        SYNTAX  DisplayString (SIZE (0..200))
        ACCESS  read-write
        STATUS  mandatory
        DESCRIPTION
                "Name of alternate file containing AHB initial host entries."
        DEFVAL  { "" }
        ::= {  wfAhb 5 }

    wfAhbDebugLevel OBJECT-TYPE
        SYNTAX  INTEGER
        ACCESS  read-write
        STATUS  mandatory
        DESCRIPTION
                "Level of debug messages to include in system log.
                Zero indicates no debug messages, higher values 
                display more detailed information."
        DEFVAL  { 0 }
        ::= {  wfAhb 6 }

    wfAhbInboundFiltDisable OBJECT-TYPE
        SYNTAX  INTEGER {
                enabled(1),
                disabled(2)
        }
        ACCESS  read-write
        STATUS  mandatory
        DESCRIPTION
                "Enable or disable inbound packet filtering on AHB circuits."
        DEFVAL  { disabled }
        ::= {  wfAhb 7 }

    wfAhbReset OBJECT-TYPE
       SYNTAX  INTEGER {
                    notreset(1),
                    reset(2)
                }
        ACCESS  read-write
        STATUS  mandatory
        DESCRIPTION
                "Reset AHB state and remove all dynamic hosts entries from half-bridge table."
        DEFVAL  { notreset }
        ::= {  wfAhb 8 }

    wfAhbStatNumNets OBJECT-TYPE
	SYNTAX  Gauge
        ACCESS  read-only
        STATUS  mandatory
        DESCRIPTION
             "Number of IP networks advertised by half-bridge."
         ::= { wfAhb 9 }

    wfAhbStatNumHosts OBJECT-TYPE
	SYNTAX  Gauge
        ACCESS  read-only
        STATUS  mandatory
        DESCRIPTION
             "Number of hosts entries maintained by half-bridge."
         ::= { wfAhb 10 }

    wfAhbStatTotOutPkts OBJECT-TYPE
	SYNTAX  Counter
        ACCESS  read-only
        STATUS  mandatory
        DESCRIPTION
             "Number of outgoing packets sent to half-bridge from other router interfaces."
         ::= { wfAhb 11 }

    wfAhbStatFwdOutPkts OBJECT-TYPE
        SYNTAX  Counter   
        ACCESS  read-only 
        STATUS  mandatory 
        DESCRIPTION 
             "Number of outgoing packets forwarded by half-bridge on ATM interfaces."
         ::= { wfAhb 12 } 

    wfAhbStatDropUnkPkts OBJECT-TYPE
        SYNTAX  Counter   
        ACCESS  read-only 
        STATUS  mandatory 
        DESCRIPTION 
             "Number of outgoing packets dropped due to unknown host."
         ::= { wfAhb 13 } 

    wfAhbStatTotInPkts OBJECT-TYPE
        SYNTAX  Counter   
        ACCESS  read-only 
        STATUS  mandatory 
        DESCRIPTION 
             "Number of packets received on all AHB interfaces."
         ::= { wfAhb 14 } 

    wfAhbStatFwdInPkts OBJECT-TYPE
        SYNTAX  Counter   
        ACCESS  read-only 
        STATUS  mandatory 
        DESCRIPTION 
             "Number of packets forwarded from AHB interfaces."
         ::= { wfAhb 15 } 

    wfAhbStatNumHostCopies OBJECT-TYPE
        SYNTAX  Counter   
        ACCESS  read-only 
        STATUS  mandatory 
        DESCRIPTION 
             "Number of host entries copied to other slots."
         ::= { wfAhb 16 } 

    wfAhbPolicyDisable OBJECT-TYPE
        SYNTAX	INTEGER {
    		    enabled(1),
    		    disabled(2)
    		}
        ACCESS	read-write
        STATUS	mandatory
        DESCRIPTION
                "Enables or disables policy table processing."
        DEFVAL	{ disabled }
        ::= {  wfAhb 17 }

    wfAhbBaseStatus OBJECT-TYPE
        SYNTAX  INTEGER {
                up(1),
                down(2),
                init(3),
                notpres(4)
        }
        ACCESS  read-only
        STATUS  mandatory
        DESCRIPTION
                "Status of the AHB module."
        DEFVAL { notpres }
        ::= { wfAhb 18 }

    wfAhbCctTable OBJECT-TYPE
        SYNTAX  SEQUENCE OF WfAhbCctEntry
        ACCESS  not-accessible
        STATUS  mandatory
        DESCRIPTION
                "A list of circuit entries in ATM bridge table."
        ::= { wfAtmHalfBridgeGroup 2 }
 
    wfAhbCctEntry OBJECT-TYPE
        SYNTAX  WfAhbCctEntry
        ACCESS  not-accessible
        STATUS  mandatory
        DESCRIPTION
                "ATM Half Bridge Interface Entry. "
        INDEX   {
                  wfAhbCctNum }
        ::= { wfAhbCctTable 1 }
 
 
    WfAhbCctEntry ::= SEQUENCE {
        wfAhbCctDelete
                INTEGER,
        wfAhbCctDisable
		INTEGER,
        wfAhbCctNum
                INTEGER,
        wfAhbCctDefSubNetMask
        	IpAddress,
        wfAhbCctProxyArpDisable
		INTEGER,
        wfAhbCctMaxIdleTime
		INTEGER,
        wfAhbCctStatus
		INTEGER,
        wfAhbCctTxPkts
		Counter,
	wfAhbCctTxDrop
		Counter,
        wfAhbCctRxPkts
		Counter,
	wfAhbCctRxDrop
		Counter
    }
 
    wfAhbCctDelete OBJECT-TYPE
        SYNTAX  INTEGER {
                created(1),
                deleted(2)
        }
        ACCESS  read-write
        STATUS  mandatory
        DESCRIPTION
                "Create/Delete this ATM HALF BRIDGE interface."
        DEFVAL  { created }
        ::= { wfAhbCctEntry 1 }

    wfAhbCctDisable OBJECT-TYPE
        SYNTAX  INTEGER {
                enabled(1),
                disabled(2)
        }
        ACCESS  read-write
        STATUS  mandatory
        DESCRIPTION
                "Enable/disable this ATM HALF BRIDGE interface."
        DEFVAL  { enabled }
        ::= { wfAhbCctEntry 2 }
 
    wfAhbCctNum OBJECT-TYPE
        SYNTAX  INTEGER
        ACCESS  read-only
        STATUS  mandatory
        DESCRIPTION
                "The circuit number associated with this AHB interface."
        ::= { wfAhbCctEntry 3 }
 
    wfAhbCctDefSubNetMask OBJECT-TYPE
        SYNTAX  IpAddress
        ACCESS  read-write
        STATUS  mandatory
        DESCRIPTION
                "The default subnet mask for hosts learned unsecurely 
                 on this interface."
        ::= { wfAhbCctEntry 4 }
 
    wfAhbCctProxyArpDisable OBJECT-TYPE
        SYNTAX  INTEGER {
                enabled(1),
                disabled(2)
        }
        ACCESS  read-write
        STATUS  mandatory
        DESCRIPTION
                "Enable/Disable proxy ARP function on this interface."
        DEFVAL { enabled }
        ::= { wfAhbCctEntry 5 }
 
    wfAhbCctMaxIdleTime OBJECT-TYPE
        SYNTAX  INTEGER {
                minimum(5),
                default(3600)
        }
        ACCESS  read-write
        STATUS  mandatory
        DESCRIPTION
                "Maximum idle time for aging unsecure host entries"
        DEFVAL { default }
        ::= { wfAhbCctEntry 6 }

    wfAhbCctStatus OBJECT-TYPE
        SYNTAX  INTEGER {
                up(1),
                down(2)
        }
        ACCESS  read-only
        STATUS  mandatory
        DESCRIPTION
                "Status of the corresponding ATM circuit."
        DEFVAL { down }
        ::= { wfAhbCctEntry 7 }
 
    wfAhbCctTxPkts OBJECT-TYPE
        SYNTAX  Counter
        ACCESS  read-only
        STATUS  mandatory
        DESCRIPTION
                "Number of outgoing packets sent on this interface."
        ::= { wfAhbCctEntry 8 }
 
    wfAhbCctTxDrop OBJECT-TYPE
        SYNTAX  Counter
        ACCESS  read-only
        STATUS  mandatory
        DESCRIPTION
                "Number of outgoing packets dropped on this interface."
        ::= { wfAhbCctEntry 9 }

    wfAhbCctRxPkts OBJECT-TYPE
        SYNTAX  Counter
        ACCESS  read-only
        STATUS  mandatory
        DESCRIPTION
                "Number of incoming packets received on this interface."
        ::= { wfAhbCctEntry 10 }
 
    wfAhbCctRxDrop OBJECT-TYPE
        SYNTAX  Counter
        ACCESS  read-only
        STATUS  mandatory
        DESCRIPTION
                "Number of incoming packets dropped on this interface."
        ::= { wfAhbCctEntry 11 }
 
    wfAhbHostTable OBJECT-TYPE
        SYNTAX  SEQUENCE OF WfAhbHostEntry
        ACCESS  not-accessible
        STATUS  mandatory
        DESCRIPTION
                "A list of host entries in ATM half-bridge table."
        ::= { wfAtmHalfBridgeGroup 3 }
 
    wfAhbHostEntry OBJECT-TYPE
        SYNTAX  WfAhbHostEntry
        ACCESS  not-accessible
        STATUS  mandatory
        DESCRIPTION
                "ATM Half Bridge Host Entry."
        INDEX   {
                  wfAhbHostSlot,
                  wfAhbHostIpAddress
		 }
        ::= { wfAhbHostTable 1 }
 
    WfAhbHostEntry ::= SEQUENCE {
        wfAhbHostDelete
                INTEGER,
        wfAhbHostSlot
                INTEGER,
        wfAhbHostSeqNum
                INTEGER,
        wfAhbHostIpAddress
                IpAddress,
        wfAhbHostSubNetMask
                IpAddress,
        wfAhbHostCct 
                INTEGER,
        wfAhbHostVcid
                INTEGER,
        wfAhbHostBridgeHdr
                DisplayString,
        wfAhbHostFlags
		INTEGER,
        wfAhbHostTxPkts
                Counter,
        wfAhbHostRxPkts
                Counter,
        wfAhbHostMaxIdleTime
		INTEGER,
        wfAhbHostCurIdleTime
		INTEGER
    }
 
    wfAhbHostDelete OBJECT-TYPE
        SYNTAX  INTEGER {
                created(1),
                deleted(2)
        }
        ACCESS  read-write
        STATUS  mandatory
        DESCRIPTION
                "Create/Delete this half-bridge host entry."
        DEFVAL  { created }
        ::= { wfAhbHostEntry 1 }

    wfAhbHostSlot OBJECT-TYPE
        SYNTAX  INTEGER
        ACCESS  read-only
        STATUS  mandatory
        DESCRIPTION
                "The slot number which is reporting this host entry.
                 If this is a new host entry to be created, it must be
                 the slot through which the host is physically attached." 
        ::= { wfAhbHostEntry 2 }

    wfAhbHostSeqNum OBJECT-TYPE
        SYNTAX  INTEGER
        ACCESS  read-write
        STATUS  mandatory
        DESCRIPTION
                "Sequence number assigned to this entry (must be zero on create)."
        ::= { wfAhbHostEntry 3 }

    wfAhbHostIpAddress OBJECT-TYPE
        SYNTAX  IpAddress
        ACCESS  read-only
        STATUS  mandatory
        DESCRIPTION
                "The IP address associated with this host entry."
        ::= { wfAhbHostEntry 4 }

    wfAhbHostSubNetMask OBJECT-TYPE
        SYNTAX  IpAddress
        ACCESS  read-write
        STATUS  mandatory
        DESCRIPTION
                "The subnet mask associated with this host entry."
	DEFVAL { 0 }
        ::= { wfAhbHostEntry 5 }
 
    wfAhbHostCct OBJECT-TYPE
        SYNTAX  INTEGER 
        ACCESS  read-write
        STATUS  mandatory
        DESCRIPTION
                "The circuit number associated with this host entry."
        ::= { wfAhbHostEntry 6 }
 
    wfAhbHostVcid OBJECT-TYPE
        SYNTAX  INTEGER
        ACCESS  read-write
        STATUS  mandatory
        DESCRIPTION
                "The ATM VPI/VCI associated with this host entry."
	DEFVAL { 0 }
        ::= { wfAhbHostEntry 7 }
 
    wfAhbHostBridgeHdr OBJECT-TYPE
        SYNTAX  DisplayString (SIZE (0..100))
        ACCESS  read-write
        STATUS  mandatory
        DESCRIPTION
                "The bridge DLL header associated with this host entry."
        ::= { wfAhbHostEntry 8 }

    wfAhbHostFlags OBJECT-TYPE
        SYNTAX  INTEGER
        ACCESS  read-write
        STATUS  mandatory
        DESCRIPTION
                "Various control flag bits for this host entry.
                 See router documentation for bit definitions."
	DEFVAL { 0 }
        ::= { wfAhbHostEntry 9 }
 
    wfAhbHostTxPkts OBJECT-TYPE
        SYNTAX  Counter
        ACCESS  read-only
        STATUS  mandatory
        DESCRIPTION
                "Number of outgoing packets sent on this host entry."
        ::= { wfAhbHostEntry 10 }
 
    wfAhbHostRxPkts OBJECT-TYPE
        SYNTAX  Counter
        ACCESS  read-only
        STATUS  mandatory
        DESCRIPTION
                "Number of incoming packets received on this host entry."
        ::= { wfAhbHostEntry 11 }

    wfAhbHostMaxIdleTime OBJECT-TYPE
        SYNTAX  INTEGER
        ACCESS  read-write
        STATUS  mandatory
        DESCRIPTION
                "Maximum idle time for this host entry."
        ::= { wfAhbHostEntry 12 }
 
    wfAhbHostCurIdleTime OBJECT-TYPE
        SYNTAX  INTEGER
        ACCESS  read-only
        STATUS  mandatory
        DESCRIPTION
                "Remaining idle time for this host entry."
        ::= { wfAhbHostEntry 13 }

    wfAhbPolicyTable OBJECT-TYPE
        SYNTAX  SEQUENCE OF WfAhbPolicyEntry
        ACCESS  not-accessible
        STATUS  mandatory
        DESCRIPTION
                "A list of policy entries for the ATM half-bridge table."
        ::= { wfAtmHalfBridgeGroup 4 }
 
    wfAhbPolicyEntry OBJECT-TYPE
        SYNTAX  WfAhbPolicyEntry
        ACCESS  not-accessible
        STATUS  mandatory
        DESCRIPTION
                "ATM Half Bridge Policy Entry."
        INDEX   {
                  wfAhbPolicyIpAddress,
		  wfAhbPolicySubNetMask
		 }
        ::= { wfAhbPolicyTable 1 }

    WfAhbPolicyEntry ::= SEQUENCE {
        wfAhbPolicyDelete
                INTEGER,
        wfAhbPolicyIpAddress
                IpAddress,
        wfAhbPolicySubNetMask
                IpAddress,
        wfAhbPolicyCct 
                INTEGER,
        wfAhbPolicyVPI
                INTEGER,
        wfAhbPolicyVCI
                INTEGER,
        wfAhbPolicyMACAddr
                MacAddress,
        wfAhbPolicyFlags
		INTEGER,
        wfAhbPolicyPermission
		INTEGER
    }
 
    wfAhbPolicyDelete OBJECT-TYPE
        SYNTAX  INTEGER {
                created(1),
                deleted(2)
        }
        ACCESS  read-write
        STATUS  mandatory
        DESCRIPTION
                "Create/Delete this half-bridge policy entry."
        DEFVAL  { created }
        ::= { wfAhbPolicyEntry 1 }

    wfAhbPolicyIpAddress OBJECT-TYPE
        SYNTAX  IpAddress
        ACCESS  read-only
        STATUS  mandatory
        DESCRIPTION
                "The IP address associated with policy host entry."
        ::= { wfAhbPolicyEntry 2 }

    wfAhbPolicySubNetMask OBJECT-TYPE
        SYNTAX  IpAddress
        ACCESS  read-only
        STATUS  mandatory
        DESCRIPTION
                "The subnet mask associated with policy host entry."
        ::= { wfAhbPolicyEntry 3 }
 
    wfAhbPolicyCct OBJECT-TYPE
        SYNTAX  INTEGER 
        ACCESS  read-write
        STATUS  mandatory
        DESCRIPTION
                "The circuit number associated with policy host entry."
        DEFVAL { 0 }
        ::= { wfAhbPolicyEntry 4 }
 
    wfAhbPolicyVPI OBJECT-TYPE
        SYNTAX  INTEGER
        ACCESS  read-write
        STATUS  mandatory
        DESCRIPTION
                "The ATM VPI associated with this policy entry."
	DEFVAL { 0 }
        ::= { wfAhbPolicyEntry 5 }
 
    wfAhbPolicyVCI OBJECT-TYPE
        SYNTAX  INTEGER
        ACCESS  read-write
        STATUS  mandatory
        DESCRIPTION
                "The ATM VCI associated with this policy entry."
	DEFVAL { 0 }
        ::= { wfAhbPolicyEntry 6 }

    wfAhbPolicyMACAddr OBJECT-TYPE
        SYNTAX  MacAddress
        ACCESS  read-write
        STATUS  mandatory
        DESCRIPTION
                "The bridge DLL header associated with this policy entry."
        ::= { wfAhbPolicyEntry 7 }

    wfAhbPolicyFlags OBJECT-TYPE
        SYNTAX  INTEGER
        ACCESS  read-write
        STATUS  mandatory
        DESCRIPTION
                "Various control flag bits for this policy entry.
                 See router documentation for bit definitions."
	DEFVAL { 0 }
        ::= { wfAhbPolicyEntry 8 }

    wfAhbPolicyPermission OBJECT-TYPE
        SYNTAX  INTEGER {
                allow(1),
                disallow(2),
		static(3),
		notused(4)
        }
        ACCESS  read-write
        STATUS  mandatory
        DESCRIPTION
                "Permission for creating host entry which matches this policy."
        DEFVAL  { allow }
        ::= { wfAhbPolicyEntry 9 }

 
   END  -- Wellfleet-AHB-MIB
