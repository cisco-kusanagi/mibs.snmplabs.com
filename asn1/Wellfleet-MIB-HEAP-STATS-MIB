Wellfleet-MIB-HEAP-STATS-MIB DEFINITIONS ::= BEGIN

-- Created by mdl2asn version 3.1
-- Creation date: Wed Aug 30 16:45:20 EDT 1995


    IMPORTS

      IpAddress, Counter, Gauge, TimeTicks, Opaque, enterprises, mgmt
        FROM RFC1155-SMI
      OBJECT-TYPE
        FROM RFC-1212
      TRAP-TYPE
        FROM RFC-1215
      DisplayString, mib-2
        FROM RFC1213-MIB
      wfMibHeapGroup
        FROM Wellfleet-COMMON-MIB;


    wfMibHeapTable OBJECT-TYPE
        SYNTAX	SEQUENCE OF WfMibHeapEntry
        ACCESS	not-accessible
        STATUS	mandatory
        DESCRIPTION
                "Table of MIB Heap Manager Stats, indexed by slot number"
        ::= { wfMibHeapGroup 1 }

    wfMibHeapEntry OBJECT-TYPE
        SYNTAX	WfMibHeapEntry
        ACCESS	not-accessible
        STATUS	mandatory
        DESCRIPTION
                "A particular interface"
        INDEX	{ wfMibHeapSlot }
        ::= { wfMibHeapTable 1 }

    WfMibHeapEntry ::= SEQUENCE {
    	    wfMibHeapSlot
    		INTEGER,
    	    wfMibHeapMemorySize
    		INTEGER,
    	    wfMibHeapBoundrySize
    		INTEGER,
    	    wfMibHeapPageSize
    		INTEGER,
    	    wfMibHeapTotalPages
    		INTEGER,
    	    wfMibHeapTotalSegs
    		INTEGER,
    	    wfMibHeapSegsFree
    		INTEGER,
    	    wfMibHeapSmlstSeg
    		INTEGER,
    	    wfMibHeapLrgstSeg
    		INTEGER,
    	    wfMibHeapStartSize
    		INTEGER,
    	    wfMibHeapSize1
    		INTEGER,
    	    wfMibHeapSize1SegsFree
    		INTEGER,
    	    wfMibHeapSize1SegsTotal
    		INTEGER,
    	    wfMibHeapSize1Pages
    		INTEGER,
    	    wfMibHeapSize2
    		INTEGER,
    	    wfMibHeapSize2SegsFree
    		INTEGER,
    	    wfMibHeapSize2SegsTotal
    		INTEGER,
    	    wfMibHeapSize2Pages
    		INTEGER,
    	    wfMibHeapSize3
    		INTEGER,
    	    wfMibHeapSize3SegsFree
    		INTEGER,
    	    wfMibHeapSize3SegsTotal
    		INTEGER,
    	    wfMibHeapSize3Pages
    		INTEGER,
    	    wfMibHeapSize4
    		INTEGER,
    	    wfMibHeapSize4SegsFree
    		INTEGER,
    	    wfMibHeapSize4SegsTotal
    		INTEGER,
    	    wfMibHeapSize4Pages
    		INTEGER,
    	    wfMibHeapSize5
    		INTEGER,
    	    wfMibHeapSize5SegsFree
    		INTEGER,
    	    wfMibHeapSize5SegsTotal
    		INTEGER,
    	    wfMibHeapSize5Pages
    		INTEGER,
    	    wfMibHeapSize6
    		INTEGER,
    	    wfMibHeapSize6SegsFree
    		INTEGER,
    	    wfMibHeapSize6SegsTotal
    		INTEGER,
    	    wfMibHeapSize6Pages
    		INTEGER,
    	    wfMibHeapSize7
    		INTEGER,
    	    wfMibHeapSize7SegsFree
    		INTEGER,
    	    wfMibHeapSize7SegsTotal
    		INTEGER,
    	    wfMibHeapSize7Pages
    		INTEGER,
    	    wfMibHeapSize8
    		INTEGER,
    	    wfMibHeapSize8SegsFree
    		INTEGER,
    	    wfMibHeapSize8SegsTotal
    		INTEGER,
    	    wfMibHeapSize8Pages
    		INTEGER,
    	    wfMibHeapSize9
    		INTEGER,
    	    wfMibHeapSize9SegsFree
    		INTEGER,
    	    wfMibHeapSize9SegsTotal
    		INTEGER,
    	    wfMibHeapSize9Pages
    		INTEGER,
    	    wfMibHeapSize10
    		INTEGER,
    	    wfMibHeapSize10SegsFree
    		INTEGER,
    	    wfMibHeapSize10SegsTotal
    		INTEGER,
    	    wfMibHeapSize10Pages
    		INTEGER
        }

    wfMibHeapSlot OBJECT-TYPE
        SYNTAX	INTEGER
        ACCESS	read-only
        STATUS	mandatory
        DESCRIPTION
                "The slot number indexes the mib heap statistics table"
        ::= { wfMibHeapEntry 1 }

    wfMibHeapMemorySize OBJECT-TYPE
        SYNTAX	INTEGER
        ACCESS	read-only
        STATUS	mandatory
        DESCRIPTION
                "Total amount of memory allocated by the mib heap manager in bytes"
        ::= { wfMibHeapEntry 2 }

    wfMibHeapBoundrySize OBJECT-TYPE
        SYNTAX	INTEGER(128..512)
        ACCESS	read-write
        STATUS	mandatory
        DESCRIPTION
                "The boundry size reflects the largest segment which will be
                allocated on a page basis. Allocations requests larger than
                the boundry size are allocated one to a page."
        DEFVAL	{ 256 }
        ::= { wfMibHeapEntry 3 }

    wfMibHeapPageSize OBJECT-TYPE
        SYNTAX	INTEGER(512..16384)
        ACCESS	read-write
        STATUS	mandatory
        DESCRIPTION
                "The page size allocated by the mib heap manager in bytes"
        DEFVAL	{ 1024 }
        ::= { wfMibHeapEntry 4 }

    wfMibHeapTotalPages OBJECT-TYPE
        SYNTAX	INTEGER
        ACCESS	read-only
        STATUS	mandatory
        DESCRIPTION
                "Total number of pages currently allocated by the mib heap manager"
        ::= { wfMibHeapEntry 5 }

    wfMibHeapTotalSegs OBJECT-TYPE
        SYNTAX	INTEGER
        ACCESS	read-only
        STATUS	mandatory
        DESCRIPTION
                "Total amount of allocatable segments within the mib heap manager"
        ::= { wfMibHeapEntry 6 }

    wfMibHeapSegsFree OBJECT-TYPE
        SYNTAX	INTEGER
        ACCESS	read-only
        STATUS	mandatory
        DESCRIPTION
                "Total amount of unallocated segments within the mib heap manager"
        ::= { wfMibHeapEntry 7 }

    wfMibHeapSmlstSeg OBJECT-TYPE
        SYNTAX	INTEGER
        ACCESS	read-only
        STATUS	mandatory
        DESCRIPTION
                "Smallest memory segment allocated by the mib in bytes"
        ::= { wfMibHeapEntry 8 }

    wfMibHeapLrgstSeg OBJECT-TYPE
        SYNTAX	INTEGER
        ACCESS	read-only
        STATUS	mandatory
        DESCRIPTION
                "Largest memory segment allocated by the mib in bytes"
        ::= { wfMibHeapEntry 9 }

    wfMibHeapStartSize OBJECT-TYPE
        SYNTAX	INTEGER(4..4096)
        ACCESS	read-write
        STATUS	mandatory
        DESCRIPTION
                "Segment size to start displaying in the mib heap stats"
        DEFVAL	{ 12 }
        ::= { wfMibHeapEntry 10 }

    wfMibHeapSize1 OBJECT-TYPE
        SYNTAX	INTEGER
        ACCESS	read-only
        STATUS	mandatory
        DESCRIPTION
                "Size of memory segment in the mib heap page table"
        ::= { wfMibHeapEntry 11 }

    wfMibHeapSize1SegsFree OBJECT-TYPE
        SYNTAX	INTEGER
        ACCESS	read-only
        STATUS	mandatory
        DESCRIPTION
                "Total number of unallocated segments of a given memory segment size"
        ::= { wfMibHeapEntry 12 }

    wfMibHeapSize1SegsTotal OBJECT-TYPE
        SYNTAX	INTEGER
        ACCESS	read-only
        STATUS	mandatory
        DESCRIPTION
                "Total number of allocatable segments of a given memory segment size"
        ::= { wfMibHeapEntry 13 }

    wfMibHeapSize1Pages OBJECT-TYPE
        SYNTAX	INTEGER
        ACCESS	read-only
        STATUS	mandatory
        DESCRIPTION
                "Total number of pages allocated for a given memory segment size"
        ::= { wfMibHeapEntry 14 }

    wfMibHeapSize2 OBJECT-TYPE
        SYNTAX	INTEGER
        ACCESS	read-only
        STATUS	mandatory
        DESCRIPTION
                "Size of memory segment in the mib heap page table"
        ::= { wfMibHeapEntry 15 }

    wfMibHeapSize2SegsFree OBJECT-TYPE
        SYNTAX	INTEGER
        ACCESS	read-only
        STATUS	mandatory
        DESCRIPTION
                "Total number of unallocated segments of a given memory segment size"
        ::= { wfMibHeapEntry 16 }

    wfMibHeapSize2SegsTotal OBJECT-TYPE
        SYNTAX	INTEGER
        ACCESS	read-only
        STATUS	mandatory
        DESCRIPTION
                "Total number of allocatable segments of a given memory segment size"
        ::= { wfMibHeapEntry 17 }

    wfMibHeapSize2Pages OBJECT-TYPE
        SYNTAX	INTEGER
        ACCESS	read-only
        STATUS	mandatory
        DESCRIPTION
                "Total number of pages allocated for a given memory segment size"
        ::= { wfMibHeapEntry 18 }

    wfMibHeapSize3 OBJECT-TYPE
        SYNTAX	INTEGER
        ACCESS	read-only
        STATUS	mandatory
        DESCRIPTION
                "Size of memory segment in the mib heap page table"
        ::= { wfMibHeapEntry 19 }

    wfMibHeapSize3SegsFree OBJECT-TYPE
        SYNTAX	INTEGER
        ACCESS	read-only
        STATUS	mandatory
        DESCRIPTION
                "Total number of unallocated segments of a given memory segment size"
        ::= { wfMibHeapEntry 20 }

    wfMibHeapSize3SegsTotal OBJECT-TYPE
        SYNTAX	INTEGER
        ACCESS	read-only
        STATUS	mandatory
        DESCRIPTION
                "Total number of allocatable segments of a given memory segment size"
        ::= { wfMibHeapEntry 21 }

    wfMibHeapSize3Pages OBJECT-TYPE
        SYNTAX	INTEGER
        ACCESS	read-only
        STATUS	mandatory
        DESCRIPTION
                "Total number of pages allocated for a given memory segment size"
        ::= { wfMibHeapEntry 22 }

    wfMibHeapSize4 OBJECT-TYPE
        SYNTAX	INTEGER
        ACCESS	read-only
        STATUS	mandatory
        DESCRIPTION
                "Size of memory segment in the mib heap page table"
        ::= { wfMibHeapEntry 23 }

    wfMibHeapSize4SegsFree OBJECT-TYPE
        SYNTAX	INTEGER
        ACCESS	read-only
        STATUS	mandatory
        DESCRIPTION
                "Total number of unallocated segments of a given memory segment size"
        ::= { wfMibHeapEntry 24 }

    wfMibHeapSize4SegsTotal OBJECT-TYPE
        SYNTAX	INTEGER
        ACCESS	read-only
        STATUS	mandatory
        DESCRIPTION
                "Total number of allocatable segments of a given memory segment size"
        ::= { wfMibHeapEntry 25 }

    wfMibHeapSize4Pages OBJECT-TYPE
        SYNTAX	INTEGER
        ACCESS	read-only
        STATUS	mandatory
        DESCRIPTION
                "Total number of pages allocated for a given memory segment size"
        ::= { wfMibHeapEntry 26 }

    wfMibHeapSize5 OBJECT-TYPE
        SYNTAX	INTEGER
        ACCESS	read-only
        STATUS	mandatory
        DESCRIPTION
                "Size of memory segment in the mib heap page table"
        ::= { wfMibHeapEntry 27 }

    wfMibHeapSize5SegsFree OBJECT-TYPE
        SYNTAX	INTEGER
        ACCESS	read-only
        STATUS	mandatory
        DESCRIPTION
                "Total number of unallocated segments of a given memory segment size"
        ::= { wfMibHeapEntry 28 }

    wfMibHeapSize5SegsTotal OBJECT-TYPE
        SYNTAX	INTEGER
        ACCESS	read-only
        STATUS	mandatory
        DESCRIPTION
                "Total number of allocatable segments of a given memory segment size"
        ::= { wfMibHeapEntry 29 }

    wfMibHeapSize5Pages OBJECT-TYPE
        SYNTAX	INTEGER
        ACCESS	read-only
        STATUS	mandatory
        DESCRIPTION
                "Total number of pages allocated for a given memory segment size"
        ::= { wfMibHeapEntry 30 }

    wfMibHeapSize6 OBJECT-TYPE
        SYNTAX	INTEGER
        ACCESS	read-only
        STATUS	mandatory
        DESCRIPTION
                "Size of memory segment in the mib heap page table"
        ::= { wfMibHeapEntry 31 }

    wfMibHeapSize6SegsFree OBJECT-TYPE
        SYNTAX	INTEGER
        ACCESS	read-only
        STATUS	mandatory
        DESCRIPTION
                "Total number of unallocated segments of a given memory segment size"
        ::= { wfMibHeapEntry 32 }

    wfMibHeapSize6SegsTotal OBJECT-TYPE
        SYNTAX	INTEGER
        ACCESS	read-only
        STATUS	mandatory
        DESCRIPTION
                "Total number of allocatable segments of a given memory segment size"
        ::= { wfMibHeapEntry 33 }

    wfMibHeapSize6Pages OBJECT-TYPE
        SYNTAX	INTEGER
        ACCESS	read-only
        STATUS	mandatory
        DESCRIPTION
                "Total number of pages allocated for a given memory segment size"
        ::= { wfMibHeapEntry 34 }

    wfMibHeapSize7 OBJECT-TYPE
        SYNTAX	INTEGER
        ACCESS	read-only
        STATUS	mandatory
        DESCRIPTION
                "Size of memory segment in the mib heap page table"
        ::= { wfMibHeapEntry 35 }

    wfMibHeapSize7SegsFree OBJECT-TYPE
        SYNTAX	INTEGER
        ACCESS	read-only
        STATUS	mandatory
        DESCRIPTION
                "Total number of unallocated segments of a given memory segment size"
        ::= { wfMibHeapEntry 36 }

    wfMibHeapSize7SegsTotal OBJECT-TYPE
        SYNTAX	INTEGER
        ACCESS	read-only
        STATUS	mandatory
        DESCRIPTION
                "Total number of allocatable segments of a given memory segment size"
        ::= { wfMibHeapEntry 37 }

    wfMibHeapSize7Pages OBJECT-TYPE
        SYNTAX	INTEGER
        ACCESS	read-only
        STATUS	mandatory
        DESCRIPTION
                "Total number of pages allocated for a given memory segment size"
        ::= { wfMibHeapEntry 38 }

    wfMibHeapSize8 OBJECT-TYPE
        SYNTAX	INTEGER
        ACCESS	read-only
        STATUS	mandatory
        DESCRIPTION
                "Size of memory segment in the mib heap page table"
        ::= { wfMibHeapEntry 39 }

    wfMibHeapSize8SegsFree OBJECT-TYPE
        SYNTAX	INTEGER
        ACCESS	read-only
        STATUS	mandatory
        DESCRIPTION
                "Total number of unallocated segments of a given memory segment size"
        ::= { wfMibHeapEntry 40 }

    wfMibHeapSize8SegsTotal OBJECT-TYPE
        SYNTAX	INTEGER
        ACCESS	read-only
        STATUS	mandatory
        DESCRIPTION
                "Total number of allocatable segments of a given memory segment size"
        ::= { wfMibHeapEntry 41 }

    wfMibHeapSize8Pages OBJECT-TYPE
        SYNTAX	INTEGER
        ACCESS	read-only
        STATUS	mandatory
        DESCRIPTION
                "Total number of pages allocated for a given memory segment size"
        ::= { wfMibHeapEntry 42 }

    wfMibHeapSize9 OBJECT-TYPE
        SYNTAX	INTEGER
        ACCESS	read-only
        STATUS	mandatory
        DESCRIPTION
                "Size of memory segment in the mib heap page table"
        ::= { wfMibHeapEntry 43 }

    wfMibHeapSize9SegsFree OBJECT-TYPE
        SYNTAX	INTEGER
        ACCESS	read-only
        STATUS	mandatory
        DESCRIPTION
                "Total number of unallocated segments of a given memory segment size"
        ::= { wfMibHeapEntry 44 }

    wfMibHeapSize9SegsTotal OBJECT-TYPE
        SYNTAX	INTEGER
        ACCESS	read-only
        STATUS	mandatory
        DESCRIPTION
                "Total number of allocatable segments of a given memory segment size"
        ::= { wfMibHeapEntry 45 }

    wfMibHeapSize9Pages OBJECT-TYPE
        SYNTAX	INTEGER
        ACCESS	read-only
        STATUS	mandatory
        DESCRIPTION
                "Total number of allocatable segments of a given memory segment size"
        ::= { wfMibHeapEntry 46 }

    wfMibHeapSize10 OBJECT-TYPE
        SYNTAX	INTEGER
        ACCESS	read-only
        STATUS	mandatory
        DESCRIPTION
                "Size of memory segment in the mib heap page table"
        ::= { wfMibHeapEntry 47 }

    wfMibHeapSize10SegsFree OBJECT-TYPE
        SYNTAX	INTEGER
        ACCESS	read-only
        STATUS	mandatory
        DESCRIPTION
                "Total number of unallocated segments of a given memory segment size"
        ::= { wfMibHeapEntry 48 }

    wfMibHeapSize10SegsTotal OBJECT-TYPE
        SYNTAX	INTEGER
        ACCESS	read-only
        STATUS	mandatory
        DESCRIPTION
                "Total number of allocatable segments of a given memory segment size"
        ::= { wfMibHeapEntry 49 }

    wfMibHeapSize10Pages OBJECT-TYPE
        SYNTAX	INTEGER
        ACCESS	read-only
        STATUS	mandatory
        DESCRIPTION
                "Total number of allocatable segments of a given memory segment size"
        ::= { wfMibHeapEntry 50 }

    wfMibHeapPageTable OBJECT-TYPE
        SYNTAX	SEQUENCE OF WfMibHeapPageEntry
        ACCESS	not-accessible
        STATUS	mandatory
        DESCRIPTION
                "Table of MIB Heap Manager Page Table Stats, indexed by slot number"
        ::= { wfMibHeapGroup 2 }

    wfMibHeapPageEntry OBJECT-TYPE
        SYNTAX	WfMibHeapPageEntry
        ACCESS	not-accessible
        STATUS	mandatory
        DESCRIPTION
                "A particular interface"
        INDEX	{ wfMibHeapPageSlot }
        ::= { wfMibHeapPageTable 1 }

    WfMibHeapPageEntry ::= SEQUENCE {
    	    wfMibHeapPageSlot
    		INTEGER,
    	    wfMibHeapPageListOffset
    		INTEGER,
    	    wfMibHeapPageSegSize
    		INTEGER,
    	    wfMibHeapPageTotal
    		INTEGER,
    	    wfMibHeapPageMemoryTotal
    		INTEGER,
    	    wfMibHeapPageSegsTotal
    		INTEGER,
    	    wfMibHeapPageSegsAllocd
    		INTEGER,
    	    wfMibHeapPageSegsFree
    		INTEGER,
    	    wfMibHeapPage1Size
    		INTEGER,
    	    wfMibHeapPage1SegsFree
    		INTEGER,
    	    wfMibHeapPage1SegsMax
    		INTEGER,
    	    wfMibHeapPage2Size
    		INTEGER,
    	    wfMibHeapPage2SegsFree
    		INTEGER,
    	    wfMibHeapPage2SegsMax
    		INTEGER,
    	    wfMibHeapPage3Size
    		INTEGER,
    	    wfMibHeapPage3SegsFree
    		INTEGER,
    	    wfMibHeapPage3SegsMax
    		INTEGER,
    	    wfMibHeapPage4Size
    		INTEGER,
    	    wfMibHeapPage4SegsFree
    		INTEGER,
    	    wfMibHeapPage4SegsMax
    		INTEGER,
    	    wfMibHeapPage5Size
    		INTEGER,
    	    wfMibHeapPage5SegsFree
    		INTEGER,
    	    wfMibHeapPage5SegsMax
    		INTEGER,
    	    wfMibHeapPage6PageSize
    		INTEGER,
    	    wfMibHeapPage6SegsFree
    		INTEGER,
    	    wfMibHeapPage6SegsMax
    		INTEGER,
    	    wfMibHeapPage7Size
    		INTEGER,
    	    wfMibHeapPage7SegsFree
    		INTEGER,
    	    wfMibHeapPage7SegsMax
    		INTEGER,
    	    wfMibHeapPage8Size
    		INTEGER,
    	    wfMibHeapPage8SegsFree
    		INTEGER,
    	    wfMibHeapPage8SegsMax
    		INTEGER,
    	    wfMibHeapPage9Size
    		INTEGER,
    	    wfMibHeapPage9SegsFree
    		INTEGER,
    	    wfMibHeapPage9SegsMax
    		INTEGER,
    	    wfMibHeapPage10Size
    		INTEGER,
    	    wfMibHeapPage10SegsFree
    		INTEGER,
    	    wfMibHeapPage10SegsMax
    		INTEGER
        }

    wfMibHeapPageSlot OBJECT-TYPE
        SYNTAX	INTEGER
        ACCESS	read-only
        STATUS	mandatory
        DESCRIPTION
                "The slot number indexes the mib heap statistics table"
        ::= { wfMibHeapPageEntry 1 }

    wfMibHeapPageListOffset OBJECT-TYPE
        SYNTAX	INTEGER
        ACCESS	read-write
        STATUS	mandatory
        DESCRIPTION
                "The offset into the page list to start displaying"
        ::= { wfMibHeapPageEntry 2 }

    wfMibHeapPageSegSize OBJECT-TYPE
        SYNTAX	INTEGER(2..4096)
        ACCESS	read-write
        STATUS	mandatory
        DESCRIPTION
                "The Segment size can be set from 4 to 4096 and the
                page statstics then gathered for that segment size"
        DEFVAL	{ 12 }
        ::= { wfMibHeapPageEntry 3 }

    wfMibHeapPageTotal OBJECT-TYPE
        SYNTAX	INTEGER
        ACCESS	read-only
        STATUS	mandatory
        DESCRIPTION
                "Total number of pages allocated for the given memory segment size"
        ::= { wfMibHeapPageEntry 4 }

    wfMibHeapPageMemoryTotal OBJECT-TYPE
        SYNTAX	INTEGER
        ACCESS	read-only
        STATUS	mandatory
        DESCRIPTION
                "Total amount of memory allocated of a given segment size in bytes"
        ::= { wfMibHeapPageEntry 5 }

    wfMibHeapPageSegsTotal OBJECT-TYPE
        SYNTAX	INTEGER
        ACCESS	read-only
        STATUS	mandatory
        DESCRIPTION
                "Total amount of allocable segments for a given segment size"
        ::= { wfMibHeapPageEntry 6 }

    wfMibHeapPageSegsAllocd OBJECT-TYPE
        SYNTAX	INTEGER
        ACCESS	read-only
        STATUS	mandatory
        DESCRIPTION
                "Total amount of segments allocated for a given segment size"
        ::= { wfMibHeapPageEntry 7 }

    wfMibHeapPageSegsFree OBJECT-TYPE
        SYNTAX	INTEGER
        ACCESS	read-only
        STATUS	mandatory
        DESCRIPTION
                "Total amount of unallocated segments for a given segment size"
        ::= { wfMibHeapPageEntry 8 }

    wfMibHeapPage1Size OBJECT-TYPE
        SYNTAX	INTEGER
        ACCESS	read-only
        STATUS	mandatory
        DESCRIPTION
                "Size in bytes of a given page"
        ::= { wfMibHeapPageEntry 9 }

    wfMibHeapPage1SegsFree OBJECT-TYPE
        SYNTAX	INTEGER
        ACCESS	read-only
        STATUS	mandatory
        DESCRIPTION
                "Total number of unallocated segments for the given page"
        ::= { wfMibHeapPageEntry 10 }

    wfMibHeapPage1SegsMax OBJECT-TYPE
        SYNTAX	INTEGER
        ACCESS	read-only
        STATUS	mandatory
        DESCRIPTION
                "Maximum amount of allocable segments for the given page"
        ::= { wfMibHeapPageEntry 11 }

    wfMibHeapPage2Size OBJECT-TYPE
        SYNTAX	INTEGER
        ACCESS	read-only
        STATUS	mandatory
        DESCRIPTION
                "Size in bytes of a given page"
        ::= { wfMibHeapPageEntry 12 }

    wfMibHeapPage2SegsFree OBJECT-TYPE
        SYNTAX	INTEGER
        ACCESS	read-only
        STATUS	mandatory
        DESCRIPTION
                "Total number of unallocated segments for the given page"
        ::= { wfMibHeapPageEntry 13 }

    wfMibHeapPage2SegsMax OBJECT-TYPE
        SYNTAX	INTEGER
        ACCESS	read-only
        STATUS	mandatory
        DESCRIPTION
                "Maximum number of allocable segments for the given page"
        ::= { wfMibHeapPageEntry 14 }

    wfMibHeapPage3Size OBJECT-TYPE
        SYNTAX	INTEGER
        ACCESS	read-only
        STATUS	mandatory
        DESCRIPTION
                "Size in bytes of a given page"
        ::= { wfMibHeapPageEntry 15 }

    wfMibHeapPage3SegsFree OBJECT-TYPE
        SYNTAX	INTEGER
        ACCESS	read-only
        STATUS	mandatory
        DESCRIPTION
                "Total number of unallocated segments for the given page"
        ::= { wfMibHeapPageEntry 16 }

    wfMibHeapPage3SegsMax OBJECT-TYPE
        SYNTAX	INTEGER
        ACCESS	read-only
        STATUS	mandatory
        DESCRIPTION
                "Maximum number of allocable segments for the given page"
        ::= { wfMibHeapPageEntry 17 }

    wfMibHeapPage4Size OBJECT-TYPE
        SYNTAX	INTEGER
        ACCESS	read-only
        STATUS	mandatory
        DESCRIPTION
                "Size in bytes of a given page"
        ::= { wfMibHeapPageEntry 18 }

    wfMibHeapPage4SegsFree OBJECT-TYPE
        SYNTAX	INTEGER
        ACCESS	read-only
        STATUS	mandatory
        DESCRIPTION
                "Total number of unallocated segments for the given page"
        ::= { wfMibHeapPageEntry 19 }

    wfMibHeapPage4SegsMax OBJECT-TYPE
        SYNTAX	INTEGER
        ACCESS	read-only
        STATUS	mandatory
        DESCRIPTION
                "Maximum number of allocable segments for the given page"
        ::= { wfMibHeapPageEntry 20 }

    wfMibHeapPage5Size OBJECT-TYPE
        SYNTAX	INTEGER
        ACCESS	read-only
        STATUS	mandatory
        DESCRIPTION
                "Size in bytes of a given page"
        ::= { wfMibHeapPageEntry 21 }

    wfMibHeapPage5SegsFree OBJECT-TYPE
        SYNTAX	INTEGER
        ACCESS	read-only
        STATUS	mandatory
        DESCRIPTION
                "Total number of unallocated segments for the given page"
        ::= { wfMibHeapPageEntry 22 }

    wfMibHeapPage5SegsMax OBJECT-TYPE
        SYNTAX	INTEGER
        ACCESS	read-only
        STATUS	mandatory
        DESCRIPTION
                "Maximum number of allocable segments for the given page"
        ::= { wfMibHeapPageEntry 23 }

    wfMibHeapPage6PageSize OBJECT-TYPE
        SYNTAX	INTEGER
        ACCESS	read-only
        STATUS	mandatory
        DESCRIPTION
                "Size in bytes of a given page"
        ::= { wfMibHeapPageEntry 24 }

    wfMibHeapPage6SegsFree OBJECT-TYPE
        SYNTAX	INTEGER
        ACCESS	read-only
        STATUS	mandatory
        DESCRIPTION
                "Total number of unallocated segments for the given page"
        ::= { wfMibHeapPageEntry 25 }

    wfMibHeapPage6SegsMax OBJECT-TYPE
        SYNTAX	INTEGER
        ACCESS	read-only
        STATUS	mandatory
        DESCRIPTION
                "Maximum number of allocable segments for the given page"
        ::= { wfMibHeapPageEntry 26 }

    wfMibHeapPage7Size OBJECT-TYPE
        SYNTAX	INTEGER
        ACCESS	read-only
        STATUS	mandatory
        DESCRIPTION
                "Size in bytes of a given page"
        ::= { wfMibHeapPageEntry 27 }

    wfMibHeapPage7SegsFree OBJECT-TYPE
        SYNTAX	INTEGER
        ACCESS	read-only
        STATUS	mandatory
        DESCRIPTION
                "Total number of unallocated segments for the given page"
        ::= { wfMibHeapPageEntry 28 }

    wfMibHeapPage7SegsMax OBJECT-TYPE
        SYNTAX	INTEGER
        ACCESS	read-only
        STATUS	mandatory
        DESCRIPTION
                "Maximum number of allocable segments for the given page"
        ::= { wfMibHeapPageEntry 29 }

    wfMibHeapPage8Size OBJECT-TYPE
        SYNTAX	INTEGER
        ACCESS	read-only
        STATUS	mandatory
        DESCRIPTION
                "Size in bytes of a given page"
        ::= { wfMibHeapPageEntry 30 }

    wfMibHeapPage8SegsFree OBJECT-TYPE
        SYNTAX	INTEGER
        ACCESS	read-only
        STATUS	mandatory
        DESCRIPTION
                "Total number of unallocated segments for the given page"
        ::= { wfMibHeapPageEntry 31 }

    wfMibHeapPage8SegsMax OBJECT-TYPE
        SYNTAX	INTEGER
        ACCESS	read-only
        STATUS	mandatory
        DESCRIPTION
                "Maximum number of allocable segments for the given page"
        ::= { wfMibHeapPageEntry 32 }

    wfMibHeapPage9Size OBJECT-TYPE
        SYNTAX	INTEGER
        ACCESS	read-only
        STATUS	mandatory
        DESCRIPTION
                "Size in bytes of a given page"
        ::= { wfMibHeapPageEntry 33 }

    wfMibHeapPage9SegsFree OBJECT-TYPE
        SYNTAX	INTEGER
        ACCESS	read-only
        STATUS	mandatory
        DESCRIPTION
                "Total number of unallocated segments for the given page"
        ::= { wfMibHeapPageEntry 34 }

    wfMibHeapPage9SegsMax OBJECT-TYPE
        SYNTAX	INTEGER
        ACCESS	read-only
        STATUS	mandatory
        DESCRIPTION
                "Maximum number of allocable segments for the given page"
        ::= { wfMibHeapPageEntry 35 }

    wfMibHeapPage10Size OBJECT-TYPE
        SYNTAX	INTEGER
        ACCESS	read-only
        STATUS	mandatory
        DESCRIPTION
                "Size in bytes of a given page"
        ::= { wfMibHeapPageEntry 36 }

    wfMibHeapPage10SegsFree OBJECT-TYPE
        SYNTAX	INTEGER
        ACCESS	read-only
        STATUS	mandatory
        DESCRIPTION
                "Total number of unallocated segments for the given page"
        ::= { wfMibHeapPageEntry 37 }

    wfMibHeapPage10SegsMax OBJECT-TYPE
        SYNTAX	INTEGER
        ACCESS	read-only
        STATUS	mandatory
        DESCRIPTION
                "Maximum number of allocable segments for the given page"
        ::= { wfMibHeapPageEntry 38 }

    END  -- Wellfleet-MIB-HEAP-STATS-MIB
