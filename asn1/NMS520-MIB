-- Copyright 1994 General DataComm Inc., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.

-- Revision History
-- Version   Date	Name		Description
-- 1.00A     25-Oct-94  N. Marino	Initial Revision
-- 1.00B     05-Dec-94  N. Marino	Added Alarm IOD's
-- 1.00C     17-Feb-95  J. Jacques      Added Diagnostics
-- 1.00D     28-Mar-95  J. Jacques      Added: 	nms520FrontPanelInhibit &
--						nms520frontPanelEnable to
--						nms520UnitCfgTable
--						nms520DiagExtDataloop to
--						nms520DiagExcTable
--						5 new alarms
--					Removed LPDA Table
-- 1.00E     17-Apr-95  R. Strempel	Removed enum netdelay from nms520DiagTestStatus
-- 					as the nms520 does not support this option.
--					Importing gdc & dsu rather than defining here.
-- 1.00F     19-Apr-95  R. Strempel     re-ordered alarm oids for 5 new ones
-- 1.00G     13-Jun-95  R. Strempel	Added nms520HdlcInvert object, added comments
--					to nms520DiagSendCode
-- 1.00H     14-Jul-95  R. Strempel	Added comments to nms520DiagTimeDelay & changed
--					alarm oid's in comment field
--						nms520JitterAlm
--						nms520BpvAlm
--						nms520FrameLossAlm
--						nms520SignalToNoiseAlm
--						nms520RxSignalLowAlm
-- 1.00I     02-Aug-95  C. Amorossi	Added comments to nms520HdlcInvert
--					Added nms520PiggyBackDetect, nms520UnitType,
--					nms520ExtPortCtrlOut1, nms520ExtPortCtrlOut2 to
--					nms520HdlcInvert.
--					Added nms520ExtInputChangeAlm and
--					nms520ExtInputLowAlm and renumbered alarm OIDs
--					Changed ENUMS for nms520DiagTestStatus
--					Set Status of nms520DiagExtLineloop to obsolete
-- 					Set Status of nms520Nms510CompatibilityMode
--					to obsolete
-- 1.00J     07-Aug-95  C. Amorossi	Changed ENUMS for nms520DiagTestStatus.
--					Changed description for nms520DiagTimeDelay.
--					Renumbered alarm OIDs.
-- 1.00K     25-Aug-95  C. Amorossi	Changed description for nms520MtpointRmRspIntrvl.
-- 1.00L     21-Aug-96  D. Baylis       Changed nms520Nms510CompatibilityMode STATUS from
--                                      obsolete to mtory and modified DESCRIPTION 

NMS520-MIB DEFINITIONS ::= BEGIN

IMPORTS
	OBJECT-TYPE			FROM RFC-1212
	DisplayString			FROM RFC1213-MIB
	SCinstance			FROM GDCMACRO-MIB
        gdc                             FROM GDCCMN-MIB
	dsu				FROM DDS-MIB;

nms520 		OBJECT IDENTIFIER ::= { dsu 2 }

-- This MIB module uses the extended OBJECT-TYPE macro as
-- defined in RFC 1212.

-- The implementation of all groups is mandatory for all products in
-- the NMS520 family.

-- All objects in this mib are directed toward one interface which
-- is the unit. There is one entry per table for each managed nms520.

-- Note:  All rows in all tables defined within this MIB module are
-- virtual.  They can neither be created or deleted by management
-- operations.

-- The Version Group. This group identifies the version information
-- for the MIB.
--
nms520MIBversion OBJECT-TYPE
    SYNTAX DisplayString (SIZE (5))
    ACCESS read-only
    STATUS mandatory
    DESCRIPTION
    	"Identifies the version of the MIB. The format of the version
    	is x.yzT, where 'x' identifies the major revision number, 'y'
    	identifies the minor revision number, 'z' identifies the
    	typographical revision, and T identifies the test revision.
    	Acceptable values for the individual revision components are
    	as follows:

    		x: 1 - 9
    		y: 0 - 9
    		z: 0 - 9
    		T: A - Z

    	Upon formal release, no designation for the test revision will
    	be present."
    ::= { nms520 1 }

-- The NMS520 Group.  This group contains objects that support the
-- specific management requirements of the NMS520 that are not
-- addressed through other standard MIB modules.  The group contains one
-- table:  NMS520 Unit Configuration table.  There is one entry in
-- this table for each managed NMS520.

nms520UnitCfgTable OBJECT-TYPE
    SYNTAX SEQUENCE OF Nms520UnitCfgEntry
    ACCESS not-accessible
    STATUS mandatory
    DESCRIPTION
    	"The NMS520 Unit Configuration table.  This table augments the 
	GDC SC5520 Unit Configuration table, providing unit level configuration 
	for each NMS520 device installed. For each entry in the GDC SC 
	Unit Configuration table that represents an NMS520, there is a 
	corresponding entry here whereby the value of the gdcSCunitCfgIndex 
	object is equivalent to the value of the nms520unitCfgIndex object."
    ::= { nms520 2 }

nms520UnitCfgEntry OBJECT-TYPE
    SYNTAX Nms520UnitCfgEntry
    ACCESS not-accessible
    STATUS mandatory
    DESCRIPTION
    	"The NMS520 Unit Configuration table entry. The information in this 
	entry augments the information in the corresponding entry in the 
	GDC SC Unit Configuration table and provides unit level configuration 
	for the installed NMS520."
    INDEX { nms520UnitCfgIndex }
    ::= { nms520UnitCfgTable 1 }

Nms520UnitCfgEntry ::= 
    SEQUENCE {
        nms520UnitCfgIndex SCinstance,
    	nms520Nms510CompatibilityMode INTEGER,	
	nms520PtToPtSentryTime INTEGER,
	nms520AlarmHystTime INTEGER,
	nms520MtpointRmRspIntrvl INTEGER,
	nms520DtePortType INTEGER,
	nms520DteCtsDelay INTEGER,
	nms520DteCtsDelayExt INTEGER,
	nms520FirmwareLevel DisplayString,
        nms520DaisyChainBps INTEGER,
	nms520AlarmCfgCountWindow INTEGER,
	nms520SoftReset INTEGER,
        nms520FrontPanelInhibit INTEGER,
        nms520FrontPanelEnable INTEGER,
        nms520HdlcInvert INTEGER,
	nms520PiggyBackDetect INTEGER,
	nms520UnitType INTEGER,
	nms520ExtPortCtrlOut1 INTEGER,
	nms520ExtPortCtrlOut2 INTEGER
    }

nms520UnitCfgIndex OBJECT-TYPE
    SYNTAX SCinstance
    ACCESS read-only
    STATUS mandatory
    DESCRIPTION
    	"The index value which uniquely identifies the NMS520 to which 
	this entry is applicable.  This has the form of a SCinstance 
	which defines the slot, line, and drop of the NMS520 with no 
	sub-identifier value."
    ::= { nms520UnitCfgEntry 1 }

nms520Nms510CompatibilityMode OBJECT-TYPE
    SYNTAX INTEGER {
    	disabled(1),
    	enabled(2)
    }
    ACCESS read-write
    STATUS mandatory
    DESCRIPTION
    	"The NMS510 compatibility mode. This mode allows the NMS520 to 
	behave in a manner compatible with that of the NMS510 in a DDSI
	multipoint circuit. If this object has the value enabled(2),
	then the device can be used in conjunction with an NMS510. A value
        of disabled(1) implies that the device is not backwardly compatible
	with the NMS510."
    ::= { nms520UnitCfgEntry 2 }

nms520PtToPtSentryTime OBJECT-TYPE
    SYNTAX INTEGER (0..127)
    ACCESS read-write
    STATUS mandatory
    DESCRIPTION
    	"The Point to point sentry time nms520PtToPtSentryTime, is used to
	control the amount of time between unsolicited alarm responses from
	a remote unit in a point to point application when there are no alarm
	conditions to report.  This unsolicited response maintains the
	management link between the two units.  These alarm responses are
	intrusive to data.  The range is from 1 minute to 127 minutes, with 
	60 minutes being the default value. The value of 0(zero) minutes will 
	disable remote alarm sentry reporting."
    ::= { nms520UnitCfgEntry 3 }

nms520AlarmHystTime OBJECT-TYPE
    SYNTAX INTEGER (1..127)
    ACCESS read-write
    STATUS mandatory
    DESCRIPTION
    	"The Alarm hysterysis time nms520AlarmHystTime, is used to control the
	amount of time a remote must wait between reporting unsolicited alarm
	conditions. A remote will send an unsolicited alarm response at the
	time of the first alarm. If second alarm occurs the remote will wait
	for the time specified by this object before it will send another alarm
	response. This time applies for both point to point and multipoint
	applications. The range is from 1 second to 127 seconds,  with 10
	seconds being the default value."
    ::= { nms520UnitCfgEntry 4 }

nms520MtpointRmRspIntrvl OBJECT-TYPE
    SYNTAX INTEGER (0..127)
    ACCESS read-write
    STATUS mandatory
    DESCRIPTION
	"The multipoint remote response interval nms520MtpointRmRspIntrvl, is
	used to control the amount of time between unsolicited alarm responses
	from a remote unit in a multipoint applications when there are no alarm
	conditions to report.  This unsolicited response maintains the
	management link between the two units. The range is from 1 second
	to 127 seconds with 10 seconds being the default value. The value
	of 0(zero) seconds is disable remote alarm sentry reporting. All
	remotes in a multipoint application must be set the same.
	These alarm responses are non-intrusive to data."
    ::= { nms520UnitCfgEntry 5 }


nms520DtePortType OBJECT-TYPE
    SYNTAX INTEGER {
    	rs232(1),
    	v35(2),
	auto(3)
    }
    ACCESS read-write
    STATUS mandatory
    DESCRIPTION
	"The value auto(3), indicates that the DTE port is automatically 
	being detected, and set. The rs232(1), will force the DTE port 
	to EIA/TIA-232-E, and v35(2), will force the DTE port to V.35."
    ::= { nms520UnitCfgEntry 6}

nms520DteCtsDelay OBJECT-TYPE
    SYNTAX INTEGER {
    	ctsOn(1),
    	cts0mSec(2),
    	ctsFixed3Char(3)
    }
    ACCESS read-write
    STATUS mandatory
    DESCRIPTION
    	"RTS/CTS Delay options

		ctsOn(1) 	Forces both RTS and CTS On regardless of the
				state of the attached business equipment (the
				transmitter is On regardless of the status of
				the RTS interface lead). MIB object
				nms520DteCtsDelayExt is ignored.

		cts0mSec(2)	Provides zero bits of delay between active
				RTS and CTS being set to active. MIB object
				nms520DteCtsDelayExt must be set to ext0mSec(1).

		ctsFix3Char(3)	Provides three character bits of delay between
 				active RTS and CTS being set to active. MIB
 				object nms520DteCtsDelayExt must be set to
 				ext0mSec(1)."
    ::= { nms520UnitCfgEntry 7 }

nms520DteCtsDelayExt OBJECT-TYPE
    SYNTAX INTEGER {
    	ext0mSec(1),
    	ext30mSec(2),
    	ext60mSec(3),
    	ext90mSec(4)
    }
    ACCESS read-write
    STATUS mandatory
    DESCRIPTION
    	"RTS/CTS Delay options extension

		ext0mSec(1)	Used to enable options cts0mSec(2) or
				ctsFix3Char(3) from MIB object
				nms520DteCtsDelay.

		ext30mSec(2)	Provides 30 msec of delay between active
				RTS and CTS being set to active. MIB object
				nms520DteCtsDelay must be set for either
				cts0mSec(2) or ctsFix3Char(3).

		ext60mSec(3)	Provides 60 msec of delay between active
				RTS and CTS being set to active. MIB object
				nms520DteCtsDelay must be set for either
				cts0mSec(2) or ctsFix3Char(3).


		ext90mSec(4)	Provides 90 msec of delay between active
				RTS and CTS being set to active. MIB object
				nms520DteCtsDelay must be set for either
				cts0mSec(2) or ctsFix3Char(3)."
   ::= { nms520UnitCfgEntry 8 }


nms520FirmwareLevel OBJECT-TYPE
    SYNTAX DisplayString (SIZE(2))
    ACCESS read-only
    STATUS mandatory
    DESCRIPTION
	 "The version number of the firmware, to allow products to know which 
	 revision is installed.  The released version number is sequenced from 
	 --, A-, ... AA, ... ZZ.  Test versions are numerical from 01 to 99."
    ::= { nms520UnitCfgEntry 9}


nms520DaisyChainBps OBJECT-TYPE
    SYNTAX INTEGER {
    	bps75(1),			-- data rate is 75 bits/sec
    	bps9600(2)			-- data rate is 9600 bits/sec
    }
    ACCESS read-write
    STATUS mandatory
    DESCRIPTION
    	"Indicates the data rate at which the management data is 
	sent/received when the gdcNmsManagementSource is daisyChain(4)." 
    ::= { nms520UnitCfgEntry 10 }


nms520AlarmCfgCountWindow OBJECT-TYPE
    SYNTAX  INTEGER (1..15)
    ACCESS read-write
    STATUS mandatory
    DESCRIPTION
    	"The DDS Alarm Threshold Alarm Interval. It specifies the amount of 
	time in minutes, 1 to 15 minutes, in which the threshold setting is 
	to be exceeded for the alarm to occur.  There is one Alarm Interval
	for all five alarms that require thresholds: nms520JitterAlm,
	nms520BpvAlm, nms520FrameLossAlm, nms520SignalToNoiseAlm and
	nms520RxSignalLowAlm. "
    ::= { nms520UnitCfgEntry 11 }

nms520SoftReset OBJECT-TYPE
    SYNTAX INTEGER {
    	normal(1),      -- read only
    	reset(2)	-- write only
    }
    ACCESS read-write
    STATUS mandatory
    DESCRIPTION
    	"This object will cause software reset in dataset."
    ::= { nms520UnitCfgEntry 12 }


nms520FrontPanelInhibit OBJECT-TYPE
    SYNTAX INTEGER {
	fpInhibited(1),		-- Read only
	fpEnabled(2),		-- Read only
    	execute(3)		-- Write only
    }
    ACCESS read-write
    STATUS mandatory
    DESCRIPTION
	"Inhibits all front panel test switches.  If a test
	switch is activated while inhibited it will simply be ignored.
	If enabled via the nms520FrontPanelEnable object the test 
	switch will function as normal."
    ::= { nms520UnitCfgEntry 13 }


nms520FrontPanelEnable OBJECT-TYPE
    SYNTAX INTEGER {
	fpInhibited(1),		-- Read only
	fpEnabled(2),		-- Read only
    	execute(3)		-- Write only
    }
    ACCESS read-write
    STATUS mandatory
    DESCRIPTION
	"Enables all front panel test switches.  If a test
	switch is activated while inhibited, via the 
	nms520FrontPanelInhibit object, it will simply be ignored.
	If enabled the test switch will function as normal."
    ::= { nms520UnitCfgEntry 14 }

nms520HdlcInvert OBJECT-TYPE
    SYNTAX INTEGER {
	normal(1),
	invert(2)
    }
    ACCESS read-write
    STATUS mandatory
    DESCRIPTION
	"Primary data invert option.  Will enhance the quality of
	data when network does not provide B8Z5.  Primarily used
	with DDS II 56k"
    ::= { nms520UnitCfgEntry 15 }

nms520PiggyBackDetect OBJECT-TYPE
    SYNTAX INTEGER  {
	not-installed(1),
	installed(2)
    }
    ACCESS read-only
    STATUS mandatory
    DESCRIPTION
	"If set to 2 then either a Data Rate Adadaptor or 530 card is
	installed."
    ::= { nms520UnitCfgEntry 16 }

nms520UnitType OBJECT-TYPE
    SYNTAX INTEGER  {
	singleHeight(1),
	withIFP(2)	
    }
    ACCESS read-only
    STATUS mandatory
    DESCRIPTION
	"with IFP(2) means that the unit has a LCD configurable display.
	single-height(1) means that the unit does NOT have a LCD
	configurable display."
    ::= { nms520UnitCfgEntry 17 }

nms520ExtPortCtrlOut1 OBJECT-TYPE
   SYNTAX INTEGER {
	on(1),
	off(2)
   }
   ACCESS read-write
   STATUS mandatory
   DESCRIPTION
	"This option sets the external output state (on/off) of the
	current network element and displays the external output."
   ::= { nms520UnitCfgEntry 18 }

nms520ExtPortCtrlOut2 OBJECT-TYPE
   SYNTAX INTEGER {
	on(1),
	off(2)
   }
   ACCESS read-write
   STATUS mandatory
   DESCRIPTION
	"This option sets the external output state (on/off) of the
	current network element and displays the external output."
   ::= { nms520UnitCfgEntry 19 }

--
-- LPDA Soft Configuration
--
--
--
-- nms520LpdaCfgTable OBJECT-TYPE
--    SYNTAX SEQUENCE OF Nms520LpdaCfgEntry
--    ACCESS not-accessible
--    STATUS mandatory
--    DESCRIPTION
--    	"The NMS520 Unit Configuration table.  This table augments 
--	the GDC SC Unit Configuration table, providing unit level 
--	configuration  for each NMS520 device installed.  For each entry 
--	in the GDC SC Unit Configuration table that represents an NMS520, 
--	there is a corresponding entry here whereby the value of the 
--	gdcSCunitCfgIndex object is equivalent to the value of the 
--	nms520LpdaCfgIndex object."
--    ::= { nms520 3 }
--
-- nms520LpdaCfgEntry OBJECT-TYPE
--    SYNTAX Nms520LpdaCfgEntry
--    ACCESS not-accessible
--    STATUS mandatory
--    DESCRIPTION
--    	"The NMS520 Unit Configuration table entry. The information in 
--	this entry arguments the information in the corresponding entry 
--	in the GDC SC Unit Configuration table and provides unit level 
--	configuration for the installed NMS520."
--    INDEX { nms520LpdaCfgIndex }
--    ::= { nms520LpdaCfgTable 1 }
--
-- Nms520LpdaCfgEntry ::= 
--    SEQUENCE {
--        nms520LpdaCfgIndex SCinstance,
--	nms520LpdaAddressing INTEGER,
--	nms520LpdaConnection INTEGER,
--	nms520LpdaAccess INTEGER,
--	nms520LpdaServiceType INTEGER,
--	nms520LpdaOperation INTEGER,
--	nms520LpdaAddress INTEGER,
--    	nms520LpdaStatus INTEGER
--    }
--
-- nms520LpdaCfgIndex OBJECT-TYPE
--    SYNTAX SCinstance
--    ACCESS read-only
--    STATUS mandatory
--    DESCRIPTION
--    	"The index value which uniquely identifies the NMS520 to which 
--	this entry is applicable.  This has the form of a SCinstance 
--	which defines the slot, line, and drop of the NMS520 with no 
--	sub-identifier value."
--    ::= { nms520LpdaCfgEntry 1 }
--
-- nms520LpdaAddressing OBJECT-TYPE
--    SYNTAX INTEGER {
--    	single(1),			Single Addressing
--    	multiple(2)			Multiple Addressing
--    }
--    ACCESS read-write
--    STATUS mandatory
--    DESCRIPTION
--    	"When multiple(2) is selected, the DSU recognizes the addresses 
--	instead of one, and the answers to any LPDA-2 commands containing 
--	one of these four addresses. This option must be entered in the 
--	remote DSU which is connected to a 'modem sharing unit'.
--
--	Because the DSU is physically connected to the 'modem sharing unit', 
--	the report to the NetView program is limited to the status of this 
--	interface.
--
--	The addresses of the DTEs attached to the same DSU through the 
--	'modem sharing unit' must have the same six most significant 
--	bits. If 'X' is any hexadecimal digit (0 to F), the possible 
--	groups of values are (with the additional usual limitations 
--	for 00, FC, FD, FE, FF):
--
--	 X0,X1,X2,X3	X4,X5,X6,X7	X8,X9,XA,XB	XC,XD,XE,XF
--
--	Tailing after the 'modem sharing unit' is not supported in a normal 
--	LPDA-2 enviroment."
--    ::= { nms520LpdaCfgEntry 2 }
--
-- nms520LpdaConnection OBJECT-TYPE
--    SYNTAX INTEGER {
--    	dte(1),			Unit is connected to the DTE
--    	tail(2)			DTE is connected to a tail circuit
--    }
--    ACCESS read-write
--    STATUS mandatory
--    DESCRIPTION
--    	"When tail(2) is selected, the DSU is connected to another DSU 
--	thru a Tailing Cable. When dte(1) is selected, the unit is 
--	derectly connected to a DTE."
--    ::= { nms520LpdaCfgEntry 3 }
--
-- nms520LpdaAccess OBJECT-TYPE
--    SYNTAX INTEGER {
--    	local(1),		Unit is connected to the front end
--    	remote(2)		Unit is a remote
--    }
--    ACCESS read-write
--    STATUS mandatory
--    DESCRIPTION
--    	"When local(1), is selected, the Unit is connected to the front 
--	end. It is a CONTROL DSU in a multipoint network, or a PRIMARY 
--	DSU in a point to point network. When the unit is a remote(2). 
--	It is either a TRIBUTARY DSU in a  multipoint network, or a 
--	SECONDARY DSU in a point to point network."
--    ::= { nms520LpdaCfgEntry 4 }
--
-- nms520LpdaServiceType OBJECT-TYPE
--    SYNTAX INTEGER {
--    	dds(1),			DDS sevice
--    	ldm(2)			Limited Distance Modem
--    }
--    ACCESS read-write
--    STATUS mandatory
--    DESCRIPTION
--    	"When the unit is a dds(1), the unit is connected to the DDS 
--	network. When the unit is a ldm(2), the unit is connected as a 
--	Limited Distance Modem."
--    ::= { nms520LpdaCfgEntry 5 }
--
-- nms520LpdaOperation OBJECT-TYPE
--    SYNTAX INTEGER {
--    	pointToPoint(1),		
--    	multipoint(2)		
--    }
--    ACCESS read-write
--    STATUS mandatory
--    DESCRIPTION
--    	"When pointToPoint(1) is selected, the unit is operation in a 
--	point to point network. When multipoint(2) is selected the unit 
--	is used in a multipoint network."
--    ::= { nms520LpdaCfgEntry 6 }
--
--
-- nms520LpdaAddress OBJECT-TYPE
--    SYNTAX INTEGER (1..251)
--    ACCESS read-write
--    STATUS mandatory
--    DESCRIPTION
--    	"Valid addresses range from 1 to 251."
--    ::= { nms520LpdaCfgEntry 7 }
--
--
-- nms520LpdaStatus OBJECT-TYPE
--    SYNTAX INTEGER {
--    	enabled(1),			LPDA option is enabled
--    	disabled(2)			LPDA option is disabled
--    }
--    ACCESS read-write
--    STATUS mandatory
--    DESCRIPTION
--    	"Identifies whether or not the LPDA option is enabled."
--    ::= { nms520LpdaCfgEntry 8 }

--**************************************************************************
--                      Alarm Configuration
--**************************************************************************
nms520AlarmData  	OBJECT IDENTIFIER ::= { nms520 4 }

nms520NoResponseAlm 		OBJECT IDENTIFIER ::= { nms520AlarmData 1 }
nms520DiagRxErrAlm 		OBJECT IDENTIFIER ::= { nms520AlarmData 2 }
nms520PowerUpAlm 		OBJECT IDENTIFIER ::= { nms520AlarmData 3 }
nms520EEChkSumErrAlm 		OBJECT IDENTIFIER ::= { nms520AlarmData 4 }
nms520StcLoopbackAlm       	OBJECT IDENTIFIER ::= { nms520AlarmData 5 } 
nms520NoNtwkLoopCurrentAlm 	OBJECT IDENTIFIER ::= { nms520AlarmData 6 } 
nms520LinePairsReversedAlm 	OBJECT IDENTIFIER ::= { nms520AlarmData 7 } 
nms520NoSignalAlm	        OBJECT IDENTIFIER ::= { nms520AlarmData 8 } 
nms520FpTestAlm	        	OBJECT IDENTIFIER ::= { nms520AlarmData 9 } 
nms520StreamingAlm      	OBJECT IDENTIFIER ::= { nms520AlarmData 10 } 
nms520DSRLossAlm		OBJECT IDENTIFIER ::= { nms520AlarmData 11 } 
nms520DTRLossAlm 		OBJECT IDENTIFIER ::= { nms520AlarmData 12 }
nms520DTPLossAlm        	OBJECT IDENTIFIER ::= { nms520AlarmData 13 }
nms520DCDLossAlm        	OBJECT IDENTIFIER ::= { nms520AlarmData 14 } 
nms520RXDLossAlm        	OBJECT IDENTIFIER ::= { nms520AlarmData 15 } 
nms520TXDLossAlm        	OBJECT IDENTIFIER ::= { nms520AlarmData 16 } 
nms520TmShortedAlm      	OBJECT IDENTIFIER ::= { nms520AlarmData 17 } 
nms520DcdShortedAlm     	OBJECT IDENTIFIER ::= { nms520AlarmData 18 } 
nms520DsrShortedAlm     	OBJECT IDENTIFIER ::= { nms520AlarmData 19 } 
nms520CtsShortedAlm     	OBJECT IDENTIFIER ::= { nms520AlarmData 20 } 
nms520RxdShortedAlm     	OBJECT IDENTIFIER ::= { nms520AlarmData 21 } 
nms520RxcShortedAlm     	OBJECT IDENTIFIER ::= { nms520AlarmData 22 } 
nms520TxcShortedAlm     	OBJECT IDENTIFIER ::= { nms520AlarmData 23 }
nms520DBURequestForScanAlm      OBJECT IDENTIFIER ::= { nms520AlarmData 24 } 
nms520DBUOnalm                  OBJECT IDENTIFIER ::= { nms520AlarmData 25 } 
nms520DBUFailedAlm              OBJECT IDENTIFIER ::= { nms520AlarmData 26 }  
nms520NoDSUResponseAlm          OBJECT IDENTIFIER ::= { nms520AlarmData 27 } 
nms520NoDTEPollingAlm           OBJECT IDENTIFIER ::= { nms520AlarmData 28 } 
nms520JitterAlm         	OBJECT IDENTIFIER ::= { nms520AlarmData 29 } 
nms520BpvAlm            	OBJECT IDENTIFIER ::= { nms520AlarmData 30 } 
nms520FrameLossAlm      	OBJECT IDENTIFIER ::= { nms520AlarmData 31 } 
nms520SignalToNoiseAlm  	OBJECT IDENTIFIER ::= { nms520AlarmData 32 } 
nms520RxSignalLowAlm    	OBJECT IDENTIFIER ::= { nms520AlarmData 33 } 
nms520ExtInputChangeAlm		OBJECT IDENTIFIER ::= { nms520AlarmData 34 }
nms520ExtInputLowAlm		OBJECT IDENTIFIER ::= { nms520AlarmData 35 }

-- The following alarms are 'NOT MASKABLE' nms520NoResponseAlm {1},
-- nms520DiagRxErrAlm {2} and nms520PowerUpAlm {3}. All other alarms 'ARE MASKABLE'. 
-- Alarm entries nms520JitterAlm{29}, nms520BpvAlm{30}, nms520FrameLossAlm{31}, 
-- nms520SignalToNoiseAlm{32}, and nms520RxSignalLowAlm{33} require 
-- threshold settings. See nms520AlarmCfgTable for alarm threshold settings.

-- Alarm		Table Entry			Port Use
-- --------------	---------------------------	------------ 
-- No Responce		nms520NoResponseAlm		DTE and Line
-- Diag Rx Error	nms520DiagRxErrAlm		DTE and Line
-- Power Up Alarm 	nms520PowerUpAlm		DTE and Line
-- EEPROM Corrupt	nms520CfgChkSumErrAlm		DTE and Line
-- Network Loop		nms520StcLoopbackAlm 		Line
-- No Loop Current	nms520NoNtwkLoopCurrentAlm 	Line
-- Line Pair Reversed	nms520LinePairsReversedAlm	Line
-- No Signal		nms520NoSignalAlm		Line
-- Front Panel Test	nms520FpTestAlm			DTE and Line
-- Streaming		nms520StreamingAlm		DTE
-- DSR Loss		nms520DSRLossAlm		DTE
-- DTR Loss		nms520DTRLossAlm		DTE
-- DTP Loss		nms520DTPLossAlm		DTE
-- DCD Loss		nms520DCDLossAlm		DTE
-- RXD Loss		nms520RXDLossAlm		DTE
-- TXD Loss		nms520TXDLossAlm		DTE
-- TM Shorted		nms520TmShortedAlm		DTE
-- DCD Shorted		nms520DcdShortedAlm		DTE
-- DSR Shorted		nms520DsrShortedAlm		DTE
-- CTS Shorted		nms520CtsShortedAlm		DTE
-- RXD Shorted		nms520RxdShortedAlm		DTE
-- RXC Shorted		nms520RxcShortedAlm		DTE
-- TXC Shorted		nms520TxcShortedAlm		DTE
-- Jitter		nms520JitterAlm			Line
-- Bipolar Violations	nms520BpvAlm			Line
-- Frame Loss		nms520FrameLossAlm		Line
-- Signal/Noise Ratio	nms520SignalToNoiseAlm		Line
-- RX Level Low		nms520RxSignalLowAlm		Line
-- DBU request for scan nms520DBURequestforScanAlm      Line
-- DBU on 		nms520DBUOnalm                  Line
-- DBU Failed		nms520DBUFailedAlm              Line
-- No response from DSU	nms520NoDSUResponseAlm          Line
-- No DTE Polling	nms520NoDTEPollingAlm           DTE

--*****************************************************************************
--                    NEW ALARMS CONFIGURATION TABLE
--*****************************************************************************
nms520AlarmCfgTable OBJECT-TYPE
        SYNTAX  SEQUENCE OF Nms520AlarmCfgEntry
        ACCESS  not-accessible
        STATUS  mandatory   
        DESCRIPTION 
                "The GDC NMS520 Alarm Configuration Table."
        ::= { nms520 8 }

nms520AlarmCfgEntry OBJECT-TYPE
        SYNTAX  Nms520AlarmCfgEntry
        ACCESS  not-accessible
        STATUS  mandatory
        DESCRIPTION
		"An entry in the GDC NMS520 alarm Configuration table."
        INDEX   { nms520AlarmCfgIndex, nms520AlarmCfgIdentifier }   
        ::= { nms520AlarmCfgTable 1 }

Nms520AlarmCfgEntry ::=
        SEQUENCE {
		nms520AlarmCfgIndex 		SCinstance,
                nms520AlarmCfgIdentifier 	OBJECT IDENTIFIER,
		nms520AlarmCfgThreshold		INTEGER
	}
nms520AlarmCfgIndex OBJECT-TYPE
        SYNTAX  SCinstance
        ACCESS  read-only
	STATUS  mandatory
        DESCRIPTION
               "This object is the index of the NMS520 Alarm 
		Threshold Configuration table."
        ::= { nms520AlarmCfgEntry 1 }

nms520AlarmCfgIdentifier OBJECT-TYPE
    SYNTAX OBJECT IDENTIFIER
    ACCESS read-only
    STATUS mandatory
    DESCRIPTION
        "The unique alarm identifier assigned to this alarm type. The
         format of this identifier is an OBJECT IDENTIFIER that has
         the following format: {iso(1) org(3) dod(6) internet(1)
         private(4) enterprises(1) gdc(498) xxx(x) alarm(z) yyy(y)
         where xxx(x) is the administratively assigned family object
        identifier (z) is the object identifier for alarms in the family
        defined MIB and yyy(y) is the administratively assigned alarm
        type identifier for this alarm."
    ::= { nms520AlarmCfgEntry 2 }


nms520AlarmCfgThreshold OBJECT-TYPE
    SYNTAX  INTEGER (-50..99)
    ACCESS read-write
    STATUS mandatory
    DESCRIPTION
    	"This function sets/reads the alarm threashold settings criteria.
	This threshold is used along with the alarm window to determine
	the number of instances in a given time frame for an alarm to 
	occur before the alarm is considered active. 

Alarm           	Table Entry		Threshold Range   Defaults
------------------	--------------------	--------------	  --------
Jitter          	nms520JitterAlm        	0 to 99 %	  9 %
Bipolar Violations	nms520BpvAlm            0 to 99 Count	  10
Frame Loss      	nms520FrameLossAlm      0 to 99 Count	  10
Signal to Noise Ratio 	nms520SignalToNoiseAlm 	0 to 50 	  0
Receive Level Low 	nms520RxSignalLowAlm    -50 to 6 dB	  -33 dB"
    ::= { nms520AlarmCfgEntry 3 }


--
-- DDS Line Statistics
--
nms520LineStatsTable OBJECT-TYPE
    SYNTAX SEQUENCE OF Nms520LineStatsEntry
    ACCESS not-accessible
    STATUS mandatory
    DESCRIPTION
    	"The DDS Line Statistics table."
    ::= { nms520 5 }

nms520LineStatsEntry OBJECT-TYPE
    SYNTAX Nms520LineStatsEntry
    ACCESS not-accessible
    STATUS mandatory
    DESCRIPTION
    	"An entry in the DDS Line Statistics Table."
    INDEX { nms520LineStatsIndex, nms520LineStatsInterval }
    ::= { nms520LineStatsTable 1 }

Nms520LineStatsEntry ::=
SEQUENCE {
    	nms520LineStatsIndex SCinstance,
	nms520LineStatsInterval INTEGER,
    	nms520LineStatsTxInterpretation INTEGER,
    	nms520LineStatsTxLevel INTEGER,
    	nms520LineStatsRxLevel INTEGER,
    	nms520LineStatsSignalToNoiseRatio INTEGER,
    	nms520LineStatsSignalQuality INTEGER,
    	nms520LineStatsJitter INTEGER,
    	nms520LineStatsBpvCount INTEGER,
    	nms520LineStatsFrameLossCount INTEGER
    }

nms520LineStatsIndex OBJECT-TYPE
    SYNTAX SCinstance
    ACCESS read-only
    STATUS mandatory
    DESCRIPTION
    	""
    ::= { nms520LineStatsEntry 1 }

nms520LineStatsInterval OBJECT-TYPE
    SYNTAX  INTEGER (1..15)
    ACCESS read-only
    STATUS mandatory
    DESCRIPTION
    	"The DDS Line Statistics Interval. It specifies the amount of time 
	in minutes (1 to 15 minutes) the unit will use to report statistical
	information. The unit will record statictics every minute and hold
	that information for 15 minutes. Past statistics can read from 1 to 
	15 minutes ago. A time must be specified to read any object in the
	ms520LineStatsTable. "
    ::= { nms520LineStatsEntry 2 }

nms520LineStatsTxInterpretation OBJECT-TYPE
    SYNTAX INTEGER {
	normal(1),
    	noSignal(2),
    	notAvailable(3),
    	overRange(4)
    }
    ACCESS read-only
    STATUS mandatory
    DESCRIPTION
    	"This object will report the status of the line measurements, 
	for the selected period. If noSignal(2), it will indicate that 
	there is no receive signal availible. If notAvailable(3), it will 
	indicate that the measurements have not completed. And if 
	overRange(4), will indicate that the measurements taken are over 
	measument the range. "
    ::= { nms520LineStatsEntry 3}
    
nms520LineStatsTxLevel OBJECT-TYPE
    SYNTAX INTEGER {
	txLevel0dB(1),
    	txLevel6dB(2)
    }
    ACCESS read-only
    STATUS mandatory
    DESCRIPTION
    	"Will report the transmit Level of the line to be 0dB txLevel0dB(1),
	or 6dB txLevel6dB(2) as measured by the unit X minutes ago
	(1 to 15 miniutes) as specified by nms520LineStatsInterval. "
    ::= { nms520LineStatsEntry 4}

nms520LineStatsRxLevel OBJECT-TYPE
    SYNTAX INTEGER (-50..6)
    ACCESS read-only
    STATUS mandatory
    DESCRIPTION
    	"This object will report the receive level measured at X minutes ago
	(1 to 15 miniutes) as specified by nms520LineStatsInterval.  The range 
	is between the -50dB to +6dB."
    ::= { nms520LineStatsEntry 5 }

nms520LineStatsSignalToNoiseRatio OBJECT-TYPE
    SYNTAX INTEGER (0..50)
    ACCESS read-only
    STATUS mandatory
    DESCRIPTION
    	"This object will the report the signal to noise ratio measured X minutes 
	ago(1 to 15 miniutes) as specified by nms520LineStatsInterval. The range
	is from 0 to 50, for the selected period. The value is absolute. "
    ::= { nms520LineStatsEntry 6 }

nms520LineStatsSignalQuality OBJECT-TYPE
    SYNTAX INTEGER {
    	good(1),
    	fair(2),
    	bad(3)
    }
    ACCESS read-only
    STATUS mandatory
    DESCRIPTION
    	"This object will the report the signal quality of the line measured X 
	minutes ago (1 to 15 miniutes) as specified by nms520LineStatsInterval."
    ::= { nms520LineStatsEntry 7 }

nms520LineStatsJitter OBJECT-TYPE
    SYNTAX INTEGER (0..99)
    ACCESS read-only
    STATUS mandatory
    DESCRIPTION
    	"This object will the report the percent jitter of the line measured X 
	minutes ago (1 to 15 miniutes) as specified by nms520LineStatsInterval.
	The range is 0% to 99% Jitter."
    ::= { nms520LineStatsEntry 8 }

nms520LineStatsBpvCount OBJECT-TYPE
    SYNTAX INTEGER (0..99)
    ACCESS read-only
    STATUS mandatory
    DESCRIPTION
    	"This object will the report the number of bipolar violation that have
	occured over the last X minutes (1 to 15 minutes). The range is from 0
	to 99 violations. "
    ::= { nms520LineStatsEntry 9 }

nms520LineStatsFrameLossCount OBJECT-TYPE
    SYNTAX INTEGER (0..99)
    ACCESS read-only
    STATUS mandatory
    DESCRIPTION
    	"This object will the report the numbrt of frame losses that have
	occured over the last X minutes (1 to 15 minutes). The range is from 0
	to 99 frame losses. "
    ::= { nms520LineStatsEntry 10 }

--
-- Diagonostics
--
--


nms520DiagCfgTable OBJECT-TYPE
    SYNTAX SEQUENCE OF Nms520DiagCfgEntry
    ACCESS not-accessible
    STATUS mandatory
    DESCRIPTION
    	"The NMS520 Unit Diagonostic table. "
    ::= { nms520 6 }

nms520DiagCfgEntry OBJECT-TYPE
    SYNTAX Nms520DiagCfgEntry
    ACCESS not-accessible
    STATUS mandatory
    DESCRIPTION
    	"The NMS520 Unit Diagonostic table entry. "
    INDEX { nms520DiagCfgIndex }
    ::= { nms520DiagCfgTable 1 }

Nms520DiagCfgEntry ::= 
    SEQUENCE {
	nms520DiagCfgIndex SCinstance,
	nms520DiagSendCode INTEGER,
	nms520DiagTestExceptions INTEGER,
	nms520DiagBitErrors INTEGER,
	nms520DiagBlockErrors INTEGER,
	nms520DiagTestReset INTEGER,
	nms520DiagTimeDelay INTEGER
    }

nms520DiagCfgIndex OBJECT-TYPE
    SYNTAX SCinstance
    ACCESS read-only
    STATUS mandatory
    DESCRIPTION
    	"The index value which uniquely identifies the NMS520 to which 
	this entry is applicable.  This has the form of a SCinstance 
	which defines the slot, line, and drop of the NMS520 with no 
	sub-identifier value."
    ::= { nms520DiagCfgEntry 1 }


nms520DiagSendCode OBJECT-TYPE
    SYNTAX INTEGER {
    	sendOtherPattern(1),
    	send511Pattern(2),
    	send2047Pattern(3),
    	send15BitPattern(4)
    }
    ACCESS read-write
    STATUS mandatory
    DESCRIPTION
	"Configures the selftest pattern to be run during any
	diagonostic test involving selftest. If option SendOtherPattern is
        selected, then pattern will default to 15 bit if unit is set
	for 56k-DDS/sc-multi point else pattern will default to 511 bit
	for all other conditions"
    ::= { nms520DiagCfgEntry 2 }


nms520DiagTestExceptions OBJECT-TYPE
    SYNTAX INTEGER {
	noExceptions(1),
	blocksOutOfRange(2),
	bitsOutOfRange(3),
	blocksAndBitsOutOfRange(4)
    }
    ACCESS read-only
    STATUS mandatory
    DESCRIPTION
    	"Indicates exceptions that have occurred that may affect
    	interpretation of the test results.

    	The value of this object is a sum.  This sum initially take
    	the value zero.  Then, for each exception, the value
    	associated with the exception is added to the sum.

    	The exception values are:

    		value	exception
		    0	No errors
   		    1   bit over range
    		    2   block over range
		    4 	bit and block over range"
    ::= { nms520DiagCfgEntry 3 }

nms520DiagBitErrors OBJECT-TYPE
    SYNTAX INTEGER (0..65535)
    ACCESS read-only
    STATUS mandatory
    DESCRIPTION
    	"The bit errors of the last diagnostic test that involved a
	Selftest pattern.  Reading bit errors while a diagnostic
	test in running will cause the unit to drop out of test
	and invalidate the bit errors.  Bit errors should be read
	only after the test is completed.  The valid range for bit
	errors is 0 to 1,023, 65535 will be returned if for any reason
	the test was terminated early."
    ::= { nms520DiagCfgEntry 4 }

nms520DiagBlockErrors OBJECT-TYPE
    SYNTAX INTEGER (0..65535)
    ACCESS read-only
    STATUS mandatory
    DESCRIPTION
    	"The block errors of the last diagnostic test that involved a
	Selftest pattern.  Reading block errors while a diagnostic
	test in running will cause the unit to drop out of test
	and invalidate the block errors.  Block errors should be read
	only after the test is completed.  The valid range for block
	errors is 0 to 1,023, 65535 will be returned if for any reason
	the test was terminated early."
    ::= { nms520DiagCfgEntry 5 }


nms520DiagTestReset OBJECT-TYPE
    SYNTAX INTEGER {
    	normal(1),      -- read only
	diagnostic(2),  -- read only
    	resetTest(3)	-- write only
    }
    ACCESS read-write
    STATUS mandatory
    DESCRIPTION
    	"This object will halt the execution of any and all
	diagnostic test that may be running with the exception 
	of the Network Delay Test."
    ::= { nms520DiagCfgEntry 6 }

nms520DiagTimeDelay OBJECT-TYPE
    SYNTAX INTEGER (0..16383)
    ACCESS read-only
    STATUS mandatory
    DESCRIPTION
    	"This object reads the results of a Network Delay Test.
	The results are valid only after the test is completed 
	which takes about 10 seconds. The unit for time delay is 
	in miliseconds. The valid range for delay is 0 to 4096, 
	16383 will be returned if for any reason the test was terminated 
	early. Reading this object while a test is in progress will
	terminate the test."
    ::= { nms520DiagCfgEntry 7 }

--
--
--

nms520DiagExcTable OBJECT-TYPE
    SYNTAX SEQUENCE OF Nms520DiagExcEntry
    ACCESS not-accessible
    STATUS mandatory
    DESCRIPTION
    	"The NMS520 Unit Diagonostic table. "
    ::= { nms520 7 }

nms520DiagExcEntry OBJECT-TYPE
    SYNTAX Nms520DiagExcEntry
    ACCESS not-accessible
    STATUS mandatory
    DESCRIPTION
    	"The NMS520 Unit Diagonostic table entry. "
    INDEX { nms520DiagExcIndex }
    ::= { nms520DiagExcTable 1 }

Nms520DiagExcEntry ::= 
    SEQUENCE {
	nms520DiagExcIndex SCinstance,
	nms520DiagExtLineloop INTEGER,
	nms520DiagIntLineloop INTEGER,
	nms520DiagIntDataloop INTEGER,
	nms520DiagEndToEndSelftest INTEGER,
	nms520DiagNetworkDelay INTEGER,
	nms520DiagTestStatus INTEGER,
 	nms520DiagExtDataloop INTEGER
}

nms520DiagExcIndex OBJECT-TYPE
    SYNTAX SCinstance
    ACCESS read-only
    STATUS mandatory
    DESCRIPTION
    	"The index value which uniquely identifies the NMS520 to which 
	this entry is applicable.  This has the form of a SCinstance 
	which defines the slot, line, and drop of the NMS520 with no 
	sub-identifier value."
    ::= { nms520DiagExcEntry 1 }


nms520DiagExtLineloop OBJECT-TYPE
  	SYNTAX INTEGER {
	lineloopOff(1),		-- Read only
        lineloopOn(2),		-- Read only
        external(3)		-- Write only
    }
    ACCESS read-write
    STATUS obsolete
    DESCRIPTION
	"Lineloop (or Analoop) can be either a Bilaterial or Unilaterial
        loopback depending on option ddsDteTermaloop.  To initiate a
	Lineloop with no Selftest SET this object and specifiy external,
	this will allow the data from the DTE to looped back to itself.
	Emun external(3) is write only.  The only valid response to a
	READ is lineloopOn(2) or lineloopOff(1). To halt this test you must
	SET the nms520DiagTestReset object. Reading test results via the
	sc5520DiagBitErrors or  nms520DiagBlockErrors objects while the test
	is running will also cause the test to terminate.
	There are no test results associated with this test. "
   ::= { nms520DiagExcEntry 2 }


nms520DiagIntLineloop OBJECT-TYPE
  	SYNTAX INTEGER {
	lineloopOff(1),		-- Read only
        lineloopOn(2),		-- Read only
	blocks1(3),		-- Write only
	blocks10(4),		-- Write only
	blocks100(5),		-- Write only
	blocks500(6),		-- Write only
	blocks1000(7),		-- Write only
	blocks5000(8),		-- Write only
	blocks10000(9),		-- Write only
	blocks50000(10) 	-- Write only
    }
    ACCESS read-write
    STATUS mandatory
    DESCRIPTION
	"Lineloop (or Analoop) can be either a Bilaterial or Unilaterial
	loopback depending on option ddsDteTermaloop.  To initiate a
	Lineloop with Selftest SET this object and specifiy a 
	blocksize. The blocksize indicates the number of blocks the 
	Selftest pattern generator will run.  There are 1000 bits/block.
	Emuns 3 through 10 are write only.  The only valid 
	responses to a READ are lineloopOn(2) or lineloopOff(1). This test 
	will terminate after the specified number of blocks have been run.
 	Reading test results via the nms520DiagBitErrors or nms520DiagBlockErrors 
	objects while the test is running will cause 
	the test to terminate prematurely and render the results invalid.
	Test results should be only read after the test is completed.  
	The current Test Status can be obtained by reading this object or the
	nms520DiagTestStatus object on the unit under test.  This test can 
	also be terminated by seting the nms520DiagTestReset object. "
    ::= { nms520DiagExcEntry 3 }



nms520DiagIntDataloop OBJECT-TYPE
	SYNTAX INTEGER {
	dataloopOff(1),		-- Read only
        dataloopOn(2),		-- Read only
	blocks1(3),		-- Write only
	blocks10(4),		-- Write only
	blocks100(5),		-- Write only
	blocks500(6),		-- Write only
	blocks1000(7),		-- Write only
	blocks5000(8),		-- Write only
	blocks10000(9),		-- Write only
	blocks50000(10)		-- Write only
    }
    ACCESS read-write
    STATUS mandatory
    DESCRIPTION
	"To initiate a Dataloop with Selftest SET this object and specifiy a 
	blocksize. The nms520 (the remote) unit will go into Dataloop and 
	the master (the sc5520) unit will go into Selftest.  The blocksize
	indicates the number of blocks the Selftest pattern generator will run.
	There are 1000 bits/block.  Emuns 3 through 10 are write only.
	The only valid responses to a READ are dataloopOn(2) or dataloopOff(1).
	This test will terminate after the specified number of blocks have been run.
 	Reading test results via the nms520DiagBitErrors or nms520DiagBlockErrors 
	objects while the test is running will cause the test to terminate 
	prematurely and render the results invalid.  Test results should be read 
	only after the test is completed and are available from the master (sc5520) 
	unit.  The current Test Status can be obtained by reading the 
	sc5520DiagTestStatus object on the master unit, reading test status on the 
	remote unit may interfere with the diagonostic test pattern and cause errors.
	This test can also be terminated by seting the nms520DiagTestReset object. "
    ::= { nms520DiagExcEntry 4 }


nms520DiagEndToEndSelftest OBJECT-TYPE
	SYNTAX INTEGER {
	endToEndOff(1),		-- Read only
        endToEndOn(2),		-- Read only
	blocks1(3),		-- Write only
	blocks10(4),		-- Write only
	blocks100(5),		-- Write only
	blocks500(6),		-- Write only
	blocks1000(7),		-- Write only
	blocks5000(8),		-- Write only
	blocks10000(9),		-- Write only
	blocks50000(10)		-- Write only
    }
    ACCESS read-write
    STATUS mandatory
    DESCRIPTION
	"To initiate an End to End Selftest(Error Rate Test) SET this object 
	and specifiy a blocksize.  Both the remote (nms520)
	amd master (sc5520) units will go into Selftest. The blocksize
	indicates the number of blocks the Selftest pattern generator will run.
	There are 1000 bits/block.  Emuns 3 through 10 are write only.
	The only valid responses to a READ are selftestOn(2) or selftestOff(1).
	This test will terminate after the specified number of blocks have been run.
 	Reading test results via the nms520DiagBitErrors or nms520DiagBlockErrors 
	objects while the test is running will cause 
	the test to terminate prematurely and render the results invalid.
	Test results should be read only after the test is completed and are 
	available from both the remote (nms520) and master (sc5520) units.  The 
	current Test Status can be obtained by reading the sc5520DiagTestStatus 
	object on the master unit, reading test status on the remote unit may 
	interfere with the diagonostic test patternand cause errors.  This test can 
	also be terminated by seting the nms520DiagTestReset object. "
   ::= { nms520DiagExcEntry 5 }


nms520DiagNetworkDelay OBJECT-TYPE
	SYNTAX INTEGER {
	delayTestOff(1),	-- Read only
        delayTestOn(2),		-- Read only
	runDelayTest(3) 	-- Write only
    }
    ACCESS read-write
    STATUS mandatory
    DESCRIPTION
	"To initiate a Network Delay test SET this object and specifiy 
	runDelayTest.  Both the remote (nms520) and master (sc5520) units 
	will go into a test to measure network delay. Emun 3 
	is write only.  The only valid responses to a READ are delayTestOn(2) 
	or delatTestOff(1).  This test will terminate after 10 seconds.  
 	Reading test results via the nms520DelayTime object while the test is 
	running will cause the test to terminate prematurely and render the 
	results invalid.  Test results should be read only after the test is 
	completed and are available from the master (sc5520) unit.  The 
	current Test Status can be obtained by reading the sc5520DiagTestStatus 
	object on the master unit, reading test status on the remote unit may 
	interfere with the test and cause errors. This test can not be 
	terminated early once it is started."
   ::= { nms520DiagExcEntry 6 }

nms520DiagTestStatus OBJECT-TYPE
    	SYNTAX INTEGER {
	noTest(1),			
	internalLineloop(2),        	-- Analoop & SelfTest
	externalDataloop(3),		-- Dataloop
  	internalDataloop(4),		-- Dataloop & SelfTest
	serviceTestCenterLoop(5),	-- Network initiated loopback
	endToend(6)			-- EndtoEnd Selftest
	}
    ACCESS read-only
    STATUS mandatory
    DESCRIPTION
	"This object gives the current diagonostic test status. noTest 
	indicates that no diagonostic test is currently active. Reading
	this object while in a diagonostic test involing two units may 
	interfere with a selftest pattern and invalidate the test results.
	Reading the sc5520DiagTestStatus (master unit) object during 
	dagonostic tests involing two unit will not disrupt the test 
	results. "
   ::= { nms520DiagExcEntry 7 }


nms520DiagExtDataloop OBJECT-TYPE
	SYNTAX INTEGER {
	dataloopOff(1),		-- Read only
        dataloopOn(2),		-- Read only
	external(3)		-- Write only
    }
    ACCESS read-write
    STATUS mandatory
    DESCRIPTION
	"To initiate a Dataloop test with no Selftest SET this object
	and specifiy external, this will allow the data from the DTE attached 
	to the far end unit (sc5520) to looped back to itself. Emun external(3) 
	is write only.  The only valid response to a READ is dataloopOn(2) or 
	dataloopOff(1). To halt this test you must SET the nms520DiagTestReset 
	object. Reading test results via the nms520DiagBitErrors or 
	nms520DiagBlockErrors objects while the test is running will also cause 
	the test to terminate. There are no test results associated with this test.  
	Reading test status on the remote unit via nms520DiagTestStatus may 
	interfere with the diagonostic test pattern generated from the terminal 
	equiptment. "
    ::= { nms520DiagExcEntry 8 }


END
