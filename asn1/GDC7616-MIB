-- Copyright 1996 General DataComm Ind., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.
--
-- Revision History
--
-- Version   Date          Name             Description
-- 1.00A     17-Apr-96  M. Cyr	        Initial Revision
-- 1.00B     23-May-96  S. Sankaran     Initial Revision
-- 1.00C     27-Jun-96  D. Baylis       Changed enum inhibit(3) to inhibit(2) on 
--                                      uas7616ChBDataRate 
-- 1.00D     10-Jul-96  D. Baylis       Changed uas7616DiagnosticTest to enum type
--					Changed uas7616Alarm OID to bql2 13
-- 1.00E     09-Sep-96  D. Baylis       Changed Performance Statistics Octet lengths
--					and added to the Descriptions
-- 1.00F     11-Sep-96  D. Baylis       Added rdl(5) to uas7616DiagnosticTest 
-- 1.00G     11-Sep-96  D. Baylis       Added rdlSelfTest(6) to uas7616DiagnosticTest 
-- 1.00H     04-Oct-96  D. Baylis       Flipped uas7616DiagnosticResetErrorCount enums to:
--					norm(1) and reset(2)
--
-- 1.00J     29-Oct-96  D. Baylis       Removed:uas7616LpSeverelyErroredSecondAlm   
--						uas7616AlarmCountWindow
--                                              uas7616LocalSES from local alarm 
--
--					Added:	uas7616LPMajorAlm
--						uas7616LPMinorAlm	 
--	          				uas7616ResetMajorAlarm to uas7616ControlTable	
--	          				uas7616ResetMinorAlarm to uas7616ControlTable
--						uas7616LPMajor to local alarm
--						uas7616LPMinor to local alarm
--
--					Changed:uas7616AlarmCountThreshold (nums)
--						uas7616Current15MinStat (added FEBES)
--						uas7616Recent24HrStat
--						uas7616Current24HrStat
--						uas7616IntervalStat
--
-- 1.00K    06-Nov-96  D. Baylis        Added: 	alarms and thresholds per 1.00H (in addition
--						  to ones added in 1.00J) to support node type 30
--						Added uas7616LocalSES back
--						
--					Changed:Names and OID's of alarms from rev 100J to support
--						  node type 45 and 45.
--						OID's for current alarms after inserting uas7616LocalSES	

GDC7616-MIB DEFINITIONS	   ::=	   BEGIN

IMPORTS

	enterprises		FROM RFC1155-SMI
	DisplayString         	FROM RFC1213-MIB
	OBJECT-TYPE             FROM RFC-1212
	SCinstance             	FROM GDCMACRO-MIB;

gdc		OBJECT IDENTIFIER		::= { enterprises 498 }
bql2		OBJECT IDENTIFIER		::= { gdc 12 }
uas7616         OBJECT IDENTIFIER               ::= { bql2 4 }


-- This is the GDC MIB for UAS 7616 product.  The UAS 7616
-- is intended to be the interface between the 2B1Q Network and the Mini-Star
-- Backplane, providing interface for up to three metallic loops.  The
-- UAS 7616 will comply with ITU G.960 line coding requirements.
--
-- This MIB is only usable when the configuration is software controllable.
--
-- See the GDC MIB requirements document to determine how the standard MIB's
-- are supported.
--
--*****************************************************************************
-- 	SCinstance is defined as the addressing/indexing method of accessing
--	table objects in this MIB. The SCinstance represents the SpectraComm
--	shelf Slot, Line, Drop and interface address.
--	Represented as SLDi, (Slot, Line, Drop, interface).
--
--	  7616
--     	 -----
--    	  SLDi
--    	  L=1
--     	  D=0
--     	  i=0 - 3
--
--*****************************************************************************




--**************************************************************************
--		GDC UAS 7616 - MIB VERSION NUMBER
--**************************************************************************

uas7616MIBVersion	OBJECT-TYPE
	SYNTAX	DisplayString (SIZE (5))
	ACCESS	read-only
	STATUS  mandatory
	DESCRIPTION
		"The version number of the MIB, to allow products to
		know which MIB is being supported.  The version number
		will be x.yzT where x is a major revision (1-9), y is a minor
		revision(0-9), z is a typo revision (0-9) and T indicates the
		MIB is still a test revision(A-Z).  When a release is complete
		no T should exist."
	::= { uas7616 1 }


--*****************************************************************************
--              GDC UAS 7616 - WHAT ARE YOU TABLE
--*****************************************************************************
--
-- This table contains network element information indexed by SLDi.
--
-- This table uses SCinstance as SLDi where i is always 0.
--
--
uas7616WhatAreYouTable OBJECT-TYPE
	SYNTAX	SEQUENCE OF Uas7616WhatAreYouEntry
	ACCESS  not-accessible
	STATUS  mandatory
	DESCRIPTION
			"The GDC 7616 What Are You Table."
	::= { uas7616 2 }

uas7616WhatAreYouEntry OBJECT-TYPE
	SYNTAX	Uas7616WhatAreYouEntry
	ACCESS  not-accessible
	STATUS  mandatory
	DESCRIPTION
			"An entry in the GDC 7616 What Are You table."
	INDEX	{ uas7616WhatAreYouIndex }
	::= { uas7616WhatAreYouTable 1 }

Uas7616WhatAreYouEntry ::=
	SEQUENCE  {
		  uas7616WhatAreYouIndex	SCinstance,
		  uas7616CodeRev		DisplayString,
		  uas7616AlarmStatus            OCTET STRING,
		  uas7616SystemTimingGenStatus	INTEGER
		  }

uas7616WhatAreYouIndex OBJECT-TYPE
	SYNTAX  SCinstance
	ACCESS  read-only
	STATUS  mandatory
	DESCRIPTION
	       "This object is the identifier of the 7616 What Are You table."
	::= { uas7616WhatAreYouEntry 1 }

uas7616CodeRev OBJECT-TYPE
	SYNTAX  DisplayString (SIZE (4))
	ACCESS  read-only
	STATUS  mandatory
	DESCRIPTION
		"This function returns the firmware code level.
		 Example A-  ,B-  "
	::= { uas7616WhatAreYouEntry 2 }

uas7616AlarmStatus OBJECT-TYPE
	SYNTAX	  OCTET STRING (SIZE (1..255))
	ACCESS	  read-only
	STATUS	  mandatory
	DESCRIPTION
		"The current alarms of the unit without the alarm masks."
	::= { uas7616WhatAreYouEntry 3 }

uas7616SystemTimingGenStatus	OBJECT-TYPE
	SYNTAX INTEGER {
			none(1),
			clk8khz(2),
			clk4mhz(3),
			clk8khzand4mhz(4)
	}
	ACCESS read-only
	STATUS mandatory
	DESCRIPTION
		"Indicates if the units configured for primary or secondary system clock are
		actually supplying clock and if it is the 8hkz, 4mhz, or both."
	::= {uas7616WhatAreYouEntry 4}

--******************************************************************************
--		GDC UAS 7616 - CONFIGURATION  TABLE
--******************************************************************************
--
-- This table contains the network element's configuration information indexed by SLDi and channel.
--
-- This table uses SCinstance defined as follows:
--     7616
--      -----
--      SLDi
--      L=1
--      D=0
--      i=1 - 3

uas7616ConfigTable OBJECT-TYPE
	SYNTAX	SEQUENCE OF Uas7616ConfigEntry
	ACCESS  not-accessible
	STATUS  mandatory
	DESCRIPTION
		"The GDC 7616 configuration table."
	::= { uas7616 3 }

uas7616ConfigEntry OBJECT-TYPE
	SYNTAX	Uas7616ConfigEntry
	ACCESS  not-accessible
	STATUS  mandatory
	DESCRIPTION
		"A listing of GDC 2B1Q 7616 options."
	INDEX	{ uas7616ConfigIndex }

	::= { uas7616ConfigTable 1 }

Uas7616ConfigEntry ::=
	SEQUENCE   {
			uas7616ConfigIndex	SCinstance,
			uas7616TXClockSource	INTEGER,
			uas7616TerminationType 	INTEGER,
			uas7616ChADataRate	INTEGER,
			uas7616ChBDataRate	INTEGER
		   }

uas7616ConfigIndex OBJECT-TYPE
	SYNTAX  SCinstance
	ACCESS  read-only
	STATUS  mandatory
	DESCRIPTION
		"A unique index for the Configuration  Table."
	::= { uas7616ConfigEntry 1 }

uas7616TXClockSource OBJECT-TYPE
	SYNTAX	INTEGER {
			system(1),
			recovered(2),
			internal(3)
			}
	ACCESS    read-write
	STATUS    mandatory
	DESCRIPTION     "Object to select the Transmit Clock  Source for the 7616."
	::= { uas7616ConfigEntry 2 }

uas7616TerminationType OBJECT-TYPE
	SYNTAX	INTEGER {
			nt(1),
			lt(2)
			}
	ACCESS    read-write
	STATUS    mandatory
	DESCRIPTION     "Object to select the Termination Type for the 7616."
	::= { uas7616ConfigEntry 3 }

uas7616ChADataRate OBJECT-TYPE
	SYNTAX  INTEGER {
			kbps64(1),
			kbps128(2),
			inhibit(3)
			}
	ACCESS    read-write
	STATUS    mandatory
	DESCRIPTION
		"Object to select the Data Rate on Channel A, Loop n."
        ::= { uas7616ConfigEntry 4 }

uas7616ChBDataRate OBJECT-TYPE
	SYNTAX  INTEGER {
			kbps64(1),
			inhibit(2)
			}
	ACCESS    read-write
	STATUS    mandatory
	DESCRIPTION
		"Object to select the Data Rate on Channel B, Loop n."
        ::= { uas7616ConfigEntry 5 }



--*****************************************************************************
--		GDC UAS 7616 - CONTROL TABLE
--*****************************************************************************
--
-- This table contains the 7616 control functions indexed by SLDi.
--
-- This table uses SCinstance defined as follows:
--      7616
--      -----
--      SLDi
--      L=1
--      D=0
--      i=0
--

uas7616ControlTable OBJECT-TYPE
	SYNTAX	SEQUENCE OF Uas7616ControlEntry
	ACCESS  not-accessible
	STATUS  mandatory
	DESCRIPTION
			"The GDC 7616 Control Table."
	::= { uas7616 5 }

uas7616ControlEntry OBJECT-TYPE
	SYNTAX	Uas7616ControlEntry
	ACCESS  not-accessible
	STATUS  mandatory
	DESCRIPTION
			"An entry in the GDC 7616 Control table."
	INDEX	{ uas7616ControlIndex }
	::= { uas7616ControlTable 1 }

Uas7616ControlEntry ::=
	SEQUENCE {
		  uas7616ControlIndex	SCinstance,
		  uas7616SoftReset	INTEGER,
		  uas7616EraseConfig	INTEGER,
		  uas7616LEDStatus	OCTET STRING,
		  uas7616InterfaceType	INTEGER,
		  uas7616SysTimingGen   INTEGER,
		  uas7616ResetIntervals	INTEGER,
		  uas7616SysUpTime      INTEGER,
		  uas7616SetRealTime    INTEGER,
		  uas7616ModuleClkSrc   INTEGER,
	          uas7616ResetMajorAlarm INTEGER,	
	          uas7616ResetMinorAlarm INTEGER	
		}

uas7616ControlIndex OBJECT-TYPE
	SYNTAX  SCinstance
	ACCESS  read-only
	STATUS  mandatory
	DESCRIPTION
	       "This object is the identifier of the  7616 Control table."
	::= { uas7616ControlEntry 1 }

uas7616SoftReset OBJECT-TYPE
	SYNTAX  INTEGER  {
			 normal(1),
			 reset(2)
			 }
        ACCESS  read-write
	STATUS  mandatory
	DESCRIPTION
                "Forces a soft reset on the network element.
                 The reset selection is write only. The normal
                 selection is read only."
	::= { uas7616ControlEntry 2 }

uas7616EraseConfig OBJECT-TYPE
	SYNTAX	INTEGER {
			normal(1),
			erase(2)
			}
	ACCESS	read-write
	STATUS  mandatory
	DESCRIPTION
		"Forces an erase of the stored configuration in the network	
		 element.  The erase selection is write only."
	::= { uas7616ControlEntry 3 }


uas7616LEDStatus OBJECT-TYPE
	SYNTAX	OCTET STRING (SIZE (3))
	ACCESS  read-only
	STATUS  mandatory
	DESCRIPTION
			"The GDC 7616 front panel LED Status.
			 A value of 1 means on, 0 is off.
			 byte 1 bit 7 (1.7) - not used
			 1.6 - not used
			 1.5 - loop 1 channel A (00 = No Change 01 = Green Active)
			 1.4 - 			(10 = Red Solid 11 = RedFlashing )
			 1.3 - loop 1 channel B (00 = No Change 01 = Green Active)
			 1.2 - 			(10 = Red Solid 11 = RedFlashing )
			 1.1 - loop 2 channel A (00 = No Change 01 = Green Active)
			 1.0 - 			(10 = Red Solid 11 = RedFlashing )

			 2.7 - not used
			 2.6 - not used
			 2.5 - loop 2 channel B (00 = No Change 01 = Green Active)
			 2.4 - 			(10 = Red Solid 11 = RedFlashing )
			 2.3 - loop 3 channel A (00 = No Change 01 = Green Active)
			 2.2 - 			(10 = Red Solid 11 = RedFlashing )
			 2.1 - loop 3 channel B (00 = No Change 01 = Green Active)
			 2.0 - 			(10 = Red Solid 11 = RedFlashing )

			 3.7 - not used
			 3.6 - not used
			 3.5 - not used
			 3.4 - alarm led
			 3.3 - test mode led
			 3.2 - in service
			 3.1 - system timing source
			 3.0 - management response"
	::= { uas7616ControlEntry 4 }

uas7616InterfaceType OBJECT-TYPE
	SYNTAX  INTEGER {
			diu(1),
			niu(2),
			notAssigned(3)
			}
	ACCESS    read-write
	STATUS    mandatory
	DESCRIPTION
		"Object used to configure the transmission interface type."
	::= {  uas7616ControlEntry 5 }

 uas7616SysTimingGen     OBJECT-TYPE
	SYNTAX INTEGER {
			none(1),
			primary(2),
			secondary(3)
			}
	ACCESS read-write
	STATUS mandatory
	DESCRIPTION
		"Selects if the unit provides system timing.
		none(1) - does not provide Timing Generator
		primary(2) - unit is primary Timing Generator for the shelf.
		secondary(3) - unit is secondary Timig Generator for the
			shelf.

		Only 1 unit in the shelf can the primary or secondary
		timing generator. All other must be none."

	::= {uas7616ControlEntry 6 }


uas7616ResetIntervals OBJECT-TYPE
     	SYNTAX INTEGER {
     		       reset(1),
     		       normal(2)
     		       }
     	ACCESS read-write
     	STATUS mandatory
        DESCRIPTION " This variable is used to reset Loop performance intervals.
 		      When it is set to reset, the Loop performance tables are
 		      reset to zero."
     	::= {  uas7616ControlEntry 7 }

 uas7616SysUpTime       OBJECT-TYPE
	 SYNTAX INTEGER (1..2147483647)
	 ACCESS read-only
	 STATUS mandatory
	 DESCRIPTION
		 "This variable is used to report the elapsed system tick
		 time for conversion to real time at the controller and is
		 not related to the sysUpTime referenced in MIB-II.
		 Upon power-up of the unit, the elapsed time is cleared.
		 The elapsed time counter rolls over upon reaching the
		 maximum count."
	 ::= { uas7616ControlEntry 8 }

 uas7616SetRealTime      OBJECT-TYPE
	SYNTAX  INTEGER (1..2147483647)
	ACCESS  read-write
	STATUS  mandatory
	DESCRIPTION
		"Number of seconds from midnight Dec 31, 1969."
	::= {uas7616ControlEntry 9 }

uas7616ModuleClkSrc OBJECT-TYPE
	SYNTAX  INTEGER {
			system(1),
			internal(2),
			recovered(3)
			}
	ACCESS    read-write
	STATUS    mandatory
	DESCRIPTION
		"This variable is used to read or set the Module Clock Source.
		 This variable must be system when uas7616SysTimingGen is set to none.
		 Any of the three selections when uas7616SysTimingGen is set to secondary,
		 and internal or recovered when uas7616SysTimingGen is set to primary."
	::= {  uas7616ControlEntry 10 }

uas7616ResetMajorAlarm	OBJECT-TYPE
	SYNTAX	INTEGER {
			reset(1),
			norm(2)
			}
     	ACCESS read-write 
     	STATUS mandatory
         DESCRIPTION " This variable is used to reset alarm per Loop basis."
     	::= { uas7616ControlEntry 11 }
 
uas7616ResetMinorAlarm	OBJECT-TYPE
	SYNTAX	INTEGER {
			reset(1),
			norm(2)
			}
     	ACCESS read-write 
     	STATUS mandatory
         DESCRIPTION " This variable is used to reset alarm per Loop basis."
     	::= { uas7616ControlEntry 12 }



--*****************************************************************************
--          GDC UAS 7616 - DIAGNOSTICS TABLE
--*****************************************************************************
--
-- This table contains the network element's diagnostic test information indexed by
-- SLDi and channel.
--
-- This table uses SCinstance defined as follows:
--     7616
--      -----
--      SLDi
--      L=1
--      D=0
--      i=1 - 3

uas7616DiagnosticTable OBJECT-TYPE
	SYNTAX	SEQUENCE OF Uas7616DiagnosticEntry
	ACCESS    not-accessible
	STATUS    mandatory
	DESCRIPTION
			"The GDC 7616 diagnostics table."
	::= { uas7616 6 }

uas7616DiagnosticEntry OBJECT-TYPE
	SYNTAX	  Uas7616DiagnosticEntry
	ACCESS    not-accessible
	STATUS    mandatory
	DESCRIPTION
			"A listing of GDC 7616 diagnostic tests"
	INDEX	   { uas7616DiagnosticIndex, uas7616DiagnosticChnlIndex }
	::= { uas7616DiagnosticTable 1 }

Uas7616DiagnosticEntry	::=
	SEQUENCE        {
			uas7616DiagnosticIndex		  SCinstance,
			uas7616DiagnosticChnlIndex	  INTEGER,
			uas7616DiagnosticTest	  	  INTEGER,
			uas7616DiagnosticResetErrorCount  INTEGER,
			uas7616DiagnosticResults	  INTEGER
			}

uas7616DiagnosticIndex OBJECT-TYPE
	SYNTAX    SCinstance
	ACCESS    read-only
	STATUS    mandatory
	DESCRIPTION
			"A unique index for the Diagnostic Table."
	::= { uas7616DiagnosticEntry 1 }

uas7616DiagnosticChnlIndex OBJECT-TYPE
	SYNTAX	INTEGER {
			channelA(1),
			channelB(2)
			}
	ACCESS	read-only
	STATUS  mandatory
	DESCRIPTION
		"A unique channel index for the Channel the test will run on."
	::= { uas7616DiagnosticEntry 2 }

uas7616DiagnosticTest  OBJECT-TYPE
	SYNTAX  INTEGER {

			 stopTest(1),
			 digitalLoopback(2),
			 patternGenTest(3),			 
			 unitTest(4),
			 rdl(5),
			 rdlSelfTest(6)
			}
	ACCESS	  read-write
	STATUS    mandatory
	DESCRIPTION
			"Selections digitalLoopback(2), patternGenTest(3), and unitTest(4) start 
			the associated test when written.  Reading will show which (if any) test
                        is active.  Writing a stopTestwill stop the test if any was in progress."
			 
	::= { uas7616DiagnosticEntry 3 }

uas7616DiagnosticResetErrorCount OBJECT-TYPE
	SYNTAX  INTEGER {
			norm (1),		-- read only
			reset (2)
			}
	ACCESS    read-write
	STATUS    mandatory
	DESCRIPTION
			"This function resets the error count on a given loop and channel.
			Management will always read a norm(1) and can only write a reset(2)."
	::= { uas7616DiagnosticEntry 4}

uas7616DiagnosticResults OBJECT-TYPE
	SYNTAX  INTEGER (0..2097153)
	ACCESS    read-only
	STATUS    mandatory
	DESCRIPTION
			"This function reads the self test results in
			 bit errors. 2^20"
	::= { uas7616DiagnosticEntry 5 }

--********************************************************************************
--	UAS 7616 ALARMS - INDIVIDUALLY IDENTIFIED FOR THE CONTROLLER
--********************************************************************************


uas7616Alarm OBJECT IDENTIFIER				        ::= { bql2 13 }

uas7616AlarmData OBJECT IDENTIFIER			        ::= { uas7616Alarm 1 }

-- no response alarm (this is a SCM generated alarm)
uas7616NoResponseAlm OBJECT IDENTIFIER     			::= { uas7616AlarmData 1 }

-- no diagnostic receive error alarm (this is a SCM generated alarm)
uas7616DiagRxErrAlm OBJECT IDENTIFIER      			::= { uas7616AlarmData 2 }

-- power up alarm
uas7616PowerUpAlm OBJECT IDENTIFIER        			::= { uas7616AlarmData 3 }

-- LOOP x loss of clock alarm
uas7616LossOfClockAlm OBJECT IDENTIFIER 	  		::= { uas7616AlarmData 4 }

-- LOOP x uas7616 out of sync alarm
uas7616LpOutofSyncAlm OBJECT IDENTIFIER    			::= { uas7616AlarmData 5 }

-- Loop x Sealing Current Non-Continuity
uas7616LpSealingCurrentNoContinuityAlm OBJECT IDENTIFIER   	::= { uas7616AlarmData 6 }

-- Loop x Unavailable Second alarm
uas7616LpUnavailableSecondAlm OBJECT IDENTIFIER     		::= { uas7616AlarmData 7 }

-- Loop x Severely Errored Second alarm
uas7616LpSeverelyErroredSecondAlm OBJECT IDENTIFIER		::= { uas7616AlarmData 8 }

-- Loop x Errored Second alarm
uas7616LpErroredSecondAlm OBJECT IDENTIFIER			::= { uas7616AlarmData 9 }
	




-- ALARM                             		Maskable  	Valid interfaces   window/threshold
-- =================================================================================================
-- uas7616NoResponseAlm         		 no         	unit           		 no
-- uas7616DiagRxErrAlm                   	 no		unit           		 no
-- uas7616PowerUpAlm                      	 no		unit	    		 no
-- uas7616LossOfClockAlm			 yes	    	loop 1,2,3            	 no
-- uas7616LpOutofSyncAlm              	 	 yes        	loop 1,2,3     		 no
-- uas7616LpSealingCurrentNoContinuityAlm 	 yes     	loop 1,2,3		 no
-- uas7616LpUnavailableSecondAlm	  	 yes       	loop 1,2,3     		 yes
-- uas7616LpSeverelyErroredSecondAlm      	 yes       	loop 1,2,3 		 yes
-- uas7616LpErroredSecondAlm             	 yes		loop 1,2,3 		 yes

--********************************************************************************
--	UAS 7616  - ALARM WINDOW AND THRESHOLDS
--********************************************************************************
uas7616AlarmConfigTable OBJECT-TYPE
-- This table uses SCinstance defined as follows:
--     7616
--      -----
--      SLDi
--      L=1
--      D=0
--      i=1 - 3

     SYNTAX SEQUENCE OF Uas7616AlarmConfigEntry
     ACCESS not-accessible
     STATUS mandatory
     DESCRIPTION
	 "The uas7616AlarmConfigTable contains entries that configure alarm
	 reporting.  The structure of the table is such that alarm
	 configuration is supported on a unit and interface basis, and
	 then on an alarm type basis within the interface.  For
	 simplicity sake alarms, be they unit or interface
	 related, are represented in one table."
     ::= { uas7616Alarm 2 }

uas7616AlarmConfigEntry OBJECT-TYPE
     SYNTAX Uas7616AlarmConfigEntry
     ACCESS not-accessible
     STATUS mandatory
     DESCRIPTION
	 "An entry in the GDC Alarm Configuration table."
     INDEX { uas7616AlarmConfigIndex, uas7616AlarmConfigIdentifier }
     ::= { uas7616AlarmConfigTable 1 }

Uas7616AlarmConfigEntry ::=
     SEQUENCE {
	 uas7616AlarmConfigIndex	SCinstance,
	 uas7616AlarmConfigIdentifier   OBJECT IDENTIFIER,
	 uas7616AlarmCountWindow 	INTEGER,
	 uas7616AlarmCountThreshold     INTEGER
     }

uas7616AlarmConfigIndex OBJECT-TYPE
     SYNTAX SCinstance
     ACCESS read-only
     STATUS mandatory
     DESCRIPTION
	 "The index value which uniquely identifies the interface to
	 which this entry is applicable."
     ::= { uas7616AlarmConfigEntry 1 }

uas7616AlarmConfigIdentifier OBJECT-TYPE
     SYNTAX OBJECT IDENTIFIER
     ACCESS read-only
     STATUS mandatory
     DESCRIPTION
	 "The unique alarm identifier assigned to this alarm type.
	 The format of this identifier is an OBJECT IDENTIFIER that has
	 the following format: {iso(1) org(3) dod(6) internet(1)
	 private(4) enterprises(1) gdc(498) xxx(x) alarm(z) yyy(y)
	 where xxx(x) is the administratively assigned family object
	 identifier (z) is the object identifier for alarms in the family
	 defined MIB and yyy(y) is the administratively assigned alarm
	 type identifier for this alarm."

     ::= { uas7616AlarmConfigEntry 2 }

uas7616AlarmCountWindow OBJECT-TYPE
     SYNTAX INTEGER{
			disabled(1),
			last1sec(2),
			last10secs(3),
			last30secs(4),
			last1min(5),
			last15min(6),
			last1hr(7),
			last24hrs(8),
			infinite(9)
		}
	ACCESS  read-write
	STATUS  mandatory
	DESCRIPTION
		"This variable sets/reads the UAS, SES or ES alarm window.

		This window is used with the alarm threshold to determine
		how long the alarm should be active before reporting."

    ::= { uas7616AlarmConfigEntry 3 }

uas7616AlarmCountThreshold OBJECT-TYPE
    SYNTAX INTEGER {
			occurrence1x(1),
			occurrence3x(2),
			occurrence10x(3),
			occurrence100x(4),
			occurrence1Kx(5),
			occurrence10Kx(6)
		}
	ACCESS  read-write
	STATUS  mandatory
	DESCRIPTION
		"This function sets/reads the UAS, SES or ES alarm threshold criteria.

		This threshold is used along with the the alarm window to
		determine the number of instances in a given time frame for
		an alarm to occur before the alarm is considered active."

    ::= { uas7616AlarmConfigEntry 4 }

 -- ********************************************************************
 -- 		GDC UAS 7616 - Current 15 Minute Performance Table
 -- ********************************************************************
-- This table uses SCinstance defined as follows:
--     7616
--      -----
--      SLDi
--      L=1
--      D=0
--      i=1 - 3


uas7616Current15MinTable    OBJECT-TYPE
	 SYNTAX  SEQUENCE OF Uas7616Current15MinEntry
	 ACCESS  not-accessible
	 STATUS  mandatory
	 DESCRIPTION
		 "The 7616 15 Min Current table."
	 ::= { uas7616 8 }


uas7616Current15MinEntry    OBJECT-TYPE
	 SYNTAX  Uas7616Current15MinEntry
	 ACCESS  not-accessible
	 STATUS  mandatory
	 DESCRIPTION
		 "An entry in the 7616 Current table."
	 INDEX   { uas7616Current15MinIndex }
	 ::= { uas7616Current15MinTable 1 }

Uas7616Current15MinEntry ::=
	 SEQUENCE {
		  uas7616Current15MinIndex	SCinstance,
		  uas7616Current15MinStat	OCTET STRING
	  }

uas7616Current15MinIndex    OBJECT-TYPE
	 SYNTAX  SCinstance
	 ACCESS  read-only
	 STATUS  mandatory
	 DESCRIPTION
	 "The index value which uniquely identifies the interface to
	 which this entry is applicable.  This has the form of a
	 SCinstance which defines the slot, line, drop, and interface."
	    ::= { uas7616Current15MinEntry 1 }

uas7616Current15MinStat    OBJECT-TYPE
	SYNTAX OCTET STRING (SIZE(10))
	ACCESS read-only
	STATUS mandatory
	DESCRIPTION
		"Returns a bitwise snapshot of the interval statistics.
		 Octet 1 bit 7 - not used
			 bit 6 - future use
			 bit 5 - future use
			 bit 4 - future use
			 bit 3 - future use
			 bit 2 - future use
			 bit 1 - 2^1
			 bit 0 - 2^0  Loop ID  

		 Octet 2 bit 7 - not used
			 bit 6 - future use
			 bit 5 - future use
			 bit 4 - future use
			 bit 3 - future use
			 bit 2 - 2^9   
			 bit 1 - 2^8
			 bit 0 - 2^7
		 Octet 3 bit 7 - not used
			 bit 6 - 2^6
			 bit 5 - 2^5 
			 bit 4 - 2^4 
			 bit 3 - 2^3 
			 bit 2 - 2^2 
			 bit 1 - 2^1
			 bit 0 - 2^0  Errored Seconds



		 Octet 4 bit 7 - not used
			 bit 6 - future use
			 bit 5 - future use
			 bit 4 - future use
			 bit 3 - future use
			 bit 2 - 2^9   
			 bit 1 - 2^8
			 bit 0 - 2^7
		 Octet 5 bit 7 - not used
			 bit 6 - 2^6
			 bit 5 - 2^5 
			 bit 4 - 2^4 
			 bit 3 - 2^3 
			 bit 2 - 2^2 
			 bit 1 - 2^1
			 bit 0 - 2^0  Severely Errored Seconds




		 Octet 6 bit 7 - not used
			 bit 6 - future use
			 bit 5 - future use
			 bit 4 - future use
			 bit 3 - future use
			 bit 2 - 2^9   
			 bit 1 - 2^8
			 bit 0 - 2^7
		 Octet 7 bit 7 - not used
			 bit 6 - 2^6
			 bit 5 - 2^5 
			 bit 4 - 2^4 
			 bit 3 - 2^3 
			 bit 2 - 2^2 
			 bit 1 - 2^1
			 bit 0 - 2^0   Unavailable Seconds


		 Octet 8 bit 7 - not used
			 bit 6 - future use
			 bit 5 - future use 
			 bit 4 - future use 
			 bit 3 - future use 
			 bit 2 - 2^16
			 bit 1 - 2^15
			 bit 0 - 2^14  
		 Octet 9 bit 7 - not used
			 bit 6 - 2^13
			 bit 5 - 2^12
			 bit 4 - 2^11
			 bit 3 - 2^10
			 bit 2 - 2^9 
			 bit 1 - 2^8
			 bit 0 - 2^7   
		Octet 10 bit 7 - not used
			 bit 6 - 2^6
			 bit 5 - 2^5 
			 bit 4 - 2^4 
			 bit 3 - 2^3 
			 bit 2 - 2^2 
			 bit 1 - 2^1
			 bit 0 - 2^0   FEBE (Far End Block Error Count)
				       (not available on network element type 30)	


"
	::= {uas7616Current15MinEntry 2 }

 -- ********************************************************************
 -- 		GDC UAS 7616 - Interval Performance Table
 -- ********************************************************************
-- This table uses SCinstance defined as follows:
--     7616
--      -----
--      SLDi
--      L=1
--      D=0
--      i=1 - 3


uas7616IntervalTable   OBJECT-TYPE
	 SYNTAX  SEQUENCE OF Uas7616IntervalEntry
	 ACCESS  not-accessible
	 STATUS  mandatory
	 DESCRIPTION
		 "The 7616 Interval table."

	 ::= { uas7616 9 }


uas7616IntervalEntry   OBJECT-TYPE
	 SYNTAX  Uas7616IntervalEntry
	 ACCESS  not-accessible
	 STATUS  mandatory
	 DESCRIPTION
		 "An entry in the Interval table."
	 INDEX   { uas7616IntervalIndex, uas7616IntervalNumber }
	 ::= { uas7616IntervalTable 1 }

Uas7616IntervalEntry ::=
	 SEQUENCE {
		  uas7616IntervalIndex	SCinstance,
		  uas7616IntervalNumber	INTEGER,
		  uas7616IntervalStat	OCTET STRING
	  }

uas7616IntervalIndex   OBJECT-TYPE
	 SYNTAX  SCinstance
	 ACCESS  read-only
	 STATUS  mandatory
	 DESCRIPTION
	 "The index value which uniquely identifies the interface to
	 which this entry is applicable.  This has the form of a
	 SCinstance which defines the slot, line, drop, and interface."
	 ::= { uas7616IntervalEntry 1 }

uas7616IntervalNumber   OBJECT-TYPE
	 SYNTAX INTEGER (1..16)
	 ACCESS read-only
	 STATUS mandatory
	 DESCRIPTION
		 "The number of Errored Seconds, Unavailable Seconds & Severely Errored
                  Seconds encountered in one of the previous 16, individual 15 minute, intervals."
	 ::= {uas7616IntervalEntry 2 }

uas7616IntervalStat   OBJECT-TYPE
	 SYNTAX OCTET STRING (SIZE(11))
	 ACCESS read-only
	 STATUS mandatory
	 DESCRIPTION
		 "Returns a bitwise map of the interface in one of the previous 16, individual 15 minute,
		 intervals.


		 Octet 1 bit 7 - not used
			 bit 6 - future use
			 bit 5 - future use
			 bit 4 - future use
			 bit 3 - future use
			 bit 2 - future use
			 bit 1 - 2^1
			 bit 0 - 2^0  Loop ID  

		 Octet 2 bit 7 - not used
			 bit 6 - future use
			 bit 5 - future use
			 bit 4 - future use
			 bit 3 - 2^3        
			 bit 2 - 2^2       
			 bit 1 - 2^1
			 bit 0 - 2^0  Interval 

		 Octet 3 bit 7 - not used
			 bit 6 - future use
			 bit 5 - future use
			 bit 4 - future use
			 bit 3 - future use
			 bit 2 - 2^9   
			 bit 1 - 2^8
			 bit 0 - 2^7
		 Octet 4 bit 7 - not used
			 bit 6 - 2^6
			 bit 5 - 2^5 
			 bit 4 - 2^4 
			 bit 3 - 2^3 
			 bit 2 - 2^2 
			 bit 1 - 2^1
			 bit 0 - 2^0  Errored Seconds



		 Octet 5 bit 7 - not used
			 bit 6 - future use
			 bit 5 - future use
			 bit 4 - future use
			 bit 3 - future use
			 bit 2 - 2^9   
			 bit 1 - 2^8
			 bit 0 - 2^7
		 Octet 6 bit 7 - not used
			 bit 6 - 2^6
			 bit 5 - 2^5 
			 bit 4 - 2^4 
			 bit 3 - 2^3 
			 bit 2 - 2^2 
			 bit 1 - 2^1
			 bit 0 - 2^0  Severely Errored Seconds




		 Octet 7 bit 7 - not used
			 bit 6 - future use
			 bit 5 - future use
			 bit 4 - future use
			 bit 3 - future use
			 bit 2 - 2^9   
			 bit 1 - 2^8
			 bit 0 - 2^7
		 Octet 8 bit 7 - not used
			 bit 6 - 2^6
			 bit 5 - 2^5 
			 bit 4 - 2^4 
			 bit 3 - 2^3 
			 bit 2 - 2^2 
			 bit 1 - 2^1
			 bit 0 - 2^0   Unavailable Seconds

		 Octet 9 bit 7 - not used
			 bit 6 - future use
			 bit 5 - future use 
			 bit 4 - future use 
			 bit 3 - future use 
			 bit 2 - 2^16
			 bit 1 - 2^15
			 bit 0 - 2^14  
		Octet 10 bit 7 - not used
			 bit 6 - 2^13
			 bit 5 - 2^12
			 bit 4 - 2^11
			 bit 3 - 2^10
			 bit 2 - 2^9 
			 bit 1 - 2^8
			 bit 0 - 2^7   
		Octet 11 bit 7 - not used
			 bit 6 - 2^6
			 bit 5 - 2^5 
			 bit 4 - 2^4 
			 bit 3 - 2^3 
			 bit 2 - 2^2 
			 bit 1 - 2^1
			 bit 0 - 2^0   	FEBE (Far End Block Error Count)
					(not available on network element type 30)

"

	 ::= {uas7616IntervalEntry 3 }

 -- ********************************************************************
 -- 		GDC UAS 7616 - Current 24 Hour Performance Table
 -- ********************************************************************
-- This table uses SCinstance defined as follows:
--     7616
--      -----
--      SLDi
--      L=1
--      D=0
--      i=1 - 3


uas7616Current24HrTable              OBJECT-TYPE
	 SYNTAX  SEQUENCE OF Uas7616Current24HrEntry
	 ACCESS  not-accessible
	 STATUS  mandatory
	 DESCRIPTION
		 "The Current24Hr table.  4 hour interval."

	 ::= { uas7616 10 }

 uas7616Current24HrEntry              OBJECT-TYPE
	 SYNTAX  Uas7616Current24HrEntry
	 ACCESS  not-accessible
	 STATUS  mandatory
	 DESCRIPTION
		 "An entry in the Current24Hr table."
	 INDEX   { uas7616Current24HrIndex }
	 ::= { uas7616Current24HrTable 1 }

Uas7616Current24HrEntry ::=
	 SEQUENCE {
		  uas7616Current24HrIndex	SCinstance,
		  uas7616Current24HrStat	OCTET STRING
	  }

uas7616Current24HrIndex              OBJECT-TYPE
	 SYNTAX  SCinstance
	 ACCESS  read-only
	 STATUS  mandatory
	 DESCRIPTION
	 "The index value which uniquely identifies the interface to
	 which this entry is applicable.  This has the form of a
	 SCinstance which defines the slot, line, drop, and interface."
	 ::= { uas7616Current24HrEntry 1 }

uas7616Current24HrStat              OBJECT-TYPE
	 SYNTAX OCTET STRING (SIZE (14))
	 ACCESS read-only
	 STATUS mandatory
	 DESCRIPTION

		"Returns a bitwise snapshot of the interval statistics.
		 Octet 1 bit 7 - not used
			 bit 6 - future use
			 bit 5 - future use
			 bit 4 - future use
			 bit 3 - future use
			 bit 2 - future use
			 bit 1 - 2^1
			 bit 0 - 2^0  Loop ID  

		 Octet 2 bit 7 - not used
			 bit 6 - future use
			 bit 5 - future use
			 bit 4 - future use
			 bit 3 - future use
			 bit 2 - >65535
			 bit 1 - 2^15
			 bit 0 - 2^14
		 Octet 3 bit 7 - not used
			 bit 6 - 2^13
			 bit 5 - 2^12
			 bit 4 - 2^11
			 bit 3 - 2^10
			 bit 2 - 2^9
			 bit 1 - 2^8
			 bit 0 - 2^7
		 Octet 4 bit 7 - not used
			 bit 6 - 2^6 
			 bit 5 - 2^5 
			 bit 4 - 2^4 
			 bit 3 - 2^3 
			 bit 2 - 2^2 
			 bit 1 - 2^1 
			 bit 0 - 2^0    Errored  Seconds


		 Octet 5 bit 7 - not used
			 bit 6 - future use
			 bit 5 - future use
			 bit 4 - future use
			 bit 3 - future use
			 bit 2 - >65535
			 bit 1 - 2^15
			 bit 0 - 2^14
		 Octet 6 bit 7 - not used
			 bit 6 - 2^13
			 bit 5 - 2^12
			 bit 4 - 2^11
			 bit 3 - 2^10
			 bit 2 - 2^9
			 bit 1 - 2^8
			 bit 0 - 2^7
		 Octet 7 bit 7 - not used
			 bit 6 - 2^6 
			 bit 5 - 2^5 
			 bit 4 - 2^4 
			 bit 3 - 2^3 
			 bit 2 - 2^2 
			 bit 1 - 2^1 
			 bit 0 - 2^0    Severely Errored Seconds


		 Octet 8 bit 7 - not used
			 bit 6 - future use
			 bit 5 - future use
			 bit 4 - future use
			 bit 3 - future use
			 bit 2 - >65535
			 bit 1 - 2^15
			 bit 0 - 2^14
		 Octet 9 bit 7 - not used
			 bit 6 - 2^13
			 bit 5 - 2^12
			 bit 4 - 2^11
			 bit 3 - 2^10
			 bit 2 - 2^9
			 bit 1 - 2^8
			 bit 0 - 2^7
        	Octet 10 bit 7 - not used
			 bit 6 - 2^6 
			 bit 5 - 2^5 
			 bit 4 - 2^4 
			 bit 3 - 2^3 
			 bit 2 - 2^2 
			 bit 1 - 2^1 
			 bit 0 - 2^0    Unavailable Seconds

		Octet 11 bit 7 - not used
			 bit 6 - future use
			 bit 5 - future use
			 bit 4 - future use
			 bit 3 - future use
			 bit 2 - 2^23
			 bit 1 - 2^22
			 bit 0 - 2^21  
		Octet 12 bit 7 - not used
			 bit 6 - 2^20
			 bit 5 - 2^19
			 bit 4 - 2^18
			 bit 3 - 2^17
			 bit 2 - 2^16
			 bit 1 - 2^15
			 bit 0 - 2^14   
		Octet 13 bit 7 - not used
			 bit 6 - 2^13
			 bit 5 - 2^12
			 bit 4 - 2^11
			 bit 3 - 2^10
			 bit 2 - 2^9 
			 bit 1 - 2^8
			 bit 0 - 2^7   
		Octet 14 bit 7 - not used
			 bit 6 - 2^6
			 bit 5 - 2^5 
			 bit 4 - 2^4 
			 bit 3 - 2^3 
			 bit 2 - 2^2 
			 bit 1 - 2^1
			 bit 0 - 2^0   	FEBE (Far End Block Error Count)
					(not available on network element type 30)

"
	 ::= {uas7616Current24HrEntry 2 }

 -- ********************************************************************
 -- 		GDC UAS 7616 - Recent 24 Hour Performance Table
 -- ********************************************************************
-- This table uses SCinstance defined as follows:
--      7616
--      -----
--      SLDi
--      L=1
--      D=0
--      i=1 - 3



uas7616Recent24HrTable              OBJECT-TYPE
	 SYNTAX  SEQUENCE OF Uas7616Recent24HrEntry
	 ACCESS  not-accessible
	 STATUS  mandatory
	 DESCRIPTION
		 "The Recent24Hr table.  4 hour interval."

	 ::= { uas7616 11 }

uas7616Recent24HrEntry              OBJECT-TYPE
	 SYNTAX  Uas7616Recent24HrEntry
	 ACCESS  not-accessible
	 STATUS  mandatory
	 DESCRIPTION
		 "An entry in the Recent24Hr table."
	 INDEX   { uas7616Recent24HrIndex }
	 ::= { uas7616Recent24HrTable 1 }

Uas7616Recent24HrEntry ::=
	 SEQUENCE {
		  uas7616Recent24HrIndex	SCinstance,
		  uas7616Recent24HrStat		OCTET STRING
	  }

uas7616Recent24HrIndex              OBJECT-TYPE
	 SYNTAX  SCinstance
	 ACCESS  read-only
	 STATUS  mandatory
	 DESCRIPTION
	 "The index value which uniquely identifies the interface to
	 which this entry is applicable.  This has the form of a
	 SCinstance which defines the slot, line, drop, and interface."

	 ::= { uas7616Recent24HrEntry 1 }

uas7616Recent24HrStat              OBJECT-TYPE
	 SYNTAX OCTET STRING (SIZE (14))
	 ACCESS read-only
	 STATUS mandatory
	 DESCRIPTION
		"Returns a bitwise snapshot of the interval statistics.
		 Octet 1 bit 7 - not used
			 bit 6 - future use
			 bit 5 - future use
			 bit 4 - future use
			 bit 3 - future use
			 bit 2 - future use
			 bit 1 - 2^1
			 bit 0 - 2^0  Loop ID  

		 Octet 2 bit 7 - not used
			 bit 6 - future use
			 bit 5 - future use
			 bit 4 - future use
			 bit 3 - future use
			 bit 2 - >65535
			 bit 1 - 2^15
			 bit 0 - 2^14
		 Octet 3 bit 7 - not used
			 bit 6 - 2^13
			 bit 5 - 2^12
			 bit 4 - 2^11
			 bit 3 - 2^10
			 bit 2 - 2^9
			 bit 1 - 2^8
			 bit 0 - 2^7
		 Octet 4 bit 7 - not used
			 bit 6 - 2^6 
			 bit 5 - 2^5 
			 bit 4 - 2^4 
			 bit 3 - 2^3 
			 bit 2 - 2^2 
			 bit 1 - 2^1 
			 bit 0 - 2^0    Errored  Seconds


		 Octet 5 bit 7 - not used
			 bit 6 - future use
			 bit 5 - future use
			 bit 4 - future use
			 bit 3 - future use
			 bit 2 - >65535
			 bit 1 - 2^15
			 bit 0 - 2^14
		 Octet 6 bit 7 - not used
			 bit 6 - 2^13
			 bit 5 - 2^12
			 bit 4 - 2^11
			 bit 3 - 2^10
			 bit 2 - 2^9
			 bit 1 - 2^8
			 bit 0 - 2^7
		 Octet 7 bit 7 - not used
			 bit 6 - 2^6 
			 bit 5 - 2^5 
			 bit 4 - 2^4 
			 bit 3 - 2^3 
			 bit 2 - 2^2 
			 bit 1 - 2^1 
			 bit 0 - 2^0    Severely Errored Seconds


		 Octet 8 bit 7 - not used
			 bit 6 - future use
			 bit 5 - future use
			 bit 4 - future use
			 bit 3 - future use
			 bit 2 - >65535
			 bit 1 - 2^15
			 bit 0 - 2^14
		 Octet 9 bit 7 - not used
			 bit 6 - 2^13
			 bit 5 - 2^12
			 bit 4 - 2^11
			 bit 3 - 2^10
			 bit 2 - 2^9
			 bit 1 - 2^8
			 bit 0 - 2^7
        	Octet 10 bit 7 - not used
			 bit 6 - 2^6 
			 bit 5 - 2^5 
			 bit 4 - 2^4 
			 bit 3 - 2^3 
			 bit 2 - 2^2 
			 bit 1 - 2^1 
			 bit 0 - 2^0    Unavailable Seconds

		Octet 11 bit 7 - not used
			 bit 6 - future use
			 bit 5 - future use
			 bit 4 - future use
			 bit 3 - future use
			 bit 2 - 2^23
			 bit 1 - 2^22
			 bit 0 - 2^21  
		Octet 12 bit 7 - not used
			 bit 6 - 2^20
			 bit 5 - 2^19
			 bit 4 - 2^18
			 bit 3 - 2^17
			 bit 2 - 2^16
			 bit 1 - 2^15
			 bit 0 - 2^14   
		Octet 13 bit 7 - not used
			 bit 6 - 2^13
			 bit 5 - 2^12
			 bit 4 - 2^11
			 bit 3 - 2^10
			 bit 2 - 2^9 
			 bit 1 - 2^8
			 bit 0 - 2^7   
		Octet 14 bit 7 - not used
			 bit 6 - 2^6
			 bit 5 - 2^5 
			 bit 4 - 2^4 
			 bit 3 - 2^3 
			 bit 2 - 2^2 
			 bit 1 - 2^1
			 bit 0 - 2^0    FEBE (Far End Block Error Count)
					(not available on network element type 30)

"
	 ::= {uas7616Recent24HrEntry 2 }


 -- ********************************************************************
 -- 		GDC UAS 7616 - Unavailable Time Registers
 -- ********************************************************************
-- This table uses SCinstance defined as follows:
--     7616
--      -----
--      SLDi
--      L=1
--      D=0
--      i=1 - 3


uas7616UnavailableTimeRegTable     OBJECT-TYPE
	 SYNTAX  SEQUENCE OF Uas7616UnavailableTimeRegEntry
	 ACCESS  not-accessible
	 STATUS  mandatory
	 DESCRIPTION
		 "The 7616 Unavailable Time Register table."

	 ::= {uas7616 12 }


uas7616UnavailableTimeRegEntry     OBJECT-TYPE
	 SYNTAX Uas7616UnavailableTimeRegEntry
	 ACCESS  not-accessible
	 STATUS  mandatory
	 DESCRIPTION
		 "An entry in the Unavailable Time Register table."
	 INDEX   {uas7616UnavailableTimeRegIndex,uas7616UnavailableTimeRegNumber }
	 ::= {uas7616UnavailableTimeRegTable 1 }

Uas7616UnavailableTimeRegEntry ::=
	 SEQUENCE {
		 uas7616UnavailableTimeRegIndex		SCinstance,
		 uas7616UnavailableTimeRegNumber	INTEGER,
		 uas7616UnavailableTimeRegStart		INTEGER,
		 uas7616UnavailableTimeRegStop		INTEGER
	  }

uas7616UnavailableTimeRegIndex     OBJECT-TYPE
	 SYNTAX  SCinstance
	 ACCESS  read-only
	 STATUS  mandatory
	 DESCRIPTION
	 "The index value which uniquely identifies the interface to
	 which this entry is applicable.  This has the form of a
	 SCinstance which defines the slot, line, drop, and interface."
	 ::= {uas7616UnavailableTimeRegEntry 1 }

uas7616UnavailableTimeRegNumber    OBJECT-TYPE
	 SYNTAX  INTEGER (1..6)
	 ACCESS  read-only
	 STATUS  mandatory
	 DESCRIPTION
		 "A number between 1 and 6, where the number is the number of the
		 Unavailable Time Register."
	 ::= {uas7616UnavailableTimeRegEntry 2 }

uas7616UnavailableTimeRegStart          OBJECT-TYPE
	SYNTAX  INTEGER (1..2147483647)
	ACCESS  read-only
	STATUS  mandatory
	DESCRIPTION
		"Start time of one of the Unavailable Time Registers."
	::= {uas7616UnavailableTimeRegEntry 3}

uas7616UnavailableTimeRegStop          OBJECT-TYPE
	SYNTAX  INTEGER (1..2147483647)
	ACCESS  read-only
	STATUS  mandatory
	DESCRIPTION
		"Stop time of one of the Unavailable Time Registers."
	::= {uas7616UnavailableTimeRegEntry 4}

--*****************************************************************************
--          GDC UAS 7616 - INTERVAL STATISTICS MAINTENANCE TABLE
--*****************************************************************************
-- This table uses SCinstance defined as follows:
--     7616
--      -----
--      SLDi
--      L=1
--      D=0
--      i=1 - 3


uas7616IntervalMaintenanceTable OBJECT-TYPE
     	SYNTAX SEQUENCE OF Uas7616IntervalMaintenanceEntry
     	ACCESS not-accessible
     	STATUS mandatory
    	DESCRIPTION
     		"The 7616 Loop Interval  Maintenance table. "
         ::= { uas7616 13 }

uas7616IntervalMaintenanceEntry OBJECT-TYPE
 	SYNTAX Uas7616IntervalMaintenanceEntry
     	ACCESS not-accessible
     	STATUS mandatory
     	DESCRIPTION
     		"The 7616  Interval Maintenance table entry. "
     	INDEX { uas7616IntervalMaintenanceIndex }
     	::= { uas7616IntervalMaintenanceTable 1 }

Uas7616IntervalMaintenanceEntry ::=
     	SEQUENCE {
     	    	 uas7616IntervalMaintenanceIndex 	SCinstance,
         	 uas7616NumberofValidIntervals		INTEGER
		 }

uas7616IntervalMaintenanceIndex OBJECT-TYPE
     	SYNTAX SCinstance
     	ACCESS read-only
     	STATUS mandatory
     	DESCRIPTION
     		"The index value which uniquely identifies the interface to
     		which this entry is applicable.  This has the form of a
     		SCinstance which defines the slot, line, drop, and interface,
     		which in this case is a Loop interface."
     	::= { uas7616IntervalMaintenanceEntry 1 }

uas7616NumberofValidIntervals OBJECT-TYPE
     	SYNTAX INTEGER (1..16)
     	ACCESS read-only
     	STATUS mandatory
        DESCRIPTION " This variable is used to read the number of intervals collected.
		        Each interval is an increment of 15 minutes."
     	::= {  uas7616IntervalMaintenanceEntry 2 }



 -- ********************************************************************
 -- GDC UAS 7616 Local Alarm Definitions
 -- ********************************************************************
 --
 -- Local Alarms are alarms that optionally activate the backplane
 -- Major or Minor buses. These alarms changes are never reported in an
 -- unsolicited message to the proxy agent hence, the reason for the alarm
 -- card. These alarms are different from the previously defined alarms
 -- in that the mask state has three possible values.
 --
 --
 -- ********************************************************************
 -- GDC Local UAS 7616 Alarm Configuration
 -- ********************************************************************
-- This table uses SCinstance defined as follows:
--     7616
--      -----
--      SLDi
--      L=1
--      D=0
--      i=1 - 3


uas7616LocalAlarmConfigTable OBJECT-TYPE
     SYNTAX SEQUENCE OF Uas7616LocalAlarmConfigEntry
     ACCESS not-accessible
     STATUS mandatory
     DESCRIPTION
	 "The 7616LocalAlarmConfigTable contains entries that configure
	 alarm reporting."
     ::= { uas7616 14 }

uas7616LocalAlarmConfigEntry OBJECT-TYPE
     SYNTAX Uas7616LocalAlarmConfigEntry
     ACCESS not-accessible
     STATUS mandatory
     DESCRIPTION
	 "An entry in the GDC Local Alarm Configuration table."
     INDEX { uas7616LocalAlarmConfigIndex }
     ::= { uas7616LocalAlarmConfigTable 1 }

Uas7616LocalAlarmConfigEntry ::=
     SEQUENCE {
	 uas7616LocalAlarmConfigIndex	 	SCinstance,
	 uas7616LocalLossOfClock		INTEGER,
	 uas7616LocalUAS			INTEGER,
	 uas7616LocalSES			INTEGER,
	 uas7616LocalES				INTEGER,
	 uas7616LocalOutOfSync			INTEGER,
	 uas7616LocalNoSealingCurrent		INTEGER,
	 uas7616LPMajor     			INTEGER,
	 uas7616LPMinor   			INTEGER
     }

uas7616LocalAlarmConfigIndex OBJECT-TYPE
     SYNTAX SCinstance
     ACCESS read-only
     STATUS mandatory
     DESCRIPTION
	 "The index value which uniquely identifies the interface to
	 which this entry is applicable."
     ::= { uas7616LocalAlarmConfigEntry 1 }

uas7616LocalLossOfClock       OBJECT-TYPE
	SYNTAX  INTEGER {
			disabled(1),
			enabledMajor(2),
			enabledMinor(3)
			}
	ACCESS  read-write
	STATUS  mandatory
	DESCRIPTION
		"Disables or enables the Loss of Clock alarm on the Major buss or
                 Minor buss."
     ::= { uas7616LocalAlarmConfigEntry 2 }


uas7616LocalUAS       OBJECT-TYPE
	SYNTAX  INTEGER {
			disabled(1),
			enabledMajor(2),
			enabledMinor(3)
			}
	ACCESS  read-write
	STATUS  mandatory
	DESCRIPTION
		"Disables or enables the UAS alarm on the Major buss or Minor
		buss."
     ::= { uas7616LocalAlarmConfigEntry 3 }



uas7616LocalSES       OBJECT-TYPE
	SYNTAX  INTEGER {
			disabled(1),
			enabledMajor(2),
			enabledMinor(3)
			}
	ACCESS  read-write
	STATUS  mandatory
	DESCRIPTION
		"Disables or enables the SES alarm on the Major buss or Minor
		buss."
     ::= { uas7616LocalAlarmConfigEntry 4 }

uas7616LocalES       OBJECT-TYPE
	SYNTAX  INTEGER {
			disabled(1),
			enabledMajor(2),
			enabledMinor(3)
			}
	ACCESS  read-write
	STATUS  mandatory
	DESCRIPTION
		"Disables or enables the ES alarm on the Major buss or Minor
		buss."
     ::= { uas7616LocalAlarmConfigEntry 5 }

uas7616LocalOutOfSync       OBJECT-TYPE
	SYNTAX  INTEGER {
			disabled(1),
			enabledMajor(2),
			enabledMinor(3)
			}
	ACCESS  read-write
	STATUS  mandatory
	DESCRIPTION
		"Disables or enables the Out of Sync alarm on the Major buss or Minor
		buss."
     ::= { uas7616LocalAlarmConfigEntry 6}


uas7616LocalNoSealingCurrent      OBJECT-TYPE
	SYNTAX  INTEGER {
			disabled(1),
			enabledMajor(2),
			enabledMinor(3)
			}
	ACCESS  read-write
	STATUS  mandatory
	DESCRIPTION
		"Disables or enables the No Sealing Current alarm on the Major buss or Minor
		buss."
     ::= { uas7616LocalAlarmConfigEntry 7 }

uas7616LPMajor         OBJECT-TYPE
	SYNTAX  INTEGER {
			disabled(1),
			enabledMajor(2),
			enabledMinor(3)
			}
	ACCESS  read-write
	STATUS  mandatory
	DESCRIPTION
		"Disables or enables the Major alarm on the Major buss or Minor
		buss."
     ::= { uas7616LocalAlarmConfigEntry 8 }

uas7616LPMinor         OBJECT-TYPE
	SYNTAX  INTEGER {
			disabled(1),
			enabledMajor(2),
			enabledMinor(3)
			}
	ACCESS  read-write
	STATUS  mandatory
	DESCRIPTION
		"Disables or enables the Minor alarm on the Minor buss or Minor
		buss."
     ::= { uas7616LocalAlarmConfigEntry 9 }

 -- ********************************************************************
 -- 		GDC UAS 7616 Time Slot Assignment Table
 -- ********************************************************************
-- This table contains the 7616 Time Slot Assignment functions indexed by SLDi.
--
-- This table uses SCinstance defined as follows:
--     7616
--      -----
--      SLDi
--      L=1
--      D=0
--      i=1 - 3
--

uas7616TSAssignTable OBJECT-TYPE
     SYNTAX SEQUENCE OF Uas7616TSAssignEntry
     ACCESS not-accessible
     STATUS mandatory
     DESCRIPTION
	 "The 7616TSAssignTable contains entries that provide a means to
	  assign a highway and time slot of that highway to the channel of a loop."
     ::= { uas7616 15 }

uas7616TSAssignEntry OBJECT-TYPE
     SYNTAX Uas7616TSAssignEntry
     ACCESS not-accessible
     STATUS mandatory
     DESCRIPTION
	 "An entry in the GDC Circuit Identification table."
     INDEX { uas7616TSAssignIndex, uas7616ChannelIndex }
     ::= { uas7616TSAssignTable 1 }

Uas7616TSAssignEntry ::=
     SEQUENCE {
		uas7616TSAssignIndex	SCinstance,
		uas7616ChannelIndex 	INTEGER,
		uas7616Highway		INTEGER,
		uas7616TimeSlot		INTEGER,
		uas7616TSCircuitID      DisplayString
	      }

uas7616TSAssignIndex OBJECT-TYPE
     	SYNTAX SCinstance
     	ACCESS read-only
     	STATUS mandatory
     	DESCRIPTION
		 "The index value which uniquely identifies the interface to
		 which this entry is applicable."
     	::= { uas7616TSAssignEntry 1 }

uas7616ChannelIndex OBJECT-TYPE
	SYNTAX INTEGER {
		channelA(1),
		channelB(2)
		}
	ACCESS read-write
	STATUS mandatory
	DESCRIPTION
		"The index value which uniquely identifies the channel of the
		interface to which this entry is applicable."
	::= {uas7616TSAssignEntry 2}

uas7616Highway	OBJECT-TYPE
	SYNTAX INTEGER{
		notAssigned(1),
		highway1(2),
		highway2(3),
		highway3(4),
		highway4(5)
		}
	ACCESS read-write
	STATUS mandatory
	DESCRIPTION
		"Defines the highway the channel of the loop is assigned to."
	::= {uas7616TSAssignEntry 3}

uas7616TimeSlot	OBJECT-TYPE
	SYNTAX INTEGER(1..64)
	ACCESS read-write
	STATUS mandatory
	DESCRIPTION
		"Defines the time slot of the highway the channel of the loop is
		assigned to. Valid range is 1 to 31. A value of 64 indicates the channel
		is not assigned to a highway."
	::= {uas7616TSAssignEntry 4}

uas7616TSCircuitID       OBJECT-TYPE
	SYNTAX  DisplayString (SIZE(16))
	ACCESS  read-write
	STATUS  mandatory
	DESCRIPTION
		"Name to identify the circuit for the channel of this loop."
        ::= { uas7616TSAssignEntry 5 }




--********************************************************************************
--	UAS 7616 ALARMS - INDIVIDUALLY IDENTIFIED FOR THE CONTROLLER
--********************************************************************************
--
--
--
--  support for "2B1Q Style" alarm reporting: 
--
--	Product codes 0x50 (type 44) and 0x51 (type 45)
--
--
--
--********************************************************************************


uas7616mAlarm OBJECT IDENTIFIER				        ::= { bql2 14 }

uas7616mAlarmData OBJECT IDENTIFIER			        ::= { uas7616mAlarm 1 }

-- no response alarm (this is a SCM generated alarm)
uas7616mNoResponseAlm OBJECT IDENTIFIER     			::= { uas7616mAlarmData 1 }

-- no diagnostic receive error alarm (this is a SCM generated alarm)
uas7616mDiagRxErrAlm OBJECT IDENTIFIER      			::= { uas7616mAlarmData 2 }

-- power up alarm
uas7616mPowerUpAlm OBJECT IDENTIFIER        			::= { uas7616mAlarmData 3 }

-- LOOP x loss of clock alarm
uas7616mLossOfClockAlm OBJECT IDENTIFIER 	  		::= { uas7616mAlarmData 4 }

-- LOOP x UAS7616m out of sync alarm
uas7616mLpOutofSyncAlm OBJECT IDENTIFIER    			::= { uas7616mAlarmData 5 }

-- Loop x Sealing Current Non-Continuity
uas7616mLpSealingCurrentNoContinuityAlm OBJECT IDENTIFIER   	::= { uas7616mAlarmData 6 }

-- Loop x Unavailable Second alarm
uas7616mLpUnavailableSecondAlm OBJECT IDENTIFIER     		::= { uas7616mAlarmData 7 }

-- Loop x Errored Second alarm
uas7616mLpErroredSecondAlm OBJECT IDENTIFIER			::= { uas7616mAlarmData 8 }
	
-- Loop x Major alarm                
uas7616mLPMajorAlm OBJECT IDENTIFIER				::= { uas7616mAlarmData 9 }

-- Loop x Minor alarm           
uas7616mLPMinorAlm OBJECT IDENTIFIER				::= { uas7616mAlarmData 10}




-- ALARM                             		Maskable  	Valid interfaces   window/threshold
-- =================================================================================================
-- uas7616mNoResponseAlm         		 no         	unit           		 no
-- uas7616mDiagRxErrAlm                   	 no		unit           		 no
-- uas7616mPowerUpAlm                      	 no		unit	    		 no
-- uas7616mLossOfClockAlm			 yes	    	loop 1,2,3            	 no
-- uas7616mLpOutofSyncAlm              	 	 yes        	loop 1,2,3     		 no
-- uas7616mLpSealingCurrentNoContinuityAlm 	 yes     	loop 1,2,3		 no
-- uas7616mLpUnavailableSecondAlm	  	 yes       	loop 1,2,3     		 no
-- uas7616mLpErroredSecondAlm             	 yes		loop 1,2,3 		 no
-- uas7616mLPMajorAlm				 yes            loop 1,2,3 		 yes
-- uas7616mLPMinorAlm				 yes            loop 1,2,3 		 yes





--********************************************************************************
--	UAS 7616m  - ALARM WINDOW AND THRESHOLDS
--********************************************************************************
uas7616mAlarmConfigTable OBJECT-TYPE
-- This table uses SCinstance defined as follows:
--     7616m
--      -----
--      SLDi
--      L=1
--      D=0
--      i=1 - 3

     SYNTAX SEQUENCE OF Uas7616mAlarmConfigEntry
     ACCESS not-accessible
     STATUS mandatory
     DESCRIPTION
	 "The uas7616mAlarmConfigTable contains entries that configure alarm
	 reporting.  The structure of the table is such that alarm
	 configuration is supported on a unit and interface basis, and
	 then on an alarm type basis within the interface.  For
	 simplicity sake alarms, be they unit or interface
	 related, are represented in one table."
     ::= { uas7616mAlarm 2 }

uas7616mAlarmConfigEntry OBJECT-TYPE
     SYNTAX Uas7616mAlarmConfigEntry
     ACCESS not-accessible
     STATUS mandatory
     DESCRIPTION
	 "An entry in the GDC Alarm Configuration table."
     INDEX { uas7616mAlarmConfigIndex, uas7616mAlarmConfigIdentifier }
     ::= { uas7616mAlarmConfigTable 1 }

Uas7616mAlarmConfigEntry ::=
     SEQUENCE {
	 uas7616mAlarmConfigIndex	SCinstance,
	 uas7616mAlarmConfigIdentifier   OBJECT IDENTIFIER,
	 uas7616mAlarmCountThreshold     INTEGER
     }

uas7616mAlarmConfigIndex OBJECT-TYPE
     SYNTAX SCinstance
     ACCESS read-only
     STATUS mandatory
     DESCRIPTION
	 "The index value which uniquely identifies the interface to
	 which this entry is applicable."
     ::= { uas7616mAlarmConfigEntry 1 }

uas7616mAlarmConfigIdentifier OBJECT-TYPE
     SYNTAX OBJECT IDENTIFIER
     ACCESS read-only
     STATUS mandatory
     DESCRIPTION
	 "The unique alarm identifier assigned to this alarm type.
	 The format of this identifier is an OBJECT IDENTIFIER that has
	 the following format: {iso(1) org(3) dod(6) internet(1)
	 private(4) enterprises(1) gdc(498) xxx(x) alarm(z) yyy(y)
	 where xxx(x) is the administratively assigned family object
	 identifier (z) is the object identifier for alarms in the family
	 defined MIB and yyy(y) is the administratively assigned alarm
	 type identifier for this alarm."

     ::= { uas7616mAlarmConfigEntry 2 }


uas7616mAlarmCountThreshold OBJECT-TYPE
     SYNTAX INTEGER {
			thres10E03(1),
			thres10E04(2),
			thres10E05(3),
			thres10E06(4)
		}
	ACCESS  read-write
	STATUS  mandatory
	DESCRIPTION
		"This function sets/reads the Major or Minor BER alarm threshold criteria."
    ::= { uas7616mAlarmConfigEntry 3 }




END
