XEDIA-CRON-MIB DEFINITIONS ::= BEGIN

IMPORTS 
    MODULE-IDENTITY, OBJECT-TYPE
        FROM SNMPv2-SMI
    DisplayString, RowStatus
        FROM SNMPv2-TC
    MODULE-COMPLIANCE, OBJECT-GROUP
        FROM SNMPv2-CONF
    xediaMibs
        FROM XEDIA-REG
    ;    

xediaCronMIB MODULE-IDENTITY
    LAST-UPDATED "9801122155Z" -- January 12, 1998
    ORGANIZATION "Xedia Corp."
    CONTACT-INFO
        "support@xedia.com"
    DESCRIPTION
        "This module defines objects for management of the 'Cron'
         batch job scheduler mechanism in Xedia devices."
    ::= { xediaMibs 13 }

-- Top-level organization of the MIB

xcronObjects          OBJECT IDENTIFIER ::= { xediaCronMIB 1 }
xcronConformance      OBJECT IDENTIFIER ::= { xediaCronMIB 2 }

xcronGeneral          OBJECT IDENTIFIER ::= { xcronObjects 1 }
xcronObjectTables     OBJECT IDENTIFIER ::= { xcronObjects 2 }

-- ***********************************
-- Cron Top Level Objects
-- ***********************************
xcronAdmin OBJECT-TYPE
    SYNTAX      INTEGER {
                    enabled(1),
                    disabled(2)
                }
    MAX-ACCESS  read-write
    STATUS      current
    DESCRIPTION
        "The administrative status of the 'Cron mechanism' in the router. 
         The value 'enabled(1)' indicates that the batch scheduler will
         try to become active. The value 'disabled(2)' indicates that 
         no attempt will be made to start the Cron batch scheduler.
     
         Changes to this object require a node reset in order to take affect."
    DEFVAL      { disabled }
    ::= { xcronGeneral 1 }

xcronOper OBJECT-TYPE
    SYNTAX      INTEGER {
                    up(1),
                    down(2),
                    stalled(3),
                    unknown(4)
                }
    MAX-ACCESS  read-only
    STATUS      current
    DESCRIPTION
        "The Operational status of the 'Cron mechanism' in the router.
     An 'up' status indicates that the scheduler is activated and
     running normally.  The 'down' status indicates that the scheduler
     is NOT running.  A 'stalled' status indicates that the scheduler
     is trying to run, but may not have enough resources to fulfill
     its jobs."
    ::= { xcronGeneral 2 }

xcronInterval OBJECT-TYPE
    SYNTAX      INTEGER (1..10)
    MAX-ACCESS  read-write
    STATUS      current
    DESCRIPTION
        "The number of minutes the scheduler sleeps.  After waiting
     for the configured number of minutes, or any configuration changes,
     the scheduler wakes up and checks for any jobs that need to be run.
     Also, a change to this parameter only takes affect AFTER the scheduler
     completes its next scheduling pass."
    DEFVAL      { 5 }
    ::= { xcronGeneral 3 }

xcronLoggingAdmin OBJECT-TYPE
    SYNTAX      INTEGER {
                    enabled(1),
                    disabled(2)
                }
    MAX-ACCESS  read-write
    STATUS      current
    DESCRIPTION
        "The administrative status of the 'logging' mechanism to attempt
     to retain as much status information as possible for each transaction
     that is performed.  Also, a change to this parameter only takes affect
     AFTER the scheduler completes its next scheduling pass."
    DEFVAL      { disabled }
    ::= { xcronGeneral 4 }

xcronLogClear OBJECT-TYPE
    SYNTAX      INTEGER {
                    ready(1),
                    clear(2)
                }
    MAX-ACCESS  read-write
    STATUS      current
    DESCRIPTION
        "The action to CLEAR all log messages of the list of batch jobs.
         When read, this object always returns the value 'ready(1)'. When 
         set to 'clear(2)', the log messages of all batch jobs will be
         cleared."
    DEFVAL      { ready }
    ::= { xcronGeneral 5 }

xcronDateTimeScheduleLast OBJECT-TYPE
    SYNTAX      DisplayString
    MAX-ACCESS  read-only  
    STATUS      current
    DESCRIPTION
        "The date and time of the LAST Scheduling pass."
    ::= { xcronGeneral 6 }

xcronDateTimeScheduleCurrent OBJECT-TYPE
    SYNTAX      DisplayString
    MAX-ACCESS  read-only  
    STATUS      current
    DESCRIPTION
        "The current date and time relating to the Scheduler."
    ::= { xcronGeneral 7 }

xcronDateTimeScheduleNext OBJECT-TYPE
    SYNTAX      DisplayString
    MAX-ACCESS  read-only  
    STATUS      current
    DESCRIPTION
        "The date and time of the NEXT Scheduling pass."
    ::= { xcronGeneral 8 }

-- ***********************************
-- Cron Entry Configuration Table
-- ***********************************
xcronBatchTable        OBJECT-TYPE
    SYNTAX      SEQUENCE OF XcronBatchEntry
    MAX-ACCESS  not-accessible
    STATUS      current
    DESCRIPTION
            "A list of cron batch entries."
    ::= { xcronObjectTables 1 }
 
xcronBatchEntry        OBJECT-TYPE
    SYNTAX      XcronBatchEntry
    MAX-ACCESS  not-accessible
    STATUS      current
    DESCRIPTION
            "An entry containing cron batch job information."
    INDEX    { xcronBatchID }
    ::= { xcronBatchTable 1 }

XcronBatchEntry ::=
    SEQUENCE {
        xcronBatchID                     INTEGER,
        xcronBatchMonth                  BIT STRING,
        xcronBatchDayOfTheMonth          BIT STRING,
        xcronBatchDayOfTheWeek           BIT STRING,
        xcronBatchHour                   BIT STRING,
        xcronBatchMinute                 BIT STRING,
        xcronBatchDateTime               DisplayString,
        xcronBatchLogMessage             DisplayString,
        xcronBatchCommand                DisplayString,
        xcronBatchScheduleStatus         INTEGER,
        xcronBatchRowStatus              RowStatus
    }

xcronBatchID OBJECT-TYPE
    SYNTAX      INTEGER(1..10)     
    MAX-ACCESS  not-accessible
    STATUS      current
    DESCRIPTION
        "The index of the table."
    ::= { xcronBatchEntry 1 }

xcronBatchMonth OBJECT-TYPE
    SYNTAX      BIT STRING { 
                    any(0),
                    jan(1),
                    feb(2),
                    mar(3),
                    apr(4),
                    may(5),
                    jun(6),
                    jul(7),
                    aug(8),
                    sep(9),
                    oct(10),
                    nov(11),
                    dec(12)
                }
    MAX-ACCESS  read-create
    STATUS      current
    DESCRIPTION
        "The bit mask associated with the Month of the year portion of the date
         in which to execute the associated command."
    ::= { xcronBatchEntry 2 }

xcronBatchDayOfTheMonth OBJECT-TYPE
    SYNTAX      BIT STRING { 
                    any(0),
                    d01(1),
                    d02(2),
                    d03(3),
                    d04(4),
                    d05(5),
                    d06(6),
                    d07(7),
                    d08(8),
                    d09(9),
                    d10(10),
                    d11(11),
                    d12(12),
                    d13(13),
                    d14(14),
                    d15(15),
                    d16(16),
                    d17(17),
                    d18(18),
                    d19(19),
                    d20(20),
                    d21(21),
                    d22(22),
                    d23(23),
                    d24(24),
                    d25(25),
                    d26(26),
                    d27(27),
                    d28(28),
                    d29(29),
                    d30(30),
                    d31(31)
                }
    MAX-ACCESS  read-create
    STATUS      current
    DESCRIPTION
        "The bit mask associated with the Day of the Month portion of the date
         to execute the associated command."
--    DEFVAL { { } }
    ::= { xcronBatchEntry 3 }

xcronBatchDayOfTheWeek OBJECT-TYPE
    SYNTAX      BIT STRING { 
                    any(0),
                    sun(1),
                    mon(2),
                    tue(3),
                    wed(4),
                    thu(5),
                    fri(6),
                    sat(7)
                }
    MAX-ACCESS  read-create
    STATUS      current
    DESCRIPTION
        "The bit mask associated with the Day of the Week portion of the date
        to execute the associated command."
--    DEFVAL { { } }
    ::= { xcronBatchEntry 4 }

xcronBatchHour  OBJECT-TYPE
    SYNTAX      BIT STRING { 
                    h00(0),
                    h01(1),
                    h02(2),
                    h03(3),
                    h04(4),
                    h05(5),
                    h06(6),
                    h07(7),
                    h08(8),
                    h09(9),
                    h10(10),
                    h11(11),
                    h12(12),
                    h13(13),
                    h14(14),
                    h15(15),
                    h16(16),
                    h17(17),
                    h18(18),
                    h19(19),
                    h20(20),
                    h21(21),
                    h22(22),
                    h23(23),
                    any(24)
                }
    MAX-ACCESS  read-create
    STATUS      current
    DESCRIPTION
        "The bit mask associated with the Hour of the day portion of the date
        to execute the associated command."
--    DEFVAL { { } }
    ::= { xcronBatchEntry 5 }

xcronBatchMinute OBJECT-TYPE
    SYNTAX      BIT STRING { 
                    m00(0),
                    m01(1),
                    m02(2),
                    m03(3),
                    m04(4),
                    m05(5),
                    m06(6),
                    m07(7),
                    m08(8),
                    m09(9),
                    m10(10),
                    m11(11),
                    m12(12),
                    m13(13),
                    m14(14),
                    m15(15),
                    m16(16),
                    m17(17),
                    m18(18),
                    m19(19),
                    m20(20),
                    m21(21),
                    m22(22),
                    m23(23),
                    m24(24),
                    m25(25),
                    m26(26),
                    m27(27),
                    m28(28),
                    m29(29),
                    m30(30),
                    m31(31),
                    m32(32),
                    m33(33),
                    m34(34),
                    m35(35),
                    m36(36),
                    m37(37),
                    m38(38),
                    m39(39),
                    m40(40),
                    m41(41),
                    m42(42),
                    m43(43),
                    m44(44),
                    m45(45),
                    m46(46),
                    m47(47),
                    m48(48),
                    m49(49),
                    m50(50),
                    m51(51),
                    m52(52),
                    m53(53),
                    m54(54),
                    m55(55),
                    m56(56),
                    m57(57),
                    m58(58),
                    m59(59),
                    any(60)
                }
    MAX-ACCESS  read-create
    STATUS      current
    DESCRIPTION
        "The bit mask associated with the Minute of the Hour portion of the date
        to execute the associated command."
--    DEFVAL { { } }
    ::= { xcronBatchEntry 6 }

xcronBatchDateTime OBJECT-TYPE
    SYNTAX      DisplayString
    MAX-ACCESS  read-only
    STATUS      current
    DESCRIPTION
        "The formatted date/time string associated with the entry." 
    ::= { xcronBatchEntry 7 }

xcronBatchLogMessage OBJECT-TYPE
    SYNTAX      DisplayString
    MAX-ACCESS  read-only  
    STATUS      current
    DESCRIPTION
        "The log message associated with the entry.  It contains errors or
     success messages, generated from the system."
    ::= { xcronBatchEntry 8 }

xcronBatchCommand OBJECT-TYPE
    SYNTAX      DisplayString
    MAX-ACCESS  read-create
    STATUS      current
    DESCRIPTION
        "The CLI command to execute.  It can be a simple command,
	 a series of commands, the execution of a TCL procedure,
	 or the sourcing of a script file."
    DEFVAL      { "" }
    ::= { xcronBatchEntry 9 }

xcronBatchScheduleStatus OBJECT-TYPE
    SYNTAX      INTEGER {
                    waiting(1),
                    scheduledToRun(2),
                    isRunning(3),
                    finishedRunning(4)
                }
    
    MAX-ACCESS  read-only
    STATUS      current
    DESCRIPTION
        "The most recent scheduling status of the batch entry."
    ::= { xcronBatchEntry 10 }

xcronBatchRowStatus OBJECT-TYPE
    SYNTAX      RowStatus
    MAX-ACCESS  read-create
    STATUS      current
    DESCRIPTION
        "This object is used to add and remove entries from the
        table. "
    REFERENCE
        "RFC1903: Textual Conventions for Version 2 of the Simple
        Network Management Protocol (SNMPv2)."
    ::= { xcronBatchEntry 11 }

-- ****************************************************************
-- Conformance Information
-- ****************************************************************

xcronCompliances OBJECT IDENTIFIER ::= { xcronConformance 1 }
xcronGroups      OBJECT IDENTIFIER ::= { xcronConformance 2 }

--
-- Compliance Statements
--

xcronCompliance MODULE-COMPLIANCE
    STATUS      current
    DESCRIPTION
        "The compliance statement for all agents that support this
        MIB. A compliant agent implements all objects defined in this
        MIB."
    MODULE  -- this module
    MANDATORY-GROUPS {
        xcronAllGroup
    }
    ::= { xcronCompliances 1 }

--
-- Object Groups
--

xcronAllGroup OBJECT-GROUP
    OBJECTS {
        xcronAdmin,
        xcronOper,
        xcronInterval,
        xcronLoggingAdmin,
        xcronLogClear,
        xcronDateTimeScheduleLast,
        xcronDateTimeScheduleCurrent,
        xcronDateTimeScheduleNext,
        xcronBatchMonth,
        xcronBatchDayOfTheMonth,
        xcronBatchDayOfTheWeek,
        xcronBatchHour,
        xcronBatchMinute,
        xcronBatchDateTime,
        xcronBatchLogMessage,
        xcronBatchCommand,
        xcronBatchScheduleStatus,
        xcronBatchRowStatus
    }
    STATUS      current
    DESCRIPTION
        "The set of all accessible objects in this MIB."
    ::= { xcronGroups 1 }

END
