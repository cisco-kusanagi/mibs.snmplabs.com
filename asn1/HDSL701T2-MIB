-- Copyright 1994 General DataComm Inc., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.

-- Revision History
-- Version   Date			Name		Description
-- 1.00A     16-May-1996  		S.Sankaran  Initial Revision
-- 1.00B     08-Sep-1996                D. Baylis   Removed RP stuff
-- 
HDSL701T2-MIB DEFINITIONS ::= BEGIN

IMPORTS
	OBJECT-TYPE			FROM RFC-1212
	DisplayString	    FROM RFC1213-MIB
	hdsl701T2             FROM GDCHDSL-MIB;

hdsl701T2System          OBJECT IDENTIFIER ::= { hdsl701T2 1 }
hdsl701T2Version         OBJECT IDENTIFIER ::= { hdsl701T2System 1 }

-- This mib is a subset of the HDSL mib for the 701T2 product.

gdc701T2SystemMIBversion OBJECT-TYPE
     	SYNTAX DisplayString (SIZE (5))
     	ACCESS read-only
     	STATUS mandatory
     	DESCRIPTION
     		"Identifies the version of the MIB. The format of the version
     		is x.yzT, where 'x' identifies the major revision number, 'y'
     		identifies the minor revision number, 'z' identifies the
     		typographical revision, and T identifies the test revision.
     		Acceptable values for the individual revision components are
     		as follows:
 
     		x: 1 - 9
     		y: 0 - 9
     		z: 0 - 9
     		T: A - Z
 
     		Upon formal release, no designation for the test revision will
     		be present."
     	::= { hdsl701T2Version 1 }

-- ********************************************************************
-- GDC Hdsl Alarm Object Identifier Definitions
-- ********************************************************************
hdsl701T2Alarms          	 OBJECT IDENTIFIER ::= { hdsl701T2 2 }

hdsl701T2NoResponseAlm		OBJECT IDENTIFIER ::= { hdsl701T2Alarms 1 }
hdsl701T2DiagRxErrAlm		OBJECT IDENTIFIER ::= { hdsl701T2Alarms 2 }
hdsl701T2PowerUpAlm		OBJECT IDENTIFIER ::= { hdsl701T2Alarms 3 }
hdsl701T2UnitFailure      	OBJECT IDENTIFIER ::= { hdsl701T2Alarms 4 }
hdsl701T2ChecksumCorrupt  	OBJECT IDENTIFIER ::= { hdsl701T2Alarms 5 }
hdsl701T2LossofSignal		OBJECT IDENTIFIER ::= { hdsl701T2Alarms 6 }
hdsl701T2UnavailableSec		OBJECT IDENTIFIER ::= { hdsl701T2Alarms 7 }
hdsl701T2ErrorSec	 	OBJECT IDENTIFIER ::= { hdsl701T2Alarms 8 }
hdsl701T2LossofSyncWord		OBJECT IDENTIFIER ::= { hdsl701T2Alarms 9 }
hdsl701T2OutofFrame		OBJECT IDENTIFIER ::= { hdsl701T2Alarms 10 }
hdsl701T2AllOnes		OBJECT IDENTIFIER ::= { hdsl701T2Alarms 11 }
hdsl701T2RemoteLossofSig	OBJECT IDENTIFIER ::= { hdsl701T2Alarms 12 }
hdsl701T2RemoteAlarmInd		OBJECT IDENTIFIER ::= { hdsl701T2Alarms 13 }
hdsl701T2MajorBER		OBJECT IDENTIFIER ::= { hdsl701T2Alarms 14 }
hdsl701T2MinorBER		OBJECT IDENTIFIER ::= { hdsl701T2Alarms 15 }
 


-- ALARM				 Maskable	Valid Interfaces
--===============================================================
--hdslNoResponseAlm			No	Unit
--hdslDiagRxErrAlm      		No      Unit
--hdslPowerUpAlm			No	Unit
--hdslUnitFailure       		No      Unit
--hdslChecksumCorrupt   		No      Unit
--hdslLossofSignal			Yes	T1, L1, L2 
--hdslUnavailableSec			Yes	T1, L1, L2
--hdslErrorSec				Yes	T1, L1, L2
--hdslLossofSyncWord			Yes	L1, L2
--hdslOutofFrame			Yes	T1
--hdslAllOnes				Yes	T1
--hdslRemoteLossofSig			Yes	T1
--hdslRemoteAlarmInd			Yes	T1 
--hdslMajorBER          		Yes     L1, L2 
--hdslMinorBER          		Yes     L1, L2



END
