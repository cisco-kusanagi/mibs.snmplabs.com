-- extracted from draft-yang-ib-performance-management-mib-00.txt
-- at Sat Nov  3 06:07:24 2001

   IB-PM-MIB DEFINITIONS ::= BEGIN 
    
   IMPORTS 
        MODULE-IDENTITY, OBJECT-TYPE, 
        Counter32, Integer32, experimental, 
        NOTIFICATION-TYPE                       FROM SNMPv2-SMI 
        TEXTUAL-CONVENTION,                              
        TruthValue                              FROM SNMPv2-TC; 
 
     
   Yang/Tsang     Internet Draft- Expires May 2002                 4 
                Infiniband Performance Management MIB        Nov 2001 
    
    
                 
    
   pm MODULE-IDENTITY 
       LAST-UPDATED "200111010000Z"  -- 01 Nov 2001 
       ORGANIZATION "IETF IP over IB Working Group 
                    Email:   ipoverib@ietf.org" 
       CONTACT-INFO "Carl Yang/Edwin Tsang 
                    Postal: TopSpin Communications, Inc. 
                    2460 Embarcadero Way 
                    Palo Alto, CA 94303 
                    United States 
                    Tel:    +1 650 251 1036 
                    Email:  carl@topspin.com" 
    
       DESCRIPTION  "The managed objects for an InfiniBand  
                    Performance Management."  
        
       REVISION    "200111010000Z" 
       DESCRIPTION "Initial version of this MIB." 
 
   ::={ experimental 117 } 
     
   Yang/Tsang     Internet Draft- Expires May 2002                 5 
                Infiniband Performance Management MIB        Nov 2001 
    
    
   -- 
   -- Objects 
   -- 
   pmMIBObjects         OBJECT IDENTIFIER ::= { pm 1 } 
    
    
   -- 
   -- ClassPortInfoTable 
   -- 
   pmClassPortInfoTable OBJECT-TYPE 
   SYNTAX              SEQUENCE OF PmClassPortInfoEntry 
   MAX-ACCESS          not-accessible 
   STATUS              current 
   DESCRIPTION 
      "A table used to list all ClassPortInfoEntry." 
   ::= { pmMIBObjects 1 } 
 
   pmClassPortInfoEntry OBJECT-TYPE 
   SYNTAX              PmClassPortInfoEntry 
   MAX-ACCESS          not-accessible 
   STATUS              current 
   DESCRIPTION 
      "Table entry for pmClassPortInfoTable." 
   INDEX        { pmClassPortInfoGUID } 
   ::= { pmClassPortInfoTable 1 } 
 
   PmClassPortInfoEntry::= SEQUENCE { 
       pmClassPortInfoGUID             OCTET STRING, 
       pmClassPortInfoAllPortSelect    TruthValue 
        } 
    
   pmClassPortInfoGUID  OBJECT-TYPE 
   SYNTAX               OCTET STRING (SIZE(8)) 
   MAX-ACCESS           read-only 
   STATUS               current 
   DESCRIPTION 
      "The GUID of this node." 
   ::= { pmClassPortInfoEntry 1 } 
    
   pmClassPortInfoAllPortSelect OBJECT-TYPE 
   SYNTAX                      TruthValue 
   MAX-ACCESS                  read-only 
   STATUS                      current 
   DESCRIPTION 
      "If reported as TRUE, indicates that all attributes containing 
      the PortSelect component support setting it to 0xFF to gather 
      data from all ports at once.  If reported as FALSE, using 0xFF in 
      PortSelect results in undefined behavior." 
   ::= { pmClassPortInfoEntry 2 } 
 
   -- 
   -- PortSampleCntrl 
   -- 
     
   Yang/Tsang     Internet Draft- Expires May 2002                 6 
                Infiniband Performance Management MIB        Nov 2001 
    
    
   pmPortSampleCntrlTable      OBJECT-TYPE 
   SYNTAX                      SEQUENCE OF PmPortSampleCntrlEntry 
   MAX-ACCESS                  not-accessible 
   STATUS                      current 
   DESCRIPTION 
      "A table used to list all PortSampleCntrlEntry." 
   ::= { pmMIBObjects 2 } 
 
   pmPortSampleCntrlEntry      OBJECT-TYPE 
   SYNTAX                      PmPortSampleCntrlEntry 
   MAX-ACCESS                  not-accessible 
   STATUS                      current 
   DESCRIPTION 
      "Table entry for pmPortSampleCntrlTable ." 
   INDEX        { pmPortSampleCntrlGUID } 
   ::= { pmPortSampleCntrlTable 1 } 
 
   PmPortSampleCntrlEntry::= SEQUENCE { 
       pmPortSampleCntrlGUID                   OCTET STRING, 
       pmPortSampleCntrlOpCode                 Integer32, 
       pmPortSampleCntrlPortSelect             Integer32, 
       pmPortSampleCntrlTick                   Integer32, 
       pmPortSampleCntrlCounterWidth           INTEGER, 
       pmPortSampleCntrlCounter0Mask           Integer32, 
       pmPortSampleCntrlCounter1Mask           Integer32, 
       pmPortSampleCntrlCounter2Mask           Integer32, 
       pmPortSampleCntrlCounter3Mask           Integer32, 
       pmPortSampleCntrlCounter4Mask           Integer32, 
       pmPortSampleCntrlCounter5Mask           Integer32, 
       pmPortSampleCntrlCounter6Mask           Integer32, 
       pmPortSampleCntrlCounter7Mask           Integer32, 
       pmPortSampleCntrlCounter8Mask           Integer32, 
       pmPortSampleCntrlCounter9Mask           Integer32, 
       pmPortSampleCntrlCounter10Mask          Integer32, 
       pmPortSampleCntrlCounter11Mask          Integer32, 
       pmPortSampleCntrlCounter12Mask          Integer32, 
       pmPortSampleCntrlCounter13Mask          Integer32, 
       pmPortSampleCntrlCounter14Mask          Integer32, 
       pmPortSampleCntrlSampleMechanisms       Integer32, 
       pmPortSampleCntrlSampleStatus           INTEGER, 
       pmPortSampleCntrlOptionMask             OCTET STRING, 
       pmPortSampleCntrlVendorMask             OCTET STRING, 
       pmPortSampleCntrlSampleStart            Integer32, 
       pmPortSampleCntrlSampleInterval         Integer32, 
       pmPortSampleCntrlTag                    OCTET STRING, 
       pmPortSampleCntrlCounterSelect0         Integer32, 
       pmPortSampleCntrlCounterSelect1         Integer32, 
       pmPortSampleCntrlCounterSelect2         Integer32, 
       pmPortSampleCntrlCounterSelect3         Integer32, 
       pmPortSampleCntrlCounterSelect4         Integer32, 
       pmPortSampleCntrlCounterSelect5         Integer32, 
       pmPortSampleCntrlCounterSelect6         Integer32, 
       pmPortSampleCntrlCounterSelect7         Integer32, 
     
   Yang/Tsang     Internet Draft- Expires May 2002                 7 
                Infiniband Performance Management MIB        Nov 2001 
    
    
       pmPortSampleCntrlCounterSelect8         Integer32, 
       pmPortSampleCntrlCounterSelect9         Integer32, 
       pmPortSampleCntrlCounterSelect10        Integer32, 
       pmPortSampleCntrlCounterSelect11        Integer32, 
       pmPortSampleCntrlCounterSelect12        Integer32, 
       pmPortSampleCntrlCounterSelect13        Integer32, 
       pmPortSampleCntrlCounterSelect14        Integer32 
        } 
    
   pmPortSampleCntrlGUID        OBJECT-TYPE 
   SYNTAX                       OCTET STRING (SIZE(8)) 
   MAX-ACCESS                   read-only 
   STATUS                       current 
   DESCRIPTION 
      "The GUID of this node." 
   ::= { pmPortSampleCntrlEntry 1 } 
    
   pmPortSampleCntrlOpCode     OBJECT-TYPE 
   SYNTAX                      Integer32 
   MAX-ACCESS                  read-write 
   STATUS                      current 
   DESCRIPTION 
      "Used to select a specific packet OpCode (as found in BTH) when 
      sampling optional quantities that are op code specific.  If 
      OpCode is 0xFF, all OpCodes are sampled as one otherwise only one 
      OpCode can be sampled at a time, although multiple quantities can 
      be sampled for the same OpCode.  The possible OpCode are defined 
      as follows: 
               0x0 : RC SEND First, 
               0x1 : RC SEND Middle, 
               0x2 : RC SEND Last, 
               0x3 : RC SEND Last with Immediate, 
               0x4 : RC SEND Only, 
               0x5 : RC SEND Only with Immediate, 
               0x6 : RC RDMA Write First, 
               0x7 : RC RDMA Write Middle, 
               0x8 : RC RDMA Write Last, 
               0x9 : RC RDMA Write Last with Immediate, 
               0xA : RC RDMA Write Only, 
               0xB : RC RDMA Write Only with Immediate, 
               0xC : RC RDMA Read Request, 
               0xD : RC RDMA Read Response First, 
               0xE : RC RDMA Read Response Middle, 
               0xF : RC RDMA Read Response Last, 
               0x10 : RC RDMA Read Response Only, 
               0x11 : RC RDMA Acknowledge, 
               0x12 : RC RDMA Atomic Acknowledge, 
               0x13 : RC RDMA CmpSwap, 
               0x14 : RC RDMA FetchAdd, 
               0x15 - 0x1F : RC Reserved, 
               0x20 : UC Send First, 
               0x21 : UC Send Middle, 
               0x22 : UC Send Last, 
     
   Yang/Tsang     Internet Draft- Expires May 2002                 8 
                Infiniband Performance Management MIB        Nov 2001 
    
    
               0x23 : UC Send Last with Immediate, 
               0x24 : UC Send Only, 
               0x25 : UC Send Only with Immediate, 
               0x26 : UC RDMA Write First, 
               0x27 : UC RDMA Write Middle, 
               0x28 : UC RDMA Write Last, 
               0x29 : UC RDMA Write Last with Immediate, 
               0x2A : UC RDMA Write Only, 
               0x2B : UC RDMA Write Only with Immediate, 
               0x2C - 0x3F : UC Reserved 
                0x40 : RD Send First, 
               0x41 : RD Send Middle, 
               0x42 : RD Send Last, 
               0x43 : RD Send Last with Immediate, 
               0x44 : RD Send Only, 
               0x45 : RD Send Only with Immediate, 
               0x46 : RD RDMA Write First, 
               0x47 : RD RDMA Write Middle, 
               0x48 : RD RDMA Write Last, 
               0x49 : RD RDMA Write Last with Immediate, 
               0x4A : RD RDMA Write Only, 
               0x4B : RD RDMA Write Only with Immediate, 
               0x4C : RD RDMA Read Request, 
               0x4D : RD RDMA Read Response First, 
               0x4E : RD RDMA Read Response Middle, 
               0x4F : RD RDMA Read Response Last, 
               0x50 : RD RDMA Read Only, 
               0x51 : RD Acknowledge, 
               0x52 : RD Atomic Acknowledge, 
               0x53 : RD CmpSwap, 
               0x54 : RD FetchAdd, 
               0x55 - 0x5F : RD Reserved, 
               0x64 : UD Send Only, 
               0x65 : UD Send Only with Immediate, 
               0x66 - 0x7F : UD Reserved, 
               0x80 - 0xBF : Reserved, 
                0xC0 - 0xEF :  Manufacture Specific Opcodes." 
   ::= { pmPortSampleCntrlEntry 2 } 
    
   pmPortSampleCntrlPortSelect OBJECT-TYPE 
   SYNTAX                      Integer32 
   MAX-ACCESS                  read-write 
   STATUS                      current 
   DESCRIPTION 
      "Selects which port will be sampled.  For an HCA or TCA, 
      PortSelect refers to an end port.  For a switch, PortSelect 
      refers to a switch port.  If the value does not correspond to an 
      actual port, the sample timers run normally but the resulting 
      sample counter values are zero.  If gathering data from all ports 
      at once is supported (see pmAllPortSelect), setting PortSelect to 
      0xFF will cause samples from all ports to be accumulated." 
   ::= { pmPortSampleCntrlEntry 3 } 
    
     
   Yang/Tsang     Internet Draft- Expires May 2002                 9 
                Infiniband Performance Management MIB        Nov 2001 
    
    
   pmPortSampleCntrlTick        OBJECT-TYPE 
   SYNTAX                       Integer32 
   MAX-ACCESS                   read-only 
   STATUS                       current 
   DESCRIPTION 
      "Indicates the nodes sampling clock interval as a multiple of 10x 
      the link transfer period.  For a 2.5G transfer link, the transfer 
      period is 400 picoseconds.  The encoding is: 
        0x00 = 10 x link transfer period (4 nanoseconds for 2.5G link) 
        0x01 = 20 x link transfer period 
        0x02 = 30 x link transfer period 
        ... 
        0xFF = 2,560 x link transfer period 
      To maximize utility of the performance attributes, implementers 
      are encouraged to choose the smallest practical tick size." 
   ::= { pmPortSampleCntrlEntry 4 } 
 
   pmPortSampleCntrlCounterWidth        OBJECT-TYPE 
   SYNTAX                               INTEGER { 
                                        width16Bits (0), 
                                        width20Bits (1), 
                                        width24Bits (2), 
                                        width28Bits (3), 
                                        width32Bits (4) 
                                        } 
   MAX-ACCESS                           read-only 
   STATUS                               current 
   DESCRIPTION 
      "Indicates the actual width in bits of the following components: 
          - SampleStart 
          - SampleInterval 
          - PortSamplesResult:Counter0 to 14 
        Counters smaller than 32 bits shall be implemented as the least 
        significant bits of the corresponding 32-bit attribute 
        component, with the unimplemented upper bits of the component 
        returning zeros for Get and ignored for Set." 
   ::= { pmPortSampleCntrlEntry 5 } 
 
   pmPortSampleCntrlCounter0Mask        OBJECT-TYPE 
   SYNTAX                               Integer32 
   MAX-ACCESS                           read-only 
   STATUS                               current 
   DESCRIPTION 
      "A bitmask that determines the capabilities of 
      PortSamplesResult:Counter0. 
          - Bit 0 = supports all mandatory quantities; shall be 1 
          - Bit 1 = supports all optional quantities 
          - Bit 2 = supports vendor-defined quantities" 
   ::= { pmPortSampleCntrlEntry 6 } 
 
   pmPortSampleCntrlCounter1Mask        OBJECT-TYPE 
   SYNTAX                               Integer32 
   MAX-ACCESS                           read-only 
     
   Yang/Tsang     Internet Draft- Expires May 2002                10 
                Infiniband Performance Management MIB        Nov 2001 
    
    
   STATUS                               current 
   DESCRIPTION 
      "A bitmask that determines the capabilities of 
      PortSamplesResult:Counter1. 
          - Bit 0 = supports all mandatory quantities; shall be 1 
          - Bit 1 = supports all optional quantities 
          - Bit 2 = supports vendor-defined quantities" 
   ::= { pmPortSampleCntrlEntry 7 } 
 
   pmPortSampleCntrlCounter2Mask        OBJECT-TYPE 
   SYNTAX                               Integer32 
   MAX-ACCESS                           read-only 
   STATUS                               current 
   DESCRIPTION 
      "A bitmask that determines the capabilities of 
      PortSamplesResult:Counter2. 
          - Bit 0 = supports all mandatory quantities; shall be 1 
          - Bit 1 = supports all optional quantities 
          - Bit 2 = supports vendor-defined quantities" 
   ::= { pmPortSampleCntrlEntry 8 } 
 
   pmPortSampleCntrlCounter3Mask        OBJECT-TYPE 
   SYNTAX                               Integer32 
   MAX-ACCESS                           read-only 
   STATUS                               current 
   DESCRIPTION 
      "A bitmask that determines the capabilities of 
      PortSamplesResult:Counter3. 
          - Bit 0 = supports all mandatory quantities; shall be 1 
          - Bit 1 = supports all optional quantities 
          - Bit 2 = supports vendor-defined quantities" 
   ::= { pmPortSampleCntrlEntry 9 } 
 
   pmPortSampleCntrlCounter4Mask        OBJECT-TYPE 
   SYNTAX                               Integer32 
   MAX-ACCESS                           read-only 
   STATUS                               current 
   DESCRIPTION 
      "A bitmask that determines the capabilities of 
      PortSamplesResult:Counter4. 
          - Bit 0 = supports all mandatory quantities; shall be 1 
          - Bit 1 = supports all optional quantities 
          - Bit 2 = supports vendor-defined quantities" 
   ::= { pmPortSampleCntrlEntry 10 } 
 
   pmPortSampleCntrlCounter5Mask        OBJECT-TYPE 
   SYNTAX                               Integer32 
   MAX-ACCESS                           read-only 
   STATUS                               current 
   DESCRIPTION 
      "A bitmask that determines the capabilities of 
      PortSamplesResult:Counter5. 
          - Bit 0 = supports all mandatory quantities; shall be 1 
     
   Yang/Tsang     Internet Draft- Expires May 2002                11 
                Infiniband Performance Management MIB        Nov 2001 
    
    
          - Bit 1 = supports all optional quantities 
          - Bit 2 = supports vendor-defined quantities" 
   ::= { pmPortSampleCntrlEntry 11 } 
 
   pmPortSampleCntrlCounter6Mask        OBJECT-TYPE 
   SYNTAX                               Integer32 
   MAX-ACCESS                           read-only 
   STATUS                               current 
   DESCRIPTION 
      "A bitmask that determines the capabilities of 
      PortSamplesResult:Counter6. 
          - Bit 0 = supports all mandatory quantities; shall be 1 
          - Bit 1 = supports all optional quantities 
          - Bit 2 = supports vendor-defined quantities" 
   ::= { pmPortSampleCntrlEntry 12 } 
 
   pmPortSampleCntrlCounter7Mask        OBJECT-TYPE 
   SYNTAX                               Integer32 
   MAX-ACCESS                           read-only 
   STATUS                               current 
   DESCRIPTION 
      "A bitmask that determines the capabilities of 
      PortSamplesResult:Counter7. 
          - Bit 0 = supports all mandatory quantities; shall be 1 
          - Bit 1 = supports all optional quantities 
          - Bit 2 = supports vendor-defined quantities" 
   ::= { pmPortSampleCntrlEntry 13 } 
 
   pmPortSampleCntrlCounter8Mask        OBJECT-TYPE 
   SYNTAX                               Integer32 
   MAX-ACCESS                           read-only 
   STATUS                               current 
   DESCRIPTION 
      "A bitmask that determines the capabilities of 
      PortSamplesResult:Counter8. 
          - Bit 0 = supports all mandatory quantities; shall be 1 
          - Bit 1 = supports all optional quantities 
          - Bit 2 = supports vendor-defined quantities" 
   ::= { pmPortSampleCntrlEntry 14 } 
 
   pmPortSampleCntrlCounter9Mask        OBJECT-TYPE 
   SYNTAX                               Integer32 
   MAX-ACCESS                           read-only 
   STATUS                               current 
   DESCRIPTION 
      "A bitmask that determines the capabilities of 
      PortSamplesResult:Counter9. 
          - Bit 0 = supports all mandatory quantities; shall be 1 
          - Bit 1 = supports all optional quantities 
          - Bit 2 = supports vendor-defined quantities" 
   ::= { pmPortSampleCntrlEntry 15 } 
 
   pmPortSampleCntrlCounter10Mask       OBJECT-TYPE 
     
   Yang/Tsang     Internet Draft- Expires May 2002                12 
                Infiniband Performance Management MIB        Nov 2001 
    
    
   SYNTAX                               Integer32 
   MAX-ACCESS                           read-only 
   STATUS                               current 
   DESCRIPTION 
      "A bitmask that determines the capabilities of 
      PortSamplesResult:Counter10. 
          - Bit 0 = supports all mandatory quantities; shall be 1 
          - Bit 1 = supports all optional quantities 
          - Bit 2 = supports vendor-defined quantities" 
   ::= { pmPortSampleCntrlEntry 16 } 
 
   pmPortSampleCntrlCounter11Mask       OBJECT-TYPE 
   SYNTAX                               Integer32 
   MAX-ACCESS                           read-only 
   STATUS                               current 
   DESCRIPTION 
      "A bitmask that determines the capabilities of 
      PortSamplesResult:Counter11. 
          - Bit 0 = supports all mandatory quantities; shall be 1 
          - Bit 1 = supports all optional quantities 
          - Bit 2 = supports vendor-defined quantities" 
   ::= { pmPortSampleCntrlEntry 17 } 
 
   pmPortSampleCntrlCounter12Mask       OBJECT-TYPE 
   SYNTAX                               Integer32 
   MAX-ACCESS                           read-only 
   STATUS                               current 
   DESCRIPTION 
      "A bitmask that determines the capabilities of 
      PortSamplesResult:Counter12. 
          - Bit 0 = supports all mandatory quantities; shall be 1 
          - Bit 1 = supports all optional quantities 
          - Bit 2 = supports vendor-defined quantities" 
   ::= { pmPortSampleCntrlEntry 18 } 
 
   pmPortSampleCntrlCounter13Mask       OBJECT-TYPE 
   SYNTAX                               Integer32 
   MAX-ACCESS                           read-only 
   STATUS                               current 
   DESCRIPTION 
      "A bitmask that determines the capabilities of 
      PortSamplesResult:Counter13. 
          - Bit 0 = supports all mandatory quantities; shall be 1 
          - Bit 1 = supports all optional quantities 
          - Bit 2 = supports vendor-defined quantities" 
   ::= { pmPortSampleCntrlEntry 19 } 
 
   pmPortSampleCntrlCounter14Mask       OBJECT-TYPE 
   SYNTAX                               Integer32 
   MAX-ACCESS                           read-only 
   STATUS                               current 
   DESCRIPTION 
     
   Yang/Tsang     Internet Draft- Expires May 2002                13 
                Infiniband Performance Management MIB        Nov 2001 
    
    
      "A bitmask that determines the capabilities of 
      PortSamplesResult:Counter14. 
          - Bit 0 = supports all mandatory quantities; shall be 1 
          - Bit 1 = supports all optional quantities 
          - Bit 2 = supports vendor-defined quantities" 
   ::= { pmPortSampleCntrlEntry 20 } 
 
   pmPortSampleCntrlSampleMechanisms    OBJECT-TYPE 
   SYNTAX                               Integer32 
   MAX-ACCESS                           read-only 
   STATUS                               current 
   DESCRIPTION 
        "The number of independent sample mechanisms implemented, i.e., 
        sets of PortSamplesControl and PortSamplesResult, minus one: 
          0 = one sample mechanism is available 
          1 = two sample mechanism is available 
          ... 
          255 = 256 sample mechanisms are available. 
        Providing multiple sampling mechanisms is optional.  N sample 
        mechanisms would permit N independent samples to be run 
        simultaneously.  A special value of Attribute Modifier 
        (0xFFFFFFFF) allows all sample mechanisms to be started with a 
        single Set, sampling the same quantities during the same 
        interval on N ports." 
   ::= { pmPortSampleCntrlEntry 21 } 
 
   pmPortSampleCntrlSampleStatus        OBJECT-TYPE 
   SYNTAX                               INTEGER { 
                                        samplingComplete (0), 
                                        sampleStartTimerRunning (1), 
                                        samplingUnderway (2), 
                                        reserved (3) 
                                        } 
   MAX-ACCESS                           read-only 
   STATUS                               current 
   DESCRIPTION 
          "Indicates the status of sampling." 
   ::= { pmPortSampleCntrlEntry 22 } 
 
   pmPortSampleCntrlOptionMask  OBJECT-TYPE 
   SYNTAX                       OCTET STRING (SIZE(8)) 
   MAX-ACCESS                   read-only 
   STATUS                       current 
   DESCRIPTION 
          "A bit mask indicating which optional InfiniBand performance 
          quantities are implemented.  Its value is described as 
          follows: 
            Bit 0 (LSB) = reserved ahall be zero 
            Bit 1 = PortXmitQueue[n] 
            Bit 2 = PortXmitDataVL[n] 
            Bit 3 = PortRcvDataVL[n] 
            Bit 4 = PortXmitPktVL[n] 
            Bit 5 = PortRcvPktVL[n] 
     
   Yang/Tsang     Internet Draft- Expires May 2002                14 
                Infiniband Performance Management MIB        Nov 2001 
    
    
            Bit 6 = PortRcvErrorDetails:PortLocalPhysicalErrors 
            Bit 7 = PortRcvErrorDetails:PortMalformedPacketErrors 
            Bit 8 = PortRcvErrorDetails:PortBufferOverrunErrors 
            Bit 9 = PortRcvErrorDetails:PortDLIDMappingErrors 
            Bit 10 = PortRcvErrorDetails:PortVLMappingErrors 
            Bit 11 = PortRcvErrorDetails:PortLoopingErrors 
            Bit 12 = PortXmitDiscardDetails:PortInactiveDiscards 
            Bit 13 = PortXmitDiscardDetails:PortNeighborMTUDiscards 
            Bit 14 = 
          PortXmitDiscardDetails:PortSwwLifetimeLimitDiscards 
            Bit 15 = 
          PortXmitDiscardDetails:PortSwHOQLifetimeLimitDiscards 
            Bit 16 = PortOpRcvCounters:PortOpRcvPkts 
            Bit 17 = PortOpRcvCounters:PortOpRcvData 
            Bit 18 = PortFlowCtlCounters:PortXmitFlowPkts 
            Bit 19 = PortFlowCtlCounters:PortRcvFlowPkts 
            Bit 20 = PortVLOpPackets:PortVLOpPackets[n] 
            Bit 21 = PortVLOpData:PortVLOpData[n] 
            Bit 22 = 
          PortVLXmitFlowCtlUpdateErrors:PortVLXmitFlowCtlUpdateErrors[n
          ] 
            Bit 23 = PortVLXmitWaitCounters:PortVLXmitWait[n] 
            Bit 24-47 = Reserved shall be zero 
            Bit 48 = SwPortVLUnkDests:PortVLUnkDests[n] 
            Bit 49-63 = Reserved shall be zero" 
   ::= { pmPortSampleCntrlEntry 23 } 
 
   pmPortSampleCntrlVendorMask  OBJECT-TYPE 
   SYNTAX                       OCTET STRING (SIZE(8)) 
   MAX-ACCESS                   read-only 
   STATUS                       current 
   DESCRIPTION 
        "A bitmask indicating which vendor-specific counters are 
        implemented.  Must be zero if the node does not support any 
        vendor-specific counters.  Otherwise use is vendor defined." 
   ::= { pmPortSampleCntrlEntry 24 } 
 
   pmPortSampleCntrlSampleStart OBJECT-TYPE 
   SYNTAX                       Integer32 
   MAX-ACCESS                   read-write 
   STATUS                       current 
   DESCRIPTION 
        "Determines when the sampling interval starts.  When Set, this 
        value is loaded into a timer and the following events occur: 
          - Sample Status is set to 1 
          - Counters in PortSamplesResult are set to zero 
          - The timer begins decrementing once per tick.  When the 
             timer reaches zero, timing stops and the following evetns 
             occur: 
              i. The PortXmitQueue quantities if selected are latched 
             ii. PortSamplesResult counters are started 
            iii. SampleStatus is set to 2 
             iv. The SampleInterval timer is started 
     
   Yang/Tsang     Internet Draft- Expires May 2002                15 
                Infiniband Performance Management MIB        Nov 2001 
    
    
        The SampleStart timer allows a performance application to 
        randomize the sample start time and insure decoupling from node 
        or network events.  Values used will typically be 10Æs of 
        milliseconds.  It is the fine granularity of this interval with 
        respect to the link rate that makes decoupling possible." 
   ::= { pmPortSampleCntrlEntry 25 } 
    
   pmPortSampleCntrlSampleInterval      OBJECT-TYPE 
   SYNTAX                               Integer32 
   MAX-ACCESS                           read-write 
   STATUS                               current 
   DESCRIPTION 
        "Detemine the length of the sampling interval.  When Set, this 
        value is loaded into a timer.  When the SampleStart counter 
        reaches zero, this timer begins decrementing once per tick.  
        When it reaches zero, timing stops and the following event 
        occur: 
          - PortSample2 counters are stopped and the resulting values 
             made available. 
          - SampleStatus is set to zero." 
   ::= { pmPortSampleCntrlEntry 26 } 
    
   pmPortSampleCntrlTag         OBJECT-TYPE 
   SYNTAX                       OCTET STRING (SIZE(4)) 
   MAX-ACCESS                   read-write 
   STATUS                       current 
   DESCRIPTION 
        "Used by a performance application when it does a 
        PerformanceSet(PortSamplesControl) to uniquely identify its 
        sample run in case of a collision with another performance 
        application.  When an application wishes to start a sample run, 
        it should pick a random Tag value and do a 
        PerformanceSet(PortSamplesControl).  If the returned value of 
        Tag does not match the selected value, another application is 
        using the sampling mechanism.  In this case the first 
        application must wait for a suitable time and retry its 
        sample." 
   ::= { pmPortSampleCntrlEntry 27 } 
    
   pmPortSampleCntrlCounterSelect0      OBJECT-TYPE 
   SYNTAX                               Integer32 
   MAX-ACCESS                           read-write 
   STATUS                               current 
   DESCRIPTION 
        "Selects quantity to be sampled by PortSamplesResult:Counter0.  
        IF an unimplemented quantity is selected, a Get to 
        PortSamplesResult:Counter0 returns zeroes.  The possible values 
        are specified in Table 187 of IBTA v1.0.a specifications." 
   ::= { pmPortSampleCntrlEntry 28 } 
    
   pmPortSampleCntrlCounterSelect1      OBJECT-TYPE 
   SYNTAX                               Integer32 
   MAX-ACCESS                           read-write 
     
   Yang/Tsang     Internet Draft- Expires May 2002                16 
                Infiniband Performance Management MIB        Nov 2001 
    
    
   STATUS                               current 
   DESCRIPTION 
        "Selects quantity to be sampled by PortSamplesResult:Counter1.  
        IF an unimplemented quantity is selected, a Get to 
        PortSamplesResult:Counter1 returns zeroes.  The possible values 
        are specified in Table 187 of IBTA v1.0.a specifications." 
   ::= { pmPortSampleCntrlEntry 29 } 
    
   pmPortSampleCntrlCounterSelect2      OBJECT-TYPE 
   SYNTAX                               Integer32 
   MAX-ACCESS                           read-write 
   STATUS                               current 
   DESCRIPTION 
        "Selects quantity to be sampled by PortSamplesResult:Counter2.  
        IF an unimplemented quantity is selected, a Get to 
        PortSamplesResult:Counter2 returns zeroes.  The possible values 
        are specified in Table 187 of IBTA v1.0.a specifications." 
   ::= { pmPortSampleCntrlEntry 30 } 
    
   pmPortSampleCntrlCounterSelect3      OBJECT-TYPE 
   SYNTAX                               Integer32 
   MAX-ACCESS                           read-write 
   STATUS                               current 
   DESCRIPTION 
        "Selects quantity to be sampled by PortSamplesResult:Counter3.  
        IF an unimplemented quantity is selected, a Get to 
        PortSamplesResult:Counter3 returns zeroes.  The possible values 
        are specified in Table 187 of IBTA v1.0.a specifications." 
   ::= { pmPortSampleCntrlEntry 31 } 
    
   pmPortSampleCntrlCounterSelect4      OBJECT-TYPE 
   SYNTAX                               Integer32 
   MAX-ACCESS                           read-write 
   STATUS                               current 
   DESCRIPTION 
        "Selects quantity to be sampled by PortSamplesResult:Counter4.  
        IF an unimplemented quantity is selected, a Get to 
        PortSamplesResult:Counter4 returns zeroes.  The possible values 
        are specified in Table 187 of IBTA v1.0.a specifications." 
   ::= { pmPortSampleCntrlEntry 32 } 
    
   pmPortSampleCntrlCounterSelect5      OBJECT-TYPE 
   SYNTAX                               Integer32 
   MAX-ACCESS                           read-write 
   STATUS                               current 
   DESCRIPTION 
        "Selects quantity to be sampled by PortSamplesResult:Counter5.  
        IF an unimplemented quantity is selected, a Get to 
        PortSamplesResult:Counter5 returns zeroes.  The possible values 
        are specified in Table 187 of IBTA v1.0.a specifications." 
   ::= { pmPortSampleCntrlEntry 33 } 
    
   pmPortSampleCntrlCounterSelect6      OBJECT-TYPE 
     
   Yang/Tsang     Internet Draft- Expires May 2002                17 
                Infiniband Performance Management MIB        Nov 2001 
    
    
   SYNTAX                               Integer32 
   MAX-ACCESS                           read-write 
   STATUS                               current 
   DESCRIPTION 
        "Selects quantity to be sampled by PortSamplesResult:Counter6.  
        IF an unimplemented quantity is selected, a Get to 
        PortSamplesResult:Counter6 returns zeroes.  The possible values 
        are specified in Table 187 of IBTA v1.0.a specifications." 
   ::= { pmPortSampleCntrlEntry 34 } 
    
   pmPortSampleCntrlCounterSelect7      OBJECT-TYPE 
   SYNTAX                               Integer32 
   MAX-ACCESS                           read-write 
   STATUS                               current 
   DESCRIPTION 
        "Selects quantity to be sampled by PortSamplesResult:Counter7.  
        IF an unimplemented quantity is selected, a Get to 
        PortSamplesResult:Counter7 returns zeroes.  The possible values 
        are specified in Table 187 of IBTA v1.0.a specifications." 
   ::= { pmPortSampleCntrlEntry 35 } 
    
   pmPortSampleCntrlCounterSelect8      OBJECT-TYPE 
   SYNTAX                               Integer32 
   MAX-ACCESS                           read-write 
   STATUS                               current 
   DESCRIPTION 
        "Selects quantity to be sampled by PortSamplesResult:Counter8.  
        IF an unimplemented quantity is selected, a Get to 
        PortSamplesResult:Counter8 returns zeroes.  The possible values 
        are specified in Table 187 of IBTA v1.0.a specifications." 
   ::= { pmPortSampleCntrlEntry 36 } 
    
   pmPortSampleCntrlCounterSelect9      OBJECT-TYPE 
   SYNTAX                               Integer32 
   MAX-ACCESS                           read-write 
   STATUS                               current 
   DESCRIPTION 
        "Selects quantity to be sampled by PortSamplesResult:Counter9. 
        IF an unimplemented quantity is selected, a Get to 
        PortSamplesResult:Counter9 returns zeroes.  The possible values 
        are specified in Table 187 of IBTA v1.0.a specifications." 
   ::= { pmPortSampleCntrlEntry 37 } 
    
   pmPortSampleCntrlCounterSelect10     OBJECT-TYPE 
   SYNTAX                               Integer32 
   MAX-ACCESS                           read-write 
   STATUS                               current 
   DESCRIPTION 
        "Selects quantity to be sampled by PortSamplesResult:Counter10.  
        IF an unimplemented quantity is selected, a Get to 
        PortSamplesResult:Counter10 returns zeroes.  The possible 
        values are specified in Table 187 of IBTA v1.0.a 
        specifications." 
     
   Yang/Tsang     Internet Draft- Expires May 2002                18 
                Infiniband Performance Management MIB        Nov 2001 
    
    
   ::= { pmPortSampleCntrlEntry 38 } 
    
   pmPortSampleCntrlCounterSelect11     OBJECT-TYPE 
   SYNTAX                               Integer32 
   MAX-ACCESS                           read-write 
   STATUS                               current 
   DESCRIPTION 
        "Selects quantity to be sampled by PortSamplesResult:Counter11.  
        IF an unimplemented quantity is selected, a Get to 
        PortSamplesResult:Counter11 returns zeroes.  The possible 
        values are specified in Table 187 of IBTA v1.0.a 
        specifications." 
   ::= { pmPortSampleCntrlEntry 39 } 
    
   pmPortSampleCntrlCounterSelect12     OBJECT-TYPE 
   SYNTAX                               Integer32 
   MAX-ACCESS                           read-write 
   STATUS                               current 
   DESCRIPTION 
        "Selects quantity to be sampled by PortSamplesResult:Counter12.  
        IF an unimplemented quantity is selected, a Get to 
        PortSamplesResult:Counter12 returns zeroes.  The possible 
        values are specified in Table 187 of IBTA v1.0.a 
        specifications." 
   ::= { pmPortSampleCntrlEntry 40 } 
    
   pmPortSampleCntrlCounterSelect13     OBJECT-TYPE 
   SYNTAX                               Integer32 
   MAX-ACCESS                           read-write 
   STATUS                               current 
   DESCRIPTION 
        "Selects quantity to be sampled by PortSamplesResult:Counter13.  
        IF an unimplemented quantity is selected, a Get to 
        PortSamplesResult:Counter13 returns zeroes.  The possible 
        values are specified in Table 187 of IBTA v1.0.a 
        specifications." 
   ::= { pmPortSampleCntrlEntry 41 } 
    
   pmPortSampleCntrlCounterSelect14     OBJECT-TYPE 
   SYNTAX                               Integer32 
   MAX-ACCESS                           read-write 
   STATUS                               current 
   DESCRIPTION 
        "Selects quantity to be sampled by PortSamplesResult:Counter14.  
        IF an unimplemented quantity is selected, a Get to 
        PortSamplesResult:Counter14 returns zeroes.  The possible 
        values are specified in Table 187 of IBTA v1.0.a 
        specifications." 
   ::= { pmPortSampleCntrlEntry 42 } 
    
   -- 
   -- PortSampleResult 
   -- 
     
   Yang/Tsang     Internet Draft- Expires May 2002                19 
                Infiniband Performance Management MIB        Nov 2001 
    
    
   pmPortSampleResultTable     OBJECT-TYPE 
   SYNTAX                      SEQUENCE OF PmPortSampleResultEntry 
   MAX-ACCESS                  not-accessible 
   STATUS                      current 
   DESCRIPTION 
      "A table used to list all pmPortSampleResultEntry." 
   ::= { pmMIBObjects 3 } 
 
   pmPortSampleResultEntry     OBJECT-TYPE 
   SYNTAX                      PmPortSampleResultEntry 
   MAX-ACCESS                  not-accessible 
   STATUS                      current 
   DESCRIPTION 
      "Table entry for pmPortSampleResultTable ." 
   INDEX        { pmPortSampleResultGUID } 
   ::= { pmPortSampleResultTable 1 } 
 
   PmPortSampleResultEntry::= SEQUENCE { 
       pmPortSampleResultGUID          OCTET STRING, 
       pmPortSampleResultTag           OCTET STRING, 
       pmResultSampleStatus            Integer32, 
       pmPortSampleResultCounter0      Counter32, 
       pmPortSampleResultCounter1      Counter32, 
       pmPortSampleResultCounter2      Counter32, 
       pmPortSampleResultCounter3      Counter32, 
       pmPortSampleResultCounter4      Counter32, 
       pmPortSampleResultCounter5      Counter32, 
       pmPortSampleResultCounter6      Counter32, 
       pmPortSampleResultCounter7      Counter32, 
       pmPortSampleResultCounter8      Counter32, 
       pmPortSampleResultCounter9      Counter32, 
       pmPortSampleResultCounter10     Counter32, 
       pmPortSampleResultCounter11     Counter32, 
       pmPortSampleResultCounter12     Counter32, 
       pmPortSampleResultCounter13     Counter32, 
       pmPortSampleResultCounter14     Counter32 
        } 
    
   pmPortSampleResultGUID       OBJECT-TYPE 
   SYNTAX                       OCTET STRING (SIZE(8)) 
   MAX-ACCESS                   read-only 
   STATUS                       current 
   DESCRIPTION 
      "The GUID of this node." 
   ::= { pmPortSampleResultEntry 1 } 
    
   pmPortSampleResultTag               OBJECT-TYPE 
   SYNTAX                              OCTET STRING (SIZE(4)) 
   MAX-ACCESS                          read-only 
   STATUS                              current 
   DESCRIPTION 
     
   Yang/Tsang     Internet Draft- Expires May 2002                20 
                Infiniband Performance Management MIB        Nov 2001 
    
    
      "Read-only copy of PortSamplesControl:Tag.  The Tag mechanism 
      provides a means for performance applications to detect 
      collisions when using the sampling mechanism." 
   ::= { pmPortSampleResultEntry 2 } 
 
   pmResultSampleStatus OBJECT-TYPE 
   SYNTAX                      Integer32 
   MAX-ACCESS                  read-only 
   STATUS                      current 
   DESCRIPTION 
      "Read-only copy of PortSamplesControl:SampleStatus.  Provided 
      here to minimize traffic whil application is polling for sample 
      completion." 
   ::= { pmPortSampleResultEntry 3 } 
 
   pmPortSampleResultCounter0          OBJECT-TYPE 
   SYNTAX                              Counter32 
   MAX-ACCESS                          read-only 
   STATUS                              current 
   DESCRIPTION 
      "Mandatory counter.  When PortSamplesControl:SampleStatus is 
      zero, contains the result of sampling the quantity selected by 
      PortSamplesControl:CounterSelect0.  Undefined when 
      PortSamplesControl:SampleStatus is non-zero.  The actual number 
      of valid (least significant) bits in the counter is defined by 
      PortSamplesControl:CounterWidth." 
   ::= { pmPortSampleResultEntry 4 } 
 
   pmPortSampleResultCounter1          OBJECT-TYPE 
   SYNTAX                              Counter32 
   MAX-ACCESS                          read-only 
   STATUS                              current 
   DESCRIPTION 
      "Mandatory counter.  When PortSamplesControl:SampleStatus is 
      zero, contains the result of sampling the quantity selected by 
      PortSamplesControl:CounterSelect1.  Undefined when 
      PortSamplesControl:SampleStatus is non-zero.  The actual number 
      of valid (least significant) bits in the counter is defined by 
      PortSamplesControl:CounterWidth." 
   ::= { pmPortSampleResultEntry 5 } 
 
   pmPortSampleResultCounter2          OBJECT-TYPE 
   SYNTAX                              Counter32 
   MAX-ACCESS                          read-only 
   STATUS                              current 
   DESCRIPTION 
      "Mandatory counter.  When PortSamplesControl:SampleStatus is 
      zero, contains the result of sampling the quantity selected by 
      PortSamplesControl:CounterSelect2.  Undefined when 
      PortSamplesControl:SampleStatus is non-zero.  The actual number 
      of valid (least significant) bits in the counter is defined by 
      PortSamplesControl:CounterWidth." 
   ::= { pmPortSampleResultEntry 6 } 
     
   Yang/Tsang     Internet Draft- Expires May 2002                21 
                Infiniband Performance Management MIB        Nov 2001 
    
    
 
   pmPortSampleResultCounter3          OBJECT-TYPE 
   SYNTAX                              Counter32 
   MAX-ACCESS                          read-only 
   STATUS                              current 
   DESCRIPTION 
      "Mandatory counter.  When PortSamplesControl:SampleStatus is 
      zero, contains the result of sampling the quantity selected by 
      PortSamplesControl:CounterSelect3.  Undefined when 
      PortSamplesControl:SampleStatus is non-zero.  The actual number 
      of valid (least significant) bits in the counter is defined by 
      PortSamplesControl:CounterWidth." 
   ::= { pmPortSampleResultEntry 7 } 
 
   pmPortSampleResultCounter4          OBJECT-TYPE 
   SYNTAX                              Counter32 
   MAX-ACCESS                          read-only 
   STATUS                              current 
   DESCRIPTION 
      "Mandatory counter.  When PortSamplesControl:SampleStatus is 
      zero, contains the result of sampling the quantity selected by 
      PortSamplesControl:CounterSelect4.  Undefined when 
      PortSamplesControl:SampleStatus is non-zero.  The actual number 
      of valid (least significant) bits in the counter is defined by 
      PortSamplesControl:CounterWidth." 
   ::= { pmPortSampleResultEntry 8 } 
 
   pmPortSampleResultCounter5          OBJECT-TYPE 
   SYNTAX                              Counter32 
   MAX-ACCESS                          read-only 
   STATUS                              current 
   DESCRIPTION 
      "Mandatory counter.  When PortSamplesControl:SampleStatus is 
      zero, contains the result of sampling the quantity selected by 
      PortSamplesControl:CounterSelect5.  Undefined when 
      PortSamplesControl:SampleStatus is non-zero.  The actual number 
      of valid (least significant) bits in the counter is defined by 
      PortSamplesControl:CounterWidth." 
   ::= { pmPortSampleResultEntry 9 } 
 
   pmPortSampleResultCounter6          OBJECT-TYPE 
   SYNTAX                              Counter32 
   MAX-ACCESS                          read-only 
   STATUS                              current 
   DESCRIPTION 
      "Mandatory counter.  When PortSamplesControl:SampleStatus is 
      zero, contains the result of sampling the quantity selected by 
      PortSamplesControl:CounterSelect6.  Undefined when 
      PortSamplesControl:SampleStatus is non-zero.  The actual number 
      of valid (least significant) bits in the counter is defined by 
      PortSamplesControl:CounterWidth." 
   ::= { pmPortSampleResultEntry 10 } 
 
     
   Yang/Tsang     Internet Draft- Expires May 2002                22 
                Infiniband Performance Management MIB        Nov 2001 
    
    
   pmPortSampleResultCounter7          OBJECT-TYPE 
   SYNTAX                              Counter32 
   MAX-ACCESS                          read-only 
   STATUS                              current 
   DESCRIPTION 
      "Mandatory counter.  When PortSamplesControl:SampleStatus is 
      zero, contains the result of sampling the quantity selected by 
      PortSamplesControl:CounterSelect7.  Undefined when 
      PortSamplesControl:SampleStatus is non-zero.  The actual number 
      of valid (least significant) bits in the counter is defined by 
      PortSamplesControl:CounterWidth." 
   ::= { pmPortSampleResultEntry 11 } 
 
   pmPortSampleResultCounter8          OBJECT-TYPE 
   SYNTAX                              Counter32 
   MAX-ACCESS                          read-only 
   STATUS                              current 
   DESCRIPTION 
      "Mandatory counter.  When PortSamplesControl:SampleStatus is 
      zero, contains the result of sampling the quantity selected by 
      PortSamplesControl:CounterSelect8.  Undefined when 
      PortSamplesControl:SampleStatus is non-zero.  The actual number 
      of valid (least significant) bits in the counter is defined by 
      PortSamplesControl:CounterWidth." 
   ::= { pmPortSampleResultEntry 12 } 
 
   pmPortSampleResultCounter9          OBJECT-TYPE 
   SYNTAX                              Counter32 
   MAX-ACCESS                          read-only 
   STATUS                              current 
   DESCRIPTION 
      "Mandatory counter.  When PortSamplesControl:SampleStatus is 
      zero, contains the result of sampling the quantity selected by 
      PortSamplesControl:CounterSelect9.  Undefined when 
      PortSamplesControl:SampleStatus is non-zero.  The actual number 
      of valid (least significant) bits in the counter is defined by 
      PortSamplesControl:CounterWidth." 
   ::= { pmPortSampleResultEntry 13 } 
 
   pmPortSampleResultCounter10         OBJECT-TYPE 
   SYNTAX                              Counter32 
   MAX-ACCESS                          read-only 
   STATUS                              current 
   DESCRIPTION 
      "Mandatory counter.  When PortSamplesControl:SampleStatus is 
      zero, contains the result of sampling the quantity selected by 
      PortSamplesControl:CounterSelect10.  Undefined when 
      PortSamplesControl:SampleStatus is non-zero.  The actual number 
      of valid (least significant) bits in the counter is defined by 
      PortSamplesControl:CounterWidth." 
   ::= { pmPortSampleResultEntry 14 } 
 
   pmPortSampleResultCounter11         OBJECT-TYPE 
     
   Yang/Tsang     Internet Draft- Expires May 2002                23 
                Infiniband Performance Management MIB        Nov 2001 
    
    
   SYNTAX                              Counter32 
   MAX-ACCESS                          read-only 
   STATUS                              current 
   DESCRIPTION 
      "Mandatory counter.  When PortSamplesControl:SampleStatus is 
      zero, contains the result of sampling the quantity selected by 
      PortSamplesControl:CounterSelect11.  Undefined when 
      PortSamplesControl:SampleStatus is non-zero.  The actual number 
      of valid (least significant) bits in the counter is defined by 
      PortSamplesControl:CounterWidth." 
   ::= { pmPortSampleResultEntry 15 } 
 
   pmPortSampleResultCounter12         OBJECT-TYPE 
   SYNTAX                              Counter32 
   MAX-ACCESS                          read-only 
   STATUS                              current 
   DESCRIPTION 
      "Mandatory counter.  When PortSamplesControl:SampleStatus is 
      zero, contains the result of sampling the quantity selected by 
      PortSamplesControl:CounterSelect12.  Undefined when 
      PortSamplesControl:SampleStatus is non-zero.  The actual number 
      of valid (least significant) bits in the counter is defined by 
      PortSamplesControl:CounterWidth." 
   ::= { pmPortSampleResultEntry 16 } 
 
   pmPortSampleResultCounter13         OBJECT-TYPE 
   SYNTAX                              Counter32 
   MAX-ACCESS                          read-only 
   STATUS                              current 
   DESCRIPTION 
      "Mandatory counter.  When PortSamplesControl:SampleStatus is 
      zero, contains the result of sampling the quantity selected by 
      PortSamplesControl:CounterSelect13.  Undefined when 
      PortSamplesControl:SampleStatus is non-zero.  The actual number 
      of valid (least significant) bits in the counter is defined by 
      PortSamplesControl:CounterWidth." 
   ::= { pmPortSampleResultEntry 17 } 
 
   pmPortSampleResultCounter14         OBJECT-TYPE 
   SYNTAX                              Counter32 
   MAX-ACCESS                          read-only 
   STATUS                              current 
   DESCRIPTION 
      "Mandatory counter.  When PortSamplesControl:SampleStatus is 
      zero, contains the result of sampling the quantity selected by 
      PortSamplesControl:CounterSelect14.  Undefined when 
      PortSamplesControl:SampleStatus is non-zero.  The actual number 
      of valid (least significant) bits in the counter is defined by 
      PortSamplesControl:CounterWidth." 
   ::= { pmPortSampleResultEntry 18 } 
 
   -- 
   -- pmPortCounters 
     
   Yang/Tsang     Internet Draft- Expires May 2002                24 
                Infiniband Performance Management MIB        Nov 2001 
    
    
   -- 
   pmPortCountersTable OBJECT-TYPE 
   SYNTAX              SEQUENCE OF PmPortCountersEntry 
   MAX-ACCESS          not-accessible 
   STATUS              current 
   DESCRIPTION 
      "A table used to list all pmPortCountersEntry." 
   ::= { pmMIBObjects 4 } 
 
   pmPortCountersoEntry OBJECT-TYPE 
   SYNTAX              PmPortCountersEntry 
   MAX-ACCESS          not-accessible 
   STATUS              current 
   DESCRIPTION 
      "Table entry for pmPortCountersTable." 
   INDEX        { pmPortCountersGUID } 
   ::= { pmPortCountersTable 1 } 
 
   PmPortCountersEntry::= SEQUENCE { 
       pmPortCountersGUID                      OCTET STRING, 
       pmPortCountersPortSelect                Integer32, 
       pmPortCountersSymbolErrors              Integer32, 
       pmPortCountersLinkErrorRecovery         Integer32, 
       pmPortCountersLinkDown                  Integer32, 
       pmPortCountersRcvErrors                 Integer32, 
       pmPortCountersRcvRemoteErrors           Integer32, 
        pmPortCountersRcvSwRelayErrors          Integer32, 
        pmPortCountersXmitDiscards              Integer32, 
        pmPortCountersXmitConstraintErrors      Integer32, 
        pmPortCountersRcvConstraintErrors       Integer32, 
        pmPortCountersLocalLinkIntegrityErrors  Integer32, 
        pmPortCountersExcessiveBufferOverrun    Integer32, 
        pmPortCountersVL15Dropped               Integer32, 
        pmPortCountersXmitData                  Integer32, 
        pmPortCountersRcvData                   Integer32, 
        pmPortCountersXmitPkts                  Integer32, 
        pmPortCountersRcvPkts                   Integer32 
        } 
    
   pmPortCountersGUID   OBJECT-TYPE 
   SYNTAX               OCTET STRING (SIZE(8)) 
   MAX-ACCESS           read-only 
   STATUS               current 
   DESCRIPTION 
      "The GUID of this node." 
   ::= { pmPortCountersoEntry 1 } 
    
   pmPortCountersPortSelect    OBJECT-TYPE 
   SYNTAX                      Integer32 
   MAX-ACCESS                  read-write 
   STATUS                      current 
   DESCRIPTION 
     
   Yang/Tsang     Internet Draft- Expires May 2002                25 
                Infiniband Performance Management MIB        Nov 2001 
    
    
      "Selects the port for which the data is reported.  Selecting a 
      non-existent port results in all zeros.  If gathering data from 
      all ports at once is supported, setting pmPortCountersPortSelect 
      to 0xFF will cause data from all ports to be accumulated." 
   ::= { pmPortCountersoEntry 2 } 
    
   pmPortCountersSymbolErrors  OBJECT-TYPE 
   SYNTAX                      Integer32 
   MAX-ACCESS                  read-write 
   STATUS                      current 
   DESCRIPTION 
      "Total number of symbol errors detected on one or more lanes." 
   ::= { pmPortCountersoEntry 3 } 
    
   pmPortCountersLinkErrorRecovery     OBJECT-TYPE 
   SYNTAX                              Integer32 
   MAX-ACCESS                          read-write 
   STATUS                              current 
   DESCRIPTION 
      "Total number of times the port training state machine has 
      successfully completed the link error recovery process." 
   ::= { pmPortCountersoEntry 4 } 
    
   pmPortCountersLinkDown      OBJECT-TYPE 
   SYNTAX                      Integer32 
   MAX-ACCESS                  read-write 
   STATUS                      current 
   DESCRIPTION 
      "Total number of times the port training state machine has failed 
      the link error recovery process and downed the link." 
   ::= { pmPortCountersoEntry 5 } 
    
   pmPortCountersRcvErrors     OBJECT-TYPE 
   SYNTAX                      Integer32 
   MAX-ACCESS                  read-write 
   STATUS                      current 
   DESCRIPTION 
      "Total number of packets containing an error that were received 
      on the port.  These errors include: 
          - Local physical errors (ICRC, VCRC, FCCRC, and all physical 
             errors that cause entry into bad) 
          - Malformed data packet errors (Lver, length, VL) 
          - Malformed link packet errors (operand, length, VL) 
          - Packets discarded due to buffer overrun" 
   ::= { pmPortCountersoEntry 6 } 
    
   pmPortCountersRcvRemoteErrors       OBJECT-TYPE 
   SYNTAX                              Integer32 
   MAX-ACCESS                          read-write 
   STATUS                              current 
   DESCRIPTION 
          "Total number of packets marked with the EBP delimiter 
          received on the port." 
     
   Yang/Tsang     Internet Draft- Expires May 2002                26 
                Infiniband Performance Management MIB        Nov 2001 
    
    
   ::= { pmPortCountersoEntry 7 } 
    
   pmPortCountersRcvSwRelayErrors      OBJECT-TYPE 
   SYNTAX                              Integer32 
   MAX-ACCESS                          read-write 
   STATUS                              current 
   DESCRIPTION 
          "Total number of packets received on the port that were 
          discarded because they could be forwarded by the switch 
          relay.  Reasons for this include: 
          - DLID mapping 
          - VL mapping 
          - Looping (output port = input port)." 
   ::= { pmPortCountersoEntry 8 } 
    
   pmPortCountersXmitDiscards  OBJECT-TYPE 
   SYNTAX                      Integer32 
   MAX-ACCESS                  read-write 
   STATUS                      current 
   DESCRIPTION 
          "Total number of outbound packets discarded by the port 
          because the port is down or congested.  Reasons for this 
          include: 
          - Output port is in the inactive state 
          - Packet length exceeded neighbor MTU 
          - Switch lifetime limit exceeds 
          - Switch HOQ limit exceeds." 
   ::= { pmPortCountersoEntry 9 } 
    
   pmPortCountersXmitConstraintErrors  OBJECT-TYPE 
   SYNTAX                              Integer32 
   MAX-ACCESS                          read-write 
   STATUS                              current 
   DESCRIPTION 
          "Total number of packets not transmitted from the port for 
          the following reasons: 
          - FilterRawOutbound is true and packet is raw 
          - PatitionEnforcementOutbound is true and packet fails 
             partition key check, IP version check, or transport header 
             version check." 
   ::= { pmPortCountersoEntry 10 } 
    
   pmPortCountersRcvConstraintErrors   OBJECT-TYPE 
   SYNTAX                              Integer32 
   MAX-ACCESS                          read-write 
   STATUS                              current 
   DESCRIPTION 
          "Total number of packets received on the port that are 
          discarded for the following reasons: 
          - FilterRawInbound is true and packet is raw 
          - PartitionEnforcementInbound is true and packet fails 
             partition key check, IP version check, or transport header 
             version check." 
     
   Yang/Tsang     Internet Draft- Expires May 2002                27 
                Infiniband Performance Management MIB        Nov 2001 
    
    
   ::= { pmPortCountersoEntry 11 } 
    
   pmPortCountersLocalLinkIntegrityErrors      OBJECT-TYPE 
   SYNTAX                                      Integer32 
   MAX-ACCESS                                  read-write 
   STATUS                                      current 
   DESCRIPTION 
          "The number of times that the frequency of packets containing 
          local physical errors exceeded local_phy_errors." 
   ::= { pmPortCountersoEntry 12 } 
    
   pmPortCountersExcessiveBufferOverrun OBJECT-TYPE 
   SYNTAX                              Integer32 
   MAX-ACCESS                          read-write 
   STATUS                              current 
   DESCRIPTION 
          "The number of times that overrun errors consecutive flow 
          control update periods occurred with at least one overrun 
          error in each period." 
   ::= { pmPortCountersoEntry 13 } 
    
   pmPortCountersVL15Dropped   OBJECT-TYPE 
   SYNTAX                      Integer32 
   MAX-ACCESS                  read-write 
   STATUS                      current 
   DESCRIPTION 
          "Number of incoming VL15 packets dropped due to resource 
          limitations on port selected by PortSelect." 
   ::= { pmPortCountersoEntry 14 } 
    
   pmPortCountersXmitData      OBJECT-TYPE 
   SYNTAX                      Integer32 
   MAX-ACCESS                  read-write 
   STATUS                      current 
   DESCRIPTION 
          "Optional; shall be zero if not implemented.  Total number of 
          data octets, divided by 4, transmitted on all VLs from the 
          port selected by PortSelect.  This includes all octets 
          between (and not including) the start of packet delimiter and 
          VCRC.  It excludes all link packets. 
           
          Implementers may choose to count data octets in groups larger 
          than four but are encouraged to choose the smallest group 
          possible.  Results are still reported as a multiple of four 
          octets." 
   ::= { pmPortCountersoEntry 15 } 
    
   pmPortCountersRcvData       OBJECT-TYPE 
   SYNTAX                      Integer32 
   MAX-ACCESS                  read-write 
   STATUS                      current 
   DESCRIPTION 
     
   Yang/Tsang     Internet Draft- Expires May 2002                28 
                Infiniband Performance Management MIB        Nov 2001 
    
    
          "Optional; shall be zero if not implemented.  Total number of 
          data octets, divided by 4, received on all VLs from the port 
          selected by PortSelect. This includes all octets between (and 
          not including) the start of packet delimiter and VCRC.  It 
          excludes all link packets. 
           
          Implementers may choose to count data octets in groups larger 
          than four but are encouraged to choose the smallest group 
          possible.  Results are still reported as a multiple of four 
          octets." 
   ::= { pmPortCountersoEntry 16 } 
    
   pmPortCountersXmitPkts      OBJECT-TYPE 
   SYNTAX                      Integer32 
   MAX-ACCESS                  read-write 
   STATUS                      current 
   DESCRIPTION 
          "Optional; shall be zero if not implemented.  Total number of 
          data packets, excluding link packets, transmitted on all VLs 
          from the port selected by PortSelect." 
   ::= { pmPortCountersoEntry 17 } 
    
   pmPortCountersRcvPkts       OBJECT-TYPE 
   SYNTAX                      Integer32 
   MAX-ACCESS                  read-write 
   STATUS                      current 
   DESCRIPTION 
          "Optional; shall be zero if not implemented.  Total number of 
          data packets, excluding link packets, received on all VLs 
          from the port selected by PortSelect." 
   ::= { pmPortCountersoEntry 18 } 
    
   END
