ERI-DNX-HDS3-MIB DEFINITIONS ::= BEGIN

IMPORTS
	MODULE-IDENTITY, OBJECT-IDENTITY, OBJECT-TYPE, Integer32,
	Counter32, NOTIFICATION-TYPE
		FROM SNMPv2-SMI
    DisplayString, TEXTUAL-CONVENTION
        FROM SNMPv2-TC
    eriMibs
        FROM ERI-ROOT-SMI
    devices, PortStatus, DecisionType, FunctionSwitch, 
    LinkPortAddress, LinkCmdStatus, trapSequence, OneByteField
        FROM ERI-DNX-SMC-MIB;

eriDNXHybridDS3MIB MODULE-IDENTITY 
      LAST-UPDATED    "200301270000Z"
      ORGANIZATION    "Eastern Research, Inc."
      CONTACT-INFO
                      "Customer Service
                Postal: Eastern Research, Inc.
                        225 Executive Drive
                        Moorestown, NJ 08057
                Phone:  +1-800-337-4374
                Email:  support@erinc.com"
      DESCRIPTION
              "The ERI Enterprise MIB Module for the DNX HDS3 Device."

      REVISION        "200301270000Z"
      DESCRIPTION
              "Nevio Poljak - eri_DnxNest MIB Rev 01.2
               Changed status of hds3PortCfgName from obsolete to current.
               Converted history comments to MODULE-IDENTITY REVISION format."

      REVISION        "200204080000Z"
      DESCRIPTION
              "Nevio Poljak - Software Release 14.2
              Converted to SMIv2 format. All 8 name fields associated with
              HDS3 Port were made obsolete."

      REVISION        "200203140000Z"
      DESCRIPTION
              "Nevio Poljak - Software Release 14.1
              Removed lcv(6) and los(7) as selectable errors to Insert for the
              DS3 Framer Status Table."

      REVISION        "200201040000Z"
      DESCRIPTION
              "Nevio Poljak - Software Release 14.1
              Added new E1 InterNational Bit field and GR303 Facility field
              was made obsolete."

      REVISION        "200110100000Z"
      DESCRIPTION
              "Nevio Poljak - Software Release 13.0
              Added new E1 National Bit field and new Tables for DS3 Framer
              Status Counters and LIU Diagnostics"

      REVISION        "200104030000Z"
      DESCRIPTION
              "Nevio Poljak - Software Release 12.0
              Added new InService-OOS commands for all links."

      REVISION        "200103010000Z"
      DESCRIPTION
              "Nevio Poljak - Software Release 11.0
              Added new GR-303 Facility field."
              
      REVISION        "200009150000Z"
      DESCRIPTION
              "Initial Release of this MIB. - Nevio Poljak"

  	::= { eriMibs 5 }

-- *************************************************************************
-- The enterprise OID will be { iso(1) org(3) dod(6) internet(1) private(4)
--                              enterprises(1) virent(644) eri(2) dnx (4) 
--                              devices(2), dnxHDS3(2) }

-- *************************************************************************
-- The HDS-3 card is currently controlled via the Config or Diag groups.
-- The Configuration branch is used to perform all HDS-3 Port and Link provisioning 
-- functions and the Diagnostic branch is used to run tests and view 
-- associated Statistics. 
-- *************************************************************************

dnxHDS3     OBJECT IDENTIFIER 	::= { devices 2 }
hds3Config  OBJECT IDENTIFIER 	::= { dnxHDS3 1 }
hds3Diag    OBJECT IDENTIFIER 	::= { dnxHDS3 2 }

-- *************************************************************************
-- The following textual conventions are used in this MIB
-- *************************************************************************

DS2GroupType ::= TEXTUAL-CONVENTION
		STATUS  current
        DESCRIPTION
           "Indicates the type of DS2/G.747 group type option used on the links. 
            VT 1.5 is used to group T1 links into 7 groups of 4 for the 28 links.
            VT 2.0 is used to group E1 links into 7 groups of 3 for the 21 links.
            Using the VT 2.0, links divisible by 4 are skipped over and not used."
        SYNTAX INTEGER {
                e1(0),
                ds1(1)
                }

-- *************************************************************************
-- This table is the HDS-3 Port configuration table

hds3PortConfigTable OBJECT-TYPE
        SYNTAX SEQUENCE OF HDS3PortConfigEntry
        MAX-ACCESS not-accessible
        STATUS current
        DESCRIPTION
            "This is the HDS-3 Port Configuration table which consists
            of an entry for each of the HDS-3 cards.  The total number of
            entries depends on the number of HDS-3 cards in the nest.
            This is the HDS-3 DS2/G.747 Configuration table which consists
            of an entry for each of the HDS-3 cards.  The total number of
            entries depends on the number of HDS-3 cards in the nest."
        ::= { hds3Config 1 }

hds3PortConfigEntry OBJECT-TYPE
        SYNTAX HDS3PortConfigEntry
        MAX-ACCESS not-accessible
        STATUS current
        DESCRIPTION
            "The conceptual row of the HDS-3 Port Configuration table. 
            A row in this table cannot be added or deleted, only modified."
        INDEX { hds3PortCfgAddr }
        ::= { hds3PortConfigTable 1 }

HDS3PortConfigEntry ::=
        SEQUENCE {
                hds3PortCfgAddr       LinkPortAddress,	-- RO
                hds3PortCfgResource   Integer32,        -- RO
                hds3PortCfgName       DisplayString,
                hds3FacilityId        DisplayString,
                hds3EquipmentId       DisplayString,
                hds3Location          DisplayString,
                hds3FrameId           DisplayString,
                hds3UnitName          DisplayString,
                hds3PortNumber        DisplayString,
                hds3Generator         DisplayString,
                hds3M13OpMode         INTEGER,
                hds3RcvLoopTiming     FunctionSwitch,
                hds3ShortCable        DecisionType,
                hds3M13RemLoop        INTEGER,
                hds3FEACLoopbackReq   FunctionSwitch,
                hds3XmtAISLocalLoop   INTEGER,
                hds3RcvAIS            INTEGER,
                hds3XmtAIS            INTEGER,
                hds3DS2Group1         DS2GroupType, 
                hds3DS2Group2         DS2GroupType,
                hds3DS2Group3         DS2GroupType,
                hds3DS2Group4         DS2GroupType,
                hds3DS2Group5         DS2GroupType,
                hds3DS2Group6         DS2GroupType,
                hds3DS2Group7         DS2GroupType,
                hds3CmdStatus         LinkCmdStatus
                }

hds3PortCfgAddr OBJECT-TYPE
        SYNTAX LinkPortAddress
        MAX-ACCESS read-only
        STATUS current
        DESCRIPTION
            "This number uniquely identifies a HDS-3 T1/E1 link resource. 
            This number will be used throughout the system to identify 
            a unique resource."
        ::= { hds3PortConfigEntry 1 }

hds3PortCfgResource OBJECT-TYPE
        SYNTAX Integer32
        MAX-ACCESS read-only
        STATUS current
        DESCRIPTION
                "Uniquely identifies an HDS3 Port in the system.
                 This number is provided as key to allow the manager to 
                 map this entry to a corresponding Resource Table entry."
        ::= { hds3PortConfigEntry 2 }

hds3PortCfgName OBJECT-TYPE
        SYNTAX DisplayString (SIZE(0..20))
        MAX-ACCESS read-write
        STATUS current
        DESCRIPTION
            "This is the user friendly text name to identify the circuit."
        ::= { hds3PortConfigEntry 3 }

hds3FacilityId OBJECT-TYPE
        SYNTAX DisplayString (SIZE(0..37))
        MAX-ACCESS read-write
        STATUS obsolete
        DESCRIPTION
        	"This is a description of the facility where this equipment 
        	 is located."
        ::= { hds3PortConfigEntry 4 }

hds3EquipmentId OBJECT-TYPE
        SYNTAX DisplayString (SIZE(0..9))
        MAX-ACCESS read-write
        STATUS obsolete
        DESCRIPTION
        	"This is a description of the equipment in use."
        ::= { hds3PortConfigEntry 5 }

hds3Location OBJECT-TYPE
        SYNTAX DisplayString (SIZE(0..10))
        MAX-ACCESS read-write          
        STATUS obsolete
        DESCRIPTION
        	"This is the user description of the location for this equipment."
        ::= { hds3PortConfigEntry 6 }

hds3FrameId OBJECT-TYPE
        SYNTAX DisplayString (SIZE(0..9))
        MAX-ACCESS read-write
        STATUS obsolete
        DESCRIPTION
        	"This is the description of the building where this equipment is 
        	located."
        ::= { hds3PortConfigEntry 7 }
 
hds3UnitName OBJECT-TYPE
        SYNTAX DisplayString (SIZE(0..5))
        MAX-ACCESS read-write
        STATUS obsolete
        DESCRIPTION
        	"This is the description of the bay or device this equipment 
        	 is part of."
        ::= { hds3PortConfigEntry 8 }

hds3PortNumber OBJECT-TYPE
        SYNTAX DisplayString (SIZE(0..37))
        MAX-ACCESS read-write
        STATUS obsolete
        DESCRIPTION
        	"This is the user description of the HDS-3 port."
        ::= { hds3PortConfigEntry 9 }

hds3Generator OBJECT-TYPE
        SYNTAX DisplayString (SIZE(0..37))
        MAX-ACCESS read-write
        STATUS obsolete
        DESCRIPTION
        	"This is the user description of the number generated by this 
        	equipment."
        ::= { hds3PortConfigEntry 10 }
        
hds3M13OpMode OBJECT-TYPE
        SYNTAX INTEGER {
                bellcoreM13(0),
                c-bitParity(1)
                }
        MAX-ACCESS read-write
        STATUS current
        DESCRIPTION
           "The framing selection for the DS1 to HDS-3 multiplexing."
        ::= { hds3PortConfigEntry 11 }

hds3RcvLoopTiming OBJECT-TYPE
        SYNTAX FunctionSwitch
        MAX-ACCESS read-write
        STATUS current
        DESCRIPTION
           "Enables or disables the HDS-3 transmit timing provided by the 
           receive clock.  When disabled, timing is provided by an on-board 
           oscillator."
        ::= { hds3PortConfigEntry 12 }

hds3ShortCable OBJECT-TYPE
        SYNTAX DecisionType
        MAX-ACCESS read-write
        STATUS current
        DESCRIPTION
           "Indicates the line build out of the HDS-3 transmitter.  'Yes' when 
           attached to a cable less than 50 feet long."
        ::= { hds3PortConfigEntry 13 }

hds3M13RemLoop OBJECT-TYPE
        SYNTAX INTEGER  {
                third-cbit-inverted (0),
                second-cbit-inverted (1),
                first-cbit-inverted (2)
                }
        MAX-ACCESS read-write
        STATUS current
        DESCRIPTION
           "Controls line codes used to set and reset DS3 remote line 
           loopback requests. This setting is provided by the carrier. 
           These codes cause a DS3 loopback in remote DS3 equipment or 
           respond to codes from remote DS3 equipment. This applies to 
           Bellcore M13 mode only. Different manufacturers use different 
           patterns in M13 mode."
        ::= { hds3PortConfigEntry 14 }


hds3FEACLoopbackReq OBJECT-TYPE
        SYNTAX FunctionSwitch
        MAX-ACCESS read-write
        STATUS current
        DESCRIPTION
           "Select enabled(1) to allow the module to respond to a Far End 
           Alarm and Control loopback request."
        ::= { hds3PortConfigEntry 15 }

hds3XmtAISLocalLoop OBJECT-TYPE
        SYNTAX INTEGER {
                none (0),
                framed-1010-cbitZero  (1),
                framed-allones-cbitZero (2),
                unframed-allones (3)
                }
        MAX-ACCESS read-write
        STATUS current
        DESCRIPTION
           "The Transmitted bit pattern used when the HDS3 port 
           is in Local Loop."
        ::= { hds3PortConfigEntry 16 }

hds3RcvAIS OBJECT-TYPE
        SYNTAX INTEGER  {
                framed1010-noOverheadBits(1),
                cbitZero-noPayloadBits(2),
                framed1010-cbitZero(3),
                framed1111-noOverheadBits(4),
                unframed-allones(5)
                }
        MAX-ACCESS read-write
        STATUS current
        DESCRIPTION
           "The Received bit pattern to use to determine when the remote 
           line is in error."
        ::= { hds3PortConfigEntry 17 }

hds3XmtAIS OBJECT-TYPE
        SYNTAX INTEGER {
                none (0),
                framed-1010-cbitZero  (1),
                framed-allones-cbitZero (2),
                unframed-allones (3)
                }
        MAX-ACCESS read-write
        STATUS current
        DESCRIPTION
           "The Transmitted bit pattern that used when the HDS3 port
            is in error."
        ::= { hds3PortConfigEntry 18 }

hds3DS2Group1 OBJECT-TYPE
        SYNTAX DS2GroupType 
        MAX-ACCESS read-write
        STATUS current
        DESCRIPTION
           "Indicates the type of grouping option used to on links 1 through 4. 
            Using the VT 2.0, link 4 is not used."
        ::= { hds3PortConfigEntry 19 }

hds3DS2Group2 OBJECT-TYPE
        SYNTAX DS2GroupType 
        MAX-ACCESS read-write
        STATUS current
        DESCRIPTION
           "Indicates the type of grouping option used to on links 5 through 8. 
            Using the VT 2.0, link 8 is not used."
        ::= { hds3PortConfigEntry 20 }

hds3DS2Group3 OBJECT-TYPE
        SYNTAX DS2GroupType 
        MAX-ACCESS read-write
        STATUS current
        DESCRIPTION
           "Indicates the type of grouping option used to on links 9 through 12. 
            Using the VT 2.0, link 12 is not used."
        ::= { hds3PortConfigEntry 21 }

hds3DS2Group4 OBJECT-TYPE
        SYNTAX DS2GroupType 
        MAX-ACCESS read-write
        STATUS current
        DESCRIPTION
           "Indicates the type of grouping option used to on links 13 through 16. 
            Using the VT 2.0, link 16 is not used."
        ::= { hds3PortConfigEntry 22 }

hds3DS2Group5 OBJECT-TYPE
        SYNTAX DS2GroupType 
        MAX-ACCESS read-write
        STATUS current
        DESCRIPTION
           "Indicates the type of grouping option used to on links 17 through 20. 
            Using the VT 2.0, link 20 is not used."
        ::= { hds3PortConfigEntry 23 }

hds3DS2Group6 OBJECT-TYPE
        SYNTAX DS2GroupType 
        MAX-ACCESS read-write
        STATUS current
        DESCRIPTION
           "Indicates the type of grouping option used to on links 21 through 24. 
            Using the VT 2.0, link 24 is not used."
        ::= { hds3PortConfigEntry 24 }

hds3DS2Group7 OBJECT-TYPE
        SYNTAX DS2GroupType 
        MAX-ACCESS read-write
        STATUS current
        DESCRIPTION
           "Indicates the type of grouping option used to on links 25 through 28. 
            Using the VT 2.0, link 28 is not used."
        ::= { hds3PortConfigEntry 25 }

hds3CmdStatus OBJECT-TYPE
        SYNTAX LinkCmdStatus
        MAX-ACCESS read-write
        STATUS current
        DESCRIPTION
           "The command status for this link configuration row/record.
           The value used in a SET will be replaced by a response
           value in the GET RESPONSE indicating success or failure.
           		
            Default Response State used in GET RESPONSE Command
                ready-for-command (0)
                    initial default status for a row           
                    
            HDS3 Link Commands used in SET Command (1..199)            
                update-link-config(1),
                    Change existing Link Configuration
               		
            Response States used in GET RESPONSE Command (200..399)
                update-successful (201)
                    Link data has been successfully changed
                                		
            HDS3 Port Config Error Codes used in GET RESPONSE Command (400..699)
                err-general-link-config-error (400)
                    Unknown link configuration error occurred                
                err-invalid-link-status (401)
                    Unrecognized link status setting
                err-invalid-link-framing (402)         
                    Line framing type not valid for link type
                err-invalid-link-command (403)
                    Unrecognized link command-action
                err-invalid-link-op-mode (407)
                    Configured M13 Op mode not valid for port; verify other
                    link parameters match desired new mode                
                err-invalid-link-rem-loop (408)         
                    Remote Loop type not valid for hds3 frame type
                err-invalid-link-ais (409)
                    Unrecognized hds3 AIS selection
                err-data-locked-by-another-user (450)
                    Another administrative user is making changes to this
                    part of the system via a terminal session. Check Event
                    Log for user name."
        ::= { hds3PortConfigEntry 26 }


-- *************************************************************************
-- This table is the HDS-3 T-1 Link configuration table

hds3T1E1LinkConfigTable OBJECT-TYPE
        SYNTAX SEQUENCE OF HDS3T1E1LinkConfigEntry
        MAX-ACCESS not-accessible
        STATUS current
        DESCRIPTION
            "This is the HDS-3 T-1 Link Configuration table which consists
            of an entry for each of the card's 28 links.  The total number of
            entries depends on the number of HDS3 cards in the nest."
        ::= { hds3Config 2 }

hds3T1E1LinkConfigEntry OBJECT-TYPE
        SYNTAX HDS3T1E1LinkConfigEntry
        MAX-ACCESS not-accessible
        STATUS current
        DESCRIPTION
            "The conceptual row of the HDS-3 T-1 Link Configuration table. 
            A row in this table cannot be added or deleted, only modified."
        INDEX { hds3T1E1CfgLinkAddr }
        ::= { hds3T1E1LinkConfigTable 1 }

HDS3T1E1LinkConfigEntry ::=
        SEQUENCE {
                hds3T1E1CfgLinkAddr     LinkPortAddress,  -- RO
                hds3T1E1CfgResource     Integer32,        -- RO
                hds3T1E1CfgLinkName     DisplayString,
                hds3T1E1Status          PortStatus,
                hds3T1E1Clear           INTEGER,                
                hds3T1E1Framing         INTEGER,
                hds3T1E1NetLoop         INTEGER,
                hds3T1E1YelAlrm         INTEGER,
                hds3T1E1RecoverTime     INTEGER,
                hds3T1E1EsfFormat       INTEGER,
                hds3T1E1IdleCode        INTEGER,
                hds3T1E1CfgCmdStatus    LinkCmdStatus,
                hds3T1E1Gr303Facility   DecisionType,  -- obsolete
                hds3T1E1NationalBits    OneByteField,
                hds3T1E1InterNational   OneByteField
                }

hds3T1E1CfgLinkAddr OBJECT-TYPE
        SYNTAX LinkPortAddress
        MAX-ACCESS read-only
        STATUS current
        DESCRIPTION
            "This number uniquely identifies a HDS-3 T1/E1 link resource. 
            This number will be used throughout the system to identify 
            a unique resource."
        ::= { hds3T1E1LinkConfigEntry 1 }

hds3T1E1CfgResource OBJECT-TYPE
        SYNTAX Integer32
        MAX-ACCESS read-only
        STATUS current
        DESCRIPTION
                "Uniquely identifies an HDS-3 T1/E1 Channel in the system.
                 This number is provided as key to allow the manager to 
                 map this entry to a corresponding Resource Table entry."
        ::= { hds3T1E1LinkConfigEntry 2 }

hds3T1E1CfgLinkName OBJECT-TYPE
        SYNTAX DisplayString (SIZE(0..20))
        MAX-ACCESS read-write
        STATUS current
        DESCRIPTION
        	"This is the user friendly text name to identify the link."
        ::= { hds3T1E1LinkConfigEntry 3 }

hds3T1E1Status OBJECT-TYPE
        SYNTAX PortStatus
        MAX-ACCESS read-write
        STATUS current
        DESCRIPTION
           "Dictates the current status of the link, in-service or 
           out-of-service."
        ::= { hds3T1E1LinkConfigEntry 4 }

hds3T1E1Clear OBJECT-TYPE
        SYNTAX INTEGER {
        	disabled (0),
        	framed   (1),
        	unframed (2)
        	}
        MAX-ACCESS read-write
        STATUS current
        DESCRIPTION
           "Determines if the port supports T1 or E1 unframed."
        ::= { hds3T1E1LinkConfigEntry 5 }

hds3T1E1Framing OBJECT-TYPE
        SYNTAX INTEGER {
        	e1 (0),
        	e1Crc (1),
        	e1Cas (2),
        	e1CasCrc (3),
        	e1Unframed (4),
        	t1Esf (5),
        	t1D4 (6),
        	t1Unframed (7)
        	}
        MAX-ACCESS read-write
        STATUS current
        DESCRIPTION
           "Determines the type of framing used on the line.  
           Choose between T1 SuperFrame 'D4', Extended SuperFrame (ESF),
           or T1 Unframed.  When value of hds3T1E1Clear is set to 
           unframed (2), the only valid framing options are: e1Unframed(4) 
           or t1Unframed(7)."
        ::= { hds3T1E1LinkConfigEntry 6 }

hds3T1E1NetLoop OBJECT-TYPE
        SYNTAX FunctionSwitch
        MAX-ACCESS read-write
        STATUS current
        DESCRIPTION
           "Determines whether or not the module should respond to loop 
           diagnostic commands received from the network supplier. Select 
           'enable' unless the commands are to be passed to another HDS3 
           device."
        ::= { hds3T1E1LinkConfigEntry 7 }

hds3T1E1YelAlrm OBJECT-TYPE
        SYNTAX DecisionType
        MAX-ACCESS read-write
        STATUS current
        DESCRIPTION
           "Causes the module to discard data and send a yellow alarm if it
           is in a red alarm condition after a 3 second period. 'Yes' must
           be chosen if the network supplier is a common carrier, such as a 
           telephone company."
        ::= { hds3T1E1LinkConfigEntry 8 }

hds3T1E1RecoverTime OBJECT-TYPE
        SYNTAX INTEGER {
        	timeout-3-secs (3),
        	timeout-10-secs(10),
        	timeout-15-secs(15)
        	}
        MAX-ACCESS read-write
        STATUS current
        DESCRIPTION
           "This is the red alarm timeout value.  Determines the amount 
           of seconds the port will wait to stop sending the yellow alarm 
           when coming out of a red alarm condition. This field does not
           apply to E1 links."
        ::= { hds3T1E1LinkConfigEntry 9 }

hds3T1E1EsfFormat OBJECT-TYPE
        SYNTAX INTEGER {
        	att-54016 (0),
        	ansi-t1-403 (1)
        	}
        MAX-ACCESS read-write
        STATUS current
        DESCRIPTION
           "Determines the type of ESF network commands the T-1 link 
           will respond to. It has no meaning for D4 networks. With ESF 
           networks, this information must be obtained from the network 
           supplier."
        ::= { hds3T1E1LinkConfigEntry 10 }

hds3T1E1IdleCode OBJECT-TYPE
        SYNTAX INTEGER {
        	busy (0),
        	idle (1)
        	}
        MAX-ACCESS read-write
        STATUS current
        DESCRIPTION
           "Determines the whether the code that will be transmitted over 
           the unused links will be 'idle' or 'busy' (all 1's)."
        ::= { hds3T1E1LinkConfigEntry 11 }

hds3T1E1CfgCmdStatus OBJECT-TYPE
        SYNTAX LinkCmdStatus 
        MAX-ACCESS read-write
        STATUS current
        DESCRIPTION
           "The command status for this link configuration row/record.
           The value used in a SET will be replaced by a response
           value in the GET RESPONSE indicating success or failure.
           		
            Default Response State used in GET RESPONSE Command
                ready-for-command (0)
                    initial default status for a row           
                    
            HDS3-T1E1 Link Commands used in SET Command (1..199)            
                update(1)
                    Change existing Link Configuration
                inServiceAll (7)
                    Change Link Status to in-service for all 8 links.
                copyToAll (9)
                    Copy T1 Link configuration to all other links 
                    within the same device
                outOfServiceAll (12)
                    Change Link Status to out-of-service for all 8 links.
               		
            Response States used in GET RESPONSE Command (100..199)
                update-successful (101)
                    Link data has been successfully changed
                insvc-successful (107)
                    All Links have been successfully placed In Service
                copy-successful (109)
                    T1 Link data has been successfully copied to other links
                oos-successful (112)
                    All Links have been successfully placed Out of Service
                                		
            HDS3-T1E1 Link Config Error Codes used in GET RESPONSE Command (400..699)
                err-general-link-config-error (400)
                    Unknown link configuration error occurred                
                err-invalid-link-status (401)
                    Unrecognized link status setting
                err-invalid-link-framing (402)         
                    Line framing type not valid for link type
                err-invalid-link-command (403)
                    Unrecognized link command-action
                err-invalid-esf-format (405)
                    ESF type not applicable to link type
                err-invalid-link-density (406)
                    Unrecognized T1 link density setting 
                err-invalid-network-loop (410)
                    Unrecognized network loop setting
                err-invalid-yellow-alrm (411)
                    Unrecognized yellow alarm setting
                err-invalid-red-timeout (412)
                    Unrecognized red alarm timeout
                err-invalid-idle-code (413)
                    Unrecognized idle code
                err-device-in-standby (414)
                    Can't change config for designated Standby device
                err-invalid-link-bits (427)
                    Reserved E1 bits must be left at zero.
                err-data-locked-by-another-user (450)
                    Another administrative user is making changes to this
                    part of the system via a terminal session. Check Event
                    Log for user name           		
                err-snmp-parse-failed (500)
                    Agent could not parse variable
                err-invalid-snmp-type (501)
                    Variable ASN type does not match Agent defined type 
                err-invalid-snmp-var-size (502)
                    Variable size is too big"                 		
        ::= { hds3T1E1LinkConfigEntry 12 }

hds3T1E1Gr303Facility OBJECT-TYPE
        SYNTAX DecisionType
        MAX-ACCESS read-only
        STATUS obsolete
        DESCRIPTION
           "Enables link to be configured as a Gr303 Facility"
        ::= { hds3T1E1LinkConfigEntry 13 }

hds3T1E1NationalBits OBJECT-TYPE
        SYNTAX OneByteField
        MAX-ACCESS read-write
        STATUS current
        DESCRIPTION
           "Enables E1 National S-bits to be set to zero or one.
           This single byte field can be changed to set the values 
           of the E1 NFA byte in odd frames as depicted below:
           
              sa8 sa7 sa6 sa5 sa4 reserved bits
              --- --- --- --- --- -------------
              1    1   1   1   1   0   0   0      = F8 (default)
              
           Values should be entered in Hex.  If reserved bits are changed,
           an error code (427) will be returned in the command status.                 
           "
        ::= { hds3T1E1LinkConfigEntry 14 }

hds3T1E1InterNational OBJECT-TYPE
        SYNTAX OneByteField
        MAX-ACCESS read-write
        STATUS current
        DESCRIPTION
           "Enables InterNational S(i) Spare bit to be set to zero or one.
           This single byte field can be changed to set the values 
           of the Bit 1 of TS0 G.704 frame as depicted below:
           
                    reserved bits        S(i)
              -------------------------- -----
              0   0   0   0   0   0   0   1      = 01 (default)
              
           Values should be entered in Hex.  If reserved bits are changed,
           an error code (427) will be returned in the command status.
           "
        ::= { hds3T1E1LinkConfigEntry 15 }


-- *************************************************************************
-- This table is the HDS-3 Framer Status Display table

hds3FramerStatusTable OBJECT-TYPE
        SYNTAX SEQUENCE OF HDS3FramerStatusEntry
        MAX-ACCESS not-accessible
        STATUS current
        DESCRIPTION
            "This is the HDS-3 Framer Status table which consists of a single
            entry for each card's Framer Display.  The total number of
            entries depends on the number of HDS3 cards in the nest."
        ::= { hds3Diag 1 }

hds3FramerStatusEntry OBJECT-TYPE
        SYNTAX HDS3FramerStatusEntry
        MAX-ACCESS not-accessible
        STATUS current
        DESCRIPTION
            "The conceptual row of the Framer table. 
            A row in this table cannot be added or deleted, only modified."
        INDEX { hds3FramerStatusAddr }
        ::= { hds3FramerStatusTable 1 }

HDS3FramerStatusEntry ::=
        SEQUENCE {
                hds3FramerStatusAddr             LinkPortAddress,  -- RO
                hds3FramerStatusResource         Integer32,        -- RO
                hds3FramerStatusState            INTEGER,
                hds3FramerStatusRedAlrmErrSecs   Counter32,
                hds3FramerStatusLOSErrSecs       Counter32,
                hds3FramerStatusOOFErrSecs       Counter32,
                hds3FramerStatusAISErrSecs       Counter32,
                hds3FramerStatusRcvIdleErrSecs   Counter32,
                hds3FramerStatusFarEndRcvErrSecs Counter32,
                hds3FramerStatusCFAErrSecs       Counter32,
                hds3FramerStatusTotErrSecs       Counter32,
                hds3FramerStatusPbitParityErrs   Counter32,
                hds3FramerStatusCbitParityErrs   Counter32,
                hds3FramerStatusFebeErrs         Counter32,
                hds3FramerStatusLCVErrs          Counter32,
                hds3FramerStatusFramingErrs      Counter32,
                hds3FramerStatusExcessZeroErrs   Counter32,
                hds3FramerStatusInsErrMode       INTEGER,        -- RW              
                hds3FramerStatusCmdStatus        INTEGER         -- RW              
              	}

hds3FramerStatusAddr OBJECT-TYPE
        SYNTAX LinkPortAddress
        MAX-ACCESS read-only
        STATUS current
        DESCRIPTION
            "This number uniquely identifies a HDS-3 Framer resource. 
            This number will be used throughout the system to identify 
            a unique resource."
        ::= { hds3FramerStatusEntry 1 }

hds3FramerStatusResource OBJECT-TYPE 
        SYNTAX Integer32
        MAX-ACCESS read-only
        STATUS current
        DESCRIPTION
            "This number uniquely identifies a HDS-3 Framer link resource. 
            This number is provided as key to allow the manager to map this
            entry to a corresponding Resource Table Entry."
        ::= { hds3FramerStatusEntry 2 }

hds3FramerStatusState OBJECT-TYPE
        SYNTAX INTEGER {
                ok  (0),
                ais (8),              -- bit 3
                lof (32),             -- bit 5
                los (64),             -- bit 6
                errors(2147483647)    -- all
                }
        MAX-ACCESS read-only
        STATUS current
        DESCRIPTION
           "Determines the current line condition status of the Framer.
                ok       (0)          - No Alarm
                ais      (8)          - Sending All Ones
                lof      (32)         - Loss/Out of Frame
                los      (64)         - Loss of Signal
                errors   (2147483647) - Multiple Errors displays raw bit field value
           "
       ::= { hds3FramerStatusEntry 3 }

hds3FramerStatusRedAlrmErrSecs OBJECT-TYPE
        SYNTAX Counter32
        MAX-ACCESS read-only
        STATUS current
        DESCRIPTION
            "This is the number of seconds a Red Alarm condition was declared.
            Declared when out of frame condition persists for more than 13.5msec."
        ::= { hds3FramerStatusEntry 4 } 
     
hds3FramerStatusLOSErrSecs OBJECT-TYPE
        SYNTAX Counter32
        MAX-ACCESS read-only
        STATUS current
        DESCRIPTION
            "This is the number of seconds a Loss of Signal condition was declared.
            Loss of signal declared after receipt of 175 contiguous zeroes."
        ::= { hds3FramerStatusEntry 5 } 
        
hds3FramerStatusOOFErrSecs OBJECT-TYPE
        SYNTAX Counter32
        MAX-ACCESS read-only
        STATUS current
        DESCRIPTION
            "This is the number of seconds Frame alignment errors were detected."
        ::= { hds3FramerStatusEntry 6 } 

hds3FramerStatusAISErrSecs OBJECT-TYPE
        SYNTAX Counter32
        MAX-ACCESS read-only
        STATUS current
        DESCRIPTION
            "This is the number of seconds a Alarm Indication Signal condition was declared.
            Declared after optioned AIS pattern is detected for more than 13.5msec."
        ::= { hds3FramerStatusEntry 7 } 
        
hds3FramerStatusRcvIdleErrSecs OBJECT-TYPE
        SYNTAX Counter32
        MAX-ACCESS read-only
        STATUS current
        DESCRIPTION
            "This is the number of seconds a Receive Idle Pattern condition was declared.
            Declared when DS3 1100 idle pattern detected for more than 13.5ms."
        ::= { hds3FramerStatusEntry 8 }     
        
hds3FramerStatusFarEndRcvErrSecs OBJECT-TYPE   
        SYNTAX Counter32
        MAX-ACCESS read-only
        STATUS current
        DESCRIPTION
            "This is the number of seconds a Far End Receive Failure condition was declared.
            Declared when both X-bits set to 0 in M13 and C-bit Parity frame format 
            (i.e., yellow alarm indicator)"
        ::= { hds3FramerStatusEntry 9 } 
        
hds3FramerStatusCFAErrSecs OBJECT-TYPE
        SYNTAX Counter32
        MAX-ACCESS read-only
        STATUS current
        DESCRIPTION
            "This is the number of seconds a Frame alignment change was detected."
        ::= { hds3FramerStatusEntry 10 } 

hds3FramerStatusTotErrSecs OBJECT-TYPE
        SYNTAX Counter32
        MAX-ACCESS read-only
        STATUS current
        DESCRIPTION
            "Total number of seconds in which any of the errored events have occurred."
        ::= { hds3FramerStatusEntry 11 } 

hds3FramerStatusPbitParityErrs OBJECT-TYPE
        SYNTAX Counter32
        MAX-ACCESS read-only
        STATUS current
        DESCRIPTION
            "The number of P-bit Parity errors detected."
        ::= { hds3FramerStatusEntry 12 } 

hds3FramerStatusCbitParityErrs OBJECT-TYPE
        SYNTAX Counter32
        MAX-ACCESS read-only
        STATUS current
        DESCRIPTION
            "The number of C-bit Parity errors detected."
        ::= { hds3FramerStatusEntry 13 } 

hds3FramerStatusFebeErrs OBJECT-TYPE
        SYNTAX Counter32
        MAX-ACCESS read-only
        STATUS current
        DESCRIPTION
            "The number of Far End Block errors detected."
        ::= { hds3FramerStatusEntry 14 } 

hds3FramerStatusLCVErrs OBJECT-TYPE
        SYNTAX Counter32
        MAX-ACCESS read-only
        STATUS current
        DESCRIPTION
            "The number of Line Code Violation errors detected."
        ::= { hds3FramerStatusEntry 15 } 

hds3FramerStatusFramingErrs OBJECT-TYPE
        SYNTAX Counter32
        MAX-ACCESS read-only
        STATUS current
        DESCRIPTION
            "The number of Framing errors detected."
        ::= { hds3FramerStatusEntry 16 } 

hds3FramerStatusExcessZeroErrs OBJECT-TYPE
        SYNTAX Counter32
        MAX-ACCESS read-only
        STATUS current
        DESCRIPTION
            "The number of Excessive Zero errors detected."
        ::= { hds3FramerStatusEntry 17 } 

hds3FramerStatusInsErrMode OBJECT-TYPE
        SYNTAX INTEGER {
                febe (1),
                p-bit-parity (2),
                c-bit-parity (3),
                multiframe-align (4),    
                frame-alignment (5),
--                lcv (6),             no longer supported
--                los (7),             no longer supported
                allErrors (8)
                }
        MAX-ACCESS read-write
        STATUS current
        DESCRIPTION
           "Determines the status of the current Insert Error mode associated 
           with the framer. In order to insert an error, the hds3FramerStatusCmdStatus 
           must be sent in a SET PDU with a value of 'insertError'."
        ::= { hds3FramerStatusEntry 18 }

hds3FramerStatusCmdStatus OBJECT-TYPE
        SYNTAX INTEGER {
    -- Initial default status for a row
            ready-for-command (0),
    -- Action States used in SET Command (1..99)
            update (1),
            clearErrors (14),
            insertError (16),
                                
    -- Response States used in GET RESPONSE Command (100..199)
            update-successful (101),
            clear-successful (114),
            insert-successful (116),
                                
    -- Error Codes used in GET RESPONSE Command (200..799)
            err-general-framer-error (200),
            err-test-in-progress (205),
            err-field-cannot-be-set (206),
            err-invalid-command (208),
            err-snmp-parse-failed(500),
            err-invalid-snmp-type(501),
            err-invalid-snmp-var-size(502) 
            }
        MAX-ACCESS read-write
        STATUS current
        DESCRIPTION
            "This is the command status for the DS3 Framer Row.
           The value used in a SET will be replaced by a response
           value in the GET RESPONSE indicating success or failure.

            Default Response State used in GET RESPONSE Command
                ready-for-command (0)
                    initial default status for a row           
                    
            DS3 Framer Action Commands used in SET Command (1..99)            
                update (1)
                    Can be used optionally when inserting errors
                    in order to get status code back in response
                clearErrors (14)
                    Resets all error counters and bert test time to zero
                insertError (16)
                    Inserts the current invalid bit pattern as indicated
                    by the value of hds3FramerStatusInsErrMode. 
                                
            Response States used in GET RESPONSE Command (100..199)
                update-successful (101)
                    Action has been successfully performed
                clear-successful (114)
                    Error counts have been successfully cleared
                insert-successful (116)
                    Errored bits have been successfully inserted
                                
            The Error Codes used in GET RESPONSE Command (200..799)
                err-general-framer-error (200)
                    Unknown request error occurred.
                err-test-in-progress (205)
                    Requested action cannot be performed during bert
                err-field-cannot-be-set (206)
                    Read-only field was included in SET request
                err-invalid-command (208)
                    Unrecognized framer Command requested                    
                err-snmp-parse-failed (500)
                    Agent could not parse variable
                err-invalid-snmp-type (501)
                    Variable ASN type does not match Agent defined type 
                err-invalid-snmp-var-size (502)
                    Variable size is too big" 
        ::= { hds3FramerStatusEntry 19 } 
        
-- *************************************************************************
-- This table is the HDS-3 LIU Diagnostic Status table

hds3LIUTable OBJECT-TYPE
        SYNTAX SEQUENCE OF HDS3LIUEntry
        MAX-ACCESS not-accessible
        STATUS current
        DESCRIPTION
            "This is the HDS-3 LIU Diagnostic Status Display table which consists
            of an entry for each HDS3 card's Line Interface Unit Display.  The 
            number of entries depends on the number of HDS3 cards in the nest."
        ::= { hds3Diag 2 }

hds3LIUEntry OBJECT-TYPE
        SYNTAX HDS3LIUEntry
        MAX-ACCESS not-accessible
        STATUS current
        DESCRIPTION
            "The conceptual row of the HDS3 LIU table. 
            A row in this table cannot be added or deleted, only modified."
        INDEX { hds3LIUAddr }
        ::= { hds3LIUTable 1 }

HDS3LIUEntry ::=
        SEQUENCE {
                hds3LIUAddr                 LinkPortAddress,  -- RO
                hds3LIUResource             Integer32,        -- RO
                hds3LIUBertState            INTEGER,          -- RW
                hds3LIUBertErrSecs          Counter32,
                hds3LIUBertDuration         Counter32,
                hds3LIULoopType             INTEGER,          -- RW   
                hds3LIUDigitalErrs          Counter32,
                hds3LIUAnalogErrs           Counter32,
                hds3LIUExcessZeroErrs       Counter32,
                hds3LIUCodingViolationErrs  Counter32,
                hds3LIUPRBSCheckErrs        Counter32,
              	hds3LIUCmdStatus            INTEGER           -- RW              
                }

hds3LIUAddr OBJECT-TYPE
        SYNTAX LinkPortAddress
        MAX-ACCESS read-only
        STATUS current
        DESCRIPTION
            "This number uniquely identifies a HDS-3 LIU resource address. 
            This number will be used throughout the system to identify 
            a unique resource."
        ::= { hds3LIUEntry 1 }

hds3LIUResource OBJECT-TYPE 
        SYNTAX Integer32
        MAX-ACCESS read-only
        STATUS current
        DESCRIPTION
            "This number uniquely identifies a HDS-3 LIU resource. 
            This number is provided as a key to allow the manager to map this
            entry to a corresponding Resource Table Entry."
        ::= { hds3LIUEntry 2 }

hds3LIUBertState OBJECT-TYPE
        SYNTAX INTEGER{
        	liu-bert  (44),
        	off (45)
        	}	
        MAX-ACCESS read-write
        STATUS current
        DESCRIPTION
            "This is the LIU Bert State indicated by liu-bert(on)/off.
            The LIU Bert is an 2^15-1 Unframed BERT."
        ::= { hds3LIUEntry 3 } 
     
hds3LIUBertErrSecs OBJECT-TYPE
        SYNTAX Counter32
        MAX-ACCESS read-only
        STATUS current
        DESCRIPTION
            "This is the number of LIU Bert Errored seconds."
        ::= { hds3LIUEntry 4 } 
        
hds3LIUBertDuration OBJECT-TYPE
        SYNTAX Counter32
        MAX-ACCESS read-only
        STATUS current
        DESCRIPTION
            "This is the number of seconds for the LIU Bert Duration."
        ::= { hds3LIUEntry 5 } 

hds3LIULoopType OBJECT-TYPE
        SYNTAX INTEGER {
        	off(0),
        	ds3-local(1),
        	ds3-line(36),
        	liu(39)
        	}
        MAX-ACCESS read-write
        STATUS current
        DESCRIPTION
            "Indicates the loopback status of the DS3 Framer/LIU for this device.            
              off        (0) - indicates loopback is disabled
        	  ds3-local  (1) - indicates DS3 local data is looped back to itself
        	  ds3-line   (36)- entire DS3 Frame is looped, framing is not regenerated
        	  liu        (39)- indicates Line Interface Unit local data is looped back
        	                   to itself."
        ::= { hds3LIUEntry 6 } 
        
hds3LIUDigitalErrs OBJECT-TYPE
        SYNTAX Counter32
        MAX-ACCESS read-only
        STATUS current
        DESCRIPTION
            "This is the number of seconds recorded for the LIU Digital Errors."
        ::= { hds3LIUEntry 7 } 

hds3LIUAnalogErrs OBJECT-TYPE   
        SYNTAX Counter32
        MAX-ACCESS read-only
        STATUS current
        DESCRIPTION
            "This is the number of seconds recorded for the LIU Analog Errors."
        ::= { hds3LIUEntry 8 } 

hds3LIUExcessZeroErrs OBJECT-TYPE
        SYNTAX Counter32
        MAX-ACCESS read-only
        STATUS current
        DESCRIPTION
            "This is the number of seconds LIU Excess zero errors were detected."
        ::= { hds3LIUEntry 9 } 

hds3LIUCodingViolationErrs OBJECT-TYPE
        SYNTAX Counter32
        MAX-ACCESS read-only
        STATUS current
        DESCRIPTION
            "This is the total number of Errored Seconds for the LIU Coding Violation."
        ::= { hds3LIUEntry 10 } 

hds3LIUPRBSCheckErrs OBJECT-TYPE
        SYNTAX Counter32
        MAX-ACCESS read-only
        STATUS current
        DESCRIPTION
            "This is the total number of Errored Seconds for the LIU PRBS check."
        ::= { hds3LIUEntry 11 } 

hds3LIUCmdStatus OBJECT-TYPE
        SYNTAX INTEGER {
    -- Initial default status for a row
            ready-for-command (0),
    -- Action States used in SET Command (1..99)
            update (1),
            clearErrors (14),
                                
    -- Response States used in GET RESPONSE Command (100..199)
            update-successful (101),
            clear-successful  (114),
                                
    -- LIU Error Codes used in GET RESPONSE Command (200..799)
            err-general-liu-error (200),
            err-invalid-loop-type (202),
            err-invalid-bert-type (203),
            err-test-in-progress (205),
            err-field-cannot-be-set (206),
            err-invalid-command (208),
            err-snmp-parse-failed(500),
            err-invalid-snmp-type(501),
            err-invalid-snmp-var-size(502) 
            }
        MAX-ACCESS read-write
        STATUS current
        DESCRIPTION
            "This is the command status for the LIU Framer Row.
           The value used in a SET will be replaced by a response
           value in the GET RESPONSE indicating success or failure.

            Default Response State used in GET RESPONSE Command
                ready-for-command (0)
                    initial default status for a row           
                    
            Commands used in SET Command (1..99)            
                update (1)
                    Can be used optionally when activating loops and berts
                    in order to get status code back in response
                clearErrors (14)
                    Resets all error counters and bert test time to zero
                                
            Response States used in GET RESPONSE Command (100..199)
                update-successful (101)
                    Test action has been successfully performed
                clear-successful (114)
                    Error counts have been successfully cleared
                                
            Error Codes used in GET RESPONSE Command (200..799)
                err-general-liu-error (200)
                    Unknown LIU request error occurred.
                err-invalid-loop-type (202)
                    Unrecognized loop selection
                err-invalid-bert-type (203)
                    Unrecognized bert selection
                err-test-in-progress (205)
                    Requested action cannot be performed during bert
                err-field-cannot-be-set (206)
                    Read-only field was included in SET request
                err-invalid-command (208)
                    Unrecognized Test Command requested                    
                err-snmp-parse-failed (500)
                    Agent could not parse variable
                err-invalid-snmp-type (501)
                    Variable ASN type does not match Agent defined type 
                err-invalid-snmp-var-size (502)
                    Variable size is too big" 
        ::= { hds3LIUEntry 12 } 

-- *************************************************************************

dnxHDS3Enterprise OBJECT-IDENTITY
      STATUS current
      DESCRIPTION "ERI DNX HDS3 Enterprise for Alarms/Events"
    ::= { dnxHDS3 0 }

hds3PortConfigTrap NOTIFICATION-TYPE
        OBJECTS {
            trapSequence,
            hds3PortCfgAddr,
            hds3CmdStatus
            }
        STATUS current
        DESCRIPTION
              	"This trap is used to notify a NMS that a user has updated 
              	the configuration for a given HDS3 Port entry."
        ::= { dnxHDS3Enterprise 1 }

hds3T1E1ConfigTrap NOTIFICATION-TYPE
        OBJECTS {
            trapSequence,
            hds3T1E1CfgLinkAddr,
            hds3T1E1CfgCmdStatus
            }
        STATUS current
        DESCRIPTION
              	"This trap is used to notify a NMS that a user has updated 
              	the Link configuration for a given HDS3-T1/E1 channel entry."
        ::= { dnxHDS3Enterprise 2 }


END

-- *************************************************************************
--
--  MIB:    ERI-DNX-OCTAL-HIGH-SPEED-MIB
--
--  Purpose:
--          This will be the MIB for the DNX Octal High Speed Interface 
--          Module. This will provide for Configuration and Diagnostics
--          on any Octal High Speed card in the nest.
--
--  Contact: Eastern Research Inc. 1-800-337-4374  Email: support@erinc.com
--
-- *************************************************************************
