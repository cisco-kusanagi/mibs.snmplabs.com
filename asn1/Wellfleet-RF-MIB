Wellfleet-RF-MIB DEFINITIONS ::= BEGIN

-- Created by mdl2asn version 3.1
-- Creation date: Wed Aug 30 16:46:51 EDT 1995


    IMPORTS

      IpAddress,  Gauge 
        FROM RFC1155-SMI
      OBJECT-TYPE
        FROM RFC-1212
      wfIpGroup
        FROM Wellfleet-COMMON-MIB;


    wfIpRfRipImportTable OBJECT-TYPE
        SYNTAX	SEQUENCE OF WfIpRfRipImportEntry
        ACCESS	not-accessible
        STATUS	mandatory
        DESCRIPTION
                "The list of Rip Import Route Filter Rules in IP"
        ::= { wfIpGroup 8 }

    wfIpRfRipImportEntry OBJECT-TYPE
        SYNTAX	WfIpRfRipImportEntry
        ACCESS	not-accessible
        STATUS	mandatory
        DESCRIPTION
                "An entry in the Rip Import Rule Table"
        INDEX	{ wfIpRfRipImportAddress,
    		  wfIpRfRipImportMask,
    		  wfIpRfRipImportRipGateway,
    		  wfIpRfRipImportRipInterface }
        ::= { wfIpRfRipImportTable 1 }

    WfIpRfRipImportEntry ::= SEQUENCE {
    	    wfIpRfRipImportCreate
    		INTEGER,
    	    wfIpRfRipImportEnable
    		INTEGER,
    	    wfIpRfRipImportAddress
    		IpAddress,
    	    wfIpRfRipImportMask
    		IpAddress,
    	    wfIpRfRipImportAction
    		INTEGER,
    	    wfIpRfRipImportPreference
    		INTEGER,
    	    wfIpRfRipImportRipGateway
    		IpAddress,
    	    wfIpRfRipImportRipInterface
    		IpAddress,
    	    wfIpRfRipImportApplyMask
    		IpAddress
        }

    wfIpRfRipImportCreate OBJECT-TYPE
        SYNTAX	INTEGER {
    		    create(1),
    		    delete(2)
    		}
        ACCESS	read-write
        STATUS	mandatory
        DESCRIPTION
                "Create/Delete parameter. Default is created.
                Users perform an SNMP SET operation on this
                object in order to create/delete this Rule."
        DEFVAL	{ create }
        ::= { wfIpRfRipImportEntry 1 }

    wfIpRfRipImportEnable OBJECT-TYPE
        SYNTAX	INTEGER {
    		    enable(1),
    		    disable(2)
    		}
        ACCESS	read-write
        STATUS	mandatory
        DESCRIPTION
                "Enable/Disable parameter. Default is enabled.
                Users perform an SNMP SET operation on this
                object in order to enable/disable this Rule."
        DEFVAL	{ enable }
        ::= { wfIpRfRipImportEntry 2 }

    wfIpRfRipImportAddress OBJECT-TYPE
        SYNTAX	IpAddress
        ACCESS	read-only
        STATUS	mandatory
        DESCRIPTION
                "The IP address to which this filter applies"
        ::= { wfIpRfRipImportEntry 3 }

    wfIpRfRipImportMask OBJECT-TYPE
        SYNTAX	IpAddress
        ACCESS	read-only
        STATUS	mandatory
        DESCRIPTION
                "The Mask to which this filter applies. When combined
                with the Address, a range is specified for application
                of this rule"
        ::= { wfIpRfRipImportEntry 4 }

    wfIpRfRipImportAction OBJECT-TYPE
        SYNTAX	INTEGER {
    		    accept(1),
    		    ignore(3)
    		}
        ACCESS	read-write
        STATUS	mandatory
        DESCRIPTION
                "The Action of this Filter"
        DEFVAL	{ accept }
        ::= { wfIpRfRipImportEntry 5 }

    wfIpRfRipImportPreference OBJECT-TYPE
        SYNTAX	INTEGER(0..16)
        ACCESS	read-write
        STATUS	mandatory
        DESCRIPTION
                "The Preference associated with this filter - only valid if accept"
        DEFVAL	{ 1 }
        ::= { wfIpRfRipImportEntry 6 }

    wfIpRfRipImportRipGateway OBJECT-TYPE
        SYNTAX	IpAddress
        ACCESS	read-only
        STATUS	mandatory
        DESCRIPTION
                "The RIP Gateway to be concerned with"
        ::= { wfIpRfRipImportEntry 7 }

    wfIpRfRipImportRipInterface OBJECT-TYPE
        SYNTAX	IpAddress
        ACCESS	read-only
        STATUS	mandatory
        DESCRIPTION
                "The IP Network Interface to be concerned with"
        ::= { wfIpRfRipImportEntry 8 }

    wfIpRfRipImportApplyMask OBJECT-TYPE
        SYNTAX	IpAddress
        ACCESS	read-write
        STATUS	mandatory
        DESCRIPTION
                "The Mask to apply to this route learned instead of the default.
                NULL means to apply the normal filter"
        ::= { wfIpRfRipImportEntry 9 }

    wfIpRfRipExportTable OBJECT-TYPE
        SYNTAX	SEQUENCE OF WfIpRfRipExportEntry
        ACCESS	not-accessible
        STATUS	mandatory
        DESCRIPTION
                "The list of Rip Export Route Filter Rules in IP"
        ::= { wfIpGroup 9 }

    wfIpRfRipExportEntry OBJECT-TYPE
        SYNTAX	WfIpRfRipExportEntry
        ACCESS	not-accessible
        STATUS	mandatory
        DESCRIPTION
                "An entry in the Rip Export Rule Table"
        INDEX	{ wfIpRfRipExportAddress,
    		  wfIpRfRipExportMask,
    		  wfIpRfRipExportFromProtocol,
    		  wfIpRfRipExportInterface }
        ::= { wfIpRfRipExportTable 1 }

    WfIpRfRipExportEntry ::= SEQUENCE {
    	    wfIpRfRipExportCreate
    		INTEGER,
    	    wfIpRfRipExportEnable
    		INTEGER,
    	    wfIpRfRipExportAddress
    		IpAddress,
    	    wfIpRfRipExportMask
    		IpAddress,
    	    wfIpRfRipExportFromProtocol
    		INTEGER,
    	    wfIpRfRipExportAction
    		INTEGER,
    	    wfIpRfRipExportInterface
    		IpAddress,
    	    wfIpRfRipExportRipMetric
    		INTEGER
        }

    wfIpRfRipExportCreate OBJECT-TYPE
        SYNTAX	INTEGER {
    		    create(1),
    		    delete(2)
    		}
        ACCESS	read-write
        STATUS	mandatory
        DESCRIPTION
                "Create/Delete parameter. Default is created.
                Users perform an SNMP SET operation on this
                object in order to create/delete this Rule."
        DEFVAL	{ create }
        ::= { wfIpRfRipExportEntry 1 }

    wfIpRfRipExportEnable OBJECT-TYPE
        SYNTAX	INTEGER {
    		    enable(1),
    		    disable(2)
    		}
        ACCESS	read-write
        STATUS	mandatory
        DESCRIPTION
                "Enable/Disable parameter. Default is enabled.
                Users perform an SNMP SET operation on this
                object in order to enable/disable this Rule."
        DEFVAL	{ enable }
        ::= { wfIpRfRipExportEntry 2 }

    wfIpRfRipExportAddress OBJECT-TYPE
        SYNTAX	IpAddress
        ACCESS	read-only
        STATUS	mandatory
        DESCRIPTION
                "The IP address to which this filter applies"
        ::= { wfIpRfRipExportEntry 3 }

    wfIpRfRipExportMask OBJECT-TYPE
        SYNTAX	IpAddress
        ACCESS	read-only
        STATUS	mandatory
        DESCRIPTION
                "The Mask for the Address Above. When combined
                with the Address, a range is specified for application
                of this filter rule"
        ::= { wfIpRfRipExportEntry 4 }

    wfIpRfRipExportFromProtocol OBJECT-TYPE
        SYNTAX	INTEGER {
    		    rip(1),
    		    egp(2),
    		    ospf(3),
    		    direct(4),
    		    static(5),
    		    bgp3(6)
    		}
        ACCESS	read-only
        STATUS	mandatory
        DESCRIPTION
                "The protocol from which this Information is derived"
        ::= { wfIpRfRipExportEntry 5 }

    wfIpRfRipExportAction OBJECT-TYPE
        SYNTAX	INTEGER {
    		    propa(2),
    		    ignore(3),
    		    aggregate(4)
    		}
        ACCESS	read-write
        STATUS	mandatory
        DESCRIPTION
                "The action of this export filter;
                if IP_RF_RIP_EXP_ACTION_AGGREGATE action, the default
                route, 0.0.0.0, is advertised instead networks that match
                this filter"
        DEFVAL	{ propa }
        ::= { wfIpRfRipExportEntry 6 }

    wfIpRfRipExportInterface OBJECT-TYPE
        SYNTAX	IpAddress
        ACCESS	read-only
        STATUS	mandatory
        DESCRIPTION
                "The optional outbound interface on which to apply this filter"
        ::= { wfIpRfRipExportEntry 7 }

    wfIpRfRipExportRipMetric OBJECT-TYPE
        SYNTAX	INTEGER(0..15)
        ACCESS	read-write
        STATUS	mandatory
        DESCRIPTION
                "The optional export RIP metric to apply to this filter.
                Zero means: use the route's actual cost. Only valid for propagate"
        ::= { wfIpRfRipExportEntry 8 }

    wfIpRfOspfImportTable OBJECT-TYPE
        SYNTAX	SEQUENCE OF WfIpRfOspfImportEntry
        ACCESS	not-accessible
        STATUS	mandatory
        DESCRIPTION
                "The list of OSPF Import Route Filter Rules in IP"
        ::= { wfIpGroup 10 }

    wfIpRfOspfImportEntry OBJECT-TYPE
        SYNTAX	WfIpRfOspfImportEntry
        ACCESS	not-accessible
        STATUS	mandatory
        DESCRIPTION
                "An entry in the OSPF Import Route Filter Table"
        INDEX	{ wfIpRfOspfImportAddress,
    		  wfIpRfOspfImportMask,
    		  wfIpRfOspfImportType,
    		  wfIpRfOspfImportTag }
        ::= { wfIpRfOspfImportTable 1 }

    WfIpRfOspfImportEntry ::= SEQUENCE {
    	    wfIpRfOspfImportCreate
    		INTEGER,
    	    wfIpRfOspfImportEnable
    		INTEGER,
    	    wfIpRfOspfImportAddress
    		IpAddress,
    	    wfIpRfOspfImportMask
    		IpAddress,
    	    wfIpRfOspfImportAction
    		INTEGER,
    	    wfIpRfOspfImportPreference
    		INTEGER,
    	    wfIpRfOspfImportType
    		INTEGER,
    	    wfIpRfOspfImportTag
    		Gauge
        }

    wfIpRfOspfImportCreate OBJECT-TYPE
        SYNTAX	INTEGER {
    		    create(1),
    		    delete(2)
    		}
        ACCESS	read-write
        STATUS	mandatory
        DESCRIPTION
                "Create/Delete parameter. Default is created.
                Users perform an SNMP SET operation on this
                object in order to create/delete this Rule."
        DEFVAL	{ create }
        ::= { wfIpRfOspfImportEntry 1 }

    wfIpRfOspfImportEnable OBJECT-TYPE
        SYNTAX	INTEGER {
    		    enable(1),
    		    disable(2)
    		}
        ACCESS	read-write
        STATUS	mandatory
        DESCRIPTION
                "Enable/Disable parameter. Default is enabled.
                Users perform an SNMP SET operation on this
                object in order to enable/disable this Rule."
        DEFVAL	{ enable }
        ::= { wfIpRfOspfImportEntry 2 }

    wfIpRfOspfImportAddress OBJECT-TYPE
        SYNTAX	IpAddress
        ACCESS	read-only
        STATUS	mandatory
        DESCRIPTION
                "The IP Address to which this filter applies"
        ::= { wfIpRfOspfImportEntry 3 }

    wfIpRfOspfImportMask OBJECT-TYPE
        SYNTAX	IpAddress
        ACCESS	read-only
        STATUS	mandatory
        DESCRIPTION
                "The Mask to which this filter applies. When combined
                with the Address, a range is specified for application
                of this rule"
        ::= { wfIpRfOspfImportEntry 4 }

    wfIpRfOspfImportAction OBJECT-TYPE
        SYNTAX	INTEGER {
    		    accept(1),
    		    ignore(3)
    		}
        ACCESS	read-write
        STATUS	mandatory
        DESCRIPTION
                "The Action of this Filter"
        DEFVAL	{ accept }
        ::= { wfIpRfOspfImportEntry 5 }

    wfIpRfOspfImportPreference OBJECT-TYPE
        SYNTAX	INTEGER(0..16)
        ACCESS	read-write
        STATUS	mandatory
        DESCRIPTION
                "The Preference associated with this filter - only valid if accept"
        DEFVAL	{ 1 }
        ::= { wfIpRfOspfImportEntry 6 }

    wfIpRfOspfImportType OBJECT-TYPE
        SYNTAX	INTEGER
        ACCESS	read-only
        STATUS	mandatory
        DESCRIPTION
                "The OSPF route Type to be concerned with. The valid values are null
                (any route type), 1 (OSPF external type 1), and 2 (OSPF external
                type 2)."
        ::= { wfIpRfOspfImportEntry 7 }

    wfIpRfOspfImportTag OBJECT-TYPE
        SYNTAX	Gauge
        ACCESS	read-only
        STATUS	mandatory
        DESCRIPTION
                "The OSPF Tag to be concerned with"
        ::= { wfIpRfOspfImportEntry 8 }

    wfIpRfOspfExportTable OBJECT-TYPE
        SYNTAX	SEQUENCE OF WfIpRfOspfExportEntry
        ACCESS	not-accessible
        STATUS	mandatory
        DESCRIPTION
                "The list of OSPF Export Route Filter Rules in IP"
        ::= { wfIpGroup 11 }

    wfIpRfOspfExportEntry OBJECT-TYPE
        SYNTAX	WfIpRfOspfExportEntry
        ACCESS	not-accessible
        STATUS	mandatory
        DESCRIPTION
                "An entry in the OSPF Export Route Filter Table"
        INDEX	{ wfIpRfOspfExportAddress,
    		  wfIpRfOspfExportMask,
    		  wfIpRfOspfExportFromProtocol }
        ::= { wfIpRfOspfExportTable 1 }

    WfIpRfOspfExportEntry ::= SEQUENCE {
    	    wfIpRfOspfExportCreate
    		INTEGER,
    	    wfIpRfOspfExportEnable
    		INTEGER,
    	    wfIpRfOspfExportAddress
    		IpAddress,
    	    wfIpRfOspfExportMask
    		IpAddress,
    	    wfIpRfOspfExportFromProtocol
    		INTEGER,
    	    wfIpRfOspfExportAction
    		INTEGER,
    	    wfIpRfOspfExportType
    		INTEGER,
    	    wfIpRfOspfExportTag
    		Gauge,
    	    wfIpRfOspfExportAutoTag
    		INTEGER
        }

    wfIpRfOspfExportCreate OBJECT-TYPE
        SYNTAX	INTEGER {
    		    create(1),
    		    delete(2)
    		}
        ACCESS	read-write
        STATUS	mandatory
        DESCRIPTION
                "Create/Delete parameter. Default is created.
                Users perform an SNMP SET operation on this
                object in order to create/delete this Rule."
        DEFVAL	{ create }
        ::= { wfIpRfOspfExportEntry 1 }

    wfIpRfOspfExportEnable OBJECT-TYPE
        SYNTAX	INTEGER {
    		    enable(1),
    		    disable(2)
    		}
        ACCESS	read-write
        STATUS	mandatory
        DESCRIPTION
                "Enable/Disable parameter. Default is enabled.
                Users perform an SNMP SET operation on this
                object in order to enable/disable this Rule."
        DEFVAL	{ enable }
        ::= { wfIpRfOspfExportEntry 2 }

    wfIpRfOspfExportAddress OBJECT-TYPE
        SYNTAX	IpAddress
        ACCESS	read-only
        STATUS	mandatory
        DESCRIPTION
                "The IP address to which this filter applies"
        ::= { wfIpRfOspfExportEntry 3 }

    wfIpRfOspfExportMask OBJECT-TYPE
        SYNTAX	IpAddress
        ACCESS	read-only
        STATUS	mandatory
        DESCRIPTION
                "The Mask for the Address Above. When combined
                with the Address, a range is specified for application
                of this filter rule"
        ::= { wfIpRfOspfExportEntry 4 }

    wfIpRfOspfExportFromProtocol OBJECT-TYPE
        SYNTAX	INTEGER {
    		    rip(1),
    		    egp(2),
    		    ospf(3),
    		    direct(4),
    		    static(5),
    		    bgp3(6)
    		}
        ACCESS	read-only
        STATUS	mandatory
        DESCRIPTION
                "The protocol from which this Information is derived"
        ::= { wfIpRfOspfExportEntry 5 }

    wfIpRfOspfExportAction OBJECT-TYPE
        SYNTAX	INTEGER {
    		    propa(2),
    		    ignore(3)
    		}
        ACCESS	read-write
        STATUS	mandatory
        DESCRIPTION
                "The action of this export filter"
        DEFVAL	{ propa }
        ::= { wfIpRfOspfExportEntry 6 }

    wfIpRfOspfExportType OBJECT-TYPE
        SYNTAX	INTEGER(0..2)
        ACCESS	read-write
        STATUS	mandatory
        DESCRIPTION
                "The ospf type to use when this filter matches"
        DEFVAL	{ 1 }
        ::= { wfIpRfOspfExportEntry 7 }

    wfIpRfOspfExportTag OBJECT-TYPE
        SYNTAX	Gauge
        ACCESS	read-write
        STATUS	mandatory
        DESCRIPTION
                "The ospf tag to use when this filter matches"
        ::= { wfIpRfOspfExportEntry 8 }

    wfIpRfOspfExportAutoTag OBJECT-TYPE
        SYNTAX	INTEGER {
    		    enable(1),
    		    disable(2)
    		}
        ACCESS	read-write
        STATUS	mandatory
        DESCRIPTION
                "BGP/OSPF automatic tag generation: if enabled, a tag will be
                generated according to the criteria in RFC 1364.  Only valid if
                wfIpRfOspfExportType is set.  If enabled, wfIpRfOspfExportTag
                is ignored."
        DEFVAL	{ disable }
        ::= { wfIpRfOspfExportEntry 9 }

    wfIpRfEgpImportTable OBJECT-TYPE
        SYNTAX	SEQUENCE OF WfIpRfEgpImportEntry
        ACCESS	not-accessible
        STATUS	mandatory
        DESCRIPTION
                "The list of Egp Import Route Filter Rules in IP"
        ::= { wfIpGroup 12 }

    wfIpRfEgpImportEntry OBJECT-TYPE
        SYNTAX	WfIpRfEgpImportEntry
        ACCESS	not-accessible
        STATUS	mandatory
        DESCRIPTION
                "An entry in the Egp Import Rule Table"
        INDEX	{ wfIpRfEgpImportAddress,
    		  wfIpRfEgpImportPeer,
    		  wfIpRfEgpImportAs,
    		  wfIpRfEgpImportGateway }
        ::= { wfIpRfEgpImportTable 1 }

    WfIpRfEgpImportEntry ::= SEQUENCE {
    	    wfIpRfEgpImportCreate
    		INTEGER,
    	    wfIpRfEgpImportEnable
    		INTEGER,
    	    wfIpRfEgpImportAddress
    		IpAddress,
    	    wfIpRfEgpImportMask
    		IpAddress,
    	    wfIpRfEgpImportAction
    		INTEGER,
    	    wfIpRfEgpImportPreference
    		INTEGER,
    	    wfIpRfEgpImportPeer
    		IpAddress,
    	    wfIpRfEgpImportAs
    		INTEGER,
    	    wfIpRfEgpImportGateway
    		IpAddress
        }

    wfIpRfEgpImportCreate OBJECT-TYPE
        SYNTAX	INTEGER {
    		    create(1),
    		    delete(2)
    		}
        ACCESS	read-write
        STATUS	mandatory
        DESCRIPTION
                "Create/Delete parameter. Default is created. Users perform an SNMP
                SET operation on this object in order to create/delete this Rule."
        DEFVAL	{ create }
        ::= { wfIpRfEgpImportEntry 1 }

    wfIpRfEgpImportEnable OBJECT-TYPE
        SYNTAX	INTEGER {
    		    enable(1),
    		    disable(2)
    		}
        ACCESS	read-write
        STATUS	mandatory
        DESCRIPTION
                "Enable/Disable parameter. Default is enabled. Users perform an SNMP
                SET operation on this object in order to enable/disable this Rule."
        DEFVAL	{ enable }
        ::= { wfIpRfEgpImportEntry 2 }

    wfIpRfEgpImportAddress OBJECT-TYPE
        SYNTAX	IpAddress
        ACCESS	read-only
        STATUS	mandatory
        DESCRIPTION
                "The advertised network to which this filter applies"
        ::= { wfIpRfEgpImportEntry 3 }

    wfIpRfEgpImportMask OBJECT-TYPE
        SYNTAX	IpAddress
        ACCESS	read-only
        STATUS	mandatory
        DESCRIPTION
                "The Mask of the Address to which this filter applies."
        ::= { wfIpRfEgpImportEntry 4 }

    wfIpRfEgpImportAction OBJECT-TYPE
        SYNTAX	INTEGER {
    		    accept(1),
    		    ignore(3)
    		}
        ACCESS	read-write
        STATUS	mandatory
        DESCRIPTION
                "The Action of this Filter"
        DEFVAL	{ accept }
        ::= { wfIpRfEgpImportEntry 5 }

    wfIpRfEgpImportPreference OBJECT-TYPE
        SYNTAX	INTEGER(0..16)
        ACCESS	read-write
        STATUS	mandatory
        DESCRIPTION
                "The Preference associated with this filter - only valid if accept"
        DEFVAL	{ 1 }
        ::= { wfIpRfEgpImportEntry 6 }

    wfIpRfEgpImportPeer OBJECT-TYPE
        SYNTAX	IpAddress
        ACCESS	read-only
        STATUS	mandatory
        DESCRIPTION
                "The Egp Peer to be to be concerned with"
        ::= { wfIpRfEgpImportEntry 7 }

    wfIpRfEgpImportAs OBJECT-TYPE
        SYNTAX	INTEGER
        ACCESS	read-only
        STATUS	mandatory
        DESCRIPTION
                "The Autonomous System number to be concerned with"
        ::= { wfIpRfEgpImportEntry 8 }

    wfIpRfEgpImportGateway OBJECT-TYPE
        SYNTAX	IpAddress
        ACCESS	read-only
        STATUS	mandatory
        DESCRIPTION
                "The EGP gateway to be concerned with"
        ::= { wfIpRfEgpImportEntry 9 }

    wfIpRfEgpExportTable OBJECT-TYPE
        SYNTAX	SEQUENCE OF WfIpRfEgpExportEntry
        ACCESS	not-accessible
        STATUS	mandatory
        DESCRIPTION
                "The list of Egp Export Route Filter Rules in IP"
        ::= { wfIpGroup 13 }

    wfIpRfEgpExportEntry OBJECT-TYPE
        SYNTAX	WfIpRfEgpExportEntry
        ACCESS	not-accessible
        STATUS	mandatory
        DESCRIPTION
                "An entry in the Egp Export Rule Table"
        INDEX	{ wfIpRfEgpExportAddress,
    		  wfIpRfEgpExportMask,
    		  wfIpRfEgpExportFromProtocol,
    		  wfIpRfEgpExportPeer,
    		  wfIpRfEgpExportOspfType,
    		  wfIpRfEgpExportOspfTag }
        ::= { wfIpRfEgpExportTable 1 }

    WfIpRfEgpExportEntry ::= SEQUENCE {
    	    wfIpRfEgpExportCreate
    		INTEGER,
    	    wfIpRfEgpExportEnable
    		INTEGER,
    	    wfIpRfEgpExportAddress
    		IpAddress,
    	    wfIpRfEgpExportMask
    		IpAddress,
    	    wfIpRfEgpExportFromProtocol
    		INTEGER,
    	    wfIpRfEgpExportAction
    		INTEGER,
    	    wfIpRfEgpExportPeer
    		IpAddress,
    	    wfIpRfEgpExportOspfType
    		INTEGER,
    	    wfIpRfEgpExportOspfTag
    		INTEGER,
    	    wfIpRfEgpExportInterface
    		IpAddress,
    	    wfIpRfEgpExportMetric
    		INTEGER
        }

    wfIpRfEgpExportCreate OBJECT-TYPE
        SYNTAX	INTEGER {
    		    create(1),
    		    delete(2)
    		}
        ACCESS	read-write
        STATUS	mandatory
        DESCRIPTION
                "Create/Delete parameter. Default is created. Users perform an SNMP
                SET operation on this object in order to create/delete this Rule."
        DEFVAL	{ create }
        ::= { wfIpRfEgpExportEntry 1 }

    wfIpRfEgpExportEnable OBJECT-TYPE
        SYNTAX	INTEGER {
    		    enable(1),
    		    disable(2)
    		}
        ACCESS	read-write
        STATUS	mandatory
        DESCRIPTION
                "Enable/Disable parameter. Default is enabled. Users perform an SNMP
                SET operation on this object in order to enable/disable this Rule."
        DEFVAL	{ enable }
        ::= { wfIpRfEgpExportEntry 2 }

    wfIpRfEgpExportAddress OBJECT-TYPE
        SYNTAX	IpAddress
        ACCESS	read-only
        STATUS	mandatory
        DESCRIPTION
                "The advertised network to which this filter applies"
        ::= { wfIpRfEgpExportEntry 3 }

    wfIpRfEgpExportMask OBJECT-TYPE
        SYNTAX	IpAddress
        ACCESS	read-only
        STATUS	mandatory
        DESCRIPTION
                "The Mask of the Address to which this filter applies."
        ::= { wfIpRfEgpExportEntry 4 }

    wfIpRfEgpExportFromProtocol OBJECT-TYPE
        SYNTAX	INTEGER {
    		    rip(1),
    		    egp(2),
    		    ospf(3),
    		    direct(4),
    		    static(5),
    		    bgp3(6)
    		}
        ACCESS	read-only
        STATUS	mandatory
        DESCRIPTION
                "The protocol from which this Information is derived"
        ::= { wfIpRfEgpExportEntry 5 }

    wfIpRfEgpExportAction OBJECT-TYPE
        SYNTAX	INTEGER {
    		    propa(2),
    		    ignore(3)
    		}
        ACCESS	read-write
        STATUS	mandatory
        DESCRIPTION
                "The action of this export filter"
        DEFVAL	{ propa }
        ::= { wfIpRfEgpExportEntry 6 }

    wfIpRfEgpExportPeer OBJECT-TYPE
        SYNTAX	IpAddress
        ACCESS	read-only
        STATUS	mandatory
        DESCRIPTION
                "The Egp Peer to be to be concerned with"
        ::= { wfIpRfEgpExportEntry 7 }

    wfIpRfEgpExportOspfType OBJECT-TYPE
        SYNTAX	INTEGER {
    		    ospfexttype1(1),
    		    ospfexttype2(2),
    		    ospfinttype(3)
    		}
        ACCESS	read-only
        STATUS	mandatory
        DESCRIPTION
                "The type of route being filtered. This field is only valid if the
                wfIpRfEgpExportFromProtocol is OSPF. Otherwise, the field is 0."
        ::= { wfIpRfEgpExportEntry 8 }

    wfIpRfEgpExportOspfTag OBJECT-TYPE
        SYNTAX	INTEGER
        ACCESS	read-only
        STATUS	mandatory
        DESCRIPTION
                "The tag of the route being filtered. This field is only valid if
                the wfIpRfEgpExportFromProtocol is OSPF. Otherwise, this field is 0."
        ::= { wfIpRfEgpExportEntry 9 }

    wfIpRfEgpExportInterface OBJECT-TYPE
        SYNTAX	IpAddress
        ACCESS	read-write
        STATUS	mandatory
        DESCRIPTION
                "The optional outbound interface on which to apply this filter"
        ::= { wfIpRfEgpExportEntry 10 }

    wfIpRfEgpExportMetric OBJECT-TYPE
        SYNTAX	INTEGER(0..255)
        ACCESS	read-write
        STATUS	mandatory
        DESCRIPTION
                "The optional export Egp metric to apply to this filter. Zero means:
                use the route's actual cost. Only valid for propagate "
        ::= { wfIpRfEgpExportEntry 11 }

    wfIpRfBgp3ImportTable OBJECT-TYPE
        SYNTAX	SEQUENCE OF WfIpRfBgp3ImportEntry
        ACCESS	not-accessible
        STATUS	mandatory
        DESCRIPTION
                "The table of BGP-3 Import Route Filter Rules"
        ::= { wfIpGroup 14 }

    wfIpRfBgp3ImportEntry OBJECT-TYPE
        SYNTAX	WfIpRfBgp3ImportEntry
        ACCESS	not-accessible
        STATUS	mandatory
        DESCRIPTION
                "An entry in the BGP-3 Import Rule Table"
        INDEX	{ wfIpRfBgp3ImportAddress,
    		  wfIpRfBgp3ImportMask,
    		  wfIpRfBgp3ImportPeerAs,
    		  wfIpRfBgp3ImportPeerAddress,
    		  wfIpRfBgp3ImportOrigAs,
    		  wfIpRfBgp3ImportRouteOrigin }
        ::= { wfIpRfBgp3ImportTable 1 }

    WfIpRfBgp3ImportEntry ::= SEQUENCE {
    	    wfIpRfBgp3ImportCreate
    		INTEGER,
    	    wfIpRfBgp3ImportEnable
    		INTEGER,
    	    wfIpRfBgp3ImportAddress
    		IpAddress,
    	    wfIpRfBgp3ImportMask
    		IpAddress,
    	    wfIpRfBgp3ImportAction
    		INTEGER,
    	    wfIpRfBgp3ImportPreference
    		INTEGER,
    	    wfIpRfBgp3ImportPeerAs
    		INTEGER,
    	    wfIpRfBgp3ImportPeerAddress
    		IpAddress,
    	    wfIpRfBgp3ImportOrigAs
    		INTEGER,
    	    wfIpRfBgp3ImportRouteOrigin
    		INTEGER,
    	    wfIpRfBgp3ImportBgp3Preference
    		Gauge
        }

    wfIpRfBgp3ImportCreate OBJECT-TYPE
        SYNTAX	INTEGER {
    		    create(1),
    		    delete(2)
    		}
        ACCESS	read-write
        STATUS	mandatory
        DESCRIPTION
                "Create/Delete parameter. if set to delete, the rule is removed."
        DEFVAL	{ create }
        ::= { wfIpRfBgp3ImportEntry 1 }

    wfIpRfBgp3ImportEnable OBJECT-TYPE
        SYNTAX	INTEGER {
    		    enable(1),
    		    disable(2)
    		}
        ACCESS	read-write
        STATUS	mandatory
        DESCRIPTION
                "Enable/Disable parameter. controls whether the rule is enabled
                or disabled."
        DEFVAL	{ enable }
        ::= { wfIpRfBgp3ImportEntry 2 }

    wfIpRfBgp3ImportAddress OBJECT-TYPE
        SYNTAX	IpAddress
        ACCESS	read-only
        STATUS	mandatory
        DESCRIPTION
                "The advertised network to which this filter applies. Zero implies
                `all networks' or the default route, based on
                wfIpRfBgp3ImportMask."
        ::= { wfIpRfBgp3ImportEntry 3 }

    wfIpRfBgp3ImportMask OBJECT-TYPE
        SYNTAX	IpAddress
        ACCESS	read-only
        STATUS	mandatory
        DESCRIPTION
                "The mask applied to wfIpRfBgp3ImportAddress. If zero, this filter
                applies to all networks. If the address is zero and this parameter
                is 255.255.255.255, this filter applies to the default route."
        ::= { wfIpRfBgp3ImportEntry 4 }

    wfIpRfBgp3ImportAction OBJECT-TYPE
        SYNTAX	INTEGER {
    		    accept(1),
    		    ignore(3)
    		}
        ACCESS	read-write
        STATUS	mandatory
        DESCRIPTION
                "The Action of this Filter"
        DEFVAL	{ ignore }
        ::= { wfIpRfBgp3ImportEntry 5 }

    wfIpRfBgp3ImportPreference OBJECT-TYPE
        SYNTAX	INTEGER(0..16)
        ACCESS	read-write
        STATUS	mandatory
        DESCRIPTION
                "The Preference associated with this filter - only valid if accept"
        DEFVAL	{ 1 }
        ::= { wfIpRfBgp3ImportEntry 6 }

    wfIpRfBgp3ImportPeerAs OBJECT-TYPE
        SYNTAX	INTEGER
        ACCESS	read-only
        STATUS	mandatory
        DESCRIPTION
                "The BGP-3 Peer's AS number (or zero if `any AS')"
        ::= { wfIpRfBgp3ImportEntry 7 }

    wfIpRfBgp3ImportPeerAddress OBJECT-TYPE
        SYNTAX	IpAddress
        ACCESS	read-only
        STATUS	mandatory
        DESCRIPTION
                "The IP address (not the peer ID) of the peer that this advertisement
                was received from (zero if `any peer')"
        ::= { wfIpRfBgp3ImportEntry 8 }

    wfIpRfBgp3ImportOrigAs OBJECT-TYPE
        SYNTAX	INTEGER
        ACCESS	read-only
        STATUS	mandatory
        DESCRIPTION
                "The AS number of the BGP-3 gateway that originated the route
                (or zero for `any AS')"
        ::= { wfIpRfBgp3ImportEntry 9 }

    wfIpRfBgp3ImportRouteOrigin OBJECT-TYPE
        SYNTAX	INTEGER {
    		    igp(1),
    		    egp(2),
    		    incomplete(3)
    		}
        ACCESS	read-only
        STATUS	mandatory
        DESCRIPTION
                "A value for the ORIGIN path attribute (or zero if not applicable)"
        ::= { wfIpRfBgp3ImportEntry 10 }

    wfIpRfBgp3ImportBgp3Preference OBJECT-TYPE
        SYNTAX	Gauge
        ACCESS	read-write
        STATUS	mandatory
        DESCRIPTION
                "The Preference associated with this filter for comparison to
                other BGP routes only - only valid if accept"
        DEFVAL	{ 1 }
        ::= { wfIpRfBgp3ImportEntry 11 }

    wfIpRfBgp3ExportTable OBJECT-TYPE
        SYNTAX	SEQUENCE OF WfIpRfBgp3ExportEntry
        ACCESS	not-accessible
        STATUS	mandatory
        DESCRIPTION
                "The table of BGP-3 Export Route Filter Rules"
        ::= { wfIpGroup 15 }

    wfIpRfBgp3ExportEntry OBJECT-TYPE
        SYNTAX	WfIpRfBgp3ExportEntry
        ACCESS	not-accessible
        STATUS	mandatory
        DESCRIPTION
                "An entry in the BGP-3 Export Rule Table"
        INDEX	{ wfIpRfBgp3ExportAddress,
    		  wfIpRfBgp3ExportMask,
    		  wfIpRfBgp3ExportFromProtocol,
    		  wfIpRfBgp3ExportPeerAs,
    		  wfIpRfBgp3ExportPeerAddress,
    		  wfIpRfBgp3ExportOspfType,
    		  wfIpRfBgp3ExportOspfTag }
        ::= { wfIpRfBgp3ExportTable 1 }

    WfIpRfBgp3ExportEntry ::= SEQUENCE {
    	    wfIpRfBgp3ExportCreate
    		INTEGER,
    	    wfIpRfBgp3ExportEnable
    		INTEGER,
    	    wfIpRfBgp3ExportAddress
    		IpAddress,
    	    wfIpRfBgp3ExportMask
    		IpAddress,
    	    wfIpRfBgp3ExportFromProtocol
    		INTEGER,
    	    wfIpRfBgp3ExportAction
    		INTEGER,
    	    wfIpRfBgp3ExportPeerAs
    		INTEGER,
    	    wfIpRfBgp3ExportPeerAddress
    		IpAddress,
    	    wfIpRfBgp3ExportOspfType
    		INTEGER,
    	    wfIpRfBgp3ExportOspfTag
    		INTEGER,
    	    wfIpRfBgp3ExportUseMetric
    		INTEGER,
    	    wfIpRfBgp3ExportInterAsMetric
    		INTEGER,
    	    wfIpRfBgp3ExportOrigin
    		INTEGER,
    	    wfIpRfBgp3ExportNeighAs
    		INTEGER
        }

    wfIpRfBgp3ExportCreate OBJECT-TYPE
        SYNTAX	INTEGER {
    		    create(1),
    		    delete(2)
    		}
        ACCESS	read-write
        STATUS	mandatory
        DESCRIPTION
                "Create/Delete: if set to delete, the rule is removed"
        DEFVAL	{ create }
        ::= { wfIpRfBgp3ExportEntry 1 }

    wfIpRfBgp3ExportEnable OBJECT-TYPE
        SYNTAX	INTEGER {
    		    enable(1),
    		    disable(2)
    		}
        ACCESS	read-write
        STATUS	mandatory
        DESCRIPTION
                "Enable/Disable: controls whether the rule is enabled or disabled"
        DEFVAL	{ enable }
        ::= { wfIpRfBgp3ExportEntry 2 }

    wfIpRfBgp3ExportAddress OBJECT-TYPE
        SYNTAX	IpAddress
        ACCESS	read-only
        STATUS	mandatory
        DESCRIPTION
                "The advertised network to which this filter applies. Zero implies
                `all networks' or the default route, based on
                 wfIpRfBgp3ExportMask."
        ::= { wfIpRfBgp3ExportEntry 3 }

    wfIpRfBgp3ExportMask OBJECT-TYPE
        SYNTAX	IpAddress
        ACCESS	read-only
        STATUS	mandatory
        DESCRIPTION
                "The mask applied to wfIpRfBgp3ExportAddress. If zero, this filter
                applies to all networks. If the address is zero and this parameter
                is 255.255.255.255, this filter applies to the default route."
        ::= { wfIpRfBgp3ExportEntry 4 }

    wfIpRfBgp3ExportFromProtocol OBJECT-TYPE
        SYNTAX	INTEGER {
    		    rip(1),
    		    egp(2),
    		    ospf(3),
    		    direct(4),
    		    static(5),
    		    bgp3(6)
    		}
        ACCESS	read-only
        STATUS	mandatory
        DESCRIPTION
                "The protocol from which this Information is derived"
        ::= { wfIpRfBgp3ExportEntry 5 }

    wfIpRfBgp3ExportAction OBJECT-TYPE
        SYNTAX	INTEGER {
    		    propa(2),
    		    ignore(3),
    		    aggregate(4)
    		}
        ACCESS	read-write
        STATUS	mandatory
        DESCRIPTION
                "The action of this export filter;
                if IP_RF_BGP3_EXP_ACTION_AGGREGATE action, the default
                route, 0.0.0.0, is advertised instead networks that match
                this filter"
        DEFVAL	{ ignore }
        ::= { wfIpRfBgp3ExportEntry 6 }

    wfIpRfBgp3ExportPeerAs OBJECT-TYPE
        SYNTAX	INTEGER
        ACCESS	read-only
        STATUS	mandatory
        DESCRIPTION
                "The AS number to which the network advertisement is going (zero
                if `any AS')"
        ::= { wfIpRfBgp3ExportEntry 7 }

    wfIpRfBgp3ExportPeerAddress OBJECT-TYPE
        SYNTAX	IpAddress
        ACCESS	read-only
        STATUS	mandatory
        DESCRIPTION
                "The IP address (not the peer ID) of the peer that this advertisement
                is going to (zero if `any peer')"
        ::= { wfIpRfBgp3ExportEntry 8 }

    wfIpRfBgp3ExportOspfType OBJECT-TYPE
        SYNTAX	INTEGER {
    		    ospfexttype1(1),
    		    ospfexttype2(2),
    		    ospfinttype(3)
    		}
        ACCESS	read-only
        STATUS	mandatory
        DESCRIPTION
                "The type of route being filtered. This field is only valid if the
                wfIpRfEgpExportFromProtocol is OSPF. Otherwise, the field is 0."
        ::= { wfIpRfBgp3ExportEntry 9 }

    wfIpRfBgp3ExportOspfTag OBJECT-TYPE
        SYNTAX	INTEGER
        ACCESS	read-only
        STATUS	mandatory
        DESCRIPTION
                "The OSPF tag of the route being filtered. This field is only valid
                if the wfIpRfBgp3ExportFromProtocol is OSPF and
                wfIpRfBgp3ExportOspfType is external type 1 or 2. Otherwise,
                this field is 0."
        ::= { wfIpRfBgp3ExportEntry 10 }

    wfIpRfBgp3ExportUseMetric OBJECT-TYPE
        SYNTAX	INTEGER {
    		    none(1),
    		    specified(2),
    		    originating(3)
    		}
        ACCESS	read-write
        STATUS	mandatory
        DESCRIPTION
                "Determines whether or not an INTER_AS_METRIC will be advertised
                for the associated network(s).  none (1) indicates that no
                metric will be advertised.  specified (2) indicates that the
                value in wfIpRfBgp3ExportInterAsMetric will be used.
                originating (3) indicates that the metric from the originating
                protocol will be used.  Only valid for propagate."
        DEFVAL	{ none }
        ::= { wfIpRfBgp3ExportEntry 11 }

    wfIpRfBgp3ExportInterAsMetric OBJECT-TYPE
        SYNTAX	INTEGER(0..65535)
        ACCESS	read-write
        STATUS	mandatory
        DESCRIPTION
                "If wfIpRfBgp3ExportUseMetric is set to specified (2),
                this is the value that will be used for the INTER_AS_METRIC.
                Only valid for propagate."
        ::= { wfIpRfBgp3ExportEntry 12 }

    wfIpRfBgp3ExportOrigin OBJECT-TYPE
        SYNTAX	INTEGER(0..3)
        ACCESS	read-write
        STATUS	mandatory
        DESCRIPTION
                "The value to use for the ORIGIN path attribute when advertising
                this route (zero means `do according to default'). Only valid for
                propagate action. Only valid if route origin is RIP or STATIC
                (ignored otherwise)."
        ::= { wfIpRfBgp3ExportEntry 13 }

    wfIpRfBgp3ExportNeighAs OBJECT-TYPE
        SYNTAX	INTEGER(0..65535)
        ACCESS	read-write
        STATUS	mandatory
        DESCRIPTION
                "If action is propagate, route origin is RIP or STATIC, and
                ExportOrigin is EGP, this AS number is used as the EGP neighbor
                AS number when constructing the AS-PATH (ignored otherwise)."
        ::= { wfIpRfBgp3ExportEntry 14 }

    END  -- Wellfleet-RF-MIB
