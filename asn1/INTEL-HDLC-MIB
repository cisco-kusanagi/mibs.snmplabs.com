INTEL-HDLC-MIB DEFINITIONS ::= BEGIN


-- Copyright (C) 1997 Intel Corporation. All rights reserved.
--
-- HDLC MIB, 10-22-1997
--
-- Proprietary MIB containing information about HDLC errors.
--
-- Change History:
-- 97-10-22 Initial version
-- 97-10-22 Scanet definitions had sneaked into the file, now
--          replaced by their Intel counterparts.

IMPORTS
    mib2ext                    FROM INTEL-GEN-MIB
    OBJECT-TYPE                FROM RFC-1212;

    hdlc                       OBJECT IDENTIFIER ::= { mib2ext 30 }
    hdlcMonitor                OBJECT IDENTIFIER ::= { hdlc 1 }

hdlcMonitorTable OBJECT-TYPE
    SYNTAX SEQUENCE OF HdlcMonitorEntry
    ACCESS not-accessible
    STATUS mandatory
    DESCRIPTION "The HDLC error counters."
    ::= { hdlcMonitor 1 }

hdlcMonitorEntry OBJECT-TYPE
    SYNTAX HdlcMonitorEntry
    ACCESS not-accessible
    STATUS mandatory
    DESCRIPTION ""
    INDEX { hdlcMonitorIndex }
    ::= { hdlcMonitorTable 1 }

HdlcMonitorEntry ::= SEQUENCE {
                        hdlcMonitorIndex
                           INTEGER,
                        hdlcMonitorReceiverChecksumErrors
                           INTEGER,
                        hdlcMonitorReceiverGiants
                           INTEGER,
                        hdlcMonitorReceiverDwarves
                           INTEGER,
                        hdlcMonitorReceiverAborts
                           INTEGER,
                        hdlcMonitorReceiverOverruns
                           INTEGER,
                        hdlcMonitorReceiverMisalignments
                           INTEGER,
                        hdlcMonitorTransmitterUnderruns
                           INTEGER,
                        hdlcMonitorReceiverAsyncParityErrors
                           INTEGER,
                        hdlcMonitorReceiverAsyncFramingErrors
                           INTEGER,
                        hdlcMonitorReceiverAsyncBreaks
                           INTEGER
                        }

hdlcMonitorIndex OBJECT-TYPE
    SYNTAX INTEGER
    ACCESS read-only
    STATUS mandatory
    DESCRIPTION "The IfIndex for the layer that these counters apply to.
                 The index may belong to the encapsulation layer (e.g. PPP),
                 an individual B-channel (ISDN), a B-channel Bundle (ISDN)
                 or the HDLC layer of a V.x WAN link."
    ::= { hdlcMonitorEntry 1 }

hdlcMonitorReceiverChecksumErrors OBJECT-TYPE
    SYNTAX INTEGER
    ACCESS read-only
    STATUS mandatory
    DESCRIPTION "The number of CRC errors."
    ::= { hdlcMonitorEntry 2 }

hdlcMonitorReceiverGiants OBJECT-TYPE
    SYNTAX INTEGER
    ACCESS read-only
    STATUS mandatory
    DESCRIPTION "The number of frames whose length exceeded the
                 maximum allowed."
    ::= { hdlcMonitorEntry 3 }

hdlcMonitorReceiverDwarves OBJECT-TYPE
    SYNTAX INTEGER
    ACCESS read-only
    STATUS mandatory
    DESCRIPTION "The number of frames that were shorter than the
                 minimum allowed."
    ::= { hdlcMonitorEntry 4 }

hdlcMonitorReceiverAborts OBJECT-TYPE
    SYNTAX INTEGER
    ACCESS read-only
    STATUS mandatory
    DESCRIPTION "The number of aborted frames."
    ::= { hdlcMonitorEntry 5 }

hdlcMonitorReceiverOverruns OBJECT-TYPE
    SYNTAX INTEGER
    ACCESS read-only
    STATUS mandatory
    DESCRIPTION "The number of frames lost due to a lack of resources."
    ::= { hdlcMonitorEntry 6 }

hdlcMonitorReceiverMisalignments OBJECT-TYPE
    SYNTAX INTEGER
    ACCESS read-only
    STATUS mandatory
    DESCRIPTION "The number of frames that did not end with a full byte (octet)."
    ::= { hdlcMonitorEntry 7 }

hdlcMonitorTransmitterUnderruns OBJECT-TYPE
    SYNTAX INTEGER
    ACCESS read-only
    STATUS mandatory
    DESCRIPTION "The number of frames not properly sent due to
                 the transmit channel being starved from data."
    ::= { hdlcMonitorEntry 8 }

hdlcMonitorReceiverAsyncParityErrors OBJECT-TYPE
    SYNTAX INTEGER
    ACCESS read-only
    STATUS mandatory
    DESCRIPTION "The number of frames received with parity errors."
    ::= { hdlcMonitorEntry 9 }

hdlcMonitorReceiverAsyncFramingErrors OBJECT-TYPE
    SYNTAX INTEGER
    ACCESS read-only
    STATUS mandatory
    DESCRIPTION "The number of frames received with framing errors."
    ::= { hdlcMonitorEntry 10 }

hdlcMonitorReceiverAsyncBreaks OBJECT-TYPE
    SYNTAX INTEGER
    ACCESS read-only
    STATUS mandatory
    DESCRIPTION "The number of times that the receiving data is held
                 in the spacing state for longer than a full word
                 transmission time (data discarded)."
    ::= { hdlcMonitorEntry 11 }

END
