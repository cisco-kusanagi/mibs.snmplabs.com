CXR-CFIP-MIB
  
  DEFINITIONS ::= BEGIN


   IMPORTS
    enterprises, Gauge	FROM RFC1155-SMI
    OBJECT-TYPE	FROM RFC-1212;

  --*************************************************************************
  -- Define the enterprise number as allocated by the internet authority
  cxr OBJECT IDENTIFIER ::= { enterprises 1425 }

  --*************************************************************************
  --*************************************************************************
  -- the overall structure of the MIB
  --*************************************************************************
  --*************************************************************************

  cfip		OBJECT IDENTIFIER ::= { cxr 800 }


  --*************************************************************************
	-- First Group: System
	
  cfSystem      OBJECT IDENTIFIER ::= { cfip  1 }

  --*************************************************************************

  cfTime		     OBJECT-TYPE
    SYNTAX      DisplayString
    ACCESS          read-write
    STATUS          current
    DESCRIPTION     "HH:MM:SS example: 10:05:00"
    ::= { cfSystem 1 }

  cfDate			   OBJECT-TYPE
    SYNTAX      DisplayString
    ACCESS          read-write
    STATUS          current
    DESCRIPTION     "AAAA-MM-JJ example: 2000-01-01"
    ::= { cfSystem 2 }

  cfSiteID     OBJECT-TYPE
    SYNTAX      DisplayString
    ACCESS          read-write
    STATUS          current
    DESCRIPTION     "Site Identification"
    ::= { cfSystem 3 }

  cfReportNumber     OBJECT-TYPE
    SYNTAX      DisplayString
    ACCESS          read-write
    STATUS          current
    DESCRIPTION     "Phone Number"
    ::= { cfSystem 4 }

  cfReportEnable     OBJECT-TYPE
    SYNTAX      INTEGER	{
                   	enable(1),
                   	disable(0)
                		}
    ACCESS          read-write
    STATUS          current
    DESCRIPTION
    "Validate phone number
	    0: not validate
  	  1: validate"
    ::= { cfSystem 5 }

  cfIpAddress     OBJECT-TYPE
		SYNTAX				IpAddress
    ACCESS          read-write
    STATUS          current
    DESCRIPTION     "CFIP IP address"
    ::= { cfSystem 7 }

  cfNetmask     OBJECT-TYPE
		SYNTAX				IpAddress
    ACCESS          read-write
    STATUS          current
    DESCRIPTION     "CFIP Netmask address"
    ::= { cfSystem 8 }

  cfEthAddress     OBJECT-TYPE
    SYNTAX      OCTET STRING
    ACCESS          read-only
    STATUS          current
    DESCRIPTION     "CFIP Mac Address"
    ::= { cfSystem 9 }

  cfSnmpTrap     OBJECT-TYPE
		SYNTAX				IpAddress
    ACCESS          read-write
    STATUS          current
    DESCRIPTION     "Trap IP Address"
    ::= { cfSystem  10 }

  cfRevision     OBJECT-TYPE
    SYNTAX      DisplayString
    ACCESS          read-only
    STATUS          current
    DESCRIPTION     "Version Software and options"
    ::= { cfSystem  11 }

  cfShelfActive     OBJECT-TYPE
    SYNTAX      INTEGER
    ACCESS          read-only
    STATUS          current
    DESCRIPTION     "Number of active shelves"
    ::= { cfSystem  12 }

  cfReset     OBJECT-TYPE
    SYNTAX      INTEGER
    ACCESS          read-write
    STATUS          current
    DESCRIPTION     "Reset the CFIP Card"
    ::= { cfSystem  13 }

  --*************************************************************************
	-- Second Group: Alarm
	
  cfAlarm      OBJECT IDENTIFIER ::= { cfip  2 }

  --*************************************************************************

  alAvailable     OBJECT-TYPE
    SYNTAX      INTEGER
    ACCESS          read-only
    STATUS          current
    DESCRIPTION     "Number of free alarms"
    ::= { cfAlarm	1 }

  alActive     OBJECT-TYPE
    SYNTAX      INTEGER
    ACCESS          read-only
    STATUS          current
    DESCRIPTION     "Number of active alarms"
    ::= { cfAlarm	2 }

  alRetired     OBJECT-TYPE
    SYNTAX      INTEGER
    ACCESS          read-only
    STATUS          current
    DESCRIPTION     "Number of retired alarms"
    ::= { cfAlarm	3 }

  alActiveAck   OBJECT-TYPE
    SYNTAX      INTEGER
    ACCESS          write-only
    STATUS          current
    DESCRIPTION     "Retire all active alarms"
    ::= { cfAlarm	4 }

  alActiveZap     OBJECT-TYPE
    SYNTAX      INTEGER
    ACCESS          write-only
    STATUS          current
    DESCRIPTION     "Clear all active alarms"
    ::= { cfAlarm	5 }

  alRetiredZap     OBJECT-TYPE
    SYNTAX      INTEGER
    ACCESS          write-only
    STATUS          current
    DESCRIPTION     "Clear all retired alarms"
    ::= { cfAlarm	6 }

  --*************************************************************************
	-- Third Group: Slot
	
  --*************************************************************************
shelfTable OBJECT-TYPE
    			     	SYNTAX SEQUENCE OF ShelfEntry
         				ACCESS not-accessible
				        STATUS mandatory
                DESCRIPTION
				"A table containing all the possible shelves"

        ::= { cfip 3 }

shelfEntry OBJECT-TYPE
                SYNTAX ShelfEntry
                ACCESS not-accessible
                STATUS mandatory
    						DESCRIPTION
        "Shelf index 1 to 16 possible
        1 is the master and others are slaves"

                INDEX { shelfIndex }
        ::= { shelfTable 1 }

ShelfEntry ::= SEQUENCE {
                shelfIndex 		INTEGER,
								shSlotActive 	INTEGER,
								shelfPowerLeft 	INTEGER,
								shelfPowerRight 	INTEGER
                }


shelfIndex OBJECT-TYPE
                SYNTAX INTEGER
                ACCESS read-only
                STATUS mandatory
                DESCRIPTION
	"Reference Shelf Number"
        ::= { shelfEntry 1 }

shSlotActive OBJECT-TYPE
    SYNTAX	INTEGER (1..16)
    ACCESS	read-only
    STATUS	current
    DESCRIPTION
	"Number of active Slots in the Shelf"
    ::= { shelfEntry 2 }


shelfPowerLeft OBJECT-TYPE
    SYNTAX INTEGER 	{
                   	ok(1),
                   	bad(0)
                		}
    ACCESS	read-only
    STATUS	current
    DESCRIPTION
	"State of Left power supply
	1: OK
	0: BAD"
    ::= { shelfEntry 3 }

shelfPowerRight OBJECT-TYPE
    SYNTAX INTEGER 	{
                   	ok(1),
                   	bad(0)
                		}
    ACCESS	read-only
    STATUS	current
    DESCRIPTION
	"State of Right power supply
	1: OK
	0: BAD"
    ::= { shelfEntry 4 }

  --*************************************************************************
	-- Forth Group: Slot
	
  --*************************************************************************
slotTable OBJECT-TYPE
    			     	SYNTAX SEQUENCE OF SlotEntry
         				ACCESS not-accessible
				        STATUS mandatory
                DESCRIPTION
	"A table containing all the possible slots"

        ::= { cfip 4 }

slotEntry OBJECT-TYPE
                SYNTAX SlotEntry
                ACCESS not-accessible
                STATUS mandatory
    						DESCRIPTION
        "Slot index: 1 to 16 for 1st shelf, 17 to 33 for 2nd shelf ,...
        i.e. 256 maximum"
                INDEX { shelfSlotIndex }
        ::= { slotTable 1 }

SlotEntry ::= SEQUENCE {
          shelfSlotIndex 		INTEGER,
					shelfIndex2		INTEGER,
					slotIndex			INTEGER,
    			portActive		INTEGER,
			    product				DisplayString
    }

shelfSlotIndex OBJECT-TYPE
                SYNTAX INTEGER
                ACCESS read-only
                STATUS mandatory
                DESCRIPTION
	"Reference ShelfSlot Number"
        ::= { slotEntry 1 }

shelfIndex2 OBJECT-TYPE
                SYNTAX INTEGER
                ACCESS read-only
                STATUS mandatory
                DESCRIPTION
	"Reference Shelf Number"
        ::= { slotEntry 2 }

slotIndex OBJECT-TYPE
                SYNTAX INTEGER
                ACCESS read-only
                STATUS mandatory
                DESCRIPTION
	"Reference Slot Number"
        ::= { slotEntry 3 }

portActive OBJECT-TYPE
    SYNTAX	INTEGER (1..16)
    ACCESS	read-only
    STATUS	current
    DESCRIPTION
	"Number of active Port"
    ::= { slotEntry 4 }

product     OBJECT-TYPE
    SYNTAX      DisplayString
    ACCESS          read-only
    STATUS          current
    DESCRIPTION     "Type of card in the slot"
    ::= { slotEntry 5 }

  --*************************************************************************
	-- Fifth Group: Port
	
  --*************************************************************************
portTable OBJECT-TYPE
    			     	SYNTAX SEQUENCE OF PortEntry
         				ACCESS not-accessible
				        STATUS mandatory
                DESCRIPTION
	"A table containing all the possible ports"

        ::= { cfip 5 }

portEntry OBJECT-TYPE
                SYNTAX PortEntry
                ACCESS not-accessible
                STATUS mandatory
    						DESCRIPTION
        "port index: 1 to 4 for 1st slot,5 to 9 for 2nd slot ..."
                INDEX { shelfSlotPortIndex }
        ::= { portTable 1 }

PortEntry ::= SEQUENCE {
    shelfSlotPortIndex	INTEGER	,
    shelfNumber			INTEGER	,
    slotNumber			INTEGER	,
    portNumber			INTEGER	,
    id						DisplayString ,
		deviceStatus	INTEGER,
		mode					INTEGER,
		dteSpeed			Gauge,
		dceSpeed			Gauge,
		eiadtr				INTEGER,
		eiacd					INTEGER,
		onlineSQ 			INTEGER,
		onlineLVL			INTEGER,
		onlineDialed	DisplayString,
		dialElapse		TimeTicks,
		dialActive		TimeTicks,
		dialInactive	TimeTicks,
		dialOrgCall		COUNTER,
		dialAnsCall		COUNTER,
		dialOrgFail		COUNTER,
		dialAnsFail		COUNTER,
		leaseElapse		TimeTicks,
		leaseActive		TimeTicks,
		leaseDown			TimeTicks,
		leaseRetrain	COUNTER,
		leaseUADBU		COUNTER,
    reset					INTEGER
}

shelfSlotPortIndex OBJECT-TYPE
                SYNTAX INTEGER
                ACCESS read-only
                STATUS mandatory
                DESCRIPTION
	"Reference Shelf*Slot*Port Number"
        ::= { portEntry 1 }

shelfNumber OBJECT-TYPE
                SYNTAX INTEGER
                ACCESS read-only
                STATUS mandatory
                DESCRIPTION
	"Reference Shelf Number"
        ::= { portEntry 2 }

slotNumber OBJECT-TYPE
                SYNTAX INTEGER
                ACCESS read-only
                STATUS mandatory
                DESCRIPTION
	"Reference Slot Number"
        ::= { portEntry 3 }

portNumber OBJECT-TYPE
                SYNTAX INTEGER
                ACCESS read-only
                STATUS mandatory
                DESCRIPTION
	"Reference Port Number"
        ::= { portEntry 4 }



id    OBJECT-TYPE
    SYNTAX      		DisplayString
    ACCESS          read-write
    STATUS          current
    DESCRIPTION     "Identification of the Port"
    ::= { portEntry 5 }

deviceStatus OBJECT-TYPE
    SYNTAX	INTEGER {
    								absent(0),
    								idle(1),
    								leased(2),
    								uadbu-connection-active(3),
    								leased-line-connection-failed(4),
    								dial-line-connection-active(5),
    								busy-out(6),
    								bad-device(7),
    								test-mode(8),
    								isdn-inactive(9),
    								isdn-active(10),
    								isdn-failed(11)    								
    								}
    ACCESS	read-only
    STATUS	current
    DESCRIPTION

	"State of the connection"
    ::= { portEntry 6 }

mode OBJECT-TYPE
    SYNTAX	INTEGER {
    								idle(0),
    								modem(1),
    								modem-V42(2),
    								fax(3),
    								v14(4),
    								v110(5),
    								v120(6),
    								ppp(7),
    								dsu(8)
    								}
    ACCESS	read-only
    STATUS	current
    DESCRIPTION
							"Connection mode"
    ::= { portEntry 7 }

dteSpeed OBJECT-TYPE
    SYNTAX      Gauge
    ACCESS      read-only
    STATUS      current
    DESCRIPTION "DTE speed"
    ::= { portEntry 8 }

dceSpeed OBJECT-TYPE
    SYNTAX      Gauge
    ACCESS      read-only
    STATUS       current
    DESCRIPTION "DCE speed"
    ::= { portEntry 9 }

eiadtr OBJECT-TYPE
    SYNTAX      INTEGER {
    										off(0),
    										on(1)
    										}
    ACCESS      read-only
    STATUS          current
    DESCRIPTION     "DTR state"
    ::= { portEntry 10 }

eiacd OBJECT-TYPE
    SYNTAX      INTEGER {
    										off(0),
    										on(1)
    										}
    ACCESS      read-only
    STATUS          current
    DESCRIPTION     "Carrier Detect state"
    ::= { portEntry 11 }

onlineSQ OBJECT-TYPE
    SYNTAX      INTEGER
    ACCESS      read-only
    STATUS          current
    DESCRIPTION     "Connection Signal Quality"
    ::= { portEntry 12 }

onlineLVL	OBJECT-TYPE
    SYNTAX      INTEGER
    ACCESS      read-only
    STATUS          current
    DESCRIPTION     "On line Level"
    ::= { portEntry 13 }

onlineDialed    OBJECT-TYPE
    SYNTAX      DisplayString
    ACCESS          read-only
    STATUS          current
    DESCRIPTION     "Last dialled number"
    ::= { portEntry 14 }


dialElapse	OBJECT-TYPE
    SYNTAX      TimeTicks
    ACCESS      read-only
    STATUS          current
    DESCRIPTION     "The time (in seconds) since the port was last
                       re-initialized."
    ::= { portEntry 16 }

dialActive	OBJECT-TYPE
    SYNTAX      TimeTicks
    ACCESS      read-only
    STATUS          current
    DESCRIPTION     "Dial Line active Time in seconds"
    ::= { portEntry 17 }

dialInactive	OBJECT-TYPE
    SYNTAX      TimeTicks
    ACCESS      read-only
    STATUS          current
    DESCRIPTION     "Dial Line inactive Time in seconds"
    ::= { portEntry 18 }

dialOrgCall	OBJECT-TYPE
    SYNTAX      COUNTER
    ACCESS      read-only
    STATUS          current
    DESCRIPTION     "Number of connections in calling mode"
    ::= { portEntry 19 }

dialAnsCall	OBJECT-TYPE
    SYNTAX      COUNTER
    ACCESS      read-only
    STATUS          current
    DESCRIPTION     "Number of connections in Answer mode"
    ::= { portEntry 20 }

dialOrgFail	OBJECT-TYPE
    SYNTAX      COUNTER
    ACCESS      read-only
    STATUS          current
    DESCRIPTION     "Number of connections errors in calling mode"
    ::= { portEntry 21 }

dialAnsFail	OBJECT-TYPE
    SYNTAX      COUNTER
    ACCESS      read-only
    STATUS          current
    DESCRIPTION     "Number of connections errors in Answer mode"
    ::= { portEntry 22 }

leaseElapse	OBJECT-TYPE
    SYNTAX      TimeTicks
    ACCESS      read-only
    STATUS          current
    DESCRIPTION     "The time (in second) since the port was last
                      re-initialized."
    ::= { portEntry 23 }

leaseActive	OBJECT-TYPE
    SYNTAX      TimeTicks
    ACCESS      read-only
    STATUS          current
    DESCRIPTION     "Lease Line active Time in seconds"
    ::= { portEntry 24 }

leaseDown	OBJECT-TYPE
    SYNTAX      TimeTicks
    ACCESS      read-only
    STATUS          current
    DESCRIPTION     "Lease Line inactive Time in seconds"
    ::= { portEntry 25 }

leaseRetrain	OBJECT-TYPE
    SYNTAX      INTEGER
    ACCESS      read-only
    STATUS          current
    DESCRIPTION     "Number of Lease Line Retrain"
    ::= { portEntry 26 }

leaseUADBU	OBJECT-TYPE
    SYNTAX      INTEGER
    ACCESS      read-only
    STATUS          current
    DESCRIPTION     "Number of unattended dial backup"
    ::= { portEntry 27 }

reset			OBJECT-TYPE
    SYNTAX      INTEGER
    ACCESS      read-write
    STATUS          current
    DESCRIPTION     "Cause a reset of the port ( like an ATZ command)"
    ::= { portEntry 28 }


  --*************************************************************************
        -- Alarm : devices
  --*************************************************************************        

 alarmUndefined TRAP-TYPE
	ENTERPRISE  cxr
    	VARIABLES   { shelfIndex, slotIndex , portIndex }
   	DESCRIPTION "Device Alarm Undefined"
    	::= 0
 newlyPowered TRAP-TYPE
	ENTERPRISE  cxr
    	VARIABLES   { shelfIndex, slotIndex , portIndex }
   	DESCRIPTION "Device Newly powered"
    	::= 1
 failsSelfTest TRAP-TYPE
	ENTERPRISE  cxr
    	VARIABLES   { shelfIndex, slotIndex , portIndex }
   	DESCRIPTION "Fails self test"
    	::= 2
 eventOverflow TRAP-TYPE
	ENTERPRISE  cxr
    	VARIABLES   { shelfIndex, slotIndex , portIndex }
   	DESCRIPTION "Event overflow"
    	::= 3
 uadbuActive TRAP-TYPE
	ENTERPRISE  cxr
    	VARIABLES   { shelfIndex, slotIndex , portIndex }
   	DESCRIPTION "UADBU active"
    	::= 4
 uadbuInactive TRAP-TYPE
	ENTERPRISE  cxr
    	VARIABLES   { shelfIndex, slotIndex , portIndex }
   	DESCRIPTION "UADBU inactive"
    	::= 5
 inLAL TRAP-TYPE
	ENTERPRISE  cxr
    	VARIABLES   { shelfIndex, slotIndex , portIndex }
   	DESCRIPTION "In LAL"
    	::= 6
 inDLB TRAP-TYPE
	ENTERPRISE  cxr
    	VARIABLES   { shelfIndex, slotIndex , portIndex }
   	DESCRIPTION "In DLB"
    	::= 7
 inRDL TRAP-TYPE
	ENTERPRISE  cxr
    	VARIABLES   { shelfIndex, slotIndex , portIndex }
   	DESCRIPTION "In RDL"
    	::= 8
 endedTest TRAP-TYPE
	ENTERPRISE  cxr
    	VARIABLES   { shelfIndex, slotIndex , portIndex }
   	DESCRIPTION "Ended test"
    	::= 9
 localSecurity TRAP-TYPE
	ENTERPRISE  cxr
    	VARIABLES   { shelfIndex, slotIndex , portIndex }
   	DESCRIPTION "Local security"
    	::= 10
 answerSecurity TRAP-TYPE
	ENTERPRISE  cxr
    	VARIABLES   { shelfIndex, slotIndex , portIndex }
   	DESCRIPTION "Answer security"
    	::= 11
 downloadSecurity TRAP-TYPE
	ENTERPRISE  cxr
    	VARIABLES   { shelfIndex, slotIndex , portIndex }
   	DESCRIPTION "Download security"
    	::= 12
 noDialtone TRAP-TYPE
	ENTERPRISE  cxr
    	VARIABLES   { shelfIndex, slotIndex , portIndex }
   	DESCRIPTION "No dial tone"
    	::= 13
 inRDLfromRemote TRAP-TYPE
	ENTERPRISE  cxr
    	VARIABLES   { shelfIndex, slotIndex , portIndex }
   	DESCRIPTION "In RDL from remote"
    	::= 14
 userChangedConfig TRAP-TYPE
	ENTERPRISE  cxr
    	VARIABLES   { shelfIndex, slotIndex , portIndex }
   	DESCRIPTION "User changed config."
    	::= 15
 resetbyATZ TRAP-TYPE
	ENTERPRISE  cxr
    	VARIABLES   { shelfIndex, slotIndex , portIndex }
   	DESCRIPTION "Reset by ATZ"
    	::= 16
 llActive TRAP-TYPE
	ENTERPRISE  cxr
    	VARIABLES   { shelfIndex, slotIndex , portIndex }
   	DESCRIPTION "LL active"
    	::= 17
 llFailed TRAP-TYPE
	ENTERPRISE  cxr
    	VARIABLES   { shelfIndex, slotIndex , portIndex }
   	DESCRIPTION "LL failed"
    	::= 18
 uadbuFailed TRAP-TYPE
	ENTERPRISE  cxr
    	VARIABLES   { shelfIndex, slotIndex , portIndex }
   	DESCRIPTION "UADBU failed"
    	::= 19
 lapmLoopBegan TRAP-TYPE
	ENTERPRISE  cxr
    	VARIABLES   { shelfIndex, slotIndex , portIndex }
   	DESCRIPTION "LAPM loop began"
    	::= 20
 remoteCmndActive TRAP-TYPE
	ENTERPRISE  cxr
    	VARIABLES   { shelfIndex, slotIndex , portIndex }
   	DESCRIPTION "Remote cmnd active"
    	::= 21
 remoteCmndInactive TRAP-TYPE
	ENTERPRISE  cxr
    	VARIABLES   { shelfIndex, slotIndex , portIndex }
   	DESCRIPTION "Remote cmnd inactive"
    	::= 22
 localDTEFailed TRAP-TYPE
	ENTERPRISE  cxr
    	VARIABLES   { shelfIndex, slotIndex , portIndex }
   	DESCRIPTION "Local DTE failed"
    	::= 23
 remoteDTEFailed TRAP-TYPE
	ENTERPRISE  cxr
    	VARIABLES   { shelfIndex, slotIndex , portIndex }
   	DESCRIPTION "Remote DTE failed"
    	::= 24
 busyRingNoAnswer TRAP-TYPE
	ENTERPRISE  cxr
    	VARIABLES   { shelfIndex, slotIndex , portIndex }
   	DESCRIPTION "Busy-ring no answer"
    	::= 25
 busySelfTestFail TRAP-TYPE
	ENTERPRISE  cxr
    	VARIABLES   { shelfIndex, slotIndex , portIndex }
   	DESCRIPTION "Busy-self test fail"
    	::= 26
 busyBadPower TRAP-TYPE
	ENTERPRISE  cxr
    	VARIABLES   { shelfIndex, slotIndex , portIndex }
   	DESCRIPTION "Busy-bad power"
    	::= 27
 busyHandshakeFail TRAP-TYPE
	ENTERPRISE  cxr
    	VARIABLES   { shelfIndex, slotIndex , portIndex }
   	DESCRIPTION "Busy-handshake fail"
    	::= 28
 busyByCommand TRAP-TYPE
	ENTERPRISE  cxr
    	VARIABLES   { shelfIndex, slotIndex , portIndex }
   	DESCRIPTION "Busy-by command"
    	::= 29
 restoredFromBusy TRAP-TYPE
	ENTERPRISE  cxr
    	VARIABLES   { shelfIndex, slotIndex , portIndex }
   	DESCRIPTION "restored from Busy"
    	::= 30
 flashUpdateBegun TRAP-TYPE
	ENTERPRISE  cxr
    	VARIABLES   { shelfIndex, slotIndex , portIndex }
   	DESCRIPTION "Flash update begun"
    	::= 31
 flashUpdateDone TRAP-TYPE
	ENTERPRISE  cxr
    	VARIABLES   { shelfIndex, slotIndex , portIndex }
   	DESCRIPTION "Flash update done"
    	::= 32
 flashUpdateFail TRAP-TYPE
	ENTERPRISE  cxr
    	VARIABLES   { shelfIndex, slotIndex , portIndex }
   	DESCRIPTION "Flash update fail"
    	::= 33
 csuCarrierOff TRAP-TYPE
	ENTERPRISE  cxr
    	VARIABLES   { shelfIndex, slotIndex , portIndex }
   	DESCRIPTION "CSU carrier off"
    	::= 34
 csuCarrierOn TRAP-TYPE
	ENTERPRISE  cxr
    	VARIABLES   { shelfIndex, slotIndex , portIndex }
   	DESCRIPTION "CSU carrier on"
    	::= 35
 outOfService TRAP-TYPE
	ENTERPRISE  cxr
    	VARIABLES   { shelfIndex, slotIndex , portIndex }
   	DESCRIPTION "Out of service"
    	::= 36
 inService TRAP-TYPE
	ENTERPRISE  cxr
    	VARIABLES   { shelfIndex, slotIndex , portIndex }
   	DESCRIPTION "In service"
    	::= 37
 csuLoopbackOff TRAP-TYPE
	ENTERPRISE  cxr
    	VARIABLES   { shelfIndex, slotIndex , portIndex }
   	DESCRIPTION "CSU loopback off"
    	::= 38
 csuLoopbackOn TRAP-TYPE
	ENTERPRISE  cxr
    	VARIABLES   { shelfIndex, slotIndex , portIndex }
   	DESCRIPTION "CSU loopback on"
    	::= 39
 dsuLoopbackOff TRAP-TYPE
	ENTERPRISE  cxr
    	VARIABLES   { shelfIndex, slotIndex , portIndex }
   	DESCRIPTION "DSU loopback off"
    	::= 40
 dsuLoopbackOn TRAP-TYPE
	ENTERPRISE  cxr
    	VARIABLES   { shelfIndex, slotIndex , portIndex }
   	DESCRIPTION "DSU loopback on"
    	::= 41
 dteLoopbackOff TRAP-TYPE
	ENTERPRISE  cxr
    	VARIABLES   { shelfIndex, slotIndex , portIndex }
   	DESCRIPTION "DTE loopback off"
    	::= 42
 dteLoopbackOn TRAP-TYPE
	ENTERPRISE  cxr
    	VARIABLES   { shelfIndex, slotIndex , portIndex }
   	DESCRIPTION "DTE loopback on"
    	::= 43
 isdnOK TRAP-TYPE
	ENTERPRISE  cxr
    	VARIABLES   { shelfIndex, slotIndex , portIndex }
   	DESCRIPTION "ISDN  OK"
    	::= 44
 isdnFailed TRAP-TYPE
	ENTERPRISE  cxr
    	VARIABLES   { shelfIndex, slotIndex , portIndex }
   	DESCRIPTION "ISDN  failed"
    	::= 45
 deviceTrap TRAP-TYPE
	ENTERPRISE  cxr
    	VARIABLES   { shelfIndex, slotIndex , portIndex }
   	DESCRIPTION "Device trap"
    	::= 46
 deviceWatchdog TRAP-TYPE
	ENTERPRISE  cxr
    	VARIABLES   { shelfIndex, slotIndex , portIndex }
   	DESCRIPTION "Device Watchdog"
    	::= 47
	
  --*************************************************************************
        -- Alarm : shelves
  --*************************************************************************        

 powerLeftFailed TRAP-TYPE 
	ENTERPRISE  cxr
    	VARIABLES   { shelfIndex }
   	DESCRIPTION "Shelf Left Power Failed"
    	::= 257

 powerRightFailed TRAP-TYPE
	ENTERPRISE  cxr
	VARIABLES   { shelfIndex }
	DESCRIPTION " Shelf Right Power Failed"
    	::= 258

 powerLeftRestored TRAP-TYPE
	ENTERPRISE  cxr
	VARIABLES   { shelfIndex }
	DESCRIPTION " Shelf Left Power Restored"
    	::= 259

 powerRightRestored TRAP-TYPE
	ENTERPRISE  cxr
	VARIABLES   { shelfIndex }
	DESCRIPTION " Shelf Right Power Restored"
    	::= 260

 shelfSecurityViolation TRAP-TYPE
	ENTERPRISE  cxr
	VARIABLES   { shelfIndex }
	DESCRIPTION "Shelf Security Violation"
    	::= 261

 selfTestFailure TRAP-TYPE
	ENTERPRISE  cxr
	VARIABLES   { shelfIndex }
	DESCRIPTION "Startup Self Test Failure"
    	::= 262

 activityBufferOverflow TRAP-TYPE
	ENTERPRISE  cxr
	VARIABLES   { shelfIndex }
	DESCRIPTION "Activity Buffer Overflow"
    	::= 263

 controllerStarted TRAP-TYPE
	ENTERPRISE  cxr
	VARIABLES   { shelfIndex }
	DESCRIPTION "Controller Started"
    	::= 264

 userControllerReset TRAP-TYPE
	ENTERPRISE  cxr
	VARIABLES   { shelfIndex }
	DESCRIPTION "Controller Reset User"
    	::= 265

 trap0 TRAP-TYPE
	ENTERPRISE  cxr
	VARIABLES   { shelfIndex }
	DESCRIPTION "Controller Trap #0"
    	::= 266

 trap1 TRAP-TYPE
	ENTERPRISE  cxr
	VARIABLES   { shelfIndex }
	DESCRIPTION "Controller Trap #1"
    	::= 267

 trap2 TRAP-TYPE
	ENTERPRISE  cxr
	VARIABLES   { shelfIndex }
	DESCRIPTION "Controller Trap #2"
    	::= 268

 trap3 TRAP-TYPE
	ENTERPRISE  cxr
	VARIABLES   { shelfIndex }
	DESCRIPTION "Controller Trap #3"
    	::= 269

 trap4 TRAP-TYPE
	ENTERPRISE  cxr
	VARIABLES   { shelfIndex }
	DESCRIPTION "Controller Trap #4"
    	::= 270

 trap5 TRAP-TYPE
	ENTERPRISE  cxr
	VARIABLES   { shelfIndex }
	DESCRIPTION "Controller Trap #5"
    	::= 271

 trap6 TRAP-TYPE
	ENTERPRISE  cxr
	VARIABLES   { shelfIndex }
	DESCRIPTION "Controller Trap #6"
    	::= 272

 trap7 TRAP-TYPE
	ENTERPRISE  cxr
	VARIABLES   { shelfIndex }
	DESCRIPTION "Controller Trap #7"
    	::= 273

 trap8 TRAP-TYPE
	ENTERPRISE  cxr
	VARIABLES   { shelfIndex }
	DESCRIPTION "Controller Trap #8"
    	::= 274

 trap9 TRAP-TYPE
	ENTERPRISE  cxr
	VARIABLES   { shelfIndex }
	DESCRIPTION "Controller Trap #9"
    	::= 275

 deviceInactive TRAP-TYPE
	ENTERPRISE  cxr
	VARIABLES   { shelfIndex slotIndex portIndex }
	DESCRIPTION "Device Inactive"
    	::= 276

 slaveControllerInactive TRAP-TYPE
	ENTERPRISE  cxr
	VARIABLES   { shelfIndex }
	DESCRIPTION "Slave Controller Inactive"
    	::= 277

END
