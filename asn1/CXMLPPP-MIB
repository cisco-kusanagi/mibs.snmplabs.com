CXMLPPP-MIB DEFINITIONS ::= BEGIN


IMPORTS
   Counter        FROM RFC1155-SMI
   OBJECT-TYPE    FROM RFC-1212
   DisplayString     FROM RFC1213-MIB
   cxMLPPP,SapIndex,Alias  FROM CXProduct-SMI;

--#CURRENT-VERSION 1


mlpppNbSmallBufs     OBJECT-TYPE
      SYNTAX   INTEGER
      ACCESS   read-write
      STATUS   mandatory
      DESCRIPTION
"Determines the number of small size buffers that you want to create for 
the MLPPP stack.

Range of Values: The maximum value of this object depends on the amount of 
RAM available on the system.

Default Value: 1

WARNING: When PPP ports are used, this  value must be greater than 50.

Configuration Changed: administrative"
      DEFVAL { 1 }
      ::= { cxMLPPP 1 }

mlpppSmallBufSize       OBJECT-TYPE
      SYNTAX   INTEGER
      ACCESS   read-write
      STATUS   mandatory
      DESCRIPTION
"WARNING: Do not modify this object without the supervision of Memotec 
personnel.

Determines the size, in bytes, of each small buffer in the MLPPP stack.

Range of Values: 1 to 65535

Note: The maximum value of this object depends on the amount of RAM 
available on the system. 

Default Value: 128

Configuration Changed: administrative"
      DEFVAL { 128 }
   --#STARTING-VERSION 1

      ::= { cxMLPPP 2 }

mlpppNbLargeBufs     OBJECT-TYPE
      SYNTAX   INTEGER
      ACCESS   read-write
      STATUS   mandatory
      DESCRIPTION
"Determines the number of large size buffers for the MLPPP stack.

Range of Values: The maximum value of this object depends on the amount of 
RAM available on the system.

Default Value: 1

WARNING: When PPP ports are used, this value must be greater than 25 
because the PPP module cannot use global buffers that were defined with 
OsParam. 

You must decrease the OsParam small buffer parameter (cxOsNbSmallBufs) 
when you increase this value or you may run out of memory, and the 
system may crash.

Configuration Changed: administrative"
      DEFVAL { 1 }
         --#STARTING-VERSION 1
      ::= { cxMLPPP 3 }

mlpppLargeBufSize       OBJECT-TYPE
      SYNTAX   INTEGER
      ACCESS   read-write
      STATUS   mandatory
      DESCRIPTION
"Do not modify this object without the supervision of Memotec personnel. 

Determines the size, in bytes, of each large size buffer of the MLPPP 
stack.

Range of Values: 1 - 65535

Note: The setting of this object depends on the amount of RAM available on 
the system, and should be set to the same value as the Operating System 
large buffer size (cxOsNbLargeBufs).

Default Value: 1600.

Configuration Changed: administrative"
      DEFVAL { 1600 }
         --#STARTING-VERSION 1
      ::= { cxMLPPP 4 }

mlpppSoftwareVersion       OBJECT-TYPE
      SYNTAX   DisplayString
      ACCESS   read-only
      STATUS   mandatory
      DESCRIPTION
"Identifies the Multilink Protocol software revision number, which is 
displayed as a string of two numbers, each separated by a period (1.2). 
The two numbers represent:

- (1) main version number
- (2) main revision number

Default Value: 1.00
"
      DEFVAL { "1.00" }
         --#STARTING-VERSION 1
      ::= { cxMLPPP 40 }

mlpppNbActiveUSap       OBJECT-TYPE
      SYNTAX   INTEGER (0..100)
      ACCESS   read-only
      STATUS   mandatory
      DESCRIPTION
"Indicates the number of MLPPP upper SAPs that have been initialized. 
Upper SAPs are used to interact with the network layer. Up to ten 
Multilink PPP links are supported in this release.

Range of Values: 0 - 100

Default Value: none"
         --#STARTING-VERSION 1
      ::= { cxMLPPP 41 }


mlpppNbActiveLSap       OBJECT-TYPE
      SYNTAX   INTEGER (0..100)
      ACCESS   read-only
      STATUS   mandatory
      DESCRIPTION
"Indicates the number of MLPPP lower SAPs that have been initialized. Each 
lower SAP has an associated PPP link. Up to ten PPP links are supported in 
this release.

Range of Values: 0 - 100

Default Value: none"  
         --#STARTING-VERSION 1
      ::= { cxMLPPP 42 }


mlpppNbActiveBundle     OBJECT-TYPE
      SYNTAX   INTEGER (0..100)
      ACCESS   read-only
      STATUS   mandatory
      DESCRIPTION
"Indicates the number of bundles that have been initialized. A bundle is a 
group of physical links that Multilink PPP uses as one virtual link. The 
network layer recognizes the bundle as a single link.

Range of Values: 0 - 100

Default Value: none"
         --#STARTING-VERSION 1
      ::= { cxMLPPP 43 }

mlpppNbSmallBufsFree       OBJECT-TYPE
      SYNTAX   INTEGER
      ACCESS   read-only
      STATUS   mandatory
      DESCRIPTION
"Displays the number of small buffers that are currently free within the 
MLPPP stack.

Default Value: none"
         --#STARTING-VERSION 1
      ::= { cxMLPPP 44 }


mlpppNbLargeBufsFree    OBJECT-TYPE
      SYNTAX   INTEGER
      ACCESS   read-only
      STATUS   mandatory
      DESCRIPTION
"Displays the number of large buffers that are currently free within the 
MLPPP stack.

Default Value: none"
         --#STARTING-VERSION 1
      ::= { cxMLPPP 45 }

mlpppMibLevel OBJECT-TYPE
   SYNTAX  INTEGER
   ACCESS  read-only
   STATUS  mandatory
   DESCRIPTION
"Used to determine current MIB module release supported
by the agent. Object is in decimal."
   --#STARTING-VERSION 1
   ::= { cxMLPPP 49 }



--  Lower Service Access Point Configuration Table

--  The table describing:
-- parameters required to configure a lower service access point
-- controls available to manipulate a lower service access point
-- status available for monitoring the current state of the lower service access point
-- statistics available for monitoring any lower service access point

--  The Lower Service Access Points here is considered as the lower access point of a PPP link
--  of this module.  These Lower Service Acess Points are used to communicate with an upper SAP 
--  of the BOP or ASYNC module; 
--
-- Each lower as an associated PPP links.
-- The following objects reflect the values of the option
-- parameters used in the PPP Link Control Protocol
--   mlpppLSapLsLocalMRU
--   mlpppLSapLsRemoteMRU
--   mlpppLSapLsLocalToPeerACCMap
--   mlpppLSapLsPeerToLocalACCMap
--   mlpppLSapLsLocalToRemoteProtComp
--   mlpppLSapLsRemoteToLocalProtComp
--   mlpppLSapLsLocalToRemoteACComp
--   mlpppLSapLsRemoteToLocalACComp

--  further connection will be added on a need basis.


mlpppLSapTable       OBJECT-TYPE
      SYNTAX   SEQUENCE OF MlpppLSapEntry
      ACCESS   not-accessible
      STATUS   mandatory
      DESCRIPTION
"The SAP table contains configuration information for each MLPPP layer 
lower SAP (service access point).

Lower SAPs exist at the lower interface of the Multilink PPP layer and 
have an associated PPP link. This PPP link attaches to the Upper SAPs of 
one of three types of physical layers: Sync, Async, or console.

Note: ISDN is not supported in this release."
         --#STARTING-VERSION 1
      ::= { cxMLPPP 50 }


mlpppLSapEntry       OBJECT-TYPE
      SYNTAX   MlpppLSapEntry
      ACCESS   not-accessible
      STATUS   mandatory
      DESCRIPTION
"Defines a row in the mlppLSapTable. Each row contains the objects which 
define a lower service access point."
      INDEX { mlpppLSapNumber }
         --#STARTING-VERSION 1
      ::= { mlpppLSapTable 1 }


MlpppLSapEntry ::=
      SEQUENCE {
-- Parameters
         mlpppLSapNumber                    SapIndex,
         mlpppLSapRowStatus                 INTEGER,
         mlpppLSapAlias                     Alias,
         mlpppLSapCompanionAlias            Alias,
-- 
         mlpppLSapLinkUSapNumber            INTEGER,
         
-- dial entry table index
         mlpppLSapDialEntry                 INTEGER,

-- these parameters used to be in the U sap before
         mlpppLSapLcInitialMRU              INTEGER,
         mlpppLSapLcTransmitACCMap          DisplayString,
         mlpppLSapLcMaxConfigure            INTEGER,
         mlpppLSapLcMaxTerminate            INTEGER,
         mlpppLSapLcMaxFailure              INTEGER,
         mlpppLSapLcRestartTimer            INTEGER,
         mlpppLSapLcProtFieldComp           INTEGER,
         mlpppLSapLcACFieldComp             INTEGER,
         mlpppLSapLcMagicNumber             INTEGER,
-- Control     
         mlpppLSapLinkControl               INTEGER,
         mlpppLSapClearStats                INTEGER,
-- Status
         mlpppLSapState                     INTEGER,
         mlpppLSapPhysNetStatus             INTEGER,
         mlpppLSapVirtNetStatus             INTEGER,
         mlpppLSapLsBadAddresses            Counter,
         mlpppLSapLsBadControls             Counter,
         mlpppLSapLsPacketTooLongs          Counter,
         mlpppLSapLsBadFCSs                 Counter,
         mlpppLSapLsLocalMRU                INTEGER,
         mlpppLSapLsRemoteMRU               INTEGER,
         mlpppLSapLsLocalToPeerACCMap       DisplayString,
         mlpppLSapLsPeerToLocalACCMap       DisplayString,
         mlpppLSapLsLocalToRemoteProtComp   INTEGER,
         mlpppLSapLsRemoteToLocalProtComp   INTEGER,
         mlpppLSapLsLocalToRemoteACComp     INTEGER,
         mlpppLSapLsRemoteToLocalACComp     INTEGER,

-- Statistics
         mlpppLSapNbBytesSent               Counter,
         mlpppLSapNbBytesReceived           Counter
         }


mlpppLSapNumber OBJECT-TYPE
      SYNTAX   SapIndex
      ACCESS   read-only
      STATUS   mandatory
      DESCRIPTION
 "Identifies the lower SAP entry with a unique numerical value.

Range of Values: 1 - 100

Default Value: none"
         --#STARTING-VERSION 1
      ::= { mlpppLSapEntry 1 }


mlpppLSapRowStatus      OBJECT-TYPE
      SYNTAX   INTEGER {
               invalid     (1),
               valid    (2)
               }
      ACCESS   read-write
      STATUS   mandatory
      DESCRIPTION
"Determines the status of the objects in a table row.

Options:
invalid (1): Row is deleted from the table, but values are still in effect 
until the next reset.

valid (2): Use this value to add a new row to the table, or modify an 
existing row.

Default Value: invalid (1)

Configuration Changed: administrative"
      DEFVAL {invalid }
         --#STARTING-VERSION 1
       ::= { mlpppLSapEntry 2 }


mlpppLSapAlias          OBJECT-TYPE
      SYNTAX   Alias
      ACCESS   read-write
      STATUS   mandatory
      DESCRIPTION
"Identifies this lower service access point by a textual name. Names must 
be unique across all service access points at all layers.

Range of Values: 0 to16 alphanumeric characters 
(first character must be a letter)

Default Value: none

Configuration Changed: administrative"
         --#STARTING-VERSION 1
      ::= { mlpppLSapEntry 3 }


mlpppLSapCompanionAlias OBJECT-TYPE
      SYNTAX   Alias
      ACCESS   read-write
      STATUS   mandatory
      DESCRIPTION
"Determines the sub-layer SAP that this SAP communicates with. This object 
contains the textual name of the sub-layer SAP.

Range of Values: 0 to16 alphanumeric characters (first character must be a 
letter)

Default Value: none

Configuration Changed: administrative"
         --#STARTING-VERSION 1
      ::= { mlpppLSapEntry 4 }


mlpppLSapLinkUSapNumber OBJECT-TYPE
      SYNTAX   INTEGER (0..100)
      ACCESS   read-write
      STATUS   mandatory
      DESCRIPTION
"Determines the MLPPP upper SAP number that is associated with this MLPPP 
lower SAP.

In this release, bundling is not supported, and the MLPPP upper SAP number 
should be unique within all lower SAPs.

--- not yet implemented ---
PPP links that use the same upper SAP number are bundled, and appear as a 
single link to the network layer.
--- not yet implemented --- 

Note: If this value is 0, then this lower SAP will not be used and its 
link will not be bundled.

Range of Values: 0 - 100

Default Value: 0

Configuration Changed: administrative"
      DEFVAL { 0 }
      ::= { mlpppLSapEntry 100 }


mlpppLSapDialEntry      OBJECT-TYPE
            SYNTAX      INTEGER 
            ACCESS      read-write
            STATUS      mandatory
            DESCRIPTION
"This object is supported in this release.

Determines the index in the dial table which corresponds to a ISDN
directory entry.. 
The access point is the B Channel Manager Directory Table entry that 
corresponds to the ISDN telephone number.

This object is meaningful only if object mlpppLSapPhysicalType is set to 
'isdn'.

Default Value: 0

Configuration Changed: administrative"
            DEFVAL { 1 }
         --#STARTING-VERSION 1
         ::= { mlpppLSapEntry 12 }



mlpppLSapLcInitialMRU         OBJECT-TYPE
                  SYNTAX      INTEGER(0..2147483647)
                  ACCESS      read-write
                  STATUS      mandatory
                  DESCRIPTION
"Determines the Maximum Receive Unit (in octets) proposed by the local 
port. The local port's proposed MRU will be negotiated with the remote 
port's proposed MRU; the result of the negotiation is displayed in 
mlpppLSapLsLocalMRU on the mlpppLSapLsTable table.

The MRU is the maximum length of the Information field, including Padding. 
The length of the Protocol field is not included in the MRU. 

If this value is set to 0, then no negotiation will occur with the remote
and the default MRU of 1500 octets is used. 

If this value is not 0, then the local PPP link will negotiate for this 
value with the remote peer.

Range of Values: 0 to 2048

Default Value: 1500

Related Objects:
mlpppLSapLsLocalMRU
mlpppLSapLsTable

Configuration Changed:  administrative"
                  REFERENCE
                  "Section 7.2, Maximum Receive Unit of RFC1331."
                  DEFVAL    { 1500 }
         --#STARTING-VERSION 1
                  ::= { mlpppLSapEntry 14 }




mlpppLSapLcTransmitACCMap     OBJECT-TYPE
                  SYNTAX      DisplayString(SIZE (0..8))
                  ACCESS      read-write
                  STATUS      mandatory
                  DESCRIPTION
"Determines the Asynchronous Control Character Map (ACC) that the local 
PPP link proposes for use on its transmit side. The local's proposed ACC 
will be negotiated with the remote's proposed ACC. The result of the 
negotiation is displayed in mlpppLSapLsPeerToLocalACCMap in the 
mlpppLSapLsTable.

The ACCMap maps the first 32 ASCII control characters (numbered 0 to 31). 
The map allows datagrams traveling over a PPP link to be transparent to 
all intermediate devices such as modems. 

The value of the object is a string of four octets. This string totals 32 
bits, and position numbers (0-31) correspond to the first 32 control 
characters. For example, if bit 19 is set to 1, then the ASCII control 
character 19 (ctrl-s) is sent transparently. 

Note: Async Control Character Map must be cleared when Multilink is used (value: 
00 00 00 00)

Range of Values: 4 octets, each character ranging from 00 to FF. 

Default Value: FFFFFFFF.

Configuration Changed:  administrative"
      REFERENCE
         "Section 7.3, page 4, Async-Control-Character-
          Map of RFC1331."
                  DEFVAL    { "FFFFFFFF" }
         --#STARTING-VERSION 1
                  ::= { mlpppLSapEntry 15 }


mlpppLSapLcMaxConfigure       OBJECT-TYPE
                  SYNTAX      INTEGER
                  ACCESS      read-write
                  STATUS      mandatory
                  DESCRIPTION
"Determines the maximum number of Configure-Request packets that the port 
can send without any acknowledgment from the peer. If the maximum number 
of packets has been sent and there is still no response from the other end 
of the link, the Link Control Protocol (LCP) assumes that the peer is 
unable to respond and that the link cannot be established.

Range of Values: 1-15

Default Value: 10
   
Configuration Changed: administrative"
                  DEFVAL    { 10 }
         --#STARTING-VERSION 1
      ::= { mlpppLSapEntry 16 }


mlpppLSapLcMaxTerminate    OBJECT-TYPE
                  SYNTAX      INTEGER
                  ACCESS      read-write
                  STATUS      mandatory
                  DESCRIPTION
"Determines the maximum number of Termination-Request packets that the 
port can send without any answer from the peer. 

If the maximum number of packets has been sent and there is still no 
response from the other end of the link, the Link Control Protocol (LCP) 
assumes that the peer is unable to respond. The link is closed without 
negociating the termination.

Range of Values: 1-5

Default Value: 2

Configuration Changed:  administrative"
      DEFVAL    { 2 }
         --#STARTING-VERSION 1
                  ::= { mlpppLSapEntry 17 }


mlpppLSapLcMaxFailure         OBJECT-TYPE
                  SYNTAX      INTEGER
                  ACCESS      read-write
                  STATUS      mandatory
                  DESCRIPTION
"Determines the maximum number of Configure-Not-Acknowledge packets which 
can be sent without receipt of a Configure-Acknowledge packet. 

A Configure-Acknowledge packet means that one end of the link accepts the 
value for the configuration parameter proposed by the peer. 

A Configure-Not-Acknowledge packet means that the peer does not accept the 
proposal. If the maximum number is exceeded, the link is closed down. This 
prevents endless loops in the configuration process.

Range of Values: 1 to 15

Default Value: 5

Configuration Changed:  administrative"
                  DEFVAL    { 5 }
         --#STARTING-VERSION 1
      ::= { mlpppLSapEntry 18 }


mlpppLSapLcRestartTimer    OBJECT-TYPE
                  SYNTAX      INTEGER
                  ACCESS      read-write
                  STATUS      mandatory
                  DESCRIPTION
"Determines the time interval (in seconds) between the sending of a 
Configure-Request or Terminate-Request packet, and the time before its 
retransmission if no acknowledgment is received. 

The packet is retransmitted up to the maximum number permitted in 
mlpppUSapLcMaxConfigure of this table.

Default Value: 3

Range of Values: 1 to 100

Configuration Changed:  administrative"
      DEFVAL    { 3 }
         --#STARTING-VERSION 1
            ::= { mlpppLSapEntry 19 }



mlpppLSapLcProtFieldComp      OBJECT-TYPE
                  SYNTAX      INTEGER { 
               enabled(1), 
               disabled(2) 
               }
                  ACCESS      read-write
                  STATUS      mandatory
                  DESCRIPTION
"Determines whether the local PPP port can receive packets with a 
compressed PPP Protocol Field. If enabled, the port informs its peer that 
it can receive packets with a compressed PPP Protocol Field (when the 
configuration of the PPP link is negotiated).

Note: Protocol Field Compression must be enabled when Multilink is used.

Options:
enabled (1)

disabled (2)

Default Value: disabled (2)

Configuration Changed:  administrative"
                  DEFVAL    { disabled }
         --#STARTING-VERSION 1
       ::= { mlpppLSapEntry 20 }


mlpppLSapLcACFieldComp     OBJECT-TYPE
      SYNTAX      INTEGER { 
               enabled(1), 
               disabled(2) 
               }
                  ACCESS      read-write
      STATUS      mandatory
      DESCRIPTION
"Determines whether the local PPP port can receive packets with compressed 
PPP Address and Control Fields. If enabled, the port informs its peer that 
it can receive packets with a compressed PPP Address and Control Field 
when the configuration of the PPP link is negotiated.

Note: Address and Control Field Compression must be enabled when Multilink is 
used. 

Options:
enabled (1)

disabled (2)

Default Value: disabled (2)

Configuration Changed:  administrative"
                  DEFVAL    { disabled }
         --#STARTING-VERSION 1
          ::= { mlpppLSapEntry 21 }


mlpppLSapLcMagicNumber     OBJECT-TYPE
                  SYNTAX      INTEGER { 
               enabled (1), 
               disabled (2) 
               }
                  ACCESS      read-write
                  STATUS      mandatory
                  DESCRIPTION
           "Determines whether the Magic Number is enabled or disabled.

The Magic Number is a unique random system generated number, present in 
every Configure-Request packet. The Magic Number is used to ensure that 
the same packet is not sent back and forth between the local and the 
remote in an endless loop.

If the Magic Number is enabled, then the local end of the link will check 
the Magic Number in each Configure-Request packet it receives. If the 
number is the same as its own, it will change its number and send a 
NoAcknowledge packet back to the remote. If the local end of the link 
continues to receive Configure-Requests with its own number, it assumes a 
loopback. After the number of Configure-Requests specified in 
mlpppUSapLcMaxConfigure of this table has been exceeded, the link will go 
down.

Note:
Magic Number must be disabled when Multilink is used.

Options: 
enabled (1)

disabled (2)

Default Value: disabled (2)

Configuration Changed:  administrative"
                  REFERENCE
                              "Section 7.6, Magic Number, of RFC1331."
                  DEFVAL    { disabled }
         --#STARTING-VERSION 1
                  ::= { mlpppLSapEntry 22 }

mlpppLSapLinkControl     OBJECT-TYPE
      SYNTAX      INTEGER { 
           enable  (1), 
           disable (2),
           stop    (3),
           start   (4)
      }
      ACCESS   read-write
      STATUS   mandatory
      DESCRIPTION
"Enables/disables the connectivity of this link to the bundle
 Stops or starts the interface 
 Acts also as an operational control.
Options:
enabled    :the link may connect to the bundle
disabled   :the link may not connect to the bundle

Default Value: enabled"
         --#STARTING-VERSION 1
      ::= { mlpppLSapEntry 23 }

mlpppLSapClearStats     OBJECT-TYPE
      SYNTAX   INTEGER
      ACCESS   write-only
      STATUS   mandatory
      DESCRIPTION
"Clears the statistics counter of the PPP link associated to this lower SAP.

Options:
clearStats :clears statistics

Default Value: none"
         --#STARTING-VERSION 1
      ::= { mlpppLSapEntry 30 }


mlpppLSapState          OBJECT-TYPE
      SYNTAX   INTEGER {
        not-used (1),
        unbound  (2),
        bound    (3)
      }
      ACCESS   read-only
      STATUS   mandatory
      DESCRIPTION
"Indicates the current state of this lower SAP (service access point).

Options:
not-used (1): SAP not in use.

unbound (2): SAP not bound to another software layer.

bound (3): SAP bound to another software layer.

Default Value: none"
         --#STARTING-VERSION 1
      ::= { mlpppLSapEntry 40 }


mlpppLSapPhysNetStatus     OBJECT-TYPE
      SYNTAX   INTEGER {
        pif-attached   (1),
        pif-detached   (2)
       }
      ACCESS   read-only
      STATUS   mandatory
      DESCRIPTION
"Indicates the most recent change in link status between MLPPP and the 
physical layer. 

Options:
pif-attached (1): A physical interface has been attached to this lower SAP.

pif-detached (2): A physical interface has been detached from this lower SAP.

Default Value: none"
         --#STARTING-VERSION 1
      ::= { mlpppLSapEntry 41 }


mlpppLSapVirtNetStatus     OBJECT-TYPE
      SYNTAX   INTEGER {
        vif-attached   (1),
        vif-detached   (2),
        vif-up         (3),
        vif-down       (4),
        vif-finished   (5)
      }
      ACCESS   read-only
      STATUS   mandatory
      DESCRIPTION
"Indicates the most recent change in link status between MLPPP and the 
network layer. 

Each lower SAP has an associated PPP link.

Options:
vif-attached (1): The PPP link has been attached to a bundle.

vif-detached (2): The PPP link has been detached from a bundle.

vif-up (3): The PPP link went up.

vif-down (4): The PPP link went down.

vif-finished (5): The PPP link is finished

Default Value: none"
         --#STARTING-VERSION 1
      ::= { mlpppLSapEntry 42 }


mlpppLSapLsBadAddresses    OBJECT-TYPE
      SYNTAX      Counter
                  ACCESS      read-only
                  STATUS      mandatory
                  DESCRIPTION
"Identifies the number of packets received at the local port which contain 
a bad address field. 

Range of Values: 0 - 4,294,967,295

Default Value: None"
               REFERENCE
                              "Section 3.1, Address Field, of RFC1331."
         --#STARTING-VERSION 1
                  ::= { mlpppLSapEntry 43}


mlpppLSapLsBadControls     OBJECT-TYPE
                  SYNTAX      Counter
                  ACCESS      read-only
                  STATUS      mandatory
                  DESCRIPTION
"Identifies the number of packets received at the local port which contain 
an incorrect control field. 

Range of Values: 0 - 4,294,967,295 

Default Value: None"
--               REFERENCE
--                 "Section 3.1, Control Field, of RFC1331."
         --#STARTING-VERSION 1
                  ::= { mlpppLSapEntry 44 }


mlpppLSapLsPacketTooLongs     OBJECT-TYPE
                  SYNTAX      Counter
                  ACCESS      read-only
                  STATUS      mandatory
                  DESCRIPTION
"Identifies the number of packets received at the local port which have 
been discarded because their length exceeded the Maximum Receive Unit 
(MRU). Packets which are longer than the MRU but which are successfully 
received and processed are not included in this count.

The MRU is the maximum length of the Information field, including Padding. 
The length of the Protocol field is not included in the MRU. 

Range of Values: 0 - 4,294,967,295 

Default Value: None"
         --#STARTING-VERSION 1
                  ::= { mlpppLSapEntry 45 }


mlpppLSapLsBadFCSs         OBJECT-TYPE
                  SYNTAX      Counter
                  ACCESS      read-only
                  STATUS      mandatory
                  DESCRIPTION
"Identifies the number of packets received at the local port which have 
been discarded because they had an incorrect Frame Check Sequence (FCS). 

Range of Values: 0 - 4,294,967,295 

Default Value: none"
         --#STARTING-VERSION 1
                  ::= { mlpppLSapEntry 46 }


mlpppLSapLsLocalMRU     OBJECT-TYPE
                  SYNTAX      INTEGER(1..2147483648)
                  ACCESS      read-only
                  STATUS      mandatory
                  DESCRIPTION
"Identifies the current value in octets of the Maximum Receive Unit (MRU) 
for the local PPP link. 

This value is the MRU that the remote is using to send packets over the 
PPP link. The value is meaningful only when the link has reached the open 
state (virtNetStatus is up).

Range of Values: 1 - 2048

Default Value: 1500"
      DEFVAL { 1500 }
         --#STARTING-VERSION 1
                        ::= { mlpppLSapEntry 47 }


mlpppLSapLsRemoteMRU    OBJECT-TYPE
      SYNTAX      INTEGER(1..2147483648)
                  ACCESS      read-only
                  STATUS      mandatory
                  DESCRIPTION
"Identifies the current value in octets of the Maximum Receive Unit (MRU) 
for the remote PPP link. 

This value is the MRU that the local is using to send packets over the PPP 
link. The value is meaningful only when the link has reached the open 
state (virtNetStatus is up).

Range of Values: 1 - 2048
               
Default Value: 1500"
      DEFVAL { 1500 }
         --#STARTING-VERSION 1
                ::= { mlpppLSapEntry 48 }


mlpppLSapLsLocalToPeerACCMap  OBJECT-TYPE
                  SYNTAX      DisplayString (SIZE (0..8))
                  ACCESS      read-only
                  STATUS      mandatory
                  DESCRIPTION
"Identifies the current value of the Asynchronous Control 
Character(ACC)Map for the local PPP link. This value is the ACCMap that 
the local link is using to send packets over the PPP link.

The value is meaningful only when the link has reached the open state 
(virtNetStatus is up); at which time it displays the result of the PPP 
negotiation.

Range of Values: 4 octets, each character in the range 00 to FF

Default Value: FF FF FF FF"
      DEFVAL { "FFFFFFFF" }
         --#STARTING-VERSION 1
            ::= { mlpppLSapEntry 49 }


mlpppLSapLsPeerToLocalACCMap     OBJECT-TYPE
                  SYNTAX      DisplayString (SIZE (0..8))
                  ACCESS    read-only
                  STATUS    mandatory
                  DESCRIPTION
"Identifies the current value of the Asynchronous Control Character(ACC) Map
for the remote PPP link. This value is the ACCMap that the remote peer is using
to send packets over the PPP link. 

The value is meaningful only when the link has reached the open state 
(virtNetStatus is up); at which time it displays the result of the PPP 
negotiation.

Range of Values: 4 octets, each character in the range 00 to FF

Default Value: FF FF FF FF"
      DEFVAL { "FFFFFFFF" }
         --#STARTING-VERSION 1
                   ::= { mlpppLSapEntry 50 }


mlpppLSapLsLocalToRemoteProtComp OBJECT-TYPE
                  SYNTAX      INTEGER {
                                  enabled(1),
                                  disabled(2)      
                        }
                  ACCESS      read-only
                  STATUS      mandatory
                  DESCRIPTION
"Indicates whether the local PPP link is using Protocol Compression when 
transmitting packets to the remote. 

This value is meaningful only when the link has reached the open state 
(virtNetStatus is up); at which time it displays the result of the PPP 
negotiation.

Options:
enabled (1)

disabled (2)

Default Value: disabled (2)"
      DEFVAL { disabled }
         --#STARTING-VERSION 1
                 ::= { mlpppLSapEntry 51 }


mlpppLSapLsRemoteToLocalProtComp OBJECT-TYPE
                  SYNTAX      INTEGER {
                                  enabled(1),
                                  disabled(2)
                       }
                  ACCESS      read-only
                  STATUS      mandatory
                  DESCRIPTION
"Indicates whether the remote PPP link is using Protocol Compression when 
transmitting packets to the local.

This value is meaningful only when the link has reached the open state 
(virtNetStatus is up); at which time it displays the result of 
the PPP negotiation.

Options:
enabled (1)

disabled (2)

Default Value: disabled (2)"
      DEFVAL { disabled }
         --#STARTING-VERSION 1
             ::= { mlpppLSapEntry 52 }


mlpppLSapLsLocalToRemoteACComp      OBJECT-TYPE
                  SYNTAX      INTEGER {
                                  enabled(1),
                                  disabled(2)
                        }
                  ACCESS    read-only
                  STATUS    mandatory
                  DESCRIPTION
"Indicates whether the local end of the PPP link is using Address and 
Control Compression when it transmits packets to the remote.

The value is meaningful only when the link has reached the open state 
(virtNetStatus is up); at which time it displays the result of the PPP 
negotiation.

Options:
enabled (1)

disabled (2)

Default Value: disabled (2)"
      DEFVAL { disabled }
         --#STARTING-VERSION 1
              ::= { mlpppLSapEntry 53 }


mlpppLSapLsRemoteToLocalACComp      OBJECT-TYPE
                  SYNTAX      INTEGER {
                                  enabled(1),
                                  disabled(2)
                           }
                  ACCESS      read-only
                  STATUS      mandatory
                  DESCRIPTION
"Indicates whether or not the remote end of the PPP link is using Address 
and Control Compression when it transmits packets to the local.

The value is meaningful only when the link has reached the open state 
(virtNetStatus is up); at which time it displays the result of the PPP 
negotiation.

Options:
enabled (1)

disabled (2)

Default Value: disabled (2)"
      DEFVAL { disabled }
         --#STARTING-VERSION 1
                  ::= { mlpppLSapEntry 54 }


mlpppLSapNbBytesSent       OBJECT-TYPE
      SYNTAX      Counter
                  ACCESS      read-only
                  STATUS      mandatory
                  DESCRIPTION
"Indicates the number of bytes sent to the physical layer through this 
lower SAP since system startup or since last statistics reset.

Range of Values: 0 - 4,294,967,295

Default Value: none"
         --#STARTING-VERSION 1
                  ::= { mlpppLSapEntry 70 }


mlpppLSapNbBytesReceived   OBJECT-TYPE
      SYNTAX      Counter
                  ACCESS      read-only
                  STATUS      mandatory
                  DESCRIPTION
"Indicates the number of bytes received from the physical layer through 
this lower SAP since system startup, or since last statistics reset.

Range of Values: 0 - 4,294,967,295

Default Value: none"
         --#STARTING-VERSION 1
                  ::= { mlpppLSapEntry 71 }



--  Upper Service Access Point Configuration Table

--  The table describing:
-- parameters required to configure an upper service access point
-- controls available to manipulate an upper service access point
-- status available for monitoring the current state of the upper service access point
-- statistics available for monitoring any upper service access point

--  The Upper Service Access Points here is considered as the upper access point of a MLPPP link
--  of this module.  These Upper Service Acess Points are used to communicate with an lower SAP 
--  of a network layer; 
--  Each upper as an associated MLPPP links and it contains all the Link Control Protocol configuration
--  parameters associated to each PPP link constituting the aggregate.
--
--    The objects below are meaningful only when the PPP link is used in a 
--    bundle with more than two PPP links, and are not yet implemented.
--
--   mlpppUSapLsLocalMRRU      
--   mlpppUSapLsRemoteMRRU 
--   mlpppUSapLsLocalToRemoteSeqFieldComp 
--   mlpppUSapLsRemoteToLocalSeqFieldComp 
--
-- These values are not available until after the PPP Option
-- negotiation has completed, which is indicated by the link
-- reaching the open state (i.e., virtNetStatus is set to up).
--
-- Therefore, when virtNetStatus is not up
-- the contents of these objects is undefined. The value
-- returned when accessing the objects is an implementation
-- dependent issue.


--  further connection will be added on a need basis.



mlpppUSapTable       OBJECT-TYPE
      SYNTAX   SEQUENCE OF MlpppUSapEntry
      ACCESS   not-accessible
      STATUS   mandatory
      DESCRIPTION
"The SAP table contains configuration information for each MLPPP layer 
upper SAP (service access point).

Upper SAPs exist at the upper interface of the Multilink PPP layer, and 
are seen as the MLPPP data links by the network layers."
         --#STARTING-VERSION 1
      ::= { cxMLPPP 51 }


mlpppUSapEntry       OBJECT-TYPE
      SYNTAX   MlpppUSapEntry
      ACCESS   not-accessible
      STATUS   mandatory
      DESCRIPTION
"Defines a row in the mlppUSapTable. Each row contains the objects which 
define an upper service access point."
      INDEX { mlpppUSapNumber }
         --#STARTING-VERSION 1
      ::= { mlpppUSapTable 1 }


MlpppUSapEntry ::=
      SEQUENCE {
-- Parameters
         mlpppUSapNumber            SapIndex,
         mlpppUSapRowStatus         INTEGER,
         mlpppUSapAlias             Alias,
-- 
--       mlpppUSapLcInitialMRU      INTEGER,
--       mlpppUSapLcReceiveACCMap   DisplayString,
--       mlpppUSapLcTransmitACCMap  DisplayString,
--       mlpppUSapLcMaxConfigure    INTEGER,
--       mlpppUSapLcMaxTerminate    INTEGER,
--       mlpppUSapLcMaxFailure      INTEGER,
--       mlpppUSapLcRestartTimer    INTEGER,
--       mlpppUSapLcProtFieldComp   INTEGER,
--       mlpppUSapLcACFieldComp     INTEGER,
--       mlpppUSapLcMagicNumber     INTEGER,

-- Implemented in this release         
         mlpppUSapLcInitialMRRU     INTEGER,
         mlpppUSapLcSeqFieldComp    INTEGER,
         mlpppUSapLcUseBACP         INTEGER,
         mlpppUSapTransmitWindow    INTEGER,
-- Generator
         mlpppUSapGenerator                INTEGER,
         mlpppUSapGeneratorLinkUSap        INTEGER,
         mlpppUSapGeneratorFrameSize       INTEGER,
         mlpppUSapGeneratorNumberOfFrames  INTEGER,
         mlpppUSapGeneratorInterFrameDelay INTEGER,
         mlpppUSapGeneratorFramePriority   INTEGER,
-- Control     
         mlpppUSapClearStats        INTEGER,
-- Protocol parameters
         mlpppUSapMlpppMode         INTEGER,

-- Status
         mlpppUSapState             INTEGER,
         mlpppUSapNbPPPLink         INTEGER,
         mlpppUSapLsLocalMRRU       INTEGER, 
         mlpppUSapLsRemoteMRRU      INTEGER,
         mlpppUSapLsLocalToRemoteSeqFieldComp INTEGER,
         mlpppUSapLsRemoteToLocalSeqFieldComp INTEGER,
-- New Status parameters
         mlpppUSapNbPPPLinkUP       INTEGER,
         mlpppUsapGenNcpState       INTEGER,
         mlpppUsapMlpNcpState       INTEGER,
         mlpppUsapBapNcpState       INTEGER,
         mlpppUsapFrNcpState        INTEGER,
         mlpppUsapIpNcpState        INTEGER,
---
-- Statistics
         mlpppUSapNbBytesSent       Counter,
         mlpppUSapNbBytesReceived   Counter
         }

mlpppUSapNumber OBJECT-TYPE
      SYNTAX   SapIndex
      ACCESS   read-only
      STATUS   mandatory
      DESCRIPTION
"Identifies the upper SAP entry with a unique numerical value.

Range of Values: 1 - 100

Default Value: none"
         --#STARTING-VERSION 1
      ::= { mlpppUSapEntry 1 }


mlpppUSapRowStatus      OBJECT-TYPE
      SYNTAX   INTEGER {
               invalid     (1),
               valid    (2)
               }
      ACCESS   read-write
      STATUS   mandatory
      DESCRIPTION
"Determines the status of the objects in a table row.

Options:
invalid (1): Row is deleted from the table, but values are still in effect 
until the next reset.

valid (2): Use this value to add a new row to the table, or modify an 
existing row.

Default Value: invalid (1)

Configuration Changed: administrative" 
     DEFVAL { invalid }
--#STARTING-VERSION 1 
     ::= { mlpppUSapEntry 2 }


mlpppUSapAlias          OBJECT-TYPE
      SYNTAX   Alias
      ACCESS   read-write
      STATUS   mandatory
      DESCRIPTION
"Identifies this upper service access point by a textual name. Names must 
be unique across all service access points at all layers.

Range of Values: 0 - 16 alphanumeric characters 
(first character must be a letter)

Default Value: none

Configuration Changed: administrative"
         --#STARTING-VERSION 1
      ::= { mlpppUSapEntry 3 }



mlpppUSapLcInitialMRRU     OBJECT-TYPE
                  SYNTAX      INTEGER(0..2147483647)
                  ACCESS      read-write
                  STATUS      mandatory
                  DESCRIPTION
"This object is not implemented in this release.

Determines the Maximum Receive Reconstructed Unit (MRRU) in octets 
proposed by the local port. The local port's proposed MRRU is negotiated 
with the remote port's proposed MRRU. The result of the negotiation is 
displayed in mlpppLSapLsLocalMRRU on the mlpppLSapLsTable table.

If this value is 0, then no negotiation will occur with the remote, and 
the default MRRU of 1500 octets is used; otherwise, the local PPP link 
will negotiate for this value with the remote peer.

Range of Values: 0 - 2048

Default Value: 1500

Configuration Changed:  administrative"
      REFERENCE
                              "Section 5.1.1, Maximum Receive 
         Reconstructed Unit of RFC1990."
                  DEFVAL    { 1500 }
         --#STARTING-VERSION 1
                 ::= { mlpppUSapEntry 20 }


mlpppUSapLcSeqFieldComp    OBJECT-TYPE
                  SYNTAX      INTEGER { 
               enabled (1), 
               disabled (2) 
               }
                  ACCESS      read-write
                  STATUS      mandatory
                  DESCRIPTION
"This object is implemented in this release.

Determines whether the Sequence Number Field is compressed or not. If the 
the Sequence Number Field is compressed, then the short sequence number 
header format is used and sequence numbers are 12 bits long. If the 
Sequence Number Field is not compressed, then the long sequence number 
header format is used and sequence numbers are 24 bits long.

Options: 
enabled (1)

disabled (2)

Default Value: disabled (2)

Configuration Changed:  administrative"
                  REFERENCE
                              "Section 5.1.2, Short Sequence Header
         Format Option, of RFC1990."
                  DEFVAL    { disabled }
         --#STARTING-VERSION 1
                  ::= { mlpppUSapEntry 21 }


mlpppUSapLcUseBACP  OBJECT-TYPE
         SYNTAX      INTEGER { 
                 enabled  (1), 
                 disabled (2) 
               }
               ACCESS      read-write
               STATUS      mandatory
               DESCRIPTION
"If enabled, BACP is used for adding/removing links 

Options: 
enabled  (1)

disabled (2)

Default Value: disabled (2)

Configuration Changed:  administrative"
                  REFERENCE
                  "PPP BACP RFC2125."
                  DEFVAL   { disabled }
         --#STARTING-VERSION 1
                  ::= { mlpppUSapEntry 22 }

mlpppUSapTransmitWindow  OBJECT-TYPE
     SYNTAX  INTEGER (1..255)
     ACCESS  read-write
     STATUS  mandatory
     DESCRIPTION
"Determines the size of the transmit window for this SAP, i.e. the maximum number
 of buffers queued by MLPPP before it starts to discard frames

Range of Values: 1 - 255
Default Value: 255
Configuration Changed: administrative "
     DEFVAL { 255 }
         --#STARTING-VERSION 1
     ::= { mlpppUSapEntry 23 }


mlpppUSapGenerator OBJECT-TYPE
     SYNTAX  INTEGER {
          disabled   (1),
          enabled    (2),
          enabledos  (3),
          retrigger  (4)
          }
     ACCESS  read-write
     STATUS  mandatory
     DESCRIPTION
"Determines whether this SAP generates for diagnostic purposes the number 
of frames set by object mlpppUSapGeneratorNumberOfFrames of a size set in 
'mlpppUSapGeneratorFrameSize'.

Options:
disabled (1): frame generator is disabled .
enabled  (2): frame generator is enabled after a system reset to generate a 
              sequence of frames.
enabledos(3): frame generator is enabled after a system reset to generate a 
              sequence of frames.The fragments are sent out-of-sequence.
retrigger(4): frame generator is enabled immediately to generate a sequence 
              of frames.

Default Value: disabled

Configuration Changed: operative "
      DEFVAL { disabled }
         --#STARTING-VERSION 1
     ::= { mlpppUSapEntry 24 }


mlpppUSapGeneratorLinkUSap OBJECT-TYPE
      SYNTAX   INTEGER
      ACCESS   read-write
      STATUS   mandatory
      DESCRIPTION
"Identifies the upper SAP entry to which all received generator frames
 are sent If 0, the received frames are discarded.

Range of Values: 0 - 100

Default Value: 0
Configuration Changed: operative "
         --#STARTING-VERSION 1
      ::= { mlpppUSapEntry 25 }



mlpppUSapGeneratorFrameSize OBJECT-TYPE
     SYNTAX  INTEGER (32..4096)
     ACCESS  read-write
     STATUS  mandatory
     DESCRIPTION
"Determines the size of each frame generated for this SAP.

Range of Values: 32 - 4096

Default Value: 32

Configuration Changed: operative "
     DEFVAL { 32 }
         --#STARTING-VERSION 1
     ::= { mlpppUSapEntry 26 }


mlpppUSapGeneratorNumberOfFrames OBJECT-TYPE
     SYNTAX  INTEGER (1..200)
     ACCESS  read-write
     STATUS  mandatory
     DESCRIPTION
"Determines the number of frames to be generated for this SAP.

Range of Values: 1 - 200 (200=continuous)

Default Value: 1

Configuration Changed: operative "
     DEFVAL { 1 }
         --#STARTING-VERSION 1
          ::= { mlpppUSapEntry 27 }


mlpppUSapGeneratorInterFrameDelay OBJECT-TYPE
     SYNTAX  INTEGER (50..60000)
     ACCESS  read-write
     STATUS  mandatory
     DESCRIPTION
"Determines the time in milliseconds that must pass between frames 
generated for this SAP.

Range of Values: 50 - 60,000

Default Value: 50

Configuration Changed: operative "
     DEFVAL { 50 }
         --#STARTING-VERSION 1
     ::= { mlpppUSapEntry 28 }


mlpppUSapGeneratorFramePriority OBJECT-TYPE
     SYNTAX  INTEGER {
          lowpri       (1),
          medpri       (2),
          highpri      (3),
          veryhighpri  (4)
          }
     ACCESS  read-write
     STATUS  mandatory
     DESCRIPTION
"Determines the priority of SAP generator frames for diagnostic purposes

Options:
lowpri      (1): low priority.
medpri      (2): medium priority 
highpri     (3): high priority 
veryhighpri (4): very high priority 

Default Value: lowpri

Configuration Changed: operative "
      DEFVAL { lowpri }
         --#STARTING-VERSION 1
     ::= { mlpppUSapEntry 29 }


mlpppUSapClearStats     OBJECT-TYPE
      SYNTAX   INTEGER
      ACCESS   write-only
      STATUS   mandatory
      DESCRIPTION
"Clears the statistics counter of the MLPPP link associated with this 
upper SAP.

Options:
clearStats : clears statistics

Default Value: none"
        --#STARTING-VERSION 1
      ::= { mlpppUSapEntry 30 }


mlpppUSapMlpppMode       OBJECT-TYPE
     SYNTAX  INTEGER {
          enabled    (1),
          disabled   (2)
          }
      ACCESS   read-write
      STATUS   mandatory
      DESCRIPTION
"Indicates the current use of this upper SAP. If MLPPP is to be used
for inverse multiplexing, it must be enabled. If disabled, dumb inverse
multiplexing and load balancing is done

Options:

enabled   (1) :   MLPPP is used
disabled  (2) :   dumb inverse multiplexing / load balancing

Default Value: enabled"
         --#STARTING-VERSION 1
      ::= { mlpppUSapEntry 31 }


mlpppUSapState          OBJECT-TYPE
      SYNTAX   INTEGER {
not-used (1),
unbound     (2),
bound    (3)
}
      ACCESS   read-only
      STATUS   mandatory
      DESCRIPTION
"Indicates the current state of this upper SAP.

Options:
not-used (1): SAP not in use

unbound (2): SAP not bound to another software layer

bound (3): SAP bound to another software layer


Default Value: none"
        --#STARTING-VERSION 1
      ::= { mlpppUSapEntry 40 }


mlpppUSapNbPPPLink      OBJECT-TYPE
      SYNTAX      INTEGER(0..100)
                  ACCESS      read-only
                  STATUS      mandatory
                  DESCRIPTION
"Indicates the number of MLPPP lower SAPs that are associated to this 
upper MLPPP SAP.

This value is equivalent to the number of PPP links that are bundled into 
one MLPPP link at this upper SAP.

Range of Values: 0 to 100

Default Value: 0"
      DEFVAL { 0 }
         --#STARTING-VERSION 1
                  ::= { mlpppUSapEntry 41 }



mlpppUSapLsLocalMRRU    OBJECT-TYPE
                  SYNTAX      INTEGER(1..2147483648)
                  ACCESS      read-only
                  STATUS      mandatory
                  DESCRIPTION
"This object is implemented in this release.

Identifies the current value in octets of the Maximum Receive Reconstructed 
Unit (MRRU) for the local bundle. This value is the MRRU that the remote 
is using to send packets over the MLPPP link. 

The MRRU is the maximum number of bytes that a reconstructed (unbundled) 
PPP packet can contain.

This value is meaningful only when the link has reached the
open state (virtNetStatus is up); at which time it displays the result of
the PPP negotiation.

Range of Values: 1 to 2048

Default Value: 1500"
      DEFVAL { 1500 }
         --#STARTING-VERSION 1
                  ::= { mlpppUSapEntry 42 }


mlpppUSapLsRemoteMRRU      OBJECT-TYPE
      SYNTAX      INTEGER(1..2147483648)
                  ACCESS      read-only
                  STATUS      mandatory
                  DESCRIPTION
"This object is implemented in this release.

Identifies the current value in octets of the Maximum Receive 
Reconstructed Unit (MRRU) for the remote bundle. This value is the MRRU 
that the local is using to send packets over the MLPPP link. 

The MRRU is the maximum number of bytes that a reconstructed (unbundled) 
PPP packet can contain.

The value is meaningful only when the link has reached the open state 
(virtNetStatus is up); at which time it displays the result of the PPP 
negotiation.

Range of Values: 1 to 2048

Default Value: 1500"
      DEFVAL { 1500 }
         --#STARTING-VERSION 1
                  ::= { mlpppUSapEntry 43 }

mlpppUSapLsLocalToRemoteSeqFieldComp   OBJECT-TYPE
    SYNTAX      INTEGER {
                        enabled(1),
                        disabled(2)
                        }
                  ACCESS    read-only
                  STATUS    mandatory
                  DESCRIPTION
"This object is implemented in this release.

Indicates whether the local end of the MLPPP link is using short sequence 
field (12 bits) when it transmits packets to the remote.

The value is meaningful only when the link has reached the open state 
(virtNetStatus is up); at which time it displays the result of the PPP 
negotiation.

Options: 
enabled (1)

disabled (2)

Default Value: enabled (1)"
      DEFVAL { enabled }
         --#STARTING-VERSION 1
                  ::= { mlpppUSapEntry 44 }


mlpppUSapLsRemoteToLocalSeqFieldComp   OBJECT-TYPE
    SYNTAX      INTEGER {
                        enabled(1),
                        disabled(2)
                        }
                  ACCESS    read-only
                  STATUS    mandatory
                  DESCRIPTION
"This object is implemented in this release.

Indicates whether the remote end of the MLPPP link is using short sequence 
field (12 bits) when it transmits packets to the local.

The value is meaningful only when the link has reached the open state 
(virtNetStatus is up); at which time it displays the result of the PPP 
negotiation.

Options:
enabled (1)

disabled (2)

Default Value: enabled (1)"
      DEFVAL { enabled }
         --#STARTING-VERSION 1
                  ::= { mlpppUSapEntry 45 }



-- New Status parameters

mlpppUSapNbPPPLinkUP      OBJECT-TYPE   
                  SYNTAX  INTEGER
                  ACCESS  read-only
                  STATUS  mandatory
                  DESCRIPTION
"The number of PPP links in a bundle which succesfully finished the LCP
 configuration phase. The PPP layer is UP on that many links of the bundle."
                  ::= { mlpppUSapEntry 46 }

mlpppUsapMlpNcpState      OBJECT-TYPE   
                  SYNTAX  INTEGER {
                            ncp-up  (1),
                            ncp-down(2),
                            ncp-na  (3)
                          }
                  ACCESS    read-only
                  STATUS    mandatory
                  DESCRIPTION
"The state of the NCP associated with the MLPPP protocol. The bundle can
 talk MLPPP only after the MRRU option has been succesfully negociated.

Options:
   ncp-up   (1)  : the NCP state is up
   ncp-down (2)  : the NCP state is down
   ncp-na   (3)  : the NCP state is not available
Default value: none"
         --#STARTING-VERSION 1
                  ::= { mlpppUSapEntry 47 }


mlpppUsapGenNcpState      OBJECT-TYPE   
                  SYNTAX  INTEGER {
                            ncp-up  (1),
                            ncp-down(2),
                            ncp-na  (3)
                          }
                  ACCESS    read-only
                  STATUS    mandatory
                  DESCRIPTION
"The state of the NCP associated with the MLPPP frame generator PID. The
 generator can be used only after two bundles have negociated the use of
 a specific PID for the generated frames. The protocol ID for the MLPPP
 frame generator is MEMOTEC proprietary and it's default value is 0xcf 
 and it's NCP is using by default 0x80cf.

Options:
   ncp-up   (1)  : the NCP state is up
   ncp-down (2)  : the NCP state is down
   ncp-na   (3)  : the NCP state is not available
Default value: none"
         --#STARTING-VERSION 1
                  ::= { mlpppUSapEntry 48 }

mlpppUsapBapNcpState      OBJECT-TYPE   
                  SYNTAX  INTEGER {
                            ncp-up  (1),
                            ncp-down(2),
                            ncp-na  (3)
                          }
                  ACCESS    read-only
                  STATUS    mandatory
                  DESCRIPTION
"The state of the NCP associated with the BAP protocol. The BAP protocol
 can be used only after two bundles have negociated it's use for adding or
 removing links to the bundles.

Options:
   ncp-up   (1)  : the NCP state is up
   ncp-down (2)  : the NCP state is down
   ncp-na   (3)  : the NCP state is not available
Default value: none"
         --#STARTING-VERSION 1
                  ::= { mlpppUSapEntry 49 }

mlpppUsapFrNcpState       OBJECT-TYPE   
                  SYNTAX  INTEGER {
                            ncp-up  (1),
                            ncp-down(2),
                            ncp-na  (3)
                          }
                  ACCESS    read-only
                  STATUS    mandatory
                  DESCRIPTION
"The state of the NCP associated with the FR protocol. The FR protocol
 can be used over MLPPP only after two bundles have negociated the FRNCP
 configuration. The protocol ID for FR over MLPPP is MEMOTEC proprietary
 and it's default value is 0xcd and for it's NCP 0x80cd.

Options:
   ncp-up   (1)  : the NCP state is up
   ncp-down (2)  : the NCP state is down
   ncp-na   (3)  : the NCP state is not available
Default value: none"
         --#STARTING-VERSION 1
                  ::= { mlpppUSapEntry 50 }

mlpppUsapIpNcpState       OBJECT-TYPE   
                  SYNTAX  INTEGER {
                            ncp-up  (1),
                            ncp-down(2),
                            ncp-na  (3)
                          }
                  ACCESS    read-only
                  STATUS    mandatory
                  DESCRIPTION
"The state of the NCP associated with the IP protocol. The IP protocol
 can be used over MLPPP only after two bundles have negociated the IPNCP
 configuration.
Options:
   ncp-up   (1)  : the NCP state is up
   ncp-down (2)  : the NCP state is down
   ncp-na   (3)  : the NCP state is not available
Default value: none"
         --#STARTING-VERSION 1
                  ::= { mlpppUSapEntry 51 }


mlpppUSapNbBytesSent       OBJECT-TYPE
      SYNTAX      Counter
                  ACCESS      read-only
                  STATUS      mandatory
                  DESCRIPTION
"Indicates the number of bytes sent to the network layer through this 
upper SAP since system startup, or since last statistics reset.

Range of Values: 0 - 4,294,967,295

Default Value: none"
         --#STARTING-VERSION 1
                  ::= { mlpppUSapEntry 70 }


mlpppUSapNbBytesReceived      OBJECT-TYPE
      SYNTAX      Counter
                  ACCESS      read-only
                  STATUS      mandatory
                  DESCRIPTION
"Indicates the number of bytes received from the network layer through 
this upper SAP since system startup, or since last statistics reset.

Range of Values: 0 - 4,294,967,295

Default Value: none"
         --#STARTING-VERSION 1
                  ::= { mlpppUSapEntry 71 }


END
