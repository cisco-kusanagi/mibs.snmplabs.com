AIXIRB-MIB DEFINITIONS ::=  BEGIN

-- Applied Innovation XIRB MIB definitions

IMPORTS
		MODULE-IDENTITY, OBJECT-TYPE, 
		enterprises
				FROM SNMPv2-SMI;


-- group object IDs

aii             OBJECT IDENTIFIER ::= { enterprises 539 }
aiSystemOID     OBJECT IDENTIFIER ::= { aii 2 }
aiSLC2		OBJECT IDENTIFIER ::= { aii 16 }

aiXirb	MODULE-IDENTITY
		LAST-UPDATED "0006201510Z"
		ORGANIZATION "Applied Innovation Inc."
		CONTACT-INFO
				"        Engineering MIB Administrator

				Postal:  Applied Innovation Inc.
								 5800 Innovation Drive
								 Dublin, OH 43016-3271

					 Tel:  614/798-2000
					 Fax:  614/798-1770
				E-mail:  snmp@aiinet.com"
		DESCRIPTION
				"SLC MIB for misc. TCP options and passive/extended link settings"
		::= { aiSLC2 5 }

-- System group for XIRBs

aiXirbSystem	OBJECT IDENTIFIER ::= { aiXirb 1 }

-- TCP group

aiXirbTcp		OBJECT IDENTIFIER ::= { aiXirb 2 }

aiXirbTcpWindowSize OBJECT-TYPE
	SYNTAX		INTEGER { ws200 (1), ws512 (2), ws1024 (3), ws2048 (4) }
	MAX-ACCESS	read-write
	STATUS		current
	DESCRIPTION
			"Default window size for TCP connections.  Current
			connections will maintain their current window sizes,
			but new connections will use the updated window size."
	::= { aiXirbTcp 1 }

aiXirbTcpSendAhead OBJECT-TYPE
	SYNTAX		INTEGER { disabled (1), enabled (2) }
	MAX-ACCESS	read-write
	STATUS		current
	DESCRIPTION
			"Indicates whether or not TCP connections wait for
			data acknowledgment before sending more data (if
			disabled (1)), or send the maximum TCP window size
			before requiring data to be acknowledged (if enabled (2))."
	::= { aiXirbTcp 2 }

-- X.25 group

aiXirbX25		OBJECT IDENTIFIER ::= { aiXirb 3 }

aiXirbBx25CallDown OBJECT-TYPE
	SYNTAX		INTEGER { on(1), off(2) }
	MAX-ACCESS	read-write
	STATUS		current
	DESCRIPTION
		"If set to off(2), a passive link will stay up after all
		 calls are disconnected. If set to on(1), a passive link
		 will drop and go into DMLOCK (see aiXirbBx25DMlock below) when
		 all the incomming calls are terminated. This object is
		 meaningful only when aiLinkX25LinkMode is set to passive(2)
		 on a given link"
	DEFVAL		{ off }
	::= { aiXirbX25 1 }

aiXirbBx25DMlock OBJECT-TYPE
	SYNTAX		INTEGER (25..6000000)
	MAX-ACCESS	read-write
	STATUS		current
	DESCRIPTION
		"The number of seconds to wait for after a link has gone
		 inactive before allowing an outgoing call to attemp to bring
		 up the link. Any outgoing call attempts will be rejected
		 until the DMLOCK timer expires and the passive link returns
		 to the standby mode. This object is meaningful only when
		 aiLinkX25LinkMode is set to passive(2) on a given link"
	DEFVAL		{ 60 }
	::= { aiXirbX25 2 }

aiXirbBx25LinkUp OBJECT-TYPE
	SYNTAX		INTEGER (5..6000000)
	MAX-ACCESS	read-write
	STATUS		current
	DESCRIPTION
		"The number of seconds to wait for a passive link to become
		 active. This object is meaningful only when aiLinkX25LinkMode
		 is set to passive(2) on a given link"
	DEFVAL		{ 25 }
	::= { aiXirbX25 3 }



aiXirbCpuStats 		OBJECT IDENTIFIER ::= { aiXirb 4 }

aiXirbCpuStatsCurrent OBJECT-TYPE
	SYNTAX  	INTEGER (0..100)
	MAX-ACCESS 	read-only
	STATUS 		current
	DESCRIPTION 
		"This indicates the average of percentage CPU utilization during 
		 last 60 seconds"
	::= { aiXirbCpuStats 1 }

aiXirbCpuStatsMax  OBJECT-TYPE
	SYNTAX  	INTEGER (0..100)
	MAX-ACCESS 	read-only
	STATUS 		current
	DESCRIPTION 
		"This shows the maximum percentage CPU utilization during last 24 
		 hours. This value is calculated from the average CPU utilization 
		 information which is found every 60 seconds."
	::= { aiXirbCpuStats 2 }

aiXirbCpuStatsReset OBJECT-TYPE
	SYNTAX  	INTEGER { normal (1), reset (2) }
	MAX-ACCESS 	read-write
	STATUS 		current
	DESCRIPTION 
		"This resets the CPU utilization statistics"
	::= { aiXirbCpuStats 3 }


aiXirbEthernet 		OBJECT IDENTIFIER ::= { aiXirb 5 }

aiXirbPpc10BaseT OBJECT-TYPE
	SYNTAX		INTEGER { off(1), on(2) }
	MAX-ACCESS	read-write
	STATUS		current
	DESCRIPTION
		"Determines whether the front panel 10 BaseT interface is enabled or not
			on  - to enable the 10 BaseT interface
			off - to disable the 10 BaseT interface"
	DEFVAL		{ 1 }
	::= { aiXirbEthernet 1 }

aiXirb10BaseTDuplex OBJECT-TYPE
  SYNTAX    INTEGER { full(1), half(2) }
  MAX-ACCESS  read-write
  STATUS      current
  DESCRIPTION
    "For AIwan only.  Setting this to full(1) puts the AIwan Ethernet
    interface into Full Duplex mode (sends and receives simultaneously).
    Setting this to half(2) puts the AIwan Ethernet interface into
    Half Duplex mode (sends OR receives, but not simultaneously -- this
    means that collisions are possible).  In general, half duplex works
    fine for switches AND hubs, whereas full duplex mode should only be
    used with switches or other interfaces that are full duplex capable."
  ::= { aiXirbEthernet 2 }
    
END
