QB-CESV2-MIB DEFINITIONS ::= BEGIN

	IMPORTS 
	MODULE-IDENTITY, OBJECT-TYPE, Counter32
		FROM SNMPv2-SMI 
	DisplayString,  TimeStamp
		FROM SNMPv2-TC
	MODULE-COMPLIANCE, OBJECT-GROUP
		FROM SNMPv2-CONF
	atmfCESStatsEntry, atmfCESConfEntry
		FROM ATMF-CES 
        AtmAddr, AtmConnKind, AtmConnCastType,
        AtmServiceCategory, AtmTrafficDescrParamIndex,
        AtmVpIdentifier, AtmVcIdentifier,
        AtmVorXAdminStatus, AtmVorXLastChange,
        AtmVorXOperStatus, atmNoClpNoScr
            FROM ATM-TC-MIB
	qbMibs
		FROM QUANTUMBRIDGE-REG
	QbEnableStatus, QbPvcConnKind, QbBitRate
		FROM QB-DWS-MIB
	;    

	qbCESMIB MODULE-IDENTITY
	LAST-UPDATED "0002142001Z" -- March 14, 2001
	ORGANIZATION "Quantum Bridge Inc."
	CONTACT-INFO
		"mvaysman@quantumbridge.com"
	DESCRIPTION
		"This module defines additional objects for the management of DS1 
		links in Quantum Bridge devices, above and beyond that is defined in the
		standard CESV2 mib, and proposed drafts."
	::= { qbMibs 4 }

	-- Top-level organization of the MIB

	qbCESObjects		  OBJECT IDENTIFIER ::= { qbCESMIB 1 }
	qbCESTables		  OBJECT IDENTIFIER ::= { qbCESMIB 2 }
	qbCESConformance	  OBJECT IDENTIFIER ::= { qbCESMIB 3 }

-- **************************************************************
-- Extensions to the CES Configuraton Table
-- **************************************************************

   qbCESConfTable  OBJECT-TYPE
	SYNTAX      SEQUENCE OF QbCESConfEntry
	MAX-ACCESS  not-accessible
	STATUS      current
	DESCRIPTION
	     "The Quantum Bridge CES Configuration Table contains 
             extensions to the CES V2 Configuration Table."
    ::= { qbCESTables 1 }
	
    qbCESConfEntry   OBJECT-TYPE
	SYNTAX      QbCESConfEntry
	MAX-ACCESS  not-accessible
	STATUS      current
	DESCRIPTION
            "An entry in the Quantum Bridge CES Configuration Table."
	AUGMENTS    { atmfCESConfEntry  }
	::= { qbCESConfTable 1 }

    QbCESConfEntry ::=
		   SEQUENCE {
		   qbCESConfConnName			DisplayString,
		   qbCESConfConnRxTrafficDescrIndex	AtmTrafficDescrParamIndex,
		   qbCESConfConnTxTrafficDescrIndex     AtmTrafficDescrParamIndex,
		   qbCESConfConnLoopback		QbEnableStatus,
		   qbCESConfConnKind			QbPvcConnKind
		   }

    qbCESConfConnName OBJECT-TYPE
        SYNTAX      DisplayString (SIZE (0..20))
	MAX-ACCESS  read-create
	STATUS      current
	DESCRIPTION
		"A textual description for the CBR traffic conection."
		DEFVAL  { "" }
	::= { qbCESConfEntry  1 }

   qbCESConfConnRxTrafficDescrIndex OBJECT-TYPE
	SYNTAX	    AtmTrafficDescrParamIndex
    	MAX-ACCESS  read-create
    	STATUS	    current
    	DESCRIPTION
		"The value of this object identifies the row
		in the ATM Traffic Descriptor Table which
		applies to the receive direction of this VCL."
	DEFVAL  { 1 }
	::= {  qbCESConfEntry 2 }

   qbCESConfConnTxTrafficDescrIndex OBJECT-TYPE
	SYNTAX	    AtmTrafficDescrParamIndex
    	MAX-ACCESS  read-create
    	STATUS	    current
    	DESCRIPTION
		"The value of this object identifies the row
		in the ATM Traffic Descriptor Table which
		applies to the transmit direction of this VCL."
	DEFVAL  { 1 }
	::= {  qbCESConfEntry 3 }

  qbCESConfConnLoopback OBJECT-TYPE
	SYNTAX      QbEnableStatus
	MAX-ACCESS  read-create
	STATUS      current
	DESCRIPTION
		"This object enables loopback on the IOT DS1/E1  
		enedpoint."
	::= { qbCESConfEntry   4}	

  qbCESConfConnKind   OBJECT-TYPE
	SYNTAX        QbPvcConnKind 
	MAX-ACCESS    read-create
	STATUS        current
	DESCRIPTION
		 "The PVC connection type."
    ::= { qbCESConfEntry 5 }


  qbCESStatsTable  OBJECT-TYPE
	SYNTAX      SEQUENCE OF QbCESStatsEntry
	MAX-ACCESS  not-accessible
	STATUS      current
	DESCRIPTION
	     "The Quantum Bridge CES Statistics Table contains 
             extensions to the CES V2 Statistics Table."
    ::= { qbCESTables 2 }
	
    qbCESStatsEntry   OBJECT-TYPE
	SYNTAX      QbCESStatsEntry
	MAX-ACCESS  not-accessible
	STATUS      current
	DESCRIPTION
            "An entry in the Quantum Bridge CES Statistics Table."
	AUGMENTS    { atmfCESStatsEntry  }
	::= { qbCESStatsTable 1 }

    QbCESStatsEntry ::=
		   SEQUENCE {
		   qbCESStatsTxCells		Counter32,
		   qbCESStatsCrcErrs		Counter32,   
		   qbCESStatsReplacedCells	Counter32,
		   qbCESStatsDroppedCells	Counter32
		   }

    qbCESStatsTxCells OBJECT-TYPE
    SYNTAX      Counter32
	MAX-ACCESS  read-only
	STATUS      current
	DESCRIPTION
		"Cells transmitted on this emulated circuit."
	::= { qbCESStatsEntry  1 }     
	
    qbCESStatsCrcErrs OBJECT-TYPE
    SYNTAX      Counter32
	MAX-ACCESS  read-only
	STATUS      current
	DESCRIPTION
		"The count of CRC errors."
	::= { qbCESStatsEntry  2 }


    qbCESStatsReplacedCells OBJECT-TYPE
    SYNTAX      Counter32
	MAX-ACCESS  read-only
	STATUS      current
	DESCRIPTION
		"Replaced Cells."
	::= { qbCESStatsEntry  3 }

    qbCESStatsDroppedCells OBJECT-TYPE
    SYNTAX      Counter32
	MAX-ACCESS  read-only
	STATUS      current
	DESCRIPTION
		"Dropped Cells."
	::= { qbCESStatsEntry  4 }


-- ****************************************************************
-- Conformance Information
-- ****************************************************************

   qbCESCompliances OBJECT IDENTIFIER ::= { qbCESConformance 1 }
   qbCESGroups      OBJECT IDENTIFIER ::= { qbCESConformance 2 }

--
-- Compliance Statements
--

    qbCESCompliance MODULE-COMPLIANCE
	STATUS      current
	DESCRIPTION
		"The compliance statement for all agents that support this
		MIB. A compliant agent implements all objects defined in this
		MIB."
	MODULE  -- this module
	MANDATORY-GROUPS {
		qbCESAllGroup
		}
    ::= { qbCESCompliances 1 }

--
-- All Object Groups
--
     qbCESAllGroup OBJECT-GROUP
        OBJECTS {
	qbCESConfConnName,
	qbCESConfConnRxTrafficDescrIndex,
	qbCESConfConnTxTrafficDescrIndex,
	qbCESConfConnLoopback, 
	qbCESStatsTxCells,
	qbCESStatsCrcErrs,   
	qbCESStatsReplacedCells,
	qbCESStatsDroppedCells
	}
	STATUS      current
	DESCRIPTION
		"The set of all accessible objects in this MIB."
    ::= { qbCESGroups 1 }

END
