--
-- This SMIv2 module has been generated by smidump 0.2-cvs. Do not edit.
--

SONUS-IP-PROTOCOL-MIB DEFINITIONS ::= BEGIN

IMPORTS
    Counter32, Gauge32, Integer32, IpAddress, MODULE-IDENTITY, 
    OBJECT-TYPE
        FROM SNMPv2-SMI
    sonusPacketMIBs
        FROM SONUS-SMI;

sonusIpProtocolMIB MODULE-IDENTITY
    LAST-UPDATED    "200008280000Z"
    ORGANIZATION    
            "Sonus Networks, Inc."
    CONTACT-INFO    
            "   Customer Support    
             Sonus Networks, Inc,
             5 carlisle Road
             Westford, MA 01886
             USA
             
             Tel: 978-692-8999
             Fax: 978-392-9118
             E-mail: cs.snmp@sonusnet.com"
    DESCRIPTION     
            "The MIB Module for IP Protocol Management."
    ::= { sonusPacketMIBs 4 }


sonusMib-2 OBJECT IDENTIFIER
    ::= { sonusIpProtocolMIB 2 }

sonusIp OBJECT IDENTIFIER
    ::= { sonusMib-2 4 }

sonusIpGeneralGroupTable OBJECT-TYPE
    SYNTAX          SEQUENCE OF SonusIpGeneralGroupEntry
    MAX-ACCESS      not-accessible
    STATUS          current
    DESCRIPTION     
            "The collection of IP General Group information for the
             specified instance."
    ::= { sonusIp 1 }

sonusIpGeneralGroupEntry OBJECT-TYPE
    SYNTAX          SonusIpGeneralGroupEntry
    MAX-ACCESS      not-accessible
    STATUS          current
    DESCRIPTION     
            "The collection of IP General Group information for the
             specified instance."
    INDEX           { sonusIpGeneralGroupShelf, sonusIpGeneralGroupSlot, 
                      sonusIpGeneralGroupInstance }
    ::= { sonusIpGeneralGroupTable 1 }

SonusIpGeneralGroupEntry ::=
    SEQUENCE {
        sonusIpForwarding               INTEGER,
        sonusIpDefaultTTL               Integer32,
        sonusIpInReceives               Counter32,
        sonusIpInHdrErrors              Counter32,
        sonusIpInAddrErrors             Counter32,
        sonusIpForwDatagrams            Counter32,
        sonusIpInUnknownProtos          Counter32,
        sonusIpInDiscards               Counter32,
        sonusIpInDelivers               Counter32,
        sonusIpOutRequests              Counter32,
        sonusIpOutDiscards              Counter32,
        sonusIpOutNoRoutes              Counter32,
        sonusIpReasmTimeout             Integer32,
        sonusIpReasmReqds               Counter32,
        sonusIpReasmOKs                 Counter32,
        sonusIpReasmFails               Counter32,
        sonusIpFragOKs                  Counter32,
        sonusIpFragFails                Counter32,
        sonusIpFragCreates              Counter32,
        sonusIpRoutingDiscards          Counter32,
        sonusIpGeneralGroupShelf        Integer32,
        sonusIpGeneralGroupSlot         Integer32,
        sonusIpGeneralGroupInstance     Integer32
    }

sonusIpForwarding OBJECT-TYPE
    SYNTAX          INTEGER { forwarding(1), notForwarding(2) }
    MAX-ACCESS      read-only
    STATUS          current
    DESCRIPTION     
            "The indication of whether this entity is acting as an IP
             router in respect to the forwarding of datagrams received
             by, but not addressed to, this entity.  IP routers forward
             datagrams.  IP hosts do not (except those source-routed via
             the host)."
    ::= { sonusIpGeneralGroupEntry 1 }

sonusIpDefaultTTL OBJECT-TYPE
    SYNTAX          Integer32 (1..255)
    MAX-ACCESS      read-only
    STATUS          current
    DESCRIPTION     
            "The default value inserted into the Time-To-Live field of
             the IP header of datagrams originated at this entity,
             whenever a TTL value is not supplied by the transport layer
             protocol."
    ::= { sonusIpGeneralGroupEntry 2 }

sonusIpInReceives OBJECT-TYPE
    SYNTAX          Counter32
    MAX-ACCESS      read-only
    STATUS          current
    DESCRIPTION     
            "The total number of input datagrams received from
             interfaces, including those received in error."
    ::= { sonusIpGeneralGroupEntry 3 }

sonusIpInHdrErrors OBJECT-TYPE
    SYNTAX          Counter32
    MAX-ACCESS      read-only
    STATUS          current
    DESCRIPTION     
            "The number of input datagrams discarded due to errors in
             their IP headers, including bad checksums, version number
             mismatch, other format errors, time-to-live exceeded, errors
             discovered in processing their IP options, etc."
    ::= { sonusIpGeneralGroupEntry 4 }

sonusIpInAddrErrors OBJECT-TYPE
    SYNTAX          Counter32
    MAX-ACCESS      read-only
    STATUS          current
    DESCRIPTION     
            "The number of input datagrams discarded because the IP
             address in their IP header's destination field was not a
             valid address to be received at this entity.  This count
             includes invalid addresses (e.g., 0.0.0.0) and addresses of
             unsupported Classes (e.g., Class E).  For entities which are
             not IP routers and therefore do not forward datagrams, this
             counter includes datagrams discarded because the destination
             address was not a local address."
    ::= { sonusIpGeneralGroupEntry 5 }

sonusIpForwDatagrams OBJECT-TYPE
    SYNTAX          Counter32
    MAX-ACCESS      read-only
    STATUS          current
    DESCRIPTION     
            "The number of input datagrams for which this entity was not
             their final IP destination, as a result of which an attempt
             was made to find a route to forward them to that final
             destination.  In entities which do not act as IP routers,
             this counter will include only those packets which were
             Source-Routed via this entity, and the Source-Route option
             processing was successful."
    ::= { sonusIpGeneralGroupEntry 6 }

sonusIpInUnknownProtos OBJECT-TYPE
    SYNTAX          Counter32
    MAX-ACCESS      read-only
    STATUS          current
    DESCRIPTION     
            "The number of locally-addressed datagrams received
             successfully but discarded because of an unknown or
             unsupported protocol."
    ::= { sonusIpGeneralGroupEntry 7 }

sonusIpInDiscards OBJECT-TYPE
    SYNTAX          Counter32
    MAX-ACCESS      read-only
    STATUS          current
    DESCRIPTION     
            "The number of input IP datagrams for which no problems were
             encountered to prevent their continued processing, but which
             were discarded (e.g., for lack of buffer space).  Note that
             this counter does not include any datagrams discarded while
             awaiting re-assembly."
    ::= { sonusIpGeneralGroupEntry 8 }

sonusIpInDelivers OBJECT-TYPE
    SYNTAX          Counter32
    MAX-ACCESS      read-only
    STATUS          current
    DESCRIPTION     
            "The total number of input datagrams successfully delivered
             to IP user-protocols (including ICMP)."
    ::= { sonusIpGeneralGroupEntry 9 }

sonusIpOutRequests OBJECT-TYPE
    SYNTAX          Counter32
    MAX-ACCESS      read-only
    STATUS          current
    DESCRIPTION     
            "The total number of IP datagrams which local IP user-
             protocols (including ICMP) supplied to IP in requests for
             transmission.  Note that this counter does not include any
             datagrams counted in ipForwDatagrams."
    ::= { sonusIpGeneralGroupEntry 10 }

sonusIpOutDiscards OBJECT-TYPE
    SYNTAX          Counter32
    MAX-ACCESS      read-only
    STATUS          current
    DESCRIPTION     
            "The number of output IP datagrams for which no problem was
             encountered to prevent their transmission to their
             destination, but which were discarded (e.g., for lack of
             buffer space).  Note that this counter would include
             datagrams counted in ipForwDatagrams if any such packets met
             this (discretionary) discard criterion."
    ::= { sonusIpGeneralGroupEntry 11 }

sonusIpOutNoRoutes OBJECT-TYPE
    SYNTAX          Counter32
    MAX-ACCESS      read-only
    STATUS          current
    DESCRIPTION     
            "The number of IP datagrams discarded because no route could
             be found to transmit them to their destination.  Note that
             this counter includes any packets counted in ipForwDatagrams
             which meet this `no-route' criterion.  Note that this
             includes any datagrams which a host cannot route because all
             of its default routers are down."
    ::= { sonusIpGeneralGroupEntry 12 }

sonusIpReasmTimeout OBJECT-TYPE
    SYNTAX          Integer32
    MAX-ACCESS      read-only
    STATUS          current
    DESCRIPTION     
            "The maximum number of seconds which received fragments are
             held while they are awaiting reassembly at this entity."
    ::= { sonusIpGeneralGroupEntry 13 }

sonusIpReasmReqds OBJECT-TYPE
    SYNTAX          Counter32
    MAX-ACCESS      read-only
    STATUS          current
    DESCRIPTION     
            "The number of IP fragments received which needed to be
             reassembled at this entity."
    ::= { sonusIpGeneralGroupEntry 14 }

sonusIpReasmOKs OBJECT-TYPE
    SYNTAX          Counter32
    MAX-ACCESS      read-only
    STATUS          current
    DESCRIPTION     
            "The number of IP datagrams successfully re-assembled."
    ::= { sonusIpGeneralGroupEntry 15 }

sonusIpReasmFails OBJECT-TYPE
    SYNTAX          Counter32
    MAX-ACCESS      read-only
    STATUS          current
    DESCRIPTION     
            "The number of failures detected by the IP re-assembly
             algorithm (for whatever reason: timed out, errors, etc).
             Note that this is not necessarily a count of discarded IP
             fragments since some algorithms (notably the algorithm in
             RFC 815) can lose track of the number of fragments by
             combining them as they are received."
    ::= { sonusIpGeneralGroupEntry 16 }

sonusIpFragOKs OBJECT-TYPE
    SYNTAX          Counter32
    MAX-ACCESS      read-only
    STATUS          current
    DESCRIPTION     
            "The number of IP datagrams that have been successfully
             fragmented at this entity."
    ::= { sonusIpGeneralGroupEntry 17 }

sonusIpFragFails OBJECT-TYPE
    SYNTAX          Counter32
    MAX-ACCESS      read-only
    STATUS          current
    DESCRIPTION     
            "The number of IP datagrams that have been discarded because
             they needed to be fragmented at this entity but could not
             be, e.g., because their Don't Fragment flag was set."
    ::= { sonusIpGeneralGroupEntry 18 }

sonusIpFragCreates OBJECT-TYPE
    SYNTAX          Counter32
    MAX-ACCESS      read-only
    STATUS          current
    DESCRIPTION     
            "The number of IP datagram fragments that have been
             generated as a result of fragmentation at this entity."
    ::= { sonusIpGeneralGroupEntry 19 }

sonusIpRoutingDiscards OBJECT-TYPE
    SYNTAX          Counter32
    MAX-ACCESS      read-only
    STATUS          current
    DESCRIPTION     
            "The number of routing entries which were chosen to be
             discarded even though they are valid.  One possible reason
             for discarding such an entry could be to free-up buffer
             space for other routing entries."
    ::= { sonusIpGeneralGroupEntry 23 }

sonusIpGeneralGroupShelf OBJECT-TYPE
    SYNTAX          Integer32
    MAX-ACCESS      read-only
    STATUS          current
    DESCRIPTION     
            "A 32-bit integer identifying the shelf
             that the IP General Group table applies to"
    ::= { sonusIpGeneralGroupEntry 24 }

sonusIpGeneralGroupSlot OBJECT-TYPE
    SYNTAX          Integer32
    MAX-ACCESS      read-only
    STATUS          current
    DESCRIPTION     
            "A 32-bit integer identifying the slot
             that the IP General Group table applies to"
    ::= { sonusIpGeneralGroupEntry 25 }

sonusIpGeneralGroupInstance OBJECT-TYPE
    SYNTAX          Integer32
    MAX-ACCESS      read-only
    STATUS          current
    DESCRIPTION     
            "A 32-bit integer identifying the instance
             that the IP General Group table applies to"
    ::= { sonusIpGeneralGroupEntry 26 }

sonusIcmp OBJECT IDENTIFIER
    ::= { sonusMib-2 5 }

sonusIcmpGeneralGroupTable OBJECT-TYPE
    SYNTAX          SEQUENCE OF SonusIcmpGeneralGroupEntry
    MAX-ACCESS      not-accessible
    STATUS          current
    DESCRIPTION     
            "The collection of ICMP General Group information for the
             specified instance."
    ::= { sonusIcmp 1 }

sonusIcmpGeneralGroupEntry OBJECT-TYPE
    SYNTAX          SonusIcmpGeneralGroupEntry
    MAX-ACCESS      not-accessible
    STATUS          current
    DESCRIPTION     
            "The collection of ICMP General Group information for the
             specified instance."
    INDEX           { sonusIcmpGeneralGroupShelf, 
                      sonusIcmpGeneralGroupSlot, 
                      sonusIcmpGeneralGroupInstance }
    ::= { sonusIcmpGeneralGroupTable 1 }

SonusIcmpGeneralGroupEntry ::=
    SEQUENCE {
        sonusIcmpInMsgs                 Counter32,
        sonusIcmpInErrors               Counter32,
        sonusIcmpInDestUnreachs         Counter32,
        sonusIcmpInTimeExcds            Counter32,
        sonusIcmpInParmProbs            Counter32,
        sonusIcmpInSrcQuenchs           Counter32,
        sonusIcmpInRedirects            Counter32,
        sonusIcmpInEchos                Counter32,
        sonusIcmpInEchoReps             Counter32,
        sonusIcmpInTimestamps           Counter32,
        sonusIcmpInTimestampReps        Counter32,
        sonusIcmpInAddrMasks            Counter32,
        sonusIcmpInAddrMaskReps         Counter32,
        sonusIcmpOutMsgs                Counter32,
        sonusIcmpOutErrors              Counter32,
        sonusIcmpOutDestUnreachs        Counter32,
        sonusIcmpOutTimeExcds           Counter32,
        sonusIcmpOutParmProbs           Counter32,
        sonusIcmpOutSrcQuenchs          Counter32,
        sonusIcmpOutRedirects           Counter32,
        sonusIcmpOutEchos               Counter32,
        sonusIcmpOutEchoReps            Counter32,
        sonusIcmpOutTimestamps          Counter32,
        sonusIcmpOutTimestampReps       Counter32,
        sonusIcmpOutAddrMasks           Counter32,
        sonusIcmpOutAddrMaskReps        Counter32,
        sonusIcmpGeneralGroupShelf      Integer32,
        sonusIcmpGeneralGroupSlot       Integer32,
        sonusIcmpGeneralGroupInstance   Integer32
    }

sonusIcmpInMsgs OBJECT-TYPE
    SYNTAX          Counter32
    MAX-ACCESS      read-only
    STATUS          current
    DESCRIPTION     
            "The total number of ICMP messages which the entity
             received.  Note that this counter includes all those counted
             by icmpInErrors."
    ::= { sonusIcmpGeneralGroupEntry 1 }

sonusIcmpInErrors OBJECT-TYPE
    SYNTAX          Counter32
    MAX-ACCESS      read-only
    STATUS          current
    DESCRIPTION     
            "The number of ICMP messages which the entity received but
             determined as having ICMP-specific errors (bad ICMP
             checksums, bad length, etc.)."
    ::= { sonusIcmpGeneralGroupEntry 2 }

sonusIcmpInDestUnreachs OBJECT-TYPE
    SYNTAX          Counter32
    MAX-ACCESS      read-only
    STATUS          current
    DESCRIPTION     
            "The number of ICMP Destination Unreachable messages
             received."
    ::= { sonusIcmpGeneralGroupEntry 3 }

sonusIcmpInTimeExcds OBJECT-TYPE
    SYNTAX          Counter32
    MAX-ACCESS      read-only
    STATUS          current
    DESCRIPTION     
            "The number of ICMP Time Exceeded messages received."
    ::= { sonusIcmpGeneralGroupEntry 4 }

sonusIcmpInParmProbs OBJECT-TYPE
    SYNTAX          Counter32
    MAX-ACCESS      read-only
    STATUS          current
    DESCRIPTION     
            "The number of ICMP Parameter Problem messages received."
    ::= { sonusIcmpGeneralGroupEntry 5 }

sonusIcmpInSrcQuenchs OBJECT-TYPE
    SYNTAX          Counter32
    MAX-ACCESS      read-only
    STATUS          current
    DESCRIPTION     
            "The number of ICMP Source Quench messages received."
    ::= { sonusIcmpGeneralGroupEntry 6 }

sonusIcmpInRedirects OBJECT-TYPE
    SYNTAX          Counter32
    MAX-ACCESS      read-only
    STATUS          current
    DESCRIPTION     
            "The number of ICMP Redirect messages received."
    ::= { sonusIcmpGeneralGroupEntry 7 }

sonusIcmpInEchos OBJECT-TYPE
    SYNTAX          Counter32
    MAX-ACCESS      read-only
    STATUS          current
    DESCRIPTION     
            "The number of ICMP Echo (request) messages received."
    ::= { sonusIcmpGeneralGroupEntry 8 }

sonusIcmpInEchoReps OBJECT-TYPE
    SYNTAX          Counter32
    MAX-ACCESS      read-only
    STATUS          current
    DESCRIPTION     
            "The number of ICMP Echo Reply messages received."
    ::= { sonusIcmpGeneralGroupEntry 9 }

sonusIcmpInTimestamps OBJECT-TYPE
    SYNTAX          Counter32
    MAX-ACCESS      read-only
    STATUS          current
    DESCRIPTION     
            "The number of ICMP Timestamp (request) messages received."
    ::= { sonusIcmpGeneralGroupEntry 10 }

sonusIcmpInTimestampReps OBJECT-TYPE
    SYNTAX          Counter32
    MAX-ACCESS      read-only
    STATUS          current
    DESCRIPTION     
            "The number of ICMP Timestamp Reply messages received."
    ::= { sonusIcmpGeneralGroupEntry 11 }

sonusIcmpInAddrMasks OBJECT-TYPE
    SYNTAX          Counter32
    MAX-ACCESS      read-only
    STATUS          current
    DESCRIPTION     
            "The number of ICMP Address Mask Request messages received."
    ::= { sonusIcmpGeneralGroupEntry 12 }

sonusIcmpInAddrMaskReps OBJECT-TYPE
    SYNTAX          Counter32
    MAX-ACCESS      read-only
    STATUS          current
    DESCRIPTION     
            "The number of ICMP Address Mask Reply messages received."
    ::= { sonusIcmpGeneralGroupEntry 13 }

sonusIcmpOutMsgs OBJECT-TYPE
    SYNTAX          Counter32
    MAX-ACCESS      read-only
    STATUS          current
    DESCRIPTION     
            "The total number of ICMP messages which this entity
             attempted to send.  Note that this counter includes all
             those counted by icmpOutErrors."
    ::= { sonusIcmpGeneralGroupEntry 14 }

sonusIcmpOutErrors OBJECT-TYPE
    SYNTAX          Counter32
    MAX-ACCESS      read-only
    STATUS          current
    DESCRIPTION     
            "The number of ICMP messages which this entity did not send
             due to problems discovered within ICMP such as a lack of
             buffers.  This value should not include errors discovered
             outside the ICMP layer such as the inability of IP to route
             the resultant datagram.  In some implementations there may
             be no types of error which contribute to this counter's
             value."
    ::= { sonusIcmpGeneralGroupEntry 15 }

sonusIcmpOutDestUnreachs OBJECT-TYPE
    SYNTAX          Counter32
    MAX-ACCESS      read-only
    STATUS          current
    DESCRIPTION     
            "The number of ICMP Destination Unreachable messages sent."
    ::= { sonusIcmpGeneralGroupEntry 16 }

sonusIcmpOutTimeExcds OBJECT-TYPE
    SYNTAX          Counter32
    MAX-ACCESS      read-only
    STATUS          current
    DESCRIPTION     
            "The number of ICMP Time Exceeded messages sent."
    ::= { sonusIcmpGeneralGroupEntry 17 }

sonusIcmpOutParmProbs OBJECT-TYPE
    SYNTAX          Counter32
    MAX-ACCESS      read-only
    STATUS          current
    DESCRIPTION     
            "The number of ICMP Parameter Problem messages sent."
    ::= { sonusIcmpGeneralGroupEntry 18 }

sonusIcmpOutSrcQuenchs OBJECT-TYPE
    SYNTAX          Counter32
    MAX-ACCESS      read-only
    STATUS          current
    DESCRIPTION     
            "The number of ICMP Source Quench messages sent."
    ::= { sonusIcmpGeneralGroupEntry 19 }

sonusIcmpOutRedirects OBJECT-TYPE
    SYNTAX          Counter32
    MAX-ACCESS      read-only
    STATUS          current
    DESCRIPTION     
            "The number of ICMP Redirect messages sent.  For a host,
             this object will always be zero, since hosts do not send
             redirects."
    ::= { sonusIcmpGeneralGroupEntry 20 }

sonusIcmpOutEchos OBJECT-TYPE
    SYNTAX          Counter32
    MAX-ACCESS      read-only
    STATUS          current
    DESCRIPTION     
            "The number of ICMP Echo (request) messages sent."
    ::= { sonusIcmpGeneralGroupEntry 21 }

sonusIcmpOutEchoReps OBJECT-TYPE
    SYNTAX          Counter32
    MAX-ACCESS      read-only
    STATUS          current
    DESCRIPTION     
            "The number of ICMP Echo Reply messages sent."
    ::= { sonusIcmpGeneralGroupEntry 22 }

sonusIcmpOutTimestamps OBJECT-TYPE
    SYNTAX          Counter32
    MAX-ACCESS      read-only
    STATUS          current
    DESCRIPTION     
            "The number of ICMP Timestamp (request) messages sent."
    ::= { sonusIcmpGeneralGroupEntry 23 }

sonusIcmpOutTimestampReps OBJECT-TYPE
    SYNTAX          Counter32
    MAX-ACCESS      read-only
    STATUS          current
    DESCRIPTION     
            "The number of ICMP Timestamp Reply messages sent."
    ::= { sonusIcmpGeneralGroupEntry 24 }

sonusIcmpOutAddrMasks OBJECT-TYPE
    SYNTAX          Counter32
    MAX-ACCESS      read-only
    STATUS          current
    DESCRIPTION     
            "The number of ICMP Address Mask Request messages sent."
    ::= { sonusIcmpGeneralGroupEntry 25 }

sonusIcmpOutAddrMaskReps OBJECT-TYPE
    SYNTAX          Counter32
    MAX-ACCESS      read-only
    STATUS          current
    DESCRIPTION     
            "The number of ICMP Address Mask Reply messages sent."
    ::= { sonusIcmpGeneralGroupEntry 26 }

sonusIcmpGeneralGroupShelf OBJECT-TYPE
    SYNTAX          Integer32
    MAX-ACCESS      read-only
    STATUS          current
    DESCRIPTION     
            "A 32-bit integer identifying the shelf
             that the ICMP General Group table applies to"
    ::= { sonusIcmpGeneralGroupEntry 27 }

sonusIcmpGeneralGroupSlot OBJECT-TYPE
    SYNTAX          Integer32
    MAX-ACCESS      read-only
    STATUS          current
    DESCRIPTION     
            "A 32-bit integer identifying the slot
             that the ICMP General Group table applies to"
    ::= { sonusIcmpGeneralGroupEntry 28 }

sonusIcmpGeneralGroupInstance OBJECT-TYPE
    SYNTAX          Integer32
    MAX-ACCESS      read-only
    STATUS          current
    DESCRIPTION     
            "A 32-bit integer identifying the instance
             that the ICMP General Group table applies to"
    ::= { sonusIcmpGeneralGroupEntry 29 }

sonusTcp OBJECT IDENTIFIER
    ::= { sonusMib-2 6 }

sonusTcpGeneralGroupTable OBJECT-TYPE
    SYNTAX          SEQUENCE OF SonusTcpGeneralGroupEntry
    MAX-ACCESS      not-accessible
    STATUS          current
    DESCRIPTION     
            "The collection of TCP General Group information for the
             specified instance."
    ::= { sonusTcp 1 }

sonusTcpGeneralGroupEntry OBJECT-TYPE
    SYNTAX          SonusTcpGeneralGroupEntry
    MAX-ACCESS      not-accessible
    STATUS          current
    DESCRIPTION     
            "The collection of TCP General Group information for the
             specified instance."
    INDEX           { sonusTcpGeneralGroupShelf, 
                      sonusTcpGeneralGroupSlot, 
                      sonusTcpGeneralGroupInstance }
    ::= { sonusTcpGeneralGroupTable 1 }

SonusTcpGeneralGroupEntry ::=
    SEQUENCE {
        sonusTcpRtoAlgorithm            INTEGER,
        sonusTcpRtoMin                  Integer32,
        sonusTcpRtoMax                  Integer32,
        sonusTcpMaxConn                 Integer32,
        sonusTcpActiveOpens             Counter32,
        sonusTcpPassiveOpens            Counter32,
        sonusTcpAttemptFails            Counter32,
        sonusTcpEstabResets             Counter32,
        sonusTcpCurrEstab               Gauge32,
        sonusTcpInSegs                  Counter32,
        sonusTcpOutSegs                 Counter32,
        sonusTcpRetransSegs             Counter32,
        sonusTcpInErrs                  Counter32,
        sonusTcpOutRsts                 Counter32,
        sonusTcpGeneralGroupShelf       Integer32,
        sonusTcpGeneralGroupSlot        Integer32,
        sonusTcpGeneralGroupInstance    Integer32
    }

sonusTcpRtoAlgorithm OBJECT-TYPE
    SYNTAX          INTEGER { other(1), constant(2), rsre(3), vanj(4) }
    MAX-ACCESS      read-only
    STATUS          current
    DESCRIPTION     
            "The algorithm used to determine the timeout value used for
             retransmitting unacknowledged octets."
    ::= { sonusTcpGeneralGroupEntry 1 }

sonusTcpRtoMin OBJECT-TYPE
    SYNTAX          Integer32
    MAX-ACCESS      read-only
    STATUS          current
    DESCRIPTION     
            "The minimum value permitted by a TCP implementation for the
             retransmission timeout, measured in milliseconds.  More
             refined semantics for objects of this type depend upon the
             algorithm used to determine the retransmission timeout.  In
             particular, when the timeout algorithm is rsre(3), an object
             of this type has the semantics of the LBOUND quantity
             described in RFC 793."
    ::= { sonusTcpGeneralGroupEntry 2 }

sonusTcpRtoMax OBJECT-TYPE
    SYNTAX          Integer32
    MAX-ACCESS      read-only
    STATUS          current
    DESCRIPTION     
            "The maximum value permitted by a TCP implementation for the
             retransmission timeout, measured in milliseconds.  More
             refined semantics for objects of this type depend upon the
             algorithm used to determine the retransmission timeout.  In
             particular, when the timeout algorithm is rsre(3), an object
             of this type has the semantics of the UBOUND quantity
             described in RFC 793."
    ::= { sonusTcpGeneralGroupEntry 3 }

sonusTcpMaxConn OBJECT-TYPE
    SYNTAX          Integer32
    MAX-ACCESS      read-only
    STATUS          current
    DESCRIPTION     
            "The limit on the total number of TCP connections the entity
             can support.  In entities where the maximum number of
             connections is dynamic, this object should contain the value
             -1."
    ::= { sonusTcpGeneralGroupEntry 4 }

sonusTcpActiveOpens OBJECT-TYPE
    SYNTAX          Counter32
    MAX-ACCESS      read-only
    STATUS          current
    DESCRIPTION     
            "The number of times TCP connections have made a direct
             transition to the SYN-SENT state from the CLOSED state."
    ::= { sonusTcpGeneralGroupEntry 5 }

sonusTcpPassiveOpens OBJECT-TYPE
    SYNTAX          Counter32
    MAX-ACCESS      read-only
    STATUS          current
    DESCRIPTION     
            "The number of times TCP connections have made a direct
             transition to the SYN-RCVD state from the LISTEN state."
    ::= { sonusTcpGeneralGroupEntry 6 }

sonusTcpAttemptFails OBJECT-TYPE
    SYNTAX          Counter32
    MAX-ACCESS      read-only
    STATUS          current
    DESCRIPTION     
            "The number of times TCP connections have made a direct
             transition to the CLOSED state from either the SYN-SENT
             state or the SYN-RCVD state, plus the number of times TCP
             connections have made a direct transition to the LISTEN
             state from the SYN-RCVD state."
    ::= { sonusTcpGeneralGroupEntry 7 }

sonusTcpEstabResets OBJECT-TYPE
    SYNTAX          Counter32
    MAX-ACCESS      read-only
    STATUS          current
    DESCRIPTION     
            "The number of times TCP connections have made a direct
             transition to the CLOSED state from either the ESTABLISHED
             state or the CLOSE-WAIT state."
    ::= { sonusTcpGeneralGroupEntry 8 }

sonusTcpCurrEstab OBJECT-TYPE
    SYNTAX          Gauge32
    MAX-ACCESS      read-only
    STATUS          current
    DESCRIPTION     
            "The number of TCP connections for which the current state
             is either ESTABLISHED or CLOSE- WAIT."
    ::= { sonusTcpGeneralGroupEntry 9 }

sonusTcpInSegs OBJECT-TYPE
    SYNTAX          Counter32
    MAX-ACCESS      read-only
    STATUS          current
    DESCRIPTION     
            "The total number of segments received, including those
             received in error.  This count includes segments received on
             currently established connections."
    ::= { sonusTcpGeneralGroupEntry 10 }

sonusTcpOutSegs OBJECT-TYPE
    SYNTAX          Counter32
    MAX-ACCESS      read-only
    STATUS          current
    DESCRIPTION     
            "The total number of segments sent, including those on
             current connections but excluding those containing only
             retransmitted octets."
    ::= { sonusTcpGeneralGroupEntry 11 }

sonusTcpRetransSegs OBJECT-TYPE
    SYNTAX          Counter32
    MAX-ACCESS      read-only
    STATUS          current
    DESCRIPTION     
            "The total number of segments retransmitted - that is, the
             number of TCP segments transmitted containing one or more
             previously transmitted octets."
    ::= { sonusTcpGeneralGroupEntry 12 }

sonusTcpInErrs OBJECT-TYPE
    SYNTAX          Counter32
    MAX-ACCESS      read-only
    STATUS          current
    DESCRIPTION     
            "The total number of segments received in error (e.g., bad
             TCP checksums)."
    ::= { sonusTcpGeneralGroupEntry 14 }

sonusTcpOutRsts OBJECT-TYPE
    SYNTAX          Counter32
    MAX-ACCESS      read-only
    STATUS          current
    DESCRIPTION     
            "The number of TCP segments sent containing the RST flag."
    ::= { sonusTcpGeneralGroupEntry 15 }

sonusTcpGeneralGroupShelf OBJECT-TYPE
    SYNTAX          Integer32
    MAX-ACCESS      read-only
    STATUS          current
    DESCRIPTION     
            "A 32-bit integer identifying the shelf
             that the TCP General Group table applies to"
    ::= { sonusTcpGeneralGroupEntry 16 }

sonusTcpGeneralGroupSlot OBJECT-TYPE
    SYNTAX          Integer32
    MAX-ACCESS      read-only
    STATUS          current
    DESCRIPTION     
            "A 32-bit integer identifying the slot
             that the TCP General Group table applies to"
    ::= { sonusTcpGeneralGroupEntry 17 }

sonusTcpGeneralGroupInstance OBJECT-TYPE
    SYNTAX          Integer32
    MAX-ACCESS      read-only
    STATUS          current
    DESCRIPTION     
            "A 32-bit integer identifying the instance
             that the TCP General Group table applies to"
    ::= { sonusTcpGeneralGroupEntry 18 }

sonusTcpConnTable OBJECT-TYPE
    SYNTAX          SEQUENCE OF SonusTcpConnEntry
    MAX-ACCESS      not-accessible
    STATUS          current
    DESCRIPTION     
            "A table containing TCP connection-specific information."
    ::= { sonusTcp 13 }

sonusTcpConnEntry OBJECT-TYPE
    SYNTAX          SonusTcpConnEntry
    MAX-ACCESS      not-accessible
    STATUS          current
    DESCRIPTION     
            "A conceptual row of the tcpConnTable containing information
             about a particular current TCP connection.  Each row of this
             table is transient, in that it ceases to exist when (or soon
             after) the connection makes the transition to the CLOSED
             state."
    INDEX           { sonusTcpConnShelf, sonusTcpConnSlot, 
                      sonusTcpConnInstance, sonusTcpConnLocalAddress, 
                      sonusTcpConnLocalPort, sonusTcpConnRemAddress, 
                      sonusTcpConnRemPort }
    ::= { sonusTcpConnTable 1 }

SonusTcpConnEntry ::=
    SEQUENCE {
        sonusTcpConnState               INTEGER,
        sonusTcpConnLocalAddress        IpAddress,
        sonusTcpConnLocalPort           Integer32,
        sonusTcpConnRemAddress          IpAddress,
        sonusTcpConnRemPort             Integer32,
        sonusTcpConnShelf               Integer32,
        sonusTcpConnSlot                Integer32,
        sonusTcpConnInstance            Integer32
    }

sonusTcpConnState OBJECT-TYPE
    SYNTAX          INTEGER { closed(1), listen(2), synSent(3), 
                        synReceived(4), established(5), finWait1(6), 
                        finWait2(7), closeWait(8), lastAck(9), 
                        closing(10), timeWait(11), deleteTCB(12) }
    MAX-ACCESS      read-only
    STATUS          current
    DESCRIPTION     
            "The state of this TCP connection.
             
             The only value which may be set by a management station is
             deleteTCB(12).  Accordingly, it is appropriate for an agent
             to return a `badValue' response if a management station
             attempts to set this object to any other value.
             
             If a management station sets this object to the value
             deleteTCB(12), then this has the effect of deleting the TCB
             (as defined in RFC 793) of the corresponding connection on
             the managed node, resulting in immediate termination of the
             connection.
             
             As an implementation-specific option, a RST segment may be
             sent from the managed node to the other TCP endpoint (note
             however that RST segments are not sent reliably)."
    ::= { sonusTcpConnEntry 1 }

sonusTcpConnLocalAddress OBJECT-TYPE
    SYNTAX          IpAddress
    MAX-ACCESS      read-only
    STATUS          current
    DESCRIPTION     
            "The local IP address for this TCP connection.  In the case
             of a connection in the listen state which is willing to
             accept connections for any IP interface associated with the
             node, the value 0.0.0.0 is used."
    ::= { sonusTcpConnEntry 2 }

sonusTcpConnLocalPort OBJECT-TYPE
    SYNTAX          Integer32 (0..65535)
    MAX-ACCESS      read-only
    STATUS          current
    DESCRIPTION     
            "The local port number for this TCP connection."
    ::= { sonusTcpConnEntry 3 }

sonusTcpConnRemAddress OBJECT-TYPE
    SYNTAX          IpAddress
    MAX-ACCESS      read-only
    STATUS          current
    DESCRIPTION     
            "The remote IP address for this TCP connection."
    ::= { sonusTcpConnEntry 4 }

sonusTcpConnRemPort OBJECT-TYPE
    SYNTAX          Integer32 (0..65535)
    MAX-ACCESS      read-only
    STATUS          current
    DESCRIPTION     
            "The remote port number for this TCP connection."
    ::= { sonusTcpConnEntry 5 }

sonusTcpConnShelf OBJECT-TYPE
    SYNTAX          Integer32
    MAX-ACCESS      read-only
    STATUS          current
    DESCRIPTION     
            "A 32-bit integer identifying the shelf
             that the TCP Connection Group table applies to"
    ::= { sonusTcpConnEntry 6 }

sonusTcpConnSlot OBJECT-TYPE
    SYNTAX          Integer32
    MAX-ACCESS      read-only
    STATUS          current
    DESCRIPTION     
            "A 32-bit integer identifying the slot
             that the TCP Connection Group table applies to"
    ::= { sonusTcpConnEntry 7 }

sonusTcpConnInstance OBJECT-TYPE
    SYNTAX          Integer32
    MAX-ACCESS      read-only
    STATUS          current
    DESCRIPTION     
            "A 32-bit integer identifying the instance
             that the TCP Connection Group table applies to"
    ::= { sonusTcpConnEntry 8 }

sonusUdp OBJECT IDENTIFIER
    ::= { sonusMib-2 7 }

sonusUdpGeneralGroupTable OBJECT-TYPE
    SYNTAX          SEQUENCE OF SonusUdpGeneralGroupEntry
    MAX-ACCESS      not-accessible
    STATUS          current
    DESCRIPTION     
            "The collection of UDP General Group information for the
             specified instance."
    ::= { sonusUdp 1 }

sonusUdpGeneralGroupEntry OBJECT-TYPE
    SYNTAX          SonusUdpGeneralGroupEntry
    MAX-ACCESS      not-accessible
    STATUS          current
    DESCRIPTION     
            "The collection of UDP General Group information for the
             specified instance."
    INDEX           { sonusUdpGeneralGroupShelf, 
                      sonusUdpGeneralGroupSlot, 
                      sonusUdpGeneralGroupInstance }
    ::= { sonusUdpGeneralGroupTable 1 }

SonusUdpGeneralGroupEntry ::=
    SEQUENCE {
        sonusUdpInDatagrams             Counter32,
        sonusUdpNoPorts                 Counter32,
        sonusUdpInErrors                Counter32,
        sonusUdpOutDatagrams            Counter32,
        sonusUdpGeneralGroupShelf       Integer32,
        sonusUdpGeneralGroupSlot        Integer32,
        sonusUdpGeneralGroupInstance    Integer32
    }

sonusUdpInDatagrams OBJECT-TYPE
    SYNTAX          Counter32
    MAX-ACCESS      read-only
    STATUS          current
    DESCRIPTION     
            "The total number of UDP datagrams delivered to UDP users."
    ::= { sonusUdpGeneralGroupEntry 1 }

sonusUdpNoPorts OBJECT-TYPE
    SYNTAX          Counter32
    MAX-ACCESS      read-only
    STATUS          current
    DESCRIPTION     
            "The total number of received UDP datagrams for which there
             was no application at the destination port."
    ::= { sonusUdpGeneralGroupEntry 2 }

sonusUdpInErrors OBJECT-TYPE
    SYNTAX          Counter32
    MAX-ACCESS      read-only
    STATUS          current
    DESCRIPTION     
            "The number of received UDP datagrams that could not be
             delivered for reasons other than the lack of an application
             at the destination port."
    ::= { sonusUdpGeneralGroupEntry 3 }

sonusUdpOutDatagrams OBJECT-TYPE
    SYNTAX          Counter32
    MAX-ACCESS      read-only
    STATUS          current
    DESCRIPTION     
            "The total number of UDP datagrams sent from this entity."
    ::= { sonusUdpGeneralGroupEntry 4 }

sonusUdpGeneralGroupShelf OBJECT-TYPE
    SYNTAX          Integer32
    MAX-ACCESS      read-only
    STATUS          current
    DESCRIPTION     
            "A 32-bit integer identifying the shelf
             that the UDP General Group table applies to"
    ::= { sonusUdpGeneralGroupEntry 5 }

sonusUdpGeneralGroupSlot OBJECT-TYPE
    SYNTAX          Integer32
    MAX-ACCESS      read-only
    STATUS          current
    DESCRIPTION     
            "A 32-bit integer identifying the slot
             that the UDP General Group table applies to"
    ::= { sonusUdpGeneralGroupEntry 6 }

sonusUdpGeneralGroupInstance OBJECT-TYPE
    SYNTAX          Integer32
    MAX-ACCESS      read-only
    STATUS          current
    DESCRIPTION     
            "A 32-bit integer identifying the instance
             that the UDP General Group table applies to"
    ::= { sonusUdpGeneralGroupEntry 7 }

sonusUdpTable OBJECT-TYPE
    SYNTAX          SEQUENCE OF SonusUdpEntry
    MAX-ACCESS      not-accessible
    STATUS          current
    DESCRIPTION     
            "A table containing UDP listener information."
    ::= { sonusUdp 5 }

sonusUdpEntry OBJECT-TYPE
    SYNTAX          SonusUdpEntry
    MAX-ACCESS      not-accessible
    STATUS          current
    DESCRIPTION     
            "Information about a particular current UDP listener."
    INDEX           { sonusUdpShelf, sonusUdpSlot, sonusUdpInstance, 
                      sonusUdpLocalAddress, sonusUdpLocalPort }
    ::= { sonusUdpTable 1 }

SonusUdpEntry ::=
    SEQUENCE {
        sonusUdpLocalAddress            IpAddress,
        sonusUdpLocalPort               Integer32,
        sonusUdpShelf                   Integer32,
        sonusUdpSlot                    Integer32,
        sonusUdpInstance                Integer32
    }

sonusUdpLocalAddress OBJECT-TYPE
    SYNTAX          IpAddress
    MAX-ACCESS      read-only
    STATUS          current
    DESCRIPTION     
            "The local IP address for this UDP listener.  In the case of
             a UDP listener which is willing to accept datagrams for any
             IP interface associated with the node, the value 0.0.0.0 is
             used."
    ::= { sonusUdpEntry 1 }

sonusUdpLocalPort OBJECT-TYPE
    SYNTAX          Integer32 (0..65535)
    MAX-ACCESS      read-only
    STATUS          current
    DESCRIPTION     
            "The local port number for this UDP listener."
    ::= { sonusUdpEntry 2 }

sonusUdpShelf OBJECT-TYPE
    SYNTAX          Integer32
    MAX-ACCESS      read-only
    STATUS          current
    DESCRIPTION     
            "A 32-bit integer identifying the shelf
             that the UDP Listener table applies to"
    ::= { sonusUdpEntry 3 }

sonusUdpSlot OBJECT-TYPE
    SYNTAX          Integer32
    MAX-ACCESS      read-only
    STATUS          current
    DESCRIPTION     
            "A 32-bit integer identifying the slot
             that the UDP Listener table applies to"
    ::= { sonusUdpEntry 4 }

sonusUdpInstance OBJECT-TYPE
    SYNTAX          Integer32
    MAX-ACCESS      read-only
    STATUS          current
    DESCRIPTION     
            "A 32-bit integer identifying the instance
             that the UDP Listener table applies to"
    ::= { sonusUdpEntry 5 }

END -- end of module SONUS-IP-PROTOCOL-MIB.
