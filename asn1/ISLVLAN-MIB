ISLVLAN-MIB DEFINITIONS ::= BEGIN

-- Hewlett-Packard Cisco ISL VLAN configuration MIB
--
-- Copyright (C)  1997-1998 Hewlett-Packard Corporation. All rights reserved.
-- Author:        Hewlett-Packard Netmetrix Division
-- Last updated:  21 January 1998
-- Purpose:       Defines objects to specify an Cisco ISL VLAN as a data source.
--
-- Change History:
--   12/20/97 map Original version.
--   01/21/98 map Integrate HLA 11 changes.
--   01/23/98 map Bring up to HLA 11B level.
--   01/28/98 map Bring up to HLA 11C level.
--   02/10/98 map Fix formatting.

IMPORTS
       MODULE-IDENTITY, OBJECT-TYPE          FROM SNMPv2-SMI
       Integer32, enterprises, IpAddress     FROM SNMPv2-SMI
       DisplayString, RowStatus              FROM SNMPv2-TC
       OwnerString                           FROM RMON-MIB
       InterfaceIndex, ifIndex               FROM IF-MIB;

hp                            OBJECT IDENTIFIER ::= {enterprises 11 }
nm                            OBJECT IDENTIFIER ::= { hp 2 }
interface	              OBJECT IDENTIFIER ::= { nm 4 }
       
islVlanMIB MODULE-IDENTITY
       LAST-UPDATED        ""
       ORGANIZATION        "Hewlett-Packard NetMetrix Division"
       CONTACT-INFO
              "NetMetrix Division
              Hewlett-Packard Company
              5070 Centennial Blvd
              Colorado Springs, CO 80919"
       DESCRIPTION
              "The MIB module to configure Cisco ISL VLAN monitoring."
::= { interface 9 }

islVlanMIBObjects       OBJECT IDENTIFIER ::= { islVlanMIB 1 }

islVlanControlTable OBJECT-TYPE
       SYNTAX       SEQUENCE OF IslVlanControlEntry
       MAX-ACCESS   not-accessible
       STATUS       current
       DESCRIPTION
              "A list ISL VLAN control entries, one for each 100BaseT
              interface.  This table should survive warm-boots and power
              losses."
::= { islVlanMIBObjects 1 }

islVlanControlEntry OBJECT-TYPE
       SYNTAX       IslVlanControlEntry
       MAX-ACCESS   not-accessible
       STATUS       current
       DESCRIPTION
              "An entry that controls the ISL behavior on a particular
              100BaseT interface."
       INDEX { islVlanControlIndex }
::= { islVlanControlTable 1 }

IslVlanControlEntry ::= SEQUENCE {
       islVlanControlIndex                 INTEGER (1..65535),
       islVlanControlDataSource            OBJECT IDENTIFIER,
       islVlanControlVtpDomain             IpAddress,
       islVlanControlVtpCommunity          OCTET STRING,
       islVlanControlEnable                INTEGER
}

islVlanControlIndex OBJECT-TYPE
       SYNTAX       INTEGER (1..65535)
       MAX-ACCESS   not-accessible
       STATUS       current
       DESCRIPTION
              "The value of this object uniquely identifies this
              islVlanControlTable entry."
::= { islVlanControlEntry 1 }

islVlanControlDataSource OBJECT-TYPE
       SYNTAX       OBJECT IDENTIFIER
       MAX-ACCESS   read-only
       STATUS       current
       DESCRIPTION
              "This contains the OID of the ifIndex of the interface this
              entry controls.  The corresponding ifType ethernetCsmacd(6)."
::= { islVlanControlEntry 2 }

islVlanControlVtpDomain OBJECT-TYPE
       SYNTAX       IpAddress
       MAX-ACCESS   read-write
       STATUS       current
       DESCRIPTION
              "The IP address of the Cisco VTP server of VLANs monitored by
              this interface."
::= { islVlanControlEntry 3 }

islVlanControlVtpCommunity OBJECT-TYPE
       SYNTAX       DisplayString
       MAX-ACCESS   read-write
       STATUS       current
       DESCRIPTION
              "The SNMP community string for the Cisco VTP server of VLANs
              monitored by this interface."
::= { islVlanControlEntry 4 }

islVlanControlEnable OBJECT-TYPE
       SYNTAX       INTEGER {
              disabled(1),       -- do not process ISL
              explicitOnly(2),   -- only monitor explicitly registered VLANs
              implicitCreate(3)  -- create entries for unregistered VLANs
       }
       MAX-ACCESS   read-write
       STATUS       current
       DESCRIPTION
              "Indicate the behavior for processing ISL VLAN packets.  
              
              A value of disabled(1) means that no per-VLAN monitoring happens
              on this interface.
              
              A value of explicitlyOnly(2) means that only VLANs that
              correspond to an islVlanEntry that was explicitly created by a
              management application.  If the probe sees an ISL packet that
              doesn't correspond to an explicitly created islVlanEntry, the
              probe will not process the packet in any per-VLAN tables.
              
              A value of implicitCreate(3) means that a new islVlanEntry is
              automatically created when a ISL packet is seen with an unknown
              VLAN ID."
::= { islVlanControlEntry 5 }

islVlanTable OBJECT-TYPE
       SYNTAX       SEQUENCE OF IslVlanEntry
       MAX-ACCESS   not-accessible
       STATUS       current
       DESCRIPTION
              "The ISL VLAN able stores the information needed to monitor
              Cisco ISL VLAN traffic on an inter-switch trunk line.  This table
              should survive warm-boots and power losses."
::= { islVlanMIBObjects 2 }

islVlanEntry OBJECT-TYPE
       SYNTAX       IslVlanEntry
       MAX-ACCESS   not-accessible
       STATUS       current
       DESCRIPTION
              "An entry in the islVlanTable.
              
              An entry can be created two ways.  A management application can
              explicitly create an entry.  Or, an entry can be automatically
              created if an unknown ISL ID is seen on an interface (see
              islVlanControlEnable.)"
       INDEX { islVlanIndex }
::= { islVlanTable 1 }

IslVlanEntry ::= SEQUENCE {
       islVlanIndex                        INTEGER (1..65535),
       islVlanControlEntryIndex            INTEGER (1..65536),
       islVlanId                           INTEGER (0..1023),
       islVlanIfIndex                      InterfaceIndex,
       islVlanName                         DisplayString(1..32),
       islVlanMtu                          Integer32,
       islVlanOwner                        OwnerString,
       islVlanStatus                       RowStatus
}

islVlanIndex OBJECT-TYPE
       SYNTAX       INTEGER (1..65535)
       MAX-ACCESS   not-accessible
       STATUS       current
       DESCRIPTION
              "The value of this object uniquely identifies this islVlanTable
              entry."
::= { islVlanEntry 1 }

islVlanControlEntryIndex OBJECT-TYPE
       SYNTAX       INTEGER (1..65535)
       MAX-ACCESS   read-create
       STATUS       current
       DESCRIPTION
              "Indicates the islVlanControlIndex of the corresponding
              islVlanControlEntry."
::= { islVlanEntry 2 }

islVlanId OBJECT-TYPE
       SYNTAX       INTEGER (0..1023)
       MAX-ACCESS   read-create
       STATUS       current
       DESCRIPTION
              "The value of this object ISL VLAN ID for this particular VLAN on
              this interface."
::= { islVlanEntry 3 }

islVlanIfIndex OBJECT-TYPE
       SYNTAX       InterfaceIndex
       MAX-ACCESS   read-only
       STATUS       current
       DESCRIPTION
              "A unique identifier associated with this islVlanTable entry.
              This value should not be same as any existing or future
              ifIndex/pvcIndex value. This value must remain constant from
              when its creation until its explicit deletion."
::= { islVlanEntry 4 }

islVlanName OBJECT-TYPE
       SYNTAX       DisplayString(1..32)
       MAX-ACCESS   read-write
       STATUS       current
       DESCRIPTION
              "This contains the VLAN name.  If the entry was created
              automatically by the probe, its value is `unknown VLAN <ID>'.
              A management application is free to change this name at any
              time. "
::= { islVlanEntry 5 }

islVlanMtu OBJECT-TYPE
       SYNTAX       Integer32
       MAX-ACCESS   read-write
       STATUS       current
       DESCRIPTION
              "The maximum transmission unit size for this VLAN.  If this was
              created automatically, this value not be known and should be set
              to 0."
::= { islVlanEntry 6 }

islVlanOwner OBJECT-TYPE
       SYNTAX       OwnerString
       MAX-ACCESS   read-create
       STATUS       current
       DESCRIPTION
              "The entity that configured this entry.  If this was
              automatically created by the probe, the value is `monitor'."
::= { islVlanEntry 7 }

islVlanStatus OBJECT-TYPE
       SYNTAX       RowStatus
       MAX-ACCESS   read-write
       STATUS       current
       DESCRIPTION
              "The status of this islVlanTable entry."
::= { islVlanEntry 8 }

END
