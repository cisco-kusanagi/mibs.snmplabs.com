--			Ascend mibatmqos MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBATMQOS-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibatmQosProfile  OBJECT IDENTIFIER ::= { configuration 21}

	-- The mibatmQosProfile table
	--
	-- This table contains parameters for the mibatmQosProfile profile
	--

    mibatmQosProfileTable	OBJECT-TYPE
	SYNTAX		SEQUENCE OF MibatmQosProfileEntry
	ACCESS		not-accessible
	STATUS		mandatory
	DESCRIPTION	"A list of mibatmQosProfile profile entries."
	::= { mibatmQosProfile 1 }

    mibatmQosProfileEntry	OBJECT-TYPE
	SYNTAX		MibatmQosProfileEntry
	ACCESS		not-accessible
	STATUS		mandatory
	DESCRIPTION	"A mibatmQosProfile entry containing objects that
			 maps to the parameters of mibatmQosProfile profile."
	INDEX		{ atmQosProfile-ContractName }
	::= { mibatmQosProfileTable 1 }

    MibatmQosProfileEntry ::=
	SEQUENCE {
	    atmQosProfile-ContractName
		DisplayString,
	    atmQosProfile-TrafficDescriptorIndex
		INTEGER,
	    atmQosProfile-TrafficDescriptorType
		INTEGER,
	    atmQosProfile-AtmServiceCategory
		INTEGER,
	    atmQosProfile-PeakRateKbitsPerSec
		INTEGER,
	    atmQosProfile-PeakCellRateCellsPerSec
		INTEGER,
	    atmQosProfile-SustainableRateKbitsPerSec
		INTEGER,
	    atmQosProfile-SustainableCellRateCellsPerSec
		INTEGER,
	    atmQosProfile-IgnoreCellDelayVariationTolerance
		INTEGER,
	    atmQosProfile-CellDelayVariationTolerance
		INTEGER,
	    atmQosProfile-IgnoreMaxBurstSize
		INTEGER,
	    atmQosProfile-MaxBurstSize
		INTEGER,
	    atmQosProfile-AalType
		INTEGER,
	    atmQosProfile-EarlyPacketDiscard
		INTEGER,
	    atmQosProfile-PartialPacketDiscard
		INTEGER,
	    atmQosProfile-TagOrDiscard
		INTEGER,
	    atmQosProfile-SubChannel
		INTEGER,
	    atmQosProfile-Action-o
		INTEGER
	}

    atmQosProfile-ContractName	OBJECT-TYPE
	SYNTAX	DisplayString
	ACCESS	read-only
	STATUS	mandatory
	DESCRIPTION	"The name of the Quality of Service (QoS) contract."
	::= { mibatmQosProfileEntry 1 }

    atmQosProfile-TrafficDescriptorIndex	OBJECT-TYPE
	SYNTAX	INTEGER
	ACCESS	read-only
	STATUS	mandatory
	DESCRIPTION	"Traffic descriptor index."
	::= { mibatmQosProfileEntry 2 }

    atmQosProfile-TrafficDescriptorType	OBJECT-TYPE
	SYNTAX	INTEGER {
		    unknownTrafficDescr (17),
		    noclpNoscr (3),
		    noclpScr (6),
		    clpNotaggingScr (7),
		    clpTaggingScr (8),
		    clpTransparentNoscr (10),
		    clpTransparentScr (11),
		    noclpTaggingNoscr (12),
		    noclpNoscrCdvt (13),
		    noclpScrCdvt (14),
		    clpNotaggingScrCdvt (15),
		    clpTaggingScrCdvt (16)
		}
	ACCESS	read-write
	STATUS	mandatory
	DESCRIPTION	"The Traffic Descriptor type."
	::= { mibatmQosProfileEntry 3 }

    atmQosProfile-AtmServiceCategory	OBJECT-TYPE
	SYNTAX	INTEGER {
		    cbr (1),
		    realTimeVbr (2),
		    nonRealTimeVbr (3),
		    ubr (4)
		}
	ACCESS	read-write
	STATUS	mandatory
	DESCRIPTION	"The ATM Service Category Type. In 7.11.x releases this field was called qos-class."
	::= { mibatmQosProfileEntry 4 }

    atmQosProfile-PeakRateKbitsPerSec	OBJECT-TYPE
	SYNTAX	INTEGER
	ACCESS	read-write
	STATUS	mandatory
	DESCRIPTION	"The Peak Cell Rate (PCR) expressed in Kbits per second ( Peak Bandwidth in KBits/sec )"
	::= { mibatmQosProfileEntry 6 }

    atmQosProfile-PeakCellRateCellsPerSec	OBJECT-TYPE
	SYNTAX	INTEGER
	ACCESS	read-write
	STATUS	mandatory
	DESCRIPTION	"The Peak Cell Rate (PCR) expressed in cells per second"
	::= { mibatmQosProfileEntry 7 }

    atmQosProfile-SustainableRateKbitsPerSec	OBJECT-TYPE
	SYNTAX	INTEGER
	ACCESS	read-write
	STATUS	mandatory
	DESCRIPTION	"The sustainable cell rate (SCR) expressed in Kbits per second ( Sustainable Bandwidth in Kbits/sec )"
	::= { mibatmQosProfileEntry 9 }

    atmQosProfile-SustainableCellRateCellsPerSec	OBJECT-TYPE
	SYNTAX	INTEGER
	ACCESS	read-write
	STATUS	mandatory
	DESCRIPTION	"The sustainable cell rate (SCR) expressed in cells per second"
	::= { mibatmQosProfileEntry 10 }

    atmQosProfile-IgnoreCellDelayVariationTolerance	OBJECT-TYPE
	SYNTAX	INTEGER {
		    no (1),
		    yes (2)
		}
	ACCESS	read-write
	STATUS	mandatory
	DESCRIPTION	"Ignore cell-delay-variation-tolerance parameter. When it is set to yes, cell-delay-variation-tolerance parameter is ignored, and an internal parameter is used to tolerate bursty CPE that does not have traffic shaping capability."
	::= { mibatmQosProfileEntry 11 }

    atmQosProfile-CellDelayVariationTolerance	OBJECT-TYPE
	SYNTAX	INTEGER
	ACCESS	read-write
	STATUS	mandatory
	DESCRIPTION	"Cell delay variation tolerance is expressed in microseconds. It is ignored when ignore-cell-delay-variation-tolerance is yes."
	::= { mibatmQosProfileEntry 12 }

    atmQosProfile-IgnoreMaxBurstSize	OBJECT-TYPE
	SYNTAX	INTEGER {
		    no (1),
		    yes (2)
		}
	ACCESS	read-write
	STATUS	mandatory
	DESCRIPTION	"Ignore max-burst-size parameter. When it is set to yes, max-burst-size parameter is ignored, and an internal parameter is used to tolerate bursty CPE that does not have traffic shaping capability."
	::= { mibatmQosProfileEntry 13 }

    atmQosProfile-MaxBurstSize	OBJECT-TYPE
	SYNTAX	INTEGER
	ACCESS	read-write
	STATUS	mandatory
	DESCRIPTION	"Maximum burst size determines the maximum number of cells that can be transmitted at the peak cell rate before they become candidates for discard or marking. It is ignored when ignore-max-burst-size is yes."
	::= { mibatmQosProfileEntry 14 }

    atmQosProfile-AalType	OBJECT-TYPE
	SYNTAX	INTEGER {
		    aal0 (1),
		    aal5 (2),
		    unspecified (3)
		}
	ACCESS	read-write
	STATUS	mandatory
	DESCRIPTION	"ATM Adaptation Layer type"
	::= { mibatmQosProfileEntry 16 }

    atmQosProfile-EarlyPacketDiscard	OBJECT-TYPE
	SYNTAX	INTEGER {
		    no (1),
		    yes (2)
		}
	ACCESS	read-write
	STATUS	mandatory
	DESCRIPTION	"Applies to egress AAL5 packets. If the first cell in a packet can not be queued then that cell and all the remaining cells in that packet are not queued."
	::= { mibatmQosProfileEntry 17 }

    atmQosProfile-PartialPacketDiscard	OBJECT-TYPE
	SYNTAX	INTEGER {
		    no (1),
		    yes (2)
		}
	ACCESS	read-write
	STATUS	mandatory
	DESCRIPTION	"Applies to ingress AAL5 packets. If non-conforming cell is discarded then the remaining cells in the packet (except the last cell) are also discarded."
	::= { mibatmQosProfileEntry 18 }

    atmQosProfile-TagOrDiscard	OBJECT-TYPE
	SYNTAX	INTEGER {
		    tag (1),
		    discard (2)
		}
	ACCESS	read-write
	STATUS	mandatory
	DESCRIPTION	"The non-conforming CLP=0 SCR cell should be tagged or discarded"
	::= { mibatmQosProfileEntry 19 }

    atmQosProfile-SubChannel	OBJECT-TYPE
	SYNTAX	INTEGER
	ACCESS	read-write
	STATUS	mandatory
	DESCRIPTION	"For DSL technologies that support multiple sub-channels on one line, when the multiple sub-channels are indeed used at same time, this parameter indicates which sub-channel will be used for this QOS profile. When only one sub-channel is used this parameter has no effect... EXAMPLE: in DMT - when the latency is set to BOTH, sub-channel #1 is the FAST channel ( typically useful for voice traffic - voice over ATM or Packet ) while sub-channel #2 is the INTERLEAVE channel ( typically useful for data traffic )."
	::= { mibatmQosProfileEntry 21 }

    atmQosProfile-Action-o	OBJECT-TYPE
	SYNTAX	INTEGER {
		    noAction (1),
		    createProfile (2),
		    deleteProfile (3)
		}
	ACCESS	read-write
	STATUS	mandatory
	DESCRIPTION	""
	::= { mibatmQosProfileEntry 20 }

END
