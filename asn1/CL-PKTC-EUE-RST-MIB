CL-PKTC-EUE-RST-MIB DEFINITIONS ::= BEGIN
 
IMPORTS 
    MODULE-IDENTITY, 
    OBJECT-TYPE, 
    Unsigned32 
                       FROM SNMPv2-SMI 
    OBJECT-GROUP, 
    MODULE-COMPLIANCE 
                       FROM SNMPv2-CONF 
    SnmpAdminString 
                       FROM SNMP-FRAMEWORK-MIB 
     
    TEXTUAL-CONVENTION, 
    TruthValue,
    RowStatus 
                       FROM SNMPv2-TC
    pktcApplicationMibs
                       FROM CLAB-DEF-MIB
    PktcEUETCActStatus,
    PktcEUETCActStatusInfo
                       FROM CL-PKTC-EUE-TC-MIB
    pktcEUEDevOpIndex
                       FROM CL-PKTC-EUE-DEV-MIB;
                  
      
pktcEUERSTMIB MODULE-IDENTITY 
    LAST-UPDATED "200708220000Z"   -- TBD: Aug 24, 2007
    ORGANIZATION "Cable Television Laboratories, Inc." 
    CONTACT-INFO 
            "Sumanth Channabasappa
             Cable Television Laboratories, Inc.
             858 Coal Creek Circle,
             Louisville, CO 80027, USA 
             Phone: +1 303-661-9100
             Email: sumanth@cablelabs.com
        
             Acknowledgements:
             Thomas Clack, Broadcom - Primary author
             John Berg, CableLabs
             Satish Kumar, Texas Instruments
             , and members of the PacketCable PACM Focus Team."
    DESCRIPTION 
            "This MIB module contains configuration MIB  
             objects for supporting RST Features specified in
             the PacketCable RST specification." 
    
    ::= { pktcApplicationMibs 2 }

-- Administrative assignments    
pktcEUERSTNotifications     OBJECT IDENTIFIER ::= { pktcEUERSTMIB 0 }    
pktcEUERSTObjects           OBJECT IDENTIFIER ::= { pktcEUERSTMIB 1 }  
pktcEUERSTConformance       OBJECT IDENTIFIER ::= { pktcEUERSTMIB 2 }  
 
pktcEUERSTCompliances       OBJECT IDENTIFIER ::= { pktcEUERSTConformance 1 }  
pktcEUERSTGroups            OBJECT IDENTIFIER ::= { pktcEUERSTConformance 2 }  
 
-- MIB Objects 
pktcEUERSTProfile           OBJECT IDENTIFIER ::= { pktcEUERSTObjects 1 }  
pktcEUERSTFeatures          OBJECT IDENTIFIER ::= { pktcEUERSTObjects 2 }  
  
 
    
    
-- ---------------------------------------------------------------------           
-- Pktc EUE RST Textual Conventions 
-- ---------------------------------------------------------------------                     

PktcRSTTCTONEANNC ::= TEXTUAL-CONVENTION 
             STATUS  current 
             DESCRIPTION 
                 "This TEXTUAL CONVENTION is being defined 
                  as a way of indicating the announcement.
                  
                  If it is an URI, it is represented as a
                  hex string representing the URI."
             REFERENCE "PacketCable RST Feature Specification"
             SYNTAX   OCTET STRING 

PktcRSTTCFeatID ::= TEXTUAL-CONVENTION 
             STATUS  current 
             DESCRIPTION 
                 "This TEXTUAL CONVENTION is being defined 
                  as a way to enumerate the RST features." 
             SYNTAX   INTEGER { 
                               other(1),
                               digitMap(2),
                               basicCall(3), 
                               announcement(4),
                               statusChange(5),
                               noAnsTimeout(6),
                               callerId(7),
                               callerIdDisplay(8),
                               callerIdBlocking(9),
                               callerIdDelivery(10),
                               callForwarding(11),
                               callWaiting(12),
                               callHold(13),
                               callTransfer(14),
                               threeWayCalling(15),
                               doNotDisturb(16),
                               subscriberPIN(17),
                               msgWaitIndicator(18),
                               autoRecall(19),
                               autoCallback(20),
                               busyLineVerify(21),
                               emergencySvc(22),
                               scf(23)
                               } 
                         

PktcEUETCRSTAppPrfIndexType ::= TEXTUAL-CONVENTION
    STATUS  current
    DESCRIPTION
          " This TEXTUAL CONVENTION is being defined to 
            indicate any indices related to RST Application
            Profiles.
            Such an instance can be referenced across
            tables to indicate an association."
                  
      SYNTAX   Unsigned32 (0..31)   

PktcEUETCRSTAppFeatIndexType ::= TEXTUAL-CONVENTION
    STATUS  current
    DESCRIPTION
          " This TEXTUAL CONVENTION is being defined to 
            indicate any indices related to RST Application
            Features.
            Such an instance can be referenced across
            tables to indicate an association."
                  
      SYNTAX   Unsigned32 (0..63)  
                  

-- ---------------------------------------------------------------------                    
--  eUE Profile Information
-- ---------------------------------------------------------------------                    
pktcEUERSTProfileVersion OBJECT-TYPE
    SYNTAX      SnmpAdminString(SIZE(0..6))
    MAX-ACCESS  read-only
    STATUS      current
    DESCRIPTION
        " This MIB Object represents the RST Profile Version for this
          MIB module. The eUE MUST set this MIB Object to a value of '1.0'."
    ::= { pktcEUERSTProfile 1 }

-- ---------------------------------------------------------------------    
-- The Application Profile to Features Map Table
--  
-- ---------------------------------------------------------------------    
pktcEUERSTAppProfileToFeatTable OBJECT-TYPE
    SYNTAX      SEQUENCE OF PktcEUERSTAppProfileToFeatEntry
    MAX-ACCESS  not-accessible
    STATUS      current
    DESCRIPTION
        " This table specifies RST profiles that can be associated
          with Users supporting the RST application."
    ::= { pktcEUERSTProfile 2 } 
    
pktcEUERSTAppProfileToFeatEntry OBJECT-TYPE
    SYNTAX      PktcEUERSTAppProfileToFeatEntry
    MAX-ACCESS  not-accessible
    STATUS      current
    DESCRIPTION
        "Each entry in this table specifies an RST profile associated
         with a set of RST features."
    INDEX  { pktcEUERSTAppProfileIndex, pktcEUERSTAppFeatIndex }
    ::= { pktcEUERSTAppProfileToFeatTable 1 } 
    
PktcEUERSTAppProfileToFeatEntry ::=
    SEQUENCE {                                
              pktcEUERSTAppProfileIndex       PktcEUETCRSTAppPrfIndexType, 
              pktcEUERSTAppFeatIndex          PktcEUETCRSTAppFeatIndexType,
              pktcEUERSTAppFeatID             PktcRSTTCFeatID,
              pktcEUERSTAppFeatIndexRef       PktcEUETCRSTAppFeatIndexType,
              pktcEUERSTAppNwActStat          PktcEUETCActStatus,
              pktcEUERSTAppNwActStatInfo      PktcEUETCActStatusInfo,
              pktcEUERSTAppEUEActStat         PktcEUETCActStatus,
              pktcEUERSTAppEUEActStatInfo     PktcEUETCActStatusInfo,
              pktcEUERSTAppRowActStatus       RowStatus
             }

pktcEUERSTAppProfileIndex  OBJECT-TYPE
    SYNTAX      PktcEUETCRSTAppPrfIndexType
    MAX-ACCESS  not-accessible
    STATUS      current
    DESCRIPTION
        " This MIB Object identifies an instance of an 
          RST application profile."
    ::= { pktcEUERSTAppProfileToFeatEntry 1 }

pktcEUERSTAppFeatIndex  OBJECT-TYPE
    SYNTAX      PktcEUETCRSTAppFeatIndexType
    MAX-ACCESS  not-accessible
    STATUS      current
    DESCRIPTION
        " This MIB Object identifies a specific RST feature
          instance."
    ::= { pktcEUERSTAppProfileToFeatEntry 2 }  
    
pktcEUERSTAppFeatID  OBJECT-TYPE
    SYNTAX      PktcRSTTCFeatID
    MAX-ACCESS  read-create
    STATUS      current
    DESCRIPTION
        " The MIB Object identifies a specific RST
          feature, as specified by PacketCable RST."
    ::= { pktcEUERSTAppProfileToFeatEntry 3 } 

pktcEUERSTAppFeatIndexRef  OBJECT-TYPE
    SYNTAX      PktcEUETCRSTAppFeatIndexType
    MAX-ACCESS  read-create
    STATUS      current
    DESCRIPTION
        " The MIB Object identifies an index into the RST
          feature table identified by the MIB Object
          pktcEUERSTAppFeatID.
          A value of '0' is reserved and is used to either
          identify a global feature configuration, or when
          no configuration data is specified for the feature.
          Setting the value to '0' in any other cases will
          result in feature configuration error."
    ::= { pktcEUERSTAppProfileToFeatEntry 4 } 

pktcEUERSTAppNwActStat  OBJECT-TYPE
    SYNTAX      PktcEUETCActStatus
    MAX-ACCESS  read-create
    STATUS      current
    DESCRIPTION
        " The status of this feature as determined by the Network.
          The default value is true(1)."
    ::= { pktcEUERSTAppProfileToFeatEntry 5 }   

pktcEUERSTAppNwActStatInfo  OBJECT-TYPE
    SYNTAX      PktcEUETCActStatusInfo
    MAX-ACCESS  read-create
    STATUS      current
    DESCRIPTION
        " This MIB Object MAY provide more information about the
          status reported by the MIB Object pktcEUERSTAppNwActStat."
    ::= { pktcEUERSTAppProfileToFeatEntry 6 } 

pktcEUERSTAppEUEActStat  OBJECT-TYPE
    SYNTAX      PktcEUETCActStatus
    MAX-ACCESS  read-only
    STATUS      current
    DESCRIPTION
        " The status of this feature as determined by the eUE."
    ::= { pktcEUERSTAppProfileToFeatEntry 7 }   

pktcEUERSTAppEUEActStatInfo  OBJECT-TYPE
    SYNTAX      PktcEUETCActStatusInfo
    MAX-ACCESS  read-only
    STATUS      current
    DESCRIPTION
        " This MIB Object MAY provide more information about the
          status reported by the MIB Object pktcEUERSTAppUEActStat."
    ::= { pktcEUERSTAppProfileToFeatEntry 8 }
    
pktcEUERSTAppRowActStatus  OBJECT-TYPE
    SYNTAX      RowStatus
    MAX-ACCESS  read-only
    STATUS      current
    DESCRIPTION
        " This MIB Object defines the row status associated with this
          particular application profile in the MIB table.

          An entry in this table is not qualified for activation
          until the object instances of all corresponding columns
          have been initialized, either by default values or via
          explicit SET operations.  Until all object instances in
          this row are initialized, the status value for this realm
          must be 'notReady(3)'.

          In particular, two columnar objects must be SET: the
          'pktcEUERSTAppFeatID' and 'pktcEUERSTAppFeatIndexRef'. 
          Once these two objects have been set the row status may be SET 
          to 'active(1)'.

          The eUE MUST not allow these two objects to be changed while
          the row is 'active'. The value of this object has no effect on
          whether other columnar objects in this row can be modified."

    ::= { pktcEUERSTAppProfileToFeatEntry 9 }  

                             
-- ---------------------------------------------------------------------                     
-- The Digit Map
-- Ref (PacketCable RST specification): 
-- ---------------------------------------------------------------------                     
pktcEUERSTDigitMapFeat  OBJECT IDENTIFIER ::= { pktcEUERSTProfile 3 }

-- Digit Map Timers are per UE

pktcEUERSTDMTimerT  OBJECT-TYPE
    SYNTAX      Unsigned32
    MAX-ACCESS  read-write
    STATUS      current
    DESCRIPTION
        " This data element provides the Digit Map Timer T."
    ::= { pktcEUERSTDigitMapFeat 1 }

pktcEUERSTDMTimerS  OBJECT-TYPE
    SYNTAX      Unsigned32
    MAX-ACCESS  read-write
    STATUS      current
    DESCRIPTION
        " This data element provides the Digit Map Timer S."
    ::= { pktcEUERSTDigitMapFeat 2 }

pktcEUERSTDMTimerL  OBJECT-TYPE
    SYNTAX      Unsigned32
    MAX-ACCESS  read-write
    STATUS      current
    DESCRIPTION
        " This data element provides the Digit Map Timer L."
    ::= { pktcEUERSTDigitMapFeat 3 }

pktcEUERSTDMTimerZ  OBJECT-TYPE
    SYNTAX      Unsigned32
    MAX-ACCESS  read-write
    STATUS      current
    DESCRIPTION
        " This data element provides the Digit Map Timer Z."
    ::= { pktcEUERSTDigitMapFeat 4 }

-- ------------------------------------------
-- Digit Map Profile Table
-- ------------------------------------------
pktcEUERSTDigitMapProfileTable OBJECT-TYPE
    SYNTAX      SEQUENCE OF PktcEUERSTDigitMapProfileEntry
    MAX-ACCESS  not-accessible
    STATUS      current
    DESCRIPTION
        " This table provides a Digit Map Profile. A Digit Map
          Profile may be shared by multiple Users"
    ::= { pktcEUERSTDigitMapFeat 5 } 
    
pktcEUERSTDigitMapProfileEntry OBJECT-TYPE
    SYNTAX      PktcEUERSTDigitMapProfileEntry
    MAX-ACCESS  not-accessible
    STATUS      current
    DESCRIPTION
        "Each entry in this table provides a digit map profile."
    INDEX  { pktcEUERSTDMIndex }
    ::= { pktcEUERSTDigitMapProfileTable 1 } 
    
PktcEUERSTDigitMapProfileEntry ::=
    SEQUENCE {
              pktcEUERSTDMIndex           PktcEUETCRSTAppFeatIndexType,
              pktcEUERSTDMValue           OCTET STRING
             }

pktcEUERSTDMIndex  OBJECT-TYPE
    SYNTAX      PktcEUETCRSTAppFeatIndexType
    MAX-ACCESS  not-accessible
    STATUS      current
    DESCRIPTION
        " This data element provides an index for the table.
          Values used for this index must be greater that zero
          and are not required to be sequential. This index 
          value may be provided as data in other objects that 
          reference this table."
    ::= { pktcEUERSTDigitMapProfileEntry 1 }

pktcEUERSTDMValue  OBJECT-TYPE
    SYNTAX      OCTET STRING(SIZE(0..8192))
    MAX-ACCESS  read-only
    STATUS      current
    DESCRIPTION
        "This MIB Object specifies the ABNF for the Digit Map.
         Refer to the PacketCable RST Feature Specification 
         for representation and validation details."
   REFERENCE "PacketCable RST Feature Specification"
    ::= { pktcEUERSTDigitMapProfileEntry 2 }

             
-- ---------------------------------------------------------------------                     
-- The Basic Call Features 
-- Ref (PacketCable RST specification): Table "Basic Call Feature Data" 
-- ---------------------------------------------------------------------                     
pktcEUERSTBasicCallFeat  OBJECT IDENTIFIER ::= { pktcEUERSTFeatures 1 } 
 
-- The USER Basic-Call Feature Table

pktcEUERSTBasicCallTable OBJECT-TYPE
    SYNTAX      SEQUENCE OF PktcEUERSTBasicCallEntry
    MAX-ACCESS  not-accessible
    STATUS      current
    DESCRIPTION
        " This data table represents User-based parameters
          associated with the Basic Call Feature for the 
          RST Service."
    ::= { pktcEUERSTBasicCallFeat 1 } 
    
pktcEUERSTBasicCallEntry OBJECT-TYPE
    SYNTAX      PktcEUERSTBasicCallEntry
    MAX-ACCESS  not-accessible
    STATUS      current
    DESCRIPTION
        " Each entry in this data table describes an association
          of an user with a Basic Call Feature parameter."
    INDEX  { pktcEUERSTBCallIndex }
    ::= { pktcEUERSTBasicCallTable 1 } 
    
PktcEUERSTBasicCallEntry ::=
    SEQUENCE {
              pktcEUERSTBCallIndex    PktcEUETCRSTAppFeatIndexType,
              pktcEUERSTBCallSDP      SnmpAdminString
             }

pktcEUERSTBCallIndex  OBJECT-TYPE
    SYNTAX      PktcEUETCRSTAppFeatIndexType
    MAX-ACCESS  not-accessible
    STATUS      current
    DESCRIPTION
        " This data element provides an index for the table.
          Values used for this index must be greater that zero
          and are not required to be sequential. This index 
          value may be provided as data in other objects that 
          reference this table."
    ::= { pktcEUERSTBasicCallEntry 1 }
   
pktcEUERSTBCallSDP  OBJECT-TYPE 
    SYNTAX      SnmpAdminString 
    MAX-ACCESS  read-write 
    STATUS      current 
    DESCRIPTION 
        " This MIB Object specifies the SDP parameters and value." 
    REFERENCE "PacketCable Residential SIP Telephony Feature Specification" 
    ::= { pktcEUERSTBasicCallEntry 2 } 


-- ---------------------------------------------------------------------                     
-- The NETWORK Basic-Call Feature Table
-- Ref (PacketCable RST specification): Table "Basic Call Feature Data" 
-- ---------------------------------------------------------------------                     

pktcEUERSTNfBasicCallTable OBJECT-TYPE
    SYNTAX      SEQUENCE OF PktcEUERSTNfBasicCallEntry
    MAX-ACCESS  not-accessible
    STATUS      current
    DESCRIPTION
        " This data table represents Network-based parameters
          associated with the Basic Call Feature for the 
          RST Service."
    ::= { pktcEUERSTBasicCallFeat 2 } 
    
pktcEUERSTNfBasicCallEntry OBJECT-TYPE
    SYNTAX      PktcEUERSTNfBasicCallEntry
    MAX-ACCESS  not-accessible
    STATUS      current
    DESCRIPTION
        " Each entry in this data table describes an association
          of an Network Service Provider with a Basic Call Feature
          parameter."
    INDEX  { pktcEUEDevOpIndex }
    ::= { pktcEUERSTNfBasicCallTable 1 } 
    
PktcEUERSTNfBasicCallEntry ::=
    SEQUENCE {
              pktcEUERSTNfBCallByeDelay            Unsigned32,
              pktcEUERSTNfBCallOrigDTTimer         Unsigned32,
              pktcEUERSTNfBCallTermOHErrSig        PktcRSTTCTONEANNC,
              pktcEUERSTNfBCallTermErrSigTimer     Unsigned32,   
              pktcEUERSTNfBCallPermSeqTone1        PktcRSTTCTONEANNC,
              pktcEUERSTNfBCallPermSeqTimer1       Unsigned32,
              pktcEUERSTNfBCallPermSeqTone2        PktcRSTTCTONEANNC,
              pktcEUERSTNfBCallPermSeqTimer2       Unsigned32,
              pktcEUERSTNfBCallPermSeqTone3        PktcRSTTCTONEANNC,
              pktcEUERSTNfBCallPermSeqTimer3       Unsigned32,
              pktcEUERSTNfBCallLORTimer            Unsigned32,
              pktcEUERSTNfBCallNEMDSCPValue        Unsigned32
             }
          
pktcEUERSTNfBCallByeDelay  OBJECT-TYPE 
    SYNTAX      Unsigned32 
    MAX-ACCESS  read-write 
    STATUS      current 
    DESCRIPTION 
        " This MIB Object specifies the Bye Delay in seconds." 
    REFERENCE "PacketCable Residential SIP Telephony Feature Specification" 
    ::= { pktcEUERSTNfBasicCallEntry 1 }  

pktcEUERSTNfBCallOrigDTTimer  OBJECT-TYPE 
    SYNTAX      Unsigned32 
    MAX-ACCESS  read-write 
    STATUS      current 
    DESCRIPTION 
        " This MIB Object specifies the Origination Mode 
          Dial Tone Timer in seconds." 
    REFERENCE "PacketCable Residential SIP Telephony Feature Specification" 
    ::= { pktcEUERSTNfBasicCallEntry 2 } 
 
pktcEUERSTNfBCallTermOHErrSig  OBJECT-TYPE 
    SYNTAX      PktcRSTTCTONEANNC 
    MAX-ACCESS  read-write 
    STATUS      current 
    DESCRIPTION 
        " This MIB Object specifies the Termination Mode Off-Hook 
          error signal." 
    REFERENCE "PacketCable Residential SIP Telephony Feature Specification" 
    ::= { pktcEUERSTNfBasicCallEntry 3 } 
                                           
pktcEUERSTNfBCallTermErrSigTimer  OBJECT-TYPE 
    SYNTAX      Unsigned32 
    MAX-ACCESS  read-write 
    STATUS      current 
    DESCRIPTION 
        " This MIB Object specifies the Termination Mode error signal 
          timer in seconds." 
    REFERENCE "PacketCable Residential SIP Telephony Feature Specification" 
    ::= { pktcEUERSTNfBasicCallEntry 4 } 
     
pktcEUERSTNfBCallPermSeqTone1  OBJECT-TYPE 
    SYNTAX      PktcRSTTCTONEANNC 
    MAX-ACCESS  read-write 
    STATUS      current 
    DESCRIPTION 
        " This MIB Object specifies the Permanent Sequence tone 1." 
    REFERENCE "PacketCable Residential SIP Telephony Feature Specification" 
    ::= { pktcEUERSTNfBasicCallEntry 5 } 
 
pktcEUERSTNfBCallPermSeqTimer1  OBJECT-TYPE 
    SYNTAX      Unsigned32 
    MAX-ACCESS  read-write 
    STATUS      current 
    DESCRIPTION 
        " This MIB Object specifies the Permanent Sequence timer 1
          in seconds." 
    REFERENCE "PacketCable Residential SIP Telephony Feature Specification" 
    ::= { pktcEUERSTNfBasicCallEntry 6 } 
  
pktcEUERSTNfBCallPermSeqTone2  OBJECT-TYPE 
    SYNTAX      PktcRSTTCTONEANNC 
    MAX-ACCESS  read-write 
    STATUS      current 
    DESCRIPTION 
        " This MIB Object specifies the Permanent Sequence tone 2." 
    REFERENCE "PacketCable Residential SIP Telephony Feature Specification" 
    ::= { pktcEUERSTNfBasicCallEntry 7 } 
 
pktcEUERSTNfBCallPermSeqTimer2  OBJECT-TYPE 
    SYNTAX      Unsigned32 
    MAX-ACCESS  read-write 
    STATUS      current 
    DESCRIPTION 
        " This MIB Object specifies the Permanent Sequence timer 2
          in seconds." 
    REFERENCE "PacketCable Residential SIP Telephony Feature Specification" 
    ::= { pktcEUERSTNfBasicCallEntry 8 } 

pktcEUERSTNfBCallPermSeqTone3  OBJECT-TYPE 
     SYNTAX      PktcRSTTCTONEANNC 
     MAX-ACCESS  read-write 
     STATUS      current 
     DESCRIPTION 
         " This MIB Object specifies the Permanent Sequence tone 3." 
     REFERENCE "PacketCable Residential SIP Telephony Feature Specification" 
     ::= { pktcEUERSTNfBasicCallEntry 9 } 
  
pktcEUERSTNfBCallPermSeqTimer3  OBJECT-TYPE 
     SYNTAX      Unsigned32 
     MAX-ACCESS  read-write 
     STATUS      current 
     DESCRIPTION 
         " This MIB Object specifies the Permanent Sequence timer 3
           in seconds." 
     REFERENCE "PacketCable Residential SIP Telephony Feature Specification" 
    ::= { pktcEUERSTNfBasicCallEntry 10 } 

pktcEUERSTNfBCallLORTimer  OBJECT-TYPE 
    SYNTAX      Unsigned32 
    MAX-ACCESS  read-write 
    STATUS      current 
    DESCRIPTION 
        " This MIB Object specifies the Lockout Reset timer in seconds." 
    REFERENCE "PacketCable Residential SIP Telephony Feature Specification" 
    ::= { pktcEUERSTNfBasicCallEntry 11 } 

pktcEUERSTNfBCallNEMDSCPValue  OBJECT-TYPE 
    SYNTAX      Unsigned32(0..63) 
    MAX-ACCESS  read-write 
    STATUS      current 
    DESCRIPTION 
        " This MIB Object specifies the Non-Emergency media DSCP Value." 
    REFERENCE "PacketCable Residential SIP Telephony Feature Specification" 
    ::= { pktcEUERSTNfBasicCallEntry 12 } 
 
-- ---------------------------------------------------------------------                     
-- Pktc EUE RST Announcement Feature Profile 
-- Ref (PacketCable RST specification): Table "Announcement Feature Data" 
-- ---------------------------------------------------------------------                     
pktcEUERSTAncFeat  OBJECT IDENTIFIER ::= { pktcEUERSTFeatures 2 } 
 
-- The USER Announcement Feature Table

pktcEUERSTAncTable OBJECT-TYPE
    SYNTAX      SEQUENCE OF PktcEUERSTAncEntry
    MAX-ACCESS  not-accessible
    STATUS      current
    DESCRIPTION
        " This data table represents User-based parameters
          associated with the Announcement Feature for the 
          RST Service."
    ::= { pktcEUERSTAncFeat 1 } 
    
pktcEUERSTAncEntry OBJECT-TYPE
    SYNTAX      PktcEUERSTAncEntry
    MAX-ACCESS  not-accessible
    STATUS      current
    DESCRIPTION
        " Each entry in this data table describes an association
          of an user with an Announcement Feature parameter."
    INDEX  { pktcEUERSTAncIndex }
    ::= { pktcEUERSTAncTable 1 } 
    
PktcEUERSTAncEntry ::=
    SEQUENCE {
              pktcEUERSTAncIndex      PktcEUETCRSTAppFeatIndexType,
              pktcEUERSTAncPrefLang   SnmpAdminString
             } 
 
pktcEUERSTAncIndex  OBJECT-TYPE
    SYNTAX      PktcEUETCRSTAppFeatIndexType
    MAX-ACCESS  not-accessible
    STATUS      current
    DESCRIPTION
        " This data element provides an index for the table.
          Values used for this index must be greater that zero
          and are not required to be sequential. This index 
          value may be provided as data in other objects that 
          reference this table."
    ::= { pktcEUERSTAncEntry 1 }
 
pktcEUERSTAncPrefLang  OBJECT-TYPE 
    SYNTAX      SnmpAdminString 
    MAX-ACCESS  read-write 
    STATUS      current 
    DESCRIPTION 
        " This MIB Object specifies the preferred language for the 
          UE announcement." 
    REFERENCE "PacketCable Residential SIP Telephony Feature Specification" 
    ::= { pktcEUERSTAncEntry 2 } 


-- ---------------------------------------------------------------------                     
-- The NETWORK Announcement Call Feature Table
-- Ref (PacketCable RST specification): Table "Basic Call Feature Data" 
-- ---------------------------------------------------------------------                     

pktcEUERSTNfAncTable OBJECT-TYPE
    SYNTAX      SEQUENCE OF PktcEUERSTNfAncEntry
    MAX-ACCESS  not-accessible
    STATUS      current
    DESCRIPTION
        " This data table represents Network-based parameters
          associated with the Announcement Feature for the 
          RST Service."
    ::= { pktcEUERSTAncFeat 2 } 
    
pktcEUERSTNfAncEntry OBJECT-TYPE
    SYNTAX      PktcEUERSTNfAncEntry
    MAX-ACCESS  not-accessible
    STATUS      current
    DESCRIPTION
        " Each entry in this data table describes an association
          of an Network Service Provider with a Announcement Feature
          parameter."
    INDEX  { pktcEUEDevOpIndex }
    ::= { pktcEUERSTNfAncTable 1 } 
    
PktcEUERSTNfAncEntry ::=
    SEQUENCE {
              pktcEUERSTNfAncRes                SnmpAdminString,
              pktcEUERSTNfAncDomain             SnmpAdminString,
              pktcEUERSTNfAncPath               SnmpAdminString,
              pktcEUERSTNfAncMIMEType           SnmpAdminString
             }
          
pktcEUERSTNfAncRes  OBJECT-TYPE 
    SYNTAX      SnmpAdminString 
    MAX-ACCESS  read-write 
    STATUS      current 
    DESCRIPTION 
        " This MIB Object specifies the Announcement Resource 
          URI for the media server" 
    REFERENCE "PacketCable Residential SIP Telephony Feature Specification" 
    ::= { pktcEUERSTNfAncEntry 1 } 

pktcEUERSTNfAncDomain  OBJECT-TYPE 
    SYNTAX      SnmpAdminString 
    MAX-ACCESS  read-write 
    STATUS      current 
    DESCRIPTION 
        " This MIB Object specifies the Announcement Domain." 
    REFERENCE "PacketCable Residential SIP Telephony Feature Specification" 
    ::= { pktcEUERSTNfAncEntry 2 } 
 
pktcEUERSTNfAncPath  OBJECT-TYPE 
    SYNTAX      SnmpAdminString 
    MAX-ACCESS  read-write 
    STATUS      current 
    DESCRIPTION 
        " This MIB Object specifies the Announcement Path." 
    REFERENCE "PacketCable Residential SIP Telephony Feature Specification" 
    ::= { pktcEUERSTNfAncEntry 3 } 
 
pktcEUERSTNfAncMIMEType OBJECT-TYPE 
    SYNTAX      SnmpAdminString 
    MAX-ACCESS  read-write 
    STATUS      current 
    DESCRIPTION 
        " This MIB Object specifies the Announcement MIME type." 
    REFERENCE "PacketCable Residential SIP Telephony Feature Specification" 
    ::= { pktcEUERSTNfAncEntry 4 } 


-- ---------------------------------------------------------------------                     
-- The NETWORK Announcement Map Feature Table
-- Ref (PacketCable RST specification): Table "Basic Call Feature Data" 
-- ---------------------------------------------------------------------                     

pktcEUERSTNfAncMapTable OBJECT-TYPE 
    SYNTAX      SEQUENCE OF PktcEUERSTNfAncMapEntry 
    MAX-ACCESS  not-accessible 
    STATUS      current 
    DESCRIPTION 
        " This data table represents the network-based announcement MAP entries" 
    REFERENCE "PacketCable Residential SIP Telephony Feature Specification" 
    ::= { pktcEUERSTAncFeat 3 }  
     
pktcEUERSTNfAncMapEntry OBJECT-TYPE 
    SYNTAX      PktcEUERSTNfAncMapEntry 
    MAX-ACCESS  not-accessible 
    STATUS      current 
    DESCRIPTION 
        " This data table represents the network-based announcement MAP entries. 
          Each entry in this table represents the Announcement MAP  
          entry URI corresponding to a response code." 
    REFERENCE "PacketCable Residential SIP Telephony Feature Specification" 
    INDEX  {pktcEUEDevOpIndex, pktcEUERSTNfAncRspCode} 
    ::= { pktcEUERSTNfAncMapTable 1 }  
     
PktcEUERSTNfAncMapEntry ::= 
    SEQUENCE { 
              pktcEUERSTNfAncRspCode           Unsigned32, 
              pktcEUERSTNfAncURI               SnmpAdminString 
             } 
 
pktcEUERSTNfAncRspCode OBJECT-TYPE 
    SYNTAX      Unsigned32(0..32000) 
    MAX-ACCESS  not-accessible 
    STATUS      current 
    DESCRIPTION 
        " This MIB Object specifies the Response code." 
    REFERENCE "PacketCable Residential SIP Telephony Feature Specification" 
    ::= { pktcEUERSTNfAncMapEntry 1 }   

pktcEUERSTNfAncURI OBJECT-TYPE 
    SYNTAX      SnmpAdminString 
    MAX-ACCESS  read-write 
    STATUS      current 
    DESCRIPTION 
        " This MIB Object specifies the Announcement Map entry. 
          A string identifying the URI for response code." 
    REFERENCE "PacketCable Residential SIP Telephony Feature Specification" 
    ::= { pktcEUERSTNfAncMapEntry 2 } 
 

-- ---------------------------------------------------------------------                     
-- The NETWORK Announcement Media Map Feature Table
-- Ref (PacketCable RST specification): Table "Basic Call Feature Data" 
-- ---------------------------------------------------------------------                     
 
pktcEUERSTNfAncMediaMapTable OBJECT-TYPE 
    SYNTAX      SEQUENCE OF PktcEUERSTNfAncMediaMapEntry 
    MAX-ACCESS  not-accessible 
    STATUS      current 
    DESCRIPTION 
        " This data table represents the network-based announcement 
          Media MAP entries" 
    REFERENCE "PacketCable Residential SIP Telephony Feature Specification" 
    ::= { pktcEUERSTAncFeat 4 }  
     
pktcEUERSTNfAncMediaMapEntry OBJECT-TYPE 
    SYNTAX      PktcEUERSTNfAncMediaMapEntry 
    MAX-ACCESS  not-accessible 
    STATUS      current 
    DESCRIPTION 
        " This data table represents the announcement Media MAP entries. 
          Each entry in this table represents the Announcement Media MAP  
          entry URI corresponding to an announcement identifier." 
    REFERENCE "PacketCable Residential SIP Telephony Feature Specification" 
    INDEX  {pktcEUEDevOpIndex, pktcEUERSTNfAncMediaId} 
    ::= { pktcEUERSTNfAncMediaMapTable 1 }  
     
PktcEUERSTNfAncMediaMapEntry ::= 
    SEQUENCE { 
              pktcEUERSTNfAncMediaId             SnmpAdminString, 
              pktcEUERSTNfAncMediaURI            SnmpAdminString,
              pktcEUERSTNfAncMediaCachMaxAge     Unsigned32 
             } 	
 
pktcEUERSTNfAncMediaId OBJECT-TYPE 
    SYNTAX      SnmpAdminString 
    MAX-ACCESS  not-accessible 
    STATUS      current 
    DESCRIPTION 
        " This MIB Object specifies the announcement Identifier." 
    REFERENCE "PacketCable Residential SIP Telephony Feature Specification" 
    ::= { pktcEUERSTNfAncMediaMapEntry 1 }   
     
pktcEUERSTNfAncMediaURI OBJECT-TYPE 
    SYNTAX      SnmpAdminString 
    MAX-ACCESS  read-write 
    STATUS      current 
    DESCRIPTION 
        " This MIB Object specifies the Announcement Media Map entry. 
          A string identifying the URI for announcement identifier." 
    REFERENCE "PacketCable Residential SIP Telephony Feature Specification" 
    ::= { pktcEUERSTNfAncMediaMapEntry 2 } 

pktcEUERSTNfAncMediaCachMaxAge OBJECT-TYPE 
    SYNTAX      Unsigned32 
    MAX-ACCESS  read-write 
    STATUS      current 
    DESCRIPTION 
        " This MIB Object specifies the Announcement Media Cache 
          maximum age in seconds." 
    REFERENCE "PacketCable Residential SIP Telephony Feature Specification" 
    ::= { pktcEUERSTNfAncMediaMapEntry 3 } 


-- ---------------------------------------------------------------------                     
-- The NETWORK Announcement Local Media Feature Table            
-- Ref (PacketCable RST specification): Table "Basic Call Feature Data" 
-- ---------------------------------------------------------------------                     
                  
pktcEUERSTNfAncLocalMediaTable OBJECT-TYPE 
    SYNTAX      SEQUENCE OF PktcEUERSTNfAncLocalMediaEntry 
    MAX-ACCESS  not-accessible 
    STATUS      current 
    DESCRIPTION 
        " This data table represents the network-based Local Media entries" 
    REFERENCE "PacketCable Residential SIP Telephony Feature Specification" 
    ::= { pktcEUERSTAncFeat 5 }  
     
pktcEUERSTNfAncLocalMediaEntry OBJECT-TYPE 
    SYNTAX      PktcEUERSTNfAncLocalMediaEntry 
    MAX-ACCESS  not-accessible 
    STATUS      current 
    DESCRIPTION 
        " Each entry in this table represents the Local Media   
          entries." 
    INDEX  {pktcEUEDevOpIndex, pktcEUERSTNfAncLclMediaURI} 
    ::= { pktcEUERSTNfAncLocalMediaTable 1 }  
     
PktcEUERSTNfAncLocalMediaEntry ::= 
    SEQUENCE { 
              pktcEUERSTNfAncLclMediaURI         SnmpAdminString, 
              pktcEUERSTNfAncLclMediaType        SnmpAdminString, 
              pktcEUERSTNfAncLclMediaData        SnmpAdminString 
             } 
             
pktcEUERSTNfAncLclMediaURI OBJECT-TYPE 
    SYNTAX      SnmpAdminString 
    MAX-ACCESS  not-accessible 
    STATUS      current 
    DESCRIPTION 
        " This MIB Object specifies the Local Media entry. 
          A string identifying the URI for the Local Media." 
    REFERENCE "PacketCable Residential SIP Telephony Feature Specification" 
    ::= { pktcEUERSTNfAncLocalMediaEntry 1 }   
     
pktcEUERSTNfAncLclMediaType OBJECT-TYPE 
    SYNTAX      SnmpAdminString 
    MAX-ACCESS  read-write 
    STATUS      current 
    DESCRIPTION 
        " This MIB Object specifies the Media Type entry." 
    REFERENCE "PacketCable Residential SIP Telephony Feature Specification" 
    ::= { pktcEUERSTNfAncLocalMediaEntry 2 } 
 
pktcEUERSTNfAncLclMediaData OBJECT-TYPE 
    SYNTAX      SnmpAdminString 
    MAX-ACCESS  read-write 
    STATUS      current 
    DESCRIPTION 
        " This MIB Object specifies the Media Data entry." 
    REFERENCE "PacketCable Residential SIP Telephony Feature Specification" 
    ::= { pktcEUERSTNfAncLocalMediaEntry 3 } 
 
  
-- ---------------------------------------------------------------------                     
-- Pktc EUE RST UE ActStatus Change Feature Profile 
-- Ref (PacketCable RST specification): "UE ActStatus Change Feature Data" 
-- ---------------------------------------------------------------------                     
pktcEUERSTUEActStatChgFeat  OBJECT IDENTIFIER ::= { pktcEUERSTFeatures 3 } 
     
-- The USER UE ActStatus Change Feature Table

pktcEUERSTUEActStatChgTable OBJECT-TYPE
    SYNTAX      SEQUENCE OF PktcEUERSTUEActStatChgEntry
    MAX-ACCESS  not-accessible
    STATUS      current
    DESCRIPTION
        " This data table represents User-based parameters
          associated with the UE ActStatus Change Feature for the 
          RST Service."
    ::= { pktcEUERSTUEActStatChgFeat 1 } 
    
pktcEUERSTUEActStatChgEntry OBJECT-TYPE
    SYNTAX      PktcEUERSTUEActStatChgEntry
    MAX-ACCESS  not-accessible
    STATUS      current
    DESCRIPTION
        " Each entry in this data table describes an association
          of an user with a UE ActStatus Change Feature parameter."
    INDEX  { pktcEUERSTUEActStatChgIndex }
    ::= { pktcEUERSTUEActStatChgTable 1 } 
    
PktcEUERSTUEActStatChgEntry ::=
    SEQUENCE {
              pktcEUERSTUEActStatChgIndex    PktcEUETCRSTAppFeatIndexType,
              pktcEUERSTUEActStatChgRegExp   Unsigned32
             }

pktcEUERSTUEActStatChgIndex  OBJECT-TYPE
    SYNTAX      PktcEUETCRSTAppFeatIndexType
    MAX-ACCESS  not-accessible
    STATUS      current
    DESCRIPTION
        " This data element provides an index for the table.
          Values used for this index must be greater that zero
          and are not required to be sequential. This index 
          value may be provided as data in other objects that 
          reference this table."
    ::= { pktcEUERSTUEActStatChgEntry 1 }
 
pktcEUERSTUEActStatChgRegExp  OBJECT-TYPE 
    SYNTAX      Unsigned32 
    MAX-ACCESS  read-write 
    STATUS      current 
    DESCRIPTION 
        " This MIB Object specifies the UE ActStatus Registration expiration 
          in seconds." 
    REFERENCE "PacketCable Residential SIP Telephony Feature Specification" 
    ::= { pktcEUERSTUEActStatChgEntry 2 } 

   
-- ---------------------------------------------------------------------                     
-- Pktc EUE RST No Answer Timeout Feature Profile 
-- Ref (PacketCable RST specification): "No Answer Timeout Feature Data" 
-- ---------------------------------------------------------------------                     
pktcEUERSTNoAnsTimeoutFeat  OBJECT IDENTIFIER ::= { pktcEUERSTFeatures 4 } 
 
-- The USER No Answer timeout Feature Table

pktcEUERSTNoAnsTimeoutTable OBJECT-TYPE
    SYNTAX      SEQUENCE OF PktcEUERSTNoAnsTimeoutEntry
    MAX-ACCESS  not-accessible
    STATUS      current
    DESCRIPTION
        " This data table represents User-based parameters
          associated with the No Answer Timeout Feature for the 
          RST Service."
    ::= { pktcEUERSTNoAnsTimeoutFeat 1 } 
    
pktcEUERSTNoAnsTimeoutEntry OBJECT-TYPE
    SYNTAX      PktcEUERSTNoAnsTimeoutEntry
    MAX-ACCESS  not-accessible
    STATUS      current
    DESCRIPTION
        " Each entry in this data table describes an association
          of an user with a No Answer Timeout Feature parameter."
    INDEX  { pktcEUERSTNoAnsTOIndex }
    ::= { pktcEUERSTNoAnsTimeoutTable 1 } 
    
PktcEUERSTNoAnsTimeoutEntry ::=
    SEQUENCE {
              pktcEUERSTNoAnsTOIndex      PktcEUETCRSTAppFeatIndexType,
              pktcEUERSTNoAnsTODuration   Unsigned32
             }

pktcEUERSTNoAnsTOIndex  OBJECT-TYPE
    SYNTAX      PktcEUETCRSTAppFeatIndexType
    MAX-ACCESS  not-accessible
    STATUS      current
    DESCRIPTION
        " This data element provides an index for the table.
          Values used for this index must be greater that zero
          and are not required to be sequential. This index 
          value may be provided as data in other objects that 
          reference this table."
    ::= { pktcEUERSTNoAnsTimeoutEntry 1 }
 
pktcEUERSTNoAnsTODuration  OBJECT-TYPE 
    SYNTAX      Unsigned32 
    MAX-ACCESS  read-write 
    STATUS      current 
    DESCRIPTION 
        " This MIB Object specifies the No Answer Timeout Duration 
          in seconds." 
    REFERENCE "PacketCable Residential SIP Telephony Feature Specification" 
    ::= { pktcEUERSTNoAnsTimeoutEntry 2 } 
 
  
-- ---------------------------------------------------------------------            
-- Pktc EUE RST Caller ID Feature Profile 
-- Ref (PacketCable RST specification): " Caller ID Feature Data" 
-- ---------------------------------------------------------------------                     
pktcEUERSTCallerIdFeat  OBJECT IDENTIFIER ::= { pktcEUERSTFeatures 5 } 
 
-- The USER Caller ID Feature Table

pktcEUERSTCIDTable OBJECT-TYPE
    SYNTAX      SEQUENCE OF PktcEUERSTCIDEntry
    MAX-ACCESS  not-accessible
    STATUS      current
    DESCRIPTION
        " This data table represents User-based parameters
          associated with the Caller ID Feature for the 
          RST Service."
    ::= { pktcEUERSTCallerIdFeat 1 } 
    
pktcEUERSTCIDEntry OBJECT-TYPE
    SYNTAX      PktcEUERSTCIDEntry
    MAX-ACCESS  not-accessible
    STATUS      current
    DESCRIPTION
        " Each entry in this data table describes an association
          of an user with a Caller ID Feature parameter."
    INDEX  { pktcEUERSTCIDIndex }
    ::= { pktcEUERSTCIDTable 1 } 
    
PktcEUERSTCIDEntry ::=
    SEQUENCE {
              pktcEUERSTCIDIndex      PktcEUETCRSTAppFeatIndexType,
              pktcEUERSTCIDPPS        INTEGER
             }

pktcEUERSTCIDIndex  OBJECT-TYPE
    SYNTAX      PktcEUETCRSTAppFeatIndexType
    MAX-ACCESS  not-accessible
    STATUS      current
    DESCRIPTION
        " This data element provides an index for the table.
          Values used for this index must be greater that zero
          and are not required to be sequential. This index 
          value may be provided as data in other objects that 
          reference this table."
    ::= { pktcEUERSTCIDEntry 1 }
 
pktcEUERSTCIDPPS  OBJECT-TYPE 
    SYNTAX      INTEGER { 
                    anonymous(1), 
                    public(2) 
                } 
    MAX-ACCESS  read-write 
    STATUS      current 
    DESCRIPTION 
        " This MIB Object specifies the Permanent Presentation ActStatus." 
    REFERENCE "PacketCable Residential SIP Telephony Feature Specification" 
    ::= { pktcEUERSTCIDEntry 2 } 
 
 
-- ---------------------------------------------------------------------            
-- Pktc EUE RST Caller ID Display Feature Profile 
-- Ref (PacketCable RST specification): "Caller ID Display Feature Data" 
-- ---------------------------------------------------------------------                     

pktcEUERSTCIDDisFeat  OBJECT IDENTIFIER ::= { pktcEUERSTFeatures 6 } 
 
-- The USER Caller ID Display Feature Table

pktcEUERSTCIDDisTable OBJECT-TYPE
    SYNTAX      SEQUENCE OF PktcEUERSTCIDDisEntry
    MAX-ACCESS  not-accessible
    STATUS      current
    DESCRIPTION
        " This data table represents User-based parameters
          associated with the Caller ID Display Feature for the 
          RST Service."
    ::= { pktcEUERSTCIDDisFeat 1 } 
    
pktcEUERSTCIDDisEntry OBJECT-TYPE
    SYNTAX      PktcEUERSTCIDDisEntry
    MAX-ACCESS  not-accessible
    STATUS      current
    DESCRIPTION
        " Each entry in this data table describes an association
          of an user with a Caller ID Display Feature parameter."
    INDEX  { pktcEUERSTCIDDisIndex }
    ::= { pktcEUERSTCIDDisTable 1 } 
    
PktcEUERSTCIDDisEntry ::=
    SEQUENCE {
              pktcEUERSTCIDDisIndex             PktcEUETCRSTAppFeatIndexType,
              pktcEUERSTCIDDisCNDActActStat     TruthValue,   
              pktcEUERSTCIDDisCNAMDActActStat   TruthValue,
              pktcEUERSTCIDDisDefCountry        SnmpAdminString
             }

pktcEUERSTCIDDisIndex  OBJECT-TYPE
    SYNTAX      PktcEUETCRSTAppFeatIndexType
    MAX-ACCESS  not-accessible
    STATUS      current
    DESCRIPTION
        " This data element provides an index for the table.
          Values used for this index must be greater that zero
          and are not required to be sequential. This index 
          value may be provided as data in other objects that 
          reference this table."
    ::= { pktcEUERSTCIDDisEntry 1 }
 
pktcEUERSTCIDDisCNDActActStat  OBJECT-TYPE 
    SYNTAX      TruthValue 
    MAX-ACCESS  read-write 
    STATUS      current 
    DESCRIPTION 
        " This MIB Object specifies the activation status for Calling  
          Number Display (CND)." 
    REFERENCE "PacketCable Residential SIP Telephony Feature Specification" 
    ::= { pktcEUERSTCIDDisEntry 2 }   
 
pktcEUERSTCIDDisCNAMDActActStat  OBJECT-TYPE 
    SYNTAX      TruthValue  
    MAX-ACCESS  read-write 
    STATUS      current 
    DESCRIPTION 
        " This MIB Object specifies the activation status for Calling 
          Name Display (CNAMD)." 
    REFERENCE "PacketCable Residential SIP Telephony Feature Specification" 
    ::= { pktcEUERSTCIDDisEntry 3 }   
 
pktcEUERSTCIDDisDefCountry  OBJECT-TYPE 
    SYNTAX      SnmpAdminString 
    MAX-ACCESS  read-write 
    STATUS      current 
    DESCRIPTION 
        " This MIB Object specifies default country code." 
    REFERENCE "PacketCable Residential SIP Telephony Feature Specification" 
    ::= { pktcEUERSTCIDDisEntry 4 } 
 
--  A static object

pktcEUERSTCIDDisTimeAdj  OBJECT-TYPE 
    SYNTAX      SnmpAdminString 
    MAX-ACCESS  read-write 
    STATUS      current 
    DESCRIPTION 
        " This MIB Object specifies the adjustment from location invariant
          time to time at current location.  The time delta in minutes."
    REFERENCE "PacketCable Residential SIP Telephony Feature Specification" 
    ::= { pktcEUERSTCIDDisFeat 2 } 


-- ---------------------------------------------------------------------       
-- Pktc EUE RST Caller ID Per Call Blocking Feature Profile 
-- Ref (PacketCable RST specification): "Caller ID Per-Call Blocking Feature Data" 
-- ---------------------------------------------------------------------                     
pktcEUERSTCIDCallBlkFeat  OBJECT IDENTIFIER ::= { pktcEUERSTFeatures 7 } 
 
-- The USER Caller Call Block Feature Table

pktcEUERSTCallBlkTable OBJECT-TYPE
    SYNTAX      SEQUENCE OF PktcEUERSTCallBlkEntry
    MAX-ACCESS  not-accessible
    STATUS      current
    DESCRIPTION
        " This data table represents User-based parameters
          associated with the Call Block Feature for the 
          RST Service."
    ::= { pktcEUERSTCIDCallBlkFeat 1 } 
    
pktcEUERSTCallBlkEntry OBJECT-TYPE
    SYNTAX      PktcEUERSTCallBlkEntry
    MAX-ACCESS  not-accessible
    STATUS      current
    DESCRIPTION
        " Each entry in this data table describes an association
          of an user with a Call Block Feature parameter."
    INDEX  { pktcEUERSTCIDBlkIndex }
    ::= { pktcEUERSTCallBlkTable 1 } 
    
PktcEUERSTCallBlkEntry ::=
    SEQUENCE {
              pktcEUERSTCIDBlkIndex           PktcEUETCRSTAppFeatIndexType,
              pktcEUERSTCIDCBlkConfTone       PktcRSTTCTONEANNC,
              pktcEUERSTCIDCBlkErrTone        PktcRSTTCTONEANNC
             }

pktcEUERSTCIDBlkIndex  OBJECT-TYPE
    SYNTAX      PktcEUETCRSTAppFeatIndexType
    MAX-ACCESS  not-accessible
    STATUS      current
    DESCRIPTION
        " This data element provides an index for the table.
          Values used for this index must be greater that zero
          and are not required to be sequential. This index 
          value may be provided as data in other objects that 
          reference this table."
    ::= { pktcEUERSTCallBlkEntry 1 }
 
pktcEUERSTCIDCBlkConfTone  OBJECT-TYPE 
    SYNTAX      PktcRSTTCTONEANNC 
    MAX-ACCESS  read-write 
    STATUS      current 
    DESCRIPTION 
        " This MIB Object specifies the confirmation tone after 
          vertical feature code." 
    REFERENCE "PacketCable Residential SIP Telephony Feature Specification" 
    ::= { pktcEUERSTCallBlkEntry 2 } 
                        
pktcEUERSTCIDCBlkErrTone  OBJECT-TYPE 
    SYNTAX      PktcRSTTCTONEANNC 
    MAX-ACCESS  read-write 
    STATUS      current 
    DESCRIPTION 
        " This MIB Object specifies the error tone after 
          vertical feature code failure." 
    REFERENCE "PacketCable Residential SIP Telephony Feature Specification" 
    ::= { pktcEUERSTCallBlkEntry 3 } 
           
          
 -- ---------------------------------------------------------------------       
 -- Pktc EUE RST Caller ID Per Call Delivery Feature Profile 
 -- Ref (PacketCable RST specification): "Caller ID Per-Call Delivery Feature  Data" 
 -- ---------------------------------------------------------------------                     
 pktcEUERSTCIDCallDelFeat  OBJECT IDENTIFIER ::= { pktcEUERSTFeatures 8 } 
  
 -- The USER Caller Call Delivery Feature Table

pktcEUERSTCallDelTable OBJECT-TYPE
    SYNTAX      SEQUENCE OF PktcEUERSTCallDelEntry
    MAX-ACCESS  not-accessible
    STATUS      current
    DESCRIPTION
        " This data table represents User-based parameters
          associated with the Call Delivery Feature for the 
          RST Service."
    ::= { pktcEUERSTCIDCallDelFeat 1 } 
    
pktcEUERSTCallDelEntry OBJECT-TYPE
    SYNTAX      PktcEUERSTCallDelEntry
    MAX-ACCESS  not-accessible
    STATUS      current
    DESCRIPTION
        " Each entry in this data table describes an association
          of an user with a Call Delivery Feature parameter."
    INDEX  { pktcEUERSTCIDDelIndex }
    ::= { pktcEUERSTCallDelTable 1 } 
    
PktcEUERSTCallDelEntry ::=
    SEQUENCE {
              pktcEUERSTCIDDelIndex       PktcEUETCRSTAppFeatIndexType,
              pktcEUERSTCIDDelConfTone    PktcRSTTCTONEANNC,
              pktcEUERSTCIDDelErrTone     PktcRSTTCTONEANNC
             }

pktcEUERSTCIDDelIndex  OBJECT-TYPE
    SYNTAX      PktcEUETCRSTAppFeatIndexType
    MAX-ACCESS  not-accessible
    STATUS      current
    DESCRIPTION
        " This data element provides an index for the table.
          Values used for this index must be greater that zero
          and are not required to be sequential. This index 
          value may be provided as data in other objects that 
          reference this table."
    ::= { pktcEUERSTCallDelEntry 1 }
 
pktcEUERSTCIDDelConfTone  OBJECT-TYPE 
     SYNTAX      PktcRSTTCTONEANNC 
     MAX-ACCESS  read-write 
     STATUS      current 
     DESCRIPTION 
         " This MIB Object specifies the confirmation tone after 
           vertical feature code." 
     REFERENCE "PacketCable Residential SIP Telephony Feature Specification" 
     ::= { pktcEUERSTCallDelEntry 2 } 
                         
pktcEUERSTCIDDelErrTone  OBJECT-TYPE 
     SYNTAX      PktcRSTTCTONEANNC 
     MAX-ACCESS  read-write 
     STATUS      current 
     DESCRIPTION 
         " This MIB Object specifies the error tone after 
           vertical feature code failure." 
     REFERENCE "PacketCable Residential SIP Telephony Feature Specification" 
     ::= { pktcEUERSTCallDelEntry 3 } 
     
 -- ---------------------------------------------------------------------                     
 -- Pktc EUE RST Call Forwarding Variable Feature Profile 
 -- Ref (PacketCable RST specification): "Call Forwarding Variable Feature Data" 
 -- ---------------------------------------------------------------------                     
pktcEUERSTCFwdFeat  OBJECT IDENTIFIER ::= { pktcEUERSTFeatures 9 } 

-- The USER Call Forwarding Feature Table

pktcEUERSTCallFwdTable OBJECT-TYPE
    SYNTAX      SEQUENCE OF PktcEUERSTCallFwdEntry
    MAX-ACCESS  not-accessible
    STATUS      current
    DESCRIPTION
        " This data table represents User-based parameters
          associated with the Call Forwarding Feature for the 
          RST Service."
    ::= { pktcEUERSTCFwdFeat 1 } 
    
pktcEUERSTCallFwdEntry OBJECT-TYPE
    SYNTAX      PktcEUERSTCallFwdEntry
    MAX-ACCESS  not-accessible
    STATUS      current
    DESCRIPTION
        " Each entry in this data table describes an association
          of an user with a Call Forwarding Feature parameter."
    INDEX  { pktcEUERSTCallFwdIndex }
    ::= { pktcEUERSTCallFwdTable 1 } 
    
PktcEUERSTCallFwdEntry ::=
    SEQUENCE {
              pktcEUERSTCallFwdIndex          PktcEUETCRSTAppFeatIndexType,
              pktcEUERSTCallFwdRingReminder   TruthValue,
              pktcEUERSTCallFwdSubDuration    Unsigned32   
             }

pktcEUERSTCallFwdIndex  OBJECT-TYPE
    SYNTAX      PktcEUETCRSTAppFeatIndexType
    MAX-ACCESS  not-accessible
    STATUS      current
    DESCRIPTION
        " This data element provides an index for the table.
          Values used for this index must be greater that zero
          and are not required to be sequential. This index 
          value may be provided as data in other objects that 
          reference this table."
    ::= { pktcEUERSTCallFwdEntry 1 }
 
pktcEUERSTCallFwdRingReminder  OBJECT-TYPE 
    SYNTAX      TruthValue 
    MAX-ACCESS  read-write 
    STATUS      current 
    DESCRIPTION 
        " This MIB Object specifies the Call Forward Ring Reminder." 
    REFERENCE "PacketCable Residential SIP Telephony Feature Specification" 
    ::= { pktcEUERSTCallFwdEntry 2 } 

pktcEUERSTCallFwdSubDuration  OBJECT-TYPE 
    SYNTAX      Unsigned32 
    MAX-ACCESS  read-write 
    STATUS      current 
    DESCRIPTION 
        " This MIB Object specifies the subscription duration in seconds." 
    REFERENCE "PacketCable Residential SIP Telephony Feature Specification" 
    ::= { pktcEUERSTCallFwdEntry 3 } 
         
          
-- The NETWORK Call Forwarding Feature Table            
                  
pktcEUERSTNfCallFwdTable OBJECT-TYPE 
    SYNTAX      SEQUENCE OF PktcEUERSTNfCallFwdEntry 
    MAX-ACCESS  not-accessible 
    STATUS      current 
    DESCRIPTION 
        " This data table represents the network-based Call Forwarding entries" 
    REFERENCE "PacketCable Residential SIP Telephony Feature Specification" 
    ::= { pktcEUERSTCFwdFeat 2 }  
     
pktcEUERSTNfCallFwdEntry OBJECT-TYPE 
    SYNTAX      PktcEUERSTNfCallFwdEntry 
    MAX-ACCESS  not-accessible 
    STATUS      current 
    DESCRIPTION 
        " Each entry in this table represents the Call Forwarding   
          entries." 
    INDEX  {pktcEUEDevOpIndex} 
    ::= { pktcEUERSTNfCallFwdTable 1 }  
     
PktcEUERSTNfCallFwdEntry ::= 
    SEQUENCE { 
              pktcEUERSTNfCallFwdSpDialTone      TruthValue 
             }
                
pktcEUERSTNfCallFwdSpDialTone  OBJECT-TYPE 
    SYNTAX      TruthValue 
    MAX-ACCESS  read-write 
    STATUS      current 
    DESCRIPTION 
        " This MIB Object specifies the special conditions dial tone 
          when forwarded indicator." 
    REFERENCE "PacketCable Residential SIP Telephony Feature Specification" 
    ::= { pktcEUERSTNfCallFwdEntry 1 } 
                                    
              
-- ---------------------------------------------------------------------       
-- Pktc EUE RST Call Waiting Feature Data 
-- Ref (PacketCable RST specification): "Call Waiting Feature Data" 
-- --------------------------------------------------------------------- 
pktcEUERSTCallWaitFeat  OBJECT IDENTIFIER ::= { pktcEUERSTFeatures 10 } 
 
-- The USER Call Waiting Feature Table

pktcEUERSTCallWaitTable OBJECT-TYPE
    SYNTAX      SEQUENCE OF PktcEUERSTCallWaitEntry
    MAX-ACCESS  not-accessible
    STATUS      current
    DESCRIPTION
        " This data table represents User-based parameters
          associated with the Call Waiting Feature for the 
          RST Service."
    ::= { pktcEUERSTCallWaitFeat 1 } 
    
pktcEUERSTCallWaitEntry OBJECT-TYPE
    SYNTAX      PktcEUERSTCallWaitEntry
    MAX-ACCESS  not-accessible
    STATUS      current
    DESCRIPTION
        " Each entry in this data table describes an association
          of an user with a Call Waiting Feature parameter."
    INDEX  { pktcEUERSTCWIndex }
    ::= { pktcEUERSTCallWaitTable 1 } 
    
PktcEUERSTCallWaitEntry ::=
    SEQUENCE {
              pktcEUERSTCWIndex          PktcEUETCRSTAppFeatIndexType,
              pktcEUERSTCWDisStarCode    SnmpAdminString
             }

pktcEUERSTCWIndex  OBJECT-TYPE
    SYNTAX      PktcEUETCRSTAppFeatIndexType
    MAX-ACCESS  not-accessible
    STATUS      current
    DESCRIPTION
        " This data element provides an index for the table.
          Values used for this index must be greater that zero
          and are not required to be sequential. This index 
          value may be provided as data in other objects that 
          reference this table."
    ::= { pktcEUERSTCallWaitEntry 1 }

pktcEUERSTCWDisStarCode  OBJECT-TYPE 
    SYNTAX      SnmpAdminString 
    MAX-ACCESS  read-write 
    STATUS      current 
    DESCRIPTION 
        " This MIB Object specifies the per call call-waiting 
          disable star code." 
    REFERENCE "PacketCable Residential SIP Telephony Feature Specification" 
    ::= { pktcEUERSTCallWaitEntry 2 }          
              
-- ---------------------------------------------------------------------       
-- Pktc EUE RST Call Hold Feature Profile 
-- Ref (PacketCable RST specification): "Call Hold Feature Data"  
-- ---------------------------------------------------------------------                     
pktcEUERSTCallHoldFeat  OBJECT IDENTIFIER ::= { pktcEUERSTFeatures 11 } 
 
-- The USER Call Hold Feature Table

pktcEUERSTCallHoldTable OBJECT-TYPE
    SYNTAX      SEQUENCE OF PktcEUERSTCallHoldEntry
    MAX-ACCESS  not-accessible
    STATUS      current
    DESCRIPTION
        " This data table represents User-based parameters
          associated with the Call Hold Feature for the 
          RST Service."
    ::= { pktcEUERSTCallHoldFeat 1 } 
    
pktcEUERSTCallHoldEntry OBJECT-TYPE
    SYNTAX      PktcEUERSTCallHoldEntry
    MAX-ACCESS  not-accessible
    STATUS      current
    DESCRIPTION
        " Each entry in this data table describes an association
          of an user with a Call Hold Feature parameter."
    INDEX  { pktcEUERSTCHIndex }
    ::= { pktcEUERSTCallHoldTable 1 } 
    
PktcEUERSTCallHoldEntry ::=
    SEQUENCE {
              pktcEUERSTCHIndex          PktcEUETCRSTAppFeatIndexType,
              pktcEUERSTCHFeatCode       SnmpAdminString,
              pktcEUERSTCHFeatConfirm    PktcRSTTCTONEANNC
             }

pktcEUERSTCHIndex  OBJECT-TYPE
    SYNTAX      PktcEUETCRSTAppFeatIndexType
    MAX-ACCESS  not-accessible
    STATUS      current
    DESCRIPTION
        " This data element provides an index for the table.
          Values used for this index must be greater that zero
          and are not required to be sequential. This index 
          value may be provided as data in other objects that 
          reference this table."
    ::= { pktcEUERSTCallHoldEntry 1 }

pktcEUERSTCHFeatCode  OBJECT-TYPE 
    SYNTAX      SnmpAdminString 
    MAX-ACCESS  read-write 
    STATUS      current 
    DESCRIPTION 
        " This MIB Object specifies the Call Hold Feature Code." 
    REFERENCE "PacketCable Residential SIP Telephony Feature Specification" 
    ::= { pktcEUERSTCallHoldEntry 2 } 
      
pktcEUERSTCHFeatConfirm  OBJECT-TYPE 
    SYNTAX      PktcRSTTCTONEANNC 
    MAX-ACCESS  read-write 
    STATUS      current 
    DESCRIPTION 
        " This MIB Object specifies the feature activation/deactivation 
          confirmation indiacator." 
    REFERENCE "PacketCable Residential SIP Telephony Feature Specification" 
    ::= { pktcEUERSTCallHoldEntry 3 } 
 
-- ---------------------------------------------------------------------           
-- Pktc EUE RST Call Transfer Feature Profile 
-- Ref (PacketCable RST specification): "Call Transfer Feature Data" 
-- ---------------------------------------------------------------------                     
pktcEUERSTCallXfrFeat  OBJECT IDENTIFIER ::= { pktcEUERSTFeatures 12 } 
 
-- The USER Call Transfer Feature Table

pktcEUERSTCallXfrTable OBJECT-TYPE
    SYNTAX      SEQUENCE OF PktcEUERSTCallXfrEntry
    MAX-ACCESS  not-accessible
    STATUS      current
    DESCRIPTION
        " This data table represents User-based parameters
          associated with the Call Hold Transfer for the 
          RST Service."
    ::= { pktcEUERSTCallXfrFeat 1 } 
    
pktcEUERSTCallXfrEntry OBJECT-TYPE
    SYNTAX      PktcEUERSTCallXfrEntry
    MAX-ACCESS  not-accessible
    STATUS      current
    DESCRIPTION
        " Each entry in this data table describes an association
          of an user with a Call Hold Transfer parameter."
    INDEX  { pktcEUERSTCXIndex }
    ::= { pktcEUERSTCallXfrTable 1 } 
    
PktcEUERSTCallXfrEntry ::=
    SEQUENCE {
              pktcEUERSTCXIndex          PktcEUETCRSTAppFeatIndexType,
              pktcEUERSTCXNtfyTimeout    Unsigned32
             }

pktcEUERSTCXIndex  OBJECT-TYPE
    SYNTAX      PktcEUETCRSTAppFeatIndexType
    MAX-ACCESS  not-accessible
    STATUS      current
    DESCRIPTION
        " This data element provides an index for the table.
          Values used for this index must be greater that zero
          and are not required to be sequential. This index 
          value may be provided as data in other objects that 
          reference this table."
    ::= { pktcEUERSTCallXfrEntry 1 }

pktcEUERSTCXNtfyTimeout  OBJECT-TYPE 
    SYNTAX      Unsigned32 
    MAX-ACCESS  read-write 
    STATUS      current 
    DESCRIPTION 
        " This MIB Object specifies the Notify Timeout in seconds." 
    REFERENCE "PacketCable Residential SIP Telephony Feature Specification" 
    ::= { pktcEUERSTCallXfrEntry 2 } 

-- --------------------------------------------------------------------- 
-- Pktc 3WC Feature Data 
-- Ref (PacketCable RST specification): "3WC Feature Data" 
-- --------------------------------------------------------------------- 
-- No extension objects for this feature
 
-- --------------------------------------------------------------------- 
-- Pktc EUE RST Do Not Disturb Feature Profile 
-- Ref (PacketCable RST specification): "DND Feature Data" 
-- --------------------------------------------------------------------- 
pktcEUERSTDnDFeat  OBJECT IDENTIFIER ::= { pktcEUERSTFeatures 13 } 
        
-- The USER Do Not Disturb Feature Table

pktcEUERSTDnDTable OBJECT-TYPE
    SYNTAX      SEQUENCE OF PktcEUERSTDnDEntry
    MAX-ACCESS  not-accessible
    STATUS      current
    DESCRIPTION
        " This data table represents User-based parameters
          associated with the Do Not Disturb feature for the 
          RST Service."
    ::= { pktcEUERSTDnDFeat 1 } 
    
pktcEUERSTDnDEntry OBJECT-TYPE
    SYNTAX      PktcEUERSTDnDEntry
    MAX-ACCESS  not-accessible
    STATUS      current
    DESCRIPTION
        " Each entry in this data table describes an association
          of an user with a Do Not Disturb parameter."
    INDEX  { pktcEUERSTDnDIndex }
    ::= { pktcEUERSTDnDTable 1 } 
    
PktcEUERSTDnDEntry ::=
    SEQUENCE {
              pktcEUERSTDnDIndex            PktcEUETCRSTAppFeatIndexType,
              pktcEUERSTDnDActConfirm       PktcRSTTCTONEANNC,
              pktcEUERSTDnDDeActConfirm     PktcRSTTCTONEANNC
             }

pktcEUERSTDnDIndex  OBJECT-TYPE
    SYNTAX      PktcEUETCRSTAppFeatIndexType
    MAX-ACCESS  not-accessible
    STATUS      current
    DESCRIPTION
        " This data element provides an index for the table.
          Values used for this index must be greater that zero
          and are not required to be sequential. This index 
          value may be provided as data in other objects that 
          reference this table."
    ::= { pktcEUERSTDnDEntry 1 }

pktcEUERSTDnDActConfirm  OBJECT-TYPE 
    SYNTAX      PktcRSTTCTONEANNC 
    MAX-ACCESS  read-write 
    STATUS      current 
    DESCRIPTION 
        " This MIB Object specifies the Feature Activation Confirmation 
          Indicator." 
    REFERENCE "PacketCable Residential SIP Telephony Feature Specification" 
    ::= { pktcEUERSTDnDEntry 2 } 
                       
pktcEUERSTDnDDeActConfirm  OBJECT-TYPE 
    SYNTAX      PktcRSTTCTONEANNC 
    MAX-ACCESS  read-write 
    STATUS      current 
    DESCRIPTION 
        " This MIB Object specifies the Feature Deactivation Confirmation 
          Indicator." 
    REFERENCE "PacketCable Residential SIP Telephony Feature Specification" 
    ::= { pktcEUERSTDnDEntry 3 }   
     
 
-- --------------------------------------------------------------------- 
-- Pktc EUE RST Subscriber Programmable PIN Feature Data 
-- Ref (PacketCable RST specification): "Subscriber Programmable PIN Feature Data" 
-- --------------------------------------------------------------------- 
-- No extension objects for this feature
 
-- --------------------------------------------------------------------- 
-- Pktc EUE RST MWI Feature Profile 
-- Ref (PacketCable RST specification): "MWI Feature Data" 
-- ---------------------------------------------------------------------       
pktcEUERSTMWIFeat  OBJECT IDENTIFIER ::= { pktcEUERSTFeatures 14 } 
                                 
-- The NETWORK MWI Feature Table            
                  
pktcEUERSTNfMWITable OBJECT-TYPE 
    SYNTAX      SEQUENCE OF PktcEUERSTNfMWIEntry 
    MAX-ACCESS  not-accessible 
    STATUS      current 
    DESCRIPTION 
        " This data table represents the network-based MWI entries" 
    REFERENCE "PacketCable Residential SIP Telephony Feature Specification" 
    ::= { pktcEUERSTMWIFeat 1 }  
     
pktcEUERSTNfMWIEntry OBJECT-TYPE 
    SYNTAX      PktcEUERSTNfMWIEntry 
    MAX-ACCESS  not-accessible 
    STATUS      current 
    DESCRIPTION 
        " Each entry in this table represents the MWI feature   
          entries." 
    INDEX  {pktcEUEDevOpIndex} 
    ::= { pktcEUERSTNfMWITable 1 }  
        
PktcEUERSTNfMWIEntry ::=
    SEQUENCE {
              pktcEUERSTNfMWISubDuration    Unsigned32        
             }

pktcEUERSTNfMWISubDuration  OBJECT-TYPE 
    SYNTAX      Unsigned32 
    MAX-ACCESS  read-write 
    STATUS      current 
    DESCRIPTION 
        " This MIB Object specifies the MWI Subscription duration." 
    REFERENCE "PacketCable Residential SIP Telephony Feature Specification" 
    ::= { pktcEUERSTNfMWIEntry 1 } 
 

-- --------------------------------------------------------------------- 
-- Pktc EUE RST Auto Recall Feature Profile 
-- Ref (PacketCable RST specification): "Auto Recall Feature Data" 
-- --------------------------------------------------------------------- 
pktcEUERSTAutoRclFeat  OBJECT IDENTIFIER ::= { pktcEUERSTFeatures 15 } 
  
-- The USER Auto Recall Feature Table

pktcEUERSTAutoRclTable OBJECT-TYPE
    SYNTAX      SEQUENCE OF PktcEUERSTAutoRclEntry
    MAX-ACCESS  not-accessible
    STATUS      current
    DESCRIPTION
        " This data table represents User-based parameters
          associated with the Auto Recall feature for the 
          RST Service."
    ::= { pktcEUERSTAutoRclFeat 1 } 
    
pktcEUERSTAutoRclEntry OBJECT-TYPE
    SYNTAX      PktcEUERSTAutoRclEntry
    MAX-ACCESS  not-accessible
    STATUS      current
    DESCRIPTION
        " Each entry in this data table describes an association
          of an user with a Auto Recall parameter."
    INDEX  { pktcEUERSTARIndex }
    ::= { pktcEUERSTAutoRclTable 1 } 
    
PktcEUERSTAutoRclEntry ::=
    SEQUENCE {
              pktcEUERSTARIndex            PktcEUETCRSTAppFeatIndexType,
              pktcEUERSTARTimer            Unsigned32,
              pktcEUERSTARSpRngDuration    Unsigned32,
              pktcEUERSTARSpRngRetryTime   Unsigned32,
              pktcEUERSTARSpRngRetries     Unsigned32,
              pktcEUERSTARMaxSubSend       Unsigned32,
              pktcEUERSTARMaxSubRec        Unsigned32                 
             }

pktcEUERSTARIndex  OBJECT-TYPE
    SYNTAX      PktcEUETCRSTAppFeatIndexType
    MAX-ACCESS  not-accessible
    STATUS      current
    DESCRIPTION
        " This data element provides an index for the table.
          Values used for this index must be greater that zero
          and are not required to be sequential. This index 
          value may be provided as data in other objects that 
          reference this table."
    ::= { pktcEUERSTAutoRclEntry 1 }

pktcEUERSTARTimer  OBJECT-TYPE 
    SYNTAX      Unsigned32 (0..30) 
    MAX-ACCESS  read-write 
    STATUS      current 
    DESCRIPTION 
        " This MIB Object specifies the auto recall timer. 
          This is minutes of feature duration." 
    REFERENCE "PacketCable Residential SIP Telephony Feature Specification" 
    DEFVAL      {30} 
    ::= { pktcEUERSTAutoRclEntry 2 } 
    
pktcEUERSTARSpRngDuration  OBJECT-TYPE 
    SYNTAX      Unsigned32  
    MAX-ACCESS  read-write 
    STATUS      current 
    DESCRIPTION 
        " This MIB Object specifies the auto recall special ring duration. 
          This is the number of special ringing ring cycles." 
    REFERENCE "PacketCable Residential SIP Telephony Feature Specification" 
    ::= { pktcEUERSTAutoRclEntry 3 } 
     
pktcEUERSTARSpRngRetryTime  OBJECT-TYPE 
    SYNTAX      Unsigned32  
    MAX-ACCESS  read-write 
    STATUS      current 
    DESCRIPTION 
        " This MIB Object specifies the auto recall special ringing retry 
          wait interval. This is seconds to wait between attempts to alert 
          the user with special ringing." 
    REFERENCE "PacketCable Residential SIP Telephony Feature Specification" 
    ::= { pktcEUERSTAutoRclEntry 4 } 
 
pktcEUERSTARSpRngRetries  OBJECT-TYPE 
    SYNTAX      Unsigned32  
    MAX-ACCESS  read-write 
    STATUS      current 
    DESCRIPTION 
        " This MIB Object specifies the number of auto recall special ringing  
          retries. 
          This is the number of times to retry special ringing before canceling 
          the AR request." 
    REFERENCE "PacketCable Residential SIP Telephony Feature Specification" 
    ::= { pktcEUERSTAutoRclEntry 5 } 
 
pktcEUERSTARMaxSubSend  OBJECT-TYPE 
    SYNTAX      Unsigned32  
    MAX-ACCESS  read-write 
    STATUS      current 
    DESCRIPTION 
        " This MIB Object specifies the maximum number of simultaneous  
          subscribes the UE should send." 
    REFERENCE "PacketCable Residential SIP Telephony Feature Specification" 
    ::= { pktcEUERSTAutoRclEntry 6 } 
 
pktcEUERSTARMaxSubRec  OBJECT-TYPE 
    SYNTAX      Unsigned32  
    MAX-ACCESS  read-write 
    STATUS      current 
    DESCRIPTION 
        " This MIB Object specifies the maximum number of simultaneous  
          subscriptions the UE should honor." 
    REFERENCE "PacketCable Residential SIP Telephony Feature Specification" 
    ::= { pktcEUERSTAutoRclEntry 7 } 
 

-- --------------------------------------------------------------------- 
-- Pktc EUE RST Auto Callback Feature Profile 
-- Ref (PacketCable RST specification): "Auto Callback Feature Data" 
-- --------------------------------------------------------------------- 
pktcEUERSTAutoCbFeat  OBJECT IDENTIFIER ::= { pktcEUERSTFeatures 16 } 
                      
-- The USER Auto Callback Feature Table

pktcEUERSTAutoCbTable OBJECT-TYPE
    SYNTAX      SEQUENCE OF PktcEUERSTAutoCbEntry
    MAX-ACCESS  not-accessible
    STATUS      current
    DESCRIPTION
        " This data table represents User-based parameters
          associated with the Auto Callback feature for the 
          RST Service."
    ::= { pktcEUERSTAutoCbFeat 1 } 
    
pktcEUERSTAutoCbEntry OBJECT-TYPE
    SYNTAX      PktcEUERSTAutoCbEntry
    MAX-ACCESS  not-accessible
    STATUS      current
    DESCRIPTION
        " Each entry in this data table describes an association
          of an user with a Auto Callback parameter."
    INDEX  { pktcEUERSTACbIndex }
    ::= { pktcEUERSTAutoCbTable 1 } 
    
PktcEUERSTAutoCbEntry ::=
    SEQUENCE {
              pktcEUERSTACbIndex            PktcEUETCRSTAppFeatIndexType,
              pktcEUERSTACbTimer            Unsigned32,
              pktcEUERSTACbSpRngDuration    Unsigned32,
              pktcEUERSTACbSpRngRetryTime   Unsigned32,
              pktcEUERSTACbSpRngRetries     Unsigned32,
              pktcEUERSTACbMaxSubSend       Unsigned32,
              pktcEUERSTACbMaxSubRec        Unsigned32                 
             }

pktcEUERSTACbIndex  OBJECT-TYPE
    SYNTAX      PktcEUETCRSTAppFeatIndexType
    MAX-ACCESS  not-accessible
    STATUS      current
    DESCRIPTION
        " This data element provides an index for the table.
          Values used for this index must be greater that zero
          and are not required to be sequential. This index 
          value may be provided as data in other objects that 
          reference this table."
    ::= { pktcEUERSTAutoCbEntry 1 }

pktcEUERSTACbTimer  OBJECT-TYPE 
    SYNTAX      Unsigned32 (0..30) 
    MAX-ACCESS  read-write 
    STATUS      current 
    DESCRIPTION 
        " This MIB Object specifies the auto callback timer. 
          This is minutes of feature duration. 0-30min. Default=30" 
    REFERENCE "PacketCable Residential SIP Telephony Feature Specification" 
    DEFVAL      {30} 
    ::= { pktcEUERSTAutoCbEntry 2 } 

pktcEUERSTACbSpRngDuration  OBJECT-TYPE 
    SYNTAX      Unsigned32  
    MAX-ACCESS  read-write 
    STATUS      current 
    DESCRIPTION 
        " This MIB Object specifies the auto callback special ring duration. 
          This is the number of special ringing ring cycles." 
    REFERENCE "PacketCable Residential SIP Telephony Feature Specification" 
    ::= { pktcEUERSTAutoCbEntry 3 } 
     
pktcEUERSTACbSpRngRetryTime  OBJECT-TYPE 
    SYNTAX      Unsigned32  
    MAX-ACCESS  read-write 
    STATUS      current 
    DESCRIPTION 
        " This MIB Object specifies the auto callback special ringing retry 
          wait interval. This is seconds to wait between attempts to alert 
          the user with special ringing." 
    REFERENCE "PacketCable Residential SIP Telephony Feature Specification" 
    ::= { pktcEUERSTAutoCbEntry 4 } 
 
pktcEUERSTACbSpRngRetries  OBJECT-TYPE 
    SYNTAX      Unsigned32  
    MAX-ACCESS  read-write 
    STATUS      current 
    DESCRIPTION 
        " This MIB Object specifies the number of auto callback special ringing 
          retries. 
          This is the number of times to retry special ringing before canceling 
          the AR request." 
    REFERENCE "PacketCable Residential SIP Telephony Feature Specification" 
    ::= { pktcEUERSTAutoCbEntry 5 } 
 
pktcEUERSTACbMaxSubSend  OBJECT-TYPE 
    SYNTAX      Unsigned32  
    MAX-ACCESS  read-write 
    STATUS      current 
    DESCRIPTION 
        " This MIB Object specifies the maximum number of simultaneous  
          subscribes the UE should send.." 
    REFERENCE "PacketCable Residential SIP Telephony Feature Specification" 
    ::= { pktcEUERSTAutoCbEntry 6 } 
 
pktcEUERSTACbMaxSubRec  OBJECT-TYPE 
    SYNTAX      Unsigned32  
    MAX-ACCESS  read-write 
    STATUS      current 
    DESCRIPTION 
        " This MIB Object specifies the maximum number of simultaneous 
          subscriptions the UE should honor." 
    REFERENCE "PacketCable Residential SIP Telephony Feature Specification" 
    ::= { pktcEUERSTAutoCbEntry 7 } 
 

-- ---------------------------------------------------------------------       
-- Pktc EUE RST Busy Line Verify Feature Profile 
-- Ref (PacketCable RST specification): "Busy Line Verify Feature Data" 
-- ---------------------------------------------------------------------                     
pktcEUERSTBusyLineVFeat  OBJECT IDENTIFIER ::= { pktcEUERSTFeatures 17 } 
        
-- The NETWORK Busy Line Verify Feature Table            
                  
pktcEUERSTNfBusyLineVTable OBJECT-TYPE 
    SYNTAX      SEQUENCE OF PktcEUERSTNfBusyLineVEntry 
    MAX-ACCESS  not-accessible 
    STATUS      current 
    DESCRIPTION 
        " This data table represents the network-based Busy Line Verify
          Feature entries" 
    REFERENCE "PacketCable Residential SIP Telephony Feature Specification" 
    ::= { pktcEUERSTBusyLineVFeat 1 }  
     
pktcEUERSTNfBusyLineVEntry OBJECT-TYPE 
    SYNTAX      PktcEUERSTNfBusyLineVEntry 
    MAX-ACCESS  not-accessible 
    STATUS      current 
    DESCRIPTION 
        " Each entry in this table represents the Busy Line Verify feature   
          entries." 
    INDEX  {pktcEUEDevOpIndex} 
    ::= { pktcEUERSTNfBusyLineVTable 1 }  
        
PktcEUERSTNfBusyLineVEntry ::=
    SEQUENCE {
              pktcEUERSTNfBLVOperId  SnmpAdminString        
             }    
             
pktcEUERSTNfBLVOperId  OBJECT-TYPE 
    SYNTAX      SnmpAdminString 
    MAX-ACCESS  read-write 
    STATUS      current 
    DESCRIPTION 
        " This MIB Object specifies the Busy Line Verify Operator Id." 
    REFERENCE "PacketCable Residential SIP Telephony Feature Specification" 
    ::= { pktcEUERSTNfBusyLineVEntry 1 } 
                        
-- --------------------------------------------------------------------- 
-- Pktc EUE RST Emergency Services Feature Profile 
-- Ref (PacketCable RST specification): "Emergency Services Feature Data" 
-- ---------------------------------------------------------------------                     
pktcEUERSTEmSvcFeat  OBJECT IDENTIFIER ::= { pktcEUERSTFeatures 18 } 
        
-- The NETWORK Emergency Services Feature Table            
                  
pktcEUERSTNfEmSvcTable OBJECT-TYPE 
    SYNTAX      SEQUENCE OF PktcEUERSTNfEmSvcEntry 
    MAX-ACCESS  not-accessible 
    STATUS      current 
    DESCRIPTION 
        " This data table represents the network-based Emergency Services
          Feature entries" 
    REFERENCE "PacketCable Residential SIP Telephony Feature Specification" 
    ::= { pktcEUERSTEmSvcFeat 1 }  
     
pktcEUERSTNfEmSvcEntry OBJECT-TYPE 
    SYNTAX      PktcEUERSTNfEmSvcEntry 
    MAX-ACCESS  not-accessible 
    STATUS      current 
    DESCRIPTION 
        " Each entry in this table represents the Emergency Services
          feature entries." 
    INDEX  {pktcEUEDevOpIndex} 
    ::= { pktcEUERSTNfEmSvcTable 1 }  
        
PktcEUERSTNfEmSvcEntry ::=
    SEQUENCE {
              pktcEUERSTNfEmSvcNwHoldTimer   Unsigned32,
              pktcEUERSTNfEmSvcHowlTimer     Unsigned32, 
              pktcEUERSTNfEmSvcMediaDSCPVal  Unsigned32     
             }    

pktcEUERSTNfEmSvcNwHoldTimer  OBJECT-TYPE 
    SYNTAX      Unsigned32 
    MAX-ACCESS  read-write 
    STATUS      current 
    DESCRIPTION 
        " This MIB Object specifies the Emergency Services network hold 
          timer in minutes." 
    REFERENCE "PacketCable Residential SIP Telephony Feature Specification" 
    DEFVAL      {45} 
    ::= { pktcEUERSTNfEmSvcEntry 1 } 
   
pktcEUERSTNfEmSvcHowlTimer  OBJECT-TYPE 
    SYNTAX      Unsigned32 
    MAX-ACCESS  read-write 
    STATUS      current 
    DESCRIPTION 
        " This MIB Object specifies the Emergency Services howler 
          timer in seconds. " 
    REFERENCE "PacketCable Residential SIP Telephony Feature Specification" 
    DEFVAL      {3} 
    ::= { pktcEUERSTNfEmSvcEntry 2 } 
                  
pktcEUERSTNfEmSvcMediaDSCPVal  OBJECT-TYPE 
    SYNTAX      Unsigned32 (0..63) 
    MAX-ACCESS  read-write 
    STATUS      current 
    DESCRIPTION 
        
         "This MIB Object specifies the Emergency Services emergency media 
         DSCP value." 
    REFERENCE "PacketCable Residential SIP Telephony Feature Specification" 
    ::= { pktcEUERSTNfEmSvcEntry 3 }    
         

 -- ---------------------------------------------------------------------                     
 -- Pktc EUE RST SCF Feature Profile 
 -- Ref (PacketCable RST specification): "SCF Feature Data" 
 -- ---------------------------------------------------------------------                     
pktcEUERSTSCFFeat  OBJECT IDENTIFIER ::= { pktcEUERSTFeatures 19 } 

-- The USER Call Forwarding Feature Table

pktcEUERSTSCFTable OBJECT-TYPE
    SYNTAX      SEQUENCE OF PktcEUERSTSCFEntry
    MAX-ACCESS  not-accessible
    STATUS      current
    DESCRIPTION
        " This data table represents User-based parameters
          associated with the RST SCF Feature." 
    ::= { pktcEUERSTSCFFeat 1 } 
    
pktcEUERSTSCFEntry OBJECT-TYPE
    SYNTAX      PktcEUERSTSCFEntry
    MAX-ACCESS  not-accessible
    STATUS      current
    DESCRIPTION
        " Each entry in this data table describes an association
          of an user with a SCF parameter."
    INDEX  { pktcEUERSTSCFIndex }
    ::= { pktcEUERSTSCFTable 1 } 
    
PktcEUERSTSCFEntry ::=
    SEQUENCE {
              pktcEUERSTSCFIndex            PktcEUETCRSTAppFeatIndexType,
              pktcEUERSTSCFCFRingReminder   TruthValue
             }

pktcEUERSTSCFIndex  OBJECT-TYPE
    SYNTAX      PktcEUETCRSTAppFeatIndexType
    MAX-ACCESS  not-accessible
    STATUS      current
    DESCRIPTION
        " This data element provides an index for the table.
          Values used for this index must be greater that zero
          and are not required to be sequential. This index 
          value may be provided as data in other objects that 
          reference this table."
    ::= { pktcEUERSTSCFEntry 1 }
 
pktcEUERSTSCFCFRingReminder  OBJECT-TYPE 
    SYNTAX      TruthValue 
    MAX-ACCESS  read-write 
    STATUS      current 
    DESCRIPTION 
        " This MIB Object specifies the Call Forward Ring Reminder." 
    REFERENCE "PacketCable Residential SIP Telephony Feature Specification" 
    ::= { pktcEUERSTSCFEntry 2 } 


-- --------------------------------------------------------------------- 
-- Conformance Information  
-- --------------------------------------------------------------------- 
pktcEUERSTMIBCompliances  OBJECT IDENTIFIER ::= { pktcEUERSTConformance 1 } 
pktcEUERSTMIBGroups       OBJECT IDENTIFIER ::= { pktcEUERSTConformance 2 } 
 
-- Compliance ActStatements 
pktcEUERSTMIBCompliance MODULE-COMPLIANCE 
    STATUS      current 
    DESCRIPTION 
            "The compliance statement for implementations of the RST Mib " 
    MODULE   -- this module 
        MANDATORY-GROUPS { 
                 pktcEUERSTProfileGroup,
                 pktcEUERSTBasicCallGroup, 
                 pktcEUERSTAncGroup, 
                 pktcEUERSTUEStGroup, 
                 pktcEUERSTNoAnsGroup, 
                 pktcEUERSTCallerIDGroup, 
                 pktcEUERSTCallFwdGroup, 
                 pktcEUERSTCallWaitGroup, 
                 pktcEUERSTCallHoldGroup, 
                 pktcEUERSTCallTransGroup, 
                 pktcEUERSTDNDGroup, 
                 pktcEUERSTMWIGroup, 
                 pktcEUERSTAutoRecallGroup, 
                 pktcEUERSTAutoCallbackGroup, 
                 pktcEUERSTBusyLineGroup, 
                 pktcEUERSTEmerSvcGroup, 
                 pktcEUERSTDigitMapGroup,
                 pktcEUERSTAppProfileGroup  
                 } 
    ::= { pktcEUERSTMIBCompliances 1 }           

pktcEUERSTProfileGroup OBJECT-GROUP
      OBJECTS { 
         pktcEUERSTProfileVersion
      }
      STATUS  current
      DESCRIPTION
            "The eUE RST Profile Group."
      ::= { pktcEUERSTMIBGroups 1}
 
pktcEUERSTBasicCallGroup OBJECT-GROUP 
      OBJECTS {             
          pktcEUERSTBCallSDP,
          pktcEUERSTNfBCallByeDelay,         
          pktcEUERSTNfBCallOrigDTTimer,      
          pktcEUERSTNfBCallTermOHErrSig,   
          pktcEUERSTNfBCallTermErrSigTimer,     
          pktcEUERSTNfBCallPermSeqTone1,     
          pktcEUERSTNfBCallPermSeqTimer1,    
          pktcEUERSTNfBCallPermSeqTone2,     
          pktcEUERSTNfBCallPermSeqTimer2,    
          pktcEUERSTNfBCallPermSeqTone3,     
          pktcEUERSTNfBCallPermSeqTimer3,    
          pktcEUERSTNfBCallLORTimer,
          pktcEUERSTNfBCallNEMDSCPValue
      } 
      STATUS  current 
      DESCRIPTION 
            "The RST Basic Call Group." 
      ::= { pktcEUERSTMIBGroups 2} 

pktcEUERSTAncGroup OBJECT-GROUP 
      OBJECTS {             
          pktcEUERSTAncPrefLang,
          pktcEUERSTNfAncRes,
          pktcEUERSTNfAncDomain,
          pktcEUERSTNfAncPath,
          pktcEUERSTNfAncMIMEType,
          pktcEUERSTNfAncURI,
          pktcEUERSTNfAncMediaURI,
          pktcEUERSTNfAncMediaCachMaxAge,
          pktcEUERSTNfAncLclMediaData,
          pktcEUERSTNfAncLclMediaType          
      } 
      STATUS  current 
      DESCRIPTION 
            "The RST Announcement Group." 
      ::= { pktcEUERSTMIBGroups 3}  
       
pktcEUERSTUEStGroup OBJECT-GROUP 
      OBJECTS {             
          pktcEUERSTUEActStatChgRegExp
      } 
      STATUS  current 
      DESCRIPTION 
            "The RST UE ActStatus Change Group." 
      ::= { pktcEUERSTMIBGroups 4}  

pktcEUERSTNoAnsGroup OBJECT-GROUP 
      OBJECTS {             
          pktcEUERSTNoAnsTODuration   
      } 
      STATUS  current 
      DESCRIPTION 
            "The RST No Answer Timeout Group." 
      ::= { pktcEUERSTMIBGroups 5}  
     
pktcEUERSTCallerIDGroup OBJECT-GROUP 
      OBJECTS {             
          pktcEUERSTCIDPPS,
          -- CID Display
          pktcEUERSTCIDDisTimeAdj,
          pktcEUERSTCIDDisCNDActActStat,
          pktcEUERSTCIDDisCNAMDActActStat,
          -- CID per Blocking  
          pktcEUERSTCIDCBlkConfTone,
          pktcEUERSTCIDCBlkErrTone,
          -- CID per Delivery 
          pktcEUERSTCIDDelConfTone,
          pktcEUERSTCIDDelErrTone,
          pktcEUERSTCIDDisDefCountry 
      } 
      STATUS  current 
      DESCRIPTION 
            "The RST Caller ID Group." 
      ::= { pktcEUERSTMIBGroups 6}  
 
pktcEUERSTCallFwdGroup OBJECT-GROUP 
      OBJECTS {             
          pktcEUERSTCallFwdRingReminder,
          pktcEUERSTCallFwdSubDuration,
          pktcEUERSTNfCallFwdSpDialTone
      } 
      STATUS  current 
      DESCRIPTION 
            "The RST Call Forward Group." 
      ::= { pktcEUERSTMIBGroups 7} 

pktcEUERSTCallWaitGroup OBJECT-GROUP 
      OBJECTS {             
          pktcEUERSTCWDisStarCode
      } 
      STATUS  current 
      DESCRIPTION 
            "The RST Call Waiting Group." 
      ::= { pktcEUERSTMIBGroups 8}  
       
pktcEUERSTCallHoldGroup OBJECT-GROUP 
      OBJECTS {             
          pktcEUERSTCHFeatCode,
          pktcEUERSTCHFeatConfirm
      } 
      STATUS  current 
      DESCRIPTION 
            "The RST Call Hold Group." 
      ::= { pktcEUERSTMIBGroups 9} 
       
pktcEUERSTCallTransGroup OBJECT-GROUP 
      OBJECTS {             
          pktcEUERSTCXNtfyTimeout
      } 
      STATUS  current 
      DESCRIPTION 
            "The RST Call Transfer Group." 
      ::= { pktcEUERSTMIBGroups 10}  
       
pktcEUERSTDNDGroup OBJECT-GROUP 
      OBJECTS {             
          pktcEUERSTDnDActConfirm,
          pktcEUERSTDnDDeActConfirm          
      } 
      STATUS  current 
      DESCRIPTION 
            "The RST Do Not Disturb Group." 
      ::= { pktcEUERSTMIBGroups 11} 
 
pktcEUERSTMWIGroup OBJECT-GROUP 
      OBJECTS {             
          pktcEUERSTNfMWISubDuration
      } 
      STATUS  current 
      DESCRIPTION 
            "The RST MWI Group." 
      ::= { pktcEUERSTMIBGroups 12} 

pktcEUERSTAutoRecallGroup OBJECT-GROUP 
      OBJECTS {             
          pktcEUERSTARTimer,
          pktcEUERSTARSpRngDuration,
          pktcEUERSTARSpRngRetryTime,
          pktcEUERSTARSpRngRetries,
          pktcEUERSTARMaxSubSend,
          pktcEUERSTARMaxSubRec
      } 
      STATUS  current 
      DESCRIPTION 
            "The RST Auto Recall Group." 
      ::= { pktcEUERSTMIBGroups 13} 
  
pktcEUERSTAutoCallbackGroup OBJECT-GROUP 
      OBJECTS {             
          pktcEUERSTACbTimer,
          pktcEUERSTACbSpRngDuration,
          pktcEUERSTACbSpRngRetryTime,
          pktcEUERSTACbSpRngRetries,
          pktcEUERSTACbMaxSubSend,
          pktcEUERSTACbMaxSubRec
      } 
      STATUS  current 
      DESCRIPTION 
            "The RST Auto Callback Group." 
      ::= { pktcEUERSTMIBGroups 14} 
 
pktcEUERSTBusyLineGroup OBJECT-GROUP 
      OBJECTS {             
          pktcEUERSTNfBLVOperId
      } 
      STATUS  current 
      DESCRIPTION 
            "The RST Busy Line Verify Group." 
      ::= { pktcEUERSTMIBGroups 15} 
 
pktcEUERSTEmerSvcGroup OBJECT-GROUP 
      OBJECTS {             
          pktcEUERSTNfEmSvcNwHoldTimer,
          pktcEUERSTNfEmSvcHowlTimer, 
          pktcEUERSTNfEmSvcMediaDSCPVal
      } 
      STATUS  current 
      DESCRIPTION 
            "The RST Emergency Services Group." 
      ::= { pktcEUERSTMIBGroups 16}    

pktcEUERSTDigitMapGroup OBJECT-GROUP 
      OBJECTS {             
          pktcEUERSTDMTimerT,
          pktcEUERSTDMTimerS,
          pktcEUERSTDMTimerL,
          pktcEUERSTDMTimerZ,
          pktcEUERSTDMValue
      } 
      STATUS  current 
      DESCRIPTION 
            "The Digit Map Group." 
      ::= { pktcEUERSTMIBGroups 17} 
      
pktcEUERSTAppProfileGroup OBJECT-GROUP 
      OBJECTS {         
          pktcEUERSTAppFeatID,
          pktcEUERSTAppFeatIndexRef,
          pktcEUERSTAppNwActStat,
          pktcEUERSTAppNwActStatInfo,
          pktcEUERSTAppEUEActStat,
          pktcEUERSTAppEUEActStatInfo,
          pktcEUERSTAppRowActStatus
      } 
      STATUS  current 
      DESCRIPTION 
            "The App Profile Group." 
      ::= { pktcEUERSTMIBGroups 18}        

pktcEUERSTSCFProfileGroup OBJECT-GROUP 
      OBJECTS {         
          pktcEUERSTSCFCFRingReminder
      } 
      STATUS  current 
      DESCRIPTION 
            "The SCF Profile Group." 
      ::= { pktcEUERSTMIBGroups 19}        
      
END
