-- @(#)ph-tcpip.mib	1.14 5/29/97

POWERHUB-TCPIP-MIB DEFINITIONS ::= BEGIN

	IMPORTS
	    enterprises, OBJECT-TYPE, NetworkAddress, IpAddress,
	    Counter, Gauge, TimeTicks FROM RFC1155-SMI

	    DisplayString, PhysAddress FROM RFC1213-MIB;

	fore		OBJECT IDENTIFIER ::= { enterprises 326 }
	systems		OBJECT IDENTIFIER ::= { fore 2 }
	lsd		OBJECT IDENTIFIER ::= { systems 6 }

	lsdproducts	OBJECT IDENTIFIER ::= { lsd 1 }
	lsdcommon	OBJECT IDENTIFIER ::= { lsd 2 }

	alrip		OBJECT IDENTIFIER ::= { lsdcommon 4 }
	altcp		OBJECT IDENTIFIER ::= { lsdcommon 5 }
	alip		OBJECT IDENTIFIER ::= { lsdcommon 6 }


	-- READ THIS!!!!!
	-- PowerHub OID branch allocations
	--  NOTE: Do NOT uncomment the mib branches below!!.
	--        This is shown here to get a general idea on
	--        the powerhub mib subtree layout while viewing
	--        this file.
	--

	-- fore		OBJECT IDENTIFIER ::= { enterprises 326 }
	-- systems	OBJECT IDENTIFIER ::= { fore 2 }
	-- lsd		OBJECT IDENTIFIER ::= { systems 6 }

	-- lsdproducts	OBJECT IDENTIFIER ::= { lsd 1 }
	-- lsdcommon	OBJECT IDENTIFIER ::= { lsd 2 }

	-- powerhub4k6k7k OBJECT IDENTIFIER ::= { lsdproducts 1 }
	-- powerbits	OBJECT IDENTIFIER ::= { lsdproducts 2 }

	-- alchassis	OBJECT IDENTIFIER ::= { powerhub4k6k7k 1 }
	-- alatm	OBJECT IDENTIFIER ::= { powerhub4k6k7k 2 }
	-- alsystem	OBJECT IDENTIFIER ::= { lsdcommon 1 }
	-- albridge	OBJECT IDENTIFIER ::= { lsdcommon 2 }
	-- almgmt	OBJECT IDENTIFIER ::= { lsdcommon 3 }
	-- alrip	OBJECT IDENTIFIER ::= { lsdcommon 4 }
	-- altcp	OBJECT IDENTIFIER ::= { lsdcommon 5 }
	-- alip		OBJECT IDENTIFIER ::= { lsdcommon 6 }
	-- alat		OBJECT IDENTIFIER ::= { lsdcommon 7 }
	-- aldecnet	OBJECT IDENTIFIER ::= { lsdcommon 8 }
	-- alipx	OBJECT IDENTIFIER ::= { lsdcommon 9 }
	-- alsnmp	OBJECT IDENTIFIER ::= { lsdcommon 10 }

	-- 1.4	The "rip" subsystem --
	-- 1.4.1 set RIP control type

	    alripControlType OBJECT-TYPE
		SYNTAX  INTEGER {
		    normal(1),
		    vlan(2)
		    }			
		ACCESS  read-write
		STATUS  mandatory
		DESCRIPTION
                    "control type to change the RIP update mechanism"
	    ::= { alrip 1 }

	--  1.4.2 RIP configuration
	--  1.4.2.1 per segment method
	--		  showcfg
	--		  set
	--	The above two commands show/set the RIP configuration for the
	--	indicated port(s). Since they operate on the port(s), a RIP
	--	configuration table can be modeled that stores the per port
	--	RIP parameters.

	    alRipNormalConfigTable OBJECT-TYPE
		SYNTAX  SEQUENCE OF AlripNormalConfigEntry
		ACCESS  not-accessible
		STATUS  mandatory
		DESCRIPTION
		    "Per port RIP configuration per segment method."
	    ::= { alrip 2 }

	    alripNormalConfigEntry OBJECT-TYPE
		SYNTAX  AlripNormalConfigEntry
		ACCESS  not-accessible
		STATUS  mandatory
		DESCRIPTION
		    "information about a specific RIP configuration entry "
		INDEX   { alripNormalConfigPort }
	    ::= { alRipNormalConfigTable 1 }
 
	    AlripNormalConfigEntry ::= 
		SEQUENCE {
			alripNormalConfigPort
			    INTEGER,
			alripNormalConfigTalk
			    INTEGER,
			alripNormalConfigListen
			    INTEGER,
			alripNormalConfigPoison
			    INTEGER,
			alripNormalConfigRptStaticRt
			    INTEGER,
			alripNormalConfigRptDefaultRt
			    INTEGER,
			alripNormalConfigAccptDefaultRt
			    INTEGER	
		}
 
	    alripNormalConfigPort OBJECT-TYPE
		SYNTAX  INTEGER
		ACCESS  read-write
		STATUS  mandatory
		DESCRIPTION
		    "Port number for which the RIP parameters
		    are to be set or viewed."
		::= { alripNormalConfigEntry 1 }

	    alripNormalConfigTalk OBJECT-TYPE
		SYNTAX  INTEGER {
			    yes(1),
			    no (2)
			}
		ACCESS  read-write 
		STATUS  mandatory
		DESCRIPTION
		    "Controls whether the hub generates RIP
		    packets on the port identified by the instance of 
		    ripConfigPort."
		DEFVAL {1}
		::= { alripNormalConfigEntry 2 }

	    alripNormalConfigListen OBJECT-TYPE
		SYNTAX  INTEGER { 
			    yes(1), 
			    no (2) 
			}
		ACCESS  read-write 
		STATUS  mandatory
		DESCRIPTION
		    "Controls whether the hub processes RIP
		    packets received on the port identified by the 
		    instance of ripConfigPort."
		DEFVAL {1}
		::= { alripNormalConfigEntry 3 }

	    alripNormalConfigPoison OBJECT-TYPE
		SYNTAX  INTEGER { 
			    yes(1), 
			    no (2) 
       			}
		ACCESS  read-write 
		STATUS  mandatory
		DESCRIPTION
		    "Controls what happens when a route goes down.
		    If set to no(2), the hub simply stops reporting the
		    route. If set to yes(1), the hub reports it one more
		    time, but with a metric value of 16, which infinity
		    as far as RIP is concerned. Thus other routers learn
		    immediately that the route is down."
		DEFVAL {0}
		::= { alripNormalConfigEntry 4 }

	    alripNormalConfigRptStaticRt OBJECT-TYPE
		SYNTAX  INTEGER { 
			    yes(1), 
			    no (2) 
			}
		ACCESS  read-write 
		STATUS  mandatory
		DESCRIPTION
		    "When RIP packets are generated on the port,
		    controls whether the hub reports the static routes
		    in its route table."
		DEFVAL {1}
		::= { alripNormalConfigEntry 5 }

	    alripNormalConfigRptDefaultRt OBJECT-TYPE
		SYNTAX  INTEGER { 
			    yes(1), 
			    no (2) 
           		}
		ACCESS  read-write 
		STATUS  mandatory
		DESCRIPTION
		    "When RIP packets are generated on the port,
		    controls whether the hub reports the default routes,
		    if any, in ints route table."
		DEFVAL {1}
		::= { alripNormalConfigEntry 6 }

	    alripNormalConfigAccptDefaultRt OBJECT-TYPE
		SYNTAX  INTEGER { 
			    yes(1), 
			    no (2) 
			}
		ACCESS  read-write 
		STATUS  mandatory
		DESCRIPTION
		    "When RIP packets are received on the port,
		    controls whether the hub accepts(learns) a default
		    route that is reported in a RIP packet."
		DEFVAL {1}
		::= { alripNormalConfigEntry 7 }

	--  1.4.2.2 per VLAN  method
	--  rip-control-table add
	--  rip-control-table del
	--  rip-control-table show
	--	The above three commands show/set the RIP configuration for the
	--	indicated VLAN(s). Since they operate on the VLAN(s), a RIP
	--	configuration table can be modeled that stores the per VLAN 
	--	RIP parameters.

	    alRipVLANConfigTable OBJECT-TYPE
		SYNTAX  SEQUENCE OF AlripVLANConfigEntry
		ACCESS  not-accessible
		STATUS  mandatory
		DESCRIPTION
		    " Per port RIP configuration per VLAN method."
	    ::= { alrip 3 }

	    alripVLANConfigEntry OBJECT-TYPE
		SYNTAX  AlripVLANConfigEntry
		ACCESS  not-accessible
		STATUS  mandatory
		DESCRIPTION
		    "information about a specific RIP configuration entry"
		INDEX   { alripVLANConfigNetNumber }
	    ::= { alRipVLANConfigTable 1 }
 
	    AlripVLANConfigEntry ::= 
		SEQUENCE {
		    alripVLANConfigNetNumber
			IpAddress,
	    	    alripVLANConfigTalk
            		INTEGER,
	    	    alripVLANConfigListen
    		        INTEGER,
		    alripVLANConfigPoison
			INTEGER,
		    alripVLANConfigRptStaticRt
			INTEGER,
		    alripVLANConfigRptDefaultRt
			INTEGER,
		    alripVLANConfigAccptDefaultRt
			INTEGER,	
		    alripVLANConfigDelete
			INTEGER
		}
 
	    alripVLANConfigNetNumber OBJECT-TYPE
		SYNTAX  IpAddress
		ACCESS  read-write
		STATUS  mandatory
		DESCRIPTION
		    "IP network number for which the RIP
		    parameters are to be set or viewed."
		::= { alripVLANConfigEntry 1 }

	    alripVLANConfigTalk OBJECT-TYPE
		SYNTAX  INTEGER {
			    yes(1),
			    no (2)
			}
		ACCESS  read-write 
		STATUS  mandatory
		DESCRIPTION
		    "Controls whether the hub generates RIP
		    packets on the port identified by the instance of 
		    ripConfigPort."
		DEFVAL {1}
		::= { alripVLANConfigEntry 2 }


	    alripVLANConfigListen OBJECT-TYPE
		SYNTAX  INTEGER { 
			    yes(1), 
			    no (2) 
        		}
		ACCESS  read-write 
		STATUS  mandatory
		DESCRIPTION
		    "Controls whether the hub processes RIP
		    packets received on the port identified by the 
		    instance of ripConfigPort. This field cannot be
		    activated if this interface is controlled by OSPF"
		DEFVAL {1}
		::= { alripVLANConfigEntry 3 }

	    alripVLANConfigPoison OBJECT-TYPE
		SYNTAX  INTEGER { 
			    yes(1), 
			    no (2) 
			}
		ACCESS  read-write 
		STATUS  mandatory
		DESCRIPTION
		    "Controls what happens when a route goes down.
		    If set to no(2), the hub simply stops reporting the
		    route. If set to yes(1), the hub reports it one more
		    time, but with a metric value of 16, which infinity
		    as far as RIP is concerned. Thus other routers learn
		    immediately that the route is down."
		DEFVAL {0}
		::= { alripVLANConfigEntry 4 }

	    alripVLANConfigRptStaticRt OBJECT-TYPE
		SYNTAX  INTEGER { 
			    yes(1), 
			    no (2) 
			}
		ACCESS  read-write 
		STATUS  mandatory
		DESCRIPTION
		    "When RIP packets are generated on the port,
		    controls whether the hub reports the static routes
		    in its route table."
		DEFVAL {1}
		::= { alripVLANConfigEntry 5 }

	    alripVLANConfigRptDefaultRt OBJECT-TYPE
		SYNTAX  INTEGER { 
			    yes(1), 
			    no (2) 
			}
		ACCESS  read-write 
		STATUS  mandatory
		DESCRIPTION
		    "When RIP packets are generated on the port,
		    controls whether the hub reports the default routes,
		    if any, in ints route table."
		DEFVAL {1}
		::= { alripVLANConfigEntry 6 }

	    alripVLANConfigAccptDefaultRt OBJECT-TYPE
		SYNTAX  INTEGER { 
			    yes(1), 
			    no (2) 
			}
		ACCESS  read-write 
		STATUS  mandatory
		DESCRIPTION
		    "When RIP packets are received on the port,
		    controls whether the hub accepts(learns) a default"
		DEFVAL {1}
		::= { alripVLANConfigEntry 7 }

	    alripVLANConfigDelete OBJECT-TYPE
		SYNTAX  INTEGER 
		ACCESS  read-write
		STATUS  mandatory
		DESCRIPTION
		    "When set to 1, this entry is deleted."
		DEFVAL { 0 }
		::= { alripVLANConfigEntry 8 }

	--	1.4.3  
	--	. stats-clear

	    alripStatsClear OBJECT-TYPE
		SYNTAX  INTEGER
		ACCESS  read-write
		STATUS  mandatory
		DESCRIPTION
		    "When set to 1, clears the RIP stats"
		DEFVAL { 0 }
		::= { alrip 4 }
	
	--	. stats
	--	  There are two kinds of stats -- 
	--	  . static - The stats that the user cannot clear.
	--	  These are cleared only when the system
	--	  resets. Corresponds to the "-t" option
	--	  of the stats command.
	--	  . dynamic - The stats that the user can reset 
	--	  any time during when the system is up.

	--	  .static stats --

	    alRipStatPktsRcvd OBJECT-TYPE
		SYNTAX	  Counter
		ACCESS	  read-only
		STATUS	  mandatory
		DESCRIPTION
		    "Packets Received."
		::= { alrip 5 }

	    alRipStatPktsXmitted OBJECT-TYPE 
		SYNTAX    Counter
		ACCESS    read-only 
		STATUS    mandatory 
		DESCRIPTION 
		    "Packets Sent."
		::= { alrip 6 }

	    alRipStatReqsRcvd OBJECT-TYPE 
		SYNTAX    Counter
		ACCESS    read-only 
		STATUS    mandatory 
		DESCRIPTION 
		    "Requests Received."
		::= { alrip 7 }

	    alRipStatRespRcvd OBJECT-TYPE 
		SYNTAX    Counter
		ACCESS    read-only 
		STATUS    mandatory 
		DESCRIPTION 
		    "Responses Received."
		::= { alrip 8 }

	    alRipStatReqsXmitted OBJECT-TYPE 
		SYNTAX    Counter
		ACCESS    read-only 
		STATUS    mandatory 
		DESCRIPTION 
		    "Requests Sent."
		::= { alrip 9 }

	    alRipStatRespXmitted OBJECT-TYPE 
		SYNTAX    Counter
		ACCESS    read-only 
		STATUS    mandatory 
		DESCRIPTION 
		    "Responses Sent."
		::= { alrip 10 }

	    alRipStatRouteTimeOuts OBJECT-TYPE 
		SYNTAX    Counter
		ACCESS    read-only 
		STATUS    mandatory 
		DESCRIPTION 
		    "Route Timeouts."
		::= { alrip 11 }

	    alRipStatShortPkts OBJECT-TYPE 
		SYNTAX    Counter
		ACCESS    read-only 
		STATUS    mandatory 
		DESCRIPTION 
		    "Short packets received."
		::= { alrip 12 }

	    alRipStatBadVer OBJECT-TYPE 
		SYNTAX    Counter
		ACCESS    read-only 
		STATUS    mandatory 
		DESCRIPTION 
		    "Bad version pkts received."
		::= { alrip 13 }

	    alRipStatBadZeroes OBJECT-TYPE 
		SYNTAX    Counter
		ACCESS    read-only 
		STATUS    mandatory 
		DESCRIPTION 
		    "Bad zeroes received."
		::= { alrip 14 }

	    alRipStatBadSrcPort OBJECT-TYPE 
		SYNTAX    Counter
		ACCESS    read-only 
		STATUS    mandatory 
		DESCRIPTION 
		    "Packets with bad Source port received."
		::= { alrip 15 }

	    alRipStatBadSrcIp OBJECT-TYPE 
		SYNTAX    Counter
		ACCESS    read-only 
		STATUS    mandatory 
		DESCRIPTION 
		    "Packets with bad source IP address received."
		::= { alrip 16 }

	    alRipStatPktsSelf OBJECT-TYPE 
		SYNTAX    Counter
		ACCESS    read-only 
		STATUS    mandatory 
		DESCRIPTION 
		    "Packets from self received."
		::= { alrip 17 }

	    alRipigUpdates OBJECT-TYPE 
		SYNTAX    Counter
		ACCESS    read-only 
		STATUS    mandatory 
		DESCRIPTION 
		    "number of RIP update trigged."
		::= { alrip 18 }

	    alRipStatPqueuePktsQueued OBJECT-TYPE 
		SYNTAX    Counter
		ACCESS    read-only 
		STATUS    mandatory 
		DESCRIPTION 
		    "Packets queued in RIP process queue."
		::= { alrip 19 }

	    alRipStatPqueueFreeQueue OBJECT-TYPE 
		SYNTAX    Counter
		ACCESS    read-only 
		STATUS    mandatory 
		DESCRIPTION 
		    "Free entries in the RIP processing queue."
		  ::= { alrip 20 }

	    alRipStatTqueuePktsQueued OBJECT-TYPE 
		SYNTAX    Counter
		ACCESS    read-only 
		STATUS    mandatory 
		DESCRIPTION 
		    "Packets queued in the RIP route timeout process queue."
		::= { alrip 21 }

	    alRipStatTqueueFreeQueue OBJECT-TYPE 
		SYNTAX    Counter
		ACCESS    read-only 
		STATUS    mandatory 
		DESCRIPTION 
		    "Free entries in the RIP route timeout queue."
		::= { alrip 22 }

	--	. dynamic stats
	    alRipDynPktsRcvd OBJECT-TYPE
		SYNTAX    Counter
		ACCESS    read-only
		STATUS    mandatory
		DESCRIPTION
		    "Packets Received."
		::= { alrip 23 }

	    alRipDynPktsXmitted OBJECT-TYPE
		SYNTAX    Counter
		ACCESS    read-only
		STATUS    mandatory
		DESCRIPTION
		    "Packets Sent."
		::= { alrip 24 }

	    alRipDynReqsRcvd OBJECT-TYPE
		SYNTAX    Counter
		ACCESS    read-only
		STATUS    mandatory
		DESCRIPTION
		    "Requests Received."
		::= { alrip 25 }
 
	    alRipDynRespRcvd OBJECT-TYPE
		SYNTAX    Counter
		ACCESS    read-only
		STATUS    mandatory
		DESCRIPTION
		    "Responses Received."
		::= { alrip 26 }

	    alRipDynReqsXmitted OBJECT-TYPE
		SYNTAX    Counter
		ACCESS    read-only
		STATUS    mandatory
		DESCRIPTION
		    "Requests Sent."
		::= { alrip 27 }
 
	    alRipDynRespXmitted OBJECT-TYPE
		SYNTAX    Counter
		ACCESS    read-only
		STATUS    mandatory
		DESCRIPTION
		    "Responses Sent."
		::= { alrip 28 }
 
	    alRipDynRouteTimeOuts OBJECT-TYPE
		SYNTAX    Counter
		ACCESS    read-only
		STATUS    mandatory
		DESCRIPTION
		    "Route Timeouts."
		::= { alrip 29 }
 
	    alRipDynShortPkts OBJECT-TYPE
		SYNTAX    Counter
		ACCESS    read-only
		STATUS    mandatory
		DESCRIPTION
		    "Short packets received."
		::= { alrip 30 }

	    alRipDynBadVer OBJECT-TYPE
		SYNTAX    Counter
		ACCESS    read-only
		STATUS    mandatory
		DESCRIPTION
		    "Bad version pkts received."
		::= { alrip 31 }

	    alRipDynBadZeroes OBJECT-TYPE
		SYNTAX    Counter
		ACCESS    read-only
		STATUS    mandatory
		DESCRIPTION
		    "Bad zeroes received."
		::= { alrip 32 }

	    alRipDynBadSrcPort OBJECT-TYPE
		SYNTAX    Counter
		ACCESS    read-only
		STATUS    mandatory
		DESCRIPTION
		    "Packets with bad Source port received."
		::= { alrip 33 }
 
	    alRipDynBadSrcIp OBJECT-TYPE
		SYNTAX    Counter
		ACCESS    read-only
		STATUS    mandatory
		DESCRIPTION
		    "Packets with bad source IP address received."
		::= { alrip 34 }

	    alRipDynPktsSelf OBJECT-TYPE
		SYNTAX    Counter
		ACCESS    read-only
		STATUS    mandatory
		DESCRIPTION
		    "Packets from self received."
		::= { alrip 35 }

	    alRipDynNumTrigUpdates OBJECT-TYPE 
		SYNTAX    Counter
		ACCESS    read-only 
		STATUS    mandatory 
		DESCRIPTION 
		    "number of RIP update trigged."
		::= { alrip 36 }

	    alRipDyntPqueuePktsQueued OBJECT-TYPE 
		SYNTAX    Counter
		ACCESS    read-only 
		STATUS    mandatory 
		DESCRIPTION 
		    "Packets queued in RIP process queue."
		::= { alrip 37 }

	    alRipDynPqueueFreeQueue OBJECT-TYPE 
		SYNTAX    Counter
		ACCESS    read-only 
		STATUS    mandatory 
		DESCRIPTION 
		    "Free entries in the RIP processing queue."
		::= { alrip 38 }


	    alRipDynTqueuePktsQueued OBJECT-TYPE 
		SYNTAX    Counter
		ACCESS    read-only 
		STATUS    mandatory 
		DESCRIPTION 
		    "Packets queued in the RIP route timeout process queue."
		::= { alrip 39 }

	    alRipDynTqueueFreeQueue OBJECT-TYPE 
		SYNTAX    Counter
		ACCESS    read-only 
		STATUS    mandatory 
		DESCRIPTION 
		    "Free entries in the RIP route timeout queue."
		::= { alrip 40 }


	--	1.4.3
	--	. rip-accept-filter
	--	Modeled as a table with filter number as the index.

	    alRipAccptFilTable OBJECT-TYPE
		SYNTAX  SEQUENCE OF RipAccptFilEntry
		ACCESS  not-accessible
		STATUS  mandatory
		DESCRIPTION
		    "RIP Accept filter table" 
		::= { alrip 41 }

	    ripAccptFilEntry OBJECT-TYPE
	        SYNTAX  RipAccptFilEntry
	        ACCESS  not-accessible
		STATUS  mandatory
		DESCRIPTION
		    "RIP Accept filter entry "
		INDEX   { ripAccptFilNumber }
		::= { alRipAccptFilTable 1 }

	    RipAccptFilEntry ::= 
		SEQUENCE {
		    ripAccptFilNumber
			INTEGER(1..64),
        	    ripAccptFilAddr
            		IpAddress,
	            ripAccptFilMask
    		        IpAddress,
		    ripAccptFilPort
			INTEGER(1..14)
		}

	    ripAccptFilNumber OBJECT-TYPE
		SYNTAX  INTEGER(1..64)
		ACCESS  read-write
		STATUS  mandatory
		DESCRIPTION
		    "Filter Number; Range 1-64"
		::= { ripAccptFilEntry 1 }

	    ripAccptFilAddr OBJECT-TYPE 
		SYNTAX  IpAddress 
		ACCESS  read-write 
		STATUS  mandatory 
		DESCRIPTION 
		    "Valid network or subnet address" 
		::= { ripAccptFilEntry 2 }

	    ripAccptFilMask OBJECT-TYPE 
		SYNTAX  IpAddress 
		ACCESS  read-write 
		STATUS  mandatory 
		DESCRIPTION 
		    "Accept filter Mask" 
		::= { ripAccptFilEntry 3 }

	    ripAccptFilPort OBJECT-TYPE 
		SYNTAX  INTEGER(1..14) 
		ACCESS  read-write 
		STATUS  mandatory 
		DESCRIPTION 
		    "Port number on which network should be 
		    accepted or not. Range 1-14." 
		::= { ripAccptFilEntry 4 }

	--	1.4.4
	--	. rip-report-filter

	    alRipReportFilTable OBJECT-TYPE
		SYNTAX  SEQUENCE OF RipReportFilEntry
		ACCESS  not-accessible
		STATUS  mandatory
		DESCRIPTION
		    "RIP Report filter table"
		::= { alrip 42 }
 
	    ripReportFilEntry OBJECT-TYPE
		SYNTAX  RipReportFilEntry
		ACCESS  not-accessible
		STATUS  mandatory
		DESCRIPTION
		    "RIP Report filter entry "
		INDEX   { ripReportFilNumber }
		::= { alRipReportFilTable 1 }
 
	    RipReportFilEntry ::= 
	    	SEQUENCE {
		    ripReportFilNumber
			INTEGER(1..64),
        	    ripReportFilAddr
            		IpAddress,
	            ripReportFilMask
    		        IpAddress,
		    ripReportFilPort
			INTEGER(1..14)
	    	}

	    ripReportFilNumber OBJECT-TYPE
		SYNTAX  INTEGER (1..64)
		ACCESS  read-write
		STATUS  mandatory
		DESCRIPTION
		    "Filter Number; Range 1-64"
		::= { ripReportFilEntry 1 }
 
	    ripReportFilAddr OBJECT-TYPE
		SYNTAX  IpAddress
		ACCESS  read-write
		STATUS  mandatory
		DESCRIPTION
		    "Valid network or subnet address"
		::= { ripReportFilEntry 2 }
 
	    ripReportFilMask OBJECT-TYPE
		SYNTAX  IpAddress
		ACCESS  read-write
		STATUS  mandatory
		DESCRIPTION
		    "Report filter Mask"
		::= { ripReportFilEntry 3 }

	    ripReportFilPort OBJECT-TYPE
		SYNTAX  INTEGER(1..14)
		ACCESS  read-write
		STATUS  mandatory
		DESCRIPTION
		    "Port number on which network should be
		    reported or not. Port number range 1-14"
		::= { ripReportFilEntry 4 }


	-- 1.5	The "tcpstack" subsystem  --
	--   	1.5.1 
	--     	  1.5.1.1  showcfg and set

	--	PowerHub UI                  	MIB- II

	--	Round Trip Algorithm         	tcpRtoAlgorithm 
	--	Min Rexmit Interval          	tcpRtoMin
	--	Max Rexmit Interval		tcpRtoMax
	--	Max Connections Allowed		tcpMaxConn
		
	--	The following parameters in the showcfg and set commands
	--	do not map to any MIB-II variables.

	--	connection-idle-time
	--	keep-alive-interval
	--	Time to disconnect on idle conn

	    alTcpConnIdleTime OBJECT-TYPE
		SYNTAX	INTEGER
		ACCESS	read-write
		STATUS	mandatory
		DESCRIPTION
        	    "Time in minutes before sending keep-alives.
		    The range is 5 to 30 minutes."
		::= { altcp 1 }

	    alTcpKeepAliveInt OBJECT-TYPE
		SYNTAX	INTEGER
		ACCESS	read-write
		STATUS	mandatory
		DESCRIPTION
		    "Time interval in seconds between two 
		    successive keep-alive sends. The range is 30 to 240
		    seconds."
		::= { altcp 2 }

	    alTcpDisconnectInt OBJECT-TYPE  
		SYNTAX	INTEGER  
		ACCESS	read-only  
		STATUS	mandatory  
		DESCRIPTION  
		    "Time interval in seconds, before an idle
		    connection is dropped. This equals to the sum of
		    alTcpConnIdleTime plus eight times the 
		    alTcpKeepAliveInt interval."
		::= { altcp 3 }


	--	  1.5.1.2  stats

	--	PowerHub UI			MIB-II
	--	------------------------------------------------------

	--	Active Opens			tcpActiveOpens
	--	Passive Opens			tcpPassiveOpens
	--	Failed Conn Attempts		tcpAttemptFails
	--	Resets In Estb State		tcpEstabResets
	--	Current Open Conns		tcpCurrEstab
	--	Segments Received		tcpInSegs
	--	Segments Sent			tcpOutSegs
	--	Rexmitted segments		tcpRetransSegs
	--	Segments Rcvd With Err		tcpInErrs
	--	Resets Sent			tcpOutRsts

	--	The stat that the PH supports but which does not match
	--	any MIB-II variable is 

	--	Short Segments Rcvd --

	    alTcpShortSegRcvd OBJECT-TYPE
		SYNTAX	INTEGER
		ACCESS	read-only
		STATUS	mandatory
		DESCRIPTION
		    "Number of short segments received."
		::= { altcp 4 }

	--  1.5.1.3  stats-clear

	    alTcpStatsClear OBJECT-TYPE
		SYNTAX	INTEGER
		ACCESS	read-write
		STATUS	mandatory
		DESCRIPTION
		    "When set to 1, clears the TCP stats."
		::= { altcp 5 }

	-- 1.5.2

	--  1.5.2.1
	--	. tcp-table

	    alTcpConnTable OBJECT-TYPE
		SYNTAX SEQUENCE OF AlTcpConnEntry
		ACCESS	not-accessible
		STATUS	mandatory
		DESCRIPTION
		    "A table containing TCP connection-specific
                    information."
		::= { altcp 6 }

	    alTcpConnEntry OBJECT-TYPE
		SYNTAX  AlTcpConnEntry
 		ACCESS  not-accessible
           	STATUS  mandatory
              	DESCRIPTION
		    "Information about a particular current TCP
		    connection.  An object of this type is transient,
                    in that it ceases to exist when (or soon after)
                    the connection makes the transition to the CLOSED
                    state."
              	INDEX   { alTcpConnId }
              	::= { alTcpConnTable 1 }

	    AlTcpConnEntry ::=
			SEQUENCE {
		    	alTcpConnId
		      		INTEGER,
			    alTcpConnState
                   	INTEGER,
			    alTcpConnLocalAddress
					IpAddress,
			    alTcpConnLocalPort
                	INTEGER,
			    alTcpConnRemAddress
                   	IpAddress,
			    alTcpConnRemPort
                   	INTEGER 
            }

	    alTcpConnId	OBJECT-TYPE
		SYNTAX  INTEGER
		ACCESS  read-only
		STATUS  mandatory
		DESCRIPTION
		    "The connection Identifier by which a 
		    connection is addressed."
		::= { alTcpConnEntry 1 }

	    alTcpConnState OBJECT-TYPE
		SYNTAX  INTEGER {
			    closed(1),
			    listen(2),
 			    synSent(3),
			    synReceived(4),
			    established(5),
			    finWait1(6),
			    finWait2(7),
			    closeWait(8),
			    lastAck(9),
			    closing(10),
			    timeWait(11),
			    deleteTCB(12)
                 }
		ACCESS  read-write
             	STATUS  mandatory
              	DESCRIPTION
                    "The state of this TCP connection.
		    The only value which may be set by a management
		    station is deleteTCB(12).  Accordingly, it is
		    appropriate for an agent to return a `badValue'
		    response if a management station attempts to set
		    this object to any other value.
 
                    If a management station sets this object to the
                    value deleteTCB(12), then this has the effect of
                    deleting the TCB (as defined in RFC 793) of the
                    corresponding connection on the managed node,
                    resulting in immediate termination of the
                    connection."
		::= { alTcpConnEntry 2 }

	    alTcpConnLocalAddress OBJECT-TYPE
         	SYNTAX  IpAddress
              	ACCESS  read-only
              	STATUS  mandatory
              	DESCRIPTION
                   "The local IP address for this TCP connection. 
                   In the case of a connection in the listen state which
                   is willing to accept connections for any IP
                   interface associated with the node, the value
                   0.0.0.0 is used."
              	::= { alTcpConnEntry 3 }

	    alTcpConnLocalPort OBJECT-TYPE
		SYNTAX  INTEGER
              	ACCESS  read-only
              	STATUS  mandatory
              	DESCRIPTION
                    "The local port number for this TCP connection."
              	::= { alTcpConnEntry 4 }
 
	    alTcpConnRemAddress OBJECT-TYPE
             	SYNTAX  IpAddress
              	ACCESS  read-only
              	STATUS  mandatory
              	DESCRIPTION
                    "The remote IP address for this TCP connection."
              	::= { alTcpConnEntry 5 }

	    alTcpConnRemPort OBJECT-TYPE
              	SYNTAX  INTEGER
              	ACCESS  read-only
              	STATUS  mandatory
              	DESCRIPTION
                    "The remote port number for this TCP connection."
            	::= { alTcpConnEntry 6 }

	--  1.5.2.2
	--	. kill-connection

	--  This command will be executed by sending a deleteTCB(12)
	--  to the connection indexed by the alTcpConnId. This will
	--  delete the connection.

	--	1.5.3
	
	--	. tcp-filter ( to add/change/show the tcp-filter )

	    alTcpFilTable OBJECT-TYPE
		SYNTAX  SEQUENCE OF TcpFilEntry
		ACCESS  not-accessible
		STATUS  mandatory
		DESCRIPTION
		    "TCP filter table"
		::= { altcp 7 }

	    tcpFilEntry OBJECT-TYPE
		SYNTAX  TcpFilEntry
		ACCESS  not-accessible
		STATUS  mandatory
		DESCRIPTION
		    "TCP filter entry "
		INDEX   { tcpFilNumber }
		::= { alTcpFilTable 1 }
 
	    TcpFilEntry ::=
		SEQUENCE {
		    tcpFilNumber
			INTEGER,
		    tcpFilSrcAddr
			IpAddress,
		    tcpFilSrcMask
			IpAddress,
		    tcpFilProtocol
			INTEGER,
		    tcpFilDstPort
			INTEGER
		}

	    tcpFilNumber  OBJECT-TYPE
		SYNTAX  INTEGER
		ACCESS  read-write
		STATUS  mandatory
		DESCRIPTION
		    "Filter Number; Range 1-32"
		::= { tcpFilEntry 1 }

	    tcpFilSrcAddr OBJECT-TYPE
		SYNTAX  IpAddress
		ACCESS  read-write
		STATUS  mandatory
		DESCRIPTION
		    "Source address"
		::= { tcpFilEntry 2 }

	    tcpFilSrcMask OBJECT-TYPE
		SYNTAX  IpAddress
		ACCESS  read-write
		STATUS  mandatory
		DESCRIPTION
		    "Mask"
		::= { tcpFilEntry 3 }

	    tcpFilProtocol OBJECT-TYPE
		SYNTAX  INTEGER
		ACCESS  read-write
		STATUS  mandatory
		DESCRIPTION
		    "tcp(1) or udp(2)"
		::= { tcpFilEntry 4 }

	    tcpFilDstPort OBJECT-TYPE
		SYNTAX  INTEGER
		ACCESS  read-write
		STATUS  mandatory
		DESCRIPTION
		    "smtp(1000), telnet(2000),
		    ftp(3000) or valid port Number"
		::= { tcpFilEntry 5 }

	-- 1.5.4

	--	. set-ctrlchar-cur
	--	. show-ctrlchar-cur
	--	. set-ctrlchar-def
	--	. show-ctrlchar-def
		

	-- 1.6	   The "ip" subsystem --
	-- 1.6.1   The arp related commands --
	-- 1.6.1.1 add-arp/del-arp/arp-table --
	--		   Map to the ipNetToMediaTable of the IP group in the MIB-II.
	
	-- 1.6.1.4 arp-tableclear

	    alArpTableClear OBJECT-TYPE
		SYNTAX  INTEGER
		ACCESS  read-write
		STATUS  mandatory
		DESCRIPTION
		    "When set, clears the ARP table."
		::= { alip 1 }
	
	-- 1.6.1.5 set-arpage

	    alArpAge 	OBJECT-TYPE
		SYNTAX  INTEGER
		ACCESS  read-write
		STATUS  mandatory
		DESCRIPTION
		    "Timeout in minutes for aging ARP entries;
		    when set to zero, set-arpage is turned off."
	    ::= { alip 2 }

	-- 1.6.1.6 stats arp

	--	. static stats - equivalent to "stats arp -t"

	    alArpStatReqsRcvd OBJECT-TYPE
		SYNTAX    Counter
		ACCESS    read-only
		STATUS    mandatory
		DESCRIPTION
		    "Requests Received."
		::= { alip 3 }

	    alArpStatRepliesRcvd OBJECT-TYPE 
		SYNTAX    Counter
		ACCESS    read-only 
		STATUS    mandatory 
		DESCRIPTION 
		    "Replies Received."
		::= { alip 4 }

	    alArpStatInvalidOpcodes OBJECT-TYPE 
		SYNTAX    Counter
		ACCESS    read-only 
		STATUS    mandatory 
		DESCRIPTION 
		    "Invalid Opcodes Received."
		::= { alip 5 }

	    alArpStatRequestsSent OBJECT-TYPE 
		SYNTAX    Counter
		ACCESS    read-only 
		STATUS    mandatory 
		DESCRIPTION 
		    "Requests Sent."
		::= { alip 6 }

	    alArpStatRepliesSent OBJECT-TYPE 
		SYNTAX    Counter
		ACCESS    read-only 
		STATUS    mandatory 
		DESCRIPTION 
		    "Replies Sent."
		::= { alip 7 }

	    alArpStatProxyReplies OBJECT-TYPE 
		SYNTAX    Counter
		ACCESS    read-only 
		STATUS    mandatory 
		DESCRIPTION 
		    "number of proxy replied"
		::= { alip 8 }

--	. dynamic stats - equivalent to "stats arp"

	    alArpDynReqsRcvd OBJECT-TYPE
		SYNTAX    Counter
		ACCESS    read-only
		STATUS    mandatory
		DESCRIPTION
		    "Requests Received."
		::= { alip 9 }
 
	    alArpDynRepliesRcvd OBJECT-TYPE
		SYNTAX    Counter
		ACCESS    read-only
		STATUS    mandatory
		DESCRIPTION
		    "Replies Received."
		::= { alip 10 }

	    alArpDynInvalidOpcodes OBJECT-TYPE
		SYNTAX    Counter
		ACCESS    read-only
		STATUS    mandatory
		DESCRIPTION
		    "Invalid Opcodes Received."
		::= { alip 11 }    
 
	    alArpDynRequestsSent OBJECT-TYPE
		SYNTAX    Counter
		ACCESS    read-only
		STATUS    mandatory
		DESCRIPTION
		    "Requests Sent."
		::= { alip 12 }
 
	    alArpDynRepliesSent OBJECT-TYPE
		SYNTAX    Counter
		ACCESS    read-only
		STATUS    mandatory
		DESCRIPTION
		    "Replies Sent."
		::= { alip 13 }

	    alArpDynProxyReplies OBJECT-TYPE 
		SYNTAX    Counter
		ACCESS    read-only 
		STATUS    mandatory 
		DESCRIPTION 
		    "number of proxy replied"
		::= { alip 14 }

	    alArpStatsClear OBJECT-TYPE
		SYNTAX  INTEGER
		ACCESS  read-write
		STATUS  mandatory
		DESCRIPTION
		    "When set to 1, clears the ARP statistics."
		DEFVAL { 0 }
		::= { alip 15 }

	-- 1.6.1.7 proxy-arp

	    alArpProxyTable OBJECT-TYPE
		SYNTAX  SEQUENCE OF ArpProxyEntry
		ACCESS  not-accessible
		STATUS  mandatory
		DESCRIPTION
		    " Per port proxy arp enable/disable "
		::= { alip 16 }
 
	    arpProxyEntry OBJECT-TYPE
		SYNTAX  ArpProxyEntry
		ACCESS  not-accessible
		STATUS  mandatory
		DESCRIPTION
		    "information of a specific arp proxy entry "
		INDEX   { arpProxyPort }
		::= { alArpProxyTable 1 }
 
	    ArpProxyEntry ::=
		SEQUENCE {
		    arpProxyPort
			INTEGER,
		    arpProxyEnable
			INTEGER
		}

	    arpProxyPort OBJECT-TYPE
		SYNTAX  INTEGER
		ACCESS  read-only
		STATUS  mandatory
		DESCRIPTION
		    "Port Number "
		::= { arpProxyEntry 1 }
 
	    arpProxyEnable OBJECT-TYPE
		SYNTAX  INTEGER
		ACCESS  read-write
		STATUS  mandatory
		DESCRIPTION
		    "If set to Enable(1), enables proxy arp
		    arp requests received on the port identified by 
		    the instance of arpProxyPort. If set to Disable(2), it
		    disables the proxy arp for arp requests received on
		    the ports identified by the instance of arpProxyPort."
		DEFVAL { 2 }
		::= { arpProxyEntry 2 }

	-- 1.6.2	IP Filtering

	-- 1.6.2.1 IP Filter Templates --
	
	-- 	. ip-fil-template add
	-- 	. ip-fil-template chng
	-- 	. ip-fil-template del
	-- 	. ip-fil-template show

	-- 	This will be modeled as a table indexed by the template number.

	    alIpTemplateTable OBJECT-TYPE
		SYNTAX  SEQUENCE OF AlipTemplateEntry
		ACCESS  not-accessible
		STATUS  mandatory
		DESCRIPTION
		    " Per template information"
		::= { alip 17 }

	    alipTemplateEntry OBJECT-TYPE
		SYNTAX  AlipTemplateEntry
		ACCESS  not-accessible
		STATUS  mandatory
		DESCRIPTION
		    "Information about a filtering template "
		INDEX   { alipTemplateNumber }
		::= { alIpTemplateTable 1 }

	    AlipTemplateEntry ::= 
		SEQUENCE {
		    alipTemplateNumber
                        INTEGER,
		    alipTemplateDelete
			INTEGER,
                    alipTemplateAction
			INTEGER,
		    alipTemplateSrcAddr
			IpAddress,
                    alipTemplateSrcMask
                        IpAddress,
		    alipTemplateDstAddr
			IpAddress, 
                    alipTemplateDstMask
                        IpAddress,
		    alipTemplateProtocol
			INTEGER,
		    alipTemplateOperator
			INTEGER,
		    alipTemplateDstPort
			INTEGER
		}

	    alipTemplateNumber OBJECT-TYPE
		SYNTAX	INTEGER(1..256)
		ACCESS	read-write
		STATUS	mandatory
		DESCRIPTION	
		    "The number of the template with which it
		    is identified."
		::= { alipTemplateEntry 1 }
			
	    alipTemplateDelete OBJECT-TYPE
		SYNTAX  INTEGER 
		ACCESS  read-write
		STATUS  mandatory
		DESCRIPTION
		    "When set to 1, this entry is deleted."
		DEFVAL { 0 }
		::= { alipTemplateEntry 2 }

	    alipTemplateAction OBJECT-TYPE
		SYNTAX  INTEGER { 
			forward(1),
			block(2)
		}
		ACCESS  read-write
		STATUS  mandatory
		DESCRIPTION
		    "Whether the packet being filtered should 
		    be forwarded or blocked"
		::= { alipTemplateEntry 3 }

	    alipTemplateSrcAddr OBJECT-TYPE
		SYNTAX  IpAddress
		ACCESS  read-write
		STATUS  mandatory
		DESCRIPTION
		    "The portion of the packet's source address
		    specified by ipTemplateSrcMask is matched with 
		    this address."
		::= { alipTemplateEntry 4 }

	    alipTemplateSrcMask OBJECT-TYPE
		SYNTAX  IpAddress
		ACCESS  read-write
		STATUS  mandatory
		DESCRIPTION
		    "Source Mask. The portion specified by 
		    this mask is matched with source address."
		::= { alipTemplateEntry 5 }

	    alipTemplateDstAddr OBJECT-TYPE
		SYNTAX  IpAddress
		ACCESS  read-write
		STATUS  mandatory
		DESCRIPTION
		    "The portion of the packet's destination 
		    address specified by ipTemplateDstMask is matched 
		    with this address." 
		::= { alipTemplateEntry 6 }

	    alipTemplateDstMask OBJECT-TYPE
		SYNTAX  IpAddress
		ACCESS  read-write
		STATUS  mandatory
		DESCRIPTION
		    "Destination mask. The portion specified by
		    this mask is matched with destination address."
		::= { alipTemplateEntry 7 }

	    alipTemplateProtocol OBJECT-TYPE
		SYNTAX  INTEGER (0..255)
		ACCESS  read-write
		STATUS  mandatory
		DESCRIPTION
		    "Determines the type of packets that need 
		    to be filtered. PowerHub currently recognizes ip(1)
		    , icmp(1), ipinip(4), tcp(6), udp(17), ospf(89). If 
                    all(0) is specified, the filter looks for all 
		    protocols other than the ones PowerHub currently accepts. 
		    The IP protocol numbers are listed in RFC 1340"
		::= { alipTemplateEntry 8 }

	    alipTemplateOperator OBJECT-TYPE
		SYNTAX  INTEGER {
			unknown(1),
			equalto(2),
			notequalto(3),
			lessthan(4),
			greaterthan(5),
			conreq(6)
		}
		ACCESS  read-write
		STATUS  mandatory
		DESCRIPTION
		    "Allowed only if the protocol field is tcp
		    or udp. The following operators allowed:
		    (1)       Unknown
		    =(2)      Equal to
		    ~=(3)     Not equal to
		    <(4)      Less than
		    >(5)      Greater than
		    conreq(6) Connect request. Connect request is valid
		    only if protocol is tcp"
		::= { alipTemplateEntry 9 }

	    alipTemplateDstPort OBJECT-TYPE
		SYNTAX  INTEGER (0..65535)
		ACCESS  read-write 
		STATUS  mandatory
		DESCRIPTION
		    "This is expressed as either a well-known 
		    protocol name or a well-known tcp or udp port
		    number. 0 means unknown"
		::= { alipTemplateEntry 10 }


	-- 1.6.2.2	IP Filter Rules

	--	. ip-fil-rule add
	--	. ip-fil-rule del
	--	. ip-fil-rule chng
	--	. ip-fil-rule show

	    alIpRuleTable OBJECT-TYPE
		SYNTAX  SEQUENCE OF AlipRuleEntry
		ACCESS  not-accessible
		STATUS  mandatory
		DESCRIPTION
		    " Per template information"
		::= { alip 18 }

	    alipRuleEntry OBJECT-TYPE
		SYNTAX  AlipRuleEntry
		ACCESS  not-accessible
		STATUS  mandatory
		DESCRIPTION
		    "Information about a specific filtering rule"
		INDEX   { alipRuleNumber }
		::= { alIpRuleTable 1 }
 
	    AlipRuleEntry ::= 
		SEQUENCE {
		    alipRuleNumber
                        INTEGER,
		    alipRuleDelete
			INTEGER,
		    alipRuleTemplates
                        DisplayString
		}


	    alipRuleNumber OBJECT-TYPE
		SYNTAX  INTEGER (1..256)
		ACCESS  read-write
		STATUS  mandatory
		DESCRIPTION
		    "The number of the rule with which it is
		    Identified."
		::= { alipRuleEntry 1 }

	    alipRuleDelete OBJECT-TYPE
		SYNTAX  INTEGER 
		ACCESS  read-write
		STATUS  mandatory
		DESCRIPTION
		    "If set to 1 the entry is deleted."
		DEFVAL { 0 }
		::= { alipRuleEntry 2 }

	    alipRuleTemplates OBJECT-TYPE
		SYNTAX  DisplayString
		ACCESS  read-write
		STATUS  mandatory
		DESCRIPTION
		    "The templates associated with the rule
		    identified by the instance of ipRuleNumber." 
		::= { alipRuleEntry 3 }

	-- 1.6.2.3	IP Filter Access Control 

	--	. ip-fil-acs-ctrl add
	--	. ip-fil-acs-ctrl del
	--	. ip-fil-acs-ctrl show

	    alipAcsCtrlTable OBJECT-TYPE
		SYNTAX  SEQUENCE OF AlipAcsCtrlEntry
		ACCESS  not-accessible
		STATUS  mandatory
		DESCRIPTION
		    "Per port IP access control filters "
		::= { alip 19 }
 
	    alipAcsCtrlEntry OBJECT-TYPE
		SYNTAX  AlipAcsCtrlEntry
		ACCESS  not-accessible
		STATUS  mandatory
		DESCRIPTION
		    " information of a specific rule applied to segment"
		INDEX   { alipAcsCtrlPort }
		::= { alipAcsCtrlTable 1 }
 
	    AlipAcsCtrlEntry ::= 
		SEQUENCE {
		    alipAcsCtrlPort
			INTEGER,
		    alipAcsCtrlDelete
			INTEGER,
		    alipAcsCtrlTarget
			INTEGER,
		    alipAcsCtrlRuleNumber
			INTEGER
                }

	    alipAcsCtrlPort   OBJECT-TYPE
		SYNTAX  INTEGER
		ACCESS  read-write
		STATUS  mandatory
		DESCRIPTION
		    "Port number of the port for which the
		    source and destination access filter apply. "
		::= { alipAcsCtrlEntry 1 }

	    alipAcsCtrlDelete   OBJECT-TYPE
		SYNTAX  INTEGER 
		ACCESS  read-write
		STATUS  mandatory
		DESCRIPTION
		    "If set to 1, the entry is deleted."
		DEFVAL { 0 }
		::= { alipAcsCtrlEntry 2 }

	    alipAcsCtrlSourceRule OBJECT-TYPE
		SYNTAX  INTEGER 
		ACCESS  read-write
		STATUS  mandatory
		DESCRIPTION
		    "the source rule is assigned to the segment"
		::= { alipAcsCtrlEntry 3 }

	    alipAcsCtrlDestRule OBJECT-TYPE
		SYNTAX  INTEGER
		ACCESS  read-write                   
		STATUS  mandatory
		DESCRIPTION                         
		    "the destination rule is assigned to the segment"
		::= { alipAcsCtrlEntry 4 }

	-- 1.6.2.4	IP Filter Statistics
	
	--	. ip-fil-stats	show [-t]

	    alipFilStatStatsTable OBJECT-TYPE
		SYNTAX  SEQUENCE OF AlipFilStatStatsEntry
		ACCESS  not-accessible
		STATUS  mandatory
		DESCRIPTION
		    " Per template static statistics -- stats
		    from the beginning of the last system reboot."
		::= { alip 20 }
 
	    alipFilStatStatsEntry OBJECT-TYPE
		SYNTAX  AlipFilStatStatsEntry
		ACCESS  not-accessible
		STATUS  mandatory
		DESCRIPTION
		    "filter statistics entry "
		INDEX   { alipFilStatStatsTemplate }
		::= { alipFilStatStatsTable 1 }
 
	   AlipFilStatStatsEntry ::= 
		SEQUENCE {
		    alipFilStatStatsTemplate
			Counter,
		    alipFilStatStatsInPkts
			Counter,
		    alipFilStatStatsOutPkts
			Counter
		}

	   alipFilStatStatsTemplate OBJECT-TYPE
		SYNTAX	Counter
		ACCESS	read-only
		STATUS	mandatory
		DESCRIPTION
		    "The template number for which 
		    the stats are displayed"
		::= { alipFilStatStatsEntry 1 }

	    alipFilStatStatsInPkts  OBJECT-TYPE
		SYNTAX  Counter
		ACCESS  read-only
		STATUS  mandatory
		DESCRIPTION
		    "The number of packets that matched 
		    the template identified by the instance of
		    alipFilStatStatsTemplate. The template has to 
		    be a Source template."
		::= { alipFilStatStatsEntry 2 }

	    alipFilStatStatsOutPkts  OBJECT-TYPE
		SYNTAX  Counter
		ACCESS  read-only
		STATUS  mandatory
		DESCRIPTION
		    "The number of packets that matched
		    the template identified by the instance of
		    alipFilStatStatsTemplate. The template has to
		    be a Destination template."
		::= { alipFilStatStatsEntry 3 }

	--	. dynamic stats - stats from the last clear
	--	. ip-fil-stats	clear

	    alipFilDynStatsTable OBJECT-TYPE
		SYNTAX  SEQUENCE OF AlipFilDynStatsEntry
		ACCESS  not-accessible
		STATUS  mandatory
		DESCRIPTION
		    " Per template dynamic statistics -- stats
		    from the beginning of the last clear." 
		::= { alip 21 }

	    alipFilDynStatsEntry OBJECT-TYPE
		SYNTAX  AlipFilDynStatsEntry
		ACCESS  not-accessible
		STATUS  mandatory
		DESCRIPTION
		    "information of a specific statistic entry"
                INDEX   { alipFilDynStatsTemplate }
		::= { alipFilDynStatsTable 1 }

	    AlipFilDynStatsEntry ::= 
		SEQUENCE {
		    alipFilDynStatsTemplate
			Counter,
		    alipFilDynStatsInPkts
			Counter,
		    alipFilDynStatsOutPkts
			Counter,
		    alipFilDynStatsClear
			Counter
		}

	    alipFilDynStatsTemplate  OBJECT-TYPE
		SYNTAX  Counter
		ACCESS  read-only
		STATUS  mandatory
		DESCRIPTION
		    "The template number for which
		    the stats are displayed"
		::= { alipFilDynStatsEntry 1 }
 
	    alipFilDynStatsInPkts  OBJECT-TYPE
		SYNTAX  Counter
		ACCESS  read-only
		STATUS  mandatory
		DESCRIPTION
		    "The number of packets that matched
		    the template identified by the instance of
		    alipFilDynStatsTemplate. The template has to
		    be a Source template."
		::= { alipFilDynStatsEntry 2 }

	    alipFilDynStatsOutPkts  OBJECT-TYPE
		SYNTAX  Counter
		ACCESS  read-only
		STATUS  mandatory
		DESCRIPTION
		    "The number of packets that matched
		    the template identified by the instance of
		    alipFilDynStatsTemplate. The template has to
		    be a Destination template."
		::= { alipFilDynStatsEntry 3 }

	    alipFilDynStatsClear  OBJECT-TYPE
		SYNTAX  INTEGER 
		ACCESS  write-only
		STATUS  mandatory
		DESCRIPTION
		    "Setting the value of 1, it will 
		    clear all the stats for the template
		    identified by the instance of 
		    alipFilDynStatsTemplate."
		::= { alipFilDynStatsEntry 4 }


	    alipTotalFilPacketForward OBJECT-TYPE
		SYNTAX  Counter
		ACCESS  read-only
		STATUS  mandatory
		DESCRIPTION
		    "The total number of packets forwarded since last
		    system reset."
		::= { alip 22 }

	    alipTotalFilPacketBlock OBJECT-TYPE
		SYNTAX  Counter
		ACCESS  read-only
		STATUS  mandatory
		DESCRIPTION
		    "The total number of packets blocked since last
		    system reset."
		::= { alip 23 }

	    alipCurrentFilPacketForward OBJECT-TYPE
		SYNTAX  Counter
		ACCESS  read-only
		STATUS  mandatory
		DESCRIPTION
		    "The total number of packets forwarded since
		    the last statistical clear."
		::= { alip 24 }

	    alipCurrentFilPacketBlock OBJECT-TYPE
		SYNTAX  Counter
		ACCESS  read-only
		STATUS  mandatory
		DESCRIPTION
		    "The total number of packets blocked since
		    the last statistical clear."
		::= { alip 25 }

	-- 1.6.3	IP port Configuration

	-- 	. add-interface
	--	. del-interface
	--	. interface-table

	    alIpInterfaceTable OBJECT-TYPE
		SYNTAX SEQUENCE OF AlIpInterfaceEntry
		ACCESS not-accessible
		STATUS  mandatory
           	DESCRIPTION
		    "IP interface table corresponding to the command
		    - interface-table."
		::= { alip 26 }
 
 	    alIpInterfaceEntry OBJECT-TYPE
   		SYNTAX  AlIpInterfaceEntry
            	ACCESS  not-accessible
              	STATUS  mandatory
              	DESCRIPTION
		    "Entry of IP interface"
           	INDEX   { ipInterfaceNumber, ipInterfaceAddress }
              	::= { alIpInterfaceTable 1 }

	    AlIpInterfaceEntry ::=
		SEQUENCE {
		    ipInterfaceNumber
			INTEGER,
		    ipInterfaceAddress
			IpAddress,
		    ipInterfaceSubnetMask
			IpAddress,
		    ipInterfaceBroadCast
			INTEGER,
		    ipInterfaceCost
			INTEGER (0..14),
		    ipInterfaceDelete
			INTEGER,
		    ipInterfaceMtu
			INTEGER,
		    ipInterfaceState
			INTEGER,
		    ipInterfacePktsIn
			Counter,
		    ipInterfaceOctetsIn
			Counter,
		    ipInterfacePktsOut
			Counter,
		    ipInterfaceOctetsOut
			Counter
		}
 
	    ipInterfaceNumber OBJECT-TYPE
		SYNTAX  INTEGER
              	ACCESS  read-write
              	STATUS  mandatory
              	DESCRIPTION
		    "Segment number of the selecetd IP address interface
		    entry."
              	::= { alIpInterfaceEntry 1 }

	    ipInterfaceAddress OBJECT-TYPE
		SYNTAX  IpAddress
		ACCESS  read-write
		STATUS  mandatory
		DESCRIPTION
		    "IP address of the selected IP segment number."
		::= { alIpInterfaceEntry 2 }

	    ipInterfaceSubnetMask OBJECT-TYPE
		SYNTAX  IpAddress
		ACCESS  read-write
		STATUS  mandatory
		DESCRIPTION
		    "IP subnet mask for the selected IP address."
		::= { alIpInterfaceEntry 3 }

	    ipInterfaceBroadCast OBJECT-TYPE
		SYNTAX  INTEGER {
			    br0 (1),
			    br1 (2)
			}
		ACCESS  read-write
		STATUS  mandatory
		DESCRIPTION
		    "Specifies style of broadcast address on a segment
		    basis: when you specify 'br0', the hub sends an
		    'all-0s' broadcast; when you sepcify 'br1', the hub 
		    sends 'all-1s' broadcast. The default is 'br1'."
		DEFVAL { br1 }
		::= { alIpInterfaceEntry 4 }

	    ipInterfaceCost OBJECT-TYPE
		SYNTAX  INTEGER (0..14)
		ACCESS  read-write
		STATUS  mandatory
		DESCRIPTION
		    "Specifies an additiopnal cost of using the subnet
		    interface. This cost is the number of extra hops to
		    the destination. The range is 1 thru 14. The default
		    is 0. When you set the cost to a value greater than
		    zero, routing is forced thru the other hub if it is
		    alive."
		DEFVAL { 0 }
		::= { alIpInterfaceEntry 5 }

	    ipInterfaceDelete OBJECT-TYPE
		SYNTAX  INTEGER
		ACCESS  read-write
		STATUS  mandatory
		DESCRIPTION
		    "When this object is set with value 1, the IP 
		    interface corresponds to the segment number will
		    be deleted; otherwise this object returns value 0."
		::= { alIpInterfaceEntry 6 }

	    ipInterfaceMtu OBJECT-TYPE
		SYNTAX  INTEGER
		ACCESS  read-only
		STATUS  mandatory
		DESCRIPTION
		    "Displays the maximum transimission unit size allowed
		    on this IP interface."
		::= { alIpInterfaceEntry 7 }

	    ipInterfaceState OBJECT-TYPE
		SYNTAX  INTEGER {
				up(1),
				down(2)
			}
		ACCESS  read-only
		STATUS  mandatory
		DESCRIPTION
		    "Displays the up/down status of the IP interface."
		::= { alIpInterfaceEntry 8 }

	    ipInterfacePktsIn OBJECT-TYPE
		SYNTAX  Counter
		ACCESS  read-only
		STATUS  mandatory
		DESCRIPTION
		    "Total number of packets received on this interface."
		::= { alIpInterfaceEntry 9 }

	    ipInterfaceOctetsIn OBJECT-TYPE
		SYNTAX  Counter
		ACCESS  read-only
		STATUS  mandatory
		DESCRIPTION
		    "Total number of bytes received on this interface."
		::= { alIpInterfaceEntry 10 }

	    ipInterfacePktsOut OBJECT-TYPE
		SYNTAX  Counter
		ACCESS  read-only
		STATUS  mandatory
		DESCRIPTION
		    "Total number of packets transmitted to the network
		    by this interface."
		::= { alIpInterfaceEntry 11 }

	    ipInterfaceOctetsOut OBJECT-TYPE
		SYNTAX  Counter
		ACCESS  read-only
		STATUS  mandatory
		DESCRIPTION
		    "Total number of bytes transimitted to the network
		    by this interface."
		::= { alIpInterfaceEntry 12 }


	-- 1.6.4	Route Cache Commands
	
	-- 	. display-routecache
	--	. flush-routecache

	    alIpRtCacheTable OBJECT-TYPE
		SYNTAX  SEQUENCE OF AlIpRtCacheEntry
		ACCESS  not-accessible
		STATUS  mandatory
		DESCRIPTION
		    "IP Route Cache for all ports"
		::= { alip 27 }

	    alIpRtCacheEntry OBJECT-TYPE
		SYNTAX  AlIpRtCacheEntry
		ACCESS  not-accessible
		STATUS  mandatory
		DESCRIPTION
                    "IP Route cache for each port "
		INDEX   { ipRtCachePort, ipRtCacheDstAddress }
		::= { alIpRtCacheTable 1 }

	    AlIpRtCacheEntry ::=
		SEQUENCE {
		    ipRtCachePort
			INTEGER,
		    ipRtCacheDstAddress
			IpAddress,
		    ipRtCacheClear
			INTEGER
		}

	    ipRtCachePort OBJECT-TYPE
		SYNTAX  INTEGER
		ACCESS  read-write
		STATUS  mandatory
		DESCRIPTION
		    "Port number for the ip route cache."
		::= { alIpRtCacheEntry 1 }

	    ipRtCacheDstAddress OBJECT-TYPE
		SYNTAX  INTEGER
		ACCESS  read-write
		STATUS  mandatory
		DESCRIPTION
		    "Ip route cache destination address."
		::= { alIpRtCacheEntry 2 }

	    ipRtCacheClear OBJECT-TYPE
		SYNTAX  INTEGER
		ACCESS  write-only
		STATUS  mandatory
		DESCRIPTION
                    "Setting this to Clear(1), will clear the
		    routecache for the port and Destination address
		    identified by the instance of ipRtCachePort and
		    ipRtCacheDstAddress."
		::= { alIpRtCacheEntry 3 }

            alVlanIpInterfaceTable OBJECT-TYPE
                SYNTAX SEQUENCE OF AlVlanIpInterfaceEntry
                ACCESS not-accessible
                STATUS  mandatory
                DESCRIPTION
                    "Vlan IP interface table corresponding to the command
                    - vlan add/del IP interface."
                ::= { alip 28 }

            alVlanIpInterfaceEntry OBJECT-TYPE
                SYNTAX  AlVlanIpInterfaceEntry
                ACCESS  not-accessible
                STATUS  mandatory
                DESCRIPTION
                    "Entry of Vlan IP interface"
                INDEX {vlanIpInterfaceNameLen, vlanIpInterfaceName, vlanIpInterfaceAddress}
                ::= { alVlanIpInterfaceTable 1 }

            AlVlanIpInterfaceEntry ::=
                SEQUENCE {
                    vlanIpInterfaceNameLen
                        INTEGER,
                    vlanIpInterfaceName
                        DisplayString,
                    vlanIpInterfaceAddress
                        IpAddress,
                    vlanIpInterfaceSubnetMask
                        IpAddress,
                    vlanIpInterfaceType
                        INTEGER,
                    vlanIpInterfaceNeighborAddress
                        IpAddress,
                    vlanIpInterfaceRowStatus
                        INTEGER
                }

            vlanIpInterfaceNameLen OBJECT-TYPE
                SYNTAX  INTEGER
                ACCESS  read-only
                STATUS  mandatory
                DESCRIPTION
                    "The string length of Vlan name of the 
                     selecetd vlan IP interface entry."
                ::= { alVlanIpInterfaceEntry 1 }
 
            vlanIpInterfaceName OBJECT-TYPE
                SYNTAX  DisplayString
                ACCESS  read-only
                STATUS  mandatory
                DESCRIPTION
                    "Vlan name of the selecetd vlan IP interface entry."
                ::= { alVlanIpInterfaceEntry 2 }
 
            vlanIpInterfaceAddress OBJECT-TYPE
                SYNTAX  IpAddress
                ACCESS  read-only
                STATUS  mandatory
                DESCRIPTION
                    "IP address of the selected vlan IP interface entry."
                ::= { alVlanIpInterfaceEntry 3 }
 
            vlanIpInterfaceSubnetMask OBJECT-TYPE
                SYNTAX  IpAddress
                ACCESS  read-write
                STATUS  mandatory
                DESCRIPTION
                    "IP subnet mask for the selected vlan IP
		     interface entry."
                ::= { alVlanIpInterfaceEntry 4 }
 
            vlanIpInterfaceType OBJECT-TYPE
                SYNTAX  INTEGER {
                            broadcast(1),
                            nbma(2),
                            pointToPoint(4)
                        }
                ACCESS  read-write
                STATUS  mandatory
                DESCRIPTION
                    "Specifies type of interface of vlan The types
		     are are broadcast, nbma (nonBroadcastMultiAccess
		     i.e.,CLIP), ptop (i.e.,PVC). Default is broadcast.
		     The discontinuos enumeration values actually mean
		     bitmask value which maps to bit positions in the
		     agent."
		DEFVAL {1}
                ::= { alVlanIpInterfaceEntry 5 }
 
            vlanIpInterfaceNeighborAddress OBJECT-TYPE
                SYNTAX  IpAddress 
                ACCESS  read-write
                STATUS  mandatory
                DESCRIPTION
                    "Specifies the ip address of neightbors of the
		     interfaces of the vlan. This object apply only
		     when interface type is pointToPoint."
                ::= { alVlanIpInterfaceEntry 6 }
 
            vlanIpInterfaceRowStatus OBJECT-TYPE
                SYNTAX	INTEGER {
                         active(1),
                         notInservice(2),
                         notReady(3),
                         createAndGo(4),
                         createAndWait(5),
                         destroy(6)
		    	}
                ACCESS  read-write
                STATUS  mandatory
                DESCRIPTION
                    "The status of the table. The table can not be changed
                     when it is active."
                ::= { alVlanIpInterfaceEntry 7 }

END
