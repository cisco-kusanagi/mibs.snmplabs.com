-- extracted from draft-aldri-disman-replication-mib-01.txt
-- at Thu Jun 20 06:09:37 2002

   REPLIC-MIB DEFINITIONS ::= BEGIN

   IMPORTS
       MODULE-IDENTITY, OBJECT-TYPE,
       Unsigned32, enterprises
           FROM SNMPv2-SMI

       RowStatus, TimeStamp
           FROM SNMPv2-TC

       MODULE-COMPLIANCE, OBJECT-GROUP
        FROM SNMPv2-CONF

       InetAddressType, InetAddress
           FROM INET-ADDRESS-MIB

       SnmpAdminString
        FROM SNMP-FRAMEWORK-MIB;

   replicMIB MODULE-IDENTITY
       LAST-UPDATED "200111010000Z"
       ORGANIZATION "Federal University of Parana' - Dept. Informatics"
       CONTACT-INFO
           "Aldri L. Santos
            Elias P. Duarte Jr.
            Federal University of Parana'
            Dept. Informatics
            P.O. Box 19018
            Curitiba, PR 81531-990
            Brazil
            Phone: +55-41-267-5244
            Email: {aldri, elias}@inf.ufpr.br

            Glenn Mansfield
            Cyber Solutions Inc.
            ICR Bldg. 3F 6-6-3 Minami Yoshinari
            Aoba-ku Sendai-shi Miyagi
            Japan
            Phone: +81-22-303-4012
            Email: cyber@cysol.co.jp"

       DESCRIPTION
         " This MIB module defines a set of objects that supports object
           replication in a three-layer clustering architecture."

       ::= { xxx   yyy }               -- to be assigned by IANA

   --
   --  The groups defined within this MIB definition:
   --

   replicObjects       OBJECT IDENTIFIER ::= { replicMIB 1 }
   replicConformance   OBJECT IDENTIFIER ::= { replicMIB 2 }

   clusterDefinition   OBJECT IDENTIFIER ::= { replicObjects 1 }
   clusterReplication  OBJECT IDENTIFIER ::= { replicObjects 2 }

   clusterTable OBJECT-TYPE
       SYNTAX     SEQUENCE OF ClusterEntry
       MAX-ACCESS not-accessible
       STATUS     current
       DESCRIPTION
         " This table allows the definition of agent clusters, which
           are used to monitor and replicate objects from other agents,
           providing alternative means of accessing information from
           those agents when they are unreachable."
       ::= { clusterDefinition 1 }

   clusterEntry OBJECT-TYPE
       SYNTAX     ClusterEntry
       MAX-ACCESS not-accessible
       STATUS     current
       DESCRIPTION
         " Each entry contains the definition of an agent cluster, its
           members and replicated objects."
       INDEX { clusterID, clusterIndex }
       ::= { clusterTable 1 }

   ClusterEntry ::= SEQUENCE {
       clusterIndex           Unsigned32,
       clusterID              Unsigned32,
       clusterAddressType     InetAddressType,
       clusterAddress         InetAddress,
       clusterMemberType      InetAddressType,
       clusterMember          InetAddress,
       clusterOID             OBJECT IDENTIFIER,
       clusterInstanceIndex   OBJECT IDENTIFIER,
       clusterRepClusterID    Unsigned32,
       clusterName            SnmpAdminString,
       clusterDescr           SnmpAdminString,
       clusterStatus          RowStatus
   }

   clusterIndex OBJECT-TYPE
       SYNTAX     Unsigned32
       MAX-ACCESS read-only
       STATUS     current
       DESCRIPTION
         " Unique value which identifies a cluster table entry."
       ::= { clusterEntry 1 }

   clusterID OBJECT-TYPE
       SYNTAX     Unsigned32
       MAX-ACCESS read-only
       STATUS     current
       DESCRIPTION
         " The unique identifier of a cluster that is defined for
           monitoring a subset of agents and replicating some of
           their objects."
       ::= { clusterEntry 2 }

   clusterAddressType OBJECT-TYPE
       SYNTAX     InetAddressType
       MAX-ACCESS read-only
       STATUS     current
       DESCRIPTION
         " The type of address in clusterAddress."
       ::= { clusterEntry 3 }

   clusterAddress OBJECT-TYPE
       SYNTAX     InetAddress
       MAX-ACCESS read-only
       STATUS     current
       DESCRIPTION
         " The IP address of a agent that monitors a set of agents and
           replicates their objects on its peer clusters."
       ::= { clusterEntry 4 }

   clusterMemberType OBJECT-TYPE
       SYNTAX     InetAddressType
       MAX-ACCESS read-only
       STATUS     current
       DESCRIPTION
         " The type of address in clusterMember."
       ::= { clusterEntry 5 }

   clusterMember OBJECT-TYPE
       SYNTAX     InetAddress
       MAX-ACCESS read-only
       STATUS     current
       DESCRIPTION
         " The IP address of an agent which has its objects monitored
           and replicated by the cluster."
       ::= { clusterEntry 6 }

   clusterOID OBJECT-TYPE
       SYNTAX     OBJECT IDENTIFIER
       MAX-ACCESS read-only
       STATUS     current
       DESCRIPTION
         " The instance identifier of a replicated managed object.
           For example:  ifInOctets "
       ::= { clusterEntry 7 }

   clusterInstanceIndex OBJECT-TYPE
       SYNTAX     OBJECT IDENTIFIER
       MAX-ACCESS read-only
       STATUS     current
       DESCRIPTION
         " Unique identifier of an instance index of a replicated
           managed object."
       ::= { clusterEntry 8 }

   clusterRepClusterID OBJECT-TYPE
       SYNTAX     Unsigned32
       MAX-ACCESS read-only
       STATUS     current
       DESCRIPTION
         " Identifier of a peer cluster which keeps replica of managed
           objects kept by the current cluster."
       ::= { clusterEntry 9 }

   clusterName OBJECT-TYPE
       SYNTAX     SnmpAdminString
       MAX-ACCESS read-only
       STATUS     current
       DESCRIPTION
         " The human manager responsible for the cluster."
       ::= { clusterEntry 10 }

   clusterDescr OBJECT-TYPE
       SYNTAX     SnmpAdminString
       MAX-ACCESS read-only
       STATUS     current
       DESCRIPTION
         " Description of the purpose of the cluster."
       ::= { clusterEntry 11 }

   clusterStatus OBJECT-TYPE
       SYNTAX     RowStatus
       MAX-ACCESS read-create
       STATUS     current
       DESCRIPTION
         " The status of this cluster entry.

           To create a row in this table, a manager must set this
           object to either createAndGo(4) or createAndWait(5).

           This object may not be active(1) until instances of all
           other objects are appropriately configured. Its value,
           meanwhile, is notReady(2)."
       ::= { clusterEntry 12 }

   memberTable OBJECT-TYPE
       SYNTAX     SEQUENCE OF MemberEntry
       MAX-ACCESS not-accessible
       STATUS     current
       DESCRIPTION
         " This table contains information that defines the set of
           agents monitored by the cluster."
        ::={ clusterDefinition 2 }

   memberEntry OBJECT-TYPE
       SYNTAX     MemberEntry
       MAX-ACCESS not-accessible
       STATUS     current
       DESCRIPTION
         " Each entry contains the definition of a cluster member."
       INDEX { cmIndex }
       ::= { memberTable 1 }

   MemberEntry ::= SEQUENCE {
       cmIndex         Unsigned32,
       cmAddressType   InetAddressType,
       cmAddress       InetAddress,
       cmSecurity      SnmpAdminString,
       cmStatus        RowStatus
   }

   cmIndex OBJECT-TYPE
       SYNTAX     Unsigned32
       MAX-ACCESS read-only
       STATUS     current
       DESCRIPTION
         " Unique identifier of a cluster member table entry."
       ::= { memberEntry 1 }

   cmAddressType OBJECT-TYPE
       SYNTAX     InetAddressType
       MAX-ACCESS read-only
       STATUS     current
       DESCRIPTION
         " The type of address in cmAddress."
       ::= { memberEntry 2 }

   cmAddress OBJECT-TYPE
       SYNTAX     InetAddress
       MAX-ACCESS read-only
       STATUS     current
       DESCRIPTION
         " The IP address of a cluster member whose objects are
           monitored and replicated by the cluster."
       ::= { memberEntry 3 }

   cmSecurity OBJECT-TYPE
       SYNTAX     SnmpAdminString
       MAX-ACCESS read-only
       STATUS     current
       DESCRIPTION
         " The security required to access cluster member objects."
       ::= { memberEntry 4 }

   cmStatus OBJECT-TYPE
       SYNTAX     RowStatus
       MAX-ACCESS read-create
       STATUS     current
       DESCRIPTION
         " The status of this cluster member entry.

           To create a row in this table, a manager must set this
           object to either createAndGo(4) or createAndWait(5).

           This object may not be active(1) until instances of all
           other objects are appropriately configured. Its value,
           meanwhile, is notReady(2)."
       ::= { memberEntry 5 }

   repObjectTable OBJECT-TYPE
       SYNTAX     SEQUENCE OF RepObjectEntry
       MAX-ACCESS not-accessible
       STATUS     current
       DESCRIPTION
         " This table allows the definition of a set of managed objects
           which are monitored and replicated by the cluster."
       ::={ clusterDefinition 3 }

   repObjectEntry OBJECT-TYPE
       SYNTAX     RepObjectEntry
       MAX-ACCESS not-accessible
       STATUS     current
       DESCRIPTION
         " An entry keeping information about an object that is replicated."
       INDEX { roIndex }
       ::= { repObjectTable 1 }

   RepObjectEntry ::= SEQUENCE {
       roIndex            Unsigned32,
       roOID              OBJECT IDENTIFIER,
       roInstanceIndex    OBJECT IDENTIFIER,
       roInterval         Unsigned32,
       roState            Unsigned32,
       roStatus           RowStatus
   }

   roIndex OBJECT-TYPE
       SYNTAX     Unsigned32
       MAX-ACCESS read-only
       STATUS     current
       DESCRIPTION
         " Unique identifier of a replicated object table entry."
       ::= { repObjectEntry 1 }

   roOID OBJECT-TYPE
       SYNTAX     OBJECT IDENTIFIER
       MAX-ACCESS read-only
       STATUS     current
       DESCRIPTION
         " The instance identifier of an object which is replicated
           by the cluster."
       ::= { repObjectEntry 2 }

   roInstanceIndex OBJECT-TYPE
       SYNTAX     OBJECT IDENTIFIER
       MAX-ACCESS read-only
       STATUS     current
       DESCRIPTION
         " Unique identifier of an instance index of an object
           which is replicated by the cluster."
       ::= { repObjectEntry 3 }

   roInterval OBJECT-TYPE
       SYNTAX      Unsigned32
       MAX-ACCESS  read-only
       STATUS      current
       DESCRIPTION
         " The time interval in which a cluster polls replicated
           objects in cluster members."
       ::= { repObjectEntry 4 }

   roState OBJECT-TYPE
       SYNTAX     Unsigned32(0|1) -- { non-active(0), active(1)}
       MAX-ACCESS read-only
       STATUS     current
       DESCRIPTION
         " The State object determines whether an object is replicated
           in a given cluster.
           Setting this value to non-active(0) requests that an object
           should not be replicated.
           Setting this value to active(1) requests that an object
           should be replicated."
       ::= { repObjectEntry 5 }

   roStatus OBJECT-TYPE
       SYNTAX     RowStatus
       MAX-ACCESS read-create
       STATUS     current
       DESCRIPTION
         " The status of this replicated object entry.

           To create a row in this table, a manager must set this
           object to either createAndGo(4) or createAndWait(5).

           This object may not be active(1) until instances of all
           other objects are appropriately configured. Its value,
           meanwhile, is notReady(2)."
       ::= { repObjectEntry 6 }

   peerTable OBJECT-TYPE
       SYNTAX     SEQUENCE OF PeerEntry
       MAX-ACCESS not-accessible
       STATUS     current
       DESCRIPTION
         " This table allows the definition of peer clusters of agent
           clusters which are used to maintain replicated objects."
       ::={ clusterDefinition 4 }

   peerEntry OBJECT-TYPE
       SYNTAX     PeerEntry
       MAX-ACCESS not-accessible
       STATUS     current
       DESCRIPTION
         " Each entry contains information of a cluster that maintains
           replicated objects."
      INDEX { pcIndex }
      ::= { peerTable 1 }

   PeerEntry ::= SEQUENCE {
       pcIndex       Unsigned32,
       pcAddressType  InetAddressType,
       pcAddress     InetAddress,
       pcROTIndex    Unsigned32,
       pcStatus      RowStatus
   }

   pcIndex OBJECT-TYPE
       SYNTAX     Unsigned32
       MAX-ACCESS read-only
       STATUS     current
       DESCRIPTION
         " Unique value which identifies a peer cluster table entry."
       ::= { peerEntry 1 }

   pcAddressType OBJECT-TYPE
       SYNTAX     InetAddressType
       MAX-ACCESS read-only
       STATUS     current
       DESCRIPTION
         " The type of address in pcAddress."
       ::= { peerEntry 2 }

   pcAddress OBJECT-TYPE
       SYNTAX     InetAddress
       MAX-ACCESS read-only
       STATUS     current
       DESCRIPTION
         " The IP address of a peer cluster which receives and
           keeps replicated objects by the cluster."
       ::= { peerEntry 3 }

   pcROTIndex OBJECT-TYPE
       SYNTAX     Unsigned32
       MAX-ACCESS read-only
       STATUS     current
       DESCRIPTION
         " Index of a object in the replicated object table which is
           replicated in a given peer cluster."
       ::= { peerEntry 4 }

   pcStatus OBJECT-TYPE
       SYNTAX     RowStatus
       MAX-ACCESS read-create
       STATUS     current
       DESCRIPTION
         " The status of this peer cluster entry.

           To create a row in this table, a manager must set this
           object to either createAndGo(4) or createAndWait(5).

           This object may not be active(1) until instances of all
           other objects are appropriately configured. Its value,
           meanwhile, is notReady(2)."
       ::= { peerEntry 5 }

   replicaTable OBJECT-TYPE
       SYNTAX     SEQUENCE OF ReplicaEntry
       MAX-ACCESS not-accessible
       STATUS     current
       DESCRIPTION
         " This table keeps the replicated instances of managed objects."
       ::={ clusterReplication 1 }

   replicaEntry OBJECT-TYPE
       SYNTAX     ReplicaEntry
       MAX-ACCESS not-accessible
       STATUS     current
       DESCRIPTION
         " Each entry keeps an instance of a given object of a given agent."
       INDEX { repIndex }
       ::= { replicaTable 1 }

   ReplicaEntry ::= SEQUENCE {
       repIndex          Unsigned32,
       repPeerType       InetAddressType,
       repPeer           InetAddress,
       repMemberType     InetAddressType,
       repMember         InetAddress,
       repOID            OBJECT IDENTIFIER,
       repInstanceIndex  OBJECT IDENTIFIER,
       repValue          OCTET STRING,
       repValueType      INTEGER,
       repTimeStamp      TimeStamp,
       repStatus         RowStatus
   }

   repIndex OBJECT-TYPE
       SYNTAX     Unsigned32
       MAX-ACCESS read-only
       STATUS     current
       DESCRIPTION
         " Unique value which identifies a replica table entry."
       ::= { replicaEntry 1 }

   repPeerType OBJECT-TYPE
       SYNTAX     InetAddressType
       MAX-ACCESS read-only
       STATUS     current
       DESCRIPTION
         " The type of address in repPeer."
       ::= { replicaEntry 2 }

   repPeer OBJECT-TYPE
       SYNTAX     InetAddress
       MAX-ACCESS read-only
       STATUS     current
       DESCRIPTION
         " The IP address of a peer cluster that monitors a set of
           agents and replicates their objects in the cluster."
       ::= { replicaEntry 3 }

   repMemberType OBJECT-TYPE
       SYNTAX     InetAddressType
       MAX-ACCESS read-only
       STATUS     current
       DESCRIPTION
         " The type of address in repMember."
       ::= { replicaEntry 4 }

   repMember OBJECT-TYPE
       SYNTAX     IpAddress
       MAX-ACCESS read-only
       STATUS     current
       DESCRIPTION
         " The IP address of an agent whose objects are replicated
           in the cluster."
       ::= { replicaEntry 5 }

   repOID OBJECT-TYPE
       SYNTAX     OBJECT IDENTIFIER
       MAX-ACCESS read-only
       STATUS     current
       DESCRIPTION
         " The instance identifier of a replicated object maintained
           in the cluster."
       ::= { replicaEntry 6 }

   repInstanceIndex OBJECT-TYPE
       SYNTAX     OBJECT IDENTIFIER
       MAX-ACCESS read-only
       STATUS     current
       DESCRIPTION
         " Unique identifier of an instance index of a replicated
           object maintained in the cluster."
       ::= { replicaEntry 7 }

   repValue OBJECT-TYPE
       SYNTAX     OCTET STRING
       MAX-ACCESS read-only
       STATUS     current
       DESCRIPTION
         " Value of an instance of a replicated object.
           The data type of the instance is specified in the next
           managed object."
       ::= { replicaEntry 8 }

   repValueType OBJECT-TYPE
       SYNTAX     INTEGER {
                     integer(0),
                     integer32(1),
                     unsigned32(2),
                     gauge32(3),
                     counter32(4),
                     counter64(5),
                     timeTicks(6),
                     octectString(7),
                     objectIdentifier(8),
                     ipAddress(9),
                     opaque(10),
                     bits(11)
             }
       MAX-ACCESS read-only
       STATUS     current
       DESCRIPTION
         " The data type of an instance of a replicated object kept
           in the previous managed object."
       ::= { replicaEntry 9 }

   repTimeStamp OBJECT-TYPE
        SYNTAX      TimeStamp
        MAX-ACCESS  read-only
        STATUS      current
        DESCRIPTION
          " The value of sysUpTime at the time of the last update
            of a value of an instance of a replicated object."
        ::= { replicaEntry 10 }

   repStatus OBJECT-TYPE
       SYNTAX      RowStatus
       MAX-ACCESS  read-create
       STATUS      current
       DESCRIPTION
         " The status of this replica entry.
           This object may not be active(1) until instances of all
           other objects are appropriately configured. Its value,
           meanwhile, is notReady(2)."
       ::= { replicaEntry 11 }

   -- Conformance information

   replicGroups      OBJECT IDENTIFIER  ::= { replicConformance 1 }
   replicCompliances OBJECT IDENTIFIER  ::= { replicConformance 2 }

   -- Compliance statements

   replicManagerCompliance MODULE-COMPLIANCE
        STATUS  current
        DESCRIPTION
          " The compliance statement for SNMP entities which
            implement the replication MIB in the manager level."
        MODULE
               MANDATORY-GROUPS { replicManagerGroup }
        ::= { replicCompliances 1 }

   replicClusterCompliance MODULE-COMPLIANCE
           STATUS  current
        DESCRIPTION
          " The compliance statement for SNMP entities which
            implement the replication MIB in the cluster level."
        MODULE
            MANDATORY-GROUPS { replicClusterGroup }
        ::= { replicCompliances 2 }

   replicFullCompliance MODULE-COMPLIANCE
        STATUS    current
        DESCRIPTION
          " The compliance statement for SNMP entities which
            implement the replication MIB in three layers."
        MODULE
            MANDATORY-GROUPS { replicManagerGroup, replicClusterGroup }
        ::= { replicCompliances 3 }

   -- Units of conformance

   replicManagerGroup OBJECT-GROUP
        OBJECTS{
             clusterIndex,
             clusterID,
             clusterAddressType,
             clusterAddress,
             clusterMemberType,
             clusterMember,
             clusterOID,
             clusterInstanceIndex,
             clusterRepClusterID,
             clusterName,
             clusterDescr,
             clusterStatus
   }
        STATUS    current
        DESCRIPTION
          " The collection of objects for the definition of agents
            clusters, which are used to replicate objects."
        ::= { replicGroups 1 }

   replicClusterGroup OBJECT-GROUP
        OBJECTS{
             cmIndex,
             cmAddressType,
             cmAddress,
             cmSecurity,
             cmStatus,
             roIndex,
             roOID,
             roInstanceIndex,
             roInterval,
             roState,
             roStatus,
             pcIndex,
             pcAddressType,
             pcAddress,
             pcROTIndex,
             pcStatus,
             repIndex,
             repPeerType,
             repPeer,
             repMemberType,
             repMember,
             repOID,
             repInstanceIndex,
             repValue,
             repValueType,
             repTimeStamp,
             repStatus
   }
        STATUS    current
        DESCRIPTION
          " The collection of objects used to monitor and keep
            the replicated objects."
        ::= { replicGroups 2 }

   END

-- 
--    Copyright (C) The Internet Society (2001). All Rights Reserved.
-- 
--    This document and translations of it may be copied and furnished to
--    others, and derivative works that comment on or otherwise explain it
--    or assist in its implementation may be prepared, copied, published
--    and distributed, in whole or in part, without restriction of any
--    kind, provided that the above copyright notice and this paragraph are
--    included on all such copies and derivative works.  However, this
--    document itself may not be modified in any way, such as by removing
--    the copyright notice or references to the Internet Society or other
--    Internet organizations, except as needed for the  purpose of
--    developing Internet standards in which case the procedures for
--    copyrights defined in the Internet Standards process must be
--    followed, or as required to translate it into languages other than
--    English.
-- 
--    The limited permissions granted above are perpetual and will not be
--    revoked by the Internet Society or its successors or assigns.
-- 
--    This document and the information contained herein is provided on an
--    "AS IS" basis and THE INTERNET SOCIETY AND THE INTERNET ENGINEERING
--    TASK FORCE DISCLAIMS ALL WARRANTIES, EXPRESS OR IMPLIED, INCLUDING
--    BUT NOT LIMITED TO ANY WARRANTY THAT THE USE OF THE INFORMATION
--    HEREIN WILL NOT INFRINGE ANY RIGHTS OR ANY IMPLIED WARRANTIES OF
--    MERCHANTABILITY OR FITNESS FOR A PARTICULAR PURPOSE.
