Wellfleet-MCT1-MIB DEFINITIONS ::= BEGIN

-- Created by mdl2asn version 3.1
-- Creation date: Wed Aug 30 16:45:09 EDT 1995


    IMPORTS

      Counter, Gauge
        FROM RFC1155-SMI
      OBJECT-TYPE
        FROM RFC-1212
      DisplayString
        FROM RFC1213-MIB
      wfMcT1Group
        FROM Wellfleet-COMMON-MIB;


    wfMcT1ModTable OBJECT-TYPE
        SYNTAX	SEQUENCE OF WfMcT1ModEntry
        ACCESS	not-accessible
        STATUS	mandatory
        DESCRIPTION
                "MCT1 MOD record - Contains MCT1 module Configuration parameters"
        ::= { wfMcT1Group 1 }

    wfMcT1ModEntry OBJECT-TYPE
        SYNTAX	WfMcT1ModEntry
        ACCESS	not-accessible
        STATUS	mandatory
        DESCRIPTION
                "An entry in the MCT1 Base table"
        INDEX	{ wfMcT1ModSlot }
        ::= { wfMcT1ModTable 1 }

    WfMcT1ModEntry ::= SEQUENCE {
    	    wfMcT1ModDelete
    		INTEGER,
    	    wfMcT1ModDisable
    		INTEGER,
    	    wfMcT1ModSlot
    		INTEGER,
    	    wfMcT1ModPrimaryClock
    		INTEGER,
    	    wfMcT1ModSecondaryClock
    		INTEGER,
    	    wfMcT1ModCurrentClock
    		INTEGER,
    	    wfMcT1ModExtClockOperational
    		INTEGER,
    	    wfMcT1ModLoop0ClockOperational
    		INTEGER,
    	    wfMcT1ModLoop1ClockOperational
    		INTEGER,
    	    wfMcT1ModRestart
    		INTEGER
        }

    wfMcT1ModDelete OBJECT-TYPE
        SYNTAX	INTEGER {
    		    created(1),
    		    deleted(2)
    		}
        ACCESS	read-write
        STATUS	mandatory
        DESCRIPTION
                "Create/Delete parameter"
        DEFVAL	{ created }
        ::= { wfMcT1ModEntry 1 }

    wfMcT1ModDisable OBJECT-TYPE
        SYNTAX	INTEGER {
    		    enabled(1),
    		    disabled(2)
    		}
        ACCESS	read-write
        STATUS	mandatory
        DESCRIPTION
                "Enable/Disable parameter"
        DEFVAL	{ enabled }
        ::= { wfMcT1ModEntry 2 }

    wfMcT1ModSlot OBJECT-TYPE
        SYNTAX	INTEGER(1..14)
        ACCESS	read-only
        STATUS	mandatory
        DESCRIPTION
                "Instance ID slot, filled in by driver"
        ::= { wfMcT1ModEntry 3 }

    wfMcT1ModPrimaryClock OBJECT-TYPE
        SYNTAX	INTEGER {
    		    external(1),
    		    loop0(2),
    		    loop1(3),
    		    int(4)
    		}
        ACCESS	read-write
        STATUS	mandatory
        DESCRIPTION
                "Specifies the primary source for T1 transmit timing.
                Both T1 ports use the same T1 transmit timing source.
                The options for T1 timing source are internal timing source,
                loop timing from either T1 port and an external timing
                source."
        DEFVAL	{ int }
        ::= { wfMcT1ModEntry 4 }

    wfMcT1ModSecondaryClock OBJECT-TYPE
        SYNTAX	INTEGER {
    		    external(1),
    		    loop0(2),
    		    loop1(3),
    		    int(4)
    		}
        ACCESS	read-write
        STATUS	mandatory
        DESCRIPTION
                "Specifies the secondary source for T1 transmit timing.
                During normal operation T1 transmit timing is derived
                from the primary timing source. If the primary timing
                source fails, the software switches to secondary timing
                source."
        DEFVAL	{ loop0 }
        ::= { wfMcT1ModEntry 5 }

    wfMcT1ModCurrentClock OBJECT-TYPE
        SYNTAX	INTEGER {
    		    primary(1),
    		    secondary(2),
    		    int(3)
    		}
        ACCESS	read-only
        STATUS	mandatory
        DESCRIPTION
                "Indicates the clock source currently in use"
        DEFVAL	{ primary }
        ::= { wfMcT1ModEntry 6 }

    wfMcT1ModExtClockOperational OBJECT-TYPE
        SYNTAX	INTEGER {
    		    oper(1),
    		    unoper(2)
    		}
        ACCESS	read-only
        STATUS	mandatory
        DESCRIPTION
                "Indicates whether the External clock is operational"
        DEFVAL	{ oper }
        ::= { wfMcT1ModEntry 7 }

    wfMcT1ModLoop0ClockOperational OBJECT-TYPE
        SYNTAX	INTEGER {
    		    oper(1),
    		    unoper(2)
    		}
        ACCESS	read-only
        STATUS	mandatory
        DESCRIPTION
                "Indicates whether the timing source from port 1
                is operational"
        DEFVAL	{ oper }
        ::= { wfMcT1ModEntry 8 }

    wfMcT1ModLoop1ClockOperational OBJECT-TYPE
        SYNTAX	INTEGER {
    		    oper(1),
    		    unoper(2)
    		}
        ACCESS	read-only
        STATUS	mandatory
        DESCRIPTION
                "Indicates whether the timing source from port 2
                is operational"
        DEFVAL	{ oper }
        ::= { wfMcT1ModEntry 9 }

    wfMcT1ModRestart OBJECT-TYPE
        SYNTAX	INTEGER
        ACCESS	read-write
        STATUS	mandatory
        DESCRIPTION
                "Indicates Module gate should be restarted to read
                new configuration"
        ::= { wfMcT1ModEntry 10 }

    wfMcT1Table OBJECT-TYPE
        SYNTAX	SEQUENCE OF WfMcT1Entry
        ACCESS	not-accessible
        STATUS	mandatory
        DESCRIPTION
                "MCT1  line record - Contains MUNICH32 Configuration parameters
                "
        ::= { wfMcT1Group 2 }

    wfMcT1Entry OBJECT-TYPE
        SYNTAX	WfMcT1Entry
        ACCESS	not-accessible
        STATUS	mandatory
        DESCRIPTION
                "An entry in the MCT1 table"
        INDEX	{ wfMcT1Slot,
    		  wfMcT1Connector }
        ::= { wfMcT1Table 1 }

    WfMcT1Entry ::= SEQUENCE {
    	    wfMcT1Delete
    		INTEGER,
    	    wfMcT1Disable
    		INTEGER,
    	    wfMcT1State
    		INTEGER,
    	    wfMcT1Slot
    		INTEGER,
    	    wfMcT1Connector
    		INTEGER,
    	    wfMcT1OperationMode
    		INTEGER,
    	    wfMcT1Mtu
    		INTEGER,
    	    wfMcT1MunichVersion
    		INTEGER,
    	    wfMcT1Dsx1LineType
    		INTEGER,
    	    wfMcT1Dsx1ZeroCoding
    		INTEGER,
    	    wfMcT1Dsx1LoopbackConfig
    		INTEGER,
    	    wfMcT1Dsx1LineStatus
    		INTEGER,
    	    wfMcT1Dsx1SetupAlarmThreshold
    		INTEGER,
    	    wfMcT1Dsx1ClearAlarmThreshold
    		INTEGER,
    	    wfMcT1Dsx1SignalLevel
    		INTEGER,
    	    wfMcT1LoopbackDisable
    		INTEGER,
    	    wfMcT1Dsx1FDLOperationMode
    		INTEGER,
    	    wfMcT1BertTxOutputLevel
    		INTEGER,
    	    wfMcT1BertTestMode
    		INTEGER,
    	    wfMcT1BertLineCode
    		INTEGER,
    	    wfMcT1BertTestPattern
    		INTEGER,
    	    wfMcT1BertSendAlarm
    		INTEGER,
    	    wfMcT1DS2282Version
    		INTEGER,
    	    wfMcT1Restart
    		INTEGER,
    	    wfMcT1Loopback
    		INTEGER,
    	    wfMcT1FDLTargetAddress
    		INTEGER
        }

    wfMcT1Delete OBJECT-TYPE
        SYNTAX	INTEGER {
    		    created(1),
    		    deleted(2)
    		}
        ACCESS	read-write
        STATUS	mandatory
        DESCRIPTION
                "Create/Delete parameter"
        DEFVAL	{ created }
        ::= { wfMcT1Entry 1 }

    wfMcT1Disable OBJECT-TYPE
        SYNTAX	INTEGER {
    		    enabled(1),
    		    disabled(2)
    		}
        ACCESS	read-write
        STATUS	mandatory
        DESCRIPTION
                "Enable/Disable parameter"
        DEFVAL	{ enabled }
        ::= { wfMcT1Entry 2 }

    wfMcT1State OBJECT-TYPE
        SYNTAX	INTEGER {
    		    init(1),
    		    up(2),
    		    bert(3),
    		    loopback(4),
    		    redalarm(5),
    		    yelalarm(6),
    		    bluealarm(7),
    		    notpresent(8)
    		}
        ACCESS	read-only
        STATUS	mandatory
        DESCRIPTION
                "Line Driver state variable"
        DEFVAL	{ notpresent }
        ::= { wfMcT1Entry 3 }

    wfMcT1Slot OBJECT-TYPE
        SYNTAX	INTEGER(1..14)
        ACCESS	read-only
        STATUS	mandatory
        DESCRIPTION
                "Instance ID Slot, filled in by driver"
        ::= { wfMcT1Entry 4 }

    wfMcT1Connector OBJECT-TYPE
        SYNTAX	INTEGER {
    		    one(1),
    		    two(2)
    		}
        ACCESS	read-only
        STATUS	mandatory
        DESCRIPTION
                "Instance ID Connector, filled in by driver"
        ::= { wfMcT1Entry 5 }

    wfMcT1OperationMode OBJECT-TYPE
        SYNTAX	INTEGER {
    		    default(1),
    		    bert(2)
    		}
        ACCESS	read-write
        STATUS	mandatory
        DESCRIPTION
                "An option to generate and analyze specific test patterns
                is provided in BERT mode of operation. Only one T1 port
                can be in BERT mode at a time. This attribute selects
                normal or BERT mode of operation"
        DEFVAL	{ default }
        ::= { wfMcT1Entry 6 }

    wfMcT1Mtu OBJECT-TYPE
        SYNTAX	INTEGER(3..4608)
        ACCESS	read-write
        STATUS	mandatory
        DESCRIPTION
                "MTU parameter. Specifies the largest frame size that
                can be received by the MCT1 link module. Any received frame
                which is larger than the MTU will be discarded."
        DEFVAL	{ 4608 }
        ::= { wfMcT1Entry 7 }

    wfMcT1MunichVersion OBJECT-TYPE
        SYNTAX	INTEGER {
    		    v1(1),
    		    v2(2)
    		}
        ACCESS	read-only
        STATUS	mandatory
        DESCRIPTION
                "Specifies version number of the MUNICH chip used"
        ::= { wfMcT1Entry 8 }

    wfMcT1Dsx1LineType OBJECT-TYPE
        SYNTAX	INTEGER {
    		    esf(2),
    		    d4(3)
    		}
        ACCESS	read-write
        STATUS	mandatory
        DESCRIPTION
                "Selects between the two framing formats supported - D4 and ESF.
                The sailent differences between the two formats are the number
                of frames per superframe and the use of F-bit position."
        DEFVAL	{ d4 }
        ::= { wfMcT1Entry 9 }

    wfMcT1Dsx1ZeroCoding OBJECT-TYPE
        SYNTAX	INTEGER {
    		    b8zs(2),
    		    ami(5)
    		}
        ACCESS	read-write
        STATUS	mandatory
        DESCRIPTION
                "Selects between the two Zero Code Suppression formats
                used on the link. In B8ZS coding, any outgoing stream of
                eight consecutive zeroes is replaced with a B8ZS code word.
                Any received B8ZS code is replaced with all zeroes."
        DEFVAL	{ ami }
        ::= { wfMcT1Entry 10 }

    wfMcT1Dsx1LoopbackConfig OBJECT-TYPE
        SYNTAX	INTEGER {
    		    noloop(1),
    		    mgrpayloadloop(2),
    		    mgrlineloop(3),
    		    netreqpayloadloop(4),
    		    netreqlineloop(5),
    		    otherloop(6)
    		}
        ACCESS	read-only
        STATUS	mandatory
        DESCRIPTION
                "Indicates the loopback configuration of the T1 interface.
                The interface can be in the following loopback states:
                Payload loopback and Line loopback or no loopback. The
                loopbacks can be initiated by the manager of this device
                or by the far end. The loopbacks initiated by the far end
                are NETREQPAYLOADLOOP and NETREQLINELOOP."
        DEFVAL	{ noloop }
        ::= { wfMcT1Entry 11 }

    wfMcT1Dsx1LineStatus OBJECT-TYPE
        SYNTAX	INTEGER {
    		    noalarm(1),
    		    farendalarm(2),
    		    alarmindicationsignal(4),
    		    lossofframe(8),
    		    lossofsignal(16),
    		    loopbackstate(32)
    		}
        ACCESS	read-only
        STATUS	mandatory
        DESCRIPTION
                "Indicates the line status of the T1 interface. It
                contains loopback state and alarm state information.
                The Dsx1LineStatus is a bit map therefore it can represent
                multiple loopback and alarm states simultaneously."
        ::= { wfMcT1Entry 12 }

    wfMcT1Dsx1SetupAlarmThreshold OBJECT-TYPE
        SYNTAX	INTEGER {
    		    threshold2(2),
    		    threshold4(4),
    		    threshold6(6),
    		    threshold8(8),
    		    threshold10(10)
    		}
        ACCESS	read-write
        STATUS	mandatory
        DESCRIPTION
                "Specifies setup time for performance failure conditions,
                in seconds. When a performance defect is present for greater
                than the time specified by this parameter a performance
                failure is registered and a message is logged."
        DEFVAL	{ threshold2 }
        ::= { wfMcT1Entry 13 }

    wfMcT1Dsx1ClearAlarmThreshold OBJECT-TYPE
        SYNTAX	INTEGER {
    		    threshold2(2),
    		    threshold4(4),
    		    threshold6(6),
    		    threshold8(8),
    		    threshold10(10)
    		}
        ACCESS	read-write
        STATUS	mandatory
        DESCRIPTION
                "Specifies clear time for performance failure conditions,
                in seconds. When a performance failure condition has been
                cleared for greater than the time specified by this parameter
                then the failure cleared condition is registered and a
                message is logged."
        DEFVAL	{ threshold2 }
        ::= { wfMcT1Entry 14 }

    wfMcT1Dsx1SignalLevel OBJECT-TYPE
        SYNTAX	INTEGER {
    		    minus15(1),
    		    minus7point5(2),
    		    minus0(3),
    		    pluspoint5(4),
    		    pluspoint8(5),
    		    plus1point1(6),
    		    plus1point5(7)
    		}
        ACCESS	read-write
        STATUS	mandatory
        DESCRIPTION
                "Specifies T1 transmit power level, in terms of DB. They
                translate into cable length as follows:
                0.0dB -> 0-133   ft
                0.5dB -> 133-266 ft
                0.8dB -> 266-399 ft
                1.1dB -> 399-533 ft
                1.5dB -> 533-655 ft"
        DEFVAL	{ minus0 }
        ::= { wfMcT1Entry 15 }

    wfMcT1LoopbackDisable OBJECT-TYPE
        SYNTAX	INTEGER {
    		    enabled(1),
    		    disabled(2)
    		}
        ACCESS	read-write
        STATUS	mandatory
        DESCRIPTION
                "The MCT1 link module is capable of detecting loop up
                and loop down codes received from the far end. This
                parameter enables or disbales loop up/down code detection
                circuitry"
        DEFVAL	{ enabled }
        ::= { wfMcT1Entry 16 }

    wfMcT1Dsx1FDLOperationMode OBJECT-TYPE
        SYNTAX	INTEGER {
    		    oper54016(1),
    		    opert1403(2)
    		}
        ACCESS	read-write
        STATUS	mandatory
        DESCRIPTION
                "Select between the two FDL modes of operation. The AT&T
                mode, 54016 is based on AT&T publication 54015-1989. The
                ANSI mode, T1403 is based on ANSI publication T1.403-1989"
        DEFVAL	{ opert1403 }
        ::= { wfMcT1Entry 17 }

    wfMcT1BertTxOutputLevel OBJECT-TYPE
        SYNTAX	INTEGER {
    		    minus15(1),
    		    minus7point5(2),
    		    minus0(3),
    		    pluspoint5(4),
    		    pluspoint8(5),
    		    plus1point1(6),
    		    plus1point5(7)
    		}
        ACCESS	read-write
        STATUS	mandatory
        DESCRIPTION
                "Specifies T1 transmit power level, in terms of DB while
                the T1 port is in BERT mode. The power levels translate into
                cable length as follows:
                0.0dB -> 0-133   ft
                0.5dB -> 133-266 ft
                0.8dB -> 266-399 ft
                1.1dB -> 399-533 ft
                1.5dB -> 533-655 ft"
        DEFVAL	{ minus0 }
        ::= { wfMcT1Entry 18 }

    wfMcT1BertTestMode OBJECT-TYPE
        SYNTAX	INTEGER {
    		    t1(1),
    		    sf(2),
    		    esf(3)
    		}
        ACCESS	read-write
        STATUS	mandatory
        DESCRIPTION
                "Selects between the framing formats while in bert mode of
                operation."
        DEFVAL	{ sf }
        ::= { wfMcT1Entry 19 }

    wfMcT1BertLineCode OBJECT-TYPE
        SYNTAX	INTEGER {
    		    ami(1),
    		    b8zs(2)
    		}
        ACCESS	read-write
        STATUS	mandatory
        DESCRIPTION
                "Selects between the two Zero Code Suppression formats
                used on the link while in BERT mode. In B8ZS coding,
                any outgoing stream of eight consecutive zeroes is replaced
                with a B8ZS code word. Any received B8ZS code is replaced
                with all zeroes."
        DEFVAL	{ ami }
        ::= { wfMcT1Entry 20 }

    wfMcT1BertTestPattern OBJECT-TYPE
        SYNTAX	INTEGER {
    		    zeros(1),
    		    ones(2),
    		    qrss(3),
    		    fifteen(4),
    		    fifteeninv(5),
    		    twenty(6),
    		    twentythree(7),
    		    twentythreeinv(8)
    		}
        ACCESS	read-write
        STATUS	mandatory
        DESCRIPTION
                "When a T1 port is in BERT mode, it is capable of generating
                a set of known patterns. This paramater selects between those
                patterns"
        DEFVAL	{ ones }
        ::= { wfMcT1Entry 21 }

    wfMcT1BertSendAlarm OBJECT-TYPE
        SYNTAX	INTEGER {
    		    blue(1),
    		    yellow(2),
    		    disabled(3)
    		}
        ACCESS	read-write
        STATUS	mandatory
        DESCRIPTION
                "Specifies a blue or yellow alarm to be transmitted
                while in BERT mode."
        DEFVAL	{ disabled }
        ::= { wfMcT1Entry 22 }

    wfMcT1DS2282Version OBJECT-TYPE
        SYNTAX	INTEGER
        ACCESS	read-only
        STATUS	mandatory
        DESCRIPTION
                "Specifies version  number of DS2282 chip"
        ::= { wfMcT1Entry 23 }

    wfMcT1Restart OBJECT-TYPE
        SYNTAX	INTEGER
        ACCESS	read-write
        STATUS	mandatory
        DESCRIPTION
                "Indicates Port gate should be restarted to read
                new configuration"
        ::= { wfMcT1Entry 24 }

    wfMcT1Loopback OBJECT-TYPE
        SYNTAX	INTEGER {
    		    linelb(1),
    		    payldlb(2),
    		    deactivate(3)
    		}
        ACCESS	read-write
        STATUS	mandatory
        DESCRIPTION
                "Selects line or payload loopback to be activated  locally"
        DEFVAL	{ deactivate }
        ::= { wfMcT1Entry 25 }

    wfMcT1FDLTargetAddress OBJECT-TYPE
        SYNTAX	INTEGER {
    		    az(1),
    		    by(2)
    		}
        ACCESS	read-write
        STATUS	mandatory
        DESCRIPTION
                "Selects between the two FDL target address modes"
        DEFVAL	{ by }
        ::= { wfMcT1Entry 26 }

    wfMcT1ConfigTable OBJECT-TYPE
        SYNTAX	SEQUENCE OF WfMcT1ConfigEntry
        ACCESS	not-accessible
        STATUS	mandatory
        DESCRIPTION
                "MCT1 configuration record - Contains MUNICH32 and Framer
                write only Configuration parameters"
        ::= { wfMcT1Group 3 }

    wfMcT1ConfigEntry OBJECT-TYPE
        SYNTAX	WfMcT1ConfigEntry
        ACCESS	not-accessible
        STATUS	mandatory
        DESCRIPTION
                "An entry in the MCT1 Config table"
        INDEX	{ wfMcT1ConfigSlot,
    		  wfMcT1ConfigConnector }
        ::= { wfMcT1ConfigTable 1 }

    WfMcT1ConfigEntry ::= SEQUENCE {
    	    wfMcT1ConfigSlot
    		INTEGER,
    	    wfMcT1ConfigConnector
    		INTEGER,
    	    wfMcT1BertRestart
    		INTEGER,
    	    wfMcT1BertPayldLb
    		INTEGER,
    	    wfMcT1BertLineLb
    		INTEGER,
    	    wfMcT1BertErrorInsert
    		INTEGER,
    	    wfMcT1Dsx1SendLoopCode
    		INTEGER,
    	    wfMcT1Dsx1SendFDLCode
    		INTEGER
        }

    wfMcT1ConfigSlot OBJECT-TYPE
        SYNTAX	INTEGER(1..14)
        ACCESS	read-only
        STATUS	mandatory
        DESCRIPTION
                "Instance ID Slot, filled in by driver"
        ::= { wfMcT1ConfigEntry 1 }

    wfMcT1ConfigConnector OBJECT-TYPE
        SYNTAX	INTEGER {
    		    one(1),
    		    two(2)
    		}
        ACCESS	read-only
        STATUS	mandatory
        DESCRIPTION
                "Instance ID Connector, filled in by driver"
        ::= { wfMcT1ConfigEntry 2 }

    wfMcT1BertRestart OBJECT-TYPE
        SYNTAX	INTEGER {
    		    restart(1),
    		    noaction(10)
    		}
        ACCESS	read-write
        STATUS	mandatory
        DESCRIPTION
                "Reset counters on BERT device"
        DEFVAL	{ noaction }
        ::= { wfMcT1ConfigEntry 3 }

    wfMcT1BertPayldLb OBJECT-TYPE
        SYNTAX	INTEGER {
    		    act(1),
    		    deact(2),
    		    noaction(10)
    		}
        ACCESS	read-write
        STATUS	mandatory
        DESCRIPTION
                "Selects a payload loopback code to be sent to the far end
                by the FDL while in BERT mode. It can be a payload loopback
                activate or deactivate code."
        DEFVAL	{ noaction }
        ::= { wfMcT1ConfigEntry 4 }

    wfMcT1BertLineLb OBJECT-TYPE
        SYNTAX	INTEGER {
    		    lpup(1),
    		    lpdn(2),
    		    fdlact(3),
    		    fdldeact(4),
    		    noaction(10)
    		}
        ACCESS	read-write
        STATUS	mandatory
        DESCRIPTION
                "Selects a line loopback code to be sent to the far end while in
                BERT mode. It can be a line loopback activate or deactivate
                code using the hardware on the MCT1 board or it can be a code
                sent by the FDL."
        DEFVAL	{ noaction }
        ::= { wfMcT1ConfigEntry 5 }

    wfMcT1BertErrorInsert OBJECT-TYPE
        SYNTAX	INTEGER {
    		    config(1),
    		    thousandconfig(2),
    		    millionconfig(3),
    		    disable(4),
    		    noaction(10)
    		}
        ACCESS	read-write
        STATUS	mandatory
        DESCRIPTION
                "Indicates that an error be injected into the transmitted data
                stream while in BERT mode."
        DEFVAL	{ noaction }
        ::= { wfMcT1ConfigEntry 6 }

    wfMcT1Dsx1SendLoopCode OBJECT-TYPE
        SYNTAX	INTEGER {
    		    loopup(1),
    		    loopdn(2),
    		    noaction(10)
    		}
        ACCESS	read-write
        STATUS	mandatory
        DESCRIPTION
                "Selects a  Loop Up/Down code to be sent to the remote end"
        DEFVAL	{ noaction }
        ::= { wfMcT1ConfigEntry 7 }

    wfMcT1Dsx1SendFDLCode OBJECT-TYPE
        SYNTAX	INTEGER {
    		    ci(1),
    		    univlbdeact(2),
    		    ia(3),
    		    linelbdeact(4),
    		    pyldlbact(5),
    		    pyldlbdeact(6),
    		    ib(7),
    		    noaction(10)
    		}
        ACCESS	read-write
        STATUS	mandatory
        DESCRIPTION
                "Selects an FDL code to be sent to the remote end"
        DEFVAL	{ noaction }
        ::= { wfMcT1ConfigEntry 8 }

    wfMcT1LineTable OBJECT-TYPE
        SYNTAX	SEQUENCE OF WfMcT1LineEntry
        ACCESS	not-accessible
        STATUS	mandatory
        DESCRIPTION
                "MCT1 Channel record - Contains configuration parameters and
                statistics for MUNICH32 which are channel specific."
        ::= { wfMcT1Group 4 }

    wfMcT1LineEntry OBJECT-TYPE
        SYNTAX	WfMcT1LineEntry
        ACCESS	not-accessible
        STATUS	mandatory
        DESCRIPTION
                "An entry in the MCT1CHANNEL table"
        INDEX	{ wfMcT1LineSlot,
    		  wfMcT1LineConnector,
    		  wfMcT1LineLine }
        ::= { wfMcT1LineTable 1 }

    WfMcT1LineEntry ::= SEQUENCE {
    	    wfMcT1LineDelete
    		INTEGER,
    	    wfMcT1LineDisable
    		INTEGER,
    	    wfMcT1LineState
    		INTEGER,
    	    wfMcT1LineSlot
    		INTEGER,
    	    wfMcT1LineConnector
    		INTEGER,
    	    wfMcT1LineLine
    		INTEGER,
    	    wfMcT1LineCct
    		INTEGER,
    	    wfMcT1LineBofl
    		INTEGER,
    	    wfMcT1LineBoflTmo
    		INTEGER,
    	    wfMcT1LineFractionalLpbk
    		INTEGER,
    	    wfMcT1LineChannelAssignment
    		DisplayString,
    	    wfMcT1LineMadr
    		OCTET STRING,
    	    wfMcT1LineWanProtocol
    		INTEGER,
    	    wfMcT1LineService
    		INTEGER,
    	    wfMcT1LineRateAdaption
    		INTEGER,
    	    wfMcT1LineIFTF
    		INTEGER,
    	    wfMcT1LineCRCSize
    		INTEGER,
    	    wfMcT1LineRxOctets
    		Counter,
    	    wfMcT1LineRxFrames
    		Counter,
    	    wfMcT1LineTxOctets
    		Counter,
    	    wfMcT1LineTxFrames
    		Counter,
    	    wfMcT1LineRxErrors
    		Counter,
    	    wfMcT1LineTxErrors
    		Counter,
    	    wfMcT1LineLackRxResources
    		Counter,
    	    wfMcT1LineLackTxResources
    		Counter,
    	    wfMcT1LineTxUnderflows
    		Counter,
    	    wfMcT1LineRxOverflows
    		Counter,
    	    wfMcT1LineRxNullFrames
    		Counter,
    	    wfMcT1LineRxShortFrames
    		Counter,
    	    wfMcT1LineRxLossSyncs
    		Counter,
    	    wfMcT1LineRxCRCErrors
    		Counter,
    	    wfMcT1LineRxNonOctetBits
    		Counter,
    	    wfMcT1LineRxLongFrames
    		Counter,
    	    wfMcT1LineRxAbortFrames
    		Counter,
    	    wfMcT1LineRxDescOverflows
    		Counter,
    	    wfMcT1LineTurboBofl
    		INTEGER,
    	    wfMcT1LineBoflNum
    		INTEGER,
    	    wfMcT1LineBoflLen
    		INTEGER,
    	    wfMcT1LineRxIntProcs
    		Counter,
    	    wfMcT1LineTxIntProcs
    		Counter,
    	    wfMcT1LineRxPktCorruptions
    		Counter,
    	    wfMcT1LineRxReplenMisses
    		Counter,
    	    wfMcT1LineRxIFCs
    		Counter,
    	    wfMcT1LineCfgTxQueueLength
    		INTEGER,
    	    wfMcT1LineCfgRxQueueLength
    		INTEGER,
    	    wfMcT1LineTxQueueLength
    		INTEGER,
    	    wfMcT1LineRxQueueLength
    		INTEGER,
    	    wfMcT1LineTxQueueEmpty
    		INTEGER,
    	    wfMcT1LineMtu
    		INTEGER,
    	    wfMcT1LineRestart
    		INTEGER,
    	    wfMcT1LineLineNumber
    		INTEGER
        }

    wfMcT1LineDelete OBJECT-TYPE
        SYNTAX	INTEGER {
    		    created(1),
    		    deleted(2)
    		}
        ACCESS	read-write
        STATUS	mandatory
        DESCRIPTION
                "Create/Delete parameter"
        DEFVAL	{ created }
        ::= { wfMcT1LineEntry 1 }

    wfMcT1LineDisable OBJECT-TYPE
        SYNTAX	INTEGER {
    		    enabled(1),
    		    disabled(2)
    		}
        ACCESS	read-write
        STATUS	mandatory
        DESCRIPTION
                "Enable/Disable parameter"
        DEFVAL	{ enabled }
        ::= { wfMcT1LineEntry 2 }

    wfMcT1LineState OBJECT-TYPE
        SYNTAX	INTEGER {
    		    up(1),
    		    down(2),
    		    init(3),
    		    loopback(4),
    		    wait(5),
    		    channel(6),
    		    stop(7),
    		    notpresent(8)
    		}
        ACCESS	read-only
        STATUS	mandatory
        DESCRIPTION
                "Line Driver state variable"
        DEFVAL	{ notpresent }
        ::= { wfMcT1LineEntry 3 }

    wfMcT1LineSlot OBJECT-TYPE
        SYNTAX	INTEGER(1..14)
        ACCESS	read-only
        STATUS	mandatory
        DESCRIPTION
                "Instance ID Slot, filled in by driver"
        ::= { wfMcT1LineEntry 4 }

    wfMcT1LineConnector OBJECT-TYPE
        SYNTAX	INTEGER {
    		    one(1),
    		    two(2)
    		}
        ACCESS	read-only
        STATUS	mandatory
        DESCRIPTION
                "Instance ID Connector, filled in by driver"
        ::= { wfMcT1LineEntry 5 }

    wfMcT1LineLine OBJECT-TYPE
        SYNTAX	INTEGER(1..24)
        ACCESS	read-only
        STATUS	mandatory
        DESCRIPTION
                "Line number for this line instance, filled in by driver.
                The line number corresponds to the position of the
                circuit, from 1 to 24, on the port."
        ::= { wfMcT1LineEntry 6 }

    wfMcT1LineCct OBJECT-TYPE
        SYNTAX	INTEGER(1..1023)
        ACCESS	read-write
        STATUS	mandatory
        DESCRIPTION
                "Circuit number for this line instance"
        ::= { wfMcT1LineEntry 7 }

    wfMcT1LineBofl OBJECT-TYPE
        SYNTAX	INTEGER {
    		    enabled(1),
    		    disabled(2)
    		}
        ACCESS	read-write
        STATUS	mandatory
        DESCRIPTION
                "Selects Breath of Life (BOFL) parameter. If selected, a BOFL
                packet is sent out on the wire as often as specifies by the
                wfMcT1LineBoflTmo parameter"
        DEFVAL	{ enabled }
        ::= { wfMcT1LineEntry 8 }

    wfMcT1LineBoflTmo OBJECT-TYPE
        SYNTAX	INTEGER(1..60)
        ACCESS	read-write
        STATUS	mandatory
        DESCRIPTION
                "Indicates the time-period between BOFL packets"
        DEFVAL	{ 5 }
        ::= { wfMcT1LineEntry 9 }

    wfMcT1LineFractionalLpbk OBJECT-TYPE
        SYNTAX	INTEGER {
    		    enabled(1),
    		    disabled(2)
    		}
        ACCESS	read-write
        STATUS	mandatory
        DESCRIPTION
                "Any circuit on this T1 port is capable of being put into
                loopback, i.e. data coming into that circuit from the wire is
                mirrorred back onto the wire. This parameter enables or
                disables this loopback feature on any circuit."
        DEFVAL	{ disabled }
        ::= { wfMcT1LineEntry 10 }

    wfMcT1LineChannelAssignment OBJECT-TYPE
        SYNTAX	DisplayString
        ACCESS	read-write
        STATUS	mandatory
        DESCRIPTION
                "Lists the time-slots which constitute this channel. User
                types in a list of time-slots from 1 to 24 separated by commas"
        ::= { wfMcT1LineEntry 11 }

    wfMcT1LineMadr OBJECT-TYPE
        SYNTAX	OCTET STRING
        ACCESS	read-only
        STATUS	mandatory
        DESCRIPTION
                "Line MAC address, fixed - line driver fills in from the 48 bit
                address stored in the serial number prom."
        ::= { wfMcT1LineEntry 12 }

    wfMcT1LineWanProtocol OBJECT-TYPE
        SYNTAX	INTEGER {
    		    standard(1),
    		    ppp(2),
    		    smds(3),
    		    framerelay(4),
    		    switch(5),
    		    sw(6)
    		}
        ACCESS	read-write
        STATUS	mandatory
        DESCRIPTION
                "WAN protocol selection is provided via this parameter. The
                supported protocols can be selected per circuit."
        DEFVAL	{ standard }
        ::= { wfMcT1LineEntry 13 }

    wfMcT1LineService OBJECT-TYPE
        SYNTAX	INTEGER {
    		    hdlc(1),
    		    llc1(2)
    		}
        ACCESS	read-write
        STATUS	mandatory
        DESCRIPTION
                "Service type for this circuit. Supports raw HDLC mode.
                Does not support LLC1 at this time. LLC1 mode
                will prefix the HDLC address and control fields to the
                frame. May support LLC1 mode in the future"
        DEFVAL	{ hdlc }
        ::= { wfMcT1LineEntry 14 }

    wfMcT1LineRateAdaption OBJECT-TYPE
        SYNTAX	INTEGER {
    		    adaption64k(1),
    		    msb(2),
    		    lsb(3)
    		}
        ACCESS	read-write
        STATUS	mandatory
        DESCRIPTION
                "Determines the number of bits and their bit positions
                within the time-slot. 64k selection uses all 8 bits in
                the time-slot. The two 56k selections use 7 of the 8
                bits in the time-slot. 56k_MSB does not use the most
                significant bit and 56k_LSB does not use the least
                significant bit in the time-slot."
        DEFVAL	{ lsb }
        ::= { wfMcT1LineEntry 15 }

    wfMcT1LineIFTF OBJECT-TYPE
        SYNTAX	INTEGER {
    		    flags(1),
    		    idles(2)
    		}
        ACCESS	read-write
        STATUS	mandatory
        DESCRIPTION
                "Determines the Interframe time fill character to be
                transmitted by the MUNICH. In case of IFTF_FLAGS, 0x7E
                is sent and in case of IFTF_IDLES 0xff is sent as the
                interframe timefill characters."
        DEFVAL	{ flags }
        ::= { wfMcT1LineEntry 16 }

    wfMcT1LineCRCSize OBJECT-TYPE
        SYNTAX	INTEGER {
    		    crc32(1),
    		    crc16(2)
    		}
        ACCESS	read-write
        STATUS	mandatory
        DESCRIPTION
                "Determines the CRC Size. When CRC32 is selected a 32 bit
                CRC is appended to the frame being transmitted and a 32
                bit CRC check is performed on the received frame. When
                CRC16 is selected, a 16 bit CRC is appended to the
                transmitted frame and a 16 bit CRC is performed. on the
                received frame."
        DEFVAL	{ crc16 }
        ::= { wfMcT1LineEntry 17 }

    wfMcT1LineRxOctets OBJECT-TYPE
        SYNTAX	Counter
        ACCESS	read-only
        STATUS	mandatory
        DESCRIPTION
                "Number of octets received without error"
        ::= { wfMcT1LineEntry 18 }

    wfMcT1LineRxFrames OBJECT-TYPE
        SYNTAX	Counter
        ACCESS	read-only
        STATUS	mandatory
        DESCRIPTION
                "Number of frames received without error"
        ::= { wfMcT1LineEntry 19 }

    wfMcT1LineTxOctets OBJECT-TYPE
        SYNTAX	Counter
        ACCESS	read-only
        STATUS	mandatory
        DESCRIPTION
                "Number of octets transmitted without error"
        ::= { wfMcT1LineEntry 20 }

    wfMcT1LineTxFrames OBJECT-TYPE
        SYNTAX	Counter
        ACCESS	read-only
        STATUS	mandatory
        DESCRIPTION
                "Number of frames transmitted without error"
        ::= { wfMcT1LineEntry 21 }

    wfMcT1LineRxErrors OBJECT-TYPE
        SYNTAX	Counter
        ACCESS	read-only
        STATUS	mandatory
        DESCRIPTION
                "Number of receive errors"
        ::= { wfMcT1LineEntry 22 }

    wfMcT1LineTxErrors OBJECT-TYPE
        SYNTAX	Counter
        ACCESS	read-only
        STATUS	mandatory
        DESCRIPTION
                "Number of transmission errors"
        ::= { wfMcT1LineEntry 23 }

    wfMcT1LineLackRxResources OBJECT-TYPE
        SYNTAX	Counter
        ACCESS	read-only
        STATUS	mandatory
        DESCRIPTION
                "Number of Rx frames dropped due to lack of buffer resources"
        ::= { wfMcT1LineEntry 24 }

    wfMcT1LineLackTxResources OBJECT-TYPE
        SYNTAX	Counter
        ACCESS	read-only
        STATUS	mandatory
        DESCRIPTION
                "Number of Tx frames dropped due to lack of buffer resources"
        ::= { wfMcT1LineEntry 25 }

    wfMcT1LineTxUnderflows OBJECT-TYPE
        SYNTAX	Counter
        ACCESS	read-only
        STATUS	mandatory
        DESCRIPTION
                "Number of Tx frames dropped due to Transmit underflow"
        ::= { wfMcT1LineEntry 26 }

    wfMcT1LineRxOverflows OBJECT-TYPE
        SYNTAX	Counter
        ACCESS	read-only
        STATUS	mandatory
        DESCRIPTION
                "Number of Rx frames dropped due to Receive overflow"
        ::= { wfMcT1LineEntry 27 }

    wfMcT1LineRxNullFrames OBJECT-TYPE
        SYNTAX	Counter
        ACCESS	read-only
        STATUS	mandatory
        DESCRIPTION
                "Number of short frames received (with no data bytes)"
        ::= { wfMcT1LineEntry 28 }

    wfMcT1LineRxShortFrames OBJECT-TYPE
        SYNTAX	Counter
        ACCESS	read-only
        STATUS	mandatory
        DESCRIPTION
                "Number of short frames received (less than or equal to two
                data bytes)"
        ::= { wfMcT1LineEntry 29 }

    wfMcT1LineRxLossSyncs OBJECT-TYPE
        SYNTAX	Counter
        ACCESS	read-only
        STATUS	mandatory
        DESCRIPTION
                "Loss of synchronization on receiver"
        ::= { wfMcT1LineEntry 30 }

    wfMcT1LineRxCRCErrors OBJECT-TYPE
        SYNTAX	Counter
        ACCESS	read-only
        STATUS	mandatory
        DESCRIPTION
                "CRC error received"
        ::= { wfMcT1LineEntry 31 }

    wfMcT1LineRxNonOctetBits OBJECT-TYPE
        SYNTAX	Counter
        ACCESS	read-only
        STATUS	mandatory
        DESCRIPTION
                "Non-Octet bits received in frame"
        ::= { wfMcT1LineEntry 32 }

    wfMcT1LineRxLongFrames OBJECT-TYPE
        SYNTAX	Counter
        ACCESS	read-only
        STATUS	mandatory
        DESCRIPTION
                "Frame longer than MFL received"
        ::= { wfMcT1LineEntry 33 }

    wfMcT1LineRxAbortFrames OBJECT-TYPE
        SYNTAX	Counter
        ACCESS	read-only
        STATUS	mandatory
        DESCRIPTION
                "Aborted frame received"
        ::= { wfMcT1LineEntry 34 }

    wfMcT1LineRxDescOverflows OBJECT-TYPE
        SYNTAX	Counter
        ACCESS	read-only
        STATUS	mandatory
        DESCRIPTION
                "Receive overflow on chip buffer"
        ::= { wfMcT1LineEntry 35 }

    wfMcT1LineTurboBofl OBJECT-TYPE
        SYNTAX	INTEGER {
    		    enabled(1),
    		    disabled(2)
    		}
        ACCESS	read-write
        STATUS	mandatory
        DESCRIPTION
                "DEBUG parameter - Turbo bofl enabled or disabled"
        DEFVAL	{ disabled }
        ::= { wfMcT1LineEntry 36 }

    wfMcT1LineBoflNum OBJECT-TYPE
        SYNTAX	INTEGER(1..127)
        ACCESS	read-write
        STATUS	mandatory
        DESCRIPTION
                "DEBUG parameter - Number of breath of life packets per breath
                of life"
        DEFVAL	{ 1 }
        ::= { wfMcT1LineEntry 37 }

    wfMcT1LineBoflLen OBJECT-TYPE
        SYNTAX	INTEGER(22..4450)
        ACCESS	read-write
        STATUS	mandatory
        DESCRIPTION
                "DEBUG parameter - breath of life packet length"
        DEFVAL	{ 200 }
        ::= { wfMcT1LineEntry 38 }

    wfMcT1LineRxIntProcs OBJECT-TYPE
        SYNTAX	Counter
        ACCESS	read-only
        STATUS	mandatory
        DESCRIPTION
                "Receive Interrupt processing count"
        ::= { wfMcT1LineEntry 39 }

    wfMcT1LineTxIntProcs OBJECT-TYPE
        SYNTAX	Counter
        ACCESS	read-only
        STATUS	mandatory
        DESCRIPTION
                "Tx interrupt processing count"
        ::= { wfMcT1LineEntry 40 }

    wfMcT1LineRxPktCorruptions OBJECT-TYPE
        SYNTAX	Counter
        ACCESS	read-only
        STATUS	mandatory
        DESCRIPTION
                "Corruption check on receive"
        ::= { wfMcT1LineEntry 41 }

    wfMcT1LineRxReplenMisses OBJECT-TYPE
        SYNTAX	Counter
        ACCESS	read-only
        STATUS	mandatory
        DESCRIPTION
                "Count of number of packet buffer misses while attempting to
                replenish driver receive ring"
        ::= { wfMcT1LineEntry 42 }

    wfMcT1LineRxIFCs OBJECT-TYPE
        SYNTAX	Counter
        ACCESS	read-only
        STATUS	mandatory
        DESCRIPTION
                "Number of times the device changes its interframe time-fill"
        ::= { wfMcT1LineEntry 43 }

    wfMcT1LineCfgTxQueueLength OBJECT-TYPE
        SYNTAX	INTEGER(0..336)
        ACCESS	read-write
        STATUS	mandatory
        DESCRIPTION
                "Configured transmit queue length"
        ::= { wfMcT1LineEntry 44 }

    wfMcT1LineCfgRxQueueLength OBJECT-TYPE
        SYNTAX	INTEGER(0..336)
        ACCESS	read-write
        STATUS	mandatory
        DESCRIPTION
                "Configured receive queue length"
        ::= { wfMcT1LineEntry 45 }

    wfMcT1LineTxQueueLength OBJECT-TYPE
        SYNTAX	INTEGER
        ACCESS	read-only
        STATUS	mandatory
        DESCRIPTION
                "Current transmit queue length"
        ::= { wfMcT1LineEntry 46 }

    wfMcT1LineRxQueueLength OBJECT-TYPE
        SYNTAX	INTEGER
        ACCESS	read-only
        STATUS	mandatory
        DESCRIPTION
                "Current Receive queue length"
        ::= { wfMcT1LineEntry 47 }

    wfMcT1LineTxQueueEmpty OBJECT-TYPE
        SYNTAX	INTEGER
        ACCESS	read-only
        STATUS	mandatory
        DESCRIPTION
                "The number of times the transmit ring is found
                empty when transmitting packets"
        ::= { wfMcT1LineEntry 48 }

    wfMcT1LineMtu OBJECT-TYPE
        SYNTAX	INTEGER
        ACCESS	read-only
        STATUS	mandatory
        DESCRIPTION
                "MTU read-only parameter. Specifies the largest frame size that
                can be received by the MCT1 link module. Any received frame
                which is larger than the MTU will be discarded. Can be set in
                MCT1Entry TABLE by the user"
        ::= { wfMcT1LineEntry 49 }

    wfMcT1LineRestart OBJECT-TYPE
        SYNTAX	INTEGER
        ACCESS	read-write
        STATUS	mandatory
        DESCRIPTION
                "Indicates channel gate should be restarted to read
                new configuration"
        ::= { wfMcT1LineEntry 50 }

    wfMcT1LineLineNumber OBJECT-TYPE
        SYNTAX	INTEGER
        ACCESS	read-write
        STATUS	mandatory
        DESCRIPTION
                "line number for this line instance"
        ::= { wfMcT1LineEntry 51 }

    wfMcT1Dsx1CurrentTable OBJECT-TYPE
        SYNTAX	SEQUENCE OF WfMcT1Dsx1CurrentEntry
        ACCESS	not-accessible
        STATUS	mandatory
        DESCRIPTION
                "The MCT1_DSX1 Current table"
        ::= { wfMcT1Group 5 }

    wfMcT1Dsx1CurrentEntry OBJECT-TYPE
        SYNTAX	WfMcT1Dsx1CurrentEntry
        ACCESS	not-accessible
        STATUS	mandatory
        DESCRIPTION
                "per circuit MCT1_DSX1 current objects - wfMcT1Dsx1CurrentIndex
                corresponds to Wellfleet circuit number"
        INDEX	{ wfMcT1Dsx1CurrentSlot,
    		  wfMcT1Dsx1CurrentConnector }
        ::= { wfMcT1Dsx1CurrentTable 1 }

    WfMcT1Dsx1CurrentEntry ::= SEQUENCE {
    	    wfMcT1Dsx1CurrentSlot
    		INTEGER,
    	    wfMcT1Dsx1CurrentConnector
    		INTEGER,
    	    wfMcT1Dsx1CurrentIntervalTimer
    		Gauge,
    	    wfMcT1Dsx1CurrentESs
    		Gauge,
    	    wfMcT1Dsx1CurrentSESs
    		Gauge,
    	    wfMcT1Dsx1CurrentBESs
    		Gauge,
    	    wfMcT1Dsx1CurrentUASs
    		Gauge,
    	    wfMcT1Dsx1CurrentCSSs
    		Gauge,
    	    wfMcT1Dsx1CurrentBPVs
    		Gauge
        }

    wfMcT1Dsx1CurrentSlot OBJECT-TYPE
        SYNTAX	INTEGER(1..14)
        ACCESS	read-only
        STATUS	mandatory
        DESCRIPTION
                "this corresponds to the Wellfleet Slot number"
        ::= { wfMcT1Dsx1CurrentEntry 1 }

    wfMcT1Dsx1CurrentConnector OBJECT-TYPE
        SYNTAX	INTEGER {
    		    one(1),
    		    two(2)
    		}
        ACCESS	read-only
        STATUS	mandatory
        DESCRIPTION
                "this corresponds to the Wellfleet Connector number"
        ::= { wfMcT1Dsx1CurrentEntry 2 }

    wfMcT1Dsx1CurrentIntervalTimer OBJECT-TYPE
        SYNTAX	Gauge
        ACCESS	read-only
        STATUS	mandatory
        DESCRIPTION
                "the number of seconds in the current 15 minute interval"
        ::= { wfMcT1Dsx1CurrentEntry 3 }

    wfMcT1Dsx1CurrentESs OBJECT-TYPE
        SYNTAX	Gauge
        ACCESS	read-only
        STATUS	mandatory
        DESCRIPTION
                "the number of errored seconds encountered by a DS1
                interface in the current 15 minute interval"
        ::= { wfMcT1Dsx1CurrentEntry 4 }

    wfMcT1Dsx1CurrentSESs OBJECT-TYPE
        SYNTAX	Gauge
        ACCESS	read-only
        STATUS	mandatory
        DESCRIPTION
                "the number of severely errored seconds in the
                current 15 minute interval"
        ::= { wfMcT1Dsx1CurrentEntry 5 }

    wfMcT1Dsx1CurrentBESs OBJECT-TYPE
        SYNTAX	Gauge
        ACCESS	read-only
        STATUS	mandatory
        DESCRIPTION
                "the number of bursty errored seconds in the
                current 15 minute interval"
        ::= { wfMcT1Dsx1CurrentEntry 6 }

    wfMcT1Dsx1CurrentUASs OBJECT-TYPE
        SYNTAX	Gauge
        ACCESS	read-only
        STATUS	mandatory
        DESCRIPTION
                "the number of unavailable seconds in the current 15
                minute interval"
        ::= { wfMcT1Dsx1CurrentEntry 7 }

    wfMcT1Dsx1CurrentCSSs OBJECT-TYPE
        SYNTAX	Gauge
        ACCESS	read-only
        STATUS	mandatory
        DESCRIPTION
                "the number of Controlled Slip seconds in the current 15
                minute interval"
        ::= { wfMcT1Dsx1CurrentEntry 8 }

    wfMcT1Dsx1CurrentBPVs OBJECT-TYPE
        SYNTAX	Gauge
        ACCESS	read-only
        STATUS	mandatory
        DESCRIPTION
                "the number of bipolar violations in the current 15
                minute interval"
        ::= { wfMcT1Dsx1CurrentEntry 9 }

    wfMcT1Dsx1IntervalTable OBJECT-TYPE
        SYNTAX	SEQUENCE OF WfMcT1Dsx1IntervalEntry
        ACCESS	not-accessible
        STATUS	mandatory
        DESCRIPTION
                "The MCT1_DSX1 Interval table"
        ::= { wfMcT1Group 6 }

    wfMcT1Dsx1IntervalEntry OBJECT-TYPE
        SYNTAX	WfMcT1Dsx1IntervalEntry
        ACCESS	not-accessible
        STATUS	mandatory
        DESCRIPTION
                "per circuit MCT1_DSX1 interval objects - wfMcT1Dsx1IntervalIndex
                corresponds to Wellfleet circuit number,
                wfMcT1Dsx1IntervalNumber is the numbered previous
                15-minute interval"
        INDEX	{ wfMcT1Dsx1IntervalSlot,
    		  wfMcT1Dsx1IntervalConnector,
    		  wfMcT1Dsx1IntervalNumber }
        ::= { wfMcT1Dsx1IntervalTable 1 }

    WfMcT1Dsx1IntervalEntry ::= SEQUENCE {
    	    wfMcT1Dsx1IntervalSlot
    		INTEGER,
    	    wfMcT1Dsx1IntervalConnector
    		INTEGER,
    	    wfMcT1Dsx1IntervalNumber
    		INTEGER,
    	    wfMcT1Dsx1IntervalESs
    		Gauge,
    	    wfMcT1Dsx1IntervalSESs
    		Gauge,
    	    wfMcT1Dsx1IntervalBESs
    		Gauge,
    	    wfMcT1Dsx1IntervalUASs
    		Gauge,
    	    wfMcT1Dsx1IntervalCSSs
    		Gauge,
    	    wfMcT1Dsx1IntervalBPVs
    		Gauge
        }

    wfMcT1Dsx1IntervalSlot OBJECT-TYPE
        SYNTAX	INTEGER(1..14)
        ACCESS	read-only
        STATUS	mandatory
        DESCRIPTION
                "this corresponds to the Wellfleet Slot number"
        ::= { wfMcT1Dsx1IntervalEntry 1 }

    wfMcT1Dsx1IntervalConnector OBJECT-TYPE
        SYNTAX	INTEGER {
    		    one(1),
    		    two(2)
    		}
        ACCESS	read-only
        STATUS	mandatory
        DESCRIPTION
                "this corresponds to the Wellfleet Connector number"
        ::= { wfMcT1Dsx1IntervalEntry 2 }

    wfMcT1Dsx1IntervalNumber OBJECT-TYPE
        SYNTAX	INTEGER(1..96)
        ACCESS	read-only
        STATUS	mandatory
        DESCRIPTION
                "1..96 where 1 is the most recent 15-minute interval and 96 is
                the least"
        ::= { wfMcT1Dsx1IntervalEntry 3 }

    wfMcT1Dsx1IntervalESs OBJECT-TYPE
        SYNTAX	Gauge
        ACCESS	read-only
        STATUS	mandatory
        DESCRIPTION
                "the number of errored seconds in the specified interval"
        ::= { wfMcT1Dsx1IntervalEntry 4 }

    wfMcT1Dsx1IntervalSESs OBJECT-TYPE
        SYNTAX	Gauge
        ACCESS	read-only
        STATUS	mandatory
        DESCRIPTION
                "the number of severely errored seconds in the specified
                interval"
        ::= { wfMcT1Dsx1IntervalEntry 5 }

    wfMcT1Dsx1IntervalBESs OBJECT-TYPE
        SYNTAX	Gauge
        ACCESS	read-only
        STATUS	mandatory
        DESCRIPTION
                "the number of bursty errored seconds in the
                specified interval"
        ::= { wfMcT1Dsx1IntervalEntry 6 }

    wfMcT1Dsx1IntervalUASs OBJECT-TYPE
        SYNTAX	Gauge
        ACCESS	read-only
        STATUS	mandatory
        DESCRIPTION
                "the number of unavailable seconds in the specified interval"
        ::= { wfMcT1Dsx1IntervalEntry 7 }

    wfMcT1Dsx1IntervalCSSs OBJECT-TYPE
        SYNTAX	Gauge
        ACCESS	read-only
        STATUS	mandatory
        DESCRIPTION
                "the number of controlled slip seconds in the specified interval"
        ::= { wfMcT1Dsx1IntervalEntry 8 }

    wfMcT1Dsx1IntervalBPVs OBJECT-TYPE
        SYNTAX	Gauge
        ACCESS	read-only
        STATUS	mandatory
        DESCRIPTION
                "the number of bipolar violations in the specified interval"
        ::= { wfMcT1Dsx1IntervalEntry 9 }

    wfMcT1Dsx1TotalTable OBJECT-TYPE
        SYNTAX	SEQUENCE OF WfMcT1Dsx1TotalEntry
        ACCESS	not-accessible
        STATUS	mandatory
        DESCRIPTION
                "The MCT1_DSX1 Total table"
        ::= { wfMcT1Group 7 }

    wfMcT1Dsx1TotalEntry OBJECT-TYPE
        SYNTAX	WfMcT1Dsx1TotalEntry
        ACCESS	not-accessible
        STATUS	mandatory
        DESCRIPTION
                "per circuit MCT1_DSX1 total objects - wfMcT1Dsx1TotalIndex
                corresponds to Wellfleet circuit number"
        INDEX	{ wfMcT1Dsx1TotalSlot,
    		  wfMcT1Dsx1TotalConnector }
        ::= { wfMcT1Dsx1TotalTable 1 }

    WfMcT1Dsx1TotalEntry ::= SEQUENCE {
    	    wfMcT1Dsx1TotalSlot
    		INTEGER,
    	    wfMcT1Dsx1TotalConnector
    		INTEGER,
    	    wfMcT1Dsx1TotalVITR
    		Gauge,
    	    wfMcT1Dsx1TotalESs
    		Gauge,
    	    wfMcT1Dsx1TotalSESs
    		Gauge,
    	    wfMcT1Dsx1TotalBESs
    		Gauge,
    	    wfMcT1Dsx1TotalUASs
    		Gauge,
    	    wfMcT1Dsx1TotalCSSs
    		Gauge,
    	    wfMcT1Dsx1TotalBPVs
    		Gauge
        }

    wfMcT1Dsx1TotalSlot OBJECT-TYPE
        SYNTAX	INTEGER(1..14)
        ACCESS	read-only
        STATUS	mandatory
        DESCRIPTION
                "this corresponds to the Wellfleet Slot number"
        ::= { wfMcT1Dsx1TotalEntry 1 }

    wfMcT1Dsx1TotalConnector OBJECT-TYPE
        SYNTAX	INTEGER {
    		    one(1),
    		    two(2)
    		}
        ACCESS	read-only
        STATUS	mandatory
        DESCRIPTION
                "this corresponds to the Wellfleet Connector number"
        ::= { wfMcT1Dsx1TotalEntry 2 }

    wfMcT1Dsx1TotalVITR OBJECT-TYPE
        SYNTAX	Gauge
        ACCESS	read-only
        STATUS	mandatory
        DESCRIPTION
                "Indicates the number of valid 15 minute intervals
                in the previous 24 hour period"
        ::= { wfMcT1Dsx1TotalEntry 3 }

    wfMcT1Dsx1TotalESs OBJECT-TYPE
        SYNTAX	Gauge
        ACCESS	read-only
        STATUS	mandatory
        DESCRIPTION
                "The number of errored seconds encountered by the DS1
                interface in the previous 24 hour interval"
        ::= { wfMcT1Dsx1TotalEntry 4 }

    wfMcT1Dsx1TotalSESs OBJECT-TYPE
        SYNTAX	Gauge
        ACCESS	read-only
        STATUS	mandatory
        DESCRIPTION
                "The number of severely errored seconds encountered by a DS1
                interface in the previous 24 hour interval"
        ::= { wfMcT1Dsx1TotalEntry 5 }

    wfMcT1Dsx1TotalBESs OBJECT-TYPE
        SYNTAX	Gauge
        ACCESS	read-only
        STATUS	mandatory
        DESCRIPTION
                "The number of bursty errored seconds encountered
                by a DS1 interface in the previous 24 hour interval"
        ::= { wfMcT1Dsx1TotalEntry 6 }

    wfMcT1Dsx1TotalUASs OBJECT-TYPE
        SYNTAX	Gauge
        ACCESS	read-only
        STATUS	mandatory
        DESCRIPTION
                "The number of unavailable seconds encountered by
                by a DS1 interface in the previous 24 hour interval"
        ::= { wfMcT1Dsx1TotalEntry 7 }

    wfMcT1Dsx1TotalCSSs OBJECT-TYPE
        SYNTAX	Gauge
        ACCESS	read-only
        STATUS	mandatory
        DESCRIPTION
                "The number of controlled slip seconds encountered
                by a DS1 interface in the previous 24 hour interval"
        ::= { wfMcT1Dsx1TotalEntry 8 }

    wfMcT1Dsx1TotalBPVs OBJECT-TYPE
        SYNTAX	Gauge
        ACCESS	read-only
        STATUS	mandatory
        DESCRIPTION
                "The number of bipolar violations encountered
                by a DS1 interface in the previous 24 hour interval"
        ::= { wfMcT1Dsx1TotalEntry 9 }

    wfMcT1AnsiTable OBJECT-TYPE
        SYNTAX	SEQUENCE OF WfMcT1AnsiEntry
        ACCESS	not-accessible
        STATUS	mandatory
        DESCRIPTION
                "ANSI Statistics line record - This table contains the
                performance parameters for the ANSI register set "
        ::= { wfMcT1Group 8 }

    wfMcT1AnsiEntry OBJECT-TYPE
        SYNTAX	WfMcT1AnsiEntry
        ACCESS	not-accessible
        STATUS	mandatory
        DESCRIPTION
                "An entry in the MCT1 Ansi table"
        INDEX	{ wfMcT1AnsiSlot,
    		  wfMcT1AnsiConnector }
        ::= { wfMcT1AnsiTable 1 }

    WfMcT1AnsiEntry ::= SEQUENCE {
    	    wfMcT1AnsiSlot
    		INTEGER,
    	    wfMcT1AnsiConnector
    		INTEGER,
    	    wfMcT1AnsiCRCCounts
    		Counter,
    	    wfMcT1AnsiBPVCounts
    		Counter,
    	    wfMcT1AnsiOOFCounts
    		Counter,
    	    wfMcT1AnsiFECounts
    		Counter,
    	    wfMcT1AnsiESCounts
    		Counter,
    	    wfMcT1AnsiSESCounts
    		Counter,
    	    wfMcT1AnsiUASCounts
    		Counter,
    	    wfMcT1AnsiPRMR0Counts
    		Counter,
    	    wfMcT1AnsiPRMR1Counts
    		Counter,
    	    wfMcT1AnsiPRMR2Counts
    		Counter,
    	    wfMcT1AnsiPRMR3Counts
    		Counter,
    	    wfMcT1AnsiPRMESCounts
    		Counter,
    	    wfMcT1AnsiPRMSESCounts
    		Counter,
    	    wfMcT1AnsiPRMECounts
    		Counter
        }

    wfMcT1AnsiSlot OBJECT-TYPE
        SYNTAX	INTEGER(1..14)
        ACCESS	read-only
        STATUS	mandatory
        DESCRIPTION
                "Instance ID Slot, filled in by driver"
        ::= { wfMcT1AnsiEntry 1 }

    wfMcT1AnsiConnector OBJECT-TYPE
        SYNTAX	INTEGER {
    		    one(1),
    		    two(2)
    		}
        ACCESS	read-only
        STATUS	mandatory
        DESCRIPTION
                "Instance ID Connector, filled in by driver"
        ::= { wfMcT1AnsiEntry 2 }

    wfMcT1AnsiCRCCounts OBJECT-TYPE
        SYNTAX	Counter
        ACCESS	read-only
        STATUS	mandatory
        DESCRIPTION
                "Counts CRC-6 error events"
        ::= { wfMcT1AnsiEntry 3 }

    wfMcT1AnsiBPVCounts OBJECT-TYPE
        SYNTAX	Counter
        ACCESS	read-only
        STATUS	mandatory
        DESCRIPTION
                "Counts bipolar violations"
        ::= { wfMcT1AnsiEntry 4 }

    wfMcT1AnsiOOFCounts OBJECT-TYPE
        SYNTAX	Counter
        ACCESS	read-only
        STATUS	mandatory
        DESCRIPTION
                "Counts out-of-frame error events"
        ::= { wfMcT1AnsiEntry 5 }

    wfMcT1AnsiFECounts OBJECT-TYPE
        SYNTAX	Counter
        ACCESS	read-only
        STATUS	mandatory
        DESCRIPTION
                "Counts errors in the FPS framing pattern"
        ::= { wfMcT1AnsiEntry 6 }

    wfMcT1AnsiESCounts OBJECT-TYPE
        SYNTAX	Counter
        ACCESS	read-only
        STATUS	mandatory
        DESCRIPTION
                "Counts errorred seconds"
        ::= { wfMcT1AnsiEntry 7 }

    wfMcT1AnsiSESCounts OBJECT-TYPE
        SYNTAX	Counter
        ACCESS	read-only
        STATUS	mandatory
        DESCRIPTION
                "Counts severly errorred seconds"
        ::= { wfMcT1AnsiEntry 8 }

    wfMcT1AnsiUASCounts OBJECT-TYPE
        SYNTAX	Counter
        ACCESS	read-only
        STATUS	mandatory
        DESCRIPTION
                "counts unavailable seconds"
        ::= { wfMcT1AnsiEntry 9 }

    wfMcT1AnsiPRMR0Counts OBJECT-TYPE
        SYNTAX	Counter
        ACCESS	read-only
        STATUS	mandatory
        DESCRIPTION
                "Counts PRMs that ewre received in the FDL in
                the last four seconds"
        ::= { wfMcT1AnsiEntry 10 }

    wfMcT1AnsiPRMR1Counts OBJECT-TYPE
        SYNTAX	Counter
        ACCESS	read-only
        STATUS	mandatory
        DESCRIPTION
                "Counts PRMs that ewre received in the FDL in
                the last four seconds"
        ::= { wfMcT1AnsiEntry 11 }

    wfMcT1AnsiPRMR2Counts OBJECT-TYPE
        SYNTAX	Counter
        ACCESS	read-only
        STATUS	mandatory
        DESCRIPTION
                "Counts PRMs that ewre received in the FDL in
                the last four seconds"
        ::= { wfMcT1AnsiEntry 12 }

    wfMcT1AnsiPRMR3Counts OBJECT-TYPE
        SYNTAX	Counter
        ACCESS	read-only
        STATUS	mandatory
        DESCRIPTION
                "Counts PRMs that ewre received in the FDL in
                the last four seconds"
        ::= { wfMcT1AnsiEntry 13 }

    wfMcT1AnsiPRMESCounts OBJECT-TYPE
        SYNTAX	Counter
        ACCESS	read-only
        STATUS	mandatory
        DESCRIPTION
                "Counts errorred seconds as reported in the Performance
                report messages"
        ::= { wfMcT1AnsiEntry 14 }

    wfMcT1AnsiPRMSESCounts OBJECT-TYPE
        SYNTAX	Counter
        ACCESS	read-only
        STATUS	mandatory
        DESCRIPTION
                "Counts severely errorred seconds as reported in the
                Performance report messages"
        ::= { wfMcT1AnsiEntry 15 }

    wfMcT1AnsiPRMECounts OBJECT-TYPE
        SYNTAX	Counter
        ACCESS	read-only
        STATUS	mandatory
        DESCRIPTION
                "Counts Performance report messages that are received
                in error"
        ::= { wfMcT1AnsiEntry 16 }

    wfMcT1BertStatsTable OBJECT-TYPE
        SYNTAX	SEQUENCE OF WfMcT1BertStatsEntry
        ACCESS	not-accessible
        STATUS	mandatory
        DESCRIPTION
                "BERT Counter line record - This table contains the
                statistics for the BERT tester."
        ::= { wfMcT1Group 9 }

    wfMcT1BertStatsEntry OBJECT-TYPE
        SYNTAX	WfMcT1BertStatsEntry
        ACCESS	not-accessible
        STATUS	mandatory
        DESCRIPTION
                "An entry in the MCT1 Bert Stats table"
        INDEX	{ wfMcT1BertStatsSlot,
    		  wfMcT1BertStatsConnector }
        ::= { wfMcT1BertStatsTable 1 }

    WfMcT1BertStatsEntry ::= SEQUENCE {
    	    wfMcT1BertStatsSlot
    		INTEGER,
    	    wfMcT1BertStatsConnector
    		INTEGER,
    	    wfMcT1BertStatsBitErrors
    		Counter,
    	    wfMcT1BertStatsBits
    		Counter
        }

    wfMcT1BertStatsSlot OBJECT-TYPE
        SYNTAX	INTEGER(1..14)
        ACCESS	read-only
        STATUS	mandatory
        DESCRIPTION
                "Instance ID Slot, filled in by driver"
        ::= { wfMcT1BertStatsEntry 1 }

    wfMcT1BertStatsConnector OBJECT-TYPE
        SYNTAX	INTEGER {
    		    one(1),
    		    two(2)
    		}
        ACCESS	read-only
        STATUS	mandatory
        DESCRIPTION
                "Instance ID Connector, filled in by driver"
        ::= { wfMcT1BertStatsEntry 2 }

    wfMcT1BertStatsBitErrors OBJECT-TYPE
        SYNTAX	Counter
        ACCESS	read-only
        STATUS	mandatory
        DESCRIPTION
                "Bit error counter"
        ::= { wfMcT1BertStatsEntry 3 }

    wfMcT1BertStatsBits OBJECT-TYPE
        SYNTAX	Counter
        ACCESS	read-only
        STATUS	mandatory
        DESCRIPTION
                "Bit counter"
        ::= { wfMcT1BertStatsEntry 4 }

    END  -- Wellfleet-MCT1-MIB
