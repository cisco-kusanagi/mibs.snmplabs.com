INTEL-FREXT-MIB DEFINITIONS ::= BEGIN

-- Copyright (C) 1997 Intel Corporation. All rights reserved.
--
-- Intel Private Frame Relay extensions MIB, 05-03-1997
--
-- This MIB provides objects for Frame Relay Encryption and Compression.
-- It complements the FRAME-RELAY-DTE-MIB.
--
-- Change History:
-- <date> <change>
--

IMPORTS
        Counter         FROM RFC1155-SMI
        OBJECT-TYPE     FROM RFC-1212
        mib2ext         FROM INTEL-GEN-MIB
        DLCI            FROM FRAME-RELAY-DTE-MIB;


frEx            OBJECT IDENTIFIER ::= { mib2ext 28 }

frCircuitExt    OBJECT IDENTIFIER ::= { frEx 1 }


InterfaceIndex ::= INTEGER    -- 1..ifNumber


frCirExtEncTable OBJECT-TYPE
    SYNTAX SEQUENCE OF FrCirExtEncEntry
    ACCESS not-accessible
    STATUS mandatory
    DESCRIPTION "Encryption information table."
    ::= { frCircuitExt 1 }

frCirExtEncEntry OBJECT-TYPE
    SYNTAX FrCirExtEncEntry
    ACCESS not-accessible
    STATUS mandatory
    DESCRIPTION ""
    INDEX { frCirExtEncIfIndex, frCirExtEncDlci }
    ::= { frCirExtEncTable 1 }

FrCirExtEncEntry ::= SEQUENCE {
    frCirExtEncIfIndex          InterfaceIndex,
    frCirExtEncDlci             DLCI,
    frCirExtEncLogicalIfIndex   InterfaceIndex,
    frCirExtEncEnabled          INTEGER,
    frCirExtEncNegotiated       INTEGER,
    frCirExtEncResetRequestsRx  Counter,
    frCirExtEncResetRequestsTx  Counter,
    frCirExtEncResetAcksRx      Counter,
    frCirExtEncResetAcksTx      Counter,
    frCirExtEncRxDiscarded      Counter,
    frCirExtEncTxDiscarded      Counter,
    frCirExtEncReceiverState    INTEGER
}

frCirExtEncIfIndex OBJECT-TYPE
    SYNTAX  InterfaceIndex
    ACCESS  read-only
    STATUS  mandatory
    DESCRIPTION
           "The ifIndex Value of the ifEntry this virtual
            circuit is layered onto."
    ::= { frCirExtEncEntry  1 }

frCirExtEncDlci OBJECT-TYPE
    SYNTAX  DLCI
    ACCESS  read-only
    STATUS  mandatory
    DESCRIPTION
           "The Data Link Connection Identifier for this
            virtual circuit."
    REFERENCE
           "Draft American National  Standard  T1.618-1991, Section 3.3.6"
    ::= { frCirExtEncEntry  2 }

frCirExtEncLogicalIfIndex OBJECT-TYPE
    SYNTAX  InterfaceIndex
    ACCESS  read-only
    STATUS  mandatory
    DESCRIPTION
       "Normally the same value as frDlcmiIfIndex, but
       different when an implementation associates a virtual
       ifEntry with a DLC or set of DLCs in order to associate
       higher layer objects such as the ipAddrEntry with a
       subset of the virtual circuits on a Frame Relay
       interface. The type of such ifEntries is defined by the
       higher layer object; for example, if PPP/Frame Relay is
       implemented, the ifType of this ifEntry would be PPP.
       If it is not so defined, as would be the case with an
       ipAddrEntry, it should be of type Other."
   ::= { frCirExtEncEntry 3 }

frCirExtEncEnabled OBJECT-TYPE
    SYNTAX INTEGER {
        no(1),
        yes(2)
        }
    ACCESS read-only
    STATUS mandatory
    DESCRIPTION "Encryption enabled on link."
    ::= { frCirExtEncEntry 4 }

frCirExtEncNegotiated OBJECT-TYPE
    SYNTAX INTEGER {
        no(1),
        yes(2)
        }
    ACCESS read-only
    STATUS mandatory
    DESCRIPTION "Encryption negotiated on link."
    ::= { frCirExtEncEntry 5 }

frCirExtEncResetRequestsRx OBJECT-TYPE
    SYNTAX Counter
    ACCESS read-only
    STATUS mandatory
    DESCRIPTION "Number of encryption history reset requests received."
    ::= { frCirExtEncEntry 6 }

frCirExtEncResetRequestsTx OBJECT-TYPE
    SYNTAX Counter
    ACCESS read-only
    STATUS mandatory
    DESCRIPTION "Number of encryption history reset requests sent."
    ::= { frCirExtEncEntry 7 }

frCirExtEncResetAcksRx OBJECT-TYPE
    SYNTAX Counter
    ACCESS read-only
    STATUS mandatory
    DESCRIPTION "Number of encryption history reset acknowledgments received."
    ::= { frCirExtEncEntry 8 }

frCirExtEncResetAcksTx OBJECT-TYPE
    SYNTAX Counter
    ACCESS read-only
    STATUS mandatory
    DESCRIPTION "Number of encryption history reset acknowledgments sent."
    ::= { frCirExtEncEntry 9 }

frCirExtEncRxDiscarded OBJECT-TYPE
    SYNTAX Counter
    ACCESS read-only
    STATUS mandatory
    DESCRIPTION "Number of packets discarded due to lack of
                 synchronisation, buffer lacks or packet errors."
    ::= { frCirExtEncEntry 10 }

frCirExtEncTxDiscarded OBJECT-TYPE
    SYNTAX Counter
    ACCESS read-only
    STATUS mandatory
    DESCRIPTION "Number of packets discarded due to buffer lacks or
    transmit queue overflows"
    ::= { frCirExtEncEntry 11 }

frCirExtEncReceiverState OBJECT-TYPE
    SYNTAX INTEGER {
        ok(1),
        error(2)
        }
    ACCESS read-only
    STATUS mandatory
    DESCRIPTION "State of receiver.
                 Error state means waiting for reset acknowledgment"
    ::= { frCirExtEncEntry 12 }


--
--
frCirExtCompTable OBJECT-TYPE
    SYNTAX SEQUENCE OF FrCirExtCompEntry
    ACCESS not-accessible
    STATUS mandatory
    DESCRIPTION "Compression information table."
    ::= { frCircuitExt 2 }

frCirExtCompEntry OBJECT-TYPE
    SYNTAX FrCirExtCompEntry
    ACCESS not-accessible
    STATUS mandatory
    DESCRIPTION ""
    INDEX { frCirExtCompIfIndex, frCirExtCompDlci }
    ::= { frCirExtCompTable 1 }

FrCirExtCompEntry ::= SEQUENCE {
    frCirExtCompIfIndex                         InterfaceIndex,
    frCirExtCompDlci                            DLCI,
    frCirExtCompLogicalIfIndex                  InterfaceIndex,
    frCirExtCompEnabled                         INTEGER,
    frCirExtCompNegotiated                      INTEGER,
    frCirExtCompDecoderBytesIn                  Counter,
    frCirExtCompDecoderDecompBytesOut           Counter,
    frCirExtCompDecoderUncompBytesOut           Counter,
    frCirExtCompDecoderCompPacketsIn            Counter,
    frCirExtCompDecoderUncompPacketsIn           Counter,
    frCirExtCompDecoderDecompQueueLength        Counter,
    frCirExtCompDecoderCompressionRatio         Counter,
    frCirExtCompDecoderResetRequestTx           Counter,
    frCirExtCompDecoderResetAcksRx              Counter,
    frCirExtCompDecoderRxDiscarded              Counter,
    frCirExtCompDecoderState                    INTEGER,
    frCirExtCompEncoderBytesIn                  Counter,
    frCirExtCompEncoderCompBytesOut             Counter,
    frCirExtCompEncoderUncompBytesOut           Counter,
    frCirExtCompEncoderCompPacketsOut           Counter,
    frCirExtCompEncoderUncompPacketsOut         Counter,
    frCirExtCompEncoderCompQueueLength          Counter,
    frCirExtCompEncoderCompressionRation        Counter,
    frCirExtCompEncoderResetRequestRx           Counter,
    frCirExtCompEncoderResetAckTx               Counter,
    frCirExtCompEncoderTxDiscarded              Counter
}

frCirExtCompIfIndex OBJECT-TYPE
    SYNTAX  InterfaceIndex
    ACCESS  read-only
    STATUS  mandatory
    DESCRIPTION
           "The ifIndex Value of the ifEntry this  virtual
            circuit is layered onto."
    ::= { frCirExtCompEntry  1 }

frCirExtCompDlci OBJECT-TYPE
    SYNTAX  DLCI
    ACCESS  read-only
    STATUS  mandatory
    DESCRIPTION
           "The Data Link Connection Identifier  for  this
            virtual circuit."
    REFERENCE
           "Draft American National  Standard  T1.618-1991,
            Section 3.3.6"
    ::= { frCirExtCompEntry  2 }

frCirExtCompLogicalIfIndex OBJECT-TYPE
    SYNTAX  InterfaceIndex
    ACCESS  read-only
    STATUS  mandatory
    DESCRIPTION
       "Normally the same value as frDlcmiIfIndex, but
       different when an implementation associates a virtual
       ifEntry with a DLC or set of DLCs in order to associate
       higher layer objects such as the ipAddrEntry with a
       subset of the virtual circuits on a Frame Relay
       interface. The type of such ifEntries is defined by the
       higher layer object; for example, if PPP/Frame Relay is
       implemented, the ifType of this ifEntry would be PPP.
       If it is not so defined, as would be the case with an
       ipAddrEntry, it should be of type Other."
   ::= { frCirExtCompEntry 3 }

frCirExtCompEnabled OBJECT-TYPE
    SYNTAX INTEGER {
        no(1),
        yes(2)
        }
    ACCESS read-only
    STATUS mandatory
    DESCRIPTION "Encryption enabled on link."
    ::= { frCirExtCompEntry 4 }

frCirExtCompNegotiated OBJECT-TYPE
    SYNTAX INTEGER {
        no(1),
        yes(2)
        }
    ACCESS read-only
    STATUS mandatory
    DESCRIPTION "Encryption negotiated on link."
    ::= { frCirExtCompEntry 5 }

frCirExtCompDecoderBytesIn OBJECT-TYPE
    SYNTAX Counter
    ACCESS read-only
    STATUS mandatory
    DESCRIPTION "Total number of bytes received by the decoder."
    ::= { frCirExtCompEntry 6 }

frCirExtCompDecoderDecompBytesOut OBJECT-TYPE
    SYNTAX Counter
    ACCESS read-only
    STATUS mandatory
    DESCRIPTION "Decompressed bytes from the decoder."
    ::= { frCirExtCompEntry 7 }

frCirExtCompDecoderUncompBytesOut OBJECT-TYPE
    SYNTAX Counter
    ACCESS read-only
    STATUS mandatory
    DESCRIPTION "Uncompressed bytes received by the decoder."
    ::= { frCirExtCompEntry 8 }

frCirExtCompDecoderCompPacketsIn OBJECT-TYPE
    SYNTAX Counter
    ACCESS read-only
    STATUS mandatory
    DESCRIPTION "Compressed packets received by the decoder."
    ::= { frCirExtCompEntry 9 }

frCirExtCompDecoderUncompPacketsIn OBJECT-TYPE
    SYNTAX Counter
    ACCESS read-only
    STATUS mandatory
    DESCRIPTION "Uncompressed packets received by the decoder."
    ::= { frCirExtCompEntry 10 }

frCirExtCompDecoderDecompQueueLength OBJECT-TYPE
    SYNTAX Counter
    ACCESS read-only
    STATUS mandatory
    DESCRIPTION "Number of packets waiting to be decompressed."
    ::= { frCirExtCompEntry 11 }

frCirExtCompDecoderCompressionRatio OBJECT-TYPE
    SYNTAX Counter
    ACCESS read-only
    STATUS mandatory
    DESCRIPTION "Receive compression ratio (multiplied by 100)."
    ::= { frCirExtCompEntry 12 }

frCirExtCompDecoderResetRequestTx OBJECT-TYPE
    SYNTAX Counter
    ACCESS read-only
    STATUS mandatory
    DESCRIPTION "The number of times the decoder requested
    re-initialization of the compression history."
    ::= { frCirExtCompEntry 13 }

frCirExtCompDecoderResetAcksRx OBJECT-TYPE
    SYNTAX Counter
    ACCESS read-only
    STATUS mandatory
    DESCRIPTION "The number of acknowledgments to reset requests received
    by the router."
    ::= { frCirExtCompEntry 14 }

frCirExtCompDecoderRxDiscarded OBJECT-TYPE
    SYNTAX Counter
    ACCESS read-only
    STATUS mandatory
    DESCRIPTION "Number of packets discarded by the decoder due to buffer
    lacks or synchronisation problems."
    ::= { frCirExtCompEntry 15 }

frCirExtCompDecoderState OBJECT-TYPE
    SYNTAX INTEGER {
        ok(1),
        error(2)
        }
    ACCESS read-only
    STATUS mandatory
    DESCRIPTION "State of decoder.
                 Error state means waiting for reset acknowledgment"
    ::= { frCirExtCompEntry 16 }

frCirExtCompEncoderBytesIn OBJECT-TYPE
    SYNTAX Counter
    ACCESS read-only
    STATUS mandatory
    DESCRIPTION "Total number of bytes received by the encoder."
    ::= { frCirExtCompEntry 17 }

frCirExtCompEncoderCompBytesOut OBJECT-TYPE
    SYNTAX Counter
    ACCESS read-only
    STATUS mandatory
    DESCRIPTION "Number of compressed bytes leaving the encoder."
    ::= { frCirExtCompEntry 18 }

frCirExtCompEncoderUncompBytesOut OBJECT-TYPE
    SYNTAX Counter
    ACCESS read-only
    STATUS mandatory
    DESCRIPTION "Number of uncompressed bytes leaving the encoder."
    ::= { frCirExtCompEntry 19 }

frCirExtCompEncoderCompPacketsOut OBJECT-TYPE
    SYNTAX Counter
    ACCESS read-only
    STATUS mandatory
    DESCRIPTION "Number of compressed packets leaving the encoder."
    ::= { frCirExtCompEntry 20 }

frCirExtCompEncoderUncompPacketsOut OBJECT-TYPE
    SYNTAX Counter
    ACCESS read-only
    STATUS mandatory
    DESCRIPTION "Number of uncompressed packets leaving the encoder."
    ::= { frCirExtCompEntry 21 }

frCirExtCompEncoderCompQueueLength OBJECT-TYPE
    SYNTAX Counter
    ACCESS read-only
    STATUS mandatory
    DESCRIPTION "Number of packets waiting to be compressed."
    ::= { frCirExtCompEntry 22 }

frCirExtCompEncoderCompressionRation OBJECT-TYPE
    SYNTAX Counter
    ACCESS read-only
    STATUS mandatory
    DESCRIPTION "Transmit compression ratio (multiplied by 100)."
    ::= { frCirExtCompEntry 23 }

frCirExtCompEncoderResetRequestRx OBJECT-TYPE
    SYNTAX Counter
    ACCESS read-only
    STATUS mandatory
    DESCRIPTION "The number of times the remote end requested
    re-initialization of the compression history."
    ::= { frCirExtCompEntry 24 }

frCirExtCompEncoderResetAckTx OBJECT-TYPE
    SYNTAX Counter
    ACCESS read-only
    STATUS mandatory
    DESCRIPTION "The number of acknowledgments to reset requests transmitted
    by the router."
    ::= { frCirExtCompEntry 25 }

frCirExtCompEncoderTxDiscarded OBJECT-TYPE
    SYNTAX Counter
    ACCESS read-only
    STATUS mandatory
    DESCRIPTION "Number of packets discarded by the encoder due to buffer
    lacks or transmit queue overflows."
    ::= { frCirExtCompEntry 26 }

END
