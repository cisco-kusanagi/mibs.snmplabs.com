CXMCPRT-MIB 

DEFINITIONS ::= BEGIN

IMPORTS
	Counter, TimeTicks      FROM RFC1155-SMI
	DisplayString           FROM RFC1213-MIB
	OBJECT-TYPE             FROM RFC-1212
	cxMc600                 FROM CXProduct-SMI;


--  cxMCPRT rev1.3 under modification


cxMcPrt   OBJECT IDENTIFIER ::= { cxMc600 1}
 

--  cxMcPrt GLOBAL CONFIGURATION GROUP.

cxMcPrtGlobal        OBJECT IDENTIFIER ::= { cxMcPrt 1}

cxMcPrtGlobalConsoleRate OBJECT-TYPE
	SYNTAX INTEGER (300..19200)
	ACCESS  read-write
	STATUS  optional
	DESCRIPTION
"The front panel console rate for the HC600.

Range of Values: 300-19 200

Default Value: 19 200"
	DEFVAL { 19200 }
	::= { cxMcPrtGlobal 1 }

cxMcPrtGlobalResetStat OBJECT-TYPE
	SYNTAX  INTEGER {
					no      (1),
					yes     (2)
				}
	ACCESS  read-write
	STATUS  optional
	DESCRIPTION
"Resets all statistics.

Options:
no(1)

yes (2)

Default Value: no (1)"
	DEFVAL { no }
	::= { cxMcPrtGlobal 2 }

cxMcPrtGlobalStationId OBJECT-TYPE
	SYNTAX  DisplayString (SIZE (0..12))
	ACCESS  read-write
	STATUS  optional
	DESCRIPTION
"The local station identification. No space allowed in write."
	DEFVAL { "           " }
	::= { cxMcPrtGlobal 3 }


--  cxMCPRT CONFIGURATION GROUP

cxMcPrtCfgTable OBJECT-TYPE
	SYNTAX  SEQUENCE OF CxMcPrtCfgEntry
	ACCESS  not-accessible
	STATUS  mandatory
	DESCRIPTION
"cx Port Station Configuration Table."
	::= { cxMcPrt 2 }


cxMcPrtCfgEntry OBJECT-TYPE
	SYNTAX  CxMcPrtCfgEntry
	ACCESS  not-accessible
	STATUS  mandatory
	DESCRIPTION
"cx Port Station Configuration Entry gives the state of the 
configuration associated to a particular port."
	INDEX { cxMcPrtCfgPortIndex }
	::= { cxMcPrtCfgTable 1 }

CxMcPrtCfgEntry ::=
	SEQUENCE {
		cxMcPrtCfgPortIndex       INTEGER, 
		cxMcPrtCfgDriverUsed      INTEGER,
		cxMcPrtCfgReinitPort      INTEGER,
		cxMcPrtCfgUpdated               INTEGER
	 }

		cxMcPrtCfgPortIndex       OBJECT-TYPE
			SYNTAX INTEGER (1..4)
			ACCESS  read-only
			STATUS  mandatory
			DESCRIPTION
"Identifies the port by a numerical value.

Range of Values: 1-4"
			::= { cxMcPrtCfgEntry 1 }

 
		cxMcPrtCfgDriverUsed      OBJECT-TYPE
			SYNTAX INTEGER 
			ACCESS  read-write
			STATUS  mandatory
			DESCRIPTION
"Specifies the port driver used. The driver is 
associated with a numerical value that identify one of the tables 
below the object identifier; cxMcPrtDriver for MC600, 
or cxMcPrtDriver for HC600 driver. Note that HC600 has only one driver.

Options:
bop(1): MC600 or HC600

asy(2): MC600 only

cop(3): MC600 only

bsy(4): MC600 only "
			::= { cxMcPrtCfgEntry 2 }

		cxMcPrtCfgReinitPort       OBJECT-TYPE
			SYNTAX INTEGER { no (1), yes (2) }
			ACCESS  read-write
			STATUS  optional
			DESCRIPTION
"Activate the planned configurations of the indexed port.

Options:
no (1)

yes (2)"
			::= { cxMcPrtCfgEntry 3 }

		cxMcPrtCfgUpdated OBJECT-TYPE
			SYNTAX INTEGER { no (1), yes (2) }
			ACCESS  read-only
			STATUS  mandatory
			DESCRIPTION
"The status of the configuration of a port.

Options:
no (1)

yes (2)"
			::= { cxMcPrtCfgEntry 4 }
 
--  cxMCPRT STATISTICS GROUP 

cxMcPrtStatTable OBJECT-TYPE
	SYNTAX  SEQUENCE OF CxMcPrtStatEntry
	ACCESS  not-accessible
	STATUS  mandatory
	DESCRIPTION
		"cx Port Station Statistic Table."
	::= { cxMcPrt 3 }


cxMcPrtStatEntry OBJECT-TYPE
	SYNTAX  CxMcPrtStatEntry
	ACCESS  not-accessible
	STATUS  mandatory
	DESCRIPTION
"cx Port Station Statistic Entry gives the state of the counters 
associated with a particular port."
	INDEX { cxMcPrtStatPortNumber }
	::= { cxMcPrtStatTable 1 }

CxMcPrtStatEntry ::=
	SEQUENCE {
		cxMcPrtStatPortNumber     INTEGER,
		cxMcPrtStatRts            INTEGER,
		cxMcPrtStatDtr            INTEGER,
		cxMcPrtStatDsr            INTEGER,
		cxMcPrtStatDcd            INTEGER,
		cxMcPrtStatCts            INTEGER,
		cxMcPrtStatCntMsgTx       Counter,
		cxMcPrtStatCntMsgRx       Counter,
		cxMcPrtStatCntReinit      Counter,
		cxMcPrtStatCntFlowCtrlTx        Counter,
		cxMcPrtStatCntFlowCtrlRx  Counter,
		cxMcPrtStatCntErrTx       Counter,
		cxMcPrtStatCntErrRx       Counter,
		cxMcPrtStatCntConnect     Counter,
		cxMcPrtStatCntChrDecomp   Counter,
		cxMcPrtStatCntChrComp     Counter,
		cxMcPrtStatCntBitDecomp   Counter,
		cxMcPrtStatCntBitComp     Counter,
		cxMcPrtStatStation        INTEGER,
		cxMcPrtStatRoute          INTEGER,
		cxMcPrtStatHwInterface    INTEGER,
		cxMcPrtStatTimeTicks      TimeTicks
	 }

		cxMcPrtStatPortNumber     OBJECT-TYPE
			SYNTAX INTEGER (1..4)
			ACCESS  read-only
			STATUS  mandatory
			DESCRIPTION
"Indicates the port number of the statistics.

Range of Values: 1-4"
			::= { cxMcPrtStatEntry 1 }

		cxMcPrtStatRts OBJECT-TYPE
			SYNTAX INTEGER { off (1), on (2) }
			ACCESS  read-only
			STATUS  mandatory
			DESCRIPTION
"Indicates the current state of the Request to Send signal. 

Options:
off (1)

on (2)"
			::= { cxMcPrtStatEntry 2 }

		cxMcPrtStatDtr OBJECT-TYPE
			SYNTAX INTEGER { off (1), on (2) }
			ACCESS  read-only
			STATUS  mandatory
			DESCRIPTION
"Indicates the current state of the Data Terminal Ready signal.

Options:
off (1)

on (2)"
			::= { cxMcPrtStatEntry 3 }

		cxMcPrtStatDsr OBJECT-TYPE
			SYNTAX INTEGER { off (1), on (2) }
			ACCESS  read-only
			STATUS  mandatory
			DESCRIPTION
"Indicates the current state of the Data Set Ready signal. 

Options:
off (1)

on (2)"
			::= { cxMcPrtStatEntry 4 }

		cxMcPrtStatDcd OBJECT-TYPE
			SYNTAX INTEGER { off (1), on (2) }
			ACCESS  read-only
			STATUS  mandatory
			DESCRIPTION
"Indicates the current state of the Data Carrier Detect signal. 

Options:
off (1)

on (2)"
			::= { cxMcPrtStatEntry 5 }

		cxMcPrtStatCts OBJECT-TYPE
			SYNTAX INTEGER { off (1), on (2) }
			ACCESS  read-only
			STATUS  mandatory
			DESCRIPTION
"Indicates the current state of the Clear to Send signal. 

Options:
off (1)

on (2)"
			::= { cxMcPrtStatEntry 6 }

		cxMcPrtStatCntMsgTx OBJECT-TYPE
			SYNTAX Counter
			ACCESS  read-only
			STATUS  mandatory
			DESCRIPTION
"Indicates the number of frames transmitted on the specified port."
			::= { cxMcPrtStatEntry 7 }

		cxMcPrtStatCntMsgRx OBJECT-TYPE
			SYNTAX Counter
			ACCESS  read-only
			STATUS  mandatory
			DESCRIPTION
"Indicates the number of frames received on the specified port."
			::= { cxMcPrtStatEntry 8 }

		cxMcPrtStatCntReinit OBJECT-TYPE
			SYNTAX Counter
			ACCESS  read-only
			STATUS  mandatory
			DESCRIPTION
"Indicates the number of times that the specified port has reinitialized."
			::= { cxMcPrtStatEntry 9 }

		cxMcPrtStatCntFlowCtrlTx OBJECT-TYPE
			SYNTAX Counter
			ACCESS  read-only
			STATUS  mandatory
			DESCRIPTION
"Indicates the number of times that the specified port has performed 
output flow control."
			::= { cxMcPrtStatEntry 10 }

		cxMcPrtStatCntFlowCtrlRx OBJECT-TYPE
			SYNTAX Counter
			ACCESS  read-only
			STATUS  mandatory
			DESCRIPTION
"Indicates the number of times that the specified port has performed 
input flow control."
			::= { cxMcPrtStatEntry 11 }

		cxMcPrtStatCntErrTx OBJECT-TYPE
			SYNTAX Counter
			ACCESS  read-only
			STATUS  mandatory
			DESCRIPTION
"Indicates the number of bad frames transmitted on the specified port."
			::= { cxMcPrtStatEntry 12 }

		cxMcPrtStatCntErrRx OBJECT-TYPE
			SYNTAX Counter
			ACCESS  read-only
			STATUS  mandatory
			DESCRIPTION
"Indicates the number of bad frames received on the specified port."
::= { cxMcPrtStatEntry 13 }

		cxMcPrtStatCntConnect OBJECT-TYPE
			SYNTAX Counter
			ACCESS  read-only
			STATUS  mandatory
			DESCRIPTION
"Indicates the number of connections for the specified port.

The number of connections is equal to the number of times that the DTR 
modem signal changed from OFF to ON."
			::= { cxMcPrtStatEntry 14 }

		cxMcPrtStatCntChrDecomp OBJECT-TYPE
			SYNTAX Counter
			ACCESS  read-only
			STATUS  mandatory
			DESCRIPTION
"Indicates the number of characters transmitted on the port."
			::= { cxMcPrtStatEntry 15 }

		cxMcPrtStatCntChrComp OBJECT-TYPE
			SYNTAX Counter
			ACCESS  read-only
			STATUS  mandatory
			DESCRIPTION
"Indicates the number of characters received on the port."
			::= { cxMcPrtStatEntry 16 }

		cxMcPrtStatCntBitDecomp OBJECT-TYPE
			SYNTAX Counter
			ACCESS  read-only
			STATUS  mandatory
			DESCRIPTION
"Indicates the number of bits transmitted on the port."
			::= { cxMcPrtStatEntry 17 }

		cxMcPrtStatCntBitComp      OBJECT-TYPE
			SYNTAX Counter
			ACCESS  read-only
			STATUS  mandatory
			DESCRIPTION
"Indicates the number of bits received on the port."
			::= { cxMcPrtStatEntry 18 }

		cxMcPrtStatStation OBJECT-TYPE
			SYNTAX INTEGER (1..16)
			ACCESS  read-only
			STATUS  mandatory
			DESCRIPTION
"Indicates the station that the port is using to transmit and receive 
data."
			::= { cxMcPrtStatEntry 19 }

		cxMcPrtStatRoute OBJECT-TYPE
			SYNTAX INTEGER (1..64)
			ACCESS  read-only
			STATUS  mandatory
			DESCRIPTION
"Indicates the route of the station that the port is using."
			::= { cxMcPrtStatEntry 20 }

		cxMcPrtStatHwInterface OBJECT-TYPE
			SYNTAX INTEGER { dce(1), dte(2) }
			ACCESS  read-only
			STATUS  mandatory
			DESCRIPTION
"Indicates whether the hardware port interface is DCE or DTE. The value 
depends on the I/O hardware.

Options:
dce (1)

dte (2)"
			::= { cxMcPrtStatEntry 21 }

		cxMcPrtStatTimeTicks OBJECT-TYPE
			SYNTAX TimeTicks
			ACCESS  read-only
			STATUS  mandatory
			DESCRIPTION
"Indicates the number of milliseconds since the last reset for the current station."
			::= { cxMcPrtStatEntry 22 }
 
--  cxMCPRT PATH GROUP

cxMcPrtPath      OBJECT IDENTIFIER       ::= { cxMcPrt 4 }

cxMcPrtPathStationPri                    OBJECT-TYPE
	SYNTAX INTEGER (1..16)
	ACCESS  read-write
	STATUS  mandatory
	DESCRIPTION
"The primary port station.

Range of Values: 1-16

Default Value: 1"
	DEFVAL { 1 }
	::= { cxMcPrtPath 1 }

cxMcPrtPathRoutePri                           OBJECT-TYPE
	SYNTAX INTEGER (1..64)
	ACCESS  read-write
	STATUS  mandatory
	DESCRIPTION
"The primary route.

Range of Values: 1-64

Default Value: 1"
	DEFVAL { 1 }
	::= { cxMcPrtPath 2 }

cxMcPrtPathStationScd                    OBJECT-TYPE
	SYNTAX INTEGER (1..16)
	ACCESS  read-write
	STATUS  mandatory
	DESCRIPTION
"The secondary port station.

Range of Values: 1-16

Default Value: 2"
	DEFVAL { 2 }
	::= { cxMcPrtPath 3 }

cxMcPrtPathRouteScd                   OBJECT-TYPE
	SYNTAX INTEGER (1..64)
	ACCESS  read-write
	STATUS  mandatory
	DESCRIPTION
"The secondary route.

Range of Values: 1-64

Default Value: 2"
	DEFVAL { 2 }
	::= { cxMcPrtPath 4 }


--  cxMCPRT DRIVERS  

cxMcPrtDriver     OBJECT IDENTIFIER       ::= { cxMcPrt 5 }


--  cxMCPRT MC600 & HC600 BOP DRIVER GROUP 

cxMcPrtBopTable OBJECT-TYPE
	SYNTAX  SEQUENCE OF CxMcPrtBopEntry
	ACCESS  not-accessible
	STATUS  mandatory
	DESCRIPTION
"cx Port Station MC600 & HC600 Bop Driver Table."
	::= { cxMcPrtDriver 1 }

cxMcPrtBopEntry OBJECT-TYPE
	SYNTAX  CxMcPrtBopEntry
	ACCESS  not-accessible
	STATUS  mandatory
	DESCRIPTION
"cx Port Station MC600 & HC600 Bop Driver Entry gives the state of 
the variables associated to the Bit Oriented Protocol."
	INDEX { cxMcPrtBopPortUsed }
	::= { cxMcPrtBopTable 1 }

CxMcPrtBopEntry ::=
	SEQUENCE {
		cxMcPrtBopPortUsed                INTEGER,
		cxMcPrtBopPortStatus              INTEGER,
		cxMcPrtBopComRate                 INTEGER,
		cxMcPrtBopUseLnkErrPassthro       INTEGER,
		cxMcPrtBopInterface               INTEGER,
		cxMcPrtBopRtsDcdModemCtrl         INTEGER,
		cxMcPrtBopUseRtsDcdCndDataTx      INTEGER,
		cxMcPrtBopUseRtsDcdCndLnk         INTEGER,
		cxMcPrtBopUseRtsDcdCndRem         INTEGER,
		cxMcPrtBopDtrCtsModemCtrl         INTEGER,
		cxMcPrtBopUseDtrCtsCndRts         INTEGER,
		cxMcPrtBopUseDtrCtsCndLnk         INTEGER,
		cxMcPrtBopUseDtrCtsCndRem         INTEGER,
		cxMcPrtBopLimitBeforeOut          INTEGER,
		cxMcPrtBopUseOutCndCtsDtrOn       INTEGER,
		cxMcPrtBopUseInCndDcdRtsOn        INTEGER,
		cxMcPrtBopSyncMode                INTEGER,
		cxMcPrtBopDataLifetime            INTEGER,
		cxMcPrtBopUseClockSync            INTEGER,
		cxMcPrtBopUseFlowCtrlClock        INTEGER,
		cxMcPrtBopFlowCtrlRate            INTEGER,
		cxMcPrtBopLimitOutFlowCtrl        INTEGER,
		cxMcPrtBopLimitInFlowCtrl         INTEGER,
		cxMcPrtBopCoding                  INTEGER,
		cxMcPrtBopOutIdleState            INTEGER,
		cxMcPrtBopDelayBeforeIdle         INTEGER,
		cxMcPrtBopOutPreambleLng          INTEGER
	 }

cxMcPrtBopPortUsed                        OBJECT-TYPE
	SYNTAX INTEGER (1..4)
	ACCESS  read-only
	STATUS  mandatory
	DESCRIPTION
	"Indicates the current port number that is used by the BOP driver.

Range of Values: 1-4"
	::= { cxMcPrtBopEntry 1 }

cxMcPrtBopPortStatus                      OBJECT-TYPE
	SYNTAX  INTEGER { 
				disable (1),
				enable (2)
			}
	ACCESS  read-write
	STATUS  mandatory
	DESCRIPTION
"Indicates whether the port is enabled or disabled.

Options:
disable (1)

enable (2)

Default Value: disable (1)"
	DEFVAL { disable }
	::= { cxMcPrtBopEntry 2 }

cxMcPrtBopComRate                 OBJECT-TYPE
	SYNTAX INTEGER 
	ACCESS  read-write
	STATUS  mandatory
	DESCRIPTION
"Indicates the port communication rates.

Range of Values:
HC600: 9600-2048000

MC600: 110-128000

Default Value: HC600: 56 000, MC600: 9600"

::= { cxMcPrtBopEntry 3 }

cxMcPrtBopUseLnkErrPassthro               OBJECT-TYPE
	SYNTAX INTEGER { no (1), yes (2) }
	ACCESS  read-write
	STATUS  mandatory
	DESCRIPTION
"Indicates the link error passthrough state on the port.

Options:
no (1)

yes (2)

Default Value: yes (2)"
	DEFVAL { yes }
	::= { cxMcPrtBopEntry 4 }

cxMcPrtBopInterface                       OBJECT-TYPE
	SYNTAX INTEGER { dce (1), dte (2) }
	ACCESS  read-write
	STATUS  mandatory
	DESCRIPTION
"Indicates whether the port interface is DTE or DCE.

Options:
dce (1)

dte (2)

Default Value: dce (1)"
	DEFVAL { dce }
	::= { cxMcPrtBopEntry 5 }

cxMcPrtBopRtsDcdModemCtrl         OBJECT-TYPE
	SYNTAX INTEGER { on (1), vary (2) }
	ACCESS  read-write
	STATUS  mandatory
	DESCRIPTION
"Use the RTS or DCD modem control on the port.

Options:
on (1)

vary (2)

Default Value: on (1)"
	DEFVAL { on }
	::= { cxMcPrtBopEntry 6 }

cxMcPrtBopUseRtsDcdCndDataTx      OBJECT-TYPE
	SYNTAX INTEGER { no (1), yes (2) }
	ACCESS  read-write
	STATUS  mandatory
	DESCRIPTION
"Use the state of the RTS or DCD modem control when the port 
selected is conditioned by the presence of data in output queue.

Options:
no (1)

yes (2)

Default Value: no (1)"
	DEFVAL { no }
	::= { cxMcPrtBopEntry 7 }

cxMcPrtBopUseRtsDcdCndLnk         OBJECT-TYPE
	SYNTAX INTEGER { no (1), yes (2) }
	ACCESS  read-write
	STATUS  mandatory
	DESCRIPTION
"Use the state of the RTS or DCD modem control when the port
 selected is conditioned by the main link status.

Options:
no (1)

yes (2)

Default Value: yes (2)"
	DEFVAL { yes }
	::= { cxMcPrtBopEntry 8 }

cxMcPrtBopUseRtsDcdCndRem         OBJECT-TYPE
	SYNTAX INTEGER { no (1), yes (2) }
	ACCESS  read-write
	STATUS  mandatory
	DESCRIPTION
"Use the state of the RTS or DCD modem control when the port 
selected is conditioned by the remote DCD or RTS.

Options:
no (1)

yes (2)

Default Value: yes (2)"
	DEFVAL { yes }
	::= { cxMcPrtBopEntry 9 }

cxMcPrtBopDtrCtsModemCtrl         OBJECT-TYPE
	SYNTAX INTEGER { on (1), vary (2) }
	ACCESS  read-write
	STATUS  mandatory
	DESCRIPTION
"Use the DTR or CTS modem control on the port.

Options:
on (1)

vary (2)

Default Value: on (1)"
DEFVAL { on }
	::= { cxMcPrtBopEntry 10 }

cxMcPrtBopUseDtrCtsCndRts         OBJECT-TYPE
	SYNTAX INTEGER { no (1), yes (2) }
	ACCESS  read-write
	STATUS  mandatory
	DESCRIPTION
"Use the state of the CTS modem control when the port
 selected is conditioned by the local RTS.

Options:
no (1)

yes (2)

Default Value: no (1)"
	DEFVAL { no }
	::= { cxMcPrtBopEntry 11 }

cxMcPrtBopUseDtrCtsCndLnk         OBJECT-TYPE
	SYNTAX INTEGER { no (1), yes (2) }
	ACCESS  read-write
	STATUS  mandatory
	DESCRIPTION
"Use the state of the RTS or DCD modem control when the port
 selected is conditioned by the main link status.

Options:
no (1)

yes (2)

Default Value: yes (2)"
	DEFVAL { yes }
	::= { cxMcPrtBopEntry 12 }

cxMcPrtBopUseDtrCtsCndRem         OBJECT-TYPE
	SYNTAX INTEGER { no (1), yes (2) }
	ACCESS  read-write
	STATUS  mandatory
	DESCRIPTION
"Use the state of the RTS or DCD modem control when the port 
selected is conditioned by the remote DCD or RTS.

Options:
no (1)

yes (2)

Default Value: yes (2)"
	DEFVAL { yes }
	::= { cxMcPrtBopEntry 13 }

cxMcPrtBopLimitBeforeOut          OBJECT-TYPE
	SYNTAX INTEGER 
	ACCESS  read-write
	STATUS  mandatory
	DESCRIPTION
"The limit before activation of output for the port.

Range of Values: HC600: 2-100, MC600: 5-4000

Default Value:  HC600: 5, MC600: 15"

	::= { cxMcPrtBopEntry 14 }

cxMcPrtBopUseOutCndCtsDtrOn       OBJECT-TYPE
	SYNTAX INTEGER { no (1), yes (2) }
	ACCESS  read-write
	STATUS  mandatory
	DESCRIPTION
"Use the output enable on CTS or DTR modem control for the port.

Options:
no(1)

yes (2)

Default Value: no (1)"
	DEFVAL { no }
	::= { cxMcPrtBopEntry 15 }

cxMcPrtBopUseInCndDcdRtsOn        OBJECT-TYPE
	SYNTAX INTEGER { no (1), yes (2) }
	ACCESS  read-write
	STATUS  mandatory
	DESCRIPTION
"Use the input enable on DCD or RTS modem control for the port.

Options:
no(1)

yes (2)

Default Value: no (1)"
	DEFVAL { no }
	::= { cxMcPrtBopEntry 16 }

cxMcPrtBopSyncMode                        OBJECT-TYPE
	SYNTAX INTEGER { normal (1), extern (2) }
	ACCESS  read-write
	STATUS  mandatory
	DESCRIPTION
"The clock synchronization for the port.

Options:
normal (1)

extern (2)

Default Value: normal (1)"
	DEFVAL { normal }
	::= { cxMcPrtBopEntry 17 }

cxMcPrtBopDataLifetime            OBJECT-TYPE
	SYNTAX INTEGER (1..60000)
	ACCESS  read-write
	STATUS  mandatory
	DESCRIPTION
"The data lifetime in millisecond for the port.

Range of Values: 1-60000

Default Value: 2000"
	DEFVAL { 2000 }
	::= { cxMcPrtBopEntry 18 }

cxMcPrtBopUseClockSync            OBJECT-TYPE
	SYNTAX INTEGER { no (1), yes (2) }
	ACCESS  read-write
	STATUS  mandatory
	DESCRIPTION
"The clocks synchronization on the port.

Options:
no(1)

yes (2)

Default Value: no (1)"
	DEFVAL { no }
	::= { cxMcPrtBopEntry 19 }

cxMcPrtBopUseFlowCtrlClock                OBJECT-TYPE
	SYNTAX INTEGER { no (1), yes (2) }
	ACCESS  read-write
	STATUS  mandatory
	DESCRIPTION
"Use the flow control by clocks for the synchronous port.

Options:
no(1)

yes (2)

Default Value: yes (2)"
	DEFVAL { yes }
	::= { cxMcPrtBopEntry 20 }

cxMcPrtBopFlowCtrlRate            OBJECT-TYPE
	SYNTAX INTEGER 
	ACCESS  read-write
	STATUS  mandatory
	DESCRIPTION
"The flow control rate of the synchronous port.

Range of Values: HC600: 300-5609, MC600: 110-9600

Default Value: HC600: 2400. MC600: 300

   HC600 DEFVAL { 2400 }
	MC600  DEFVAL { 300 }"
	::= { cxMcPrtBopEntry 21 }

cxMcPrtBopLimitOutFlowCtrl                OBJECT-TYPE
	SYNTAX INTEGER 
	ACCESS  read-write
	STATUS  mandatory
	DESCRIPTION
"The limit before output flow control of the synchronous port.

Range of Values: HC600: 1-100, MC600: 0-4000

Default Value: HC600: 15, MC600: 3
"
	::= { cxMcPrtBopEntry 22 }

cxMcPrtBopLimitInFlowCtrl         OBJECT-TYPE
	SYNTAX INTEGER 
	ACCESS  read-write
	STATUS  mandatory
	DESCRIPTION
"The overflow limit before input flow control of the synchronous port.

Ranges of Values: HC600: 1-100, MC600: 0-4000

Default Value: HC600: 32, MC600: 512"
	::= { cxMcPrtBopEntry 23 }

cxMcPrtBopCoding                  OBJECT-TYPE
	SYNTAX INTEGER { nrz (1), nrzi (2) }
	ACCESS  read-write
	STATUS  mandatory
	DESCRIPTION
"The coding on the port for bit-oriented protocols.

Options:
nrz (1)

nrzi (2)

Default Value: nrz (1)"
	DEFVAL { nrz }
	::= { cxMcPrtBopEntry 24 }

cxMcPrtBopOutIdleState                    OBJECT-TYPE
	SYNTAX INTEGER { flag (1), mark (2) }
	ACCESS  read-write
	STATUS  mandatory
	DESCRIPTION
"The output idle state of the synchronous port.

Options:
flag (1)

mark (2)

Default Value: flag (1)"
	DEFVAL { flag }
	::= { cxMcPrtBopEntry 25 }

cxMcPrtBopDelayBeforeIdle         OBJECT-TYPE
	SYNTAX INTEGER (0..2000)
	ACCESS  read-write
	STATUS  mandatory
	DESCRIPTION
"The delay between frames before idle for the port.

Range of Values: 0-2000

Default Value: 0"
	DEFVAL { 0 }
	::= { cxMcPrtBopEntry 26 }

cxMcPrtBopOutPreambleLng          OBJECT-TYPE
	SYNTAX INTEGER 
	ACCESS  read-write
	STATUS  mandatory
	DESCRIPTION
"The output preamble length of the synchronous port.

Options:
zero (1): HC600 or MC600

one (2): HC600 only

two (3): HC600 only

four (4): HC600 only

eight (5): HC600 only

Default Value: zero (1)"
	::= { cxMcPrtBopEntry 27 }

--  cxMCPRT MC600 ASY DRIVER GROUP 

cxMcPrtAsyTable OBJECT-TYPE
	SYNTAX  SEQUENCE OF CxMcPrtAsyEntry
	ACCESS  not-accessible
	STATUS  mandatory
DESCRIPTION
		"cx Port Station MC600 Asy Driver Table."
	::= { cxMcPrtDriver 2 }


cxMcPrtAsyEntry OBJECT-TYPE
	SYNTAX  CxMcPrtAsyEntry
	ACCESS  not-accessible
	STATUS  mandatory
	DESCRIPTION
"cx Port Station MC600 Asy Driver Entry gives the state of the variables 
associated 
		to the Asynchronous Protocol."
	INDEX { cxMcPrtAsyPortUsed }
	::= { cxMcPrtAsyTable 1 }

CxMcPrtAsyEntry ::=
	SEQUENCE {
		cxMcPrtAsyPortUsed                INTEGER,
		cxMcPrtAsyPortStatus              INTEGER,
		cxMcPrtAsyComRate                 INTEGER,
		cxMcPrtAsyUseLnkErrPassthro       INTEGER,
		cxMcPrtAsyInterface               INTEGER,
		cxMcPrtAsyRtsDcdModemCtrl         INTEGER,
		cxMcPrtAsyUseRtsDcdCndDataTx      INTEGER,
		cxMcPrtAsyUseRtsDcdCndLnk         INTEGER,
		cxMcPrtAsyUseRtsDcdCndRem         INTEGER,
		cxMcPrtAsyDtrCtsModemCtrl         INTEGER,
		cxMcPrtAsyUseDtrCtsCndRts         INTEGER,
		cxMcPrtAsyUseDtrCtsCndLnk         INTEGER,
		cxMcPrtAsyUseDtrCtsCndRem         INTEGER,
		cxMcPrtAsyLimitBeforeOut          INTEGER,
		cxMcPrtAsyOutCndCtsDtrOn          INTEGER,
		cxMcPrtAsyInCndDcdRtsOn           INTEGER,
		cxMcPrtAsySyncMode                INTEGER,
		cxMcPrtAsyUseDataLifeLimited      INTEGER,
		cxMcPrtAsyDataLifetime            INTEGER,
		cxMcPrtAsyOutFlowCtrl             INTEGER,
		cxMcPrtAsyInFlowCtrl              INTEGER,
		cxMcPrtAsyXonChr                  INTEGER,
		cxMcPrtAsyXoffChr                 INTEGER,
		cxMcPrtAsyNbBitPerChr             INTEGER,
		cxMcPrtAsyParity                  INTEGER,
		cxMcPrtAsyNbStopBit               INTEGER,
		cxMcPrtAsyUseFlushOutChr          INTEGER,
		cxMcPrtAsyFlushOutChr             INTEGER
	 }

cxMcPrtAsyPortUsed                OBJECT-TYPE
	SYNTAX INTEGER
	ACCESS  read-only
	STATUS  mandatory
DESCRIPTION
	"The current port number that is used by the ASY driver."
	::= { cxMcPrtAsyEntry 1 }

cxMcPrtAsyPortStatus              OBJECT-TYPE
	SYNTAX  INTEGER { 
				disable (1),
				enable (2)
			 }
	ACCESS  read-write
	STATUS  mandatory
	DESCRIPTION
"The port status for enabling or disabling the port.

Options:
disable (1)

enable (2)

Default Value: disable (1)"
	DEFVAL { disable }
	::= { cxMcPrtAsyEntry 2 }

cxMcPrtAsyComRate         OBJECT-TYPE
	SYNTAX INTEGER (110..128000)
	ACCESS  read-write
	STATUS  mandatory
	DESCRIPTION
"The port communication rates.

Range of Values: 110-128000

Default Value: 9600"
	DEFVAL { 9600 }
	::= { cxMcPrtAsyEntry 3 }

cxMcPrtAsyUseLnkErrPassthro               OBJECT-TYPE
	SYNTAX INTEGER { no (1), yes (2) }
	ACCESS  read-write
	STATUS  mandatory
	DESCRIPTION
"Use the link error pass through on the port.

Options:
no (1)

yes (2)

Default Value: yes (2)"
	DEFVAL { yes }
	::= { cxMcPrtAsyEntry 4 }

cxMcPrtAsyInterface               OBJECT-TYPE
	SYNTAX INTEGER { dce (1), dte (2) }
	ACCESS  read-write
	STATUS  mandatory
	DESCRIPTION
"The port interface to DTE or DCE.

Options:
dce (1)

dte (2)

Default Value: dce (1)"
	DEFVAL { dce }
	::= { cxMcPrtAsyEntry 5 }

cxMcPrtAsyRtsDcdModemCtrl         OBJECT-TYPE
	SYNTAX INTEGER { on (1), vary (2) }
	ACCESS  read-write
	STATUS  mandatory
	DESCRIPTION
"Use the RTS or DCD modem control on the port.

Options:
on (1)

vary (2)

Default Value: on (1)"
	DEFVAL { on }
	::= { cxMcPrtAsyEntry 6 }

cxMcPrtAsyUseRtsDcdCndDataTx              OBJECT-TYPE
	SYNTAX INTEGER { no (1), yes (2) }
	ACCESS  read-write
	STATUS  mandatory
	DESCRIPTION
"Use the state of the RTS or DCD modem control when the port 
selected is conditioned by the presence of data in output queue.

Options:
no (1)

yes (2)

Default Value: no (1)"
	DEFVAL { no }
	::= { cxMcPrtAsyEntry 7 }

cxMcPrtAsyUseRtsDcdCndLnk         OBJECT-TYPE
	SYNTAX INTEGER { no (1), yes (2) }
	ACCESS  read-write
	STATUS  mandatory
	DESCRIPTION
"Use the state of the RTS or DCD modem control when the port 
selected is conditioned by the main link status.

Options:
no (1)

yes (2)

Default Value: yes (2)"
	DEFVAL { yes }
	::= { cxMcPrtAsyEntry 8 }

cxMcPrtAsyUseRtsDcdCndRem         OBJECT-TYPE
	SYNTAX INTEGER { no (1), yes (2) }
	ACCESS  read-write
	STATUS  mandatory
	DESCRIPTION
"Use the state of the RTS or DCD modem control when the port 
selected is conditioned by the remote DCD or RTS.

Options:
no (1)

yes (2)

Default Value: yes (2)"
	DEFVAL { yes }
	::= { cxMcPrtAsyEntry 9 }

cxMcPrtAsyDtrCtsModemCtrl         OBJECT-TYPE
	SYNTAX INTEGER { on (1), vary (2) }
	ACCESS  read-write
	STATUS  mandatory
	DESCRIPTION
"Use the DTR or CTS modem control on the port.

Options:
on (1)

vary (2)

Default Value: on (1)"
	DEFVAL { on }
	::= { cxMcPrtAsyEntry 10 }

cxMcPrtAsyUseDtrCtsCndRts         OBJECT-TYPE
	SYNTAX INTEGER { no (1), yes (2) }
	ACCESS  read-write
	STATUS  mandatory
	DESCRIPTION
"Use the state of the CTS modem control when the port 
selected is conditioned by the local RTS.

Options:
no (1)

yes (2)

Default Value: no (1)"
	DEFVAL { no }
	::= { cxMcPrtAsyEntry 11 }

cxMcPrtAsyUseDtrCtsCndLnk         OBJECT-TYPE
	SYNTAX INTEGER { no (1), yes (2) }
	ACCESS  read-write
	STATUS  mandatory
	DESCRIPTION
"Use the state of the RTS or DCD modem control when the port 
selected is conditioned by the main link status.

Options:
no (1)

yes (2)

Default Value: yes (2)"
	DEFVAL { yes }
	::= { cxMcPrtAsyEntry 12 }

cxMcPrtAsyUseDtrCtsCndRem         OBJECT-TYPE
	SYNTAX INTEGER { no (1), yes (2) }
	ACCESS  read-write
	STATUS  mandatory
	DESCRIPTION
"Use the state of the RTS or DCD modem control when the port 
selected is conditioned by the remote DCD or RTS.

Options:
no (1)

yes (2)

Default Value: yes (2)"
	DEFVAL { yes }
	::= { cxMcPrtAsyEntry 13 }

cxMcPrtAsyLimitBeforeOut          OBJECT-TYPE
	SYNTAX INTEGER (1..100)
	ACCESS  read-write
	STATUS  mandatory
	DESCRIPTION
"The limit before activation of output for the port.

Range of Values: 1-100

Default Value: 15"
	DEFVAL { 15 }
	::= { cxMcPrtAsyEntry 14 }

cxMcPrtAsyOutCndCtsDtrOn               OBJECT-TYPE
	SYNTAX INTEGER { no (1), yes (2) }
	ACCESS  read-write
	STATUS  mandatory
	DESCRIPTION
"Use the output enable on CTS or DTR modem control for the port.

Options:
no (1)

yes (2)

Default Value: no (1)"
	DEFVAL { no }
	::= { cxMcPrtAsyEntry 15 }

cxMcPrtAsyInCndDcdRtsOn                OBJECT-TYPE
	SYNTAX INTEGER { no (1), yes (2) }
	ACCESS  read-write
	STATUS  mandatory
	DESCRIPTION
"Use the input enable on DCD or RTS modem control for the port.

Options:
no (1)

yes (2)

Default Value: no (1)"
	DEFVAL { no }
	::= { cxMcPrtAsyEntry 16 }

cxMcPrtAsySyncMode                OBJECT-TYPE
	SYNTAX INTEGER { normal (1), extern (2) }
	ACCESS  read-write
	STATUS  mandatory
	DESCRIPTION
"The clock synchronization for the port.

Options:
normal (1)

extern (2)

Default Value: normal (1)"
	DEFVAL { normal }
	::= { cxMcPrtAsyEntry 17 }

cxMcPrtAsyUseDataLifeLimited              OBJECT-TYPE
	SYNTAX INTEGER { no (1), yes (2) }
	ACCESS  read-write
	STATUS  mandatory
	DESCRIPTION
"Use the data lifetime limited on the asynchronous port.

Options:
no (1)

yes (2)

Default Value: no (1)"
	DEFVAL { no }
	::= { cxMcPrtAsyEntry 18 }

cxMcPrtAsyDataLifetime            OBJECT-TYPE
	SYNTAX INTEGER (1..60000)
	ACCESS  read-write
	STATUS  mandatory
	DESCRIPTION
"The data lifetime in milliseconds for the port.

Range of Values: 1-60000

Default Value: 2000"
	DEFVAL { 2000 }
	::= { cxMcPrtAsyEntry 19 }

cxMcPrtAsyOutFlowCtrl             OBJECT-TYPE
	SYNTAX INTEGER { disable (1), xonxoff (2), ctsdtr(3) }
	ACCESS  read-write
	STATUS  mandatory
	DESCRIPTION
"The output flow control of the asynchronous port.

Options:
disable (1)

xonxoff (2)

ctsdtr (3)

Default Value: xonxoff (2)"
	DEFVAL { xonxoff }
	::= { cxMcPrtAsyEntry 20 }

cxMcPrtAsyInFlowCtrl              OBJECT-TYPE
	SYNTAX INTEGER { disable (1), xonxoff (2), ctsdtr(3) }
	ACCESS  read-write
	STATUS  mandatory
	DESCRIPTION
"The input flow control of the asynchronous port.

Options:
disable (1)

xonxoff (2)

ctsdtr (3)

Default Value: xonxoff (2)"
	DEFVAL { xonxoff }
	::= { cxMcPrtAsyEntry 21 }

cxMcPrtAsyXonChr          OBJECT-TYPE
	SYNTAX INTEGER (0..255)
	ACCESS  read-write
	STATUS  mandatory
	DESCRIPTION
"The XON character value of the asynchronous port.

Range of Values: 0-255
Default Value: 17
"
	DEFVAL { 17 }
	::= { cxMcPrtAsyEntry 22 }
cxMcPrtAsyXoffChr         OBJECT-TYPE
	SYNTAX INTEGER (0..255)
	ACCESS  read-write
	STATUS  mandatory
	DESCRIPTION
"The XOFF character value of the asynchronous port.

Range of Values: 0-255

Default Value: 19"
	DEFVAL { 19 }
	::= { cxMcPrtAsyEntry 23 }

cxMcPrtAsyNbBitPerChr             OBJECT-TYPE
	SYNTAX INTEGER { six (1), seven (2), eight (3) }
	ACCESS  read-write
	STATUS  mandatory
	DESCRIPTION
"The number of bits per character on the  port.

Options:
six (1)

seven (2)

eight (3)

Default Value: eight (3)"
	DEFVAL { eight }
	::= { cxMcPrtAsyEntry 24 }

cxMcPrtAsyParity          OBJECT-TYPE
	SYNTAX INTEGER { none (1), even (2), odd (3) }
	ACCESS  read-write
	STATUS  mandatory
	DESCRIPTION
	"The parity on the port.

Options:
none (1)

even (2)

odd (3)

Default Value: none (1)"
	DEFVAL { none }
	::= { cxMcPrtAsyEntry 25 }

cxMcPrtAsyNbStopBit               OBJECT-TYPE
	SYNTAX INTEGER { one (1), onehalf (2), two (3) }
	ACCESS  read-write
	STATUS  mandatory
	DESCRIPTION
"The number of stop bits per character on the asynchronous port.

Options:
one (1)

onehalf (2)

two (3)

Default Value: one (1)"
	DEFVAL { one }
	::= { cxMcPrtAsyEntry 26 }

cxMcPrtAsyUseFlushOutChr          OBJECT-TYPE
	SYNTAX INTEGER { no (1), yes (2) }
	ACCESS  read-write
	STATUS  mandatory
	DESCRIPTION
"The flush output on specific character on the asynchronous port.

Options:
no (1)

yes (2)

Default Value: no (1)"
	DEFVAL { no }
	::= { cxMcPrtAsyEntry 27 }

cxMcPrtAsyFlushOutChr             OBJECT-TYPE
	SYNTAX INTEGER (0..255)
	ACCESS  read-write
	STATUS  mandatory
	DESCRIPTION
"The flush character on the asynchronous port.

Range of Values: 0-255

Default Value: 127"
	DEFVAL { 127 }
	::= { cxMcPrtAsyEntry 28 }

 
--  cxMCPRT MC600 COP DRIVER GROUP 

cxMcPrtCopTable OBJECT-TYPE
	SYNTAX  SEQUENCE OF CxMcPrtCopEntry
	ACCESS  not-accessible
	STATUS  mandatory
	DESCRIPTION
"cx Port Station MC600 Cop Driver Table."
	::= { cxMcPrtDriver 3 }


cxMcPrtCopEntry OBJECT-TYPE
	SYNTAX  CxMcPrtCopEntry
	ACCESS  not-accessible
	STATUS  mandatory
	DESCRIPTION
"cx Port Station MC600 Cop Driver Entry gives the state of the variables 
associated to the Character Oriented Protocol."
	INDEX { cxMcPrtCopPortUsed }
	::= { cxMcPrtCopTable 1 }

CxMcPrtCopEntry ::=
	SEQUENCE {
		cxMcPrtCopPortUsed                INTEGER,
		cxMcPrtCopPortStatus              INTEGER,
		cxMcPrtCopComRate                 INTEGER,
		cxMcPrtCopUseLnkErrPassthro       INTEGER,
		cxMcPrtCopInterfaceType           INTEGER,
		cxMcPrtCopRtsDcdModemCtrl         INTEGER,
		cxMcPrtCopUseRtsDcdCndDataTx      INTEGER,
		cxMcPrtCopUseRtsDcdCndLnk         INTEGER,
		cxMcPrtCopUseRtsDcdCndRem         INTEGER,
		cxMcPrtCopDtrCtsModemCtrl         INTEGER,
		cxMcPrtCopUseDtrCtsCndRts         INTEGER,
		cxMcPrtCopUseDtrCtsCndLnk         INTEGER,
		cxMcPrtCopUseDtrCtsCndRem         INTEGER,
		cxMcPrtCopLimitBeforeOut          INTEGER,
		cxMcPrtCopUseOutCndCtsDtrOn       INTEGER,
		cxMcPrtCopUseInCndDcdRtsOn        INTEGER,
		cxMcPrtCopSyncMode                INTEGER,
		cxMcPrtCopDataLifetime            INTEGER,
		cxMcPrtCopUseClockSync            INTEGER,
		cxMcPrtCopUseFlowCtrlClock        INTEGER,
		cxMcPrtCopFlowCtrlRate            INTEGER,
		cxMcPrtCopLimitOutFlowCtrl        INTEGER,
		cxMcPrtCopLimitInFlowCtrl         INTEGER,
		cxMcPrtCopOutIdleState            INTEGER,
		cxMcPrtCopNbBitPerChr             INTEGER,
		cxMcPrtCopParity                  INTEGER,
		cxMcPrtCopSyncChrOne              INTEGER,
		cxMcPrtCopSyncChrTwo              INTEGER,
		cxMcPrtCopNbSyncChr               INTEGER,
		cxMcPrtCopUseDesyncChr            INTEGER,
		cxMcPrtCopDesyncChr               INTEGER,
		cxMcPrtCopNbDesyncChr             INTEGER,
		cxMcPrtCopUseDesyncRtsFall        INTEGER,
		cxMcPrtCopBitSense                INTEGER
	 }

cxMcPrtCopPortUsed                        OBJECT-TYPE
	SYNTAX INTEGER (1..4)
	ACCESS  read-only
	STATUS  mandatory
	DESCRIPTION
	"The current port number that is used by the COP Driver.

Range of Values: 1-4"
	::= { cxMcPrtCopEntry 1 }

cxMcPrtCopPortStatus                      OBJECT-TYPE
	SYNTAX  INTEGER { 
				disable (1),
				enable (2)
			 }
	ACCESS  read-write
	STATUS  mandatory
	DESCRIPTION
	"The port status for enabling or disabling the port.

Options:
disable (1)

enable (2)

Default Value: disable (1)"
	DEFVAL { disable }
	::= { cxMcPrtCopEntry 2 }

cxMcPrtCopComRate                 OBJECT-TYPE
	SYNTAX INTEGER (110..128000)
	ACCESS  read-write
	STATUS  mandatory
	DESCRIPTION
"The port communication rates.

Range of Values: 110-128000

Default Value: 9600"
	DEFVAL { 9600 }
	::= { cxMcPrtCopEntry 3 }

cxMcPrtCopUseLnkErrPassthro               OBJECT-TYPE
	SYNTAX INTEGER { no (1), yes (2) }
	ACCESS  read-write
	STATUS  mandatory
	DESCRIPTION
"Use the link error pass through on the port.

Options:
no (1)

yes (2)

Default Value: yes (2)"
	DEFVAL { yes }
	::= { cxMcPrtCopEntry 4 }

cxMcPrtCopInterfaceType           OBJECT-TYPE
	SYNTAX INTEGER { dce (1), dte (2) }
	ACCESS  read-write
	STATUS  mandatory
	DESCRIPTION
"The port interface type: DTE or DCE.

Options:
dce (1)

dte (2)

Default: dce (2)"
	DEFVAL { dce }
	::= { cxMcPrtCopEntry 5 }

cxMcPrtCopRtsDcdModemCtrl         OBJECT-TYPE
	SYNTAX INTEGER { on (1), vary (2) }
	ACCESS  read-write
	STATUS  mandatory
	DESCRIPTION
"Use the RTS or DCD modem control on the port.

Options 
on (1)

vary (2)

Default Value: on (1)"
	DEFVAL { on }
	::= { cxMcPrtCopEntry 6 }

cxMcPrtCopUseRtsDcdCndDataTx      OBJECT-TYPE
	SYNTAX INTEGER { no (1), yes (2) }
	ACCESS  read-write
	STATUS  mandatory
	DESCRIPTION
"Use the state of the RTS or DCD modem control when the port 
selected is conditioned by the presence of data in output queue.

Options:
no (1)

yes (2)

Default Value: no (1)"
DEFVAL { no }
	::= { cxMcPrtCopEntry 7 }

cxMcPrtCopUseRtsDcdCndLnk         OBJECT-TYPE
	SYNTAX INTEGER { no (1), yes (2) }
	ACCESS  read-write
	STATUS  mandatory
	DESCRIPTION
"Use the state of the RTS or DCD modem control when the port 
selected is conditioned by the main link status.

Options:
no (1)

yes (2)

Default Value: yes (2)"
	DEFVAL { yes }
	::= { cxMcPrtCopEntry 8 }

cxMcPrtCopUseRtsDcdCndRem         OBJECT-TYPE
	SYNTAX INTEGER { no (1), yes (2) }
	ACCESS  read-write
	STATUS  mandatory
	DESCRIPTION
"Use the state of the RTS or DCD modem control when the port 
selected is conditioned by the remote DCD or RTS.

Options:
no (1)

yes (2)

Default Value: yes (2)"
	DEFVAL { yes }
	::= { cxMcPrtCopEntry 9 }

cxMcPrtCopDtrCtsModemCtrl         OBJECT-TYPE
	SYNTAX INTEGER { on (1), vary (2) }
	ACCESS  read-write
	STATUS  mandatory
	DESCRIPTION
"Use the DTR or CTS modem control on the port.

Options:
on (1)

vary (2)

Default Value: on (1)"
	DEFVAL { on }
	::= { cxMcPrtCopEntry 10 }

cxMcPrtCopUseDtrCtsCndRts         OBJECT-TYPE
	SYNTAX INTEGER { no (1), yes (2) }
	ACCESS  read-write
	STATUS  mandatory
	DESCRIPTION
"Use the state of the CTS modem control when the port 
selected is conditioned by the local RTS.

Options:
no (1)

yes (2)

Default Value: no (1)"
	DEFVAL { no }
	::= { cxMcPrtCopEntry 11 }

cxMcPrtCopUseDtrCtsCndLnk         OBJECT-TYPE
	SYNTAX INTEGER { no (1), yes (2) }
	ACCESS  read-write
	STATUS  mandatory
	DESCRIPTION
"Use the the RTS or DCD modem control when the port 
selected is conditioned by the main link status.

Options:
no (1)

yes (2)

Default Value: yes (2)"
	DEFVAL { yes }
	::= { cxMcPrtCopEntry 12 }


cxMcPrtCopUseDtrCtsCndRem         OBJECT-TYPE
	SYNTAX INTEGER { no (1), yes (2) }
	ACCESS  read-write
	STATUS  mandatory
	DESCRIPTION
"Use the state of the RTS or DCD modem control when the port 
selected is conditioned by the remote DCD or RTS.

Options:
no (1)

yes (2)

Default Value: yes (2)"
	DEFVAL { yes }
	::= { cxMcPrtCopEntry 13 }

cxMcPrtCopLimitBeforeOut          OBJECT-TYPE
	SYNTAX INTEGER (5..4000)
	ACCESS  read-write
	STATUS  mandatory
	DESCRIPTION
"The limit before activation of output for the port.

Range of Values: 5-4000

Default Value: 15"
	DEFVAL { 15 }
	::= { cxMcPrtCopEntry 14 }

cxMcPrtCopUseOutCndCtsDtrOn               OBJECT-TYPE
	SYNTAX INTEGER { no (1), yes (2) }
	ACCESS  read-write
	STATUS  mandatory
	DESCRIPTION
"The output enable on CTS or DTR modem control for the port.

Options:
no (1)

yes (2)

Default Value: no (1)"
	DEFVAL { no }
	::= { cxMcPrtCopEntry 15 }

cxMcPrtCopUseInCndDcdRtsOn                OBJECT-TYPE
	SYNTAX INTEGER { no (1), yes (2) }
	ACCESS  read-write
	STATUS  mandatory
	DESCRIPTION
"The input enable on DCD or RTS modem control for the port.

Options:
no (1)

yes (2)

Default Value: no (1)"
	DEFVAL { no }
	::= { cxMcPrtCopEntry 16 }

cxMcPrtCopSyncMode                        OBJECT-TYPE
	SYNTAX INTEGER { normal (1), extern (2) }
	ACCESS  read-write
	STATUS  mandatory
	DESCRIPTION
"The clock synchronization for the port.

Options:
normal (1)

extern (2)

Default Value: normal (1)"
	DEFVAL { normal }
	::= { cxMcPrtCopEntry 17 }

cxMcPrtCopDataLifetime            OBJECT-TYPE
	SYNTAX INTEGER (1..60000)
	ACCESS  read-write
	STATUS  mandatory
	DESCRIPTION
"The data lifetime in milliseconds for the port.

Range of Values: 1-60000"
	DEFVAL { 2000 }
	::= { cxMcPrtCopEntry 18 }

cxMcPrtCopUseClockSync            OBJECT-TYPE
	SYNTAX INTEGER { no (1), yes (2) }
	ACCESS  read-write
	STATUS  mandatory
	DESCRIPTION
	"The clocks synchronization on the port."
	DEFVAL { no }
	::= { cxMcPrtCopEntry 19 }

cxMcPrtCopUseFlowCtrlClock                OBJECT-TYPE
	SYNTAX INTEGER { no (1), yes (2) }
	ACCESS  read-write
	STATUS  mandatory
	DESCRIPTION
	"The use of flow control by clocks of the synchronous port."
	DEFVAL { no }
	::= { cxMcPrtCopEntry 20 }

cxMcPrtCopFlowCtrlRate            OBJECT-TYPE
	SYNTAX INTEGER (110..9600)
	ACCESS  read-write
	STATUS  mandatory
	DESCRIPTION
	"The use of flow control rate of the synchronous port."
	DEFVAL { 300 }
	::= { cxMcPrtCopEntry 21 }

cxMcPrtCopLimitOutFlowCtrl                OBJECT-TYPE
	SYNTAX INTEGER (0..4000)
	ACCESS  read-write
	STATUS  mandatory
	DESCRIPTION
	"The limit before output flow control of the synchronous port."
	DEFVAL { 15 }
	::= { cxMcPrtCopEntry 22 }

cxMcPrtCopLimitInFlowCtrl         OBJECT-TYPE
	SYNTAX INTEGER (0..4000)
	ACCESS  read-write
	STATUS  mandatory
	DESCRIPTION
	"The overflow limit before input flow control for the port."
	DEFVAL { 512 }
	::= { cxMcPrtCopEntry 23 }

cxMcPrtCopOutIdleState                    OBJECT-TYPE
	SYNTAX INTEGER { space (1), mark (2) }
	ACCESS  read-write
	STATUS  mandatory
	DESCRIPTION
	"The output idle state for the port."
	DEFVAL { mark }
	::= { cxMcPrtCopEntry 24 }

cxMcPrtCopNbBitPerChr             OBJECT-TYPE
	SYNTAX INTEGER { six (1), seven (2), eight (3) }
	ACCESS  read-write
	STATUS  mandatory
	DESCRIPTION
	"The number of bits per character on the  port."
	DEFVAL { eight }
	::= { cxMcPrtCopEntry 25 }

cxMcPrtCopParity                  OBJECT-TYPE
	SYNTAX INTEGER { none (1), even (2), odd (3) }
	ACCESS  read-write
	STATUS  mandatory
	DESCRIPTION
	"The parity on the port."
	DEFVAL { none }
	::= { cxMcPrtCopEntry 26 }

cxMcPrtCopSyncChrOne                      OBJECT-TYPE
	SYNTAX INTEGER (0..255)
	ACCESS  read-write
	STATUS  mandatory
	DESCRIPTION
	"The synchronization character number one for the port."
	DEFVAL { 255 }
	::= { cxMcPrtCopEntry 27 }

cxMcPrtCopSyncChrTwo              OBJECT-TYPE
	SYNTAX INTEGER (0..255)
	ACCESS  read-write
	STATUS  mandatory
	DESCRIPTION
	"The synchronization character number two for the port."
	DEFVAL { 127 }
	::= { cxMcPrtCopEntry 28 }

cxMcPrtCopNbSyncChr                       OBJECT-TYPE
	SYNTAX INTEGER (0..255)
	ACCESS  read-write
	STATUS  mandatory
	DESCRIPTION
	"The number of synchronization character for the port."
	DEFVAL { 4 }
	::= { cxMcPrtCopEntry 29 }

cxMcPrtCopUseDesyncChr            OBJECT-TYPE
	SYNTAX INTEGER { no (1), yes (2) }
	ACCESS  read-write
	STATUS  mandatory
	DESCRIPTION
	"Use the desynchronization character on the port."
	DEFVAL { yes }
	::= { cxMcPrtCopEntry 30 }

cxMcPrtCopDesyncChr                       OBJECT-TYPE
	SYNTAX INTEGER (0..255)
	ACCESS  read-write
	STATUS  mandatory
	DESCRIPTION
	"The desynchronization character for the port."
	DEFVAL { 255 }
	::= { cxMcPrtCopEntry 31 }

cxMcPrtCopNbDesyncChr             OBJECT-TYPE
	SYNTAX INTEGER (0..255)
	ACCESS  read-write
	STATUS  mandatory
	DESCRIPTION
	"The number of desynchronization character for the port."
	DEFVAL { 20 }
	::= { cxMcPrtCopEntry 32 }

cxMcPrtCopUseDesyncRtsFall                OBJECT-TYPE
	SYNTAX INTEGER { no (1), yes (2) }
	ACCESS  read-write
	STATUS  mandatory
	DESCRIPTION
	"Use the desynchronization on RTS fall on the port."
	DEFVAL { no }
	::= { cxMcPrtCopEntry 33 }

cxMcPrtCopBitSense                        OBJECT-TYPE
	SYNTAX INTEGER { normal (1), inverted (2) }
	ACCESS  read-write
	STATUS  mandatory
	DESCRIPTION
	"The bit sense on the port."
	DEFVAL { normal }
	::= { cxMcPrtCopEntry 34 }

--  cxMCPRT MC600 BSY DRIVER GROUP 

cxMcPrtBsyTable OBJECT-TYPE
	SYNTAX  SEQUENCE OF CxMcPrtBsyEntry
	ACCESS  not-accessible
	STATUS  mandatory
	DESCRIPTION
		"cx Port Station MC600 Bsy Driver Table."
	::= { cxMcPrtDriver 4 }


cxMcPrtBsyEntry OBJECT-TYPE
	SYNTAX  CxMcPrtBsyEntry
	ACCESS  not-accessible
	STATUS  mandatory
	DESCRIPTION
		"cx Port Station MC600 Bsy Driver Entry gives the state of the variables associated
		 to the Bi-synchronous Protocol."
	INDEX { cxMcPrtBsyPortUsed }
	::= { cxMcPrtBsyTable 1 }

CxMcPrtBsyEntry ::=
	SEQUENCE {
		cxMcPrtBsyPortUsed                INTEGER,
		cxMcPrtBsyPortStatus              INTEGER,
		cxMcPrtBsyComRate                 INTEGER,
		cxMcPrtBsyUseLnkErrPassthro       INTEGER,
		cxMcPrtBsyInterface               INTEGER,
		cxMcPrtBsyRtsDcdModemCtrl         INTEGER,
		cxMcPrtBsyUseRtsDcdCndDataTx      INTEGER,
		cxMcPrtBsyUseRtsDcdCndLnk         INTEGER,
		cxMcPrtBsyUseRtsDcdCndRem         INTEGER,
		cxMcPrtBsyDtrCtsModemCtrl         INTEGER,
		cxMcPrtBsyUseDtrCtsCndRts         INTEGER,
		cxMcPrtBsyUseDtrCtsCndLnk         INTEGER,
		cxMcPrtBsyUseDtrCtsCndRem         INTEGER,
		cxMcPrtBsyLimitBeforeOut          INTEGER,
		cxMcPrtBsyUseOutCndCtsDtrOn       INTEGER,
		cxMcPrtBsyUseInCndDcdRtsOn        INTEGER,
		cxMcPrtBsySyncMode                INTEGER,
		cxMcPrtBsyDataLifetime            INTEGER,
		cxMcPrtBsyChrSet                  INTEGER,
		cxMcPrtBsyParity                  INTEGER,
		cxMcPrtBsyBlkChkChr               INTEGER,
		cxMcPrtBsyNbSyncChr               INTEGER,
		cxMcPrtBsyMaxFrameSize            INTEGER
	 }


cxMcPrtBsyPortUsed                        OBJECT-TYPE
	SYNTAX INTEGER (1..4)
	ACCESS  read-only
	STATUS  mandatory
	DESCRIPTION
	"The current port number that is used by the BSY Driver."
	::= { cxMcPrtBsyEntry 1 }

cxMcPrtBsyPortStatus                      OBJECT-TYPE
	SYNTAX  INTEGER { 
				disable (1),
				enable (2)
			 }
	ACCESS  read-write
	STATUS  mandatory
	DESCRIPTION
	"The port status for enabling or disabling the port."
	DEFVAL { disable }
	::= { cxMcPrtBsyEntry 2 }

cxMcPrtBsyComRate                 OBJECT-TYPE
	SYNTAX INTEGER (110..64000)
	ACCESS  read-write
	STATUS  mandatory
	DESCRIPTION
	"The port communication rates."
	DEFVAL { 9600 }
	::= { cxMcPrtBsyEntry 3 }

cxMcPrtBsyUseLnkErrPassthro               OBJECT-TYPE
	SYNTAX INTEGER { no (1), yes (2) }
	ACCESS  read-write
	STATUS  mandatory
	DESCRIPTION
	"Use the link error pass through on the port."
	DEFVAL { yes }
	::= { cxMcPrtBsyEntry 4 }

cxMcPrtBsyInterface                       OBJECT-TYPE
	SYNTAX INTEGER { dce (1), dte (2) }
	ACCESS  read-write
	STATUS  mandatory
	DESCRIPTION
	"The port interface type:  DTE or DCE."
	DEFVAL { dce }
	::= { cxMcPrtBsyEntry 5 }

cxMcPrtBsyRtsDcdModemCtrl         OBJECT-TYPE
	SYNTAX INTEGER { on (1), vary (2) }
	ACCESS  read-write
	STATUS  mandatory
	DESCRIPTION
	"Use the RTS or DCD modem control on the port."
	DEFVAL { on }
	::= { cxMcPrtBsyEntry 6 }

cxMcPrtBsyUseRtsDcdCndDataTx      OBJECT-TYPE
	SYNTAX INTEGER { no (1), yes (2) }
	ACCESS  read-write
	STATUS  mandatory
	DESCRIPTION
	"Use the state of the RTS or DCD modem control when the port 
	selected is conditioned by the presence of data in output queue."
	DEFVAL { no }
	::= { cxMcPrtBsyEntry 7 }

cxMcPrtBsyUseRtsDcdCndLnk         OBJECT-TYPE
	SYNTAX INTEGER { no (1), yes (2) }
	ACCESS  read-write
	STATUS  mandatory
	DESCRIPTION
	"Use the state of the RTS or DCD modem control when the port 
	selected is conditioned by the main link status."
	DEFVAL { yes }
	::= { cxMcPrtBsyEntry 8 }

cxMcPrtBsyUseRtsDcdCndRem         OBJECT-TYPE
	SYNTAX INTEGER { no (1), yes (2) }
	ACCESS  read-write
	STATUS  mandatory
	DESCRIPTION
	"Use the state of the RTS or DCD modem control when the port 
	selected is conditioned by the remote DCD or RTS."
	DEFVAL { yes }
	::= { cxMcPrtBsyEntry 9 }

cxMcPrtBsyDtrCtsModemCtrl         OBJECT-TYPE
	SYNTAX INTEGER { on (1), vary (2) }
	ACCESS  read-write
	STATUS  mandatory
	DESCRIPTION
	"Use the DTR or CTS modem control on the port."
	DEFVAL { on }
	::= { cxMcPrtBsyEntry 10 }

cxMcPrtBsyUseDtrCtsCndRts         OBJECT-TYPE
	SYNTAX INTEGER { no (1), yes (2) }
	ACCESS  read-write
	STATUS  mandatory
	DESCRIPTION
	"Use the state of the CTS modem control when the port 
	selected is conditioned by the local RTS."
	DEFVAL { no }
	::= { cxMcPrtBsyEntry 11 }

cxMcPrtBsyUseDtrCtsCndLnk         OBJECT-TYPE
	SYNTAX INTEGER { no (1), yes (2) }
	ACCESS  read-write
	STATUS  mandatory
	DESCRIPTION
	"Use the state of the RTS or DCD modem control when the port 
	selected is conditioned by the main link status."
	DEFVAL { yes }
	::= { cxMcPrtBsyEntry 12 }

cxMcPrtBsyUseDtrCtsCndRem         OBJECT-TYPE
	SYNTAX INTEGER { no (1), yes (2) }
	ACCESS  read-write
	STATUS  mandatory
	DESCRIPTION
	"Use the state of the RTS or DCD modem control when the port 
	selected is conditioned by the remote DCD or RTS."
	DEFVAL { yes }
	::= { cxMcPrtBsyEntry 13 }

cxMcPrtBsyLimitBeforeOut          OBJECT-TYPE
	SYNTAX INTEGER (5..4000)
	ACCESS  read-write
	STATUS  mandatory
	DESCRIPTION
	"The limit before activation of output for the port."
	DEFVAL { 10 }
	::= { cxMcPrtBsyEntry 14 }

cxMcPrtBsyUseOutCndCtsDtrOn               OBJECT-TYPE
	SYNTAX INTEGER { no (1), yes (2) }
	ACCESS  read-write
	STATUS  mandatory
	DESCRIPTION
	"Use the output enable on CTS or DTR modem control for the port."
	DEFVAL { no }
	::= { cxMcPrtBsyEntry 15 }

cxMcPrtBsyUseInCndDcdRtsOn                OBJECT-TYPE
	SYNTAX INTEGER { no (1), yes (2) }
	ACCESS  read-write
	STATUS  mandatory
	DESCRIPTION
	"Use the input enable on DCD or RTS modem control for the port."
	DEFVAL { no }
	::= { cxMcPrtBsyEntry 16 }

cxMcPrtBsySyncMode                        OBJECT-TYPE
	SYNTAX INTEGER { normal (1), extern (2) }
	ACCESS  read-write
	STATUS  mandatory
	DESCRIPTION
	"The clock synchronization for the port."
	DEFVAL { normal }
	::= { cxMcPrtBsyEntry 17 }

cxMcPrtBsyDataLifetime                    OBJECT-TYPE
	SYNTAX INTEGER (1..60000)
	ACCESS  read-write
	STATUS  mandatory
	DESCRIPTION
	"The data lifetime in milliseconds for the port."
	DEFVAL { 2000 }
	::= { cxMcPrtBsyEntry 18 }

cxMcPrtBsyChrSet                  OBJECT-TYPE
	SYNTAX INTEGER { ebcdic (1), usaascii (2), trans (3) }
	ACCESS  read-write
	STATUS  mandatory
	DESCRIPTION
	"The character set on the port."
	DEFVAL { usaascii }
	::= { cxMcPrtBsyEntry 19 }

cxMcPrtBsyParity                          OBJECT-TYPE
	SYNTAX INTEGER { none (1), even (2), odd (3) }
	ACCESS  read-write
	STATUS  mandatory
	DESCRIPTION
	"The parity on the port."
	DEFVAL { none }
	::= { cxMcPrtBsyEntry 20 }

cxMcPrtBsyBlkChkChr                       OBJECT-TYPE
	SYNTAX INTEGER { crc (1), lrc(2) }
	ACCESS  read-write
	STATUS  mandatory
	DESCRIPTION
	"The block check character on the port."
	DEFVAL { crc }
	::= { cxMcPrtBsyEntry 21 }

cxMcPrtBsyNbSyncChr                       OBJECT-TYPE
	SYNTAX INTEGER (2..255)
	ACCESS  read-write
	STATUS  mandatory
	DESCRIPTION "The number of synchronization character for the port."
	DEFVAL { 2 }
	::= { cxMcPrtBsyEntry 22 }

cxMcPrtBsyMaxFrameSize            OBJECT-TYPE
	SYNTAX INTEGER (1..64000)
	ACCESS  read-write
	STATUS  mandatory
	DESCRIPTION "The maximum frame size for the port."
	DEFVAL { 4000 }
	::= { cxMcPrtBsyEntry 23 }
END
