-- extracted from draft-ietf-l2tpext-l2tpmib-base-01.txt
-- at Sat Nov  9 06:11:21 2002

   L2TPV3-MIB DEFINITIONS ::= BEGIN

   IMPORTS
           MODULE-IDENTITY,
           NOTIFICATION-TYPE,
           OBJECT-TYPE,
           Counter32,
           Counter64,
           Gauge32,
           Integer32,
           Unsigned32
                   FROM SNMPv2-SMI

           TEXTUAL-CONVENTION,
           DisplayString,
           RowStatus,
           TruthValue
                   FROM SNMPv2-TC

           SnmpAdminString
                   FROM SNMP-FRAMEWORK-MIB

           MODULE-COMPLIANCE,
           NOTIFICATION-GROUP,
           OBJECT-GROUP
                   FROM SNMPv2-CONF

           InterfaceIndex
                   FROM IF-MIB;

   l2tpv3  MODULE-IDENTITY
           LAST-UPDATED    "200211030000Z" -- 3 November 2002
           ORGANIZATION    "IETF L2TP Working Group"
           CONTACT-INFO
               "Layer Two Tunneling Protocol Extensions WG
                Working Group Area:        Internet
                Working Group Name:        l2tpext
                General Discussion:        l2tp@l2tp.net"

           DESCRIPTION
               "The MIB module that describes managed objects of general
                use by the Layer Two Tunneling Protocol, Version 3
                (L2TPv3)."

   --
   --      Revision log
   --
           REVISION        "200211030000Z" -- 3 November 2002
           DESCRIPTION
               "First revision."
           ::= { transmission XXX } -- To be assigned by IANA

   --
   --      Textual Conventions
   --
   L2tpv3MilliSeconds ::=  TEXTUAL-CONVENTION
           DISPLAY-HINT    "d-3"
           STATUS          current
           DESCRIPTION
               "A period of time, measured in units of .001 seconds.
                When used in conjunction with the DISPLAY-HINT, shows
                seconds and fractions of a second with a resolution of
                .001 of a second."
           SYNTAX          Integer32 (0..2147483646)

   L2tpv3TransportType ::= TEXTUAL-CONVENTION
           DISPLAY-HINT    ""
           STATUS          current
           DESCRIPTION
               "Supported L2TP transport types.  Different transports
                may define MIB extensions to the L2TP control connection
                table to fully describe the transport layer.  Objects of
                this type may be used to determine which MIB extensions
                to reference."
           SYNTAX          INTEGER {
                               other(1),
                               none(2),
                               ipv4(3),
                               udpIpv4(4),
                               ipv6(5),
                               udpIpv6(6),
                               mpls(7),
                               frameRelay(8),
                               atm(9)
                           }

   L2tpv3PWType ::=        TEXTUAL-CONVENTION
           DISPLAY-HINT    ""
           STATUS          current
           DESCRIPTION
               "Supported L2TP pseudowire types."
           SYNTAX          INTEGER {
                               frameRelay(1),
                               atmAAL5(2),
                               atmTransCell(3),
                               ethernetVLAN(4),
                               ethernet(5),
                               hdlc(6),
                               ppp(7),
                               cem(8),
                               atmVCCCell(9),
                               atmVPCCell(10)
                           }

   L2tpv3DataSequencing ::= TEXTUAL-CONVENTION
           DISPLAY-HINT    ""
           STATUS          current
           DESCRIPTION
               "L2TP data sequencing levels.  A value of 'none'
                indicates that no received data packets require
                sequencing.  A value of 'nonIP' indicates that only
                non-IP data packets require sequencing.  A value of
                'all' indicates that all received data packets require
                sequencing.  The appropriate sequencing level is
                communicated to the peer via the Data Sequencing AVP."
           SYNTAX          INTEGER {
                               none(0),
                               nonIP(1),
                               all(2)
                           }

   --
   --      Definitions of significant branches
   --
   l2tpv3Notifications     OBJECT IDENTIFIER  ::= { l2tpv3 0 }
   l2tpv3Objects           OBJECT IDENTIFIER  ::= { l2tpv3 1 }
   l2tpv3Conformance       OBJECT IDENTIFIER  ::= { l2tpv3 2 }

   --
   --      The L2TP Stack Configuration Group
   --
   --      This group of objects is used to manage configuration
   --      of the L2TP stack.
   --
   l2tpv3StackCfg          OBJECT IDENTIFIER  ::= { l2tpv3Objects 1 }

   l2tpv3StackCfgAdminState OBJECT-TYPE
           SYNTAX          INTEGER {
                               enabled(1),
                               disabled(2)
                           }
           MAX-ACCESS      read-write
           STATUS          current
           DESCRIPTION
               "The administrative state of the L2TP stack.  Setting
                this object to 'disabled' causes all control connections
                to be immediately disconnected.  After this point, no
                further control connections or session may be initiated
                or accepted.  The value of this object must be
                maintained in non-volatile memory."
           ::= { l2tpv3StackCfg 1 }

   l2tpv3StackCfgDrain     OBJECT-TYPE
           SYNTAX          TruthValue
           MAX-ACCESS      read-write
           STATUS          current
           DESCRIPTION
               "Setting this object to 'true' prevents any new control
                connections and/or sessions from being initiated or
                accepted.  However, it does not disconnect any active
                control connections and/or sessions.  The
                'l2tpv3StackStatsIsDraining' object and the
                'l2tpv3CtrlStatsIsDraining' object of each control
                connection is set to 'true'.  To cancel a drain, this
                object is set to 'false'.  The value of this object must
                be maintained in non-volatile memory."
           ::= { l2tpv3StackCfg 2 }

   --
   --      The L2TP Status and Statistics Group
   --
   --      This group of objects describe the current state and
   --      statistics of the L2TP stack.
   --
   l2tpv3StackStats        OBJECT IDENTIFIER  ::= { l2tpv3Objects 2 }

   l2tpv3StackStatsVersion OBJECT-TYPE
           SYNTAX          Integer32 (1..65535)
           MAX-ACCESS      read-only
           STATUS          current
           DESCRIPTION
               "The highest protocol version number supported by this
                L2TP stack."
           ::= { l2tpv3StackStats 1 }

   l2tpv3StackStatsRevision OBJECT-TYPE
           SYNTAX          Integer32 (1..65535)
           MAX-ACCESS      read-only
           STATUS          current
           DESCRIPTION
               "The revision number of the L2TP stack."
           ::= { l2tpv3StackStats 2 }

   l2tpv3StackStatsVendorName OBJECT-TYPE
           SYNTAX          SnmpAdminString
           MAX-ACCESS      read-only
           STATUS          current
           DESCRIPTION
               "The vendor name of the L2TP stack."
           ::= { l2tpv3StackStats 3 }

   l2tpv3StackStatsAdminState OBJECT-TYPE
           SYNTAX          INTEGER {
                               enabled(1),
                               disabled(2)
                           }
           MAX-ACCESS      read-only
           STATUS          current
           DESCRIPTION
               "The administrative state of the L2TP stack.  It reflects
                the value of the l2tpv3StackCfgAdminState object."
           ::= { l2tpv3StackStats 4 }

   l2tpv3StackStatsIsDraining OBJECT-TYPE
           SYNTAX          TruthValue
           MAX-ACCESS      read-only
           STATUS          current
           DESCRIPTION
               "Indicates whether the L2TP stack is draining sessions
                from all control connections."
           ::= { l2tpv3StackStats 5 }

   l2tpv3StackStatsNumCtrlEst OBJECT-TYPE
           SYNTAX          Counter32
           MAX-ACCESS      read-only
           STATUS          current
           DESCRIPTION
               "The total number of control connections that are
                currently established."
           ::= { l2tpv3StackStats 6 }

   l2tpv3StackStatsNumSessEst OBJECT-TYPE
           SYNTAX          Counter32
           MAX-ACCESS      read-only
           STATUS          current
           DESCRIPTION
               "The total number of sessions that are currently
                established."
           ::= { l2tpv3StackStats 7 }

   --
   --      The L2TP Control Connection Configuration Table
   --
   l2tpv3CtrlCfgTable      OBJECT-TYPE
           SYNTAX          SEQUENCE OF L2tpv3CtrlCfgEntry
           MAX-ACCESS      not-accessible
           STATUS          current
           DESCRIPTION
               "Table used to (re)configure the operational
                characteristics of a single L2TP control connection.
                There is a 1:1 correspondence between conceptual rows of
                this table and conceptual rows of the
                l2tpv3CtrlStatsTable.  Entries in this table have the
                same persistency characteristics as that of the
                l2tpv3CtrlStatsTable."
           ::= { l2tpv3Objects 3 }

   l2tpv3CtrlCfgEntry      OBJECT-TYPE
           SYNTAX          L2tpv3CtrlCfgEntry
           MAX-ACCESS      not-accessible
           STATUS          current
           DESCRIPTION
               "An L2TP control connection configuration entry.  Entries
                in this table are added and deleted as a result of
                protocol interactions or management operations.  The
                latter occurs when a row is instantiated in the
                l2tpv3CtrlCfgTable row and the encapsulation method is
                'l2tp'."
           INDEX { l2tpv3CtrlCfgIfIndex }
           ::= { l2tpv3CtrlCfgTable 1 }

   L2tpv3CtrlCfgEntry ::=
           SEQUENCE {
               l2tpv3CtrlCfgIfIndex                InterfaceIndex,
               l2tpv3CtrlCfgRouterID               SnmpAdminString,
               l2tpv3CtrlCfgTransport              L2tpv3TransportType,
               l2tpv3CtrlCfgPWCap                  OCTET STRING,
               l2tpv3CtrlCfgFallback               TruthValue,
               l2tpv3CtrlCfgDrain                  TruthValue,
               l2tpv3CtrlCfgAuth                   INTEGER,
               l2tpv3CtrlCfgSecret                 SnmpAdminString,
               l2tpv3CtrlCfgSecurity               INTEGER,
               l2tpv3CtrlCfgHelloInt               Integer32,
               l2tpv3CtrlCfgRWS                    Integer32,
               l2tpv3CtrlCfgMaxRetrans             Integer32,
               l2tpv3CtrlCfgMaxRetransTO           Integer32,
               l2tpv3CtrlCfgReassemblyTO           L2tpv3MilliSeconds,
               l2tpv3CtrlCfgIdleTO                 Integer32
           }

   l2tpv3CtrlCfgIfIndex    OBJECT-TYPE
           SYNTAX          InterfaceIndex
           MAX-ACCESS      not-accessible
           STATUS          current
           DESCRIPTION
               "Value equal to the ifIndex value of the Interfaces Group
                MIB for an interface of type L2TP."
           ::= { l2tpv3CtrlCfgEntry 1 }

   l2tpv3CtrlCfgRouterID   OBJECT-TYPE
           SYNTAX          SnmpAdminString
           MAX-ACCESS      read-write
           STATUS          current
           DESCRIPTION
               "The local router ID of this peer, as communicated via
                the Router ID AVP for this control connection."
           ::= { l2tpv3CtrlCfgEntry 2 }

   l2tpv3CtrlCfgTransport  OBJECT-TYPE
           SYNTAX          L2tpv3TransportType
           MAX-ACCESS      read-write
           STATUS          current
           DESCRIPTION
               "The transport type of this control connection entry.
                This object cannot be modified when the control
                connection is in a connecting or connected state."
           ::= { l2tpv3CtrlCfgEntry 3 }

   l2tpv3CtrlCfgPWCap      OBJECT-TYPE
           SYNTAX          OCTET STRING (SIZE(1..256))
           MAX-ACCESS      read-write
           STATUS          current
           DESCRIPTION
               "The pseudowire capabilities of this control connection
                entry.  Each octet must be a value within the range
                specified by the L2tpv3PWType textual convention."
           ::= { l2tpv3CtrlCfgEntry 4 }

   l2tpv3CtrlCfgFallback   OBJECT-TYPE
           SYNTAX          TruthValue
           MAX-ACCESS      read-write
           STATUS          current
           DESCRIPTION
               "Indicates whether fallback to older versions of L2TP is
                enabled during control connection establishment."
           ::= { l2tpv3CtrlCfgEntry 5 }

   l2tpv3CtrlCfgDrain      OBJECT-TYPE
           SYNTAX          TruthValue
           MAX-ACCESS      read-write
           STATUS          current
           DESCRIPTION
               "Setting this object to 'true' prevents any new sessions
                from being either initiated or accepted by this control
                connection.  However, it does not disconnect any active
                sessions for this control connection.  The
                'l2tpv3CtrlStatsIsDraining' object for this control
                connection is set to 'true'.  To cancel a drain, this
                object is set to 'false'.  This object may be overridden
                by the global 'l2tpv3StackCfgDrain' object, which
                globally applies drain settings to all control
                connections."
           DEFVAL { false }
           ::= { l2tpv3CtrlCfgEntry 6 }

   l2tpv3CtrlCfgAuth       OBJECT-TYPE
           SYNTAX          INTEGER {
                               none(1),
                               simple(2),
                               challenge(3)
                           }
           MAX-ACCESS      read-write
           STATUS          current
           DESCRIPTION
               "Describes how a pair of LCCEs are to be authenticated.
                The value 'simple' indicates that peers are
                authenticated by their host name as described in the
                Host Name AVP.  The value 'challenge' indicates that all
                peers are challenged to prove their identification.
                This object cannot be modified when the control
                connection is in a connecting or connected state."
           DEFVAL { none }
           ::= { l2tpv3CtrlCfgEntry 7 }

   l2tpv3CtrlCfgSecret     OBJECT-TYPE
           SYNTAX          SnmpAdminString (SIZE (0..255))
           MAX-ACCESS      read-write
           STATUS          current
           DESCRIPTION
               "The shared secret used during the authentication phase
                of control connection establishment.  This object cannot
                be modified when the control connection is in a
                connecting or connected state.  This object MUST be
                accessible only via requests using both authentication
                and privacy.  The agent MUST report an empty string in
                response to get, get-next, and get-bulk requests."
           ::= { l2tpv3CtrlCfgEntry 8 }

   l2tpv3CtrlCfgSecurity   OBJECT-TYPE
           SYNTAX          INTEGER {
                               none(1),
                               other(2),
                               ipsec(3)

                           }
           MAX-ACCESS      read-write
           STATUS          current
           DESCRIPTION
               "Sets whether this control connection is to be secured.
                The value of 'ipsec' indicates that all control packets
                have IPsec headers.  The types of IPsec headers (e.g.
                AH, ESP, etc.) and their usage are outside the scope of
                this document.  This object cannot be modified when the
                control connection is in a connecting or connected
                state."
           DEFVAL { none }
           ::= { l2tpv3CtrlCfgEntry 9 }

   l2tpv3CtrlCfgHelloInt   OBJECT-TYPE
           SYNTAX          Integer32  (0..3600)
           UNITS           "seconds"
           MAX-ACCESS      read-write
           STATUS          current
           DESCRIPTION
               "The interval in which Hello (keepalive) packets are sent
                by a local peer.  The value zero effectively disables
                the sending of Hello packets.  Modifications to this
                object have immediate effect."
           DEFVAL { 60 }
           ::= { l2tpv3CtrlCfgEntry 10 }

   l2tpv3CtrlCfgRWS        OBJECT-TYPE
           SYNTAX          Integer32 (1..65535)
           MAX-ACCESS      read-write
           STATUS          current
           DESCRIPTION
               "The control packet receive window size.  It specifies
                the maximum number of control packets an LCCE can send
                for the control connection without waiting for an
                acknowledgement from the peer.  This object cannot be
                modified when the control connection is in a connecting
                or connected state."
           DEFVAL { 4 }
           ::= { l2tpv3CtrlCfgEntry 11 }

   l2tpv3CtrlCfgMaxRetrans OBJECT-TYPE
           SYNTAX          Integer32 (0..32)
           MAX-ACCESS      read-write
           STATUS          current
           DESCRIPTION
               "The number of control packet retransmissions that the
                L2TP stack attempts for this control connection before
                assuming that the peer is no longer responding.  A value
                of zero indicates that this peer does not attempt to
                retransmit an unacknowledged control packet.
                Modifications to this object have immediate effect."
           DEFVAL { 5 }
           ::= { l2tpv3CtrlCfgEntry 12 }

   l2tpv3CtrlCfgMaxRetransTO OBJECT-TYPE
           SYNTAX          Integer32 (1..32)
           UNITS           "seconds"
           MAX-ACCESS      read-write
           STATUS          current
           DESCRIPTION
               "The maximum retransmission timeout interval that the
                control connection waits before retransmitting an
                unacknowledged control packet.  Modifications to this
                object have immediate effect."
           DEFVAL { 16 }
           ::= { l2tpv3CtrlCfgEntry 13 }

   l2tpv3CtrlCfgReassemblyTO OBJECT-TYPE
           SYNTAX          L2tpv3MilliSeconds
           MAX-ACCESS      read-write
           STATUS          current
           DESCRIPTION
               "The number of milliseconds that this control connection
                waits before processing data packets that were received
                out of sequence (and that are being held for processing
                in sequence).  A low value increases the chance of
                delayed packets being discarded, while a high value may
                cause more queueing and possibly degrade throughput if
                packets are truly lost.  The default value for this
                object is zero, which means that delayed packets are
                considered lost, and received packets are processed in
                increasing order, despite any sequence number gaps."
           DEFVAL { 0 }
           ::= { l2tpv3CtrlCfgEntry 14 }

   l2tpv3CtrlCfgIdleTO     OBJECT-TYPE
           SYNTAX          Integer32 (-1..86400)
           UNITS           "seconds"
           MAX-ACCESS      read-write
           STATUS          current
           DESCRIPTION
               "The period of time that an established control
                connection with no sessions waits before disconnecting
                the control connection.  A value of zero indicates that
                the control connection disconnects immediately after the
                last session disconnects.  A value of -1 leaves the
                control connection up indefinitely.  Modifications to
                this object have immediate effect."
           DEFVAL { 0 }
           ::= { l2tpv3CtrlCfgEntry 15 }

   --
   --      The L2TP Control Connection Status and Statistics Table
   --
   l2tpv3CtrlStatsTable    OBJECT-TYPE
           SYNTAX          SEQUENCE OF L2tpv3CtrlStatsEntry
           MAX-ACCESS      not-accessible
           STATUS          current
           DESCRIPTION
               "Table describing the current status and statistics of a
                single L2TP control connection.  There is a 1:1
                correspondence between conceptual rows of this table and
                conceptual rows of the l2tpv3CtrlCfgTable."
           ::= { l2tpv3Objects 4 }

   l2tpv3CtrlStatsEntry    OBJECT-TYPE
           SYNTAX          L2tpv3CtrlStatsEntry
           MAX-ACCESS      not-accessible
           STATUS          current
           DESCRIPTION
               "An L2TP control connection interface statistics entry."
           AUGMENTS { l2tpv3CtrlCfgEntry }
           ::= { l2tpv3CtrlStatsTable 1 }

   L2tpv3CtrlStatsEntry ::=
           SEQUENCE {
               l2tpv3CtrlStatsLocalID              Unsigned32,
               l2tpv3CtrlStatsRemoteID             Unsigned32,
               l2tpv3CtrlStatsRemoteRouterID       SnmpAdminString,
               l2tpv3CtrlStatsState                INTEGER,
               l2tpv3CtrlStatsIsDraining           TruthValue,
               l2tpv3CtrlStatsInitiated            INTEGER,
               l2tpv3CtrlStatsRemoteHostName       SnmpAdminString,
               l2tpv3CtrlStatsRemoteVendorName     SnmpAdminString,
               l2tpv3CtrlStatsRemoteVersion        OCTET STRING,
               l2tpv3CtrlStatsRemotePWCap          OCTET STRING,
               l2tpv3CtrlStatsInitialRemoteRWS     Integer32,
               l2tpv3CtrlStatsCtrlRxZLB            Counter32,
               l2tpv3CtrlStatsCtrlOutOfSeq         Counter32,
               l2tpv3CtrlStatsCtrlOutOfWindow      Counter32,
               l2tpv3CtrlStatsCtrlTxZLB            Counter32,
               l2tpv3CtrlStatsCtrlAckTO            Counter32,
               l2tpv3CtrlStatsCurrentRemoteRWS     Gauge32,
               l2tpv3CtrlStatsTxSeq                Integer32,
               l2tpv3CtrlStatsRxSeq                Integer32,
               l2tpv3CtrlStatsNumSessCumEst        Counter32,
               l2tpv3CtrlStatsNumSessCurrentEst    Gauge32,
               l2tpv3CtrlStatsNumSessFailed        Counter32,
               l2tpv3CtrlStatsLastResultCode       Integer32,
               l2tpv3CtrlStatsLastErrorCode        Integer32,
               l2tpv3CtrlStatsLastErrorMessage     SnmpAdminString,
               l2tpv3CtrlStatsCtrlRxOctets         Counter32,
               l2tpv3CtrlStatsCtrlRxPkts           Counter32,
               l2tpv3CtrlStatsCtrlTxOctets         Counter32,
               l2tpv3CtrlStatsCtrlTxPkts           Counter32,
               l2tpv3CtrlStatsDataRxOctets         Counter32,
               l2tpv3CtrlStatsDataRxPkts           Counter32,
               l2tpv3CtrlStatsDataRxDrops          Counter32,
               l2tpv3CtrlStatsDataTxOctets         Counter32,
               l2tpv3CtrlStatsDataTxPkts           Counter32,
               l2tpv3CtrlStatsCtrlHCRxOctets       Counter64,
               l2tpv3CtrlStatsCtrlHCRxPkts         Counter64,
               l2tpv3CtrlStatsCtrlHCTxOctets       Counter64,
               l2tpv3CtrlStatsCtrlHCTxPkts         Counter64,
               l2tpv3CtrlStatsDataHCRxOctets       Counter64,
               l2tpv3CtrlStatsDataHCRxPkts         Counter64,
               l2tpv3CtrlStatsDataHCRxDrops        Counter64,
               l2tpv3CtrlStatsDataHCTxOctets       Counter64,
               l2tpv3CtrlStatsDataHCTxPkts         Counter64
           }

   l2tpv3CtrlStatsLocalID  OBJECT-TYPE
           SYNTAX          Unsigned32
           MAX-ACCESS      read-only
           STATUS          current
           DESCRIPTION
               "The local control connection ID."
           ::= { l2tpv3CtrlStatsEntry 1 }

   l2tpv3CtrlStatsRemoteID OBJECT-TYPE
           SYNTAX          Unsigned32
           MAX-ACCESS      read-only
           STATUS          current
           DESCRIPTION
               "The remote control connection ID."
           ::= { l2tpv3CtrlStatsEntry 2 }

   l2tpv3CtrlStatsRemoteRouterID OBJECT-TYPE
           SYNTAX          SnmpAdminString
           MAX-ACCESS      read-only
           STATUS          current
           DESCRIPTION
               "The remote router ID for this control connection, as
                communicated by the peer via the Router ID AVP."
           ::= { l2tpv3CtrlStatsEntry 3 }

   l2tpv3CtrlStatsState    OBJECT-TYPE
           SYNTAX          INTEGER {
                               ctrlIdle(1),
                               ctrlConnecting(2),
                               ctrlEstablished(3),
                               ctrlDisconnecting(4)
                           }
           MAX-ACCESS      read-only
           STATUS          current
           DESCRIPTION
               "The current state of the control connection."
           ::= { l2tpv3CtrlStatsEntry 4 }

   l2tpv3CtrlStatsIsDraining OBJECT-TYPE
           SYNTAX          TruthValue
           MAX-ACCESS      read-only
           STATUS          current
           DESCRIPTION
               "Indicates whether the control connection is draining
                sessions.  This object is set to 'true' if either
                'l2tpv3StackCfgDrain' or 'l2tpv3CtrlCfgDrain' is set to
                'true', and is only set to 'false' if both configuration
                objects are 'false'."
           ::= { l2tpv3CtrlStatsEntry 5 }

   l2tpv3CtrlStatsInitiated OBJECT-TYPE
           SYNTAX          INTEGER {
                               locally(1),
                               remotely(2)
                           }
           MAX-ACCESS      read-only
           STATUS          current
           DESCRIPTION
               "Indicates whether the control connection was initiated
                locally or remotely."
           ::= { l2tpv3CtrlStatsEntry 6 }

   l2tpv3CtrlStatsRemoteHostName OBJECT-TYPE
           SYNTAX          SnmpAdminString
           MAX-ACCESS      read-only
           STATUS          current
           DESCRIPTION
               "The peer's host name as discovered during the control
                connection establishment (via the Host Name AVP).  If
                the control connection is idle, this object should
                maintain its value from the last time it was connected."
           ::= { l2tpv3CtrlStatsEntry 7 }

   l2tpv3CtrlStatsRemoteVendorName OBJECT-TYPE
           SYNTAX          SnmpAdminString
           MAX-ACCESS      read-only
           STATUS          current
           DESCRIPTION
               "The vendor name of the peer.  If the control connection
                is idle, this object should maintain its value from the
                last time it was connected."
           ::= { l2tpv3CtrlStatsEntry 8 }

   l2tpv3CtrlStatsRemotePWCap OBJECT-TYPE
           SYNTAX          OCTET STRING (SIZE(1..256))
           MAX-ACCESS      read-write
           STATUS          current
           DESCRIPTION
               "The peer's pseudowire capabilities for this control
                connection.  Each octet must be a value within the range
                specified by the L2tpv3PWType textual convention."
           ::= { l2tpv3CtrlStatsEntry 9 }

   l2tpv3CtrlStatsRemoteVersion OBJECT-TYPE
           SYNTAX          OCTET STRING (SIZE(2))
           MAX-ACCESS      read-only
           STATUS          current
           DESCRIPTION
               "The peer implementation's protocol version number and
                revision number.  The first octet contains the protocol
                version number.  The second octet contains the protocol
                revision number."
           ::= { l2tpv3CtrlStatsEntry 10 }

   l2tpv3CtrlStatsInitialRemoteRWS OBJECT-TYPE
           SYNTAX          Integer32 (0..65535)
           MAX-ACCESS      read-only
           STATUS          current
           DESCRIPTION
               "The peer's receive window size as conveyed during
                control connection establishment (via the Remote Window
                Size AVP).  If the control connection is idle, this
                object should maintain its value from the last time it
                was connected."
           ::= { l2tpv3CtrlStatsEntry 11 }

   l2tpv3CtrlStatsCtrlRxZLB OBJECT-TYPE
           SYNTAX          Counter32
           MAX-ACCESS      read-only
           STATUS          current
           DESCRIPTION
               "The number of Zero-Length-Body (acknowledgement) control
                packets that have been received on the control
                connection."
           ::= { l2tpv3CtrlStatsEntry 12 }

   l2tpv3CtrlStatsCtrlOutOfSeq OBJECT-TYPE
           SYNTAX          Counter32
           MAX-ACCESS      read-only
           STATUS          current
           DESCRIPTION
               "The number of control packets that have been received
                out of order (per the sequence numbers) on this control
                connection, including out of window packets."
           ::= { l2tpv3CtrlStatsEntry 13 }

   l2tpv3CtrlStatsCtrlOutOfWindow OBJECT-TYPE
           SYNTAX          Counter32
           MAX-ACCESS      read-only
           STATUS          current
           DESCRIPTION
               "The number of control packets that have been received
                outside of the offered receive window for the control
                connection.  Whether these packets are queued or
                discarded is implementation-specific."
           ::= { l2tpv3CtrlStatsEntry 14 }

   l2tpv3CtrlStatsCtrlTxZLB OBJECT-TYPE
           SYNTAX          Counter32
           MAX-ACCESS      read-only
           STATUS          current
           DESCRIPTION
               "The number of Zero-Length-Body (acknowledgement) control
                packets that have been sent to the peer for this control
                connection."
           ::= { l2tpv3CtrlStatsEntry 15 }

   l2tpv3CtrlStatsCtrlAckTO OBJECT-TYPE
           SYNTAX          Counter32
           MAX-ACCESS      read-only
           STATUS          current
           DESCRIPTION
               "The number of control packet timeouts due to late
                acknowledgements from the peer for this control
                connection."
           ::= { l2tpv3CtrlStatsEntry 16 }

   l2tpv3CtrlStatsCurrentRemoteRWS OBJECT-TYPE
           SYNTAX          Gauge32 (0..65535)
           MAX-ACCESS      read-only
           STATUS          current
           DESCRIPTION
               "The current remote receive window size as determined by
                the local flow control mechanism employed."
           ::= { l2tpv3CtrlStatsEntry 17 }

   l2tpv3CtrlStatsTxSeq    OBJECT-TYPE
           SYNTAX          Integer32 (0..65535)
           MAX-ACCESS      read-only
           STATUS          current
           DESCRIPTION
               "The next send (Ns) sequence number for the control
                connection."
           ::= { l2tpv3CtrlStatsEntry 18 }

   l2tpv3CtrlStatsRxSeq    OBJECT-TYPE
           SYNTAX          Integer32 (0..65535)
           MAX-ACCESS      read-only
           STATUS          current
           DESCRIPTION
               "The next receive (Nr) sequence number for the control
                connection."
           ::= { l2tpv3CtrlStatsEntry 19 }

   l2tpv3CtrlStatsNumSessCumEst OBJECT-TYPE
           SYNTAX          Counter32
           MAX-ACCESS      read-only
           STATUS          current
           DESCRIPTION
               "The cumulative number of sessions that this control
                connection has established during its lifetime."
           ::= { l2tpv3CtrlStatsEntry 20 }

   l2tpv3CtrlStatsNumSessCurrentEst OBJECT-TYPE
           SYNTAX          Gauge32
           MAX-ACCESS      read-only
           STATUS          current
           DESCRIPTION
               "The number of sessions currently in the established
                state for this control connection."
           ::= { l2tpv3CtrlStatsEntry 21 }

   l2tpv3CtrlStatsNumSessFailed OBJECT-TYPE
           SYNTAX          Counter32
           MAX-ACCESS      read-only
           STATUS          current
           DESCRIPTION
               "The total number of sessions that were negotiated but
                failed to be established by this control connection."
           ::= { l2tpv3CtrlStatsEntry 22 }

   l2tpv3CtrlStatsLastResultCode OBJECT-TYPE
           SYNTAX          Integer32 (0..65535)
           MAX-ACCESS      read-only
           STATUS          current
           DESCRIPTION
               "The result code as conveyed by the Result Code AVP from
                the most recent session to be torn down."
           ::= { l2tpv3CtrlStatsEntry 23 }

   l2tpv3CtrlStatsLastErrorCode OBJECT-TYPE
           SYNTAX          Integer32 (0..65535)
           MAX-ACCESS      read-only
           STATUS          current
           DESCRIPTION
               "The error code as conveyed by the Result Code AVP from
                the most recent session to be torn down."
           ::= { l2tpv3CtrlStatsEntry 24 }

   l2tpv3CtrlStatsLastErrorMessage OBJECT-TYPE
           SYNTAX          SnmpAdminString
           MAX-ACCESS      read-only
           STATUS          current
           DESCRIPTION
               "The optional message as conveyed by the Result Code AVP
                from the most recent session to be torn down."
           ::= { l2tpv3CtrlStatsEntry 25 }

   l2tpv3CtrlStatsCtrlRxOctets OBJECT-TYPE
           SYNTAX          Counter32
           MAX-ACCESS      read-only
           STATUS          current
           DESCRIPTION
               "The number of control octets that have been received by
                this control connection."
           ::= { l2tpv3CtrlStatsEntry 26 }

   l2tpv3CtrlStatsCtrlRxPkts OBJECT-TYPE
           SYNTAX          Counter32
           MAX-ACCESS      read-only
           STATUS          current
           DESCRIPTION
               "The number of control packets that have been received by
                this control connection."
           ::= { l2tpv3CtrlStatsEntry 27 }

   l2tpv3CtrlStatsCtrlTxOctets OBJECT-TYPE
           SYNTAX          Counter32
           MAX-ACCESS      read-only
           STATUS          current
           DESCRIPTION
               "The number of control octets that have been sent by this
                control connection."
           ::= { l2tpv3CtrlStatsEntry 28 }

   l2tpv3CtrlStatsCtrlTxPkts OBJECT-TYPE
           SYNTAX          Counter32
           MAX-ACCESS      read-only
           STATUS          current
           DESCRIPTION
               "The number of control packets that have been sent by
                this control connection."
           ::= { l2tpv3CtrlStatsEntry 29 }

   l2tpv3CtrlStatsDataRxOctets OBJECT-TYPE
           SYNTAX          Counter32
           MAX-ACCESS      read-only
           STATUS          current
           DESCRIPTION
               "The number of data octets that have been received by
                sessions negotiated by this control connection."
           ::= { l2tpv3CtrlStatsEntry 30 }

   l2tpv3CtrlStatsDataRxPkts OBJECT-TYPE
           SYNTAX          Counter32
           MAX-ACCESS      read-only
           STATUS          current
           DESCRIPTION
               "The number of data packets that have been received by
                sessions negotiated by this control connection."
           ::= { l2tpv3CtrlStatsEntry 31 }

   l2tpv3CtrlStatsDataRxDrops OBJECT-TYPE
           SYNTAX          Counter32
           MAX-ACCESS      read-only
           STATUS          current
           DESCRIPTION
               "The number of received data packets that have been
                dropped by sessions negotiated by this control
                connection."
           ::= { l2tpv3CtrlStatsEntry 32 }

   l2tpv3CtrlStatsDataTxOctets OBJECT-TYPE
           SYNTAX          Counter32
           MAX-ACCESS      read-only
           STATUS          current
           DESCRIPTION
               "The number of data octets that have been sent by
                sessions negotiated by this control connection."
           ::= { l2tpv3CtrlStatsEntry 33 }

   l2tpv3CtrlStatsDataTxPkts OBJECT-TYPE
           SYNTAX          Counter32
           MAX-ACCESS      read-only
           STATUS          current
           DESCRIPTION
               "The number of data packets that have been sent by
                sessions negotiated by this control connection."
           ::= { l2tpv3CtrlStatsEntry 34 }

   --
   -- High-capacity counter objects.  These objects are all 64-bit versions
   -- of the above 32-bit counters.  They have the same basic semantics as
   -- their 32-bit counterparts.
   --
   l2tpv3CtrlStatsCtrlHCRxOctets OBJECT-TYPE
           SYNTAX          Counter64
           MAX-ACCESS      read-only
           STATUS          current
           DESCRIPTION
               "The 64-bit version of l2tpv3CtrlStatsCtrlRxOctets."
           ::= { l2tpv3CtrlStatsEntry 35 }

   l2tpv3CtrlStatsCtrlHCRxPkts OBJECT-TYPE
           SYNTAX          Counter64
           MAX-ACCESS      read-only
           STATUS          current
           DESCRIPTION
               "The 64-bit version of l2tpv3CtrlStatsCtrlRxPkts."
           ::= { l2tpv3CtrlStatsEntry 36 }

   l2tpv3CtrlStatsCtrlHCTxOctets OBJECT-TYPE
           SYNTAX          Counter64
           MAX-ACCESS      read-only
           STATUS          current
           DESCRIPTION
               "The 64-bit version of l2tpv3CtrlStatsCtrlTxOctets."
           ::= { l2tpv3CtrlStatsEntry 37 }

   l2tpv3CtrlStatsCtrlHCTxPkts OBJECT-TYPE
           SYNTAX          Counter64
           MAX-ACCESS      read-only
           STATUS          current
           DESCRIPTION
               "The 64-bit version of l2tpv3CtrlStatsCtrlTxPkts."
           ::= { l2tpv3CtrlStatsEntry 38 }

   l2tpv3CtrlStatsDataHCRxOctets OBJECT-TYPE
           SYNTAX          Counter64
           MAX-ACCESS      read-only
           STATUS          current
           DESCRIPTION
               "The 64-bit version of l2tpv3CtrlStatsDataRxOctets."
           ::= { l2tpv3CtrlStatsEntry 39 }

   l2tpv3CtrlStatsDataHCRxPkts OBJECT-TYPE
           SYNTAX          Counter64
           MAX-ACCESS      read-only
           STATUS          current
           DESCRIPTION
               "The 64-bit version of l2tpv3CtrlStatsDataRxPkts."
           ::= { l2tpv3CtrlStatsEntry 40 }

   l2tpv3CtrlStatsDataHCRxDrops OBJECT-TYPE
           SYNTAX          Counter64
           MAX-ACCESS      read-only
           STATUS          current
           DESCRIPTION
               "The 64-bit version of l2tpv3CtrlStatsDataRxDrops."
           ::= { l2tpv3CtrlStatsEntry 41 }

   l2tpv3CtrlStatsDataHCTxOctets OBJECT-TYPE
           SYNTAX          Counter64
           MAX-ACCESS      read-only
           STATUS          current
           DESCRIPTION
               "The 64-bit version of l2tpv3CtrlStatsDataTxOctets."
           ::= { l2tpv3CtrlStatsEntry 42 }

   l2tpv3CtrlStatsDataHCTxPkts OBJECT-TYPE
           SYNTAX          Counter64
           MAX-ACCESS      read-only
           STATUS          current
           DESCRIPTION
               "The 64-bit version of l2tpv3CtrlStatsDataTxPkts."
           ::= { l2tpv3CtrlStatsEntry 43 }

   --
   --      The L2TP Control Connection Mapping Table
   --
   l2tpv3CtrlMapTable      OBJECT-TYPE
           SYNTAX          SEQUENCE OF L2tpv3CtrlMapEntry
           MAX-ACCESS      not-accessible
           STATUS          current
           DESCRIPTION
               "Table intended to assist management applications to
                quickly determine the ifIndex value for a given local
                control connection ID."
           ::= { l2tpv3Objects 5 }

   l2tpv3CtrlMapEntry      OBJECT-TYPE
           SYNTAX          L2tpv3CtrlMapEntry
           MAX-ACCESS      not-accessible
           STATUS          current
           DESCRIPTION
               "An L2TP control connection index map entry."
           INDEX { l2tpv3CtrlMapLocalID }
           ::= { l2tpv3CtrlMapTable 1 }

   L2tpv3CtrlMapEntry ::=
           SEQUENCE {
               l2tpv3CtrlMapLocalID                Unsigned32,
               l2tpv3CtrlMapIfIndex                InterfaceIndex
           }

   l2tpv3CtrlMapLocalID    OBJECT-TYPE
           SYNTAX          Unsigned32
           MAX-ACCESS      not-accessible
           STATUS          current
           DESCRIPTION
               "The local control connection ID."
           ::= { l2tpv3CtrlMapEntry 1 }

   l2tpv3CtrlMapIfIndex    OBJECT-TYPE
           SYNTAX          InterfaceIndex
           MAX-ACCESS      read-only
           STATUS          current
           DESCRIPTION
               "The ifIndex value of a control connection interface,
                represented in the Interfaces Group MIB as an entry with
                an interface type of L2TP."
           ::= { l2tpv3CtrlMapEntry 2 }

   --
   --      The L2TP Session Configuration Table
   --
   l2tpv3SessionCfgTable   OBJECT-TYPE
           SYNTAX          SEQUENCE OF L2tpv3SessionCfgEntry
           MAX-ACCESS      not-accessible
           STATUS          current
           DESCRIPTION
               "Table used to (re)configure the operational
                characteristics of a single L2TP session.  There is a
                1:1 correspondence between conceptual rows of this table
                and conceptual rows of the l2tpv3SessionStatsTable.
                Entries in this table have the same persistency
                characteristics as that of the l2tpv3SessionStatsTable."
           ::= { l2tpv3Objects 6 }

   l2tpv3SessionCfgEntry   OBJECT-TYPE
           SYNTAX          L2tpv3SessionCfgEntry
           MAX-ACCESS      not-accessible
           STATUS          current
           DESCRIPTION
               "An L2TP session configuration entry.  Entries in this
                table are added and deleted as a result of protocol
                interactions or management operations."
           INDEX { l2tpv3SessionCfgIfIndex }
           ::= { l2tpv3SessionCfgTable 1 }

   L2tpv3SessionCfgEntry ::=
           SEQUENCE {
               l2tpv3SessionCfgIfIndex             InterfaceIndex,
               l2tpv3SessionCfgLocalID             Unsigned32,
               l2tpv3SessionCfgRemoteID            Unsigned32,
               l2tpv3SessionCfgCtrlLocalID         Unsigned32,
               l2tpv3SessionCfgPWType              L2tpv3PWType,
               l2tpv3SessionCfgEndID               DisplayString,
               l2tpv3SessionCfgAppID               DisplayString,
               l2tpv3SessionCfgPWEncap             INTEGER,
               l2tpv3SessionCfgSeq                 L2tpv3DataSequencing,
               l2tpv3SessionCfgLocalCookie         DisplayString,
               l2tpv3SessionCfgRemoteCookie        DisplayString,
               l2tpv3SessionCfgCallType            INTEGER
           }

   l2tpv3SessionCfgIfIndex OBJECT-TYPE
           SYNTAX          InterfaceIndex
           MAX-ACCESS      not-accessible
           STATUS          current
           DESCRIPTION
               "The ifIndex value of the interface from which L2 frames
                are being forwarded.  For example, the ifIndex could be
                a DS0 on an LAC or a virtual PPP interface on an LNS."
           ::= { l2tpv3SessionCfgEntry 1 }

   l2tpv3SessionCfgLocalID OBJECT-TYPE
           SYNTAX          Unsigned32
           MAX-ACCESS      read-create
           STATUS          current
           DESCRIPTION
               "Sets the local session ID."
           ::= { l2tpv3SessionCfgEntry 2 }

   l2tpv3SessionCfgRemoteID OBJECT-TYPE
           SYNTAX          Unsigned32
           MAX-ACCESS      read-create
           STATUS          current
           DESCRIPTION
               "Sets the remote session ID."
           ::= { l2tpv3SessionCfgEntry 3 }

   l2tpv3SessionCfgCtrlLocalID OBJECT-TYPE
           SYNTAX          Unsigned32
           MAX-ACCESS      read-create
           STATUS          current
           DESCRIPTION
               "Sets the local control connection ID of the control
                connection with which this session may be associated.
                If the session is not associated with a control
                connection, the value of this object is 0."
           ::= { l2tpv3SessionCfgEntry 4 }

   l2tpv3SessionCfgPWType  OBJECT-TYPE
           SYNTAX          L2tpv3PWType
           MAX-ACCESS      read-create
           STATUS          current
           DESCRIPTION
               "Sets the pseudowire type of the session, which is sent
                to the peer via the Pseudowire Type AVP."
           ::= { l2tpv3SessionCfgEntry 5 }

   l2tpv3SessionCfgEndID   OBJECT-TYPE
           SYNTAX          DisplayString (SIZE(0..255))
           MAX-ACCESS      read-create
           STATUS          current
           DESCRIPTION
               "Sets the End Identifier that is sent to the peer via the
                End ID AVP."
           ::= { l2tpv3SessionCfgEntry 6 }

   l2tpv3SessionCfgAppID   OBJECT-TYPE
           SYNTAX          DisplayString (SIZE(0..255))
           MAX-ACCESS      read-create
           STATUS          current
           DESCRIPTION
               "Sets the Application Code and Application Info that are
                sent to the peer via the Application ID AVP."
           ::= { l2tpv3SessionCfgEntry 7 }

   l2tpv3SessionCfgPWEncap OBJECT-TYPE
           SYNTAX          INTEGER {
                              none(0),
                              default(1)
                           }
           MAX-ACCESS      read-create
           STATUS          current
           DESCRIPTION
               "Sets the Control Encapsulation Type that is sent to the
                peer via the Pseudowire Control Encapsulation AVP."
           DEFVAL { none }
           ::= { l2tpv3SessionCfgEntry 8 }

   l2tpv3SessionCfgSeq     OBJECT-TYPE
           SYNTAX          L2tpv3DataSequencing
           MAX-ACCESS      read-create
           STATUS          current
           DESCRIPTION
               "Sets the Data Sequencing Level that is required of the
                peer.  Sent to the peer via the Data Sequencing AVP."
           DEFVAL { none }
           ::= { l2tpv3SessionCfgEntry 9 }

   l2tpv3SessionCfgLocalCookie OBJECT-TYPE
           SYNTAX          DisplayString (SIZE(0..8))
           MAX-ACCESS      read-create
           STATUS          current
           DESCRIPTION
               "Sets the local cookie that is included in outgoing data
                packets."
           ::= { l2tpv3SessionCfgEntry 10 }

   l2tpv3SessionCfgRemoteCookie OBJECT-TYPE
           SYNTAX          DisplayString (SIZE(0..8))
           MAX-ACCESS      read-create
           STATUS          current
           DESCRIPTION
               "Sets the remote cookie that is expected in incoming data
                packets."
           ::= { l2tpv3SessionCfgEntry 11 }

   l2tpv3SessionCfgCallType OBJECT-TYPE
           SYNTAX          INTEGER {
                              lacInitiator(1),
                              lacResponder(2),
                              lnsInitiator(3),
                              lnsResponder(4)
                           }
           MAX-ACCESS      read-create
           STATUS          current
           DESCRIPTION
               "The role this LCCE is playing for this session.  For
                example, 'lacInitiator' indicates that this control
                connection peer is acting as an LAC and generated an
                call request (ICRQ or OCRQ) to its peer."
           ::= { l2tpv3SessionCfgEntry 12 }

   --
   --      The L2TP Session Status and Statistics Table
   --
   l2tpv3SessionStatsTable OBJECT-TYPE
           SYNTAX          SEQUENCE OF L2tpv3SessionStatsEntry
           MAX-ACCESS      not-accessible
           STATUS          current
           DESCRIPTION
               "Table that describes the current status and statistics
                of a single L2TP session."
           ::= { l2tpv3Objects 7 }

   l2tpv3SessionStatsEntry OBJECT-TYPE
           SYNTAX          L2tpv3SessionStatsEntry
           MAX-ACCESS      not-accessible
           STATUS          current
           DESCRIPTION
               "An L2TP session interface statistics entry."
           AUGMENTS { l2tpv3SessionCfgEntry }
           ::= { l2tpv3SessionStatsTable 1 }

   L2tpv3SessionStatsEntry ::=
           SEQUENCE {
               l2tpv3SessionStatsRemoteEndID       DisplayString,
               l2tpv3SessionStatsRemoteAppID       DisplayString,
               l2tpv3SessionStatsRemotePWEncap     INTEGER,
               l2tpv3SessionStatsRemoteSeq         L2tpv3DataSequencing,
               l2tpv3SessionStatsState             INTEGER,
               l2tpv3SessionStatsCircuitStatus     Unsigned32,
               l2tpv3SessionStatsSerialNumber      Unsigned32,
               l2tpv3SessionStatsRxConnectSpeed    Unsigned32,
               l2tpv3SessionStatsTxConnectSpeed    Unsigned32,
               l2tpv3SessionStatsPhysChannelID     Unsigned32,
               l2tpv3SessionStatsPrivateGroupID    SnmpAdminString,
               l2tpv3SessionStatsOutOfSeq          Counter32,
               l2tpv3SessionStatsReassemblyTO      Counter32,
               l2tpv3SessionStatsTxSeq             Counter32,
               l2tpv3SessionStatsRxSeq             Counter32,
               l2tpv3SessionStatsRxOctets          Counter32,
               l2tpv3SessionStatsRxPkts            Counter32,
               l2tpv3SessionStatsRxDrops           Counter32,
               l2tpv3SessionStatsTxOctets          Counter32,
               l2tpv3SessionStatsTxPkts            Counter32,
               l2tpv3SessionStatsHCRxOctets        Counter64,
               l2tpv3SessionStatsHCRxPkts          Counter64,
               l2tpv3SessionStatsHCRxDrops         Counter64,
               l2tpv3SessionStatsHCTxOctets        Counter64,
               l2tpv3SessionStatsHCTxPkts          Counter64
           }

   l2tpv3SessionStatsRemoteEndID OBJECT-TYPE
           SYNTAX          DisplayString (SIZE(0..255))
           MAX-ACCESS      read-only
           STATUS          current
           DESCRIPTION
               "The peer's End Identifier, as communicated via the End
                ID AVP."
           ::= { l2tpv3SessionStatsEntry 1 }

   l2tpv3SessionStatsRemoteAppID OBJECT-TYPE
           SYNTAX          DisplayString (SIZE(0..255))
           MAX-ACCESS      read-only
           STATUS          current
           DESCRIPTION
               "The peer's Application Code and Application Info, as
                communicated via the Application ID AVP."
           ::= { l2tpv3SessionStatsEntry 2 }

   l2tpv3SessionStatsRemotePWEncap OBJECT-TYPE
           SYNTAX          INTEGER {
                              none(0),
                              default(1)
                           }
           MAX-ACCESS      read-only
           STATUS          current
           DESCRIPTION
               "The peer's Control Encapsulation Type, as communicated
                via the Pseudowire Control Encapsulation AVP."
           ::= { l2tpv3SessionStatsEntry 3 }

   l2tpv3SessionStatsRemoteSeq OBJECT-TYPE
           SYNTAX          L2tpv3DataSequencing
           MAX-ACCESS      read-create
           STATUS          current
           DESCRIPTION
               "The peer's Data Sequencing Level, as communicated via
                the Data Sequencing AVP."
           DEFVAL { none }
           ::= { l2tpv3SessionStatsEntry 4 }

   l2tpv3SessionStatsState OBJECT-TYPE
           SYNTAX          INTEGER {
                               sessionIdle(1),
                               sessionConnecting(2),
                               sessionEstablished(3),
                               sessionDisconnecting(4)
                           }
           MAX-ACCESS      read-only
           STATUS          current
           DESCRIPTION
               "The current state of the session."
           ::= { l2tpv3SessionStatsEntry 5 }

   l2tpv3SessionStatsCircuitStatus OBJECT-TYPE
           SYNTAX          Unsigned32
           MAX-ACCESS      read-only
           STATUS          current
           DESCRIPTION
               "The current status of the circuit forwarded by the
                session."
           ::= { l2tpv3SessionStatsEntry 6 }

   l2tpv3SessionStatsSerialNumber OBJECT-TYPE
           SYNTAX          Unsigned32
           MAX-ACCESS      read-only
           STATUS          current
           DESCRIPTION
               "The serial number that has been assigned to this
                session."
           ::= { l2tpv3SessionStatsEntry 7 }

   l2tpv3SessionStatsRxConnectSpeed OBJECT-TYPE
           SYNTAX          Unsigned32
           UNITS           "bits per second"
           MAX-ACCESS      read-only
           STATUS          current
           DESCRIPTION
               "The last known receive baud rate for this session."
           ::= { l2tpv3SessionStatsEntry 8 }

   l2tpv3SessionStatsTxConnectSpeed OBJECT-TYPE
           SYNTAX          Unsigned32
           UNITS           "bits per second"
           MAX-ACCESS      read-only
           STATUS          current
           DESCRIPTION
               "The last known transmit baud rate for this session."
           ::= { l2tpv3SessionStatsEntry 9 }

   l2tpv3SessionStatsPhysChannelID OBJECT-TYPE
           SYNTAX          Unsigned32
           MAX-ACCESS      read-only
           STATUS          current
           DESCRIPTION
               "The physical channel identifier for the session."
           ::= { l2tpv3SessionStatsEntry 10 }

   l2tpv3SessionStatsPrivateGroupID OBJECT-TYPE
           SYNTAX          SnmpAdminString
           MAX-ACCESS      read-only
           STATUS          current
           DESCRIPTION
               "The private group ID used for this L2TP session.  If no
                private group ID is found, then a null string is
                returned."
           ::= { l2tpv3SessionStatsEntry 11 }

   l2tpv3SessionStatsOutOfSeq OBJECT-TYPE
           SYNTAX          Counter32
           MAX-ACCESS      read-only
           STATUS          current
           DESCRIPTION
               "The total number of data packets received out of
                sequence for this session."
           ::= { l2tpv3SessionStatsEntry 12 }

   l2tpv3SessionStatsReassemblyTO OBJECT-TYPE
           SYNTAX          Counter32
           MAX-ACCESS      read-only
           STATUS          current
           DESCRIPTION
               "The number of reassembly timeouts that have occurred for
                this session."
           ::= { l2tpv3SessionStatsEntry 13 }

   l2tpv3SessionStatsTxSeq OBJECT-TYPE
           SYNTAX          Counter32
           MAX-ACCESS      read-only
           STATUS          current
           DESCRIPTION
               "The current sequence number for outgoing data packets
                for this session."
           ::= { l2tpv3SessionStatsEntry 14 }

   l2tpv3SessionStatsRxSeq OBJECT-TYPE
           SYNTAX          Counter32
           MAX-ACCESS      read-only
           STATUS          current
           DESCRIPTION
               "The current sequence number for incoming data packets
                for this session."
           ::= { l2tpv3SessionStatsEntry 15 }

   l2tpv3SessionStatsRxOctets OBJECT-TYPE
           SYNTAX          Counter32
           MAX-ACCESS      read-only
           STATUS          current
           DESCRIPTION
               "The number of data octets that have been received by
                this session."
           ::= { l2tpv3SessionStatsEntry 16 }

   l2tpv3SessionStatsRxPkts OBJECT-TYPE
           SYNTAX          Counter32
           MAX-ACCESS      read-only
           STATUS          current
           DESCRIPTION
               "The number of data packets that have been received by
                this session."
           ::= { l2tpv3SessionStatsEntry 17 }

   l2tpv3SessionStatsRxDrops OBJECT-TYPE
           SYNTAX          Counter32
           MAX-ACCESS      read-only
           STATUS          current
           DESCRIPTION
               "The number of received data packets that have been
                dropped by this session."
           ::= { l2tpv3SessionStatsEntry 18 }

   l2tpv3SessionStatsTxOctets OBJECT-TYPE
           SYNTAX          Counter32
           MAX-ACCESS      read-only
           STATUS          current
           DESCRIPTION
               "The number of data octets that have been sent by this
                session."
           ::= { l2tpv3SessionStatsEntry 19 }

   l2tpv3SessionStatsTxPkts OBJECT-TYPE
           SYNTAX          Counter32
           MAX-ACCESS      read-only
           STATUS          current
           DESCRIPTION
               "The number of data packets that have been sent by this
                session."
           ::= { l2tpv3SessionStatsEntry 20 }

   l2tpv3SessionStatsHCRxOctets OBJECT-TYPE
           SYNTAX          Counter64
           MAX-ACCESS      read-only
           STATUS          current
           DESCRIPTION
               "The 64-bit version of l2tpv3SessionStatsRxOctets."
           ::= { l2tpv3SessionStatsEntry 21 }

   l2tpv3SessionStatsHCRxPkts OBJECT-TYPE
           SYNTAX          Counter64
           MAX-ACCESS      read-only
           STATUS          current
           DESCRIPTION
               "The 64-bit version of l2tpv3SessionStatsRxPkts."
           ::= { l2tpv3SessionStatsEntry 22 }

   l2tpv3SessionStatsHCRxDrops OBJECT-TYPE
           SYNTAX          Counter64
           MAX-ACCESS      read-only
           STATUS          current
           DESCRIPTION
               "The 64-bit version of l2tpv3SessionStatsRxDrops."
           ::= { l2tpv3SessionStatsEntry 23 }

   l2tpv3SessionStatsHCTxOctets OBJECT-TYPE
           SYNTAX          Counter64
           MAX-ACCESS      read-only
           STATUS          current
           DESCRIPTION
               "The 64-bit version of l2tpv3SessionStatsTxOctets."
           ::= { l2tpv3SessionStatsEntry 24 }

   l2tpv3SessionStatsHCTxPkts OBJECT-TYPE
           SYNTAX          Counter64
           MAX-ACCESS      read-only
           STATUS          current
           DESCRIPTION
               "The 64-bit version of l2tpv3SessionStatsTxPkts."
           ::= { l2tpv3SessionStatsEntry 25 }

   --
   --      The L2TP Session Mapping Table
   --
   l2tpv3SessionMapTable   OBJECT-TYPE
           SYNTAX          SEQUENCE OF L2tpv3SessionMapEntry
           MAX-ACCESS      not-accessible
           STATUS          current
           DESCRIPTION
               "Table intended to assist management applications to map
                interfaces to control connection and session IDs."
           ::= { l2tpv3Objects 8 }

   l2tpv3SessionMapEntry   OBJECT-TYPE
           SYNTAX          L2tpv3SessionMapEntry
           MAX-ACCESS      not-accessible
           STATUS          current
           DESCRIPTION
               "An L2TP session index map entry."
           INDEX { l2tpv3SessionMapIfIndex }
           ::= { l2tpv3SessionMapTable 1 }

   L2tpv3SessionMapEntry ::=
           SEQUENCE {
               l2tpv3SessionMapIfIndex     InterfaceIndex,
               l2tpv3SessionMapCtrlIfIndex InterfaceIndex,
               l2tpv3SessionMapLocalID     Unsigned32,
               l2tpv3SessionMapStatus      RowStatus
           }

   l2tpv3SessionMapIfIndex   OBJECT-TYPE
           SYNTAX          InterfaceIndex
           MAX-ACCESS      not-accessible
           STATUS          current
           DESCRIPTION
               "The ifIndex value of the interface being forwarded via
                an L2TP session.  For example, the interface could be an
                Ethernet interface on an LAC or a virtual PPP interface
                on the LNS."
           ::= { l2tpv3SessionMapEntry 1 }

   l2tpv3SessionMapCtrlIfIndex OBJECT-TYPE
           SYNTAX          InterfaceIndex
           MAX-ACCESS      read-create
           STATUS          current
           DESCRIPTION
               "The ifIndex value of the session's control connection.
                The object establishes a binding between a particular
                interface identified by l2tpv3SessionMapIfIndex to a
                particular control connection."
           ::= { l2tpv3SessionMapEntry 2 }

   l2tpv3SessionMapLocalID OBJECT-TYPE
           SYNTAX          Unsigned32
           MAX-ACCESS      read-only
           STATUS          current
           DESCRIPTION
               "The local session ID for this session."
           ::= { l2tpv3SessionMapEntry 3 }

   l2tpv3SessionMapStatus  OBJECT-TYPE
           SYNTAX          RowStatus
           MAX-ACCESS      read-create
           STATUS          current
           DESCRIPTION
               "The status of this session map entry."
           ::= { l2tpv3SessionMapEntry 4 }

   --
   --      Definition of generic L2TP notifications
   --
   l2tpv3CtrlAuthFailure   NOTIFICATION-TYPE
           OBJECTS {
               l2tpv3CtrlStatsInitiated,
               l2tpv3CtrlStatsRemoteHostName
           }
           STATUS          current
           DESCRIPTION
               "Trap signifying that an attempt to establish a control
                connection to a remote peer has failed authentication."
           ::= { l2tpv3Notifications 1 }

   --
   --      Conformance information
   --
   l2tpv3Groups      OBJECT IDENTIFIER ::= { l2tpv3Conformance 1 }
   l2tpv3Compliances OBJECT IDENTIFIER ::= { l2tpv3Conformance 2 }
   --
   --      Compliance statements
   --
   l2tpv3MIBFullCompliance MODULE-COMPLIANCE
           STATUS          current
           DESCRIPTION
               "An implementation claims full compliance when this MIB
                is implemented with support for read-create and read-
                write operations, thereby allowing configuration and
                monitoring, respectively."

           MODULE    -- this module

        -- unconditionally mandatory groups
           MANDATORY-GROUPS {
                                l2tpv3CfgGroup,
                                l2tpv3StatsGroup,
                                l2tpv3TrapGroup
                            }

        -- optional Mapping Group
           GROUP           l2tpv3MappingGroup
           DESCRIPTION
               "Optional group for L2TP devices that provide index
                mapping."

        -- optional Security Group
           GROUP           l2tpv3SecurityGroup
           DESCRIPTION
               "Optional group for SNMP agents that support both
                authentication and privacy of SNMP messages for the
                management of L2TP keys."

        -- optional High Capacity Group
           GROUP           l2tpv3HCPacketGroup
           DESCRIPTION
               "Optional group for implementations that cannot overflow
                the 32-bit packet and byte counters in less than one
                hour.  Mandatory otherwise."

          ::= { l2tpv3Compliances 1 }

   l2tpv3MIBReadOnlyCompliance MODULE-COMPLIANCE
           STATUS          current
           DESCRIPTION
               "An implementation claims read-only compliance when this
                MIB is implemented without support for read-create and
                read-write operations (i.e. operates in read-only mode),
                thereby allowing monitoring but not configuration."

           MODULE    -- this module

        -- unconditionally mandatory groups
           MANDATORY-GROUPS {
                                l2tpv3CfgGroup,
                                l2tpv3StatsGroup,
                                l2tpv3TrapGroup
                            }

           OBJECT          l2tpv3StackCfgAdminState
           MIN-ACCESS      read-only
           DESCRIPTION
               "Write access is not required."

           OBJECT          l2tpv3StackCfgDrain
           MIN-ACCESS      read-only
           DESCRIPTION
               "Write access is not required."

           OBJECT          l2tpv3CtrlCfgRouterID
           MIN-ACCESS      read-only
           DESCRIPTION
               "Write access is not required."

           OBJECT          l2tpv3CtrlCfgTransport
           MIN-ACCESS      read-only
           DESCRIPTION
               "Write access is not required."

           OBJECT          l2tpv3CtrlCfgPWCap
           MIN-ACCESS      read-only
           DESCRIPTION
               "Write access is not required."

           OBJECT          l2tpv3CtrlCfgFallback
           MIN-ACCESS      read-only
           DESCRIPTION
               "Write access is not required."

           OBJECT          l2tpv3CtrlCfgDrain
           MIN-ACCESS      read-only
           DESCRIPTION
               "Write access is not required."

           OBJECT          l2tpv3CtrlCfgAuth
           MIN-ACCESS      read-only
           DESCRIPTION
               "Write access is not required."

           OBJECT          l2tpv3CtrlCfgSecret
           MIN-ACCESS      read-only
           DESCRIPTION
               "Write access is not required."

           OBJECT          l2tpv3CtrlCfgSecurity
           MIN-ACCESS      read-only
           DESCRIPTION
               "Write access is not required."

           OBJECT          l2tpv3CtrlCfgHelloInt
           MIN-ACCESS      read-only
           DESCRIPTION
               "Write access is not required."

           OBJECT          l2tpv3CtrlCfgRWS
           MIN-ACCESS      read-only
           DESCRIPTION
               "Write access is not required."

           OBJECT          l2tpv3CtrlCfgMaxRetrans
           MIN-ACCESS      read-only
           DESCRIPTION
               "Write access is not required."

           OBJECT          l2tpv3CtrlCfgMaxRetransTO
           MIN-ACCESS      read-only
           DESCRIPTION
               "Write access is not required."

           OBJECT          l2tpv3CtrlCfgReassemblyTO
           MIN-ACCESS      read-only
           DESCRIPTION
               "Write access is not required."

           OBJECT          l2tpv3CtrlCfgIdleTO
           MIN-ACCESS      read-only
           DESCRIPTION
               "Write access is not required."

           OBJECT          l2tpv3SessionCfgLocalID
           MIN-ACCESS      read-only
           DESCRIPTION
               "Write/create access is not required."

           OBJECT          l2tpv3SessionCfgRemoteID
           MIN-ACCESS      read-only
           DESCRIPTION
               "Write/create access is not required."

           OBJECT          l2tpv3SessionCfgCtrlLocalID
           MIN-ACCESS      read-only
           DESCRIPTION
               "Write/create access is not required."

           OBJECT          l2tpv3SessionCfgPWType
           MIN-ACCESS      read-only
           DESCRIPTION
               "Write/create access is not required."

           OBJECT          l2tpv3SessionCfgEndID
           MIN-ACCESS      read-only
           DESCRIPTION
               "Write/create access is not required."

           OBJECT          l2tpv3SessionCfgAppID
           MIN-ACCESS      read-only
           DESCRIPTION
               "Write/create access is not required."

           OBJECT          l2tpv3SessionCfgPWEncap
           MIN-ACCESS      read-only
           DESCRIPTION
               "Write/create access is not required."

           OBJECT          l2tpv3SessionCfgSeq
           MIN-ACCESS      read-only
           DESCRIPTION
               "Write/create access is not required."

           OBJECT          l2tpv3SessionCfgLocalCookie
           MIN-ACCESS      read-only
           DESCRIPTION
               "Write/create access is not required."

           OBJECT          l2tpv3SessionCfgRemoteCookie
           MIN-ACCESS      read-only
           DESCRIPTION
               "Write/create access is not required."

           OBJECT          l2tpv3SessionCfgCallType
           MIN-ACCESS      read-only
           DESCRIPTION
               "Write/create access is not required."

        -- optional Mapping Group
           GROUP           l2tpv3MappingGroup
           DESCRIPTION
               "Optional group for L2TP devices that provide index
                mapping."

           OBJECT          l2tpv3SessionMapCtrlIfIndex
           MIN-ACCESS      read-only
           DESCRIPTION
               "Write access is not required."

           OBJECT          l2tpv3SessionMapStatus
           MIN-ACCESS      read-only
           DESCRIPTION
               "Write access is not required."

        -- optional Security Group
           GROUP           l2tpv3SecurityGroup
           DESCRIPTION
               "Optional group for SNMP agents that support both
                authentication and privacy of SNMP messages for the
                management of L2TP keys."

        -- optional High Capacity Group
           GROUP           l2tpv3HCPacketGroup
           DESCRIPTION
               "Optional group for implementations that cannot overflow
                the 32-bit packet and byte counters in less than one
                hour.  Mandatory otherwise."
           ::= { l2tpv3Compliances 2 }

   --
   -- Units of conformance
   --
   l2tpv3CfgGroup          OBJECT-GROUP
           OBJECTS {
               l2tpv3StackCfgAdminState,
               l2tpv3StackCfgDrain,
               l2tpv3CtrlCfgRouterID,
               l2tpv3CtrlCfgTransport,
               l2tpv3CtrlCfgPWCap,
               l2tpv3CtrlCfgFallback,
               l2tpv3CtrlCfgDrain,
               l2tpv3CtrlCfgAuth,
               l2tpv3CtrlCfgSecret,
               l2tpv3CtrlCfgSecurity,
               l2tpv3CtrlCfgHelloInt,
               l2tpv3CtrlCfgRWS,
               l2tpv3CtrlCfgMaxRetrans,
               l2tpv3CtrlCfgMaxRetransTO,
               l2tpv3CtrlCfgReassemblyTO,
               l2tpv3CtrlCfgIdleTO,
               l2tpv3SessionCfgLocalID,
               l2tpv3SessionCfgRemoteID,
               l2tpv3SessionCfgCtrlLocalID,
               l2tpv3SessionCfgPWType,
               l2tpv3SessionCfgEndID,
               l2tpv3SessionCfgAppID,
               l2tpv3SessionCfgPWEncap,
               l2tpv3SessionCfgSeq,
               l2tpv3SessionCfgLocalCookie,
               l2tpv3SessionCfgRemoteCookie,
               l2tpv3SessionCfgCallType
           }
           STATUS          current
           DESCRIPTION
               "A collection of objects providing configuration
                information of the L2TP stack, its control connections,
                and its sessions."
           ::= { l2tpv3Groups 1 }

   l2tpv3StatsGroup                OBJECT-GROUP
           OBJECTS {
               l2tpv3StackStatsVersion,
               l2tpv3StackStatsRevision,
               l2tpv3StackStatsVendorName,
               l2tpv3StackStatsAdminState,
               l2tpv3StackStatsIsDraining,
               l2tpv3StackStatsNumCtrlEst,
               l2tpv3StackStatsNumSessEst,
               l2tpv3CtrlStatsLocalID,
               l2tpv3CtrlStatsRemoteID,
               l2tpv3CtrlStatsState,
               l2tpv3CtrlStatsIsDraining,
               l2tpv3CtrlStatsInitiated,
               l2tpv3CtrlStatsRemoteRouterID,
               l2tpv3CtrlStatsRemoteHostName,
               l2tpv3CtrlStatsRemoteVendorName,
               l2tpv3CtrlStatsRemoteVersion,
               l2tpv3CtrlStatsRemotePWCap,
               l2tpv3CtrlStatsInitialRemoteRWS,
               l2tpv3CtrlStatsCtrlRxZLB,
               l2tpv3CtrlStatsCtrlOutOfSeq,
               l2tpv3CtrlStatsCtrlOutOfWindow,
               l2tpv3CtrlStatsCtrlTxZLB,
               l2tpv3CtrlStatsCtrlAckTO,
               l2tpv3CtrlStatsCurrentRemoteRWS,
               l2tpv3CtrlStatsTxSeq,
               l2tpv3CtrlStatsRxSeq,
               l2tpv3CtrlStatsNumSessCumEst,
               l2tpv3CtrlStatsNumSessCurrentEst,
               l2tpv3CtrlStatsNumSessFailed,
               l2tpv3CtrlStatsLastResultCode,
               l2tpv3CtrlStatsLastErrorCode,
               l2tpv3CtrlStatsLastErrorMessage,
               l2tpv3CtrlStatsCtrlRxOctets,
               l2tpv3CtrlStatsCtrlRxPkts,
               l2tpv3CtrlStatsCtrlTxOctets,
               l2tpv3CtrlStatsCtrlTxPkts,
               l2tpv3CtrlStatsDataRxOctets,
               l2tpv3CtrlStatsDataRxPkts,
               l2tpv3CtrlStatsDataRxDrops,
               l2tpv3CtrlStatsDataTxOctets,
               l2tpv3CtrlStatsDataTxPkts,
               l2tpv3SessionStatsRemoteEndID,
               l2tpv3SessionStatsRemoteAppID,
               l2tpv3SessionStatsRemotePWEncap,
               l2tpv3SessionStatsRemoteSeq,
               l2tpv3SessionStatsState,
               l2tpv3SessionStatsCircuitStatus,
               l2tpv3SessionStatsSerialNumber,
               l2tpv3SessionStatsRxConnectSpeed,
               l2tpv3SessionStatsTxConnectSpeed,
               l2tpv3SessionStatsPhysChannelID,
               l2tpv3SessionStatsPrivateGroupID,
               l2tpv3SessionStatsOutOfSeq,
               l2tpv3SessionStatsReassemblyTO,
               l2tpv3SessionStatsTxSeq,
               l2tpv3SessionStatsRxSeq,
               l2tpv3SessionStatsRxOctets,
               l2tpv3SessionStatsRxPkts,
               l2tpv3SessionStatsRxDrops,
               l2tpv3SessionStatsTxOctets,
               l2tpv3SessionStatsTxPkts
           }
           STATUS          current
           DESCRIPTION
               "A collection of objects providing status and statistics
                of the L2TP stack, its control connections, and its
                sessions."
           ::= { l2tpv3Groups 2 }

   l2tpv3MappingGroup      OBJECT-GROUP
           OBJECTS {
               l2tpv3CtrlMapIfIndex,
               l2tpv3SessionMapCtrlIfIndex,
               l2tpv3SessionMapLocalID,
               l2tpv3SessionMapStatus
           }
           STATUS          current
           DESCRIPTION
               "A collection of objects providing index mapping."
           ::= { l2tpv3Groups 3 }

   l2tpv3SecurityGroup     OBJECT-GROUP
           OBJECTS {
               l2tpv3CtrlCfgAuth,
               l2tpv3CtrlCfgSecret,
               l2tpv3CtrlCfgSecurity
           }
           STATUS          current
           DESCRIPTION
               "A collection of objects providing L2TP security
                configuration."
           ::= { l2tpv3Groups 4 }

   l2tpv3TrapGroup         NOTIFICATION-GROUP
           NOTIFICATIONS {
               l2tpv3CtrlAuthFailure
           }
           STATUS          current
           DESCRIPTION
               "A collection of L2TP trap events as specified in
                NOTIFICATION-TYPE constructs."
           ::= { l2tpv3Groups 5 }

   l2tpv3HCPacketGroup     OBJECT-GROUP
           OBJECTS {
               l2tpv3CtrlStatsCtrlHCRxOctets,
               l2tpv3CtrlStatsCtrlHCRxPkts,
               l2tpv3CtrlStatsCtrlHCTxOctets,
               l2tpv3CtrlStatsCtrlHCTxPkts,
               l2tpv3CtrlStatsDataHCRxOctets,
               l2tpv3CtrlStatsDataHCRxPkts,
               l2tpv3CtrlStatsDataHCRxDrops,
               l2tpv3CtrlStatsDataHCTxOctets,
               l2tpv3CtrlStatsDataHCTxPkts,
               l2tpv3SessionStatsHCRxOctets,
               l2tpv3SessionStatsHCRxPkts,
               l2tpv3SessionStatsHCRxDrops,
               l2tpv3SessionStatsHCTxOctets,
               l2tpv3SessionStatsHCTxPkts
            }
           STATUS          current
           DESCRIPTION
               "A collection of objects providing high-capacity 64-bit
                counter objects."
           ::= { l2tpv3Groups 6 }

   END
