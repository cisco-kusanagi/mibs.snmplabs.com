--  @(#)ph-atm.mib	1.5 3/6/97
POWERHUB-ATM-MIB DEFINITIONS ::= BEGIN

        IMPORTS
            enterprises, OBJECT-TYPE, NetworkAddress, IpAddress,
            Counter, Gauge, TimeTicks FROM RFC1155-SMI
			TRAP-TYPE FROM RFC-1215                 

            DisplayString, PhysAddress FROM RFC1213-MIB;

	fore		OBJECT IDENTIFIER ::= { enterprises 326 }
	systems		OBJECT IDENTIFIER ::= { fore 2 }
	lsd		OBJECT IDENTIFIER ::= { systems 6 }

	lsdproducts	OBJECT IDENTIFIER ::= { lsd 1 }
	lsdcommon	OBJECT IDENTIFIER ::= { lsd 2 }

	powerhub4k6k7k	OBJECT IDENTIFIER ::= { lsdproducts 1 }
	powerbits	OBJECT IDENTIFIER ::= { lsdproducts 2 }

	alchassis	OBJECT IDENTIFIER ::= { powerhub4k6k7k 1 }
	alatm		OBJECT IDENTIFIER ::= { powerhub4k6k7k 2 }


        -- READ THIS!!!!!
	-- PowerHub OID branch allocations
	--      NOTE: Do NOT uncomment the mib branches below!!.
	--            This is shown here to get a general idea on
	--            the powerhub mib subtree layout while viewing
	--            this file.
	--

	-- fore		OBJECT IDENTIFIER ::= { enterprises 326 }
	-- systems	OBJECT IDENTIFIER ::= { fore 2 }
	-- lsd		OBJECT IDENTIFIER ::= { systems 6 }

	-- lsdproducts	OBJECT IDENTIFIER ::= { lsd 1 }
	-- lsdcommon	OBJECT IDENTIFIER ::= { lsd 2 }

	-- powerhub4k6k7k OBJECT IDENTIFIER ::= { lsdproducts 1 }
	-- powerbits	OBJECT IDENTIFIER ::= { lsdproducts 2 }

	-- alchassis	OBJECT IDENTIFIER ::= { powerhub4k6k7k 1 }
	-- alatm		OBJECT IDENTIFIER ::= { powerhub4k6k7k 2 }

	-- alsystem	OBJECT IDENTIFIER ::= { lsdcommon 1 }
	-- albridge	OBJECT IDENTIFIER ::= { lsdcommon 2 }
	-- almgmt	OBJECT IDENTIFIER ::= { lsdcommon 3 }
	-- alrip	OBJECT IDENTIFIER ::= { lsdcommon 4 }
	-- altcp	OBJECT IDENTIFIER ::= { lsdcommon 5 }
	-- alip		OBJECT IDENTIFIER ::= { lsdcommon 6 }
	-- alat		OBJECT IDENTIFIER ::= { lsdcommon 7 }
	-- aldecnet	OBJECT IDENTIFIER ::= { lsdcommon 8 }
	-- alipx	OBJECT IDENTIFIER ::= { lsdcommon 9 }
	-- alsnmp	OBJECT IDENTIFIER ::= { lsdcommon 10 }

                alAtmAMASlotTable OBJECT-TYPE
                        SYNTAX  SEQUENCE OF AlAtmAMASlotEntry
                        ACCESS  not-accessible
                        STATUS  mandatory
                        DESCRIPTION
                        "A table that contains information about
                         AMA for ATM slot in the PowerHub 7000 chassis."

                        ::= { alatm 8 }
 
                alAtmAMASlotEntry OBJECT-TYPE
                        SYNTAX  AlAtmAMASlotEntry
                        ACCESS  not-accessible
                        STATUS  mandatory
                        DESCRIPTION
                                "AMA information about a specific slot."
                        INDEX   { alAtmAMASlotNumber }
 
                        ::= { alAtmAMASlotTable 1 }

                AlAtmAMASlotEntry ::=
                        SEQUENCE {
                                        alAtmAMASlotNumber
                                                INTEGER,
                                        alAtmAMAUserSelect
                                                INTEGER,
                                        alAtmAMAActualUse
                                                INTEGER,
                                        alAtmAMAUTLevPrime
                                                INTEGER,
                                        alAtmAMAUTLevBack
                                                INTEGER,
                                        alAtmAMAUTVerPrime
                                                INTEGER,
                                        alAtmAMAUTVerBack
                                                INTEGER,
                                        alAtmAMAProtoPrime
                                                INTEGER,
                                        alAtmAMAProtoBack
                                                INTEGER,
                                        alAtmAMAMediaPrime
                                                INTEGER,
                                        alAtmAMAMediaBack
                                                INTEGER,
					alAtmPreviousAMA
                                                INTEGER,
                                        alAtmPreviousAMAType
                                                INTEGER,
                                        alAtmCurrentAMAType
                                                INTEGER

                                }


                alAtmAMASlotNumber OBJECT-TYPE
                        SYNTAX  INTEGER
                        ACCESS  read-only
                        STATUS  mandatory
                        DESCRIPTION
                        "The slot number for which the following AMA
                         information applies."

                ::= { alAtmAMASlotEntry 1 }

                alAtmAMAUserSelect OBJECT-TYPE
                        SYNTAX  INTEGER {
				    primary(1),
				    backup(2)
				}
                        ACCESS  read-write
                        STATUS  mandatory
                        DESCRIPTION
			"The user specified AMA for normal operation.
			 Unless the user explicitly changes the AMA 
			 assignments, the software uses the primary 
			 AMA by default and the backup AMA only if 
                         the link to the primary AMA fails."

                ::= { alAtmAMASlotEntry 2 }

                alAtmAMAActualUse OBJECT-TYPE
                        SYNTAX  INTEGER {
				    primary(1),
				    backup(2)
				}
                        ACCESS  read-only
                        STATUS  mandatory
                        DESCRIPTION
			"The AMA that is actually being used. If the 
			 link to the primary AMA fails, this field 
                         shows that the backup AMA is in use, even
			 though the primary AMA was selected for 
		         use."

                ::= { alAtmAMASlotEntry 3 }

                alAtmAMAUTLevPrime OBJECT-TYPE
                        SYNTAX  INTEGER
                        ACCESS  read-only
                        STATUS  mandatory
                        DESCRIPTION
			"The PHY UTOPIA level in use by the
			 PowerCell module and the Primary AMA.
			 UTOPIA is an ATM standard for 
		         communication between the PowerCell 
			 module and the PHY (AMA). The level can
			 be 1 or 2."

                ::= { alAtmAMASlotEntry 4 }


                alAtmAMAUTLevBack OBJECT-TYPE
                        SYNTAX  INTEGER
                        ACCESS  read-only
                        STATUS  mandatory
 	                DESCRIPTION
			"The PHY UTOPIA level in use by the
                         PowerCell module and the Backup AMA.
                         UTOPIA is an ATM standard for
                         communication between the PowerCell
                         module and the PHY (AMA). The level can
                         be 1 or 2. Returns value '1000' if 
			 Backup AMA is not installed"

                ::= { alAtmAMASlotEntry 5 }

                alAtmAMAUTVerPrime OBJECT-TYPE
                        SYNTAX  INTEGER
                        ACCESS  read-only
                        STATUS  mandatory
                        DESCRIPTION
			"The version of the PHY UTOPIA in use by the
                         PowerCell module and the Primary AMA."

                ::= { alAtmAMASlotEntry 6 }

                alAtmAMAUTVerBack OBJECT-TYPE
                        SYNTAX  INTEGER
                        ACCESS  read-only
                        STATUS  mandatory
                        DESCRIPTION
			"The version of the PHY UTOPIA in use by the
                         PowerCell module and the Backup AMA. Returns
			 value '1000' if Backup AMA is not installed"

                ::= { alAtmAMASlotEntry 7 }

                alAtmAMAProtoPrime OBJECT-TYPE
                        SYNTAX  INTEGER {
				    oc3-155Mbps(1),
				    ds3-45Mbps(2),
				    e3-39Mbps(3),
				    unknown(4)
				}
                        ACCESS  read-only
                        STATUS  mandatory
                        DESCRIPTION
			"The PHY-layer protocol in use on the
                         Primary AMA. The protocol can be one
                         of the following:
                         155M OC3 - 155 Mb/s using an OC-3 connector
                         45M  DS3 - 45  Mb/s using a DS3 connector
                         39M  E3  - 39  Mb/s using an E3 connector"

                ::= { alAtmAMASlotEntry 8 }

                alAtmAMAProtoBack OBJECT-TYPE
                        SYNTAX  INTEGER {
				    oc3-155Mbps(1),
				    ds3-45Mbps(2),
				    e3-39Mbps(3),
				    unknown(4)
				}
                        ACCESS  read-only
                        STATUS  mandatory
                        DESCRIPTION
			"The PHY-layer protocol in use on the
                         Backup AMA. The protocol can be one
                         of the following:
                         155M OC3 - 155 Mb/s using an OC-3 connector
                         45M  DS3 - 45  Mb/s using a DS3 connector
                         39M  E3  - 39  Mb/s using an E3 connector"

                ::= { alAtmAMASlotEntry 9 }

                alAtmAMAMediaPrime OBJECT-TYPE
                        SYNTAX  INTEGER {
				    cat5utp(1),
				    coax(2),
				    mf(3),
				    sf(4),
				    unknown(5)
				}
                        ACCESS  read-only
                        STATUS  mandatory
                        DESCRIPTION
		        "The type of cable connecting the Primary
			 AMA to the ATM switch. The cable type 
			 can be one of the following:
			 CAT5 UTP
			 Coaxial Cable
			 Multimode Fiber
			 Single Mode Fiber"
	
                ::= { alAtmAMASlotEntry 10 }

                alAtmAMAMediaBack OBJECT-TYPE
                        SYNTAX  INTEGER {
				    cat5utp(1),
				    coax(2),
				    mf(3),
				    sf(4),
				    unknown(5)
				}
                        ACCESS  read-only
                        STATUS  mandatory
                        DESCRIPTION
			"The type of cable connecting the Backup 
                         AMA to the ATM switch. The cable type 
                         can be one of the following: 
                         CAT5 UTP 
                         Coaxial Cable 
                         Multimode Fiber 
                         Single Mode Fiber" 

                ::= { alAtmAMASlotEntry 11 }

                alAtmPreviousAMA OBJECT-TYPE
                        SYNTAX  INTEGER {
				    primary(1),
				    backup(2),
				    unknown(3)
				}
                        ACCESS  read-only
                        STATUS  mandatory
                        DESCRIPTION
			"The AMA that is actually being used before
                         link down or cut over. The initial value
			 is notset."
                ::= { alAtmAMASlotEntry 12 }

                alAtmPreviousAMAType OBJECT-TYPE
                        SYNTAX  INTEGER {
				    oc3-155Mbps(1),
				    ds3-45Mbps(2),
				    e3-39Mbps(3),
				    unknown(4)
				}
                        ACCESS  read-only
                        STATUS  mandatory
                        DESCRIPTION
			"The PHY-layer protocol in use before
                         link down or cut-over. 
                         The protocol can be one of the following:
                         155M OC3 - 155 Mb/s using an OC-3 connector
                         45M  DS3 - 45  Mb/s using a DS3 connector
                         39M  E3  - 39  Mb/s using an E3 connector."
                ::= { alAtmAMASlotEntry 13 }

                alAtmCurrentAMAType OBJECT-TYPE
                        SYNTAX  INTEGER {
				    oc3-155Mbps(1),
				    ds3-45Mbps(2),
				    e3-39Mbps(3)
				}
                        ACCESS  read-only
                        STATUS  mandatory
                        DESCRIPTION
			"The PHY-layer protocol actually in use. 
                         The protocol can be one of the following:
                         155M OC3 - 155 Mb/s using an OC-3 connector
                         45M  DS3 - 45  Mb/s using a DS3 connector
                         39M  E3  - 39  Mb/s using an E3 connector."
                ::= { alAtmAMASlotEntry 14 }

 -- Traps for use by ATM

   atmLinkUp TRAP-TYPE
       ENTERPRISE alatm
       VARIABLES { alAtmAMASlotNumber, 
		   alAtmAMAActualUse, alAtmCurrentAMAType }
       DESCRIPTION
		"A LinkUp trap is sent by the ATM interface
                 while link up is dected. The slot id is reported
                 because individual virtual port number is not applicable 
                 here."
       ::= 1

   atmLinkDown TRAP-TYPE
       ENTERPRISE alatm
       VARIABLES { alAtmAMASlotNumber, alAtmPreviousAMA, 
		   alAtmPreviousAMAType }
       DESCRIPTION
			"A LinkDown trap is sent by the ATM interface
             while link down is dected. The slot id is reported
             because individual virtual port number is not applicable 
             here."
       ::= 2

   atmCutOver TRAP-TYPE
      ENTERPRISE alatm
      VARIABLES { alAtmAMASlotNumber,alAtmAMAActualUse,
		  alAtmCurrentAMAType,alAtmPreviousAMA,alAtmPreviousAMAType }
      DESCRIPTION
	       "A trap is sent if cut over is dected. The cut over 
            can be from primary to back or vice versa."
      ::= 3

   atmBootUp TRAP-TYPE
       ENTERPRISE alatm
       VARIABLES { alAtmAMASlotNumber, alAtmAMAActualUse,
		   alAtmCurrentAMAType }
       DESCRIPTION
			"A BootUp trap is sent by the ATM interface
             while startup  is dected. The slot id is reported
             because individual virtual port number is not applicable 
             here."
       ::= 4

   atmFault TRAP-TYPE
       ENTERPRISE alatm
       VARIABLES { alAtmAMASlotNumber } 
       DESCRIPTION
		"A Fault trap is sent by the ATM interface
         while a series of link down is dected. The slot id is reported
         because individual virtual port number is not applicable 
         here."
       ::= 5
END
