-- Module not found
-- created from scratch by circitor

SONOMASYSTEMS-SONOMA-MIB DEFINITIONS ::= BEGIN
      IMPORTS
        enterprises
        FROM RFC1155-SMI;

    -- enterprises OBJECT IDENTIFIER ::= { private 4 }
     sonomaSystems OBJECT IDENTIFIER ::= {  enterprises 2926 }
     sonomaSeries OBJECT IDENTIFIER ::= { sonomaSystems 25 }
     sonomaATM OBJECT IDENTIFIER ::= { sonomaSeries 7 }
     sonomaLAN       OBJECT IDENTIFIER ::= { sonomaSeries 5 }
     sonomaApplications OBJECT IDENTIFIER ::= { sonomaSeries 8 }
     sonomaRouting OBJECT IDENTIFIER ::= { sonomaSeries 4 }
     sonomaBridging OBJECT IDENTIFIER ::= { sonomaSeries 3 }
END
