PANDATEL-ETC-MODEM-MIB DEFINITIONS ::= BEGIN

 -- This is the private mib group section for the ETC modems.
 -- Because these modems must be installed in the PANDATEL modem rack
 -- the PANDATEL-MODEM-MIB also applies.


 -- Ver.1.00    Nov.21.2000

        IMPORTS
                enterprises
                        FROM RFC1155-SMI
                DisplayString
                        FROM RFC1213-MIB
                OBJECT-TYPE
                        FROM RFC-1212
                mdmSpecifics, device-id
                        FROM PANDATEL-MODEM-MIB;

-- ********************** THE MDM-ETC SUBTREE ******************************

-- the specific identifier is identical to the modem type integer
-- of the ETC modem entries in the PANDATEL-MODEM-MIB mdmModemTable.

etc-modem      OBJECT IDENTIFIER ::= { device-id 901 }     -- chassis-mib

etc            OBJECT IDENTIFIER ::= { mdmSpecifics 901 }  -- this subtree

etcModemTable OBJECT-TYPE
        SYNTAX  SEQUENCE OF EtcTableEntry
        ACCESS  not-accessible
        STATUS  mandatory
        DESCRIPTION
                "The table of all ETC modems in this housing."
        ::= { etc 1 }

etcTableEntry OBJECT-TYPE
        SYNTAX  EtcTableEntry
        ACCESS  not-accessible
        STATUS  mandatory
        DESCRIPTION
                "The index of the table."
        INDEX   { mdmRack, mdmModem, mdmPosition }
        ::= { etcModemTable 1 }

EtcTableEntry ::= SEQUENCE {
        mdmRack
                INTEGER,
        mdmModem
                INTEGER,
        mdmPosition
                INTEGER,
        mdmModemName
                DisplayString,
        mdmDataEquipmentEmulation
                INTEGER,
        mdmModemProperty
                INTEGER,
        mdmAlarm
                INTEGER,
        mdmRemoteAccessMode
                INTEGER,
        mdmForcedRemoteAccess
                INTEGER,
        mdmOperationMode
                INTEGER,
        mdmFoPower
                INTEGER,
        mdmAutoDetectModemProperty
                INTEGER,
        mdmInterfaceAlarmCondition
                INTEGER,
        mdmLineAlarmCondition
                INTEGER,
        mdmStatusInterfacePort
                INTEGER,
        mdmStatusLinePort
                INTEGER
        }

mdmRack OBJECT-TYPE
        SYNTAX  INTEGER
        ACCESS  read-only
        STATUS  mandatory
        DESCRIPTION
                "The index of the rack where the modem is installed."
        ::= { etcTableEntry 1 }

mdmModem OBJECT-TYPE
        SYNTAX  INTEGER
        ACCESS  read-only
        STATUS  mandatory
        DESCRIPTION
                "This variable displays the slot number where the
                 corresponding modem is installed in the rack."
        ::= { etcTableEntry 2 }

mdmPosition OBJECT-TYPE
        SYNTAX  INTEGER {
                local  (1),
                remote (2)
        }
        ACCESS  read-only
        STATUS  mandatory
        DESCRIPTION
                "This variable displays the location of the corresponding
                 modem: 'local' or 'remote'.
                 The modem which is plugged into a managed rack is 'local',
                 the counterpart is 'remote'."
        ::= { etcTableEntry 3 }

mdmModemName OBJECT-TYPE
        SYNTAX  DisplayString
        ACCESS  read-only
        STATUS  mandatory
        DESCRIPTION
                "A verbal name of this modem."
        ::= { etcTableEntry 5 }

mdmDataEquipmentEmulation OBJECT-TYPE
        SYNTAX  INTEGER {
                other       (1),
                to-hub      (8),
                to-nic      (9),
				unknown     (99)
        }
        ACCESS  read-only
        STATUS  mandatory
        DESCRIPTION
                "Interface mode of the unit: 'dte' or 'dce', 'te' or 'nt'."
        ::= { etcTableEntry 6 }

mdmModemProperty OBJECT-TYPE
        SYNTAX  INTEGER {
                other                     (1),
                eth100base-tx-full-duplex (16),
                eth100base-tx-half-duplex (17),
                unknown                   (99)
        }
        ACCESS  read-write
        STATUS  mandatory
        DESCRIPTION
                "The speed class of the unit: 'eth100base-tx-full-duplex' 
                 or 'eth100base-tx-half-duplex'."
        ::= { etcTableEntry 7 }

mdmAlarm OBJECT-TYPE
        SYNTAX  INTEGER {
                other (1),
                off   (2),
                on    (3)
        }
        ACCESS  read-only
        STATUS  mandatory
        DESCRIPTION
                "The status of local alarm: 'off' or 'on'."
        ::= { etcTableEntry 15 }

mdmRemoteAccessMode OBJECT-TYPE
        SYNTAX  INTEGER {
                other                    (1),
                enable                   (5),
                disable-local            (8),
                disable-local-and-remote (9)
        }
        ACCESS  read-write
        STATUS  mandatory
        DESCRIPTION
                "The possibility of remote management: 'enabled', 'disabled local' 
                 or 'disable local and remote'. 
                 Once disabled management at local and remote unit, it is not possible 
                 to enable it at the remote unit again."
        ::= { etcTableEntry 64 }

mdmForcedRemoteAccess OBJECT-TYPE
        SYNTAX  INTEGER {
                off         (1),
                on          (2)
        }
        ACCESS  read-write
        STATUS  mandatory
        DESCRIPTION
                "Activation of remote management: 'on' or 'off'.
                 Status 'on' enables management of remote unit. During this
                 process the link is restricted to management data. The
                 transmission of user data is interrupted.
                 Status 'off' disables management of remote unit. The link
                 transmits user data."
        ::= { etcTableEntry 65 }

mdmOperationMode OBJECT-TYPE
        SYNTAX  INTEGER {
                other                  (1),
                normal                 (7),
                remote-fault-detection (8),
                link-pass-through      (9)
        }
        ACCESS  read-write
        STATUS  mandatory
        DESCRIPTION
                "The possibility of operation mode: 'normal', 'remote-fault-detection mode' 
                 or 'link-pass-through'."
        ::= { etcTableEntry 66 }

mdmFoPower OBJECT-TYPE
        SYNTAX  INTEGER {
                other (1),
                low   (2),
                high  (3)
        }
        ACCESS  read-only
        STATUS  mandatory
        DESCRIPTION
                "The status of transmitter power: 'low' or 'high'."
        ::= { etcTableEntry 71 }

mdmAutoDetectModemProperty OBJECT-TYPE
        SYNTAX  INTEGER {
                other (1),
                off   (2),
                on    (3)
        }
        ACCESS  read-write
        STATUS  mandatory
        DESCRIPTION
                "The status of auto detect of modem property: 'off' or 'on'."
        ::= { etcTableEntry 74 }

mdmInterfaceAlarmCondition OBJECT-TYPE
        SYNTAX  INTEGER {
                other                        (1),
                disable                      (2),
                no-link-signal               (3),
                not-available                (100)
        }
        ACCESS  read-write
        STATUS  mandatory
        DESCRIPTION
                "The alarm trigger mode at interface port: 'disable', i.e. no alarm
                 is triggered, 'no-link-signal', i.e. an alarm is triggered if
                 the link is down."
        ::= { etcTableEntry 98 }

mdmLineAlarmCondition OBJECT-TYPE
        SYNTAX  INTEGER {
                other                          (1),
                disable                        (2),
                no-link-signal                 (3),
                laser-fail                     (4),
                no-link-signal-or-laser-fail   (5),
                not-available                  (100)
        }
        ACCESS  read-write
        STATUS  mandatory
        DESCRIPTION
                "The alarm trigger mode at line port: 'disable', i.e. no alarm
                 is triggered, 'no-link-signal', i.e. an alarm is triggered if
                 the link is down, 'laser-fail', i.e. an alarm is triggered
                 if the laser diode is defective, or 'no-link-signal-or-laser-fail',
                 i.e. the link is down or the laser diode is defective."
        ::= { etcTableEntry 99 }

mdmStatusInterfacePort OBJECT-TYPE
        SYNTAX  INTEGER {
                other   (1),
                disable (2),
                enable  (3)
        }
        ACCESS  read-write
        STATUS  mandatory
        DESCRIPTION
                "The status 'disable': port is not active.
                 The status 'enable': port is active."
        ::= { etcTableEntry 140 }

mdmStatusLinePort OBJECT-TYPE
        SYNTAX  INTEGER {
                other   (1),
                disable (2),
                enable  (3)
        }
        ACCESS  read-write
        STATUS  mandatory
        DESCRIPTION
                "The status 'disable': port is not active.
                 The status 'enable': port is active."
        ::= { etcTableEntry 141 }

END
