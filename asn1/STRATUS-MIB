--  COPYRIGHT 2001 - 2003  Stratus Technologies Bermuda Ltd.
--  All Rights Reserved.
-- 
--   @File:
--     sra_ftServer.MIB
-- 
--   @Description:
--     This file defines the Stratus ftServer-specific SNMP MIB.
--     Definitions for Linux, VOS, and Windows agents appear here.
--     Stratus MIB definitions for other agents are not in this file.
-- 


STRATUS-MIB DEFINITIONS ::= BEGIN

IMPORTS
        enterprises
                FROM RFC1155-SMI
        OBJECT-TYPE
                FROM RFC-1212
        DisplayString
                FROM RFC1213-MIB
        TRAP-TYPE
                FROM RFC-1215;


stratus         OBJECT IDENTIFIER ::= { enterprises 458 }


    --  These are the major categories of the Stratus namespace.
    --  Note: Values less than 101 are not used to prevent collision with 
    --  old products.

experimental    OBJECT IDENTIFIER ::= { stratus 101 }
agentInfo       OBJECT IDENTIFIER ::= { stratus 102 }
systemInfo      OBJECT IDENTIFIER ::= { stratus 103 }
productIdent    OBJECT IDENTIFIER ::= { stratus 104 }
ftServerOid     OBJECT IDENTIFIER ::= { stratus 105 }
stcpOid         OBJECT IDENTIFIER ::= { stratus 106 }


    -- The Agent Information table is used to provide information about
    -- the capabilities of the SNMP agent.

sraAgentMibFamily  OBJECT-TYPE
    SYNTAX      INTEGER  {
                    stcp(1),
                    ftServer(2)
                }
    ACCESS      read-only
    STATUS      mandatory
    DESCRIPTION
            "This variable indicates which OIDs are supported by the agent.
             When support for variables and/or traps are removed from an
             agent, a new family must be created."
    ::= { agentInfo 1 }

sraAgentMibRevision  OBJECT-TYPE
    SYNTAX      INTEGER  {
                    rev01(1)
                }
    ACCESS      read-only
    STATUS      mandatory
    DESCRIPTION
            "This variable indicates whether variables and/or traps have been
             added to the MIB.  When a MIB family is created this is initially
             one. When OIDs are added to those an agent supports, this integer
             is incremented. Each time a MIB is published, the corresponding
             Revision will be defined in the MIB."
    ::= { agentInfo 2 }


    --  The System Information table provides information about system as a
    --  whole.  These variables are platform independent.

sraSiSystemType OBJECT-TYPE
    SYNTAX      OBJECT IDENTIFIER
    ACCESS      read-only
    STATUS      mandatory
    DESCRIPTION
            "The authoritative identification of the hardware and software
             in the entity.  This value provides an easy and unambiguous means
             for determining `what kind of box' is being managed.  This value
             is an OID that indicates the product family, operating system and
             CPU architecture.  Values are enumerated in the 
             Product Identification (OID 104) table."
    ::= { systemInfo 1 }

sraSiManufacturer OBJECT-TYPE
    SYNTAX      DisplayString
    ACCESS      read-only
    STATUS      mandatory
    DESCRIPTION
            "This value is a string to indicate the manufacturer of the system.  
             If unknown, the agent may return a null string."
    ::= { systemInfo 2 }

sraSiModel OBJECT-TYPE
    SYNTAX      DisplayString
    ACCESS      read-only
    STATUS      mandatory
    DESCRIPTION
            "This value is a string to indicate the model of the system.  
             If unsupported the agent may return a null string."
    ::= { systemInfo 3 }

sraSiOverallSystemStatus OBJECT-TYPE
    SYNTAX  INTEGER  {
                unsupported(1),
                noFaults(2),
                systemFault(3),
                systemDown(4)
            }
    ACCESS      read-only
    STATUS      mandatory
    DESCRIPTION
            "This integer indicates the overall status of the system."
    ::= { systemInfo 4 }

sraSiSystemName OBJECT-TYPE
    SYNTAX      DisplayString
    ACCESS      read-only
    STATUS      mandatory
    DESCRIPTION
            "This value is a string representing the network name of the
             system.  This is expected to be unique on a LAN but possibly
             not globally unique.  If unsupported by the agent, a null
             string may be returned.  When the OS is Windows, this is the
             *computer name* portion of the network id, or the Lan Manager
             name of the computer (e.g. PCAT). In contrast, the MIB-II 
             sysName is typically the fully-qualified domain name
             (e.g. pcat.mno.stratus.com).  On VOS, this is the system and
             module name (e.g. %sys#m1). On UNIX this is the hostname."
    ::= { systemInfo 5 }

sraSiSystemSerialNumber OBJECT-TYPE
    SYNTAX      DisplayString
    ACCESS      read-only
    STATUS      mandatory
    DESCRIPTION
            "This value is a string containing the serial number of the 
             system. If unsupported by the agent, a null string may be
             returned."
    ::= { systemInfo 6 }

sraSiSiteID     OBJECT-TYPE
    SYNTAX      DisplayString
    ACCESS      read-only
    STATUS      mandatory
    DESCRIPTION
            "This string value contains the SiteID.  SiteID is part of 
             the RSN/ASN service model."
    ::= { systemInfo 7 }

sraSiCpuFamily OBJECT-TYPE
    SYNTAX      INTEGER  {
                    unsupported(1),
                    m68k(2),
                    i860(3),
                    hppa(4),
                    ia32(5),
                    ia64(6)
                }
    ACCESS      read-only
    STATUS      mandatory
    DESCRIPTION
            "This value is an integer that indicates the CPU architecture."
    ::= { systemInfo 8 }

sraSiOsType OBJECT-TYPE
    SYNTAX      INTEGER  {
                    unsupported(1),
                    ftx(2),
                    hpux(3),
                    linux(4),
                    vos(5),
                    windows(6)
                }
    ACCESS      read-only
    STATUS      mandatory
    DESCRIPTION
            "This value is an integer that indicates Operating System type."
    ::= { systemInfo 9 }


    -- The Product Identification table is used to identify specific Stratus
    -- products.  This table defines OIDs but there are no variables.  Where
    -- possible these will be used as the value of the RFC-1213 MIB-II 
    -- system.sysObjectID variable. However, with a non-Stratus OS, like
    -- Windows, MIB-II system.sysObjectID is not under our control.
    -- Consequently these same values are reported in the Stratus variable
    -- sraSiSystemType.

osFTX                   OBJECT IDENTIFIER ::= { productIdent 1 }
sraProductIdFtxJetta    OBJECT IDENTIFIER ::= { osFTX 1 }
sraProductIdFtxPolo     OBJECT IDENTIFIER ::= { osFTX 2 }

osHPUX                  OBJECT IDENTIFIER ::= { productIdent 2 }
sraProductIdHpuxPolo    OBJECT IDENTIFIER ::= { osHPUX 1 }

osLinux                 OBJECT IDENTIFIER ::= { productIdent 3 }
sraProductIdLnxFtsIa32  OBJECT IDENTIFIER ::= { osLinux 1 }

osVOS                   OBJECT IDENTIFIER ::= { productIdent 4 }
sraProductIdVos68k      OBJECT IDENTIFIER ::= { osVOS 1 }
sraProductIdVosI860     OBJECT IDENTIFIER ::= { osVOS 2 }
sraProductIdVosJetta    OBJECT IDENTIFIER ::= { osVOS 3 }
sraProductIdVosIa32     OBJECT IDENTIFIER ::= { osVOS 4 }


osWindowsFt             OBJECT IDENTIFIER ::= { productIdent 5 }
sraProductIdWinFtsIa32  OBJECT IDENTIFIER ::= { osWindowsFt 1 }
sraProductIdWinFtsIa64  OBJECT IDENTIFIER ::= { osWindowsFt 2 }

osRadio                 OBJECT IDENTIFIER ::= { productIdent 6 }
sraProductIdWinRadIa32  OBJECT IDENTIFIER ::= { osRadio 1 }


    -- The following table contains OIDs unique to the ftSM MIB.
    -- There are three groups of OIDs within this table:
    -- OIDs that identify GET/SET variables,
    -- OIDs that identify ftSM TRAPs, and
    -- OIDs used to identify variable fields in TRAP PDUs.

ftsmVar                 OBJECT IDENTIFIER ::= { ftServerOid 1 }
ftsmTrapId              OBJECT IDENTIFIER ::= { ftServerOid 2 }
ftsmTrapData            OBJECT IDENTIFIER ::= { ftServerOid 3 }


    -- ftServer GET/SET variables

ftsmVarHostModelName OBJECT-TYPE
    SYNTAX      DisplayString
    ACCESS      read-only
    STATUS      mandatory
    DESCRIPTION
            "This string contains the model name from the
             SRA_Customer class in WMI. (This differs from
             the information reported in the sraSiModel variable.)"
    ::= { ftsmVar 1 }


    -- ftServer TRAP PDU Data Fields
    -- This table contains variables that may be included in trap PDUs.

ftsmTrapDataDevicePathId OBJECT-TYPE
    SYNTAX      DisplayString (SIZE (0..31))
    ACCESS      read-only
    STATUS      mandatory
    DESCRIPTION
            "This string identifies the specific device that caused 
             the event that resulted in the trap.  This string is in 
             standard #/# notation."
    ::= { ftsmTrapData 1 }

ftsmTrapDataDeviceClassname OBJECT-TYPE
    SYNTAX      DisplayString 
    ACCESS      read-only
    STATUS      mandatory
    DESCRIPTION
            "This string identifies the type of device that caused 
             the event that resulted in the trap. (CIM class name)"
    ::= { ftsmTrapData 2 }

ftsmTrapDataNewState OBJECT-TYPE
    SYNTAX      INTEGER  {
                    sraFtsm-state-empty                     (65536), --  '10000'h
                    sraFtsm-state-not-present               (65560), --  '10018'h
                    sraFtsm-state-removed                  (131073), --  '20001'h
                    sraFtsm-state-dumping                  (131076), --  '20004'h
                    sraFtsm-state-diagnostics-passed       (131078), --  '20006'h
                    sraFtsm-state-initializing             (131079), --  '20007'h
                    sraFtsm-state-syncing                  (131080), --  '20008'h
                    sraFtsm-state-firmware-update          (131081), --  '20009'h
                    sraFtsm-state-offline                  (131082), --  '2000a'h
                    sraFtsm-state-device-ready             (131083), --  '2000b'h
                    sraFtsm-state-stopped                  (131084), --  '2000c'h
                    sraFtsm-state-stop-pending             (131085), --  '2000d'h
                    sraFtsm-state-remove-pending           (131086), --  '2000e'h
                    sraFtsm-state-surprise-removal         (131087), --  '2000f'h
                    sraFtsm-state-firmware-update-complete (131088), --  '20010'h
                    sraFtsm-state-diagnostics              (262149), --  '40005'h
                    sraFtsm-state-online                   (524308), --  '80014'h
                    sraFtsm-state-simplex                  (524309), --  '80015'h
                    sraFtsm-state-duplex                  (1572886), -- '180016'h
                    sraFtsm-state-triplex                 (1572887), -- '180017'h
                    sraFtsm-state-shot                    (2097154), -- '200002'h
                    sraFtsm-state-broken                  (2097155)  -- '200003'h
                }
    ACCESS      read-only
    STATUS      mandatory
    DESCRIPTION
            "This integer identifies the new operational state of the device
             after the event that caused the trap."
    ::= { ftsmTrapData 3 }

ftsmTrapDataNewReason OBJECT-TYPE
    SYNTAX      INTEGER  {
                    sraFtsm-reason-none                     (0),
                    sraFtsm-reason-below-mtbf               (1),
                    sraFtsm-reason-diagnostics-failed       (2),
                    sraFtsm-reason-hardware-incompatible    (3),
                    sraFtsm-reason-holding-dump             (4),
                    sraFtsm-reason-bringup-failed           (5),
                    sraFtsm-reason-parent-broken            (6),
                    sraFtsm-reason-media-disconnect         (7),
                    sraFtsm-reason-firmware-burn-fail       (8),
                    sraFtsm-reason-firmware-file-not-found  (9),
                    sraFtsm-reason-firmware-file-error     (10),
                    sraFtsm-reason-firmware-prom-error     (11),
                    sraFtsm-reason-autoburn-disabled       (12),
                    sraFtsm-reason-idprom-read-error       (13),
                    sraFtsm-reason-primary                 (14),
                    sraFtsm-reason-secondary               (15),
                    sraFtsm-reason-parent-empty            (16),
                    sraFtsm-reason-deferred-bringup        (17)
                }
    ACCESS      read-only
    STATUS      mandatory
    DESCRIPTION
            "This integer identifies the new operational reason of the 
             device after the event that caused the trap.  This provides 
             additional detail of the operational state of hardware 
             elements of the ftServer."
    ::= { ftsmTrapData 4 }

ftsmTrapDataNewThreshold OBJECT-TYPE
    SYNTAX      INTEGER  {
                    sraFtsm-sensor-status-unavailable       (0),
                    sraFtsm-sensor-status-normal            (1),
                    sraFtsm-sensor-status-below-warning     (2),
                    sraFtsm-sensor-status-below-critical    (3),
                    sraFtsm-sensor-status-above-warning     (4),
                    sraFtsm-sensor-status-above-critical    (5),
                    sraFtsm-sensor-status-below-fatal       (6),
                    sraFtsm-sensor-status-above-fatal       (7)
                }
    ACCESS      read-only
    STATUS      mandatory
    DESCRIPTION
            "This integer identifies the new status of a sensor, 
             compared to thresholds, after the threshold event that 
             caused the trap."
    ::= { ftsmTrapData 5 }

ftsmTrapDataEventId OBJECT-TYPE
    SYNTAX      INTEGER
    ACCESS      read-only
    STATUS      mandatory
    DESCRIPTION
            "This integer contains the Win32 EventID associated with the 
             event that caused this trap."
    ::= { ftsmTrapData 6 }

ftsmTrapDataAlarmId OBJECT-TYPE
    SYNTAX      INTEGER
    ACCESS      read-only
    STATUS      mandatory
    DESCRIPTION
            "This integer contains the ftSM AlarmID associated with the 
             event that caused this trap."
    ::= { ftsmTrapData 7 }

ftsmTrapDataEventDescription OBJECT-TYPE
    SYNTAX      DisplayString
    ACCESS      read-only
    STATUS      mandatory
    DESCRIPTION
            "This is the formatted string that describes the event.
             This string is composed by using the EventId to select
             a message template string and applying formatting
             directives in that string to other parameters.  This is
             further explained in the Microsoft Windows Platform SDK
             documentation on Event Logging."
    ::= { ftsmTrapData 8 }

ftsmTrapDataEventParameterStrings OBJECT IDENTIFIER ::= { ftsmTrapData 9 }

    -- This table contains the language-independent substitution strings
    -- that are inserted into a message template string.

ftsmTrapDataEventP1 OBJECT-TYPE
    SYNTAX      DisplayString
    ACCESS      read-only
    STATUS      mandatory
    DESCRIPTION
            "This language-independent substitution string replaces 
             any occurance of %1 in the message template string."
    ::= { ftsmTrapDataEventParameterStrings 1 }

ftsmTrapDataEventP2 OBJECT-TYPE
    SYNTAX      DisplayString
    ACCESS      read-only
    STATUS      mandatory
    DESCRIPTION
            "This language-independent substitution string replaces 
             any occurance of %2 in the message template string."
    ::= { ftsmTrapDataEventParameterStrings 2 }

ftsmTrapDataEventP3 OBJECT-TYPE
    SYNTAX      DisplayString
    ACCESS      read-only
    STATUS      mandatory
    DESCRIPTION
            "This language-independent substitution string replaces 
             any occurance of %3 in the message template string."
    ::= { ftsmTrapDataEventParameterStrings 3 }

ftsmTrapDataEventP4 OBJECT-TYPE
    SYNTAX      DisplayString
    ACCESS      read-only
    STATUS      mandatory
    DESCRIPTION
            "This language-independent substitution string replaces 
             any occurance of %4 in the message template string."
    ::= { ftsmTrapDataEventParameterStrings 4 }

ftsmTrapDataEventP5 OBJECT-TYPE
    SYNTAX      DisplayString
    ACCESS      read-only
    STATUS      mandatory
    DESCRIPTION
            "This language-independent substitution string replaces 
             any occurance of %5 in the message template string."
    ::= { ftsmTrapDataEventParameterStrings 5 }

ftsmTrapDataEventP6 OBJECT-TYPE
    SYNTAX      DisplayString
    ACCESS      read-only
    STATUS      mandatory
    DESCRIPTION
            "This language-independent substitution string replaces 
             any occurance of %6 in the message template string."
    ::= { ftsmTrapDataEventParameterStrings 6 }

ftsmTrapDataEventP7 OBJECT-TYPE
    SYNTAX      DisplayString
    ACCESS      read-only
    STATUS      mandatory
    DESCRIPTION
            "This language-independent substitution string replaces 
             any occurance of %7 in the message template string."
    ::= { ftsmTrapDataEventParameterStrings 7 }

ftsmTrapDataEventP8 OBJECT-TYPE
    SYNTAX      DisplayString
    ACCESS      read-only
    STATUS      mandatory
    DESCRIPTION
            "This language-independent substitution string replaces 
             any occurance of %8 in the message template string."
    ::= { ftsmTrapDataEventParameterStrings 8 }

ftsmTrapDataEventP9 OBJECT-TYPE
    SYNTAX      DisplayString
    ACCESS      read-only
    STATUS      mandatory
    DESCRIPTION
            "This language-independent substitution string replaces 
             any occurance of %9 in the message template string."
    ::= { ftsmTrapDataEventParameterStrings 9 }


    -- ftSM Traps
    --
    -- All ftServer traps use *ftsmTrapId* as the enterprise OID.
    -- The traps are distinguished by a unique enterprise-specific TrapId.
    -- The TrapId is the last token, following ::= in the TRAP-TYPE macro
    -- invocation.
    --
    -- TrapId's are used as follows.
    --   Zero is a reserved value that will not be used as a TrapId.  The
    --   coding of the ftSM agent assumes that zero is not a valid TrapId.
    --
    --   TrapId 101 through 199 are used for Device State Changes.
    --   TrapId 201 through 299 are used for Threshold Crossing Events.
    --   TrapId 301 through 399 are used for Miscellaneous Alarms.
    --   Other TrapId values are not currently used.

ftsmTrapEnterBrokenState       TRAP-TYPE
    ENTERPRISE  ftsmTrapId
    VARIABLES   { ftsmTrapDataDevicePathId, ftsmTrapDataDeviceClassname,
                  ftsmTrapDataNewState,     ftsmTrapDataNewReason }
    DESCRIPTION "A ftsmTrapEnterBrokenState trap indicates that the
                 device entered the broken SNMP state."
        ::= 101

ftsmTrapLeaveBrokenState       TRAP-TYPE
    ENTERPRISE  ftsmTrapId
    VARIABLES   { ftsmTrapDataDevicePathId, ftsmTrapDataDeviceClassname,
                  ftsmTrapDataNewState,     ftsmTrapDataNewReason }
    DESCRIPTION "A ftsmTrapLeaveBrokenState trap indicates that the
                 device left the broken SNMP state."
        ::= 102

ftsmTrapEnterOnlineState       TRAP-TYPE
    ENTERPRISE  ftsmTrapId
    VARIABLES   { ftsmTrapDataDevicePathId, ftsmTrapDataDeviceClassname,
                  ftsmTrapDataNewState,     ftsmTrapDataNewReason }
    DESCRIPTION "A ftsmTrapEnterOnlineState trap indicates that the
                 device entered the online SNMP state."
        ::= 103

ftsmTrapLeaveOnlineState       TRAP-TYPE
    ENTERPRISE  ftsmTrapId
    VARIABLES   { ftsmTrapDataDevicePathId, ftsmTrapDataDeviceClassname,
                  ftsmTrapDataNewState,     ftsmTrapDataNewReason }
    DESCRIPTION "A ftsmTrapLeaveOnlineState trap indicates that the
                 device left the online SNMP state."
        ::= 104

ftsmTrapEnterOutOfServiceState TRAP-TYPE
    ENTERPRISE  ftsmTrapId
    VARIABLES   { ftsmTrapDataDevicePathId, ftsmTrapDataDeviceClassname,
                  ftsmTrapDataNewState,     ftsmTrapDataNewReason }
    DESCRIPTION "A ftsmTrapEnterOutOfServiceState trap indicates that the
                 device entered the out-of-service SNMP state."
        ::= 105

ftsmTrapLeaveOutOfServiceState TRAP-TYPE
    ENTERPRISE  ftsmTrapId
    VARIABLES   { ftsmTrapDataDevicePathId, ftsmTrapDataDeviceClassname,
                  ftsmTrapDataNewState,     ftsmTrapDataNewReason }
    DESCRIPTION "A ftsmTrapLeaveOutOfServiceState trap indicates that the
                 device left the out-of-service SNMP state."
        ::= 106

    -- Trap Type Table separator

ftsmTrapImprove2Normal         TRAP-TYPE
    ENTERPRISE  ftsmTrapId
    VARIABLES   { ftsmTrapDataDevicePathId, ftsmTrapDataDeviceClassname,
                  ftsmTrapDataNewState,     ftsmTrapDataNewReason,
                  ftsmTrapDataNewThreshold  }
    DESCRIPTION "A ftsmTrapImprove2Normal trap indicates that the
                 status improved to the normal range."
        ::= 201

ftsmTrapImprove2Warning        TRAP-TYPE
    ENTERPRISE  ftsmTrapId
    VARIABLES   { ftsmTrapDataDevicePathId, ftsmTrapDataDeviceClassname,
                  ftsmTrapDataNewState,     ftsmTrapDataNewReason,
                  ftsmTrapDataNewThreshold  }
    DESCRIPTION "A ftsmTrapImprove2Warning trap indicates that the
                 status improved to the warning range."
        ::= 202

ftsmTrapImprove2Critical       TRAP-TYPE
    ENTERPRISE  ftsmTrapId
    VARIABLES   { ftsmTrapDataDevicePathId, ftsmTrapDataDeviceClassname,
                  ftsmTrapDataNewState,     ftsmTrapDataNewReason,
                  ftsmTrapDataNewThreshold  }
    DESCRIPTION "A ftsmTrapImprove2Critical trap indicates that the
                 status improved to the critical range."
        ::= 203

ftsmTrapUnavailable            TRAP-TYPE
    ENTERPRISE  ftsmTrapId
    VARIABLES   { ftsmTrapDataDevicePathId, ftsmTrapDataDeviceClassname,
                  ftsmTrapDataNewState,     ftsmTrapDataNewReason,
                  ftsmTrapDataNewThreshold  }
    DESCRIPTION "A ftsmTrapUnavailable trap indicates that the
                 threshold or status information became unavailable."
        ::= 204

ftsmTrapWorse2Fatal            TRAP-TYPE
    ENTERPRISE  ftsmTrapId
    VARIABLES   { ftsmTrapDataDevicePathId, ftsmTrapDataDeviceClassname,
                  ftsmTrapDataNewState,     ftsmTrapDataNewReason,
                  ftsmTrapDataNewThreshold  }
    DESCRIPTION "A ftsmTrapWorse2Fatal trap indicates that the
                 status worsened to the fatal range."
        ::= 205

ftsmTrapWorse2Critical         TRAP-TYPE
    ENTERPRISE  ftsmTrapId
    VARIABLES   { ftsmTrapDataDevicePathId, ftsmTrapDataDeviceClassname,
                  ftsmTrapDataNewState,     ftsmTrapDataNewReason,
                  ftsmTrapDataNewThreshold  }
    DESCRIPTION "A ftsmTrapWorse2Critical trap indicates that the
                 status worsened to the critical range."
        ::= 206

ftsmTrapWorse2Warning          TRAP-TYPE
    ENTERPRISE  ftsmTrapId
    VARIABLES   { ftsmTrapDataDevicePathId, ftsmTrapDataDeviceClassname,
                  ftsmTrapDataNewState,     ftsmTrapDataNewReason,
                  ftsmTrapDataNewThreshold  }
    DESCRIPTION "A ftsmTrapWorse2Warning trap indicates that the
                 status worsened to the warning range."
        ::= 207

    -- Trap Type Table separator

ftsmTrapMgmtServiceFailure     TRAP-TYPE
    ENTERPRISE  ftsmTrapId
    VARIABLES   { ftsmTrapDataEventId, ftsmTrapDataAlarmId,
                  ftsmTrapDataEventDescription }
    DESCRIPTION "A ftsmTrapMgmtServiceFailure trap indicates that one
                 or more Stratus ftServer management services have failed."
        ::= 301

ftsmTrapUnsentAlarm            TRAP-TYPE
    ENTERPRISE  ftsmTrapId
    VARIABLES   { ftsmTrapDataEventId, ftsmTrapDataAlarmId,
                  ftsmTrapDataEventDescription }
    DESCRIPTION "A ftsmTrapUnsentAlarm trap indicates that
                 the Alarm Service failed to send an alarm message
                 due to possible connection or ASN hub failures.
                 The alarm message file has been renamed with .drop 
                 extension and saved in the alarm file directory."
        ::= 302


-- End-of MIB(ftSM) Revision 1.

END
