--
-- Based on Frame Relay Service RFC 1604 and Micom Frame Relay DCE/HTDS 
-- MIB Requirement Document

-- MIB Revision Dated: 4-24-97
-- Updated on 4-24 by Ron Carmona
-- 
-- MIB Revision : 1.0 dated 4-24-97
-- Change Desc. : None. 
--
-- MIB Revision : 1.1 dated 7-8-97
-- Change Desc. : Range changes for few objects  - B. Jafari
--
--
-- MIB Revision : 1.2 dated 9-16-97
-- Change Desc  : Renamed nodes to unique names in order to comply 
--                with Nortel CSU tool - S. Gaur
--
-- MIB Revision : 1.3 dated 10-8-97
-- Change Desc. : Replaced MPA with 4400 - B. Jafari. 
-- 
--
-- *** RELEASE 3.0 ***
-- MIB Revision : 1.4 dated 6-26-98
-- Change Desc. : Obsoleted the counter reset tables: 
--                mcmFrMgtVCSigCntrTable and
--                mcmFrPVCEndptCntrTable.
--                Replaced all instances of the "4400" string 
--                with the generic string "access device"  - S. Gaur. 
-- 
-- MIB Revision : 1.5 dated 1-26-99
-- Change Desc. : Changed range of 2 objects mcmFrPVCEndptInMaxFrameSize 
--		  and mcmFrPVCEndptOutMaxFrameSize.
--						-K. Chan

 
-- This MIB file contains a MICOM proprietary version of the RFC 1604
-- Frame Relay Service MIB. This MIB file is one of 2 MICOM proprietary
-- MIB files that constitute the SNMP management capabilities of a
-- Frame Relay DCE interface on the access device integration unit.
 

MICOM-RFC1604-MIB DEFINITIONS ::= BEGIN
	IMPORTS
		Counter 
                   		 	FROM RFC1155-SMI
		OBJECT-TYPE
                    			FROM RFC-1212
	    	micom-oscar 
		    			FROM MICOM-OSCAR-MIB;


-- group OBJECT IDENTIFIERs

	micom-rfc1604		 OBJECT IDENTIFIER ::= {micom-oscar 8}
	rfc1604-configuration	 OBJECT IDENTIFIER ::= {micom-rfc1604 1}
	rfc1604-control		 OBJECT IDENTIFIER ::= {micom-rfc1604 2}


-- Note: The following groups each contain 2 related tables for all configuration
--       functionality. 
--	 1) The Standard or Operational Parameters (Operational) provide the SNMP 
--	 management interface with the access devices operational modules.
--	 Objects defined for this interface begin with the 'mcm' prefix.
--	 2) The Configuration Parameters (Configuration) provide the SNMP 
--	 management interface with a stored access devices configuration. 
--	 Objects defined for this interface begin with the 'nvm' prefix.
--	


--  Operational Parameter (Operational) Tables


--  the Frame Relay Logical Port Group (Standard/Operational Parameters)

--  This table is an interface specific addendum to the generic ifTable
--  from MIB-II.  It contains the parameters required to configure the Frame
--  Relay DCE Service on the specified port. (Operational)

mcmFrLportTable OBJECT-TYPE
	SYNTAX  SEQUENCE OF McmFrLportEntry
	ACCESS  not-accessible
	STATUS  mandatory
	DESCRIPTION
 	  "NAME = ; 
    	   DESC = The Frame Relay Logical Port Information \
		  table (Operational).;
   	   HELP = ;
    	   CAPABILITIES = NET_CFG, VPN_CFG;"
 	::= { rfc1604-configuration 1 }

mcmFrLportEntry OBJECT-TYPE
	SYNTAX  McmFrLportEntry
	ACCESS  not-accessible
	STATUS  mandatory
 	DESCRIPTION
   	  "NAME = ; 
    	   DESC = An entry in the Frame Relay Logical \
            	  Port Information table (Operational).;
    	   HELP = ;
    	   CAPABILITIES = ;"
 	INDEX   { mcmFrLportIfIndex }
	::= { mcmFrLportTable 1 }

McmFrLportEntry ::= SEQUENCE {
	mcmFrLportIfIndex		INTEGER,
	mcmFrLportNumPlan		INTEGER,
      	mcmFrLportType			INTEGER,
      	mcmFrLportAddrDLCILen		INTEGER,
      	mcmFrLportVCSigProtocol		INTEGER
 	}

mcmFrLportIfIndex OBJECT-TYPE
	SYNTAX	INTEGER (1..255)
	ACCESS	read-only
	STATUS	mandatory
	DESCRIPTION
	  "NAME = ;
	   DESC = The ifIndex of the local DCE interface. \
		  (Analogous to the ifIndex pointer in the \
		  MIB II Interfaces Group, but specific to \
		  the FR Logical Port info table.) (Operational);
	   HELP = ;
	   CAPABILITIES = ;"
	::= { mcmFrLportEntry 1 }

mcmFrLportNumPlan OBJECT-TYPE
     	SYNTAX	INTEGER {
      		other(1),
           	e164(2),
          	x121(3),
           	none(4)
		}
  	ACCESS  read-only
     	STATUS  mandatory
     	DESCRIPTION
    	  "NAME = ; 
	   DESC = The value of this object identifies \
	        the network address numbering plan \
	        for this UNI logical port. \
	        (Operational);
	   HELP = The network address is the object ifPhysAddress. \
	        The value 'none' implies that there is \
	        no ifPhysAddress (the SNMP proxy-agent \
	        will return an octet string of zero \
	        length for ifPhysAddress).  The value \
	        'other' means that an address has been \
	        assigned to this interface, but the \
	        numbering plan is not enumerated here. ;
	   CAPABILITIES = ;"
     	::= { mcmFrLportEntry 2 }


mcmFrLportType OBJECT-TYPE
   	SYNTAX	INTEGER {
               	uni(1),
               	nni(2)
             	}
     	ACCESS  read-only
     	STATUS  mandatory
     	DESCRIPTION
       	  "NAME = ; 
	   DESC = The value of this object identifies \
	        the type of network interface for this \
	        logical port. (Operational);
	   HELP = ;
	   CAPABILITIES = ;"
     	::= { mcmFrLportEntry 3 }

mcmFrLportAddrDLCILen OBJECT-TYPE
     	SYNTAX	INTEGER {
      		twoOctets10Bits(1),
      		threeOctets10Bits(2),
      		threeOctets16Bits(3),
      		fourOctets17Bits(4),
      		fourOctets23Bits(5)
    		}
    	ACCESS  read-only
     	STATUS  mandatory
     	DESCRIPTION
       	  "NAME = ; 
	   DESC = The value of this object identifies \
	        the Q.922 Address field length and \
	        DLCI length for this UNI logical \
	        port. (Operational);
	   HELP = ;
	   CAPABILITIES = ;"
     	::= { mcmFrLportEntry 4 }

mcmFrLportVCSigProtocol OBJECT-TYPE
     	SYNTAX	INTEGER {
               	none(1),
               	lmi(2),
               	ccittQ933A(5),
		ansiT1617D-1994(6)
             		}
    	ACCESS  read-only
     	STATUS  mandatory
     	DESCRIPTION
          "NAME = ; 
	   DESC = The value of this object identifies \
	        the Local In-Channel Signaling Protocol \
	        that is used for this frame relay UNI \
	        logical port. (Operational);
	   HELP = ;
	   CAPABILITIES = ;"
	DEFVAL { 6 }
	::= { mcmFrLportEntry 5 }


-- the Frame Relay Management VC Signaling Group (Standard/Operational Parameters)

-- This Group contains managed objects for the Local In-Channel Signaling
-- Parameters and for signaling errors.  Only elements required for the UNI
-- Local In-Channel Signaling (from RFC 1604) have been included. (Operational)

mcmFrMgtVCSigTable OBJECT-TYPE
     	SYNTAX  SEQUENCE OF McmFrMgtVCSigEntry
     	ACCESS  not-accessible
     	STATUS  mandatory
     	DESCRIPTION
          "NAME = ; 
	   DESC = The Frame Relay Management VC \
		Signaling Parameters and Errors table. (Operational);
	   HELP = ;
	   CAPABILITIES = NET_CFG, VPN_CFG;"
     	::= { rfc1604-configuration 2 }

mcmFrMgtVCSigEntry OBJECT-TYPE
     	SYNTAX  McmFrMgtVCSigEntry
     	ACCESS  not-accessible
     	STATUS  mandatory
     	DESCRIPTION
          "NAME = ; 
	   DESC = An entry in the Frame Relay Management \
	        VC Signaling Parameters and Errors table. (Operational);
 	   HELP = ;
	CAPABILITIES = ;"
     	INDEX   { mcmFrMgtVCSigIfIndex }
     	::= { mcmFrMgtVCSigTable 1 }

McmFrMgtVCSigEntry ::= SEQUENCE {
	mcmFrMgtVCSigIfIndex		INTEGER,
    	mcmFrMgtVCSigProced		INTEGER,
      	mcmFrMgtVCSigNetN392		INTEGER,
      	mcmFrMgtVCSigNetN393		INTEGER,
    	mcmFrMgtVCSigNetT392		INTEGER,
     	mcmFrMgtVCSigNetLinkRelErrors	Counter,
      	mcmFrMgtVCSigNetProtErrors	Counter,
      	mcmFrMgtVCSigNetChanInactive	Counter
	}

mcmFrMgtVCSigIfIndex OBJECT-TYPE
	SYNTAX	INTEGER (1..255)
	ACCESS	read-only
	STATUS	mandatory
	DESCRIPTION
	  "NAME = ;
	   DESC = The ifIndex of the local DCE interface. \
		   (Operational);
	   HELP = (Analogous to the ifIndex pointer in the \
		  MIB II Interfaces Group but specific to \
		  the FR Mgmt VC Sig table.);
	   CAPABILITIES = ;"
	::= { mcmFrMgtVCSigEntry 1 }

mcmFrMgtVCSigProced OBJECT-TYPE
     	SYNTAX  INTEGER {
            	u2nnet(1),
               	bidirect(2)
             	}
    	ACCESS  read-only
     	STATUS  mandatory
     	DESCRIPTION
          "NAME = ; 
	   DESC = The value of this object identifies \
	        the Local In-Channel Signaling Procedure \
	        that is used for this UNI logical \
	        port.   (Operational);
	   HELP = The UNI logical port can \
	        be performing only user-to-network \
	        network-side procedures.;
	   CAPABILITIES = ;"
     	::= { mcmFrMgtVCSigEntry 2 }

mcmFrMgtVCSigNetN392 OBJECT-TYPE
     	SYNTAX  INTEGER (1..10)
    	ACCESS  read-only
     	STATUS  mandatory
     	DESCRIPTION
          "NAME = ; 
	   DESC = The value of this object identifies \
	        the Network-side N392 error threshold \
	        value for this UNI logical port (nN2 for LMI). \
	         (Operational);
	   HELP = If the logical port is not performing \
	        network-side procedures, then this value is \
		equal to noSuchName. This object \
	        applies to Q.933 Annex A, T1.617 \
	        Annex D, and LMI.;
	   CAPABILITIES = ;"
     	DEFVAL { 3 }
     	::= { mcmFrMgtVCSigEntry 3 }

mcmFrMgtVCSigNetN393 OBJECT-TYPE
     	SYNTAX  INTEGER (1..10)
    	ACCESS  read-only
     	STATUS  mandatory
     	DESCRIPTION
       	  "NAME = ; 
	   DESC = The value of this object identifies \
	        the Network-side N393 monitored events \
	        count value for this UNI logical port \
	        (nN3 for LMI).   (Operational);
	   HELP = If the logical port is not performing \
	        network-side procedures, then this value is equal \
		to noSuchName. This object \
	        applies to Q.933 Annex A, T1.617 \
	        Annex D, and LMI.;
	   CAPABILITIES = ;"
     	DEFVAL { 3 }
     	::= { mcmFrMgtVCSigEntry 4 }

mcmFrMgtVCSigNetT392 OBJECT-TYPE
     	SYNTAX  INTEGER (5..30)
     	ACCESS  read-only
     	STATUS  mandatory
     	DESCRIPTION
          "NAME = ; 
	   DESC = The value of this object identifies \
	        the Network-side T392 polling verification \
	        timer value for this UNI logical port \
	        (nT2 for LMI).   (Operational);
	   HELP = This value is in seconds. \
	        If the logical port is not performing\
	        network-side procedures, \
	        then this value is equal to noSuchName. \
	        This object applies to Q.933 Annex A, \
	        T1.617 Annex D, and LMI.;
	   CAPABILITIES = ;"
     	DEFVAL { 15 }
     	::= { mcmFrMgtVCSigEntry 5 }

mcmFrMgtVCSigNetLinkRelErrors OBJECT-TYPE
     	SYNTAX  Counter
     	ACCESS  read-only
     	STATUS  mandatory
     	DESCRIPTION
          "NAME = ; 
	   DESC = The number of network-side local in-channel \
		signaling link reliability errors. \
	         (Operational);
	   HELP = Marks non-receipt of Status/Status Enquiry \
	        messages or invalid sequence numbers \
	        in a Link Integrity Verification Information \
	        Element for this UNI logical port. \
	        If the logical port is not performing \
	        network-side procedures, then this value is equal \
		to noSuchName. Note: no Configuration counterpart \
		for this object.;
 	   CAPABILITIES = ;"
     	::= { mcmFrMgtVCSigEntry 6 }

mcmFrMgtVCSigNetProtErrors OBJECT-TYPE
     	SYNTAX  Counter
    	ACCESS  read-only
     	STATUS  mandatory
     	DESCRIPTION
          "NAME = ; 
	   DESC = The number of network-side local in-channel \
		signaling protocol errors. (Operational); 
	   HELP = Types include protocol discriminator, message type, call reference, \
	        and mandatory information element errors) \
	        for this UNI logical port.  If \
	        the logical port is not performing \
	        network-side procedures, then this value is equal \
		to noSuchName. \
	        Note: no Configuration counterpart for this object.;
	   CAPABILITIES = ;"
     	::= { mcmFrMgtVCSigEntry 7 }

mcmFrMgtVCSigNetChanInactive OBJECT-TYPE
     	SYNTAX  Counter
     	ACCESS  read-only
     	STATUS  mandatory
     	DESCRIPTION
          "NAME = ; 
	   DESC = The number of times the network-side channel \
	        was declared inactive.; (Operational) \
	        ;
	   HELP =  If the logical port is not performing \
	        network-side procedures, then this value \
	        is equal to noSuchName. Note: no Configuration \
		counterpart for this object.;
	   CAPABILITIES = ;"
     	::= { mcmFrMgtVCSigEntry 8 }


-- The PVC End-Point Group (Standard/Operational Parameters)

-- This table is used to identify the traffic parameters
-- for a bi-directional PVC segment end-point, and it also
-- provides statistics for a PVC segment end-point.
-- A PVC segment end-point is identified by a UNI
-- logical port index value and DLCI index value.

mcmFrPVCEndptTable OBJECT-TYPE
     	SYNTAX  SEQUENCE OF McmFrPVCEndptEntry
    	ACCESS  not-accessible
     	STATUS  mandatory
     	DESCRIPTION
          "NAME = ; 
	   DESC = The Frame Relay PVC End-Point table. \
	        (Operational);
	   HELP =  This table contains the \
	        traffic parameters and statistics for \
		a PVC end-point.;
	   CAPABILITIES = NET_CFG, VPN_CFG;"
     	::= { rfc1604-configuration 3 }

mcmFrPVCEndptEntry OBJECT-TYPE
     	SYNTAX  McmFrPVCEndptEntry
    	ACCESS  not-accessible
     	STATUS  mandatory
     	DESCRIPTION
          "NAME = ; 
	   DESC = An entry in the Frame Relay PVC End-point \
	        table. (Operational);
	   HELP = ;
	   CAPABILITIES = ;"
     	INDEX   { mcmFrPVCEndptIfIndex, mcmFrPVCEndptDLCIIndex }
     	::= { mcmFrPVCEndptTable 1 }

McmFrPVCEndptEntry ::= SEQUENCE {
	mcmFrPVCEndptIfIndex		INTEGER,
      	mcmFrPVCEndptDLCIIndex		INTEGER,
     	mcmFrPVCEndptInMaxFrameSize	INTEGER,
     	mcmFrPVCEndptInBc		INTEGER,
       	mcmFrPVCEndptInBe		INTEGER,
       	mcmFrPVCEndptInCIR		INTEGER,
      	mcmFrPVCEndptOutMaxFrameSize	INTEGER,
      	mcmFrPVCEndptOutBc		INTEGER,
    	mcmFrPVCEndptOutBe		INTEGER,
	mcmFrPVCEndptOutCIR		INTEGER,
      	mcmFrPVCEndptInFrames		Counter,
      	mcmFrPVCEndptOutFrames		Counter,
  	mcmFrPVCEndptInDEFrames		Counter,
	mcmFrPVCEndptInExcessFrames	Counter,
     	mcmFrPVCEndptOutExcessFrames	Counter,
    	mcmFrPVCEndptInDiscards		Counter,
   	mcmFrPVCEndptInOctets		Counter,
    	mcmFrPVCEndptOutOctets		Counter
	}

mcmFrPVCEndptIfIndex OBJECT-TYPE
	SYNTAX	INTEGER (1..255)
	ACCESS	read-only
	STATUS	mandatory
	DESCRIPTION
	  "NAME = ;
	   DESC = The ifIndex of the local DCE interface. \
		   (Operational);
	   HELP = (Analogous to the ifIndex pointer in the \
		  MIB II Interfaces Group but specific to \
		  the PVC end-point table.);
	   CAPABILITIES = ;"
	::= { mcmFrPVCEndptEntry 1 }

mcmFrPVCEndptDLCIIndex OBJECT-TYPE
     	SYNTAX	INTEGER (16..991)
    	ACCESS  read-only
     	STATUS  mandatory
     	DESCRIPTION
          "NAME = ;
	   DESC = The value of this object is equal to the \
	        DLCI value for this PVC end-point. (Operational);
	   HELP = ;
	   CAPABILITIES = ;"
     	::= { mcmFrPVCEndptEntry 2 }

mcmFrPVCEndptInMaxFrameSize OBJECT-TYPE
     	SYNTAX	INTEGER (0..4096)
     	ACCESS  read-only
     	STATUS  mandatory
     	DESCRIPTION
          "NAME = ; 
	   DESC = The  largest frame relay information field \
	       in octets for this PVC end-point data sent \
	       into the network.  (Operational);
	   HELP = The value must be \
	        less than or equal to the corresponding \
	        ifMtu (mcmFrPhyPortMtuSize) for this \
	        Frame Relay UNI logical port.;
	   CAPABILITIES = ;"
     	::= { mcmFrPVCEndptEntry 3 }

mcmFrPVCEndptInBc OBJECT-TYPE
     	SYNTAX 	INTEGER (0..2560000)
     	ACCESS  read-only
     	STATUS  mandatory
     	DESCRIPTION
          "NAME = ; 
	   DESC = The committed burst size (Bc) in bits \
	       for this PVC end-point data sent into \
	       frame relay network.(Operational);
	   HELP = ;
	   CAPABILITIES = ;"
     	::= { mcmFrPVCEndptEntry 4 }

mcmFrPVCEndptInBe OBJECT-TYPE
	SYNTAX 	INTEGER (0..2560000)
     	ACCESS  read-only
     	STATUS  mandatory
     	DESCRIPTION
          "NAME = ; 
	   DESC = The committed excess size (Be) in bits \
	       for this PVC end-point data sent into \
	       frame relay network. (Operational);
	   HELP = ;
	   CAPABILITIES = ;"
     	::= { mcmFrPVCEndptEntry 5 }

mcmFrPVCEndptInCIR OBJECT-TYPE
	SYNTAX 	INTEGER (0..65535)
     	ACCESS  read-only
     	STATUS  mandatory
     	DESCRIPTION
          "NAME = ; 
	   DESC = The committed information rate (CIR) in bits/sec \
	       for this PVC end-point data sent into \
	       frame relay network.;
	   HELP = ;
	   CAPABILITIES = ;"
     	::= { mcmFrPVCEndptEntry 6 }

mcmFrPVCEndptOutMaxFrameSize OBJECT-TYPE
	SYNTAX	INTEGER (0..4096)
     	ACCESS  read-only
     	STATUS  mandatory
     	DESCRIPTION
          "NAME = ; 
	   DESC = The  largest frame relay information field \
	       in octets for this PVC end-point data received \
	       from the network. (Operational);
	   HELP = ;
	   CAPABILITIES = ;"
     	::= { mcmFrPVCEndptEntry 7 }

mcmFrPVCEndptOutBc OBJECT-TYPE
	SYNTAX 	INTEGER (0..2560000)
     	ACCESS  read-only
     	STATUS  mandatory
     	DESCRIPTION
          "NAME = ; 
	   DESC =  (Operational);
	   HELP = The committed burst size (Bc) in bits \
	       for this PVC end-point data received from \
	       frame relay network.;
	   CAPABILITIES = ;"
     	::= { mcmFrPVCEndptEntry 8 }

mcmFrPVCEndptOutBe OBJECT-TYPE
	SYNTAX 	INTEGER (0..2560000)
     	ACCESS  read-only
     	STATUS  mandatory
     	DESCRIPTION
          "NAME = ; 
	   DESC = The committed excess size (Be) in bits \
	       for this PVC end-point data received from \
	       frame relay network. (Operational);
	   HELP = ;
	   CAPABILITIES = ;"
     	::= { mcmFrPVCEndptEntry 9 }

mcmFrPVCEndptOutCIR OBJECT-TYPE
	SYNTAX 	INTEGER (0..65535)
     	ACCESS  read-only
     	STATUS  mandatory
     	DESCRIPTION
          "NAME = ; 
	   DESC =The committed information rate (CIR) in bits/sec \
	       for this PVC end-point data received from \
	       frame relay network.(Operational);
	   HELP = ;
	   CAPABILITIES = ;"
     	::= { mcmFrPVCEndptEntry 10 }

mcmFrPVCEndptInFrames OBJECT-TYPE
	SYNTAX  Counter
    	ACCESS  read-only
     	STATUS  mandatory
     	DESCRIPTION
          "NAME = ; 
	   DESC = The number of frames received by the \
	        network (ingress) for this PVC end-point. \
	         (Operational);
	   HELP = This includes any frames discarded \
	        by the network due to submitting more \
	        than Bc + Be data or due to any network \
	        congestion recovery procedures. \
 		Note: no Configuration counterpart for this object.;
	   CAPABILITIES = ;"
     	::= { mcmFrPVCEndptEntry 11 }

mcmFrPVCEndptOutFrames OBJECT-TYPE
	SYNTAX  Counter
    	ACCESS  read-only
     	STATUS  mandatory
     	DESCRIPTION
          "NAME = ; 
	   DESC = The number of frames sent by the network \
	        (egress) regardless of whether they \
	        are Bc or Be frames for this PVC end-point. (Operational) \
;
	   HELP = Note: no Configuration counterpart for this object.;
	   CAPABILITIES = ;"
     	::= { mcmFrPVCEndptEntry 12 }

mcmFrPVCEndptInDEFrames OBJECT-TYPE
	SYNTAX  Counter
    	ACCESS  read-only
     	STATUS  mandatory
     	DESCRIPTION
          "NAME = ; 
	   DESC = The number of frames received by the \
	        network (ingress) with the DE bit set \
	        to (1) for this PVC end-point. (Operational);
	   HELP = Note: no Configuration counterpart for this object.;
	   CAPABILITIES = ;"
     	::= { mcmFrPVCEndptEntry 13 }

mcmFrPVCEndptInExcessFrames OBJECT-TYPE
	SYNTAX  Counter
    	ACCESS  read-only
     	STATUS  mandatory
     	DESCRIPTION
          "NAME = ; 
	   DESC = The number of frames received by the \
	        network (ingress) for this PVC end-point \
	        which were treated as excess traffic. \
	         (Operational);
	   HELP = Frames which are sent to the network \
	        with DE set to zero are treated as \
	        excess when more than Bc bits are submitted \
	        to the network during the Committed \
	        Information Rate Measurement Interval \
	        (Tc).  Excess traffic may or may not \
	        be discarded at the ingress if more \
	        than Bc + Be bits are submitted to \
	        the network during Tc.  Traffic discarded \
	        at the ingress is not recorded in \
	        mcmFrPVCEndptInExcessFrames. \
	        Frames which are sent to the network \
	        with DE set to one are also treated \
	        as excess traffic. \
		Note: no Configuration counterpart for this object.;
	   CAPABILITIES = ;"
     	::= { mcmFrPVCEndptEntry 14 }

mcmFrPVCEndptOutExcessFrames OBJECT-TYPE
	SYNTAX  Counter
    	ACCESS  read-only
     	STATUS  mandatory
     	DESCRIPTION
          "NAME = ; 
	   DESC = The number of frames sent by the network \
	        (egress) for this PVC end-point which \
	        were treated as excess traffic.  (The \
	        DE bit may be set to one.) (Operational);
	   HELP =  Note: no Configuration counterpart for this object.;
	   CAPABILITIES = ;"
     	::= { mcmFrPVCEndptEntry 15 }

mcmFrPVCEndptInDiscards OBJECT-TYPE
	SYNTAX  Counter
    	ACCESS  read-only
     	STATUS  mandatory
     	DESCRIPTION
          "NAME = ; 
	   DESC = The number of frames received by the \
	        the network (ingress) that were discarded \
	        due to traffic enforcement for this \
	        PVC end-point. (Operational);
	   HELP = Note: no Configuration counterpart for this object.;
	   CAPABILITIES = ;"
     	::= { mcmFrPVCEndptEntry 16 }

mcmFrPVCEndptInOctets OBJECT-TYPE
	SYNTAX  Counter
    	ACCESS  read-only
     	STATUS  mandatory
     	DESCRIPTION
          "NAME = ; 
	   DESC = The number of octets received by the \
	        network (ingress) for this PVC end-point. \
	         (Operational);
	   HELP = This counter should only count octets \
	        from the beginning of the frame relay \
	        header field to the end of user data. \
	        If the network supporting Frame Relay \
	        cannot count octets, then this count \
	        should be an approximation. \
		Note: no Configuration counterpart for this object.;
	   CAPABILITIES = ;"
     	::= { mcmFrPVCEndptEntry 17 }

mcmFrPVCEndptOutOctets OBJECT-TYPE
	SYNTAX  Counter
    	ACCESS  read-only
     	STATUS  mandatory
     	DESCRIPTION
          "NAME = ; 
	   DESC = The number of octets sent by the network \
	        (egress) for this PVC end-point.   (Operational);
	        ;
	   HELP = This counter should only count octets from \
	        the beginning of the frame relay header \
	        field to the end of user data.  If \
	        the network supporting Frame Relay \
	        can not count octets, then this count \
	        should be an approximation.
		Note: no Configuration counterpart for this object.;
	   CAPABILITIES = ;"
     	::= { mcmFrPVCEndptEntry 18 }




--  Configuration Parameter (Configuration) Tables


--  the Frame Relay Logical Port Group (Configuration Parameters)

--  This table is an interface specific addendum to the generic ifTable
--  from MIB-II.  It contains the parameters required to configure the Frame
--  Relay DCE Service on the specified port. (Configuration)

nvmFrLportTable OBJECT-TYPE
	SYNTAX  SEQUENCE OF NvmFrLportEntry
	ACCESS  not-accessible
	STATUS  mandatory
	DESCRIPTION
 	  "NAME = ; 
    	   DESC = The Frame Relay Logical Port Information \
		  table (Configuration).;
   	   HELP = NET_CFG, VPN_CFG;
    	   CAPABILITIES = ;"
 	::= { rfc1604-configuration 4 }

nvmFrLportEntry OBJECT-TYPE
	SYNTAX  NvmFrLportEntry
	ACCESS  not-accessible
	STATUS  mandatory
 	DESCRIPTION
   	  "NAME = ; 
    	   DESC = An entry in the Frame Relay Logical \
            	  Port Information table (Configuration).;
    	   HELP = ;
    	   CAPABILITIES = ;"
 	INDEX   { nvmFrLportIfIndex }
	::= { nvmFrLportTable 1 }

NvmFrLportEntry ::= SEQUENCE {
	nvmFrLportIfIndex		INTEGER,
	nvmFrLportNumPlan		INTEGER,
      	nvmFrLportType			INTEGER,
      	nvmFrLportAddrDLCILen		INTEGER,
      	nvmFrLportVCSigProtocol		INTEGER
 	}

nvmFrLportIfIndex OBJECT-TYPE
	SYNTAX	INTEGER (1..255)
	ACCESS	read-only
	STATUS	mandatory
	DESCRIPTION
	  "NAME = ;
	   DESC = The ifIndex of the local DCE interface. \
		  (Analogous to the ifIndex pointer in the \
		  MIB II Interfaces Group but specific to \
		  the FR Logical Port info table..) (Configuration);
	   HELP = ;
	   CAPABILITIES = ;"
	::= { nvmFrLportEntry 1 }

nvmFrLportNumPlan OBJECT-TYPE
     	SYNTAX	INTEGER {
      		other(1),
           	e164(2),
          	x121(3),
           	none(4)
		}
  	ACCESS  read-only
     	STATUS  mandatory
     	DESCRIPTION
    	  "NAME = ; 
	   DESC = The value of this object identifies \
	        the network address numbering plan \
	        for this UNI logical port. \
	        (Configuration);
	   HELP = The network address is the object ifPhysAddress. \
	        The value 'none' implies that there is \
	        no ifPhysAddress (the SNMP proxy-agent \
	        will return an octet string of zero \
	        length for ifPhysAddress).  The value \
	        'other' means that an address has been \
	        assigned to this interface, but the \
	        numbering plan is not enumerated here. \
	        (For Release 1.1, only none(4) will be supported. \
	        This object has temporarily been assigned read-only \
	        access.  Read-write access will be assigned when \
	        other enumeration values are supported.) ;
	   CAPABILITIES = ;"
     	::= { nvmFrLportEntry 2 }


nvmFrLportType OBJECT-TYPE
   	SYNTAX	INTEGER {
               	uni(1),
               	nni(2)
             	}
     	ACCESS  read-only
     	STATUS  mandatory
     	DESCRIPTION
       	  "NAME = ; 
	   DESC = The value of this object identifies \
	        the type of network interface for this \
	        logical port. (Always uni(1) for Release 1.1). \
		(Configuration);
	        
	   HELP = This object has temporarily been assigned read-only \
	        access.  Read-write access will be assigned when \
	        other enumeration values are supported. ;
	   CAPABILITIES = ;"
     	::= { nvmFrLportEntry 3 }

nvmFrLportAddrDLCILen OBJECT-TYPE
     	SYNTAX	INTEGER {
      		twoOctets10Bits(1),
      		threeOctets10Bits(2),
      		threeOctets16Bits(3),
      		fourOctets17Bits(4),
      		fourOctets23Bits(5)
    		}
    	ACCESS  read-only
     	STATUS  mandatory
     	DESCRIPTION
       	  "NAME = ; 
	   DESC = The value of this object identifies \
	        the Q.922 Address field length and \
	        DLCI length for this UNI logical port.\
	        (Always twoOctets10Bits(1) for Release 1.1). \
	        (Configuration);

	   HELP = This object has temporarily been assigned read-only \
	        access.  Read-write access will be assigned when \
	        other enumeration values are supported.);
	   CAPABILITIES = ;"
     	::= { nvmFrLportEntry 4 }

nvmFrLportVCSigProtocol OBJECT-TYPE
     	SYNTAX	INTEGER {
               	none(1),
               	lmi(2),
               	ccittQ933A(5),
		ansiT1617D-1994(6)
             	}
    	ACCESS  read-write
     	STATUS  mandatory
     	DESCRIPTION
          "NAME = ; 
	   DESC = The value of this object identifies \
	        the Local In-Channel Signaling Protocol \
	        that is used for this frame relay UNI \
	        logical port. (Configuration);
	   HELP = ;
	   CAPABILITIES = ;"
	DEFVAL { 6 }
     	::= { nvmFrLportEntry 5 }


-- the Frame Relay Management VC Signaling Group (Configuration Parameters)

-- This Group contains managed objects for the Local In-Channel Signaling
-- Parameters and for signaling errors.  Only elements required for the UNI
-- Local In-Channel Signaling (from RFC 1604) have been included. (Configuration)

nvmFrMgtVCSigTable OBJECT-TYPE
     	SYNTAX  SEQUENCE OF NvmFrMgtVCSigEntry
     	ACCESS  not-accessible
     	STATUS  mandatory
     	DESCRIPTION
          "NAME = ; 
	   DESC = The Frame Relay Management VC \
		Signaling Parameters and Errors table. (Configuration);
	   HELP = ;
	   CAPABILITIES = NET_CFG, VPN_CFG;"
     	::= { rfc1604-configuration 5 }

nvmFrMgtVCSigEntry OBJECT-TYPE
     	SYNTAX  NvmFrMgtVCSigEntry
     	ACCESS  not-accessible
     	STATUS  mandatory
     	DESCRIPTION
          "NAME = ; 
	   DESC = An entry in the Frame Relay Management \
	        VC Signaling Parameters and Errors table. (Configuration);
 	   HELP = ;
	CAPABILITIES = ;"
     	INDEX   { nvmFrMgtVCSigIfIndex }
     	::= { nvmFrMgtVCSigTable 1 }

NvmFrMgtVCSigEntry ::= SEQUENCE {
	nvmFrMgtVCSigIfIndex		INTEGER,
    	nvmFrMgtVCSigProced		INTEGER,
      	nvmFrMgtVCSigNetN392		INTEGER,
      	nvmFrMgtVCSigNetN393		INTEGER,
    	nvmFrMgtVCSigNetT392		INTEGER
	}

nvmFrMgtVCSigIfIndex OBJECT-TYPE
	SYNTAX	INTEGER (1..255)
	ACCESS	read-only
	STATUS	mandatory
	DESCRIPTION
	  "NAME = ;
	   DESC = The ifIndex of the local DCE interface. \
		  (Analogous to the ifIndex pointer in the \
		  MIB II Interfaces Group but specific to \
		  the FR Mgmt VC Sig table.) (Configuration);
	   HELP = ;
	   CAPABILITIES = ;"
	::= { nvmFrMgtVCSigEntry 1 }

nvmFrMgtVCSigProced OBJECT-TYPE
     	SYNTAX  INTEGER {
               	u2nnet(1),
               	bidirect(2)
             	}
    	ACCESS  read-only
     	STATUS  mandatory
     	DESCRIPTION
          "NAME = ; 
	   DESC = The value of this object identifies \
	        the Local In-Channel Signaling Procedure \
	        that is used for this UNI logical \
	        port.  (Configuration);

	   HELP = The UNI logical port can \
	        be performing only user-to-network \
	        network-side procedures. \
	        Always u2nnet(1) for Release 1.1. \
	        This object has temporarily been assigned read-only \
	        access.  Read-write access will be assigned when \
	        other enumeration values are supported. ;
	   CAPABILITIES = ;"
     	::= { nvmFrMgtVCSigEntry 2 }

nvmFrMgtVCSigNetN392 OBJECT-TYPE
     	SYNTAX  INTEGER (1..10)
    	ACCESS  read-write
     	STATUS  mandatory
     	DESCRIPTION
          "NAME = ; 
	   DESC = The value of this object identifies \
	        the Network-side N392 error threshold \
	        value for this UNI logical port (nN2 for LMI). \
	         (Configuration);
	   HELP = If the logical port is not performing \
	        network-side procedures, then this value is \
	        equal to noSuchName. This object \
	        applies to Q.933 Annex A, T1.617 \
	        Annex D, and LMI.;
	   CAPABILITIES = ;"
     	DEFVAL { 3 }
     	::= { nvmFrMgtVCSigEntry 3}

nvmFrMgtVCSigNetN393 OBJECT-TYPE
	SYNTAX  INTEGER (1..10)
    	ACCESS  read-only
     	STATUS  mandatory
     	DESCRIPTION
       	  "NAME = ; 
	   DESC = The value of this object identifies \
	        the Network-side N393 monitored events \
	        count value for this UNI logical port \
	        (nN3 for LMI).  (Configuration);
	   HELP = If the logical port is not performing \
	        network-side procedures, then this value is equal \
	        to noSuchName. This object applies to Q.933 \
	        Annex A, T1.617 Annex D, and LMI. \
	        (Always set to value of N392 for Release 1.1. \
	        This object has temporarily been assigned read-only \
	        access.  Read-write access will be assigned when \
	        other values are supported.) ;
	   CAPABILITIES = ;"
     	DEFVAL { 3 }
     	::= { nvmFrMgtVCSigEntry 4 }

nvmFrMgtVCSigNetT392 OBJECT-TYPE
	SYNTAX  INTEGER (5..30)
     	ACCESS  read-write
     	STATUS  mandatory
     	DESCRIPTION
          "NAME = ; 
	   DESC = The value of this object identifies \
	        the Network-side T392 polling verification \
	        timer value for this UNI logical port \
	        (nT2 for LMI). (Configuration);
	   HELP =  This value is in seconds. \
	        If the logical port is not performing\
	        network-side procedures, \
	        then this value is equal to noSuchName. \
	        This object applies to Q.933 Annex A, \
	        T1.617 Annex D, and LMI;
	   CAPABILITIES = ;"
     	DEFVAL { 15 }
     	::= { nvmFrMgtVCSigEntry 5 }


-- The PVC End-Point Group (Configuration Parameters)

-- This table is used to identify the traffic parameters
-- for a bi-directional PVC segment end-point.
-- A PVC segment end-point is identified by a UNI
-- logical port index value and DLCI index value.
-- A user is able to modify PVC end-points via this table.
-- Entries into this table are automatically added and deleted
-- when the corresponding End-to-End Connection entries 
-- (see proprietary MIB file mcmfrdce.mib) are created
-- and deleted.

nvmFrPVCEndptTable OBJECT-TYPE
     	SYNTAX  SEQUENCE OF NvmFrPVCEndptEntry
    	ACCESS  not-accessible
     	STATUS  mandatory
     	DESCRIPTION
          "NAME = ; 
	   DESC = The Frame Relay PVC End-Point table. \
	        This table is used to model a PVC \
	        end-point. (Configuration);
	   HELP = This table contains the \
	        traffic parameters and statistics for \
		a PVC end-point.;
	   CAPABILITIES = NET_CFG, VPN_CFG;"
     	::= { rfc1604-configuration 6 }

nvmFrPVCEndptEntry OBJECT-TYPE
     	SYNTAX  NvmFrPVCEndptEntry
    	ACCESS  not-accessible
     	STATUS  mandatory
     	DESCRIPTION
          "NAME = ; 
	   DESC = An entry in the Frame Relay PVC End-point \
	        table. (Configuration);
	   HELP = ;
	   CAPABILITIES = ;"
     	INDEX   { nvmFrPVCEndptIfIndex, nvmFrPVCEndptDLCIIndex }
     	::= { nvmFrPVCEndptTable 1 }

NvmFrPVCEndptEntry ::= SEQUENCE {
	nvmFrPVCEndptIfIndex		INTEGER,
      	nvmFrPVCEndptDLCIIndex		INTEGER,
     	nvmFrPVCEndptInMaxFrameSize	INTEGER,
     	nvmFrPVCEndptInBc 		INTEGER,
       	nvmFrPVCEndptInBe 		INTEGER,
       	nvmFrPVCEndptInCIR		INTEGER,
      	nvmFrPVCEndptOutMaxFrameSize	INTEGER,
      	nvmFrPVCEndptOutBc		INTEGER,
    	nvmFrPVCEndptOutBe		INTEGER,
	nvmFrPVCEndptOutCIR		INTEGER
	}

nvmFrPVCEndptIfIndex OBJECT-TYPE
	SYNTAX	INTEGER (1..255)
	ACCESS	read-only
	STATUS	mandatory
	DESCRIPTION
	  "NAME = ;
	   DESC = The ifIndex of the local DCE interface. \
		  (Configuration);
	   HELP = (Analogous to the ifIndex pointer in the \
		  MIB II Interfaces Group but specific to \
		  the PVC end-point table.);
	   CAPABILITIES = ;"
	::= { nvmFrPVCEndptEntry 1 }

nvmFrPVCEndptDLCIIndex OBJECT-TYPE
     	SYNTAX	INTEGER (16..991)
    	ACCESS  read-only
     	STATUS  mandatory
     	DESCRIPTION
          "NAME = ;
	   DESC = The value of this object is equal to the \
	        DLCI value for this PVC end-point. (Configuration);
	   HELP = ;
	   CAPABILITIES = ;"
     	::= { nvmFrPVCEndptEntry 2 }

nvmFrPVCEndptInMaxFrameSize OBJECT-TYPE
     	SYNTAX	INTEGER (0..4096)
     	ACCESS  read-write
     	STATUS  mandatory
     	DESCRIPTION
          "NAME = ; 
	   DESC =  The largest frame relay information field \
	       in octets for this PVC end-point data sent \
	       into the network.  (Configuration);
	   HELP = The value must be \
	        less than or equal to the corresponding \
	        ifMtu (nvmFrPhyPortMtuSize) for this \
	        Frame Relay UNI logical port.;
	   CAPABILITIES = ;"
     	::= { nvmFrPVCEndptEntry 3 }

nvmFrPVCEndptInBc OBJECT-TYPE
     	SYNTAX 	INTEGER (0..2560000)
     	ACCESS  read-only
     	STATUS  mandatory
     	DESCRIPTION
          "NAME = ; 
	   DESC = The committed burst size (Bc) in bits \
	       for this PVC end-point data sent into \
	       frame relay network. (Configuration);
	   HELP = This object has temporarily \
	        been assigned read-only access.  Read-write \
	        access may be assigned in future \
	        releases.;
	   CAPABILITIES = ;"
     	::= { nvmFrPVCEndptEntry 4 }

nvmFrPVCEndptInBe OBJECT-TYPE
	SYNTAX 	INTEGER (0..2560000)
     	ACCESS  read-write
     	STATUS  mandatory
     	DESCRIPTION
          "NAME = ; 
	   DESC = The committed excess size (Be) in bits \
	       for this PVC end-point data sent into \
	       frame relay network. (Configuration);
	   HELP = ;
	   CAPABILITIES = ;"
     	::= { nvmFrPVCEndptEntry 5 }

nvmFrPVCEndptInCIR OBJECT-TYPE
	SYNTAX 	INTEGER (0..2560000)
     	ACCESS  read-write
     	STATUS  mandatory
     	DESCRIPTION
          "NAME = ; 
	   DESC = The committed information rate (CIR) in bits/sec \
	       for this PVC end-point data sent into \
	       frame relay network.(Configuration);
	   HELP = ;
	   CAPABILITIES = ;"
     	::= { nvmFrPVCEndptEntry 6 }

nvmFrPVCEndptOutMaxFrameSize OBJECT-TYPE
	SYNTAX	INTEGER (0..4096)
     	ACCESS  read-write
     	STATUS  mandatory
     	DESCRIPTION
          "NAME = ; 
	   DESC = The largest frame relay information field \
	       in octets for this PVC end-point data received \
	       from the network. (Configuration);
	   HELP =  The value must be \
	        less than or equal to the corresponding \
	        ifMtu (nvmFrPhyPortMtuSize) for this \
	        Frame Relay UNI logical port.;
	   CAPABILITIES = ;"
     	::= { nvmFrPVCEndptEntry 7 }

nvmFrPVCEndptOutBc OBJECT-TYPE
	SYNTAX 	INTEGER (0..2560000)
     	ACCESS  read-only
     	STATUS  mandatory
     	DESCRIPTION
          "NAME = ; 
	   DESC = The committed burst size (Bc) in bits \
	       for this PVC end-point data received from \
	       frame relay network. (Configuration);
	   HELP = This object has temporarily \
	        been assigned read-only access.  Read-write \
	        access may be assigned in future \
	        releases.;
	   CAPABILITIES = ;"
     	::= { nvmFrPVCEndptEntry 8 }

nvmFrPVCEndptOutBe OBJECT-TYPE
	SYNTAX 	INTEGER (0..2560000)
     	ACCESS  read-write
     	STATUS  mandatory
     	DESCRIPTION
          "NAME = ; 
	   DESC =  The committed excess size (Be) in bits \
	       for this PVC end-point data received from \
	       frame relay network. (Configuration);
	   HELP = ;
	   CAPABILITIES = ;"
     	::= { nvmFrPVCEndptEntry 9 }

nvmFrPVCEndptOutCIR OBJECT-TYPE
	SYNTAX 	INTEGER (0..2560000)
     	ACCESS  read-write
     	STATUS  mandatory
     	DESCRIPTION
          "NAME = ; 
	   DESC = The committed information rate (CIR) in bits/sec \
	       for this PVC end-point data received from \
	       frame relay network. (Configuration);
	   HELP = ;
	   CAPABILITIES = ;"
     	::= { nvmFrPVCEndptEntry 10 }



-- The Frame Relay DCE (Proprietary RFC 1604) Counter Reset Group

-- The FR Management VC Signaling Group Counter Reset Table

-- *** NOTE THAT BOTH THE mcmFrMgtVCSigCntrTable AND 
--     mcmFrPVCEndptCntrTable ARE OBSOLETE AND WILL
--     NO LONGER BE SUPPORTED IN RELEASE 3.0 AND 
--     BEYOND.

mcmFrMgtVCSigCntrTable OBJECT-TYPE
	SYNTAX  SEQUENCE OF McmFrMgtVCSigCntrEntry
	ACCESS  not-accessible
	STATUS  obsolete
	DESCRIPTION
	  "NAME = ;
	   DESC = The Frame Relay Management VC Signaling \
		  Parameters counter reset table.;
	   HELP = ;
	   CAPABILITIES = NET_OPER, VPN_OPER;"
	::= { rfc1604-control 1 }

mcmFrMgtVCSigCntrEntry OBJECT-TYPE
	SYNTAX  McmFrMgtVCSigCntrEntry
	ACCESS  not-accessible
	STATUS  obsolete
	DESCRIPTION
	  "NAME = ;
	   DESC = An entry in the Frame Relay Management VC \
		  Signaling Parameters counter reset table.;
	   HELP = ;
	   CAPABILITIES = ;"
	INDEX   { mcmFrMgtVCSigCntrIfIndex }
	::= { mcmFrMgtVCSigCntrTable 1 }

McmFrMgtVCSigCntrEntry ::= SEQUENCE {
	mcmFrMgtVCSigCntrIfIndex 	INTEGER,
	mcmFrMgtVCSigCntrAction 	INTEGER
	}

mcmFrMgtVCSigCntrIfIndex OBJECT-TYPE
	SYNTAX	INTEGER (1..255)
	ACCESS	read-only
	STATUS	obsolete
	DESCRIPTION
	  "NAME = ;
	   DESC = The ifIndex of the FR Management VC Signaling \
		  Parameters table. This index specifies \
		  the particular row of counter objects to \
		  be reset.;
	   HELP = ;
	   CAPABILITIES = ;"
	::= { mcmFrMgtVCSigCntrEntry 1 }

mcmFrMgtVCSigCntrAction OBJECT-TYPE
	SYNTAX  INTEGER { 
		reset (1) 
		}
	ACCESS	write-only
	STATUS  obsolete
	DESCRIPTION
	  "NAME = ;
	   DESC = Setting this object to reset(1) will \
		  zero the values of a specific row of \
		  counters in the FR Management VC \
		  Signaling Parameters table.;
	   HELP = When set to reset(1), a row containing \
		  the following counter objects are reset: \
		    mcmFrMgtVCSigNetLinkRelErrors \
		    mcmFrMgtVCSigNetProtErrors \
		    mcmFrMgtVCSigNetChanInactive;
	   CAPABILITIES = ;"
	::= { mcmFrMgtVCSigCntrEntry 2 }


-- The FR PVC End-Point Group Counter Reset Table

-- *** NOTE THAT BOTH THE mcmFrMgtVCSigCntrTable AND 
--     mcmFrPVCEndptCntrTable ARE OBSOLETE AND WILL
--     NO LONGER BE SUPPORTED IN RELEASE 3.0 AND 
--     BEYOND.

mcmFrPVCEndptCntrTable OBJECT-TYPE
	SYNTAX  SEQUENCE OF McmFrPVCEndptCntrEntry
	ACCESS  not-accessible
	STATUS  obsolete
	DESCRIPTION
	  "NAME = ;
	   DESC = The Frame Relay PVC End-Point Group \
		  counter reset table.;
	   HELP = ;
	   CAPABILITIES = NET_OPER, VPN_OPER;"
	::= { rfc1604-control 2 }

mcmFrPVCEndptCntrEntry OBJECT-TYPE
	SYNTAX  McmFrPVCEndptCntrEntry
	ACCESS  not-accessible
	STATUS  obsolete
	DESCRIPTION
	  "NAME = ;
	   DESC = An entry in the Frame Relay PVC End-Point \
		  Group counter reset table.;
	   HELP = ;
	   CAPABILITIES = ;"
	INDEX   { mcmFrPVCEndptCntrIfIndex, mcmFrPVCEndptCntrDLCIIndex }
	::= { mcmFrPVCEndptCntrTable 1 }

McmFrPVCEndptCntrEntry ::= SEQUENCE {
	mcmFrPVCEndptCntrIfIndex 	INTEGER,
	mcmFrPVCEndptCntrDLCIIndex 	INTEGER,
	mcmFrPVCEndptCntrAction 	INTEGER
	}

mcmFrPVCEndptCntrIfIndex OBJECT-TYPE
	SYNTAX	INTEGER
	ACCESS	read-only
	STATUS	obsolete
	DESCRIPTION
	  "NAME = ;
	   DESC = The ifIndex of the FR PVC End-Point \
		  table. This index (in conjunction with \
		  the DLCI index) specifies the particular \
		  row of counter objects to be reset.;
	   HELP = ;
	   CAPABILITIES = ;"
	::= { mcmFrPVCEndptCntrEntry 1 }

mcmFrPVCEndptCntrDLCIIndex OBJECT-TYPE
	SYNTAX	INTEGER
	ACCESS	read-only
	STATUS	obsolete
	DESCRIPTION
	  "NAME = ;
	   DESC = The DLCI Index of the FR PVC End-Point \
		  table. This index (in conjunction with \
		  the ifIndex) specifies the particular \
		  row of counter objects to be reset.;
	   HELP = ;
	   CAPABILITIES = ;"
	::= { mcmFrPVCEndptCntrEntry 2 }

mcmFrPVCEndptCntrAction OBJECT-TYPE
	SYNTAX  INTEGER { 
		reset (1) 
		}
	ACCESS	write-only
	STATUS  obsolete
	DESCRIPTION
	  "NAME = ;
	   DESC = Setting this object to reset(1) will \
		  zero the values of a specific row of \
		  counters in the FR PVC End-Point table;
	   HELP = When set to reset(1), a row containing \
		  the following counter objects are reset: \
		    mcmFrPVCEndptInFrames \
		    mcmFrPVCEndptOutFrames \
		    mcmFrPVCEndptInDEFrames \
		    mcmFrPVCEndptInExcessFrames \
		    mcmFrPVCEndptOutExcessFrames \
		    mcmFrPVCEndptInDiscards \
		    mcmFrPVCEndptInOctets \
		    mcmFrPVCEndptOutOctets;
	   CAPABILITIES = ;"
	::= { mcmFrPVCEndptCntrEntry 3 }


END
